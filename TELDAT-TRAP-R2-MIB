-- file automatically created


TELDAT-TRAP-R2-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


r2TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the R2 event subsystem."
    REVISION "201401200930Z"
    DESCRIPTION "Initial implementation"
        ::= { telEventTraps 100 }


r2EventsGroup	OBJECT IDENTIFIER	::= { r2TrapsMIB 1 }

r2Notifications	OBJECT IDENTIFIER	::= { r2TrapsMIB 2 }
r2NotificationsPrefix	OBJECT IDENTIFIER	::= { r2Notifications 0 }

r2EventObjects1 OBJECT-IDENTITY
    STATUS current
    DESCRIPTION
        "Event R2.1
        Message generated for each event received on the state machine that
        shows the effect produced."
    ::= { r2EventsGroup 1 }

r21_event OBJECT-TYPE
    SYNTAX DisplayString
    MAX-ACCESS accessible-for-notify
    STATUS current
    DESCRIPTION
        "Parameter 'event' in event R2.1"
    ::= { r2EventObjects1 1 }

r21_interface OBJECT-TYPE
    SYNTAX DisplayString
    MAX-ACCESS accessible-for-notify
    STATUS current
    DESCRIPTION
        "Parameter 'interface' in event R2.1"
    ::= { r2EventObjects1 2 }

r21_channel OBJECT-TYPE
    SYNTAX Integer32
    MAX-ACCESS accessible-for-notify
    STATUS current
    DESCRIPTION
        "Parameter 'channel' in event R2.1"
    ::= { r2EventObjects1 3 }

r2EventObjects2 OBJECT-IDENTITY
    STATUS current
    DESCRIPTION
        "Event R2.2
        Message generated for each change on multiframe alignment detection."
    ::= { r2EventsGroup 2 }

r22_message OBJECT-TYPE
    SYNTAX DisplayString
    MAX-ACCESS accessible-for-notify
    STATUS current
    DESCRIPTION
        "Parameter 'message' in event R2.2"
    ::= { r2EventObjects2 1 }

r22_interface OBJECT-TYPE
    SYNTAX DisplayString
    MAX-ACCESS accessible-for-notify
    STATUS current
    DESCRIPTION
        "Parameter 'interface' in event R2.2"
    ::= { r2EventObjects2 2 }

r22_channel OBJECT-TYPE
    SYNTAX Integer32
    MAX-ACCESS accessible-for-notify
    STATUS current
    DESCRIPTION
        "Parameter 'channel' in event R2.2"
    ::= { r2EventObjects2 3 }

r2EventObjects3 OBJECT-IDENTITY
    STATUS current
    DESCRIPTION
        "Event R2.3
        Message generated for each change on the alarm bit."
    ::= { r2EventsGroup 3 }

r23_message OBJECT-TYPE
    SYNTAX DisplayString
    MAX-ACCESS accessible-for-notify
    STATUS current
    DESCRIPTION
        "Parameter 'message' in event R2.3"
    ::= { r2EventObjects3 1 }

r23_interface OBJECT-TYPE
    SYNTAX DisplayString
    MAX-ACCESS accessible-for-notify
    STATUS current
    DESCRIPTION
        "Parameter 'interface' in event R2.3"
    ::= { r2EventObjects3 2 }

r23_channel OBJECT-TYPE
    SYNTAX Integer32
    MAX-ACCESS accessible-for-notify
    STATUS current
    DESCRIPTION
        "Parameter 'channel' in event R2.3"
    ::= { r2EventObjects3 3 }

r2EventObjects4 OBJECT-IDENTITY
    STATUS current
    DESCRIPTION
        "Event R2.4
        Command sent to the r2 api"
    ::= { r2EventsGroup 4 }

r24_command OBJECT-TYPE
    SYNTAX DisplayString
    MAX-ACCESS accessible-for-notify
    STATUS current
    DESCRIPTION
        "Parameter 'command' in event R2.4"
    ::= { r2EventObjects4 1 }

r24_interface OBJECT-TYPE
    SYNTAX DisplayString
    MAX-ACCESS accessible-for-notify
    STATUS current
    DESCRIPTION
        "Parameter 'interface' in event R2.4"
    ::= { r2EventObjects4 2 }

r24_channel OBJECT-TYPE
    SYNTAX Integer32
    MAX-ACCESS accessible-for-notify
    STATUS current
    DESCRIPTION
        "Parameter 'channel' in event R2.4"
    ::= { r2EventObjects4 3 }

r2EventObjects5 OBJECT-IDENTITY
    STATUS current
    DESCRIPTION
        "Event R2.5
        Error in r2 channel"
    ::= { r2EventsGroup 5 }

r25_error OBJECT-TYPE
    SYNTAX DisplayString
    MAX-ACCESS accessible-for-notify
    STATUS current
    DESCRIPTION
        "Parameter 'error' in event R2.5"
    ::= { r2EventObjects5 1 }

r25_context OBJECT-TYPE
    SYNTAX DisplayString
    MAX-ACCESS accessible-for-notify
    STATUS current
    DESCRIPTION
        "Parameter 'context' in event R2.5"
    ::= { r2EventObjects5 2 }

r25_interface OBJECT-TYPE
    SYNTAX DisplayString
    MAX-ACCESS accessible-for-notify
    STATUS current
    DESCRIPTION
        "Parameter 'interface' in event R2.5"
    ::= { r2EventObjects5 3 }

r25_channel OBJECT-TYPE
    SYNTAX Integer32
    MAX-ACCESS accessible-for-notify
    STATUS current
    DESCRIPTION
        "Parameter 'channel' in event R2.5"
    ::= { r2EventObjects5 4 }

r2EventObjects6 OBJECT-IDENTITY
    STATUS current
    DESCRIPTION
        "Event R2.6
        Phase changed in mfc r2 protocol"
    ::= { r2EventsGroup 6 }

r26_old_state OBJECT-TYPE
    SYNTAX DisplayString
    MAX-ACCESS accessible-for-notify
    STATUS current
    DESCRIPTION
        "Parameter 'old_state' in event R2.6"
    ::= { r2EventObjects6 1 }

r26_new_state OBJECT-TYPE
    SYNTAX DisplayString
    MAX-ACCESS accessible-for-notify
    STATUS current
    DESCRIPTION
        "Parameter 'new_state' in event R2.6"
    ::= { r2EventObjects6 2 }

r26_interface OBJECT-TYPE
    SYNTAX DisplayString
    MAX-ACCESS accessible-for-notify
    STATUS current
    DESCRIPTION
        "Parameter 'interface' in event R2.6"
    ::= { r2EventObjects6 3 }

r26_channel OBJECT-TYPE
    SYNTAX Integer32
    MAX-ACCESS accessible-for-notify
    STATUS current
    DESCRIPTION
        "Parameter 'channel' in event R2.6"
    ::= { r2EventObjects6 4 }

r2EventObjects7 OBJECT-IDENTITY
    STATUS current
    DESCRIPTION
        "Event R2.7
        Phase changed in mfc r2 protocol"
    ::= { r2EventsGroup 7 }

r27_old_state OBJECT-TYPE
    SYNTAX DisplayString
    MAX-ACCESS accessible-for-notify
    STATUS current
    DESCRIPTION
        "Parameter 'old_state' in event R2.7"
    ::= { r2EventObjects7 1 }

r27_new_state OBJECT-TYPE
    SYNTAX DisplayString
    MAX-ACCESS accessible-for-notify
    STATUS current
    DESCRIPTION
        "Parameter 'new_state' in event R2.7"
    ::= { r2EventObjects7 2 }

r27_interface OBJECT-TYPE
    SYNTAX DisplayString
    MAX-ACCESS accessible-for-notify
    STATUS current
    DESCRIPTION
        "Parameter 'interface' in event R2.7"
    ::= { r2EventObjects7 3 }

r27_channel OBJECT-TYPE
    SYNTAX Integer32
    MAX-ACCESS accessible-for-notify
    STATUS current
    DESCRIPTION
        "Parameter 'channel' in event R2.7"
    ::= { r2EventObjects7 4 }

r2EventObjects8 OBJECT-IDENTITY
    STATUS current
    DESCRIPTION
        "Event R2.8
        MFC signal sent or received"
    ::= { r2EventsGroup 8 }

r28_signal OBJECT-TYPE
    SYNTAX Integer32
    MAX-ACCESS accessible-for-notify
    STATUS current
    DESCRIPTION
        "Parameter 'signal' in event R2.8"
    ::= { r2EventObjects8 1 }

r28_received OBJECT-TYPE
    SYNTAX DisplayString
    MAX-ACCESS accessible-for-notify
    STATUS current
    DESCRIPTION
        "Parameter 'received' in event R2.8"
    ::= { r2EventObjects8 2 }

r28_interface OBJECT-TYPE
    SYNTAX DisplayString
    MAX-ACCESS accessible-for-notify
    STATUS current
    DESCRIPTION
        "Parameter 'interface' in event R2.8"
    ::= { r2EventObjects8 3 }

r28_channel OBJECT-TYPE
    SYNTAX Integer32
    MAX-ACCESS accessible-for-notify
    STATUS current
    DESCRIPTION
        "Parameter 'channel' in event R2.8"
    ::= { r2EventObjects8 4 }

r2EventObjects9 OBJECT-IDENTITY
    STATUS current
    DESCRIPTION
        "Event R2.9
        MFC signal sent or received"
    ::= { r2EventsGroup 9 }

r29_received OBJECT-TYPE
    SYNTAX DisplayString
    MAX-ACCESS accessible-for-notify
    STATUS current
    DESCRIPTION
        "Parameter 'received' in event R2.9"
    ::= { r2EventObjects9 1 }

r29_a OBJECT-TYPE
    SYNTAX DisplayString
    MAX-ACCESS accessible-for-notify
    STATUS current
    DESCRIPTION
        "Parameter 'a' in event R2.9"
    ::= { r2EventObjects9 2 }

r29_b OBJECT-TYPE
    SYNTAX DisplayString
    MAX-ACCESS accessible-for-notify
    STATUS current
    DESCRIPTION
        "Parameter 'b' in event R2.9"
    ::= { r2EventObjects9 3 }

r29_c OBJECT-TYPE
    SYNTAX DisplayString
    MAX-ACCESS accessible-for-notify
    STATUS current
    DESCRIPTION
        "Parameter 'c' in event R2.9"
    ::= { r2EventObjects9 4 }

r29_d OBJECT-TYPE
    SYNTAX DisplayString
    MAX-ACCESS accessible-for-notify
    STATUS current
    DESCRIPTION
        "Parameter 'd' in event R2.9"
    ::= { r2EventObjects9 5 }

r29_interface OBJECT-TYPE
    SYNTAX DisplayString
    MAX-ACCESS accessible-for-notify
    STATUS current
    DESCRIPTION
        "Parameter 'interface' in event R2.9"
    ::= { r2EventObjects9 6 }

r29_channel OBJECT-TYPE
    SYNTAX Integer32
    MAX-ACCESS accessible-for-notify
    STATUS current
    DESCRIPTION
        "Parameter 'channel' in event R2.9"
    ::= { r2EventObjects9 7 }


r2Notification1 NOTIFICATION-TYPE
    OBJECTS { 
              r21_event, 
              r21_interface,
              r21_channel 
            }
    STATUS current
    DESCRIPTION
        "Notification of Event R2.1

        Message: 'Event received on state machine: $1 on $2$3'

        Parameters list:
              $1: r21_event
              $2: r21_interface
              $3: r21_channel

        Message generated for each event received on the state machine that
        shows the effect produced."
    ::= { r2NotificationsPrefix 1 }

r2Notification2 NOTIFICATION-TYPE
    OBJECTS { 
              r22_message, 
              r22_interface,
              r22_channel 
            }
    STATUS current
    DESCRIPTION
        "Notification of Event R2.2

        Message: 'Multiframe alignment change detected: $1 on $2:$3'

        Parameters list:
              $1: r22_message
              $2: r22_interface
              $3: r22_channel

        Message generated for each change on multiframe alignment detection."
    ::= { r2NotificationsPrefix 2 }

r2Notification3 NOTIFICATION-TYPE
    OBJECTS { 
              r23_message, 
              r23_interface,
              r23_channel 
            }
    STATUS current
    DESCRIPTION
        "Notification of Event R2.3

        Message: 'Alarm: $1 on $2:$3'

        Parameters list:
              $1: r23_message
              $2: r23_interface
              $3: r23_channel

        Message generated for each change on the alarm bit."
    ::= { r2NotificationsPrefix 3 }

r2Notification4 NOTIFICATION-TYPE
    OBJECTS { 
              r24_command, 
              r24_interface,
              r24_channel 
            }
    STATUS current
    DESCRIPTION
        "Notification of Event R2.4

        Message: 'Command: $1 sent to $2:$3'

        Parameters list:
              $1: r24_command
              $2: r24_interface
              $3: r24_channel

        Command sent to the r2 api"
    ::= { r2NotificationsPrefix 4 }

r2Notification5 NOTIFICATION-TYPE
    OBJECTS { 
              r25_error, 
              r25_context,
              r25_interface,
              r25_channel 
            }
    STATUS current
    DESCRIPTION
        "Notification of Event R2.5

        Message: 'Error $1 context $2 on $3:$4'

        Parameters list:
              $1: r25_error
              $2: r25_context
              $3: r25_interface
              $4: r25_channel

        Error in r2 channel"
    ::= { r2NotificationsPrefix 5 }

r2Notification6 NOTIFICATION-TYPE
    OBJECTS { 
              r26_old_state, 
              r26_new_state,
              r26_interface,
              r26_channel 
            }
    STATUS current
    DESCRIPTION
        "Notification of Event R2.6

        Message: 'MFC phase change $1->$2 on $3:$4'

        Parameters list:
              $1: r26_old_state
              $2: r26_new_state
              $3: r26_interface
              $4: r26_channel

        Phase changed in mfc r2 protocol"
    ::= { r2NotificationsPrefix 6 }

r2Notification7 NOTIFICATION-TYPE
    OBJECTS { 
              r27_old_state, 
              r27_new_state,
              r27_interface,
              r27_channel 
            }
    STATUS current
    DESCRIPTION
        "Notification of Event R2.7

        Message: 'MFC state change $1->$2 on $3:$4'

        Parameters list:
              $1: r27_old_state
              $2: r27_new_state
              $3: r27_interface
              $4: r27_channel

        Phase changed in mfc r2 protocol"
    ::= { r2NotificationsPrefix 7 }

r2Notification8 NOTIFICATION-TYPE
    OBJECTS { 
              r28_signal, 
              r28_received,
              r28_interface,
              r28_channel 
            }
    STATUS current
    DESCRIPTION
        "Notification of Event R2.8

        Message: 'MFC $1 signal $2 on $3:$4'

        Parameters list:
              $1: r28_signal
              $2: r28_received
              $3: r28_interface
              $4: r28_channel

        MFC signal sent or received"
    ::= { r2NotificationsPrefix 8 }

r2Notification9 NOTIFICATION-TYPE
    OBJECTS { 
              r29_received, 
              r29_a,
              r29_b,
              r29_c,
              r29_d,
              r29_interface,
              r29_channel 
            }
    STATUS current
    DESCRIPTION
        "Notification of Event R2.9

        Message: 'ABCD signal $1 $2$3$4$5 on $6:$7'

        Parameters list:
              $1: r29_received
              $2: r29_a
              $3: r29_b
              $4: r29_c
              $5: r29_d
              $6: r29_interface
              $7: r29_channel

        MFC signal sent or received"
    ::= { r2NotificationsPrefix 9 }


END
