-- file automatically created


TELDAT-TRAP-WWAN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


wwanTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the WWAN event subsystem."
    REVISION "201401200930Z"
    DESCRIPTION "Initial implementation"
        ::= { telEventTraps 211 }


wwanEventsGroup	OBJECT IDENTIFIER	::= { wwanTrapsMIB 1 }

wwanNotifications	OBJECT IDENTIFIER	::= { wwanTrapsMIB 2 }
wwanNotificationsPrefix	OBJECT IDENTIFIER	::= { wwanNotifications 0 }

wwanEventObjects1 OBJECT-IDENTITY
    STATUS current
    DESCRIPTION
        "Event WWAN.1
        Generic informational event."
    ::= { wwanEventsGroup 1 }

wwan1_info_string OBJECT-TYPE
    SYNTAX DisplayString
    MAX-ACCESS accessible-for-notify
    STATUS current
    DESCRIPTION
        "Parameter 'info_string' in event WWAN.1"
    ::= { wwanEventObjects1 1 }

wwan1_ifcname OBJECT-TYPE
    SYNTAX DisplayString
    MAX-ACCESS accessible-for-notify
    STATUS current
    DESCRIPTION
        "Parameter 'ifcname' in event WWAN.1"
    ::= { wwanEventObjects1 2 }

wwanEventObjects2 OBJECT-IDENTITY
    STATUS current
    DESCRIPTION
        "Event WWAN.2
        Generic error report."
    ::= { wwanEventsGroup 2 }

wwan2_error_string OBJECT-TYPE
    SYNTAX DisplayString
    MAX-ACCESS accessible-for-notify
    STATUS current
    DESCRIPTION
        "Parameter 'error_string' in event WWAN.2"
    ::= { wwanEventObjects2 1 }

wwan2_ifcname OBJECT-TYPE
    SYNTAX DisplayString
    MAX-ACCESS accessible-for-notify
    STATUS current
    DESCRIPTION
        "Parameter 'ifcname' in event WWAN.2"
    ::= { wwanEventObjects2 2 }

wwanEventObjects3 OBJECT-IDENTITY
    STATUS current
    DESCRIPTION
        "Event WWAN.3
        Registration state has changed."
    ::= { wwanEventsGroup 3 }

wwan3_state OBJECT-TYPE
    SYNTAX DisplayString
    MAX-ACCESS accessible-for-notify
    STATUS current
    DESCRIPTION
        "Parameter 'state' in event WWAN.3"
    ::= { wwanEventObjects3 1 }

wwan3_ifcname OBJECT-TYPE
    SYNTAX DisplayString
    MAX-ACCESS accessible-for-notify
    STATUS current
    DESCRIPTION
        "Parameter 'ifcname' in event WWAN.3"
    ::= { wwanEventObjects3 2 }

wwanEventObjects4 OBJECT-IDENTITY
    STATUS current
    DESCRIPTION
        "Event WWAN.4
        The wireless wan interface now uses a different Public Land Mobile Network,
        (Mobile Operator) identified by the number displayed."
    ::= { wwanEventsGroup 4 }

wwan4_operator OBJECT-TYPE
    SYNTAX Integer32
    MAX-ACCESS accessible-for-notify
    STATUS current
    DESCRIPTION
        "Parameter 'operator' in event WWAN.4"
    ::= { wwanEventObjects4 1 }

wwan4_ifcname OBJECT-TYPE
    SYNTAX DisplayString
    MAX-ACCESS accessible-for-notify
    STATUS current
    DESCRIPTION
        "Parameter 'ifcname' in event WWAN.4"
    ::= { wwanEventObjects4 2 }

wwanEventObjects5 OBJECT-IDENTITY
    STATUS current
    DESCRIPTION
        "Event WWAN.5
        The wireless wan interface is connected to a different base station,
        identified by the Location Area Code (LAC) and the Cell Identifier code
        (CiD)."
    ::= { wwanEventsGroup 5 }

wwan5_location_area_code OBJECT-TYPE
    SYNTAX Integer32
    MAX-ACCESS accessible-for-notify
    STATUS current
    DESCRIPTION
        "Parameter 'location_area_code' in event WWAN.5"
    ::= { wwanEventObjects5 1 }

wwan5_cell_id OBJECT-TYPE
    SYNTAX Integer32
    MAX-ACCESS accessible-for-notify
    STATUS current
    DESCRIPTION
        "Parameter 'cell_id' in event WWAN.5"
    ::= { wwanEventObjects5 2 }

wwan5_ifcname OBJECT-TYPE
    SYNTAX DisplayString
    MAX-ACCESS accessible-for-notify
    STATUS current
    DESCRIPTION
        "Parameter 'ifcname' in event WWAN.5"
    ::= { wwanEventObjects5 3 }

wwanEventObjects6 OBJECT-IDENTITY
    STATUS current
    DESCRIPTION
        "Event WWAN.6
        Notify a change of the used wireless wan technology, which implies different
        radio bands, coding methods and therefore different data rates."
    ::= { wwanEventsGroup 6 }

wwan6_technology OBJECT-TYPE
    SYNTAX DisplayString
    MAX-ACCESS accessible-for-notify
    STATUS current
    DESCRIPTION
        "Parameter 'technology' in event WWAN.6"
    ::= { wwanEventObjects6 1 }

wwan6_ifcname OBJECT-TYPE
    SYNTAX DisplayString
    MAX-ACCESS accessible-for-notify
    STATUS current
    DESCRIPTION
        "Parameter 'ifcname' in event WWAN.6"
    ::= { wwanEventObjects6 2 }

wwanEventObjects7 OBJECT-IDENTITY
    STATUS current
    DESCRIPTION
        "Event WWAN.7
        Received Signal Strength Indication (RSSI) changed to the level
        displayed. This event depends of user's configuration thresholds and
        appears only if the used technology is GSM or GPRS."
    ::= { wwanEventsGroup 7 }

wwan7_rssi_level OBJECT-TYPE
    SYNTAX Integer32
    MAX-ACCESS accessible-for-notify
    STATUS current
    DESCRIPTION
        "Parameter 'rssi_level' in event WWAN.7"
    ::= { wwanEventObjects7 1 }

wwan7_ifcname OBJECT-TYPE
    SYNTAX DisplayString
    MAX-ACCESS accessible-for-notify
    STATUS current
    DESCRIPTION
        "Parameter 'ifcname' in event WWAN.7"
    ::= { wwanEventObjects7 2 }

wwanEventObjects8 OBJECT-IDENTITY
    STATUS current
    DESCRIPTION
        "Event WWAN.8
        Received Signal Code Power (RSCP) has changed to the level displayed or
        the EcNo ratio (received energy per chip divided by the power density in
        the band) has changed to the value displayed. This event depends of
        user's configuration thresholds and appears only if the used technology
        is UMTS, HSDPA or CDMA."
    ::= { wwanEventsGroup 8 }

wwan8_rscp_level OBJECT-TYPE
    SYNTAX Integer32
    MAX-ACCESS accessible-for-notify
    STATUS current
    DESCRIPTION
        "Parameter 'rscp_level' in event WWAN.8"
    ::= { wwanEventObjects8 1 }

wwan8_ecno_level OBJECT-TYPE
    SYNTAX Integer32
    MAX-ACCESS accessible-for-notify
    STATUS current
    DESCRIPTION
        "Parameter 'ecno_level' in event WWAN.8"
    ::= { wwanEventObjects8 2 }

wwan8_ifcname OBJECT-TYPE
    SYNTAX DisplayString
    MAX-ACCESS accessible-for-notify
    STATUS current
    DESCRIPTION
        "Parameter 'ifcname' in event WWAN.8"
    ::= { wwanEventObjects8 3 }

wwanEventObjects9 OBJECT-IDENTITY
    STATUS current
    DESCRIPTION
        "Event WWAN.9
        Active SIM is placed in the displayed socked."
    ::= { wwanEventsGroup 9 }

wwan9_sim_socket OBJECT-TYPE
    SYNTAX DisplayString
    MAX-ACCESS accessible-for-notify
    STATUS current
    DESCRIPTION
        "Parameter 'sim_socket' in event WWAN.9"
    ::= { wwanEventObjects9 1 }

wwan9_ifcname OBJECT-TYPE
    SYNTAX DisplayString
    MAX-ACCESS accessible-for-notify
    STATUS current
    DESCRIPTION
        "Parameter 'ifcname' in event WWAN.9"
    ::= { wwanEventObjects9 2 }

wwanEventObjects10 OBJECT-IDENTITY
    STATUS current
    DESCRIPTION
        "Event WWAN.10
        Interface call stated changed to the state displayed"
    ::= { wwanEventsGroup 10 }

wwan10_call_state_string OBJECT-TYPE
    SYNTAX DisplayString
    MAX-ACCESS accessible-for-notify
    STATUS current
    DESCRIPTION
        "Parameter 'call_state_string' in event WWAN.10"
    ::= { wwanEventObjects10 1 }

wwan10_call_state_num OBJECT-TYPE
    SYNTAX Integer32
    MAX-ACCESS accessible-for-notify
    STATUS current
    DESCRIPTION
        "Parameter 'call_state_num' in event WWAN.10"
    ::= { wwanEventObjects10 2 }

wwan10_ifcname OBJECT-TYPE
    SYNTAX DisplayString
    MAX-ACCESS accessible-for-notify
    STATUS current
    DESCRIPTION
        "Parameter 'ifcname' in event WWAN.10"
    ::= { wwanEventObjects10 3 }

wwanEventObjects11 OBJECT-IDENTITY
    STATUS current
    DESCRIPTION
        "Event WWAN.11
        A successful upgrade has been done to the displayed release"
    ::= { wwanEventsGroup 11 }

wwan11_frmwr_release OBJECT-TYPE
    SYNTAX DisplayString
    MAX-ACCESS accessible-for-notify
    STATUS current
    DESCRIPTION
        "Parameter 'frmwr_release' in event WWAN.11"
    ::= { wwanEventObjects11 1 }

wwan11_ifcname OBJECT-TYPE
    SYNTAX DisplayString
    MAX-ACCESS accessible-for-notify
    STATUS current
    DESCRIPTION
        "Parameter 'ifcname' in event WWAN.11"
    ::= { wwanEventObjects11 2 }

wwanEventObjects12 OBJECT-IDENTITY
    STATUS current
    DESCRIPTION
        "Event WWAN.12
        Current SIM is the configured as main"
    ::= { wwanEventsGroup 12 }

wwan12_sim_socket OBJECT-TYPE
    SYNTAX DisplayString
    MAX-ACCESS accessible-for-notify
    STATUS current
    DESCRIPTION
        "Parameter 'sim_socket' in event WWAN.12"
    ::= { wwanEventObjects12 1 }

wwan12_ifcname OBJECT-TYPE
    SYNTAX DisplayString
    MAX-ACCESS accessible-for-notify
    STATUS current
    DESCRIPTION
        "Parameter 'ifcname' in event WWAN.12"
    ::= { wwanEventObjects12 2 }

wwanEventObjects13 OBJECT-IDENTITY
    STATUS current
    DESCRIPTION
        "Event WWAN.13
        Current SIM is the configured as backup."
    ::= { wwanEventsGroup 13 }

wwan13_sim_socket OBJECT-TYPE
    SYNTAX DisplayString
    MAX-ACCESS accessible-for-notify
    STATUS current
    DESCRIPTION
        "Parameter 'sim_socket' in event WWAN.13"
    ::= { wwanEventObjects13 1 }

wwan13_ifcname OBJECT-TYPE
    SYNTAX DisplayString
    MAX-ACCESS accessible-for-notify
    STATUS current
    DESCRIPTION
        "Parameter 'ifcname' in event WWAN.13"
    ::= { wwanEventObjects13 2 }

wwanEventObjects14 OBJECT-IDENTITY
    STATUS current
    DESCRIPTION
        "Event WWAN.14
        A switching criteria is met and backup SIM is activated"
    ::= { wwanEventsGroup 14 }

wwan14_criteria OBJECT-TYPE
    SYNTAX DisplayString
    MAX-ACCESS accessible-for-notify
    STATUS current
    DESCRIPTION
        "Parameter 'criteria' in event WWAN.14"
    ::= { wwanEventObjects14 1 }

wwan14_sim_socket OBJECT-TYPE
    SYNTAX DisplayString
    MAX-ACCESS accessible-for-notify
    STATUS current
    DESCRIPTION
        "Parameter 'sim_socket' in event WWAN.14"
    ::= { wwanEventObjects14 2 }

wwan14_ifcname OBJECT-TYPE
    SYNTAX DisplayString
    MAX-ACCESS accessible-for-notify
    STATUS current
    DESCRIPTION
        "Parameter 'ifcname' in event WWAN.14"
    ::= { wwanEventObjects14 3 }

wwanEventObjects15 OBJECT-IDENTITY
    STATUS current
    DESCRIPTION
        "Event WWAN.15
        A return criteria is met and main SIM is activated"
    ::= { wwanEventsGroup 15 }

wwan15_criteria OBJECT-TYPE
    SYNTAX DisplayString
    MAX-ACCESS accessible-for-notify
    STATUS current
    DESCRIPTION
        "Parameter 'criteria' in event WWAN.15"
    ::= { wwanEventObjects15 1 }

wwan15_sim_socket OBJECT-TYPE
    SYNTAX DisplayString
    MAX-ACCESS accessible-for-notify
    STATUS current
    DESCRIPTION
        "Parameter 'sim_socket' in event WWAN.15"
    ::= { wwanEventObjects15 2 }

wwan15_ifcname OBJECT-TYPE
    SYNTAX DisplayString
    MAX-ACCESS accessible-for-notify
    STATUS current
    DESCRIPTION
        "Parameter 'ifcname' in event WWAN.15"
    ::= { wwanEventObjects15 3 }

wwanEventObjects16 OBJECT-IDENTITY
    STATUS current
    DESCRIPTION
        "Event WWAN.16
        A error is found and reported during SIM management"
    ::= { wwanEventsGroup 16 }

wwan16_error OBJECT-TYPE
    SYNTAX DisplayString
    MAX-ACCESS accessible-for-notify
    STATUS current
    DESCRIPTION
        "Parameter 'error' in event WWAN.16"
    ::= { wwanEventObjects16 1 }

wwan16_ifcname OBJECT-TYPE
    SYNTAX DisplayString
    MAX-ACCESS accessible-for-notify
    STATUS current
    DESCRIPTION
        "Parameter 'ifcname' in event WWAN.16"
    ::= { wwanEventObjects16 2 }


wwanNotification1 NOTIFICATION-TYPE
    OBJECTS { 
              wwan1_info_string, 
              wwan1_ifcname 
            }
    STATUS current
    DESCRIPTION
        "Notification of Event WWAN.1

        Message: '$1 intf $2'

        Parameters list:
              $1: wwan1_info_string
              $2: wwan1_ifcname

        Generic informational event."
    ::= { wwanNotificationsPrefix 1 }

wwanNotification2 NOTIFICATION-TYPE
    OBJECTS { 
              wwan2_error_string, 
              wwan2_ifcname 
            }
    STATUS current
    DESCRIPTION
        "Notification of Event WWAN.2

        Message: '$1 intf $2'

        Parameters list:
              $1: wwan2_error_string
              $2: wwan2_ifcname

        Generic error report."
    ::= { wwanNotificationsPrefix 2 }

wwanNotification3 NOTIFICATION-TYPE
    OBJECTS { 
              wwan3_state, 
              wwan3_ifcname 
            }
    STATUS current
    DESCRIPTION
        "Notification of Event WWAN.3

        Message: 'CHANGED Registration state to $1, on interface $2'

        Parameters list:
              $1: wwan3_state
              $2: wwan3_ifcname

        Registration state has changed."
    ::= { wwanNotificationsPrefix 3 }

wwanNotification4 NOTIFICATION-TYPE
    OBJECTS { 
              wwan4_operator, 
              wwan4_ifcname 
            }
    STATUS current
    DESCRIPTION
        "Notification of Event WWAN.4

        Message: 'CHANGED PLMN to $1, on interface $2'

        Parameters list:
              $1: wwan4_operator
              $2: wwan4_ifcname

        The wireless wan interface now uses a different Public Land Mobile Network,
        (Mobile Operator) identified by the number displayed."
    ::= { wwanNotificationsPrefix 4 }

wwanNotification5 NOTIFICATION-TYPE
    OBJECTS { 
              wwan5_location_area_code, 
              wwan5_cell_id,
              wwan5_ifcname 
            }
    STATUS current
    DESCRIPTION
        "Notification of Event WWAN.5

        Message: 'CHANGE Connected cell LAC $1 WWAN ID $2, on interface $3'

        Parameters list:
              $1: wwan5_location_area_code
              $2: wwan5_cell_id
              $3: wwan5_ifcname

        The wireless wan interface is connected to a different base station,
        identified by the Location Area Code (LAC) and the Cell Identifier code
        (CiD)."
    ::= { wwanNotificationsPrefix 5 }

wwanNotification6 NOTIFICATION-TYPE
    OBJECTS { 
              wwan6_technology, 
              wwan6_ifcname 
            }
    STATUS current
    DESCRIPTION
        "Notification of Event WWAN.6

        Message: 'CHANGED wireless wan technology to $1, on interface $2'

        Parameters list:
              $1: wwan6_technology
              $2: wwan6_ifcname

        Notify a change of the used wireless wan technology, which implies different
        radio bands, coding methods and therefore different data rates."
    ::= { wwanNotificationsPrefix 6 }

wwanNotification7 NOTIFICATION-TYPE
    OBJECTS { 
              wwan7_rssi_level, 
              wwan7_ifcname 
            }
    STATUS current
    DESCRIPTION
        "Notification of Event WWAN.7

        Message: 'CHANGED GSM/GPRS Coverage, RSSI $1 dBm, on interface $2'

        Parameters list:
              $1: wwan7_rssi_level
              $2: wwan7_ifcname

        Received Signal Strength Indication (RSSI) changed to the level
        displayed. This event depends of user's configuration thresholds and
        appears only if the used technology is GSM or GPRS."
    ::= { wwanNotificationsPrefix 7 }

wwanNotification8 NOTIFICATION-TYPE
    OBJECTS { 
              wwan8_rscp_level, 
              wwan8_ecno_level,
              wwan8_ifcname 
            }
    STATUS current
    DESCRIPTION
        "Notification of Event WWAN.8

        Message: 'CHANGED 3GPP Coverage, RSCP to $1 dBm and EcNo to $2 dB, on interface $3'

        Parameters list:
              $1: wwan8_rscp_level
              $2: wwan8_ecno_level
              $3: wwan8_ifcname

        Received Signal Code Power (RSCP) has changed to the level displayed or
        the EcNo ratio (received energy per chip divided by the power density in
        the band) has changed to the value displayed. This event depends of
        user's configuration thresholds and appears only if the used technology
        is UMTS, HSDPA or CDMA."
    ::= { wwanNotificationsPrefix 8 }

wwanNotification9 NOTIFICATION-TYPE
    OBJECTS { 
              wwan9_sim_socket, 
              wwan9_ifcname 
            }
    STATUS current
    DESCRIPTION
        "Notification of Event WWAN.9

        Message: 'CHANGED Used SIM. Used SIM is located in the $1 socket, on interface $2'

        Parameters list:
              $1: wwan9_sim_socket
              $2: wwan9_ifcname

        Active SIM is placed in the displayed socked."
    ::= { wwanNotificationsPrefix 9 }

wwanNotification10 NOTIFICATION-TYPE
    OBJECTS { 
              wwan10_call_state_string, 
              wwan10_call_state_num,
              wwan10_ifcname 
            }
    STATUS current
    DESCRIPTION
        "Notification of Event WWAN.10

        Message: 'CHANGED Call state to $1 ($2), on interface $3'

        Parameters list:
              $1: wwan10_call_state_string
              $2: wwan10_call_state_num
              $3: wwan10_ifcname

        Interface call stated changed to the state displayed"
    ::= { wwanNotificationsPrefix 10 }

wwanNotification11 NOTIFICATION-TYPE
    OBJECTS { 
              wwan11_frmwr_release, 
              wwan11_ifcname 
            }
    STATUS current
    DESCRIPTION
        "Notification of Event WWAN.11

        Message: 'CHANGED wireless wan module firmware to release $1, on interface $2'

        Parameters list:
              $1: wwan11_frmwr_release
              $2: wwan11_ifcname

        A successful upgrade has been done to the displayed release"
    ::= { wwanNotificationsPrefix 11 }

wwanNotification12 NOTIFICATION-TYPE
    OBJECTS { 
              wwan12_sim_socket, 
              wwan12_ifcname 
            }
    STATUS current
    DESCRIPTION
        "Notification of Event WWAN.12

        Message: 'Main SIM is $1 and now is active, on interface $2'

        Parameters list:
              $1: wwan12_sim_socket
              $2: wwan12_ifcname

        Current SIM is the configured as main"
    ::= { wwanNotificationsPrefix 12 }

wwanNotification13 NOTIFICATION-TYPE
    OBJECTS { 
              wwan13_sim_socket, 
              wwan13_ifcname 
            }
    STATUS current
    DESCRIPTION
        "Notification of Event WWAN.13

        Message: 'Backup SIM is $1, and now is active, on interface $2'

        Parameters list:
              $1: wwan13_sim_socket
              $2: wwan13_ifcname

        Current SIM is the configured as backup."
    ::= { wwanNotificationsPrefix 13 }

wwanNotification14 NOTIFICATION-TYPE
    OBJECTS { 
              wwan14_criteria, 
              wwan14_sim_socket,
              wwan14_ifcname 
            }
    STATUS current
    DESCRIPTION
        "Notification of Event WWAN.14

        Message: 'Switching criteria $1 is met. Switching to backup SIM ($2), on interface $3'

        Parameters list:
              $1: wwan14_criteria
              $2: wwan14_sim_socket
              $3: wwan14_ifcname

        A switching criteria is met and backup SIM is activated"
    ::= { wwanNotificationsPrefix 14 }

wwanNotification15 NOTIFICATION-TYPE
    OBJECTS { 
              wwan15_criteria, 
              wwan15_sim_socket,
              wwan15_ifcname 
            }
    STATUS current
    DESCRIPTION
        "Notification of Event WWAN.15

        Message: 'Return criteria $1 is met. Switching to main SIM ($2), on interface $3'

        Parameters list:
              $1: wwan15_criteria
              $2: wwan15_sim_socket
              $3: wwan15_ifcname

        A return criteria is met and main SIM is activated"
    ::= { wwanNotificationsPrefix 15 }

wwanNotification16 NOTIFICATION-TYPE
    OBJECTS { 
              wwan16_error, 
              wwan16_ifcname 
            }
    STATUS current
    DESCRIPTION
        "Notification of Event WWAN.16

        Message: 'SIM Management error $1, on interface $2'

        Parameters list:
              $1: wwan16_error
              $2: wwan16_ifcname

        A error is found and reported during SIM management"
    ::= { wwanNotificationsPrefix 16 }


END
