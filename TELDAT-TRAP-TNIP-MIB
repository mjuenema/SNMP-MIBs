-- file automatically created


TELDAT-TRAP-TNIP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tnipTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TNIP event subsystem."
    REVISION "201401200930Z"
    DESCRIPTION "Initial implementation"
        ::= { telEventTraps 120 }


tnipEventsGroup	OBJECT IDENTIFIER	::= { tnipTrapsMIB 1 }

tnipNotifications	OBJECT IDENTIFIER	::= { tnipTrapsMIB 2 }
tnipNotificationsPrefix	OBJECT IDENTIFIER	::= { tnipNotifications 0 }

tnipEventObjects1 OBJECT-IDENTITY
    STATUS current
    DESCRIPTION
        "Event TNIP.1
        An encapsulated packet for an external protocol was received on
        an interface to be desencapsulated."
    ::= { tnipEventsGroup 1 }

tnip1_str_enc_protocol OBJECT-TYPE
    SYNTAX DisplayString
    MAX-ACCESS accessible-for-notify
    STATUS current
    DESCRIPTION
        "Parameter 'str_enc_protocol' in event TNIP.1"
    ::= { tnipEventObjects1 1 }

tnip1_num_external_protocol OBJECT-TYPE
    SYNTAX Integer32
    MAX-ACCESS accessible-for-notify
    STATUS current
    DESCRIPTION
        "Parameter 'num_external_protocol' in event TNIP.1"
    ::= { tnipEventObjects1 2 }

tnip1_source_ip_address OBJECT-TYPE
    SYNTAX IpAddress
    MAX-ACCESS accessible-for-notify
    STATUS current
    DESCRIPTION
        "Parameter 'source_ip_address' in event TNIP.1"
    ::= { tnipEventObjects1 3 }

tnip1_destination_ip_address OBJECT-TYPE
    SYNTAX IpAddress
    MAX-ACCESS accessible-for-notify
    STATUS current
    DESCRIPTION
        "Parameter 'destination_ip_address' in event TNIP.1"
    ::= { tnipEventObjects1 4 }

tnip1_interface OBJECT-TYPE
    SYNTAX DisplayString
    MAX-ACCESS accessible-for-notify
    STATUS current
    DESCRIPTION
        "Parameter 'interface' in event TNIP.1"
    ::= { tnipEventObjects1 5 }

tnipEventObjects2 OBJECT-IDENTITY
    STATUS current
    DESCRIPTION
        "Event TNIP.2
        A packet for an external protocol and with a certain encapsulation was
        received. There is no tunnel between the encapsulated packet source and
        destination address."
    ::= { tnipEventsGroup 2 }

tnip2_str_enc_protocol OBJECT-TYPE
    SYNTAX DisplayString
    MAX-ACCESS accessible-for-notify
    STATUS current
    DESCRIPTION
        "Parameter 'str_enc_protocol' in event TNIP.2"
    ::= { tnipEventObjects2 1 }

tnip2_external_protocol_num OBJECT-TYPE
    SYNTAX Integer32
    MAX-ACCESS accessible-for-notify
    STATUS current
    DESCRIPTION
        "Parameter 'external_protocol_num' in event TNIP.2"
    ::= { tnipEventObjects2 2 }

tnip2_source_ip_address OBJECT-TYPE
    SYNTAX IpAddress
    MAX-ACCESS accessible-for-notify
    STATUS current
    DESCRIPTION
        "Parameter 'source_ip_address' in event TNIP.2"
    ::= { tnipEventObjects2 3 }

tnip2_destination_ip_address OBJECT-TYPE
    SYNTAX IpAddress
    MAX-ACCESS accessible-for-notify
    STATUS current
    DESCRIPTION
        "Parameter 'destination_ip_address' in event TNIP.2"
    ::= { tnipEventObjects2 4 }

tnipEventObjects3 OBJECT-IDENTITY
    STATUS current
    DESCRIPTION
        "Event TNIP.3
        The tunnel interfaz is down so the interface entry function
        has discarded the packet."
    ::= { tnipEventsGroup 3 }

tnip3_interface OBJECT-TYPE
    SYNTAX DisplayString
    MAX-ACCESS accessible-for-notify
    STATUS current
    DESCRIPTION
        "Parameter 'interface' in event TNIP.3"
    ::= { tnipEventObjects3 1 }

tnipEventObjects4 OBJECT-IDENTITY
    STATUS current
    DESCRIPTION
        "Event TNIP.4
        The tunnel interface has no configuration so the packet is discarded."
    ::= { tnipEventsGroup 4 }

tnip4_interface OBJECT-TYPE
    SYNTAX DisplayString
    MAX-ACCESS accessible-for-notify
    STATUS current
    DESCRIPTION
        "Parameter 'interface' in event TNIP.4"
    ::= { tnipEventObjects4 1 }

tnipEventObjects5 OBJECT-IDENTITY
    STATUS current
    DESCRIPTION
        "Event TNIP.5
        The interface entry function has discarded the packet because the
        interface configuracion has a different encapsulation protocol."
    ::= { tnipEventsGroup 5 }

tnip5_interface OBJECT-TYPE
    SYNTAX DisplayString
    MAX-ACCESS accessible-for-notify
    STATUS current
    DESCRIPTION
        "Parameter 'interface' in event TNIP.5"
    ::= { tnipEventObjects5 1 }

tnipEventObjects6 OBJECT-IDENTITY
    STATUS current
    DESCRIPTION
        "Event TNIP.6
        The packet has activated the routing option so the GRE desencapsulation
        funcion has discarded it."
    ::= { tnipEventsGroup 6 }

tnip6_interface OBJECT-TYPE
    SYNTAX DisplayString
    MAX-ACCESS accessible-for-notify
    STATUS current
    DESCRIPTION
        "Parameter 'interface' in event TNIP.6"
    ::= { tnipEventObjects6 1 }

tnipEventObjects7 OBJECT-IDENTITY
    STATUS current
    DESCRIPTION
        "Event TNIP.7
        This message is generated when a packet has an invalid checksum.
        The received checksum, together with the correct checksum,
        are displayed."
    ::= { tnipEventsGroup 7 }

tnip7_checksum OBJECT-TYPE
    SYNTAX Integer32
    MAX-ACCESS accessible-for-notify
    STATUS current
    DESCRIPTION
        "Parameter 'checksum' in event TNIP.7"
    ::= { tnipEventObjects7 1 }

tnip7_expected_checksum OBJECT-TYPE
    SYNTAX Integer32
    MAX-ACCESS accessible-for-notify
    STATUS current
    DESCRIPTION
        "Parameter 'expected_checksum' in event TNIP.7"
    ::= { tnipEventObjects7 2 }

tnip7_interface OBJECT-TYPE
    SYNTAX DisplayString
    MAX-ACCESS accessible-for-notify
    STATUS current
    DESCRIPTION
        "Parameter 'interface' in event TNIP.7"
    ::= { tnipEventObjects7 3 }

tnipEventObjects8 OBJECT-IDENTITY
    STATUS current
    DESCRIPTION
        "Event TNIP.8
        This message is generated when the key packet is invalid. The received
        key, together with the correct key, are displayed."
    ::= { tnipEventsGroup 8 }

tnip8_key OBJECT-TYPE
    SYNTAX Integer32
    MAX-ACCESS accessible-for-notify
    STATUS current
    DESCRIPTION
        "Parameter 'key' in event TNIP.8"
    ::= { tnipEventObjects8 1 }

tnip8_expected_key OBJECT-TYPE
    SYNTAX Integer32
    MAX-ACCESS accessible-for-notify
    STATUS current
    DESCRIPTION
        "Parameter 'expected_key' in event TNIP.8"
    ::= { tnipEventObjects8 2 }

tnip8_interface OBJECT-TYPE
    SYNTAX DisplayString
    MAX-ACCESS accessible-for-notify
    STATUS current
    DESCRIPTION
        "Parameter 'interface' in event TNIP.8"
    ::= { tnipEventObjects8 3 }

tnipEventObjects9 OBJECT-IDENTITY
    STATUS current
    DESCRIPTION
        "Event TNIP.9
        This message is generated when a packet has no key and the tunnel is
        configured to check identification key."
    ::= { tnipEventsGroup 9 }

tnip9_expected_key OBJECT-TYPE
    SYNTAX Integer32
    MAX-ACCESS accessible-for-notify
    STATUS current
    DESCRIPTION
        "Parameter 'expected_key' in event TNIP.9"
    ::= { tnipEventObjects9 1 }

tnip9_interface OBJECT-TYPE
    SYNTAX DisplayString
    MAX-ACCESS accessible-for-notify
    STATUS current
    DESCRIPTION
        "Parameter 'interface' in event TNIP.9"
    ::= { tnipEventObjects9 2 }

tnipEventObjects10 OBJECT-IDENTITY
    STATUS current
    DESCRIPTION
        "Event TNIP.10
        This message is generated when a packet has a key and the tunnel is
        configured not to check identification key."
    ::= { tnipEventsGroup 10 }

tnip10_key OBJECT-TYPE
    SYNTAX Integer32
    MAX-ACCESS accessible-for-notify
    STATUS current
    DESCRIPTION
        "Parameter 'key' in event TNIP.10"
    ::= { tnipEventObjects10 1 }

tnip10_interface OBJECT-TYPE
    SYNTAX DisplayString
    MAX-ACCESS accessible-for-notify
    STATUS current
    DESCRIPTION
        "Parameter 'interface' in event TNIP.10"
    ::= { tnipEventObjects10 2 }

tnipEventObjects11 OBJECT-IDENTITY
    STATUS current
    DESCRIPTION
        "Event TNIP.11
        This message is generated when a packet has a wrong sequence number.
        The received sequence number, together with the correct sequence number,
        are displayed."
    ::= { tnipEventsGroup 11 }

tnip11_seq_num OBJECT-TYPE
    SYNTAX Integer32
    MAX-ACCESS accessible-for-notify
    STATUS current
    DESCRIPTION
        "Parameter 'seq_num' in event TNIP.11"
    ::= { tnipEventObjects11 1 }

tnip11_expected_seq_num OBJECT-TYPE
    SYNTAX Integer32
    MAX-ACCESS accessible-for-notify
    STATUS current
    DESCRIPTION
        "Parameter 'expected_seq_num' in event TNIP.11"
    ::= { tnipEventObjects11 2 }

tnip11_interface OBJECT-TYPE
    SYNTAX DisplayString
    MAX-ACCESS accessible-for-notify
    STATUS current
    DESCRIPTION
        "Parameter 'interface' in event TNIP.11"
    ::= { tnipEventObjects11 3 }

tnipEventObjects12 OBJECT-IDENTITY
    STATUS current
    DESCRIPTION
        "Event TNIP.12
        The packet has the recursion option active so the desencaptulation
        GRE function has discarded it. Multiple encapsulation is not accepted."
    ::= { tnipEventsGroup 12 }

tnip12_interface OBJECT-TYPE
    SYNTAX DisplayString
    MAX-ACCESS accessible-for-notify
    STATUS current
    DESCRIPTION
        "Parameter 'interface' in event TNIP.12"
    ::= { tnipEventObjects12 1 }

tnipEventObjects13 OBJECT-IDENTITY
    STATUS current
    DESCRIPTION
        "Event TNIP.13
        The packet has an unknown version so the desencaptulation GRE function
        has discarded it."
    ::= { tnipEventsGroup 13 }

tnip13_version OBJECT-TYPE
    SYNTAX Integer32
    MAX-ACCESS accessible-for-notify
    STATUS current
    DESCRIPTION
        "Parameter 'version' in event TNIP.13"
    ::= { tnipEventObjects13 1 }

tnip13_interface OBJECT-TYPE
    SYNTAX DisplayString
    MAX-ACCESS accessible-for-notify
    STATUS current
    DESCRIPTION
        "Parameter 'interface' in event TNIP.13"
    ::= { tnipEventObjects13 2 }

tnipEventObjects14 OBJECT-IDENTITY
    STATUS current
    DESCRIPTION
        "Event TNIP.14
        Successful packet GRE desencapsulation. Internal protocol of the
        GRE packet, source and destination address, together with the interface
        are displayed."
    ::= { tnipEventsGroup 14 }

tnip14_protocol_num OBJECT-TYPE
    SYNTAX Integer32
    MAX-ACCESS accessible-for-notify
    STATUS current
    DESCRIPTION
        "Parameter 'protocol_num' in event TNIP.14"
    ::= { tnipEventObjects14 1 }

tnip14_source_ip_address OBJECT-TYPE
    SYNTAX IpAddress
    MAX-ACCESS accessible-for-notify
    STATUS current
    DESCRIPTION
        "Parameter 'source_ip_address' in event TNIP.14"
    ::= { tnipEventObjects14 2 }

tnip14_destination_ip_address OBJECT-TYPE
    SYNTAX IpAddress
    MAX-ACCESS accessible-for-notify
    STATUS current
    DESCRIPTION
        "Parameter 'destination_ip_address' in event TNIP.14"
    ::= { tnipEventObjects14 3 }

tnip14_interface OBJECT-TYPE
    SYNTAX DisplayString
    MAX-ACCESS accessible-for-notify
    STATUS current
    DESCRIPTION
        "Parameter 'interface' in event TNIP.14"
    ::= { tnipEventObjects14 4 }

tnip14_seq_num OBJECT-TYPE
    SYNTAX Integer32
    MAX-ACCESS accessible-for-notify
    STATUS current
    DESCRIPTION
        "Parameter 'seq_num' in event TNIP.14"
    ::= { tnipEventObjects14 5 }

tnipEventObjects15 OBJECT-IDENTITY
    STATUS current
    DESCRIPTION
        "Event TNIP.15
        Unknown protocol of the desencapsulated GRE packet."
    ::= { tnipEventsGroup 15 }

tnip15_protocol_num OBJECT-TYPE
    SYNTAX Integer32
    MAX-ACCESS accessible-for-notify
    STATUS current
    DESCRIPTION
        "Parameter 'protocol_num' in event TNIP.15"
    ::= { tnipEventObjects15 1 }

tnip15_interface OBJECT-TYPE
    SYNTAX DisplayString
    MAX-ACCESS accessible-for-notify
    STATUS current
    DESCRIPTION
        "Parameter 'interface' in event TNIP.15"
    ::= { tnipEventObjects15 2 }

tnipEventObjects16 OBJECT-IDENTITY
    STATUS current
    DESCRIPTION
        "Event TNIP.16
        The interface is down so the outgoing packet has been discarded."
    ::= { tnipEventsGroup 16 }

tnip16_interface OBJECT-TYPE
    SYNTAX DisplayString
    MAX-ACCESS accessible-for-notify
    STATUS current
    DESCRIPTION
        "Parameter 'interface' in event TNIP.16"
    ::= { tnipEventObjects16 1 }

tnipEventObjects17 OBJECT-IDENTITY
    STATUS current
    DESCRIPTION
        "Event TNIP.17
        The interface is no configured so the outging packet has been discarded."
    ::= { tnipEventsGroup 17 }

tnip17_interface OBJECT-TYPE
    SYNTAX DisplayString
    MAX-ACCESS accessible-for-notify
    STATUS current
    DESCRIPTION
        "Parameter 'interface' in event TNIP.17"
    ::= { tnipEventObjects17 1 }

tnipEventObjects18 OBJECT-IDENTITY
    STATUS current
    DESCRIPTION
        "Event TNIP.18
        The internal protocol (payload protocol) has been rejected so
        the outgoing packet has been discarded."
    ::= { tnipEventsGroup 18 }

tnip18_protocol_num OBJECT-TYPE
    SYNTAX Integer32
    MAX-ACCESS accessible-for-notify
    STATUS current
    DESCRIPTION
        "Parameter 'protocol_num' in event TNIP.18"
    ::= { tnipEventObjects18 1 }

tnip18_interface OBJECT-TYPE
    SYNTAX DisplayString
    MAX-ACCESS accessible-for-notify
    STATUS current
    DESCRIPTION
        "Parameter 'interface' in event TNIP.18"
    ::= { tnipEventObjects18 2 }

tnipEventObjects19 OBJECT-IDENTITY
    STATUS current
    DESCRIPTION
        "Event TNIP.19
        Successfully encapsulated GRE packet. The protocol, source and
        destination of the encapsulated packet are displayed."
    ::= { tnipEventsGroup 19 }

tnip19_protocol_num OBJECT-TYPE
    SYNTAX Integer32
    MAX-ACCESS accessible-for-notify
    STATUS current
    DESCRIPTION
        "Parameter 'protocol_num' in event TNIP.19"
    ::= { tnipEventObjects19 1 }

tnip19_source_ip_address OBJECT-TYPE
    SYNTAX IpAddress
    MAX-ACCESS accessible-for-notify
    STATUS current
    DESCRIPTION
        "Parameter 'source_ip_address' in event TNIP.19"
    ::= { tnipEventObjects19 2 }

tnip19_destination_ip_address OBJECT-TYPE
    SYNTAX IpAddress
    MAX-ACCESS accessible-for-notify
    STATUS current
    DESCRIPTION
        "Parameter 'destination_ip_address' in event TNIP.19"
    ::= { tnipEventObjects19 3 }

tnip19_interface OBJECT-TYPE
    SYNTAX DisplayString
    MAX-ACCESS accessible-for-notify
    STATUS current
    DESCRIPTION
        "Parameter 'interface' in event TNIP.19"
    ::= { tnipEventObjects19 4 }

tnipEventObjects20 OBJECT-IDENTITY
    STATUS current
    DESCRIPTION
        "Event TNIP.20
        A packet is sent. The encapsulation protocol, the external protocol
        (delivery protocol), source, destination and the interface that
        encapsulated the packet are displayed."
    ::= { tnipEventsGroup 20 }

tnip20_str_enc_protocol OBJECT-TYPE
    SYNTAX DisplayString
    MAX-ACCESS accessible-for-notify
    STATUS current
    DESCRIPTION
        "Parameter 'str_enc_protocol' in event TNIP.20"
    ::= { tnipEventObjects20 1 }

tnip20_protocol_num OBJECT-TYPE
    SYNTAX Integer32
    MAX-ACCESS accessible-for-notify
    STATUS current
    DESCRIPTION
        "Parameter 'protocol_num' in event TNIP.20"
    ::= { tnipEventObjects20 2 }

tnip20_source_ip_address OBJECT-TYPE
    SYNTAX IpAddress
    MAX-ACCESS accessible-for-notify
    STATUS current
    DESCRIPTION
        "Parameter 'source_ip_address' in event TNIP.20"
    ::= { tnipEventObjects20 3 }

tnip20_destination_ip_address OBJECT-TYPE
    SYNTAX IpAddress
    MAX-ACCESS accessible-for-notify
    STATUS current
    DESCRIPTION
        "Parameter 'destination_ip_address' in event TNIP.20"
    ::= { tnipEventObjects20 4 }

tnip20_interface OBJECT-TYPE
    SYNTAX DisplayString
    MAX-ACCESS accessible-for-notify
    STATUS current
    DESCRIPTION
        "Parameter 'interface' in event TNIP.20"
    ::= { tnipEventObjects20 5 }

tnip20_num_sec OBJECT-TYPE
    SYNTAX Integer32
    MAX-ACCESS accessible-for-notify
    STATUS current
    DESCRIPTION
        "Parameter 'num_sec' in event TNIP.20"
    ::= { tnipEventObjects20 6 }

tnipEventObjects21 OBJECT-IDENTITY
    STATUS current
    DESCRIPTION
        "Event TNIP.21
        A free dinamic tunnel has taken to set up the new tunnel."
    ::= { tnipEventsGroup 21 }

tnip21_interface OBJECT-TYPE
    SYNTAX DisplayString
    MAX-ACCESS accessible-for-notify
    STATUS current
    DESCRIPTION
        "Parameter 'interface' in event TNIP.21"
    ::= { tnipEventObjects21 1 }

tnip21_source_ip_address OBJECT-TYPE
    SYNTAX IpAddress
    MAX-ACCESS accessible-for-notify
    STATUS current
    DESCRIPTION
        "Parameter 'source_ip_address' in event TNIP.21"
    ::= { tnipEventObjects21 2 }

tnip21_destination_ip_address OBJECT-TYPE
    SYNTAX IpAddress
    MAX-ACCESS accessible-for-notify
    STATUS current
    DESCRIPTION
        "Parameter 'destination_ip_address' in event TNIP.21"
    ::= { tnipEventObjects21 3 }

tnipEventObjects22 OBJECT-IDENTITY
    STATUS current
    DESCRIPTION
        "Event TNIP.22
        A dinamic tunnel is released because there are no static nor RIP routes
        or because keepalive failed."
    ::= { tnipEventsGroup 22 }

tnip22_interface OBJECT-TYPE
    SYNTAX DisplayString
    MAX-ACCESS accessible-for-notify
    STATUS current
    DESCRIPTION
        "Parameter 'interface' in event TNIP.22"
    ::= { tnipEventObjects22 1 }

tnipEventObjects23 OBJECT-IDENTITY
    STATUS current
    DESCRIPTION
        "Event TNIP.23
        A new tunnel is set up. It has the same IP address than a previous
        tunnel. At this moment the release conditions are attained."
    ::= { tnipEventsGroup 23 }

tnip23_interface OBJECT-TYPE
    SYNTAX DisplayString
    MAX-ACCESS accessible-for-notify
    STATUS current
    DESCRIPTION
        "Parameter 'interface' in event TNIP.23"
    ::= { tnipEventObjects23 1 }

tnip23_ip_address OBJECT-TYPE
    SYNTAX IpAddress
    MAX-ACCESS accessible-for-notify
    STATUS current
    DESCRIPTION
        "Parameter 'ip_address' in event TNIP.23"
    ::= { tnipEventObjects23 2 }

tnipEventObjects24 OBJECT-IDENTITY
    STATUS current
    DESCRIPTION
        "Event TNIP.24
        A packet that will cause an infinite loop has been detected."
    ::= { tnipEventsGroup 24 }

tnip24_interface OBJECT-TYPE
    SYNTAX DisplayString
    MAX-ACCESS accessible-for-notify
    STATUS current
    DESCRIPTION
        "Parameter 'interface' in event TNIP.24"
    ::= { tnipEventObjects24 1 }

tnipEventObjects25 OBJECT-IDENTITY
    STATUS current
    DESCRIPTION
        "Event TNIP.25
        The payload of a GRE packet has been ciphered successfully.
        The protocol, source and destination of the encapsulated packet
        are displayed."
    ::= { tnipEventsGroup 25 }

tnip25_protocol_num OBJECT-TYPE
    SYNTAX Integer32
    MAX-ACCESS accessible-for-notify
    STATUS current
    DESCRIPTION
        "Parameter 'protocol_num' in event TNIP.25"
    ::= { tnipEventObjects25 1 }

tnip25_source_ip_address OBJECT-TYPE
    SYNTAX IpAddress
    MAX-ACCESS accessible-for-notify
    STATUS current
    DESCRIPTION
        "Parameter 'source_ip_address' in event TNIP.25"
    ::= { tnipEventObjects25 2 }

tnip25_destination_ip_address OBJECT-TYPE
    SYNTAX IpAddress
    MAX-ACCESS accessible-for-notify
    STATUS current
    DESCRIPTION
        "Parameter 'destination_ip_address' in event TNIP.25"
    ::= { tnipEventObjects25 3 }

tnip25_interface OBJECT-TYPE
    SYNTAX DisplayString
    MAX-ACCESS accessible-for-notify
    STATUS current
    DESCRIPTION
        "Parameter 'interface' in event TNIP.25"
    ::= { tnipEventObjects25 4 }

tnipEventObjects26 OBJECT-IDENTITY
    STATUS current
    DESCRIPTION
        "Event TNIP.26
        The payload of a GRE packet has been deciphered successfully.
        The internal protocol, source and destination of the GRE packet and
        the interface are displayed."
    ::= { tnipEventsGroup 26 }

tnip26_protocol_num OBJECT-TYPE
    SYNTAX Integer32
    MAX-ACCESS accessible-for-notify
    STATUS current
    DESCRIPTION
        "Parameter 'protocol_num' in event TNIP.26"
    ::= { tnipEventObjects26 1 }

tnip26_source_ip_address OBJECT-TYPE
    SYNTAX IpAddress
    MAX-ACCESS accessible-for-notify
    STATUS current
    DESCRIPTION
        "Parameter 'source_ip_address' in event TNIP.26"
    ::= { tnipEventObjects26 2 }

tnip26_destination_ip_address OBJECT-TYPE
    SYNTAX IpAddress
    MAX-ACCESS accessible-for-notify
    STATUS current
    DESCRIPTION
        "Parameter 'destination_ip_address' in event TNIP.26"
    ::= { tnipEventObjects26 3 }

tnip26_interface OBJECT-TYPE
    SYNTAX DisplayString
    MAX-ACCESS accessible-for-notify
    STATUS current
    DESCRIPTION
        "Parameter 'interface' in event TNIP.26"
    ::= { tnipEventObjects26 4 }

tnipEventObjects27 OBJECT-IDENTITY
    STATUS current
    DESCRIPTION
        "Event TNIP.27
        A deciphered packet has an invalid cipher checksum or the protocol
        is not ciphered."
    ::= { tnipEventsGroup 27 }

tnip27_interface OBJECT-TYPE
    SYNTAX DisplayString
    MAX-ACCESS accessible-for-notify
    STATUS current
    DESCRIPTION
        "Parameter 'interface' in event TNIP.27"
    ::= { tnipEventObjects27 1 }

tnipEventObjects28 OBJECT-IDENTITY
    STATUS current
    DESCRIPTION
        "Event TNIP.28
        Successful packet GRE desencapsulation. The internal protocol of the
        GRE packet together with the interface are displayed."
    ::= { tnipEventsGroup 28 }

tnip28_protocol_num OBJECT-TYPE
    SYNTAX Integer32
    MAX-ACCESS accessible-for-notify
    STATUS current
    DESCRIPTION
        "Parameter 'protocol_num' in event TNIP.28"
    ::= { tnipEventObjects28 1 }

tnip28_interface OBJECT-TYPE
    SYNTAX DisplayString
    MAX-ACCESS accessible-for-notify
    STATUS current
    DESCRIPTION
        "Parameter 'interface' in event TNIP.28"
    ::= { tnipEventObjects28 2 }

tnip28_seq_num OBJECT-TYPE
    SYNTAX Integer32
    MAX-ACCESS accessible-for-notify
    STATUS current
    DESCRIPTION
        "Parameter 'seq_num' in event TNIP.28"
    ::= { tnipEventObjects28 3 }

tnipEventObjects29 OBJECT-IDENTITY
    STATUS current
    DESCRIPTION
        "Event TNIP.29
        The payload of a GRE packet has been ciphered successfully. The protocol
        of the encapsulated packet is displayed."
    ::= { tnipEventsGroup 29 }

tnip29_protocol_num OBJECT-TYPE
    SYNTAX Integer32
    MAX-ACCESS accessible-for-notify
    STATUS current
    DESCRIPTION
        "Parameter 'protocol_num' in event TNIP.29"
    ::= { tnipEventObjects29 1 }

tnip29_interface OBJECT-TYPE
    SYNTAX DisplayString
    MAX-ACCESS accessible-for-notify
    STATUS current
    DESCRIPTION
        "Parameter 'interface' in event TNIP.29"
    ::= { tnipEventObjects29 2 }

tnipEventObjects30 OBJECT-IDENTITY
    STATUS current
    DESCRIPTION
        "Event TNIP.30
        Successfully encapsulated GRE packet. The protocol of the encapsulated
        packet is displayed."
    ::= { tnipEventsGroup 30 }

tnip30_protocol_num OBJECT-TYPE
    SYNTAX Integer32
    MAX-ACCESS accessible-for-notify
    STATUS current
    DESCRIPTION
        "Parameter 'protocol_num' in event TNIP.30"
    ::= { tnipEventObjects30 1 }

tnip30_interface OBJECT-TYPE
    SYNTAX DisplayString
    MAX-ACCESS accessible-for-notify
    STATUS current
    DESCRIPTION
        "Parameter 'interface' in event TNIP.30"
    ::= { tnipEventObjects30 2 }

tnipEventObjects31 OBJECT-IDENTITY
    STATUS current
    DESCRIPTION
        "Event TNIP.31
        Successful packet GRE desencapsulation. The internal protocol of the
        GRE packet, the MAC source and the MAC destination, together with the
        interface and the sequence number are displayed."
    ::= { tnipEventsGroup 31 }

tnip31_protocol_num OBJECT-TYPE
    SYNTAX Integer32
    MAX-ACCESS accessible-for-notify
    STATUS current
    DESCRIPTION
        "Parameter 'protocol_num' in event TNIP.31"
    ::= { tnipEventObjects31 1 }

tnip31_source_mac_address OBJECT-TYPE
    SYNTAX DisplayString
    MAX-ACCESS accessible-for-notify
    STATUS current
    DESCRIPTION
        "Parameter 'source_mac_address' in event TNIP.31"
    ::= { tnipEventObjects31 2 }

tnip31_destination_mac_address OBJECT-TYPE
    SYNTAX DisplayString
    MAX-ACCESS accessible-for-notify
    STATUS current
    DESCRIPTION
        "Parameter 'destination_mac_address' in event TNIP.31"
    ::= { tnipEventObjects31 3 }

tnip31_interface OBJECT-TYPE
    SYNTAX DisplayString
    MAX-ACCESS accessible-for-notify
    STATUS current
    DESCRIPTION
        "Parameter 'interface' in event TNIP.31"
    ::= { tnipEventObjects31 4 }

tnip31_seq_num OBJECT-TYPE
    SYNTAX Integer32
    MAX-ACCESS accessible-for-notify
    STATUS current
    DESCRIPTION
        "Parameter 'seq_num' in event TNIP.31"
    ::= { tnipEventObjects31 5 }

tnipEventObjects32 OBJECT-IDENTITY
    STATUS current
    DESCRIPTION
        "Event TNIP.32
        The payload of a GRE packet has been ciphered successfully.
        The protocol, MAC source and destination of the encapsulated packet,
        together with the interface are displayed."
    ::= { tnipEventsGroup 32 }

tnip32_protocol_num OBJECT-TYPE
    SYNTAX Integer32
    MAX-ACCESS accessible-for-notify
    STATUS current
    DESCRIPTION
        "Parameter 'protocol_num' in event TNIP.32"
    ::= { tnipEventObjects32 1 }

tnip32_source_mac_address OBJECT-TYPE
    SYNTAX DisplayString
    MAX-ACCESS accessible-for-notify
    STATUS current
    DESCRIPTION
        "Parameter 'source_mac_address' in event TNIP.32"
    ::= { tnipEventObjects32 2 }

tnip32_destination_mac_address OBJECT-TYPE
    SYNTAX DisplayString
    MAX-ACCESS accessible-for-notify
    STATUS current
    DESCRIPTION
        "Parameter 'destination_mac_address' in event TNIP.32"
    ::= { tnipEventObjects32 3 }

tnip32_interface OBJECT-TYPE
    SYNTAX DisplayString
    MAX-ACCESS accessible-for-notify
    STATUS current
    DESCRIPTION
        "Parameter 'interface' in event TNIP.32"
    ::= { tnipEventObjects32 4 }

tnipEventObjects33 OBJECT-IDENTITY
    STATUS current
    DESCRIPTION
        "Event TNIP.33
        Successfully encapsulated GRE packet. The protocol, MAC source and
        destination of the encapsulated packet, together with the interface are
        displayed."
    ::= { tnipEventsGroup 33 }

tnip33_protocol_num OBJECT-TYPE
    SYNTAX Integer32
    MAX-ACCESS accessible-for-notify
    STATUS current
    DESCRIPTION
        "Parameter 'protocol_num' in event TNIP.33"
    ::= { tnipEventObjects33 1 }

tnip33_source_mac_address OBJECT-TYPE
    SYNTAX DisplayString
    MAX-ACCESS accessible-for-notify
    STATUS current
    DESCRIPTION
        "Parameter 'source_mac_address' in event TNIP.33"
    ::= { tnipEventObjects33 2 }

tnip33_destination_mac_address OBJECT-TYPE
    SYNTAX DisplayString
    MAX-ACCESS accessible-for-notify
    STATUS current
    DESCRIPTION
        "Parameter 'destination_mac_address' in event TNIP.33"
    ::= { tnipEventObjects33 3 }

tnip33_interface OBJECT-TYPE
    SYNTAX DisplayString
    MAX-ACCESS accessible-for-notify
    STATUS current
    DESCRIPTION
        "Parameter 'interface' in event TNIP.33"
    ::= { tnipEventObjects33 4 }

tnipEventObjects34 OBJECT-IDENTITY
    STATUS current
    DESCRIPTION
        "Event TNIP.34
        A buffer could not be allocated when needed for keepalive request."
    ::= { tnipEventsGroup 34 }

tnip34_interface OBJECT-TYPE
    SYNTAX DisplayString
    MAX-ACCESS accessible-for-notify
    STATUS current
    DESCRIPTION
        "Parameter 'interface' in event TNIP.34"
    ::= { tnipEventObjects34 1 }

tnipEventObjects35 OBJECT-IDENTITY
    STATUS current
    DESCRIPTION
        "Event TNIP.35
        A keepalive is going to be sent on specified interface to test tunnel
        endpoint reachability."
    ::= { tnipEventsGroup 35 }

tnip35_interface OBJECT-TYPE
    SYNTAX DisplayString
    MAX-ACCESS accessible-for-notify
    STATUS current
    DESCRIPTION
        "Parameter 'interface' in event TNIP.35"
    ::= { tnipEventObjects35 1 }

tnipEventObjects36 OBJECT-IDENTITY
    STATUS current
    DESCRIPTION
        "Event TNIP.36
        A keepalive was received on specified interface with an unexpected
        identification number. The received and the expected identification
        numbers are shown, as well as incoming interface name."
    ::= { tnipEventsGroup 36 }

tnip36_received_id OBJECT-TYPE
    SYNTAX Integer32
    MAX-ACCESS accessible-for-notify
    STATUS current
    DESCRIPTION
        "Parameter 'received_id' in event TNIP.36"
    ::= { tnipEventObjects36 1 }

tnip36_expected_id OBJECT-TYPE
    SYNTAX Integer32
    MAX-ACCESS accessible-for-notify
    STATUS current
    DESCRIPTION
        "Parameter 'expected_id' in event TNIP.36"
    ::= { tnipEventObjects36 2 }

tnip36_interface OBJECT-TYPE
    SYNTAX DisplayString
    MAX-ACCESS accessible-for-notify
    STATUS current
    DESCRIPTION
        "Parameter 'interface' in event TNIP.36"
    ::= { tnipEventObjects36 3 }

tnipEventObjects37 OBJECT-IDENTITY
    STATUS current
    DESCRIPTION
        "Event TNIP.37
        A keepalive response was received on specified interface."
    ::= { tnipEventsGroup 37 }

tnip37_interface OBJECT-TYPE
    SYNTAX DisplayString
    MAX-ACCESS accessible-for-notify
    STATUS current
    DESCRIPTION
        "Parameter 'interface' in event TNIP.37"
    ::= { tnipEventObjects37 1 }

tnipEventObjects38 OBJECT-IDENTITY
    STATUS current
    DESCRIPTION
        "Event TNIP.38
        An unexpected keepalive response was received on specified interface."
    ::= { tnipEventsGroup 38 }

tnip38_interface OBJECT-TYPE
    SYNTAX DisplayString
    MAX-ACCESS accessible-for-notify
    STATUS current
    DESCRIPTION
        "Parameter 'interface' in event TNIP.38"
    ::= { tnipEventObjects38 1 }

tnipEventObjects39 OBJECT-IDENTITY
    STATUS current
    DESCRIPTION
        "Event TNIP.39
        The router received an ICMP Path MTU 'too big' message (RFC 1191),
        indicating that a sent packet was too big and was unable
        to be fragmented for some reason. The 'source' IP address indicates
        the router whose next hop MTU is too small for the packet."
    ::= { tnipEventsGroup 39 }

tnip39_rmtu OBJECT-TYPE
    SYNTAX Integer32
    MAX-ACCESS accessible-for-notify
    STATUS current
    DESCRIPTION
        "Parameter 'rmtu' in event TNIP.39"
    ::= { tnipEventObjects39 1 }

tnip39_src_ip_addr OBJECT-TYPE
    SYNTAX IpAddress
    MAX-ACCESS accessible-for-notify
    STATUS current
    DESCRIPTION
        "Parameter 'src_ip_addr' in event TNIP.39"
    ::= { tnipEventObjects39 2 }

tnip39_dest_ip_addr OBJECT-TYPE
    SYNTAX IpAddress
    MAX-ACCESS accessible-for-notify
    STATUS current
    DESCRIPTION
        "Parameter 'dest_ip_addr' in event TNIP.39"
    ::= { tnipEventObjects39 3 }

tnip39_interface OBJECT-TYPE
    SYNTAX DisplayString
    MAX-ACCESS accessible-for-notify
    STATUS current
    DESCRIPTION
        "Parameter 'interface' in event TNIP.39"
    ::= { tnipEventObjects39 4 }

tnipEventObjects40 OBJECT-IDENTITY
    STATUS current
    DESCRIPTION
        "Event TNIP.40
        A keepalive received on specified interface is being forwarded."
    ::= { tnipEventsGroup 40 }

tnip40_interface OBJECT-TYPE
    SYNTAX DisplayString
    MAX-ACCESS accessible-for-notify
    STATUS current
    DESCRIPTION
        "Parameter 'interface' in event TNIP.40"
    ::= { tnipEventObjects40 1 }


tnipNotification1 NOTIFICATION-TYPE
    OBJECTS { 
              tnip1_str_enc_protocol, 
              tnip1_num_external_protocol,
              tnip1_source_ip_address,
              tnip1_destination_ip_address,
              tnip1_interface 
            }
    STATUS current
    DESCRIPTION
        "Notification of Event TNIP.1

        Message: 'Packet received with encapsulation $1, external protocol 0x$2, (source $3 y destination $4), on interface $5'

        Parameters list:
              $1: tnip1_str_enc_protocol
              $2: tnip1_num_external_protocol
              $3: tnip1_source_ip_address
              $4: tnip1_destination_ip_address
              $5: tnip1_interface

        An encapsulated packet for an external protocol was received on
        an interface to be desencapsulated."
    ::= { tnipNotificationsPrefix 1 }

tnipNotification2 NOTIFICATION-TYPE
    OBJECTS { 
              tnip2_str_enc_protocol, 
              tnip2_external_protocol_num,
              tnip2_source_ip_address,
              tnip2_destination_ip_address 
            }
    STATUS current
    DESCRIPTION
        "Notification of Event TNIP.2

        Message: 'Received packet with encapsulation $1, external protocol 0x$2, (source $3 y destination $4). There is no tunnel for it'

        Parameters list:
              $1: tnip2_str_enc_protocol
              $2: tnip2_external_protocol_num
              $3: tnip2_source_ip_address
              $4: tnip2_destination_ip_address

        A packet for an external protocol and with a certain encapsulation was
        received. There is no tunnel between the encapsulated packet source and
        destination address."
    ::= { tnipNotificationsPrefix 2 }

tnipNotification3 NOTIFICATION-TYPE
    OBJECTS { 
              tnip3_interface 
            }
    STATUS current
    DESCRIPTION
        "Notification of Event TNIP.3

        Message: 'Incoming packet discarded. The interfaz is down. Interface $1'

        Parameters list:
              $1: tnip3_interface

        The tunnel interfaz is down so the interface entry function
        has discarded the packet."
    ::= { tnipNotificationsPrefix 3 }

tnipNotification4 NOTIFICATION-TYPE
    OBJECTS { 
              tnip4_interface 
            }
    STATUS current
    DESCRIPTION
        "Notification of Event TNIP.4

        Message: 'Incoming packet discarded. The interfaz has no configuration. Interface $1'

        Parameters list:
              $1: tnip4_interface

        The tunnel interface has no configuration so the packet is discarded."
    ::= { tnipNotificationsPrefix 4 }

tnipNotification5 NOTIFICATION-TYPE
    OBJECTS { 
              tnip5_interface 
            }
    STATUS current
    DESCRIPTION
        "Notification of Event TNIP.5

        Message: 'Incoming packet has been discarded because the interface configuration has a different encapsulation protocol, interface $1'

        Parameters list:
              $1: tnip5_interface

        The interface entry function has discarded the packet because the
        interface configuracion has a different encapsulation protocol."
    ::= { tnipNotificationsPrefix 5 }

tnipNotification6 NOTIFICATION-TYPE
    OBJECTS { 
              tnip6_interface 
            }
    STATUS current
    DESCRIPTION
        "Notification of Event TNIP.6

        Message: 'Error in GRE header. Flags have the routing option, interface $1'

        Parameters list:
              $1: tnip6_interface

        The packet has activated the routing option so the GRE desencapsulation
        funcion has discarded it."
    ::= { tnipNotificationsPrefix 6 }

tnipNotification7 NOTIFICATION-TYPE
    OBJECTS { 
              tnip7_checksum, 
              tnip7_expected_checksum,
              tnip7_interface 
            }
    STATUS current
    DESCRIPTION
        "Notification of Event TNIP.7

        Message: 'Error in GRE header, checksum 0x$1 (des 0x$2), interface $3'

        Parameters list:
              $1: tnip7_checksum
              $2: tnip7_expected_checksum
              $3: tnip7_interface

        This message is generated when a packet has an invalid checksum.
        The received checksum, together with the correct checksum,
        are displayed."
    ::= { tnipNotificationsPrefix 7 }

tnipNotification8 NOTIFICATION-TYPE
    OBJECTS { 
              tnip8_key, 
              tnip8_expected_key,
              tnip8_interface 
            }
    STATUS current
    DESCRIPTION
        "Notification of Event TNIP.8

        Message: 'Packet GRE discarded, key $1 (expected $2), interface $3'

        Parameters list:
              $1: tnip8_key
              $2: tnip8_expected_key
              $3: tnip8_interface

        This message is generated when the key packet is invalid. The received
        key, together with the correct key, are displayed."
    ::= { tnipNotificationsPrefix 8 }

tnipNotification9 NOTIFICATION-TYPE
    OBJECTS { 
              tnip9_expected_key, 
              tnip9_interface 
            }
    STATUS current
    DESCRIPTION
        "Notification of Event TNIP.9

        Message: 'Packet GRE with no key discarded (expected $1), interface $2'

        Parameters list:
              $1: tnip9_expected_key
              $2: tnip9_interface

        This message is generated when a packet has no key and the tunnel is
        configured to check identification key."
    ::= { tnipNotificationsPrefix 9 }

tnipNotification10 NOTIFICATION-TYPE
    OBJECTS { 
              tnip10_key, 
              tnip10_interface 
            }
    STATUS current
    DESCRIPTION
        "Notification of Event TNIP.10

        Message: 'Packet GRE with key discarded, key $1 (not expected key), interface $2'

        Parameters list:
              $1: tnip10_key
              $2: tnip10_interface

        This message is generated when a packet has a key and the tunnel is
        configured not to check identification key."
    ::= { tnipNotificationsPrefix 10 }

tnipNotification11 NOTIFICATION-TYPE
    OBJECTS { 
              tnip11_seq_num, 
              tnip11_expected_seq_num,
              tnip11_interface 
            }
    STATUS current
    DESCRIPTION
        "Notification of Event TNIP.11

        Message: 'Packet GRE discarded, sequence number $1 less than expected $2, interface $3'

        Parameters list:
              $1: tnip11_seq_num
              $2: tnip11_expected_seq_num
              $3: tnip11_interface

        This message is generated when a packet has a wrong sequence number.
        The received sequence number, together with the correct sequence number,
        are displayed."
    ::= { tnipNotificationsPrefix 11 }

tnipNotification12 NOTIFICATION-TYPE
    OBJECTS { 
              tnip12_interface 
            }
    STATUS current
    DESCRIPTION
        "Notification of Event TNIP.12

        Message: 'Error in GRE header. Recursion option active, interface $1'

        Parameters list:
              $1: tnip12_interface

        The packet has the recursion option active so the desencaptulation
        GRE function has discarded it. Multiple encapsulation is not accepted."
    ::= { tnipNotificationsPrefix 12 }

tnipNotification13 NOTIFICATION-TYPE
    OBJECTS { 
              tnip13_version, 
              tnip13_interface 
            }
    STATUS current
    DESCRIPTION
        "Notification of Event TNIP.13

        Message: 'Error in GRE header, encapsulation version $1 invalid, interface $2'

        Parameters list:
              $1: tnip13_version
              $2: tnip13_interface

        The packet has an unknown version so the desencaptulation GRE function
        has discarded it."
    ::= { tnipNotificationsPrefix 13 }

tnipNotification14 NOTIFICATION-TYPE
    OBJECTS { 
              tnip14_protocol_num, 
              tnip14_source_ip_address,
              tnip14_destination_ip_address,
              tnip14_interface,
              tnip14_seq_num 
            }
    STATUS current
    DESCRIPTION
        "Notification of Event TNIP.14

        Message: 'Desencapsulated GRE packet successfully, internal protocol 0x$1, (source $2 and destination $3), interface $4 sequence number $5'

        Parameters list:
              $1: tnip14_protocol_num
              $2: tnip14_source_ip_address
              $3: tnip14_destination_ip_address
              $4: tnip14_interface
              $5: tnip14_seq_num

        Successful packet GRE desencapsulation. Internal protocol of the
        GRE packet, source and destination address, together with the interface
        are displayed."
    ::= { tnipNotificationsPrefix 14 }

tnipNotification15 NOTIFICATION-TYPE
    OBJECTS { 
              tnip15_protocol_num, 
              tnip15_interface 
            }
    STATUS current
    DESCRIPTION
        "Notification of Event TNIP.15

        Message: 'Error in desencapsulated GRE packet, unknown internal protocol 0x$1, interface $2'

        Parameters list:
              $1: tnip15_protocol_num
              $2: tnip15_interface

        Unknown protocol of the desencapsulated GRE packet."
    ::= { tnipNotificationsPrefix 15 }

tnipNotification16 NOTIFICATION-TYPE
    OBJECTS { 
              tnip16_interface 
            }
    STATUS current
    DESCRIPTION
        "Notification of Event TNIP.16

        Message: 'The interface is down so the outgoing packet has been discarded, interface $1'

        Parameters list:
              $1: tnip16_interface

        The interface is down so the outgoing packet has been discarded."
    ::= { tnipNotificationsPrefix 16 }

tnipNotification17 NOTIFICATION-TYPE
    OBJECTS { 
              tnip17_interface 
            }
    STATUS current
    DESCRIPTION
        "Notification of Event TNIP.17

        Message: 'The interface is no configured so the outging packet has been discarded, interface $1'

        Parameters list:
              $1: tnip17_interface

        The interface is no configured so the outging packet has been discarded."
    ::= { tnipNotificationsPrefix 17 }

tnipNotification18 NOTIFICATION-TYPE
    OBJECTS { 
              tnip18_protocol_num, 
              tnip18_interface 
            }
    STATUS current
    DESCRIPTION
        "Notification of Event TNIP.18

        Message: 'The internal protocol 0x$1 has been rejected so the outgoing packet has been discarded, interface $2'

        Parameters list:
              $1: tnip18_protocol_num
              $2: tnip18_interface

        The internal protocol (payload protocol) has been rejected so
        the outgoing packet has been discarded."
    ::= { tnipNotificationsPrefix 18 }

tnipNotification19 NOTIFICATION-TYPE
    OBJECTS { 
              tnip19_protocol_num, 
              tnip19_source_ip_address,
              tnip19_destination_ip_address,
              tnip19_interface 
            }
    STATUS current
    DESCRIPTION
        "Notification of Event TNIP.19

        Message: 'Successfully encapsulated GRE packet, internal protocol 0x$1, (source $2 destination $3), interface $4'

        Parameters list:
              $1: tnip19_protocol_num
              $2: tnip19_source_ip_address
              $3: tnip19_destination_ip_address
              $4: tnip19_interface

        Successfully encapsulated GRE packet. The protocol, source and
        destination of the encapsulated packet are displayed."
    ::= { tnipNotificationsPrefix 19 }

tnipNotification20 NOTIFICATION-TYPE
    OBJECTS { 
              tnip20_str_enc_protocol, 
              tnip20_protocol_num,
              tnip20_source_ip_address,
              tnip20_destination_ip_address,
              tnip20_interface,
              tnip20_num_sec 
            }
    STATUS current
    DESCRIPTION
        "Notification of Event TNIP.20

        Message: 'Sendind packet $1, ext prt 0x$2, (source $3 destination $4), interface $5 sequence number $6'

        Parameters list:
              $1: tnip20_str_enc_protocol
              $2: tnip20_protocol_num
              $3: tnip20_source_ip_address
              $4: tnip20_destination_ip_address
              $5: tnip20_interface
              $6: tnip20_num_sec

        A packet is sent. The encapsulation protocol, the external protocol
        (delivery protocol), source, destination and the interface that
        encapsulated the packet are displayed."
    ::= { tnipNotificationsPrefix 20 }

tnipNotification21 NOTIFICATION-TYPE
    OBJECTS { 
              tnip21_interface, 
              tnip21_source_ip_address,
              tnip21_destination_ip_address 
            }
    STATUS current
    DESCRIPTION
        "Notification of Event TNIP.21

        Message: 'Interface $1 sets up a tunnel with source address $2 and destination $3'

        Parameters list:
              $1: tnip21_interface
              $2: tnip21_source_ip_address
              $3: tnip21_destination_ip_address

        A free dinamic tunnel has taken to set up the new tunnel."
    ::= { tnipNotificationsPrefix 21 }

tnipNotification22 NOTIFICATION-TYPE
    OBJECTS { 
              tnip22_interface 
            }
    STATUS current
    DESCRIPTION
        "Notification of Event TNIP.22

        Message: 'Error tunnel release, interface $1'

        Parameters list:
              $1: tnip22_interface

        A dinamic tunnel is released because there are no static nor RIP routes
        or because keepalive failed."
    ::= { tnipNotificationsPrefix 22 }

tnipNotification23 NOTIFICATION-TYPE
    OBJECTS { 
              tnip23_interface, 
              tnip23_ip_address 
            }
    STATUS current
    DESCRIPTION
        "Notification of Event TNIP.23

        Message: 'Release tunnel interface $1 set up another tunnel with the same address $2'

        Parameters list:
              $1: tnip23_interface
              $2: tnip23_ip_address

        A new tunnel is set up. It has the same IP address than a previous
        tunnel. At this moment the release conditions are attained."
    ::= { tnipNotificationsPrefix 23 }

tnipNotification24 NOTIFICATION-TYPE
    OBJECTS { 
              tnip24_interface 
            }
    STATUS current
    DESCRIPTION
        "Notification of Event TNIP.24

        Message: 'Error loop in tunnel, interface $1'

        Parameters list:
              $1: tnip24_interface

        A packet that will cause an infinite loop has been detected."
    ::= { tnipNotificationsPrefix 24 }

tnipNotification25 NOTIFICATION-TYPE
    OBJECTS { 
              tnip25_protocol_num, 
              tnip25_source_ip_address,
              tnip25_destination_ip_address,
              tnip25_interface 
            }
    STATUS current
    DESCRIPTION
        "Notification of Event TNIP.25

        Message: 'Successfully ciphered GRE packet, internal protocol 0x$1, (source $2 and destination $3), interface $4'

        Parameters list:
              $1: tnip25_protocol_num
              $2: tnip25_source_ip_address
              $3: tnip25_destination_ip_address
              $4: tnip25_interface

        The payload of a GRE packet has been ciphered successfully.
        The protocol, source and destination of the encapsulated packet
        are displayed."
    ::= { tnipNotificationsPrefix 25 }

tnipNotification26 NOTIFICATION-TYPE
    OBJECTS { 
              tnip26_protocol_num, 
              tnip26_source_ip_address,
              tnip26_destination_ip_address,
              tnip26_interface 
            }
    STATUS current
    DESCRIPTION
        "Notification of Event TNIP.26

        Message: 'Successfully deciphered GRE packet, internal protocol 0x$1, (source $2 and destination $3), interface $4'

        Parameters list:
              $1: tnip26_protocol_num
              $2: tnip26_source_ip_address
              $3: tnip26_destination_ip_address
              $4: tnip26_interface

        The payload of a GRE packet has been deciphered successfully.
        The internal protocol, source and destination of the GRE packet and
        the interface are displayed."
    ::= { tnipNotificationsPrefix 26 }

tnipNotification27 NOTIFICATION-TYPE
    OBJECTS { 
              tnip27_interface 
            }
    STATUS current
    DESCRIPTION
        "Notification of Event TNIP.27

        Message: 'Error deciphering GRE, interface $1'

        Parameters list:
              $1: tnip27_interface

        A deciphered packet has an invalid cipher checksum or the protocol
        is not ciphered."
    ::= { tnipNotificationsPrefix 27 }

tnipNotification28 NOTIFICATION-TYPE
    OBJECTS { 
              tnip28_protocol_num, 
              tnip28_interface,
              tnip28_seq_num 
            }
    STATUS current
    DESCRIPTION
        "Notification of Event TNIP.28

        Message: 'Desencapsulated GRE packet successfully, internal protocol 0x$1, interface $2 sequence number $3'

        Parameters list:
              $1: tnip28_protocol_num
              $2: tnip28_interface
              $3: tnip28_seq_num

        Successful packet GRE desencapsulation. The internal protocol of the
        GRE packet together with the interface are displayed."
    ::= { tnipNotificationsPrefix 28 }

tnipNotification29 NOTIFICATION-TYPE
    OBJECTS { 
              tnip29_protocol_num, 
              tnip29_interface 
            }
    STATUS current
    DESCRIPTION
        "Notification of Event TNIP.29

        Message: 'Successful ciphered GRE packet, internal protocol 0x$1, interface $2'

        Parameters list:
              $1: tnip29_protocol_num
              $2: tnip29_interface

        The payload of a GRE packet has been ciphered successfully. The protocol
        of the encapsulated packet is displayed."
    ::= { tnipNotificationsPrefix 29 }

tnipNotification30 NOTIFICATION-TYPE
    OBJECTS { 
              tnip30_protocol_num, 
              tnip30_interface 
            }
    STATUS current
    DESCRIPTION
        "Notification of Event TNIP.30

        Message: 'Successfully encapsulated GRE packet, internal protocol 0x$1, interface $2'

        Parameters list:
              $1: tnip30_protocol_num
              $2: tnip30_interface

        Successfully encapsulated GRE packet. The protocol of the encapsulated
        packet is displayed."
    ::= { tnipNotificationsPrefix 30 }

tnipNotification31 NOTIFICATION-TYPE
    OBJECTS { 
              tnip31_protocol_num, 
              tnip31_source_mac_address,
              tnip31_destination_mac_address,
              tnip31_interface,
              tnip31_seq_num 
            }
    STATUS current
    DESCRIPTION
        "Notification of Event TNIP.31

        Message: 'Desencapsulated GRE packet successfully, internal protocol 0x$1, (source $2 and destination $3), interface $4 sequence number $5'

        Parameters list:
              $1: tnip31_protocol_num
              $2: tnip31_source_mac_address
              $3: tnip31_destination_mac_address
              $4: tnip31_interface
              $5: tnip31_seq_num

        Successful packet GRE desencapsulation. The internal protocol of the
        GRE packet, the MAC source and the MAC destination, together with the
        interface and the sequence number are displayed."
    ::= { tnipNotificationsPrefix 31 }

tnipNotification32 NOTIFICATION-TYPE
    OBJECTS { 
              tnip32_protocol_num, 
              tnip32_source_mac_address,
              tnip32_destination_mac_address,
              tnip32_interface 
            }
    STATUS current
    DESCRIPTION
        "Notification of Event TNIP.32

        Message: 'Successfully ciphered GRE packet, internal protocol 0x$1, (source $2 and destination $3), interface $4'

        Parameters list:
              $1: tnip32_protocol_num
              $2: tnip32_source_mac_address
              $3: tnip32_destination_mac_address
              $4: tnip32_interface

        The payload of a GRE packet has been ciphered successfully.
        The protocol, MAC source and destination of the encapsulated packet,
        together with the interface are displayed."
    ::= { tnipNotificationsPrefix 32 }

tnipNotification33 NOTIFICATION-TYPE
    OBJECTS { 
              tnip33_protocol_num, 
              tnip33_source_mac_address,
              tnip33_destination_mac_address,
              tnip33_interface 
            }
    STATUS current
    DESCRIPTION
        "Notification of Event TNIP.33

        Message: 'Successfully encapsulated GRE packet, internal protocol 0x$1, (source $2 destination $3), interface $4'

        Parameters list:
              $1: tnip33_protocol_num
              $2: tnip33_source_mac_address
              $3: tnip33_destination_mac_address
              $4: tnip33_interface

        Successfully encapsulated GRE packet. The protocol, MAC source and
        destination of the encapsulated packet, together with the interface are
        displayed."
    ::= { tnipNotificationsPrefix 33 }

tnipNotification34 NOTIFICATION-TYPE
    OBJECTS { 
              tnip34_interface 
            }
    STATUS current
    DESCRIPTION
        "Notification of Event TNIP.34

        Message: 'No packet for keepalive interface $1'

        Parameters list:
              $1: tnip34_interface

        A buffer could not be allocated when needed for keepalive request."
    ::= { tnipNotificationsPrefix 34 }

tnipNotification35 NOTIFICATION-TYPE
    OBJECTS { 
              tnip35_interface 
            }
    STATUS current
    DESCRIPTION
        "Notification of Event TNIP.35

        Message: 'Sending keepalive packet on interface $1'

        Parameters list:
              $1: tnip35_interface

        A keepalive is going to be sent on specified interface to test tunnel
        endpoint reachability."
    ::= { tnipNotificationsPrefix 35 }

tnipNotification36 NOTIFICATION-TYPE
    OBJECTS { 
              tnip36_received_id, 
              tnip36_expected_id,
              tnip36_interface 
            }
    STATUS current
    DESCRIPTION
        "Notification of Event TNIP.36

        Message: 'Unexpected keepalive identification number $1 (expected $2) received on interface $3'

        Parameters list:
              $1: tnip36_received_id
              $2: tnip36_expected_id
              $3: tnip36_interface

        A keepalive was received on specified interface with an unexpected
        identification number. The received and the expected identification
        numbers are shown, as well as incoming interface name."
    ::= { tnipNotificationsPrefix 36 }

tnipNotification37 NOTIFICATION-TYPE
    OBJECTS { 
              tnip37_interface 
            }
    STATUS current
    DESCRIPTION
        "Notification of Event TNIP.37

        Message: 'Received keepalive on interface $1'

        Parameters list:
              $1: tnip37_interface

        A keepalive response was received on specified interface."
    ::= { tnipNotificationsPrefix 37 }

tnipNotification38 NOTIFICATION-TYPE
    OBJECTS { 
              tnip38_interface 
            }
    STATUS current
    DESCRIPTION
        "Notification of Event TNIP.38

        Message: 'Discarded keepalive on interface $1'

        Parameters list:
              $1: tnip38_interface

        An unexpected keepalive response was received on specified interface."
    ::= { tnipNotificationsPrefix 38 }

tnipNotification39 NOTIFICATION-TYPE
    OBJECTS { 
              tnip39_rmtu, 
              tnip39_src_ip_addr,
              tnip39_dest_ip_addr,
              tnip39_interface 
            }
    STATUS current
    DESCRIPTION
        "Notification of Event TNIP.39

        Message: 'Rcvd ICMP PMTU: Next-hop mtu = $1 bytes, pkt $2 -> $3, on interface $4'

        Parameters list:
              $1: tnip39_rmtu
              $2: tnip39_src_ip_addr
              $3: tnip39_dest_ip_addr
              $4: tnip39_interface

        The router received an ICMP Path MTU 'too big' message (RFC 1191),
        indicating that a sent packet was too big and was unable
        to be fragmented for some reason. The 'source' IP address indicates
        the router whose next hop MTU is too small for the packet."
    ::= { tnipNotificationsPrefix 39 }

tnipNotification40 NOTIFICATION-TYPE
    OBJECTS { 
              tnip40_interface 
            }
    STATUS current
    DESCRIPTION
        "Notification of Event TNIP.40

        Message: 'Forwarding keepalive on interface $1'

        Parameters list:
              $1: tnip40_interface

        A keepalive received on specified interface is being forwarded."
    ::= { tnipNotificationsPrefix 40 }


END
