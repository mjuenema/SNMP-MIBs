-- file automatically created


TELDAT-TRAP-SIP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


sipTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SIP event subsystem."
    REVISION "201401200930Z"
    DESCRIPTION "Initial implementation"
        ::= { telEventTraps 180 }


sipEventsGroup	OBJECT IDENTIFIER	::= { sipTrapsMIB 1 }

sipNotifications	OBJECT IDENTIFIER	::= { sipTrapsMIB 2 }
sipNotificationsPrefix	OBJECT IDENTIFIER	::= { sipNotifications 0 }

sipEventObjects1 OBJECT-IDENTITY
    STATUS current
    DESCRIPTION
        "Event SIP.1
        Event related with task creation/deletion."
    ::= { sipEventsGroup 1 }

sip1_description OBJECT-TYPE
    SYNTAX DisplayString
    MAX-ACCESS accessible-for-notify
    STATUS current
    DESCRIPTION
        "Parameter 'description' in event SIP.1"
    ::= { sipEventObjects1 1 }

sip1_task OBJECT-TYPE
    SYNTAX DisplayString
    MAX-ACCESS accessible-for-notify
    STATUS current
    DESCRIPTION
        "Parameter 'task' in event SIP.1"
    ::= { sipEventObjects1 2 }

sipEventObjects2 OBJECT-IDENTITY
    STATUS current
    DESCRIPTION
        "Event SIP.2
        Event related with message processing."
    ::= { sipEventsGroup 2 }

sip2_description OBJECT-TYPE
    SYNTAX DisplayString
    MAX-ACCESS accessible-for-notify
    STATUS current
    DESCRIPTION
        "Parameter 'description' in event SIP.2"
    ::= { sipEventObjects2 1 }

sip2_message OBJECT-TYPE
    SYNTAX DisplayString
    MAX-ACCESS accessible-for-notify
    STATUS current
    DESCRIPTION
        "Parameter 'message' in event SIP.2"
    ::= { sipEventObjects2 2 }

sip2_task OBJECT-TYPE
    SYNTAX DisplayString
    MAX-ACCESS accessible-for-notify
    STATUS current
    DESCRIPTION
        "Parameter 'task' in event SIP.2"
    ::= { sipEventObjects2 3 }

sip2_cdr OBJECT-TYPE
    SYNTAX Integer32
    MAX-ACCESS accessible-for-notify
    STATUS current
    DESCRIPTION
        "Parameter 'cdr' in event SIP.2"
    ::= { sipEventObjects2 4 }

sipEventObjects3 OBJECT-IDENTITY
    STATUS current
    DESCRIPTION
        "Event SIP.3
        Error related with task creation/deletion."
    ::= { sipEventsGroup 3 }

sip3_error OBJECT-TYPE
    SYNTAX DisplayString
    MAX-ACCESS accessible-for-notify
    STATUS current
    DESCRIPTION
        "Parameter 'error' in event SIP.3"
    ::= { sipEventObjects3 1 }

sip3_task OBJECT-TYPE
    SYNTAX DisplayString
    MAX-ACCESS accessible-for-notify
    STATUS current
    DESCRIPTION
        "Parameter 'task' in event SIP.3"
    ::= { sipEventObjects3 2 }

sipEventObjects4 OBJECT-IDENTITY
    STATUS current
    DESCRIPTION
        "Event SIP.4
        Error related with message processing."
    ::= { sipEventsGroup 4 }

sip4_description OBJECT-TYPE
    SYNTAX DisplayString
    MAX-ACCESS accessible-for-notify
    STATUS current
    DESCRIPTION
        "Parameter 'description' in event SIP.4"
    ::= { sipEventObjects4 1 }

sip4_error OBJECT-TYPE
    SYNTAX DisplayString
    MAX-ACCESS accessible-for-notify
    STATUS current
    DESCRIPTION
        "Parameter 'error' in event SIP.4"
    ::= { sipEventObjects4 2 }

sip4_task OBJECT-TYPE
    SYNTAX DisplayString
    MAX-ACCESS accessible-for-notify
    STATUS current
    DESCRIPTION
        "Parameter 'task' in event SIP.4"
    ::= { sipEventObjects4 3 }

sip4_cdr OBJECT-TYPE
    SYNTAX Integer32
    MAX-ACCESS accessible-for-notify
    STATUS current
    DESCRIPTION
        "Parameter 'cdr' in event SIP.4"
    ::= { sipEventObjects4 4 }

sipEventObjects5 OBJECT-IDENTITY
    STATUS current
    DESCRIPTION
        "Event SIP.5
        Event related with queues."
    ::= { sipEventsGroup 5 }

sip5_queue OBJECT-TYPE
    SYNTAX DisplayString
    MAX-ACCESS accessible-for-notify
    STATUS current
    DESCRIPTION
        "Parameter 'queue' in event SIP.5"
    ::= { sipEventObjects5 1 }

sip5_description OBJECT-TYPE
    SYNTAX DisplayString
    MAX-ACCESS accessible-for-notify
    STATUS current
    DESCRIPTION
        "Parameter 'description' in event SIP.5"
    ::= { sipEventObjects5 2 }

sip5_total-msgs OBJECT-TYPE
    SYNTAX Integer32
    MAX-ACCESS accessible-for-notify
    STATUS current
    DESCRIPTION
        "Parameter 'total-msgs' in event SIP.5"
    ::= { sipEventObjects5 3 }

sip5_task OBJECT-TYPE
    SYNTAX DisplayString
    MAX-ACCESS accessible-for-notify
    STATUS current
    DESCRIPTION
        "Parameter 'task' in event SIP.5"
    ::= { sipEventObjects5 4 }

sipEventObjects6 OBJECT-IDENTITY
    STATUS current
    DESCRIPTION
        "Event SIP.6
        Event showing type of message in process."
    ::= { sipEventsGroup 6 }

sip6_app OBJECT-TYPE
    SYNTAX DisplayString
    MAX-ACCESS accessible-for-notify
    STATUS current
    DESCRIPTION
        "Parameter 'app' in event SIP.6"
    ::= { sipEventObjects6 1 }

sip6_type OBJECT-TYPE
    SYNTAX DisplayString
    MAX-ACCESS accessible-for-notify
    STATUS current
    DESCRIPTION
        "Parameter 'type' in event SIP.6"
    ::= { sipEventObjects6 2 }

sip6_cdr OBJECT-TYPE
    SYNTAX Integer32
    MAX-ACCESS accessible-for-notify
    STATUS current
    DESCRIPTION
        "Parameter 'cdr' in event SIP.6"
    ::= { sipEventObjects6 3 }

sipEventObjects7 OBJECT-IDENTITY
    STATUS current
    DESCRIPTION
        "Event SIP.7
        Event related with client registration or unregistration received."
    ::= { sipEventsGroup 7 }

sip7_description OBJECT-TYPE
    SYNTAX DisplayString
    MAX-ACCESS accessible-for-notify
    STATUS current
    DESCRIPTION
        "Parameter 'description' in event SIP.7"
    ::= { sipEventObjects7 1 }

sip7_user OBJECT-TYPE
    SYNTAX DisplayString
    MAX-ACCESS accessible-for-notify
    STATUS current
    DESCRIPTION
        "Parameter 'user' in event SIP.7"
    ::= { sipEventObjects7 2 }

sip7_user-host OBJECT-TYPE
    SYNTAX DisplayString
    MAX-ACCESS accessible-for-notify
    STATUS current
    DESCRIPTION
        "Parameter 'user-host' in event SIP.7"
    ::= { sipEventObjects7 3 }

sip7_location OBJECT-TYPE
    SYNTAX DisplayString
    MAX-ACCESS accessible-for-notify
    STATUS current
    DESCRIPTION
        "Parameter 'location' in event SIP.7"
    ::= { sipEventObjects7 4 }

sip7_location-host OBJECT-TYPE
    SYNTAX DisplayString
    MAX-ACCESS accessible-for-notify
    STATUS current
    DESCRIPTION
        "Parameter 'location-host' in event SIP.7"
    ::= { sipEventObjects7 5 }

sip7_time-to-live OBJECT-TYPE
    SYNTAX Integer32
    MAX-ACCESS accessible-for-notify
    STATUS current
    DESCRIPTION
        "Parameter 'time-to-live' in event SIP.7"
    ::= { sipEventObjects7 6 }

sipEventObjects8 OBJECT-IDENTITY
    STATUS current
    DESCRIPTION
        "Event SIP.8
        SIP Stack event."
    ::= { sipEventsGroup 8 }

sip8_event-type OBJECT-TYPE
    SYNTAX DisplayString
    MAX-ACCESS accessible-for-notify
    STATUS current
    DESCRIPTION
        "Parameter 'event-type' in event SIP.8"
    ::= { sipEventObjects8 1 }

sip8_event OBJECT-TYPE
    SYNTAX DisplayString
    MAX-ACCESS accessible-for-notify
    STATUS current
    DESCRIPTION
        "Parameter 'event' in event SIP.8"
    ::= { sipEventObjects8 2 }

sipEventObjects9 OBJECT-IDENTITY
    STATUS current
    DESCRIPTION
        "Event SIP.9
        Event related with call state."
    ::= { sipEventsGroup 9 }

sip9_app OBJECT-TYPE
    SYNTAX DisplayString
    MAX-ACCESS accessible-for-notify
    STATUS current
    DESCRIPTION
        "Parameter 'app' in event SIP.9"
    ::= { sipEventObjects9 1 }

sip9_call-id OBJECT-TYPE
    SYNTAX Integer32
    MAX-ACCESS accessible-for-notify
    STATUS current
    DESCRIPTION
        "Parameter 'call-id' in event SIP.9"
    ::= { sipEventObjects9 2 }

sip9_org OBJECT-TYPE
    SYNTAX DisplayString
    MAX-ACCESS accessible-for-notify
    STATUS current
    DESCRIPTION
        "Parameter 'org' in event SIP.9"
    ::= { sipEventObjects9 3 }

sip9_dest OBJECT-TYPE
    SYNTAX DisplayString
    MAX-ACCESS accessible-for-notify
    STATUS current
    DESCRIPTION
        "Parameter 'dest' in event SIP.9"
    ::= { sipEventObjects9 4 }

sip9_state OBJECT-TYPE
    SYNTAX DisplayString
    MAX-ACCESS accessible-for-notify
    STATUS current
    DESCRIPTION
        "Parameter 'state' in event SIP.9"
    ::= { sipEventObjects9 5 }

sipEventObjects10 OBJECT-IDENTITY
    STATUS current
    DESCRIPTION
        "Event SIP.10
        Event related with application state."
    ::= { sipEventsGroup 10 }

sip10_app OBJECT-TYPE
    SYNTAX DisplayString
    MAX-ACCESS accessible-for-notify
    STATUS current
    DESCRIPTION
        "Parameter 'app' in event SIP.10"
    ::= { sipEventObjects10 1 }

sip10_state OBJECT-TYPE
    SYNTAX DisplayString
    MAX-ACCESS accessible-for-notify
    STATUS current
    DESCRIPTION
        "Parameter 'state' in event SIP.10"
    ::= { sipEventObjects10 2 }

sipEventObjects11 OBJECT-IDENTITY
    STATUS current
    DESCRIPTION
        "Event SIP.11
        Event showing type of message sent."
    ::= { sipEventsGroup 11 }

sip11_app OBJECT-TYPE
    SYNTAX DisplayString
    MAX-ACCESS accessible-for-notify
    STATUS current
    DESCRIPTION
        "Parameter 'app' in event SIP.11"
    ::= { sipEventObjects11 1 }

sip11_type OBJECT-TYPE
    SYNTAX DisplayString
    MAX-ACCESS accessible-for-notify
    STATUS current
    DESCRIPTION
        "Parameter 'type' in event SIP.11"
    ::= { sipEventObjects11 2 }

sip11_cdr OBJECT-TYPE
    SYNTAX Integer32
    MAX-ACCESS accessible-for-notify
    STATUS current
    DESCRIPTION
        "Parameter 'cdr' in event SIP.11"
    ::= { sipEventObjects11 3 }

sipEventObjects12 OBJECT-IDENTITY
    STATUS current
    DESCRIPTION
        "Event SIP.12
        Event showing media negotiation events."
    ::= { sipEventsGroup 12 }

sip12_event OBJECT-TYPE
    SYNTAX DisplayString
    MAX-ACCESS accessible-for-notify
    STATUS current
    DESCRIPTION
        "Parameter 'event' in event SIP.12"
    ::= { sipEventObjects12 1 }

sipEventObjects13 OBJECT-IDENTITY
    STATUS current
    DESCRIPTION
        "Event SIP.13
        Event related with registration or unregistration in external server."
    ::= { sipEventsGroup 13 }

sip13_description OBJECT-TYPE
    SYNTAX DisplayString
    MAX-ACCESS accessible-for-notify
    STATUS current
    DESCRIPTION
        "Parameter 'description' in event SIP.13"
    ::= { sipEventObjects13 1 }

sip13_user OBJECT-TYPE
    SYNTAX DisplayString
    MAX-ACCESS accessible-for-notify
    STATUS current
    DESCRIPTION
        "Parameter 'user' in event SIP.13"
    ::= { sipEventObjects13 2 }

sip13_dial-peer OBJECT-TYPE
    SYNTAX Integer32
    MAX-ACCESS accessible-for-notify
    STATUS current
    DESCRIPTION
        "Parameter 'dial-peer' in event SIP.13"
    ::= { sipEventObjects13 3 }

sip13_time-to-live OBJECT-TYPE
    SYNTAX Integer32
    MAX-ACCESS accessible-for-notify
    STATUS current
    DESCRIPTION
        "Parameter 'time-to-live' in event SIP.13"
    ::= { sipEventObjects13 4 }

sipEventObjects16 OBJECT-IDENTITY
    STATUS current
    DESCRIPTION
        "Event SIP.16
        Event showing call finnished due to keepalive failed"
    ::= { sipEventsGroup 16 }

sip16_cdr OBJECT-TYPE
    SYNTAX Integer32
    MAX-ACCESS accessible-for-notify
    STATUS current
    DESCRIPTION
        "Parameter 'cdr' in event SIP.16"
    ::= { sipEventObjects16 1 }

sipEventObjects17 OBJECT-IDENTITY
    STATUS current
    DESCRIPTION
        "Event SIP.17
        A register has expired"
    ::= { sipEventsGroup 17 }

sip17_user OBJECT-TYPE
    SYNTAX DisplayString
    MAX-ACCESS accessible-for-notify
    STATUS current
    DESCRIPTION
        "Parameter 'user' in event SIP.17"
    ::= { sipEventObjects17 1 }

sip17_user-host OBJECT-TYPE
    SYNTAX DisplayString
    MAX-ACCESS accessible-for-notify
    STATUS current
    DESCRIPTION
        "Parameter 'user-host' in event SIP.17"
    ::= { sipEventObjects17 2 }

sip17_location OBJECT-TYPE
    SYNTAX DisplayString
    MAX-ACCESS accessible-for-notify
    STATUS current
    DESCRIPTION
        "Parameter 'location' in event SIP.17"
    ::= { sipEventObjects17 3 }

sip17_location-host OBJECT-TYPE
    SYNTAX DisplayString
    MAX-ACCESS accessible-for-notify
    STATUS current
    DESCRIPTION
        "Parameter 'location-host' in event SIP.17"
    ::= { sipEventObjects17 4 }

sipEventObjects18 OBJECT-IDENTITY
    STATUS current
    DESCRIPTION
        "Event SIP.18
        Socket connect event, local connection."
    ::= { sipEventsGroup 18 }

sip18_type OBJECT-TYPE
    SYNTAX DisplayString
    MAX-ACCESS accessible-for-notify
    STATUS current
    DESCRIPTION
        "Parameter 'type' in event SIP.18"
    ::= { sipEventObjects18 1 }

sip18_identifier OBJECT-TYPE
    SYNTAX Integer32
    MAX-ACCESS accessible-for-notify
    STATUS current
    DESCRIPTION
        "Parameter 'identifier' in event SIP.18"
    ::= { sipEventObjects18 2 }

sip18_description OBJECT-TYPE
    SYNTAX DisplayString
    MAX-ACCESS accessible-for-notify
    STATUS current
    DESCRIPTION
        "Parameter 'description' in event SIP.18"
    ::= { sipEventObjects18 3 }

sipEventObjects19 OBJECT-IDENTITY
    STATUS current
    DESCRIPTION
        "Event SIP.19
        Socket accept event, remote connection."
    ::= { sipEventsGroup 19 }

sip19_type OBJECT-TYPE
    SYNTAX DisplayString
    MAX-ACCESS accessible-for-notify
    STATUS current
    DESCRIPTION
        "Parameter 'type' in event SIP.19"
    ::= { sipEventObjects19 1 }

sip19_identifier OBJECT-TYPE
    SYNTAX Integer32
    MAX-ACCESS accessible-for-notify
    STATUS current
    DESCRIPTION
        "Parameter 'identifier' in event SIP.19"
    ::= { sipEventObjects19 2 }

sip19_description OBJECT-TYPE
    SYNTAX DisplayString
    MAX-ACCESS accessible-for-notify
    STATUS current
    DESCRIPTION
        "Parameter 'description' in event SIP.19"
    ::= { sipEventObjects19 3 }

sipEventObjects20 OBJECT-IDENTITY
    STATUS current
    DESCRIPTION
        "Event SIP.20
        Socket close local event."
    ::= { sipEventsGroup 20 }

sip20_type OBJECT-TYPE
    SYNTAX DisplayString
    MAX-ACCESS accessible-for-notify
    STATUS current
    DESCRIPTION
        "Parameter 'type' in event SIP.20"
    ::= { sipEventObjects20 1 }

sip20_identifier OBJECT-TYPE
    SYNTAX Integer32
    MAX-ACCESS accessible-for-notify
    STATUS current
    DESCRIPTION
        "Parameter 'identifier' in event SIP.20"
    ::= { sipEventObjects20 2 }

sipEventObjects21 OBJECT-IDENTITY
    STATUS current
    DESCRIPTION
        "Event SIP.21
        Socket close local event."
    ::= { sipEventsGroup 21 }

sip21_type OBJECT-TYPE
    SYNTAX DisplayString
    MAX-ACCESS accessible-for-notify
    STATUS current
    DESCRIPTION
        "Parameter 'type' in event SIP.21"
    ::= { sipEventObjects21 1 }

sip21_identifier OBJECT-TYPE
    SYNTAX Integer32
    MAX-ACCESS accessible-for-notify
    STATUS current
    DESCRIPTION
        "Parameter 'identifier' in event SIP.21"
    ::= { sipEventObjects21 2 }

sipEventObjects22 OBJECT-IDENTITY
    STATUS current
    DESCRIPTION
        "Event SIP.22
        A certificate has been loaded or unloaded"
    ::= { sipEventsGroup 22 }

sip22_name OBJECT-TYPE
    SYNTAX DisplayString
    MAX-ACCESS accessible-for-notify
    STATUS current
    DESCRIPTION
        "Parameter 'name' in event SIP.22"
    ::= { sipEventObjects22 1 }

sip22_loaded OBJECT-TYPE
    SYNTAX DisplayString
    MAX-ACCESS accessible-for-notify
    STATUS current
    DESCRIPTION
        "Parameter 'loaded' in event SIP.22"
    ::= { sipEventObjects22 2 }

sipEventObjects23 OBJECT-IDENTITY
    STATUS current
    DESCRIPTION
        "Event SIP.23
        An error has happenned while loading a certificate"
    ::= { sipEventsGroup 23 }

sip23_name OBJECT-TYPE
    SYNTAX DisplayString
    MAX-ACCESS accessible-for-notify
    STATUS current
    DESCRIPTION
        "Parameter 'name' in event SIP.23"
    ::= { sipEventObjects23 1 }

sip23_error OBJECT-TYPE
    SYNTAX DisplayString
    MAX-ACCESS accessible-for-notify
    STATUS current
    DESCRIPTION
        "Parameter 'error' in event SIP.23"
    ::= { sipEventObjects23 2 }


sipNotification1 NOTIFICATION-TYPE
    OBJECTS { 
              sip1_description, 
              sip1_task 
            }
    STATUS current
    DESCRIPTION
        "Notification of Event SIP.1

        Message: 'Task: $1 $2'

        Parameters list:
              $1: sip1_description
              $2: sip1_task

        Event related with task creation/deletion."
    ::= { sipNotificationsPrefix 1 }

sipNotification2 NOTIFICATION-TYPE
    OBJECTS { 
              sip2_description, 
              sip2_message,
              sip2_task,
              sip2_cdr 
            }
    STATUS current
    DESCRIPTION
        "Notification of Event SIP.2

        Message: 'Msg: $1 $2 Task:$3, cdr $4'

        Parameters list:
              $1: sip2_description
              $2: sip2_message
              $3: sip2_task
              $4: sip2_cdr

        Event related with message processing."
    ::= { sipNotificationsPrefix 2 }

sipNotification3 NOTIFICATION-TYPE
    OBJECTS { 
              sip3_error, 
              sip3_task 
            }
    STATUS current
    DESCRIPTION
        "Notification of Event SIP.3

        Message: 'Task: $1 $2'

        Parameters list:
              $1: sip3_error
              $2: sip3_task

        Error related with task creation/deletion."
    ::= { sipNotificationsPrefix 3 }

sipNotification4 NOTIFICATION-TYPE
    OBJECTS { 
              sip4_description, 
              sip4_error,
              sip4_task,
              sip4_cdr 
            }
    STATUS current
    DESCRIPTION
        "Notification of Event SIP.4

        Message: 'Msg: $1 $2 Task:$3, cdr $4'

        Parameters list:
              $1: sip4_description
              $2: sip4_error
              $3: sip4_task
              $4: sip4_cdr

        Error related with message processing."
    ::= { sipNotificationsPrefix 4 }

sipNotification5 NOTIFICATION-TYPE
    OBJECTS { 
              sip5_queue, 
              sip5_description,
              sip5_total-msgs,
              sip5_task 
            }
    STATUS current
    DESCRIPTION
        "Notification of Event SIP.5

        Message: 'Queue: $1 $2 Msgs:$3  Task: $4'

        Parameters list:
              $1: sip5_queue
              $2: sip5_description
              $3: sip5_total-msgs
              $4: sip5_task

        Event related with queues."
    ::= { sipNotificationsPrefix 5 }

sipNotification6 NOTIFICATION-TYPE
    OBJECTS { 
              sip6_app, 
              sip6_type,
              sip6_cdr 
            }
    STATUS current
    DESCRIPTION
        "Notification of Event SIP.6

        Message: '$1 Processing Msg: $2, cdr $3'

        Parameters list:
              $1: sip6_app
              $2: sip6_type
              $3: sip6_cdr

        Event showing type of message in process."
    ::= { sipNotificationsPrefix 6 }

sipNotification7 NOTIFICATION-TYPE
    OBJECTS { 
              sip7_description, 
              sip7_user,
              sip7_user-host,
              sip7_location,
              sip7_location-host,
              sip7_time-to-live 
            }
    STATUS current
    DESCRIPTION
        "Notification of Event SIP.7

        Message: '$1: $2@$3 location $4@$5 ttl: $6'

        Parameters list:
              $1: sip7_description
              $2: sip7_user
              $3: sip7_user-host
              $4: sip7_location
              $5: sip7_location-host
              $6: sip7_time-to-live

        Event related with client registration or unregistration received."
    ::= { sipNotificationsPrefix 7 }

sipNotification8 NOTIFICATION-TYPE
    OBJECTS { 
              sip8_event-type, 
              sip8_event 
            }
    STATUS current
    DESCRIPTION
        "Notification of Event SIP.8

        Message: '$1: $2'

        Parameters list:
              $1: sip8_event-type
              $2: sip8_event

        SIP Stack event."
    ::= { sipNotificationsPrefix 8 }

sipNotification9 NOTIFICATION-TYPE
    OBJECTS { 
              sip9_app, 
              sip9_call-id,
              sip9_org,
              sip9_dest,
              sip9_state 
            }
    STATUS current
    DESCRIPTION
        "Notification of Event SIP.9

        Message: '$1: Call $2 from $3 to $4 $5'

        Parameters list:
              $1: sip9_app
              $2: sip9_call-id
              $3: sip9_org
              $4: sip9_dest
              $5: sip9_state

        Event related with call state."
    ::= { sipNotificationsPrefix 9 }

sipNotification10 NOTIFICATION-TYPE
    OBJECTS { 
              sip10_app, 
              sip10_state 
            }
    STATUS current
    DESCRIPTION
        "Notification of Event SIP.10

        Message: '$1: $2'

        Parameters list:
              $1: sip10_app
              $2: sip10_state

        Event related with application state."
    ::= { sipNotificationsPrefix 10 }

sipNotification11 NOTIFICATION-TYPE
    OBJECTS { 
              sip11_app, 
              sip11_type,
              sip11_cdr 
            }
    STATUS current
    DESCRIPTION
        "Notification of Event SIP.11

        Message: '$1 Sending Msg: $2, cdr $3'

        Parameters list:
              $1: sip11_app
              $2: sip11_type
              $3: sip11_cdr

        Event showing type of message sent."
    ::= { sipNotificationsPrefix 11 }

sipNotification12 NOTIFICATION-TYPE
    OBJECTS { 
              sip12_event 
            }
    STATUS current
    DESCRIPTION
        "Notification of Event SIP.12

        Message: 'SDP: $1'

        Parameters list:
              $1: sip12_event

        Event showing media negotiation events."
    ::= { sipNotificationsPrefix 12 }

sipNotification13 NOTIFICATION-TYPE
    OBJECTS { 
              sip13_description, 
              sip13_user,
              sip13_dial-peer,
              sip13_time-to-live 
            }
    STATUS current
    DESCRIPTION
        "Notification of Event SIP.13

        Message: '$1: User $2 dial-peer $3 ttl: $4'

        Parameters list:
              $1: sip13_description
              $2: sip13_user
              $3: sip13_dial-peer
              $4: sip13_time-to-live

        Event related with registration or unregistration in external server."
    ::= { sipNotificationsPrefix 13 }

sipNotification14 NOTIFICATION-TYPE
    STATUS current
    DESCRIPTION
        "Notification of Event SIP.14

        Message: 'Server: Survival ON'

        SIP server application enters survival mode."
    ::= { sipNotificationsPrefix 14 }

sipNotification15 NOTIFICATION-TYPE
    STATUS current
    DESCRIPTION
        "Notification of Event SIP.15

        Message: 'Server: Survival OFF'

        SIP server application finish survival mode."
    ::= { sipNotificationsPrefix 15 }

sipNotification16 NOTIFICATION-TYPE
    OBJECTS { 
              sip16_cdr 
            }
    STATUS current
    DESCRIPTION
        "Notification of Event SIP.16

        Message: 'Keep-alive failed, call finnished cdr $1'

        Parameters list:
              $1: sip16_cdr

        Event showing call finnished due to keepalive failed"
    ::= { sipNotificationsPrefix 16 }

sipNotification17 NOTIFICATION-TYPE
    OBJECTS { 
              sip17_user, 
              sip17_user-host,
              sip17_location,
              sip17_location-host 
            }
    STATUS current
    DESCRIPTION
        "Notification of Event SIP.17

        Message: 'Unregister User: $1@$2 location $3@$4'

        Parameters list:
              $1: sip17_user
              $2: sip17_user-host
              $3: sip17_location
              $4: sip17_location-host

        A register has expired"
    ::= { sipNotificationsPrefix 17 }

sipNotification18 NOTIFICATION-TYPE
    OBJECTS { 
              sip18_type, 
              sip18_identifier,
              sip18_description 
            }
    STATUS current
    DESCRIPTION
        "Notification of Event SIP.18

        Message: 'Socket $1 id:$2 open connect $3'

        Parameters list:
              $1: sip18_type
              $2: sip18_identifier
              $3: sip18_description

        Socket connect event, local connection."
    ::= { sipNotificationsPrefix 18 }

sipNotification19 NOTIFICATION-TYPE
    OBJECTS { 
              sip19_type, 
              sip19_identifier,
              sip19_description 
            }
    STATUS current
    DESCRIPTION
        "Notification of Event SIP.19

        Message: 'Socket $1 id:$2 open accept $3'

        Parameters list:
              $1: sip19_type
              $2: sip19_identifier
              $3: sip19_description

        Socket accept event, remote connection."
    ::= { sipNotificationsPrefix 19 }

sipNotification20 NOTIFICATION-TYPE
    OBJECTS { 
              sip20_type, 
              sip20_identifier 
            }
    STATUS current
    DESCRIPTION
        "Notification of Event SIP.20

        Message: 'Socket $1 id:$2 close local'

        Parameters list:
              $1: sip20_type
              $2: sip20_identifier

        Socket close local event."
    ::= { sipNotificationsPrefix 20 }

sipNotification21 NOTIFICATION-TYPE
    OBJECTS { 
              sip21_type, 
              sip21_identifier 
            }
    STATUS current
    DESCRIPTION
        "Notification of Event SIP.21

        Message: 'Socket $1 id:$2 close remote'

        Parameters list:
              $1: sip21_type
              $2: sip21_identifier

        Socket close local event."
    ::= { sipNotificationsPrefix 21 }

sipNotification22 NOTIFICATION-TYPE
    OBJECTS { 
              sip22_name, 
              sip22_loaded 
            }
    STATUS current
    DESCRIPTION
        "Notification of Event SIP.22

        Message: 'Certificate $1 $2'

        Parameters list:
              $1: sip22_name
              $2: sip22_loaded

        A certificate has been loaded or unloaded"
    ::= { sipNotificationsPrefix 22 }

sipNotification23 NOTIFICATION-TYPE
    OBJECTS { 
              sip23_name, 
              sip23_error 
            }
    STATUS current
    DESCRIPTION
        "Notification of Event SIP.23

        Message: 'Certificate $1 loading error: $2'

        Parameters list:
              $1: sip23_name
              $2: sip23_error

        An error has happenned while loading a certificate"
    ::= { sipNotificationsPrefix 23 }


END
