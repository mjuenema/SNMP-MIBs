-- file automatically created


TELDAT-TRAP-GBGP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


gbgpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the GBGP event subsystem."
    REVISION "201401200930Z"
    DESCRIPTION "Initial implementation"
        ::= { telEventTraps 169 }


gbgpEventsGroup	OBJECT IDENTIFIER	::= { gbgpTrapsMIB 1 }

gbgpNotifications	OBJECT IDENTIFIER	::= { gbgpTrapsMIB 2 }
gbgpNotificationsPrefix	OBJECT IDENTIFIER	::= { gbgpNotifications 0 }

gbgpEventObjects2 OBJECT-IDENTITY
    STATUS current
    DESCRIPTION
        "Event GBGP.2
        A connection to a ESTABLISHED BGP peer has been lost. Possible causes
        are either a keepalive timer timeout or a TCP protocol error. The status
        of this peer is changed to ACTIVE."
    ::= { gbgpEventsGroup 2 }

gbgp2_RemotePeerAddress OBJECT-TYPE
    SYNTAX IpAddress
    MAX-ACCESS accessible-for-notify
    STATUS current
    DESCRIPTION
        "Parameter 'RemotePeerAddress' in event GBGP.2"
    ::= { gbgpEventObjects2 1 }

gbgp2_AutonomousSystem OBJECT-TYPE
    SYNTAX Integer32
    MAX-ACCESS accessible-for-notify
    STATUS current
    DESCRIPTION
        "Parameter 'AutonomousSystem' in event GBGP.2"
    ::= { gbgpEventObjects2 2 }

gbgpEventObjects3 OBJECT-IDENTITY
    STATUS current
    DESCRIPTION
        "Event GBGP.3
        Syntax errors found in configuration file."
    ::= { gbgpEventsGroup 3 }

gbgp3_ParserErrors OBJECT-TYPE
    SYNTAX Integer32
    MAX-ACCESS accessible-for-notify
    STATUS current
    DESCRIPTION
        "Parameter 'ParserErrors' in event GBGP.3"
    ::= { gbgpEventObjects3 1 }

gbgpEventObjects4 OBJECT-IDENTITY
    STATUS current
    DESCRIPTION
        "Event GBGP.4
        A valid incoming BGP message has been received from a peer.
        The type of message is shown, as well as the remote peer address and
        autonomous system."
    ::= { gbgpEventsGroup 4 }

gbgp4_PacketType OBJECT-TYPE
    SYNTAX DisplayString
    MAX-ACCESS accessible-for-notify
    STATUS current
    DESCRIPTION
        "Parameter 'PacketType' in event GBGP.4"
    ::= { gbgpEventObjects4 1 }

gbgp4_RemotePeerAddress OBJECT-TYPE
    SYNTAX IpAddress
    MAX-ACCESS accessible-for-notify
    STATUS current
    DESCRIPTION
        "Parameter 'RemotePeerAddress' in event GBGP.4"
    ::= { gbgpEventObjects4 2 }

gbgp4_AutonomousSystem OBJECT-TYPE
    SYNTAX Integer32
    MAX-ACCESS accessible-for-notify
    STATUS current
    DESCRIPTION
        "Parameter 'AutonomousSystem' in event GBGP.4"
    ::= { gbgpEventObjects4 3 }

gbgpEventObjects5 OBJECT-IDENTITY
    STATUS current
    DESCRIPTION
        "Event GBGP.5
        A message is been sent to a remote peer.
        The type of message is shown, as well as the remote peer address and
        autonomous system."
    ::= { gbgpEventsGroup 5 }

gbgp5_PacketType OBJECT-TYPE
    SYNTAX DisplayString
    MAX-ACCESS accessible-for-notify
    STATUS current
    DESCRIPTION
        "Parameter 'PacketType' in event GBGP.5"
    ::= { gbgpEventObjects5 1 }

gbgp5_RemotePeerAddress OBJECT-TYPE
    SYNTAX IpAddress
    MAX-ACCESS accessible-for-notify
    STATUS current
    DESCRIPTION
        "Parameter 'RemotePeerAddress' in event GBGP.5"
    ::= { gbgpEventObjects5 2 }

gbgp5_AutonomousSystem OBJECT-TYPE
    SYNTAX Integer32
    MAX-ACCESS accessible-for-notify
    STATUS current
    DESCRIPTION
        "Parameter 'AutonomousSystem' in event GBGP.5"
    ::= { gbgpEventObjects5 3 }

gbgpEventObjects6 OBJECT-IDENTITY
    STATUS current
    DESCRIPTION
        "Event GBGP.6
        An incoming BGP message has been rejected. The rejection cause is shown
        in the message."
    ::= { gbgpEventsGroup 6 }

gbgp6_RemotePeerName OBJECT-TYPE
    SYNTAX DisplayString
    MAX-ACCESS accessible-for-notify
    STATUS current
    DESCRIPTION
        "Parameter 'RemotePeerName' in event GBGP.6"
    ::= { gbgpEventObjects6 1 }

gbgp6_ErrorMessage OBJECT-TYPE
    SYNTAX DisplayString
    MAX-ACCESS accessible-for-notify
    STATUS current
    DESCRIPTION
        "Parameter 'ErrorMessage' in event GBGP.6"
    ::= { gbgpEventObjects6 2 }

gbgpEventObjects7 OBJECT-IDENTITY
    STATUS current
    DESCRIPTION
        "Event GBGP.7
        An active open from a remote system has been rejected. The address, AS
        and rejection cause are shown."
    ::= { gbgpEventsGroup 7 }

gbgp7_RemotePeerName OBJECT-TYPE
    SYNTAX DisplayString
    MAX-ACCESS accessible-for-notify
    STATUS current
    DESCRIPTION
        "Parameter 'RemotePeerName' in event GBGP.7"
    ::= { gbgpEventObjects7 1 }

gbgp7_ErrorMessage OBJECT-TYPE
    SYNTAX DisplayString
    MAX-ACCESS accessible-for-notify
    STATUS current
    DESCRIPTION
        "Parameter 'ErrorMessage' in event GBGP.7"
    ::= { gbgpEventObjects7 2 }

gbgpEventObjects8 OBJECT-IDENTITY
    STATUS current
    DESCRIPTION
        "Event GBGP.8
        A valid connection has been made to a configured BGP peer. Peer status
        is changed to ESTABLISHED."
    ::= { gbgpEventsGroup 8 }

gbgp8_RemotePeerAddress OBJECT-TYPE
    SYNTAX IpAddress
    MAX-ACCESS accessible-for-notify
    STATUS current
    DESCRIPTION
        "Parameter 'RemotePeerAddress' in event GBGP.8"
    ::= { gbgpEventObjects8 1 }

gbgp8_AutonomousSystem OBJECT-TYPE
    SYNTAX Integer32
    MAX-ACCESS accessible-for-notify
    STATUS current
    DESCRIPTION
        "Parameter 'AutonomousSystem' in event GBGP.8"
    ::= { gbgpEventObjects8 2 }

gbgpEventObjects10 OBJECT-IDENTITY
    STATUS current
    DESCRIPTION
        "Event GBGP.10
        An update message for the route shown has been received. This message
        does not mean that this route has been made active, it just means that
        the system has received information for this route from a BGP peer. This
        route will be processed, and, taking into account the
        configured preference rules, will be or not exported to the active
        routes table. To be able to see changes in the active RT, please
        use the IP subsystem events."
    ::= { gbgpEventsGroup 10 }

gbgp10_RouteDest OBJECT-TYPE
    SYNTAX IpAddress
    MAX-ACCESS accessible-for-notify
    STATUS current
    DESCRIPTION
        "Parameter 'RouteDest' in event GBGP.10"
    ::= { gbgpEventObjects10 1 }

gbgp10_RouteMask OBJECT-TYPE
    SYNTAX IpAddress
    MAX-ACCESS accessible-for-notify
    STATUS current
    DESCRIPTION
        "Parameter 'RouteMask' in event GBGP.10"
    ::= { gbgpEventObjects10 2 }

gbgp10_NextHop OBJECT-TYPE
    SYNTAX IpAddress
    MAX-ACCESS accessible-for-notify
    STATUS current
    DESCRIPTION
        "Parameter 'NextHop' in event GBGP.10"
    ::= { gbgpEventObjects10 3 }

gbgp10_Preference OBJECT-TYPE
    SYNTAX Integer32
    MAX-ACCESS accessible-for-notify
    STATUS current
    DESCRIPTION
        "Parameter 'Preference' in event GBGP.10"
    ::= { gbgpEventObjects10 4 }

gbgp10_Metric OBJECT-TYPE
    SYNTAX DisplayString
    MAX-ACCESS accessible-for-notify
    STATUS current
    DESCRIPTION
        "Parameter 'Metric' in event GBGP.10"
    ::= { gbgpEventObjects10 5 }

gbgp10_LocalPref OBJECT-TYPE
    SYNTAX DisplayString
    MAX-ACCESS accessible-for-notify
    STATUS current
    DESCRIPTION
        "Parameter 'LocalPref' in event GBGP.10"
    ::= { gbgpEventObjects10 6 }

gbgpEventObjects11 OBJECT-IDENTITY
    STATUS current
    DESCRIPTION
        "Event GBGP.11
        An unreach message has been received for this route. This message
        does not mean that this route will be deleted from the active RT
        (it is possible that the route was not even made active when it
        was received). To be able to see changes in the active RT, please
        use the IP subsystem events."
    ::= { gbgpEventsGroup 11 }

gbgp11_RouteDest OBJECT-TYPE
    SYNTAX IpAddress
    MAX-ACCESS accessible-for-notify
    STATUS current
    DESCRIPTION
        "Parameter 'RouteDest' in event GBGP.11"
    ::= { gbgpEventObjects11 1 }

gbgp11_RouteMask OBJECT-TYPE
    SYNTAX IpAddress
    MAX-ACCESS accessible-for-notify
    STATUS current
    DESCRIPTION
        "Parameter 'RouteMask' in event GBGP.11"
    ::= { gbgpEventObjects11 2 }

gbgp11_BGPPeer OBJECT-TYPE
    SYNTAX DisplayString
    MAX-ACCESS accessible-for-notify
    STATUS current
    DESCRIPTION
        "Parameter 'BGPPeer' in event GBGP.11"
    ::= { gbgpEventObjects11 3 }

gbgpEventObjects12 OBJECT-IDENTITY
    STATUS current
    DESCRIPTION
        "Event GBGP.12
        The holdtime for a given BGP peer has expired."
    ::= { gbgpEventsGroup 12 }

gbgp12_RemotePeerAddress OBJECT-TYPE
    SYNTAX IpAddress
    MAX-ACCESS accessible-for-notify
    STATUS current
    DESCRIPTION
        "Parameter 'RemotePeerAddress' in event GBGP.12"
    ::= { gbgpEventObjects12 1 }

gbgp12_AutonomousSystem OBJECT-TYPE
    SYNTAX Integer32
    MAX-ACCESS accessible-for-notify
    STATUS current
    DESCRIPTION
        "Parameter 'AutonomousSystem' in event GBGP.12"
    ::= { gbgpEventObjects12 2 }

gbgpEventObjects14 OBJECT-IDENTITY
    STATUS current
    DESCRIPTION
        "Event GBGP.14
        Deleting route from BGP routing Database."
    ::= { gbgpEventsGroup 14 }

gbgp14_Dest OBJECT-TYPE
    SYNTAX IpAddress
    MAX-ACCESS accessible-for-notify
    STATUS current
    DESCRIPTION
        "Parameter 'Dest' in event GBGP.14"
    ::= { gbgpEventObjects14 1 }

gbgp14_Mask OBJECT-TYPE
    SYNTAX IpAddress
    MAX-ACCESS accessible-for-notify
    STATUS current
    DESCRIPTION
        "Parameter 'Mask' in event GBGP.14"
    ::= { gbgpEventObjects14 2 }

gbgp14_BGPPeer OBJECT-TYPE
    SYNTAX DisplayString
    MAX-ACCESS accessible-for-notify
    STATUS current
    DESCRIPTION
        "Parameter 'BGPPeer' in event GBGP.14"
    ::= { gbgpEventObjects14 3 }

gbgpEventObjects15 OBJECT-IDENTITY
    STATUS current
    DESCRIPTION
        "Event GBGP.15
        Adding route to BGP routing Database."
    ::= { gbgpEventsGroup 15 }

gbgp15_Dest OBJECT-TYPE
    SYNTAX IpAddress
    MAX-ACCESS accessible-for-notify
    STATUS current
    DESCRIPTION
        "Parameter 'Dest' in event GBGP.15"
    ::= { gbgpEventObjects15 1 }

gbgp15_Mask OBJECT-TYPE
    SYNTAX IpAddress
    MAX-ACCESS accessible-for-notify
    STATUS current
    DESCRIPTION
        "Parameter 'Mask' in event GBGP.15"
    ::= { gbgpEventObjects15 2 }

gbgp15_NextHop OBJECT-TYPE
    SYNTAX IpAddress
    MAX-ACCESS accessible-for-notify
    STATUS current
    DESCRIPTION
        "Parameter 'NextHop' in event GBGP.15"
    ::= { gbgpEventObjects15 3 }

gbgpEventObjects16 OBJECT-IDENTITY
    STATUS current
    DESCRIPTION
        "Event GBGP.16
        Adding direct route to BGP routing Database."
    ::= { gbgpEventsGroup 16 }

gbgp16_Dest OBJECT-TYPE
    SYNTAX IpAddress
    MAX-ACCESS accessible-for-notify
    STATUS current
    DESCRIPTION
        "Parameter 'Dest' in event GBGP.16"
    ::= { gbgpEventObjects16 1 }

gbgp16_Mask OBJECT-TYPE
    SYNTAX IpAddress
    MAX-ACCESS accessible-for-notify
    STATUS current
    DESCRIPTION
        "Parameter 'Mask' in event GBGP.16"
    ::= { gbgpEventObjects16 2 }

gbgpEventObjects18 OBJECT-IDENTITY
    STATUS current
    DESCRIPTION
        "Event GBGP.18
        BGP subsystem is trying to connect to a remote peer."
    ::= { gbgpEventsGroup 18 }

gbgp18_RemotePeer OBJECT-TYPE
    SYNTAX DisplayString
    MAX-ACCESS accessible-for-notify
    STATUS current
    DESCRIPTION
        "Parameter 'RemotePeer' in event GBGP.18"
    ::= { gbgpEventObjects18 1 }

gbgpEventObjects19 OBJECT-IDENTITY
    STATUS current
    DESCRIPTION
        "Event GBGP.19
        A notification message has been sent or received."
    ::= { gbgpEventsGroup 19 }

gbgp19_fromto OBJECT-TYPE
    SYNTAX DisplayString
    MAX-ACCESS accessible-for-notify
    STATUS current
    DESCRIPTION
        "Parameter 'fromto' in event GBGP.19"
    ::= { gbgpEventObjects19 1 }

gbgp19_RemoteAS OBJECT-TYPE
    SYNTAX DisplayString
    MAX-ACCESS accessible-for-notify
    STATUS current
    DESCRIPTION
        "Parameter 'RemoteAS' in event GBGP.19"
    ::= { gbgpEventObjects19 2 }

gbgp19_code OBJECT-TYPE
    SYNTAX DisplayString
    MAX-ACCESS accessible-for-notify
    STATUS current
    DESCRIPTION
        "Parameter 'code' in event GBGP.19"
    ::= { gbgpEventObjects19 3 }

gbgp19_subcode OBJECT-TYPE
    SYNTAX Integer32
    MAX-ACCESS accessible-for-notify
    STATUS current
    DESCRIPTION
        "Parameter 'subcode' in event GBGP.19"
    ::= { gbgpEventObjects19 4 }

gbgpEventObjects20 OBJECT-IDENTITY
    STATUS current
    DESCRIPTION
        "Event GBGP.20
        Changing state of peer to idled. The cause is printed at the end of
        the message."
    ::= { gbgpEventsGroup 20 }

gbgp20_RemotePeer OBJECT-TYPE
    SYNTAX DisplayString
    MAX-ACCESS accessible-for-notify
    STATUS current
    DESCRIPTION
        "Parameter 'RemotePeer' in event GBGP.20"
    ::= { gbgpEventObjects20 1 }

gbgp20_cause OBJECT-TYPE
    SYNTAX DisplayString
    MAX-ACCESS accessible-for-notify
    STATUS current
    DESCRIPTION
        "Parameter 'cause' in event GBGP.20"
    ::= { gbgpEventObjects20 2 }

gbgpEventObjects22 OBJECT-IDENTITY
    STATUS current
    DESCRIPTION
        "Event GBGP.22
        The error printed occurred while reading the configuration."
    ::= { gbgpEventsGroup 22 }

gbgp22_DiagnosticMessage OBJECT-TYPE
    SYNTAX DisplayString
    MAX-ACCESS accessible-for-notify
    STATUS current
    DESCRIPTION
        "Parameter 'DiagnosticMessage' in event GBGP.22"
    ::= { gbgpEventObjects22 1 }

gbgpEventObjects23 OBJECT-IDENTITY
    STATUS current
    DESCRIPTION
        "Event GBGP.23
        An update packet has been received with community attributes."
    ::= { gbgpEventsGroup 23 }

gbgp23_NumberOfComms OBJECT-TYPE
    SYNTAX Integer32
    MAX-ACCESS accessible-for-notify
    STATUS current
    DESCRIPTION
        "Parameter 'NumberOfComms' in event GBGP.23"
    ::= { gbgpEventObjects23 1 }

gbgp23_Communities OBJECT-TYPE
    SYNTAX DisplayString
    MAX-ACCESS accessible-for-notify
    STATUS current
    DESCRIPTION
        "Parameter 'Communities' in event GBGP.23"
    ::= { gbgpEventObjects23 2 }

gbgpEventObjects24 OBJECT-IDENTITY
    STATUS current
    DESCRIPTION
        "Event GBGP.24
        A route received in an update packet has been discarded due to
        preconfigured route-map in/out policy for this neighbor."
    ::= { gbgpEventsGroup 24 }

gbgp24_RouteDest OBJECT-TYPE
    SYNTAX IpAddress
    MAX-ACCESS accessible-for-notify
    STATUS current
    DESCRIPTION
        "Parameter 'RouteDest' in event GBGP.24"
    ::= { gbgpEventObjects24 1 }

gbgp24_RouteMask OBJECT-TYPE
    SYNTAX IpAddress
    MAX-ACCESS accessible-for-notify
    STATUS current
    DESCRIPTION
        "Parameter 'RouteMask' in event GBGP.24"
    ::= { gbgpEventObjects24 2 }

gbgp24_Route-MapName OBJECT-TYPE
    SYNTAX DisplayString
    MAX-ACCESS accessible-for-notify
    STATUS current
    DESCRIPTION
        "Parameter 'Route-MapName' in event GBGP.24"
    ::= { gbgpEventObjects24 3 }

gbgpEventObjects25 OBJECT-IDENTITY
    STATUS current
    DESCRIPTION
        "Event GBGP.25
        The local pref value of a route received in an update packet
        has been changed due to a preconfigured route-map in/out policy
        for this neighbor."
    ::= { gbgpEventsGroup 25 }

gbgp25_RouteDest OBJECT-TYPE
    SYNTAX IpAddress
    MAX-ACCESS accessible-for-notify
    STATUS current
    DESCRIPTION
        "Parameter 'RouteDest' in event GBGP.25"
    ::= { gbgpEventObjects25 1 }

gbgp25_RouteMask OBJECT-TYPE
    SYNTAX IpAddress
    MAX-ACCESS accessible-for-notify
    STATUS current
    DESCRIPTION
        "Parameter 'RouteMask' in event GBGP.25"
    ::= { gbgpEventObjects25 2 }

gbgp25_OldLocalPref OBJECT-TYPE
    SYNTAX DisplayString
    MAX-ACCESS accessible-for-notify
    STATUS current
    DESCRIPTION
        "Parameter 'OldLocalPref' in event GBGP.25"
    ::= { gbgpEventObjects25 3 }

gbgp25_NewLocalPref OBJECT-TYPE
    SYNTAX DisplayString
    MAX-ACCESS accessible-for-notify
    STATUS current
    DESCRIPTION
        "Parameter 'NewLocalPref' in event GBGP.25"
    ::= { gbgpEventObjects25 4 }

gbgpEventObjects26 OBJECT-IDENTITY
    STATUS current
    DESCRIPTION
        "Event GBGP.26
        Could not apply the route-map policy: max number of communities per
        route exceeded."
    ::= { gbgpEventsGroup 26 }

gbgp26_RouteMapName OBJECT-TYPE
    SYNTAX DisplayString
    MAX-ACCESS accessible-for-notify
    STATUS current
    DESCRIPTION
        "Parameter 'RouteMapName' in event GBGP.26"
    ::= { gbgpEventObjects26 1 }

gbgpEventObjects27 OBJECT-IDENTITY
    STATUS current
    DESCRIPTION
        "Event GBGP.27
        The metric value of a route received in an update packet
        has been changed due to a preconfigured route-map in/out policy
        for this neighbor."
    ::= { gbgpEventsGroup 27 }

gbgp27_RouteDest OBJECT-TYPE
    SYNTAX IpAddress
    MAX-ACCESS accessible-for-notify
    STATUS current
    DESCRIPTION
        "Parameter 'RouteDest' in event GBGP.27"
    ::= { gbgpEventObjects27 1 }

gbgp27_RouteMask OBJECT-TYPE
    SYNTAX IpAddress
    MAX-ACCESS accessible-for-notify
    STATUS current
    DESCRIPTION
        "Parameter 'RouteMask' in event GBGP.27"
    ::= { gbgpEventObjects27 2 }

gbgp27_OldMetric OBJECT-TYPE
    SYNTAX DisplayString
    MAX-ACCESS accessible-for-notify
    STATUS current
    DESCRIPTION
        "Parameter 'OldMetric' in event GBGP.27"
    ::= { gbgpEventObjects27 3 }

gbgp27_NewMetric OBJECT-TYPE
    SYNTAX DisplayString
    MAX-ACCESS accessible-for-notify
    STATUS current
    DESCRIPTION
        "Parameter 'NewMetric' in event GBGP.27"
    ::= { gbgpEventObjects27 4 }

gbgpEventObjects28 OBJECT-IDENTITY
    STATUS current
    DESCRIPTION
        "Event GBGP.28
        The status of the specified peer has changed from a higher
        numbered status to a lower numbered status."
    ::= { gbgpEventsGroup 28 }

gbgp28_RemotePeerAddress OBJECT-TYPE
    SYNTAX IpAddress
    MAX-ACCESS accessible-for-notify
    STATUS current
    DESCRIPTION
        "Parameter 'RemotePeerAddress' in event GBGP.28"
    ::= { gbgpEventObjects28 1 }

gbgp28_AutonomousSystem OBJECT-TYPE
    SYNTAX Integer32
    MAX-ACCESS accessible-for-notify
    STATUS current
    DESCRIPTION
        "Parameter 'AutonomousSystem' in event GBGP.28"
    ::= { gbgpEventObjects28 2 }

gbgpEventObjects29 OBJECT-IDENTITY
    STATUS current
    DESCRIPTION
        "Event GBGP.29
        A connection to a ESTABLISHED BGP peer has been lost. Possible causes
        are either a keepalive timer timeout or a TCP protocol error. The status
        of this peer is changed to ACTIVE."
    ::= { gbgpEventsGroup 29 }

gbgp29_RemotePeerAddress OBJECT-TYPE
    SYNTAX DisplayString
    MAX-ACCESS accessible-for-notify
    STATUS current
    DESCRIPTION
        "Parameter 'RemotePeerAddress' in event GBGP.29"
    ::= { gbgpEventObjects29 1 }

gbgp29_AutonomousSystem OBJECT-TYPE
    SYNTAX Integer32
    MAX-ACCESS accessible-for-notify
    STATUS current
    DESCRIPTION
        "Parameter 'AutonomousSystem' in event GBGP.29"
    ::= { gbgpEventObjects29 2 }

gbgpEventObjects30 OBJECT-IDENTITY
    STATUS current
    DESCRIPTION
        "Event GBGP.30
        A valid incoming BGP message has been received from a peer.
        The type of message is shown, as well as the remote peer address and
        autonomous system."
    ::= { gbgpEventsGroup 30 }

gbgp30_PacketType OBJECT-TYPE
    SYNTAX DisplayString
    MAX-ACCESS accessible-for-notify
    STATUS current
    DESCRIPTION
        "Parameter 'PacketType' in event GBGP.30"
    ::= { gbgpEventObjects30 1 }

gbgp30_RemotePeerAddress OBJECT-TYPE
    SYNTAX DisplayString
    MAX-ACCESS accessible-for-notify
    STATUS current
    DESCRIPTION
        "Parameter 'RemotePeerAddress' in event GBGP.30"
    ::= { gbgpEventObjects30 2 }

gbgp30_AutonomousSystem OBJECT-TYPE
    SYNTAX Integer32
    MAX-ACCESS accessible-for-notify
    STATUS current
    DESCRIPTION
        "Parameter 'AutonomousSystem' in event GBGP.30"
    ::= { gbgpEventObjects30 3 }

gbgpEventObjects31 OBJECT-IDENTITY
    STATUS current
    DESCRIPTION
        "Event GBGP.31
        A message is been sent to a remote peer.
        The type of message is shown, as well as the remote peer address and
        autonomous system."
    ::= { gbgpEventsGroup 31 }

gbgp31_PacketType OBJECT-TYPE
    SYNTAX DisplayString
    MAX-ACCESS accessible-for-notify
    STATUS current
    DESCRIPTION
        "Parameter 'PacketType' in event GBGP.31"
    ::= { gbgpEventObjects31 1 }

gbgp31_RemotePeerAddress OBJECT-TYPE
    SYNTAX DisplayString
    MAX-ACCESS accessible-for-notify
    STATUS current
    DESCRIPTION
        "Parameter 'RemotePeerAddress' in event GBGP.31"
    ::= { gbgpEventObjects31 2 }

gbgp31_AutonomousSystem OBJECT-TYPE
    SYNTAX Integer32
    MAX-ACCESS accessible-for-notify
    STATUS current
    DESCRIPTION
        "Parameter 'AutonomousSystem' in event GBGP.31"
    ::= { gbgpEventObjects31 3 }

gbgpEventObjects32 OBJECT-IDENTITY
    STATUS current
    DESCRIPTION
        "Event GBGP.32
        A valid connection has been made to a configured BGP peer. Peer status
        is changed to ESTABLISHED."
    ::= { gbgpEventsGroup 32 }

gbgp32_RemotePeerAddress OBJECT-TYPE
    SYNTAX DisplayString
    MAX-ACCESS accessible-for-notify
    STATUS current
    DESCRIPTION
        "Parameter 'RemotePeerAddress' in event GBGP.32"
    ::= { gbgpEventObjects32 1 }

gbgp32_AutonomousSystem OBJECT-TYPE
    SYNTAX Integer32
    MAX-ACCESS accessible-for-notify
    STATUS current
    DESCRIPTION
        "Parameter 'AutonomousSystem' in event GBGP.32"
    ::= { gbgpEventObjects32 2 }

gbgpEventObjects33 OBJECT-IDENTITY
    STATUS current
    DESCRIPTION
        "Event GBGP.33
        An update message for the route shown has been received. This message
        does not mean that this route has been made active, it just means that
        the system has received information for this route from a BGP peer. This
        route will be processed, and, taking into account the
        configured preference rules, will be or not exported to the active
        routes table. To be able to see changes in the active RT, please
        use the IPv6 subsystem events."
    ::= { gbgpEventsGroup 33 }

gbgp33_RouteDest OBJECT-TYPE
    SYNTAX DisplayString
    MAX-ACCESS accessible-for-notify
    STATUS current
    DESCRIPTION
        "Parameter 'RouteDest' in event GBGP.33"
    ::= { gbgpEventObjects33 1 }

gbgp33_RoutePrefixLen OBJECT-TYPE
    SYNTAX Integer32
    MAX-ACCESS accessible-for-notify
    STATUS current
    DESCRIPTION
        "Parameter 'RoutePrefixLen' in event GBGP.33"
    ::= { gbgpEventObjects33 2 }

gbgp33_NextHop OBJECT-TYPE
    SYNTAX DisplayString
    MAX-ACCESS accessible-for-notify
    STATUS current
    DESCRIPTION
        "Parameter 'NextHop' in event GBGP.33"
    ::= { gbgpEventObjects33 3 }

gbgp33_Preference OBJECT-TYPE
    SYNTAX Integer32
    MAX-ACCESS accessible-for-notify
    STATUS current
    DESCRIPTION
        "Parameter 'Preference' in event GBGP.33"
    ::= { gbgpEventObjects33 4 }

gbgp33_Metric OBJECT-TYPE
    SYNTAX DisplayString
    MAX-ACCESS accessible-for-notify
    STATUS current
    DESCRIPTION
        "Parameter 'Metric' in event GBGP.33"
    ::= { gbgpEventObjects33 5 }

gbgp33_LocalPref OBJECT-TYPE
    SYNTAX DisplayString
    MAX-ACCESS accessible-for-notify
    STATUS current
    DESCRIPTION
        "Parameter 'LocalPref' in event GBGP.33"
    ::= { gbgpEventObjects33 6 }

gbgpEventObjects34 OBJECT-IDENTITY
    STATUS current
    DESCRIPTION
        "Event GBGP.34
        An update message for the route shown has been received. This message
        does not mean that this route has been made active, it just means that
        the system has received information for this route from a BGP peer. This
        route will be processed, and, taking into account the
        configured preference rules, will be or not exported to the active
        routes table. To be able to see changes in the active RT, please
        use the IPv6 subsystem events."
    ::= { gbgpEventsGroup 34 }

gbgp34_RouteDest OBJECT-TYPE
    SYNTAX DisplayString
    MAX-ACCESS accessible-for-notify
    STATUS current
    DESCRIPTION
        "Parameter 'RouteDest' in event GBGP.34"
    ::= { gbgpEventObjects34 1 }

gbgp34_RoutePrefixLen OBJECT-TYPE
    SYNTAX Integer32
    MAX-ACCESS accessible-for-notify
    STATUS current
    DESCRIPTION
        "Parameter 'RoutePrefixLen' in event GBGP.34"
    ::= { gbgpEventObjects34 2 }

gbgp34_NextHop OBJECT-TYPE
    SYNTAX DisplayString
    MAX-ACCESS accessible-for-notify
    STATUS current
    DESCRIPTION
        "Parameter 'NextHop' in event GBGP.34"
    ::= { gbgpEventObjects34 3 }

gbgp34_NextHopLocal OBJECT-TYPE
    SYNTAX DisplayString
    MAX-ACCESS accessible-for-notify
    STATUS current
    DESCRIPTION
        "Parameter 'NextHopLocal' in event GBGP.34"
    ::= { gbgpEventObjects34 4 }

gbgp34_Preference OBJECT-TYPE
    SYNTAX Integer32
    MAX-ACCESS accessible-for-notify
    STATUS current
    DESCRIPTION
        "Parameter 'Preference' in event GBGP.34"
    ::= { gbgpEventObjects34 5 }

gbgp34_Metric OBJECT-TYPE
    SYNTAX DisplayString
    MAX-ACCESS accessible-for-notify
    STATUS current
    DESCRIPTION
        "Parameter 'Metric' in event GBGP.34"
    ::= { gbgpEventObjects34 6 }

gbgp34_LocalPref OBJECT-TYPE
    SYNTAX DisplayString
    MAX-ACCESS accessible-for-notify
    STATUS current
    DESCRIPTION
        "Parameter 'LocalPref' in event GBGP.34"
    ::= { gbgpEventObjects34 7 }

gbgpEventObjects35 OBJECT-IDENTITY
    STATUS current
    DESCRIPTION
        "Event GBGP.35
        An unreach message has been received for this route. This message
        does not mean that this route will be deleted from the active RT
        (it is possible that the route was not even made active when it
        was received). To be able to see changes in the active RT, please
        use the IPv6 subsystem events."
    ::= { gbgpEventsGroup 35 }

gbgp35_RouteDest OBJECT-TYPE
    SYNTAX DisplayString
    MAX-ACCESS accessible-for-notify
    STATUS current
    DESCRIPTION
        "Parameter 'RouteDest' in event GBGP.35"
    ::= { gbgpEventObjects35 1 }

gbgp35_RoutePrefixLen OBJECT-TYPE
    SYNTAX Integer32
    MAX-ACCESS accessible-for-notify
    STATUS current
    DESCRIPTION
        "Parameter 'RoutePrefixLen' in event GBGP.35"
    ::= { gbgpEventObjects35 2 }

gbgp35_BGPPeer OBJECT-TYPE
    SYNTAX DisplayString
    MAX-ACCESS accessible-for-notify
    STATUS current
    DESCRIPTION
        "Parameter 'BGPPeer' in event GBGP.35"
    ::= { gbgpEventObjects35 3 }

gbgpEventObjects36 OBJECT-IDENTITY
    STATUS current
    DESCRIPTION
        "Event GBGP.36
        The holdtime for a given BGP peer has expired."
    ::= { gbgpEventsGroup 36 }

gbgp36_RemotePeerAddress OBJECT-TYPE
    SYNTAX DisplayString
    MAX-ACCESS accessible-for-notify
    STATUS current
    DESCRIPTION
        "Parameter 'RemotePeerAddress' in event GBGP.36"
    ::= { gbgpEventObjects36 1 }

gbgp36_AutonomousSystem OBJECT-TYPE
    SYNTAX Integer32
    MAX-ACCESS accessible-for-notify
    STATUS current
    DESCRIPTION
        "Parameter 'AutonomousSystem' in event GBGP.36"
    ::= { gbgpEventObjects36 2 }

gbgpEventObjects37 OBJECT-IDENTITY
    STATUS current
    DESCRIPTION
        "Event GBGP.37
        Adding route into BGP routing Database."
    ::= { gbgpEventsGroup 37 }

gbgp37_Dest OBJECT-TYPE
    SYNTAX DisplayString
    MAX-ACCESS accessible-for-notify
    STATUS current
    DESCRIPTION
        "Parameter 'Dest' in event GBGP.37"
    ::= { gbgpEventObjects37 1 }

gbgp37_PrefixLen OBJECT-TYPE
    SYNTAX Integer32
    MAX-ACCESS accessible-for-notify
    STATUS current
    DESCRIPTION
        "Parameter 'PrefixLen' in event GBGP.37"
    ::= { gbgpEventObjects37 2 }

gbgp37_NextHop OBJECT-TYPE
    SYNTAX DisplayString
    MAX-ACCESS accessible-for-notify
    STATUS current
    DESCRIPTION
        "Parameter 'NextHop' in event GBGP.37"
    ::= { gbgpEventObjects37 3 }

gbgpEventObjects38 OBJECT-IDENTITY
    STATUS current
    DESCRIPTION
        "Event GBGP.38
        Adding direct route to BGP routing Database."
    ::= { gbgpEventsGroup 38 }

gbgp38_Dest OBJECT-TYPE
    SYNTAX DisplayString
    MAX-ACCESS accessible-for-notify
    STATUS current
    DESCRIPTION
        "Parameter 'Dest' in event GBGP.38"
    ::= { gbgpEventObjects38 1 }

gbgp38_PrefixLen OBJECT-TYPE
    SYNTAX Integer32
    MAX-ACCESS accessible-for-notify
    STATUS current
    DESCRIPTION
        "Parameter 'PrefixLen' in event GBGP.38"
    ::= { gbgpEventObjects38 2 }

gbgpEventObjects39 OBJECT-IDENTITY
    STATUS current
    DESCRIPTION
        "Event GBGP.39
        A route received in an update packet has been discarded due to
        preconfigured route-map in/out policy for this neighbor."
    ::= { gbgpEventsGroup 39 }

gbgp39_RouteDest OBJECT-TYPE
    SYNTAX DisplayString
    MAX-ACCESS accessible-for-notify
    STATUS current
    DESCRIPTION
        "Parameter 'RouteDest' in event GBGP.39"
    ::= { gbgpEventObjects39 1 }

gbgp39_RoutePrefixLen OBJECT-TYPE
    SYNTAX Integer32
    MAX-ACCESS accessible-for-notify
    STATUS current
    DESCRIPTION
        "Parameter 'RoutePrefixLen' in event GBGP.39"
    ::= { gbgpEventObjects39 2 }

gbgp39_Route-MapName OBJECT-TYPE
    SYNTAX DisplayString
    MAX-ACCESS accessible-for-notify
    STATUS current
    DESCRIPTION
        "Parameter 'Route-MapName' in event GBGP.39"
    ::= { gbgpEventObjects39 3 }

gbgpEventObjects40 OBJECT-IDENTITY
    STATUS current
    DESCRIPTION
        "Event GBGP.40
        The local pref value of a route received in an update packet
        has been changed due to a preconfigured route-map in/out policy
        for this neighbor."
    ::= { gbgpEventsGroup 40 }

gbgp40_RouteDest OBJECT-TYPE
    SYNTAX DisplayString
    MAX-ACCESS accessible-for-notify
    STATUS current
    DESCRIPTION
        "Parameter 'RouteDest' in event GBGP.40"
    ::= { gbgpEventObjects40 1 }

gbgp40_RoutePrefixLen OBJECT-TYPE
    SYNTAX Integer32
    MAX-ACCESS accessible-for-notify
    STATUS current
    DESCRIPTION
        "Parameter 'RoutePrefixLen' in event GBGP.40"
    ::= { gbgpEventObjects40 2 }

gbgp40_OldLocalPref OBJECT-TYPE
    SYNTAX DisplayString
    MAX-ACCESS accessible-for-notify
    STATUS current
    DESCRIPTION
        "Parameter 'OldLocalPref' in event GBGP.40"
    ::= { gbgpEventObjects40 3 }

gbgp40_NewLocalPref OBJECT-TYPE
    SYNTAX DisplayString
    MAX-ACCESS accessible-for-notify
    STATUS current
    DESCRIPTION
        "Parameter 'NewLocalPref' in event GBGP.40"
    ::= { gbgpEventObjects40 4 }

gbgpEventObjects41 OBJECT-IDENTITY
    STATUS current
    DESCRIPTION
        "Event GBGP.41
        The metric value of a route received in an update packet
        has been changed due to a preconfigured route-map in/out policy
        for this neighbor."
    ::= { gbgpEventsGroup 41 }

gbgp41_RouteDest OBJECT-TYPE
    SYNTAX DisplayString
    MAX-ACCESS accessible-for-notify
    STATUS current
    DESCRIPTION
        "Parameter 'RouteDest' in event GBGP.41"
    ::= { gbgpEventObjects41 1 }

gbgp41_RoutePrefixLen OBJECT-TYPE
    SYNTAX Integer32
    MAX-ACCESS accessible-for-notify
    STATUS current
    DESCRIPTION
        "Parameter 'RoutePrefixLen' in event GBGP.41"
    ::= { gbgpEventObjects41 2 }

gbgp41_OldMetric OBJECT-TYPE
    SYNTAX DisplayString
    MAX-ACCESS accessible-for-notify
    STATUS current
    DESCRIPTION
        "Parameter 'OldMetric' in event GBGP.41"
    ::= { gbgpEventObjects41 3 }

gbgp41_NewMetric OBJECT-TYPE
    SYNTAX DisplayString
    MAX-ACCESS accessible-for-notify
    STATUS current
    DESCRIPTION
        "Parameter 'NewMetric' in event GBGP.41"
    ::= { gbgpEventObjects41 4 }

gbgpEventObjects42 OBJECT-IDENTITY
    STATUS current
    DESCRIPTION
        "Event GBGP.42
        The nexthop value of a route received in an update packet
        has been changed due to a preconfigured route-map in/out policy
        for this neighbor."
    ::= { gbgpEventsGroup 42 }

gbgp42_RouteDest OBJECT-TYPE
    SYNTAX DisplayString
    MAX-ACCESS accessible-for-notify
    STATUS current
    DESCRIPTION
        "Parameter 'RouteDest' in event GBGP.42"
    ::= { gbgpEventObjects42 1 }

gbgp42_RoutePrefixLen OBJECT-TYPE
    SYNTAX Integer32
    MAX-ACCESS accessible-for-notify
    STATUS current
    DESCRIPTION
        "Parameter 'RoutePrefixLen' in event GBGP.42"
    ::= { gbgpEventObjects42 2 }

gbgp42_OldNexthop OBJECT-TYPE
    SYNTAX DisplayString
    MAX-ACCESS accessible-for-notify
    STATUS current
    DESCRIPTION
        "Parameter 'OldNexthop' in event GBGP.42"
    ::= { gbgpEventObjects42 3 }

gbgp42_NewNexthop OBJECT-TYPE
    SYNTAX DisplayString
    MAX-ACCESS accessible-for-notify
    STATUS current
    DESCRIPTION
        "Parameter 'NewNexthop' in event GBGP.42"
    ::= { gbgpEventObjects42 4 }

gbgp42_rtmapinout OBJECT-TYPE
    SYNTAX DisplayString
    MAX-ACCESS accessible-for-notify
    STATUS current
    DESCRIPTION
        "Parameter 'rtmapinout' in event GBGP.42"
    ::= { gbgpEventObjects42 5 }

gbgpEventObjects43 OBJECT-IDENTITY
    STATUS current
    DESCRIPTION
        "Event GBGP.43
        The nexthop value of a route transmitted in an update packet
        has been set due to a preconfigured route-map in/out policy
        for this neighbor."
    ::= { gbgpEventsGroup 43 }

gbgp43_RouteDest OBJECT-TYPE
    SYNTAX DisplayString
    MAX-ACCESS accessible-for-notify
    STATUS current
    DESCRIPTION
        "Parameter 'RouteDest' in event GBGP.43"
    ::= { gbgpEventObjects43 1 }

gbgp43_RoutePrefixLen OBJECT-TYPE
    SYNTAX Integer32
    MAX-ACCESS accessible-for-notify
    STATUS current
    DESCRIPTION
        "Parameter 'RoutePrefixLen' in event GBGP.43"
    ::= { gbgpEventObjects43 2 }

gbgp43_NewNexthop OBJECT-TYPE
    SYNTAX DisplayString
    MAX-ACCESS accessible-for-notify
    STATUS current
    DESCRIPTION
        "Parameter 'NewNexthop' in event GBGP.43"
    ::= { gbgpEventObjects43 3 }

gbgp43_rtmapinout OBJECT-TYPE
    SYNTAX DisplayString
    MAX-ACCESS accessible-for-notify
    STATUS current
    DESCRIPTION
        "Parameter 'rtmapinout' in event GBGP.43"
    ::= { gbgpEventObjects43 4 }

gbgpEventObjects44 OBJECT-IDENTITY
    STATUS current
    DESCRIPTION
        "Event GBGP.44
        The nexthop value of a route received in an update packet
        has been changed due to a preconfigured route-map in/out policy
        for this neighbor."
    ::= { gbgpEventsGroup 44 }

gbgp44_RouteDest OBJECT-TYPE
    SYNTAX DisplayString
    MAX-ACCESS accessible-for-notify
    STATUS current
    DESCRIPTION
        "Parameter 'RouteDest' in event GBGP.44"
    ::= { gbgpEventObjects44 1 }

gbgp44_RouteMask OBJECT-TYPE
    SYNTAX DisplayString
    MAX-ACCESS accessible-for-notify
    STATUS current
    DESCRIPTION
        "Parameter 'RouteMask' in event GBGP.44"
    ::= { gbgpEventObjects44 2 }

gbgp44_OldNexthop OBJECT-TYPE
    SYNTAX DisplayString
    MAX-ACCESS accessible-for-notify
    STATUS current
    DESCRIPTION
        "Parameter 'OldNexthop' in event GBGP.44"
    ::= { gbgpEventObjects44 3 }

gbgp44_NewNexthop OBJECT-TYPE
    SYNTAX DisplayString
    MAX-ACCESS accessible-for-notify
    STATUS current
    DESCRIPTION
        "Parameter 'NewNexthop' in event GBGP.44"
    ::= { gbgpEventObjects44 4 }

gbgp44_rtmapinout OBJECT-TYPE
    SYNTAX DisplayString
    MAX-ACCESS accessible-for-notify
    STATUS current
    DESCRIPTION
        "Parameter 'rtmapinout' in event GBGP.44"
    ::= { gbgpEventObjects44 5 }

gbgpEventObjects45 OBJECT-IDENTITY
    STATUS current
    DESCRIPTION
        "Event GBGP.45
        The nexthop value of a route transmitted in an update packet
        has been set due to a preconfigured route-map in/out policy
        for this neighbor."
    ::= { gbgpEventsGroup 45 }

gbgp45_RouteDest OBJECT-TYPE
    SYNTAX DisplayString
    MAX-ACCESS accessible-for-notify
    STATUS current
    DESCRIPTION
        "Parameter 'RouteDest' in event GBGP.45"
    ::= { gbgpEventObjects45 1 }

gbgp45_RouteMask OBJECT-TYPE
    SYNTAX DisplayString
    MAX-ACCESS accessible-for-notify
    STATUS current
    DESCRIPTION
        "Parameter 'RouteMask' in event GBGP.45"
    ::= { gbgpEventObjects45 2 }

gbgp45_NewNexthop OBJECT-TYPE
    SYNTAX DisplayString
    MAX-ACCESS accessible-for-notify
    STATUS current
    DESCRIPTION
        "Parameter 'NewNexthop' in event GBGP.45"
    ::= { gbgpEventObjects45 3 }

gbgp45_rtmapinout OBJECT-TYPE
    SYNTAX DisplayString
    MAX-ACCESS accessible-for-notify
    STATUS current
    DESCRIPTION
        "Parameter 'rtmapinout' in event GBGP.45"
    ::= { gbgpEventObjects45 4 }

gbgpEventObjects46 OBJECT-IDENTITY
    STATUS current
    DESCRIPTION
        "Event GBGP.46
        The status of the specified peer has changed from a higher
        numbered status to a lower numbered status."
    ::= { gbgpEventsGroup 46 }

gbgp46_RemotePeerAddress OBJECT-TYPE
    SYNTAX DisplayString
    MAX-ACCESS accessible-for-notify
    STATUS current
    DESCRIPTION
        "Parameter 'RemotePeerAddress' in event GBGP.46"
    ::= { gbgpEventObjects46 1 }

gbgp46_AutonomousSystem OBJECT-TYPE
    SYNTAX Integer32
    MAX-ACCESS accessible-for-notify
    STATUS current
    DESCRIPTION
        "Parameter 'AutonomousSystem' in event GBGP.46"
    ::= { gbgpEventObjects46 2 }

gbgpEventObjects47 OBJECT-IDENTITY
    STATUS current
    DESCRIPTION
        "Event GBGP.47
        The update received contains an invalid field."
    ::= { gbgpEventsGroup 47 }

gbgp47_Error_msg OBJECT-TYPE
    SYNTAX DisplayString
    MAX-ACCESS accessible-for-notify
    STATUS current
    DESCRIPTION
        "Parameter 'Error_msg' in event GBGP.47"
    ::= { gbgpEventObjects47 1 }

gbgp47_RemotePeerAddress OBJECT-TYPE
    SYNTAX DisplayString
    MAX-ACCESS accessible-for-notify
    STATUS current
    DESCRIPTION
        "Parameter 'RemotePeerAddress' in event GBGP.47"
    ::= { gbgpEventObjects47 2 }

gbgp47_AutonomousSystem OBJECT-TYPE
    SYNTAX Integer32
    MAX-ACCESS accessible-for-notify
    STATUS current
    DESCRIPTION
        "Parameter 'AutonomousSystem' in event GBGP.47"
    ::= { gbgpEventObjects47 3 }

gbgpEventObjects48 OBJECT-IDENTITY
    STATUS current
    DESCRIPTION
        "Event GBGP.48
        Received an open msg with an optional parameter."
    ::= { gbgpEventsGroup 48 }

gbgp48_opt_param OBJECT-TYPE
    SYNTAX Integer32
    MAX-ACCESS accessible-for-notify
    STATUS current
    DESCRIPTION
        "Parameter 'opt_param' in event GBGP.48"
    ::= { gbgpEventObjects48 1 }

gbgp48_opt_param_str OBJECT-TYPE
    SYNTAX DisplayString
    MAX-ACCESS accessible-for-notify
    STATUS current
    DESCRIPTION
        "Parameter 'opt_param_str' in event GBGP.48"
    ::= { gbgpEventObjects48 2 }

gbgp48_RemotePeerAddress OBJECT-TYPE
    SYNTAX DisplayString
    MAX-ACCESS accessible-for-notify
    STATUS current
    DESCRIPTION
        "Parameter 'RemotePeerAddress' in event GBGP.48"
    ::= { gbgpEventObjects48 3 }

gbgpEventObjects49 OBJECT-IDENTITY
    STATUS current
    DESCRIPTION
        "Event GBGP.49
        Received an open msg with capability in the optional paramater."
    ::= { gbgpEventsGroup 49 }

gbgp49_capab_code OBJECT-TYPE
    SYNTAX Integer32
    MAX-ACCESS accessible-for-notify
    STATUS current
    DESCRIPTION
        "Parameter 'capab_code' in event GBGP.49"
    ::= { gbgpEventObjects49 1 }

gbgp49_capab_len OBJECT-TYPE
    SYNTAX Integer32
    MAX-ACCESS accessible-for-notify
    STATUS current
    DESCRIPTION
        "Parameter 'capab_len' in event GBGP.49"
    ::= { gbgpEventObjects49 2 }

gbgp49_RemotePeerAddress OBJECT-TYPE
    SYNTAX DisplayString
    MAX-ACCESS accessible-for-notify
    STATUS current
    DESCRIPTION
        "Parameter 'RemotePeerAddress' in event GBGP.49"
    ::= { gbgpEventObjects49 3 }

gbgpEventObjects50 OBJECT-IDENTITY
    STATUS current
    DESCRIPTION
        "Event GBGP.50
        Received an open msg with MP_EXT capability."
    ::= { gbgpEventsGroup 50 }

gbgp50_afi OBJECT-TYPE
    SYNTAX Integer32
    MAX-ACCESS accessible-for-notify
    STATUS current
    DESCRIPTION
        "Parameter 'afi' in event GBGP.50"
    ::= { gbgpEventObjects50 1 }

gbgp50_safi OBJECT-TYPE
    SYNTAX Integer32
    MAX-ACCESS accessible-for-notify
    STATUS current
    DESCRIPTION
        "Parameter 'safi' in event GBGP.50"
    ::= { gbgpEventObjects50 2 }

gbgp50_RemotePeerAddress OBJECT-TYPE
    SYNTAX DisplayString
    MAX-ACCESS accessible-for-notify
    STATUS current
    DESCRIPTION
        "Parameter 'RemotePeerAddress' in event GBGP.50"
    ::= { gbgpEventObjects50 3 }

gbgpEventObjects51 OBJECT-IDENTITY
    STATUS current
    DESCRIPTION
        "Event GBGP.51
        Received an open msg with an unsupported capability (ignoring)."
    ::= { gbgpEventsGroup 51 }

gbgp51_capab_code OBJECT-TYPE
    SYNTAX Integer32
    MAX-ACCESS accessible-for-notify
    STATUS current
    DESCRIPTION
        "Parameter 'capab_code' in event GBGP.51"
    ::= { gbgpEventObjects51 1 }

gbgp51_RemotePeerAddress OBJECT-TYPE
    SYNTAX DisplayString
    MAX-ACCESS accessible-for-notify
    STATUS current
    DESCRIPTION
        "Parameter 'RemotePeerAddress' in event GBGP.51"
    ::= { gbgpEventObjects51 2 }

gbgpEventObjects52 OBJECT-IDENTITY
    STATUS current
    DESCRIPTION
        "Event GBGP.52
        When a route is received, there are four posible actions: install (ins),
        remove (rem), discard (dis) or idle (idl).
        - install : the route is installed in the BGP table and marked as usable
        (the preference is a positive integer).
        - remove : the route will be removed from the BGP table if already exists.
        - discard : the route won't be installed in the BGP table.
        - idle : the route will never be usable (the preference is a negative
        integer).
        Along with each action, an informative message is shown. If everything
        goes well, the message is 'ok'. Otherwise, a descriptive message will
        explain the cause of the error."
    ::= { gbgpEventsGroup 52 }

gbgp52_Action OBJECT-TYPE
    SYNTAX DisplayString
    MAX-ACCESS accessible-for-notify
    STATUS current
    DESCRIPTION
        "Parameter 'Action' in event GBGP.52"
    ::= { gbgpEventObjects52 1 }

gbgp52_Prefix OBJECT-TYPE
    SYNTAX DisplayString
    MAX-ACCESS accessible-for-notify
    STATUS current
    DESCRIPTION
        "Parameter 'Prefix' in event GBGP.52"
    ::= { gbgpEventObjects52 2 }

gbgp52_PrefixLen OBJECT-TYPE
    SYNTAX Integer32
    MAX-ACCESS accessible-for-notify
    STATUS current
    DESCRIPTION
        "Parameter 'PrefixLen' in event GBGP.52"
    ::= { gbgpEventObjects52 3 }

gbgp52_Information OBJECT-TYPE
    SYNTAX DisplayString
    MAX-ACCESS accessible-for-notify
    STATUS current
    DESCRIPTION
        "Parameter 'Information' in event GBGP.52"
    ::= { gbgpEventObjects52 4 }

gbgp52_Origin OBJECT-TYPE
    SYNTAX DisplayString
    MAX-ACCESS accessible-for-notify
    STATUS current
    DESCRIPTION
        "Parameter 'Origin' in event GBGP.52"
    ::= { gbgpEventObjects52 5 }

gbgpEventObjects53 OBJECT-IDENTITY
    STATUS current
    DESCRIPTION
        "Event GBGP.53
        Data has been received from the specified peer. The received data is
        shown in hexadecimal."
    ::= { gbgpEventsGroup 53 }

gbgp53_RemotePeerName OBJECT-TYPE
    SYNTAX DisplayString
    MAX-ACCESS accessible-for-notify
    STATUS current
    DESCRIPTION
        "Parameter 'RemotePeerName' in event GBGP.53"
    ::= { gbgpEventObjects53 1 }

gbgp53_DataHexDump OBJECT-TYPE
    SYNTAX DisplayString
    MAX-ACCESS accessible-for-notify
    STATUS current
    DESCRIPTION
        "Parameter 'DataHexDump' in event GBGP.53"
    ::= { gbgpEventObjects53 2 }

gbgpEventObjects54 OBJECT-IDENTITY
    STATUS current
    DESCRIPTION
        "Event GBGP.54
        An invalid message has been received from the specified peer. The
        received message data is shown in hexadecimal."
    ::= { gbgpEventsGroup 54 }

gbgp54_RemotePeerName OBJECT-TYPE
    SYNTAX DisplayString
    MAX-ACCESS accessible-for-notify
    STATUS current
    DESCRIPTION
        "Parameter 'RemotePeerName' in event GBGP.54"
    ::= { gbgpEventObjects54 1 }

gbgp54_DataHexDump OBJECT-TYPE
    SYNTAX DisplayString
    MAX-ACCESS accessible-for-notify
    STATUS current
    DESCRIPTION
        "Parameter 'DataHexDump' in event GBGP.54"
    ::= { gbgpEventObjects54 2 }

gbgpEventObjects55 OBJECT-IDENTITY
    STATUS current
    DESCRIPTION
        "Event GBGP.55
        A message has been received from the specified peer. The received
        message data is shown in hexadecimal."
    ::= { gbgpEventsGroup 55 }

gbgp55_RemotePeerName OBJECT-TYPE
    SYNTAX DisplayString
    MAX-ACCESS accessible-for-notify
    STATUS current
    DESCRIPTION
        "Parameter 'RemotePeerName' in event GBGP.55"
    ::= { gbgpEventObjects55 1 }

gbgp55_DataHexDump OBJECT-TYPE
    SYNTAX DisplayString
    MAX-ACCESS accessible-for-notify
    STATUS current
    DESCRIPTION
        "Parameter 'DataHexDump' in event GBGP.55"
    ::= { gbgpEventObjects55 2 }

gbgpEventObjects56 OBJECT-IDENTITY
    STATUS current
    DESCRIPTION
        "Event GBGP.56
        A message is sent to the specified peer. The message data is shown in
        hexadecimal."
    ::= { gbgpEventsGroup 56 }

gbgp56_RemotePeerName OBJECT-TYPE
    SYNTAX DisplayString
    MAX-ACCESS accessible-for-notify
    STATUS current
    DESCRIPTION
        "Parameter 'RemotePeerName' in event GBGP.56"
    ::= { gbgpEventObjects56 1 }

gbgp56_DataHexDump OBJECT-TYPE
    SYNTAX DisplayString
    MAX-ACCESS accessible-for-notify
    STATUS current
    DESCRIPTION
        "Parameter 'DataHexDump' in event GBGP.56"
    ::= { gbgpEventObjects56 2 }

gbgpEventObjects57 OBJECT-IDENTITY
    STATUS current
    DESCRIPTION
        "Event GBGP.57
        Data has been sent to the specified peer. The data is shown in
        hexadecimal."
    ::= { gbgpEventsGroup 57 }

gbgp57_RemotePeerName OBJECT-TYPE
    SYNTAX DisplayString
    MAX-ACCESS accessible-for-notify
    STATUS current
    DESCRIPTION
        "Parameter 'RemotePeerName' in event GBGP.57"
    ::= { gbgpEventObjects57 1 }

gbgp57_DataHexDump OBJECT-TYPE
    SYNTAX DisplayString
    MAX-ACCESS accessible-for-notify
    STATUS current
    DESCRIPTION
        "Parameter 'DataHexDump' in event GBGP.57"
    ::= { gbgpEventObjects57 2 }

gbgpEventObjects58 OBJECT-IDENTITY
    STATUS current
    DESCRIPTION
        "Event GBGP.58
        Received an open message without Multiprotocol Extensions Capability for
        an AFI/SAFI which is needed to operate."
    ::= { gbgpEventsGroup 58 }

gbgp58_afi OBJECT-TYPE
    SYNTAX DisplayString
    MAX-ACCESS accessible-for-notify
    STATUS current
    DESCRIPTION
        "Parameter 'afi' in event GBGP.58"
    ::= { gbgpEventObjects58 1 }

gbgp58_safi OBJECT-TYPE
    SYNTAX DisplayString
    MAX-ACCESS accessible-for-notify
    STATUS current
    DESCRIPTION
        "Parameter 'safi' in event GBGP.58"
    ::= { gbgpEventObjects58 2 }

gbgp58_RemotePeerAddress OBJECT-TYPE
    SYNTAX DisplayString
    MAX-ACCESS accessible-for-notify
    STATUS current
    DESCRIPTION
        "Parameter 'RemotePeerAddress' in event GBGP.58"
    ::= { gbgpEventObjects58 3 }

gbgpEventObjects59 OBJECT-IDENTITY
    STATUS current
    DESCRIPTION
        "Event GBGP.59
        Received an open message with Graceful Restart Capability. The Restart
        Flags and Restart Time values are shown."
    ::= { gbgpEventsGroup 59 }

gbgp59_restart_flags OBJECT-TYPE
    SYNTAX Integer32
    MAX-ACCESS accessible-for-notify
    STATUS current
    DESCRIPTION
        "Parameter 'restart_flags' in event GBGP.59"
    ::= { gbgpEventObjects59 1 }

gbgp59_restart_time OBJECT-TYPE
    SYNTAX Integer32
    MAX-ACCESS accessible-for-notify
    STATUS current
    DESCRIPTION
        "Parameter 'restart_time' in event GBGP.59"
    ::= { gbgpEventObjects59 2 }

gbgp59_RemotePeerAddress OBJECT-TYPE
    SYNTAX DisplayString
    MAX-ACCESS accessible-for-notify
    STATUS current
    DESCRIPTION
        "Parameter 'RemotePeerAddress' in event GBGP.59"
    ::= { gbgpEventObjects59 3 }

gbgpEventObjects60 OBJECT-IDENTITY
    STATUS current
    DESCRIPTION
        "Event GBGP.60
        Received an open message with Graceful Restart Capability, with the
        Address Family specified by the afi/safi pair. The Address Family Flags
        are shown."
    ::= { gbgpEventsGroup 60 }

gbgp60_afi OBJECT-TYPE
    SYNTAX DisplayString
    MAX-ACCESS accessible-for-notify
    STATUS current
    DESCRIPTION
        "Parameter 'afi' in event GBGP.60"
    ::= { gbgpEventObjects60 1 }

gbgp60_safi OBJECT-TYPE
    SYNTAX DisplayString
    MAX-ACCESS accessible-for-notify
    STATUS current
    DESCRIPTION
        "Parameter 'safi' in event GBGP.60"
    ::= { gbgpEventObjects60 2 }

gbgp60_flags OBJECT-TYPE
    SYNTAX Integer32
    MAX-ACCESS accessible-for-notify
    STATUS current
    DESCRIPTION
        "Parameter 'flags' in event GBGP.60"
    ::= { gbgpEventObjects60 3 }

gbgp60_RemotePeerAddress OBJECT-TYPE
    SYNTAX DisplayString
    MAX-ACCESS accessible-for-notify
    STATUS current
    DESCRIPTION
        "Parameter 'RemotePeerAddress' in event GBGP.60"
    ::= { gbgpEventObjects60 4 }

gbgpEventObjects61 OBJECT-IDENTITY
    STATUS current
    DESCRIPTION
        "Event GBGP.61
        An Update message conforming to the End-Of-RIB marker specification is
        sent for the Address Family specified by the afi/safi pair."
    ::= { gbgpEventsGroup 61 }

gbgp61_afi OBJECT-TYPE
    SYNTAX DisplayString
    MAX-ACCESS accessible-for-notify
    STATUS current
    DESCRIPTION
        "Parameter 'afi' in event GBGP.61"
    ::= { gbgpEventObjects61 1 }

gbgp61_safi OBJECT-TYPE
    SYNTAX DisplayString
    MAX-ACCESS accessible-for-notify
    STATUS current
    DESCRIPTION
        "Parameter 'safi' in event GBGP.61"
    ::= { gbgpEventObjects61 2 }

gbgp61_RemotePeerAddress OBJECT-TYPE
    SYNTAX DisplayString
    MAX-ACCESS accessible-for-notify
    STATUS current
    DESCRIPTION
        "Parameter 'RemotePeerAddress' in event GBGP.61"
    ::= { gbgpEventObjects61 3 }

gbgpEventObjects62 OBJECT-IDENTITY
    STATUS current
    DESCRIPTION
        "Event GBGP.62
        An Update message conforming to the End-Of-RIB marker specification has
        been received for the Address Family specified by the afi/safi pair."
    ::= { gbgpEventsGroup 62 }

gbgp62_afi OBJECT-TYPE
    SYNTAX DisplayString
    MAX-ACCESS accessible-for-notify
    STATUS current
    DESCRIPTION
        "Parameter 'afi' in event GBGP.62"
    ::= { gbgpEventObjects62 1 }

gbgp62_safi OBJECT-TYPE
    SYNTAX DisplayString
    MAX-ACCESS accessible-for-notify
    STATUS current
    DESCRIPTION
        "Parameter 'safi' in event GBGP.62"
    ::= { gbgpEventObjects62 2 }

gbgp62_RemotePeerAddress OBJECT-TYPE
    SYNTAX DisplayString
    MAX-ACCESS accessible-for-notify
    STATUS current
    DESCRIPTION
        "Parameter 'RemotePeerAddress' in event GBGP.62"
    ::= { gbgpEventObjects62 3 }

gbgpEventObjects64 OBJECT-IDENTITY
    STATUS current
    DESCRIPTION
        "Event GBGP.64
        Send an open message with Graceful Restart Capability. The Restart
        Flags and Restart Time values are shown."
    ::= { gbgpEventsGroup 64 }

gbgp64_restart_flags OBJECT-TYPE
    SYNTAX Integer32
    MAX-ACCESS accessible-for-notify
    STATUS current
    DESCRIPTION
        "Parameter 'restart_flags' in event GBGP.64"
    ::= { gbgpEventObjects64 1 }

gbgp64_restart_time OBJECT-TYPE
    SYNTAX Integer32
    MAX-ACCESS accessible-for-notify
    STATUS current
    DESCRIPTION
        "Parameter 'restart_time' in event GBGP.64"
    ::= { gbgpEventObjects64 2 }

gbgp64_RemotePeerAddress OBJECT-TYPE
    SYNTAX DisplayString
    MAX-ACCESS accessible-for-notify
    STATUS current
    DESCRIPTION
        "Parameter 'RemotePeerAddress' in event GBGP.64"
    ::= { gbgpEventObjects64 3 }

gbgpEventObjects65 OBJECT-IDENTITY
    STATUS current
    DESCRIPTION
        "Event GBGP.65
        Send an open message with Graceful Restart Capability, with the
        Address Family specified by the afi/safi pair. The Address Family Flags
        are shown."
    ::= { gbgpEventsGroup 65 }

gbgp65_afi OBJECT-TYPE
    SYNTAX DisplayString
    MAX-ACCESS accessible-for-notify
    STATUS current
    DESCRIPTION
        "Parameter 'afi' in event GBGP.65"
    ::= { gbgpEventObjects65 1 }

gbgp65_safi OBJECT-TYPE
    SYNTAX DisplayString
    MAX-ACCESS accessible-for-notify
    STATUS current
    DESCRIPTION
        "Parameter 'safi' in event GBGP.65"
    ::= { gbgpEventObjects65 2 }

gbgp65_flags OBJECT-TYPE
    SYNTAX Integer32
    MAX-ACCESS accessible-for-notify
    STATUS current
    DESCRIPTION
        "Parameter 'flags' in event GBGP.65"
    ::= { gbgpEventObjects65 3 }

gbgp65_RemotePeerAddress OBJECT-TYPE
    SYNTAX DisplayString
    MAX-ACCESS accessible-for-notify
    STATUS current
    DESCRIPTION
        "Parameter 'RemotePeerAddress' in event GBGP.65"
    ::= { gbgpEventObjects65 4 }

gbgpEventObjects66 OBJECT-IDENTITY
    STATUS current
    DESCRIPTION
        "Event GBGP.66
        A peer session is being closed, and a backup for Graceful Restart has
        been triggered. Stale information is discarded because Graceful Restart
        is disabled."
    ::= { gbgpEventsGroup 66 }

gbgp66_RemotePeerAddress OBJECT-TYPE
    SYNTAX DisplayString
    MAX-ACCESS accessible-for-notify
    STATUS current
    DESCRIPTION
        "Parameter 'RemotePeerAddress' in event GBGP.66"
    ::= { gbgpEventObjects66 1 }

gbgpEventObjects67 OBJECT-IDENTITY
    STATUS current
    DESCRIPTION
        "Event GBGP.67
        A peer session is being closed, and a backup for Graceful Restart has
        been triggered. New stale information is generated from scratch or
        reinitializing old stale information as specified in stale_type."
    ::= { gbgpEventsGroup 67 }

gbgp67_stale_type OBJECT-TYPE
    SYNTAX DisplayString
    MAX-ACCESS accessible-for-notify
    STATUS current
    DESCRIPTION
        "Parameter 'stale_type' in event GBGP.67"
    ::= { gbgpEventObjects67 1 }

gbgp67_RemotePeerAddress OBJECT-TYPE
    SYNTAX DisplayString
    MAX-ACCESS accessible-for-notify
    STATUS current
    DESCRIPTION
        "Parameter 'RemotePeerAddress' in event GBGP.67"
    ::= { gbgpEventObjects67 2 }

gbgpEventObjects68 OBJECT-IDENTITY
    STATUS current
    DESCRIPTION
        "Event GBGP.68
        Graceful Restart has created a stale route to the specified destination
        network."
    ::= { gbgpEventsGroup 68 }

gbgp68_dest_addr OBJECT-TYPE
    SYNTAX DisplayString
    MAX-ACCESS accessible-for-notify
    STATUS current
    DESCRIPTION
        "Parameter 'dest_addr' in event GBGP.68"
    ::= { gbgpEventObjects68 1 }

gbgp68_dest_len OBJECT-TYPE
    SYNTAX Integer32
    MAX-ACCESS accessible-for-notify
    STATUS current
    DESCRIPTION
        "Parameter 'dest_len' in event GBGP.68"
    ::= { gbgpEventObjects68 2 }

gbgp68_RemotePeerAddress OBJECT-TYPE
    SYNTAX DisplayString
    MAX-ACCESS accessible-for-notify
    STATUS current
    DESCRIPTION
        "Parameter 'RemotePeerAddress' in event GBGP.68"
    ::= { gbgpEventObjects68 3 }

gbgpEventObjects69 OBJECT-IDENTITY
    STATUS current
    DESCRIPTION
        "Event GBGP.69
        Graceful Restart made a backup generating stale information for a
        receiving or restarting speaker (as specified in speaker_type) with the
        specified number of address families and routes."
    ::= { gbgpEventsGroup 69 }

gbgp69_speaker_type OBJECT-TYPE
    SYNTAX DisplayString
    MAX-ACCESS accessible-for-notify
    STATUS current
    DESCRIPTION
        "Parameter 'speaker_type' in event GBGP.69"
    ::= { gbgpEventObjects69 1 }

gbgp69_family_count OBJECT-TYPE
    SYNTAX Integer32
    MAX-ACCESS accessible-for-notify
    STATUS current
    DESCRIPTION
        "Parameter 'family_count' in event GBGP.69"
    ::= { gbgpEventObjects69 2 }

gbgp69_route_count OBJECT-TYPE
    SYNTAX Integer32
    MAX-ACCESS accessible-for-notify
    STATUS current
    DESCRIPTION
        "Parameter 'route_count' in event GBGP.69"
    ::= { gbgpEventObjects69 3 }

gbgp69_RemotePeerAddress OBJECT-TYPE
    SYNTAX DisplayString
    MAX-ACCESS accessible-for-notify
    STATUS current
    DESCRIPTION
        "Parameter 'RemotePeerAddress' in event GBGP.69"
    ::= { gbgpEventObjects69 4 }

gbgpEventObjects70 OBJECT-IDENTITY
    STATUS current
    DESCRIPTION
        "Event GBGP.70
        Graceful Restart detected the session establishment for a receiving or
        restarting speaker as specified in speaker_type."
    ::= { gbgpEventsGroup 70 }

gbgp70_speaker_type OBJECT-TYPE
    SYNTAX DisplayString
    MAX-ACCESS accessible-for-notify
    STATUS current
    DESCRIPTION
        "Parameter 'speaker_type' in event GBGP.70"
    ::= { gbgpEventObjects70 1 }

gbgp70_RemotePeerAddress OBJECT-TYPE
    SYNTAX DisplayString
    MAX-ACCESS accessible-for-notify
    STATUS current
    DESCRIPTION
        "Parameter 'RemotePeerAddress' in event GBGP.70"
    ::= { gbgpEventObjects70 2 }

gbgpEventObjects71 OBJECT-IDENTITY
    STATUS current
    DESCRIPTION
        "Event GBGP.71
        Graceful Restart detected the session establishment for a restarting
        speaker, but no graceful restart capability was received or it was
        received with the 'Restart State' bit set. This peer will not be waited
        for to stop deferring."
    ::= { gbgpEventsGroup 71 }

gbgp71_afi OBJECT-TYPE
    SYNTAX DisplayString
    MAX-ACCESS accessible-for-notify
    STATUS current
    DESCRIPTION
        "Parameter 'afi' in event GBGP.71"
    ::= { gbgpEventObjects71 1 }

gbgp71_safi OBJECT-TYPE
    SYNTAX DisplayString
    MAX-ACCESS accessible-for-notify
    STATUS current
    DESCRIPTION
        "Parameter 'safi' in event GBGP.71"
    ::= { gbgpEventObjects71 2 }

gbgp71_RemotePeerAddress OBJECT-TYPE
    SYNTAX DisplayString
    MAX-ACCESS accessible-for-notify
    STATUS current
    DESCRIPTION
        "Parameter 'RemotePeerAddress' in event GBGP.71"
    ::= { gbgpEventObjects71 3 }

gbgpEventObjects72 OBJECT-IDENTITY
    STATUS current
    DESCRIPTION
        "Event GBGP.72
        Graceful Restart has deferred a restarting speaker route received in an
        update message. The route destination network is specified."
    ::= { gbgpEventsGroup 72 }

gbgp72_dest_addr OBJECT-TYPE
    SYNTAX DisplayString
    MAX-ACCESS accessible-for-notify
    STATUS current
    DESCRIPTION
        "Parameter 'dest_addr' in event GBGP.72"
    ::= { gbgpEventObjects72 1 }

gbgp72_dest_len OBJECT-TYPE
    SYNTAX Integer32
    MAX-ACCESS accessible-for-notify
    STATUS current
    DESCRIPTION
        "Parameter 'dest_len' in event GBGP.72"
    ::= { gbgpEventObjects72 2 }

gbgp72_RemotePeerAddress OBJECT-TYPE
    SYNTAX DisplayString
    MAX-ACCESS accessible-for-notify
    STATUS current
    DESCRIPTION
        "Parameter 'RemotePeerAddress' in event GBGP.72"
    ::= { gbgpEventObjects72 3 }

gbgpEventObjects73 OBJECT-IDENTITY
    STATUS current
    DESCRIPTION
        "Event GBGP.73
        Graceful Restart has deleted a stale route. The route destination
        network is specified. Possible causes are: 'rx nlri' when
        the receiving speaker stale route is superseded by a nlri received on an
        update message; 'term' when the BGP process is terminating; 'rx eor'
        when the End-of-RIB marker has been received by a receiving speaker;
        'estab' when the receiving speaker BGP session has been established and
        no 'Forwarding State' bit has been received for an address family;
        'stop defer' when the restarting speaker stops deferring an address
        family."
    ::= { gbgpEventsGroup 73 }

gbgp73_dest_addr OBJECT-TYPE
    SYNTAX DisplayString
    MAX-ACCESS accessible-for-notify
    STATUS current
    DESCRIPTION
        "Parameter 'dest_addr' in event GBGP.73"
    ::= { gbgpEventObjects73 1 }

gbgp73_dest_len OBJECT-TYPE
    SYNTAX Integer32
    MAX-ACCESS accessible-for-notify
    STATUS current
    DESCRIPTION
        "Parameter 'dest_len' in event GBGP.73"
    ::= { gbgpEventObjects73 2 }

gbgp73_cause OBJECT-TYPE
    SYNTAX DisplayString
    MAX-ACCESS accessible-for-notify
    STATUS current
    DESCRIPTION
        "Parameter 'cause' in event GBGP.73"
    ::= { gbgpEventObjects73 3 }

gbgp73_RemotePeerAddress OBJECT-TYPE
    SYNTAX DisplayString
    MAX-ACCESS accessible-for-notify
    STATUS current
    DESCRIPTION
        "Parameter 'RemotePeerAddress' in event GBGP.73"
    ::= { gbgpEventObjects73 4 }

gbgpEventObjects74 OBJECT-IDENTITY
    STATUS current
    DESCRIPTION
        "Event GBGP.74
        Graceful Restart stale information has timed out for the specified peer."
    ::= { gbgpEventsGroup 74 }

gbgp74_RemotePeerAddress OBJECT-TYPE
    SYNTAX DisplayString
    MAX-ACCESS accessible-for-notify
    STATUS current
    DESCRIPTION
        "Parameter 'RemotePeerAddress' in event GBGP.74"
    ::= { gbgpEventObjects74 1 }

gbgpEventObjects75 OBJECT-IDENTITY
    STATUS current
    DESCRIPTION
        "Event GBGP.75
        Graceful Restart stale information is deleted. The cause is specified."
    ::= { gbgpEventsGroup 75 }

gbgp75_cause OBJECT-TYPE
    SYNTAX DisplayString
    MAX-ACCESS accessible-for-notify
    STATUS current
    DESCRIPTION
        "Parameter 'cause' in event GBGP.75"
    ::= { gbgpEventObjects75 1 }

gbgp75_RemotePeerAddress OBJECT-TYPE
    SYNTAX DisplayString
    MAX-ACCESS accessible-for-notify
    STATUS current
    DESCRIPTION
        "Parameter 'RemotePeerAddress' in event GBGP.75"
    ::= { gbgpEventObjects75 2 }

gbgpEventObjects76 OBJECT-IDENTITY
    STATUS current
    DESCRIPTION
        "Event GBGP.76
        Graceful Restart stale peer is deleted. This is an idle unconfigured
        peer which lost the stale iformation. The cause is specified."
    ::= { gbgpEventsGroup 76 }

gbgp76_cause OBJECT-TYPE
    SYNTAX DisplayString
    MAX-ACCESS accessible-for-notify
    STATUS current
    DESCRIPTION
        "Parameter 'cause' in event GBGP.76"
    ::= { gbgpEventObjects76 1 }

gbgp76_RemotePeerAddress OBJECT-TYPE
    SYNTAX DisplayString
    MAX-ACCESS accessible-for-notify
    STATUS current
    DESCRIPTION
        "Parameter 'RemotePeerAddress' in event GBGP.76"
    ::= { gbgpEventObjects76 2 }

gbgpEventObjects77 OBJECT-IDENTITY
    STATUS current
    DESCRIPTION
        "Event GBGP.77
        Graceful Restart initial update has been deferred for the specified
        address family."
    ::= { gbgpEventsGroup 77 }

gbgp77_afi OBJECT-TYPE
    SYNTAX DisplayString
    MAX-ACCESS accessible-for-notify
    STATUS current
    DESCRIPTION
        "Parameter 'afi' in event GBGP.77"
    ::= { gbgpEventObjects77 1 }

gbgp77_safi OBJECT-TYPE
    SYNTAX DisplayString
    MAX-ACCESS accessible-for-notify
    STATUS current
    DESCRIPTION
        "Parameter 'safi' in event GBGP.77"
    ::= { gbgpEventObjects77 2 }

gbgp77_RemotePeerAddress OBJECT-TYPE
    SYNTAX DisplayString
    MAX-ACCESS accessible-for-notify
    STATUS current
    DESCRIPTION
        "Parameter 'RemotePeerAddress' in event GBGP.77"
    ::= { gbgpEventObjects77 3 }

gbgpEventObjects78 OBJECT-IDENTITY
    STATUS current
    DESCRIPTION
        "Event GBGP.78
        Graceful Restart initial update with End-of-RIB marker has been started
        for the specified address family."
    ::= { gbgpEventsGroup 78 }

gbgp78_afi OBJECT-TYPE
    SYNTAX DisplayString
    MAX-ACCESS accessible-for-notify
    STATUS current
    DESCRIPTION
        "Parameter 'afi' in event GBGP.78"
    ::= { gbgpEventObjects78 1 }

gbgp78_safi OBJECT-TYPE
    SYNTAX DisplayString
    MAX-ACCESS accessible-for-notify
    STATUS current
    DESCRIPTION
        "Parameter 'safi' in event GBGP.78"
    ::= { gbgpEventObjects78 2 }

gbgp78_RemotePeerAddress OBJECT-TYPE
    SYNTAX DisplayString
    MAX-ACCESS accessible-for-notify
    STATUS current
    DESCRIPTION
        "Parameter 'RemotePeerAddress' in event GBGP.78"
    ::= { gbgpEventObjects78 3 }

gbgpEventObjects79 OBJECT-IDENTITY
    STATUS current
    DESCRIPTION
        "Event GBGP.79
        Graceful Restart selection deferral started for all address families.
        The selection deferral timer has been started with the specified
        timeout."
    ::= { gbgpEventsGroup 79 }

gbgp79_timeout_seconds OBJECT-TYPE
    SYNTAX Integer32
    MAX-ACCESS accessible-for-notify
    STATUS current
    DESCRIPTION
        "Parameter 'timeout_seconds' in event GBGP.79"
    ::= { gbgpEventObjects79 1 }

gbgpEventObjects83 OBJECT-IDENTITY
    STATUS current
    DESCRIPTION
        "Event GBGP.83
        Graceful Restart selection deferral ended for the specified address
        family."
    ::= { gbgpEventsGroup 83 }

gbgp83_afi OBJECT-TYPE
    SYNTAX DisplayString
    MAX-ACCESS accessible-for-notify
    STATUS current
    DESCRIPTION
        "Parameter 'afi' in event GBGP.83"
    ::= { gbgpEventObjects83 1 }

gbgp83_safi OBJECT-TYPE
    SYNTAX DisplayString
    MAX-ACCESS accessible-for-notify
    STATUS current
    DESCRIPTION
        "Parameter 'safi' in event GBGP.83"
    ::= { gbgpEventObjects83 2 }

gbgpEventObjects84 OBJECT-IDENTITY
    STATUS current
    DESCRIPTION
        "Event GBGP.84
        Graceful Restart has stopped deferring a restarting speaker route. The
        route destination network is specified."
    ::= { gbgpEventsGroup 84 }

gbgp84_dest_addr OBJECT-TYPE
    SYNTAX DisplayString
    MAX-ACCESS accessible-for-notify
    STATUS current
    DESCRIPTION
        "Parameter 'dest_addr' in event GBGP.84"
    ::= { gbgpEventObjects84 1 }

gbgp84_dest_len OBJECT-TYPE
    SYNTAX Integer32
    MAX-ACCESS accessible-for-notify
    STATUS current
    DESCRIPTION
        "Parameter 'dest_len' in event GBGP.84"
    ::= { gbgpEventObjects84 2 }

gbgp84_RemotePeerAddress OBJECT-TYPE
    SYNTAX DisplayString
    MAX-ACCESS accessible-for-notify
    STATUS current
    DESCRIPTION
        "Parameter 'RemotePeerAddress' in event GBGP.84"
    ::= { gbgpEventObjects84 3 }

gbgpEventObjects85 OBJECT-IDENTITY
    STATUS current
    DESCRIPTION
        "Event GBGP.85
        Graceful Restart peer has started address family deferral."
    ::= { gbgpEventsGroup 85 }

gbgp85_RemotePeerAddress OBJECT-TYPE
    SYNTAX DisplayString
    MAX-ACCESS accessible-for-notify
    STATUS current
    DESCRIPTION
        "Parameter 'RemotePeerAddress' in event GBGP.85"
    ::= { gbgpEventObjects85 1 }

gbgpEventObjects86 OBJECT-IDENTITY
    STATUS current
    DESCRIPTION
        "Event GBGP.86
        Graceful Restart peer has stopped address family deferral."
    ::= { gbgpEventsGroup 86 }

gbgp86_RemotePeerAddress OBJECT-TYPE
    SYNTAX DisplayString
    MAX-ACCESS accessible-for-notify
    STATUS current
    DESCRIPTION
        "Parameter 'RemotePeerAddress' in event GBGP.86"
    ::= { gbgpEventObjects86 1 }

gbgpEventObjects87 OBJECT-IDENTITY
    STATUS current
    DESCRIPTION
        "Event GBGP.87
        The local origin value of a route received in an update packet
        has been changed due to a preconfigured route-map in/out policy
        for this neighbor."
    ::= { gbgpEventsGroup 87 }

gbgp87_RouteDest OBJECT-TYPE
    SYNTAX DisplayString
    MAX-ACCESS accessible-for-notify
    STATUS current
    DESCRIPTION
        "Parameter 'RouteDest' in event GBGP.87"
    ::= { gbgpEventObjects87 1 }

gbgp87_MaskLenght OBJECT-TYPE
    SYNTAX Integer32
    MAX-ACCESS accessible-for-notify
    STATUS current
    DESCRIPTION
        "Parameter 'MaskLenght' in event GBGP.87"
    ::= { gbgpEventObjects87 2 }

gbgp87_NewOrigin OBJECT-TYPE
    SYNTAX DisplayString
    MAX-ACCESS accessible-for-notify
    STATUS current
    DESCRIPTION
        "Parameter 'NewOrigin' in event GBGP.87"
    ::= { gbgpEventObjects87 3 }

gbgpEventObjects88 OBJECT-IDENTITY
    STATUS current
    DESCRIPTION
        "Event GBGP.88
        The peer prefix database is above the maximum-prefix configured limit.
        Both this limit and the current prefix count are shown."
    ::= { gbgpEventsGroup 88 }

gbgp88_maximum_prefixes OBJECT-TYPE
    SYNTAX Integer32
    MAX-ACCESS accessible-for-notify
    STATUS current
    DESCRIPTION
        "Parameter 'maximum_prefixes' in event GBGP.88"
    ::= { gbgpEventObjects88 1 }

gbgp88_current_prefixes OBJECT-TYPE
    SYNTAX Integer32
    MAX-ACCESS accessible-for-notify
    STATUS current
    DESCRIPTION
        "Parameter 'current_prefixes' in event GBGP.88"
    ::= { gbgpEventObjects88 2 }

gbgp88_RemotePeerAddress OBJECT-TYPE
    SYNTAX DisplayString
    MAX-ACCESS accessible-for-notify
    STATUS current
    DESCRIPTION
        "Parameter 'RemotePeerAddress' in event GBGP.88"
    ::= { gbgpEventObjects88 3 }

gbgp88_AutonomousSystem OBJECT-TYPE
    SYNTAX Integer32
    MAX-ACCESS accessible-for-notify
    STATUS current
    DESCRIPTION
        "Parameter 'AutonomousSystem' in event GBGP.88"
    ::= { gbgpEventObjects88 4 }


gbgpNotification1 NOTIFICATION-TYPE
    STATUS current
    DESCRIPTION
        "Notification of Event GBGP.1

        Message: 'BGP subsystem started succesfully.'

        The BGP subsystem initialization process was started successfully."
    ::= { gbgpNotificationsPrefix 1 }

gbgpNotification2 NOTIFICATION-TYPE
    OBJECTS { 
              gbgp2_RemotePeerAddress, 
              gbgp2_AutonomousSystem 
            }
    STATUS current
    DESCRIPTION
        "Notification of Event GBGP.2

        Message: 'The system disconnected from a configured BGP peer. Remote address is $1 AS $2'

        Parameters list:
              $1: gbgp2_RemotePeerAddress
              $2: gbgp2_AutonomousSystem

        A connection to a ESTABLISHED BGP peer has been lost. Possible causes
        are either a keepalive timer timeout or a TCP protocol error. The status
        of this peer is changed to ACTIVE."
    ::= { gbgpNotificationsPrefix 2 }

gbgpNotification3 NOTIFICATION-TYPE
    OBJECTS { 
              gbgp3_ParserErrors 
            }
    STATUS current
    DESCRIPTION
        "Notification of Event GBGP.3

        Message: '$1 errors were found in the configuration'

        Parameters list:
              $1: gbgp3_ParserErrors

        Syntax errors found in configuration file."
    ::= { gbgpNotificationsPrefix 3 }

gbgpNotification4 NOTIFICATION-TYPE
    OBJECTS { 
              gbgp4_PacketType, 
              gbgp4_RemotePeerAddress,
              gbgp4_AutonomousSystem 
            }
    STATUS current
    DESCRIPTION
        "Notification of Event GBGP.4

        Message: 'Received $1 message from peer $2/AS $3'

        Parameters list:
              $1: gbgp4_PacketType
              $2: gbgp4_RemotePeerAddress
              $3: gbgp4_AutonomousSystem

        A valid incoming BGP message has been received from a peer.
        The type of message is shown, as well as the remote peer address and
        autonomous system."
    ::= { gbgpNotificationsPrefix 4 }

gbgpNotification5 NOTIFICATION-TYPE
    OBJECTS { 
              gbgp5_PacketType, 
              gbgp5_RemotePeerAddress,
              gbgp5_AutonomousSystem 
            }
    STATUS current
    DESCRIPTION
        "Notification of Event GBGP.5

        Message: 'Sending $1 message to peer $2/AS $3'

        Parameters list:
              $1: gbgp5_PacketType
              $2: gbgp5_RemotePeerAddress
              $3: gbgp5_AutonomousSystem

        A message is been sent to a remote peer.
        The type of message is shown, as well as the remote peer address and
        autonomous system."
    ::= { gbgpNotificationsPrefix 5 }

gbgpNotification6 NOTIFICATION-TYPE
    OBJECTS { 
              gbgp6_RemotePeerName, 
              gbgp6_ErrorMessage 
            }
    STATUS current
    DESCRIPTION
        "Notification of Event GBGP.6

        Message: 'Packet from peer $1 has been rejected. Cause is $2'

        Parameters list:
              $1: gbgp6_RemotePeerName
              $2: gbgp6_ErrorMessage

        An incoming BGP message has been rejected. The rejection cause is shown
        in the message."
    ::= { gbgpNotificationsPrefix 6 }

gbgpNotification7 NOTIFICATION-TYPE
    OBJECTS { 
              gbgp7_RemotePeerName, 
              gbgp7_ErrorMessage 
            }
    STATUS current
    DESCRIPTION
        "Notification of Event GBGP.7

        Message: 'Rejected incoming connection from $1. Cause: $2'

        Parameters list:
              $1: gbgp7_RemotePeerName
              $2: gbgp7_ErrorMessage

        An active open from a remote system has been rejected. The address, AS
        and rejection cause are shown."
    ::= { gbgpNotificationsPrefix 7 }

gbgpNotification8 NOTIFICATION-TYPE
    OBJECTS { 
              gbgp8_RemotePeerAddress, 
              gbgp8_AutonomousSystem 
            }
    STATUS current
    DESCRIPTION
        "Notification of Event GBGP.8

        Message: 'The system connected to BGP peer. Address is $1, AS is $2.'

        Parameters list:
              $1: gbgp8_RemotePeerAddress
              $2: gbgp8_AutonomousSystem

        A valid connection has been made to a configured BGP peer. Peer status
        is changed to ESTABLISHED."
    ::= { gbgpNotificationsPrefix 8 }

gbgpNotification9 NOTIFICATION-TYPE
    STATUS current
    DESCRIPTION
        "Notification of Event GBGP.9

        Message: 'BGP subsystem stopped: normal stop.'

        The BGP subsystem was stopped due to an user request."
    ::= { gbgpNotificationsPrefix 9 }

gbgpNotification10 NOTIFICATION-TYPE
    OBJECTS { 
              gbgp10_RouteDest, 
              gbgp10_RouteMask,
              gbgp10_NextHop,
              gbgp10_Preference,
              gbgp10_Metric,
              gbgp10_LocalPref 
            }
    STATUS current
    DESCRIPTION
        "Notification of Event GBGP.10

        Message: 'received route update $1/$2 $3 pref $4 metric $5 localpref $6'

        Parameters list:
              $1: gbgp10_RouteDest
              $2: gbgp10_RouteMask
              $3: gbgp10_NextHop
              $4: gbgp10_Preference
              $5: gbgp10_Metric
              $6: gbgp10_LocalPref

        An update message for the route shown has been received. This message
        does not mean that this route has been made active, it just means that
        the system has received information for this route from a BGP peer. This
        route will be processed, and, taking into account the
        configured preference rules, will be or not exported to the active
        routes table. To be able to see changes in the active RT, please
        use the IP subsystem events."
    ::= { gbgpNotificationsPrefix 10 }

gbgpNotification11 NOTIFICATION-TYPE
    OBJECTS { 
              gbgp11_RouteDest, 
              gbgp11_RouteMask,
              gbgp11_BGPPeer 
            }
    STATUS current
    DESCRIPTION
        "Notification of Event GBGP.11

        Message: 'route $1/$2 from $3 is now unreachable'

        Parameters list:
              $1: gbgp11_RouteDest
              $2: gbgp11_RouteMask
              $3: gbgp11_BGPPeer

        An unreach message has been received for this route. This message
        does not mean that this route will be deleted from the active RT
        (it is possible that the route was not even made active when it
        was received). To be able to see changes in the active RT, please
        use the IP subsystem events."
    ::= { gbgpNotificationsPrefix 11 }

gbgpNotification12 NOTIFICATION-TYPE
    OBJECTS { 
              gbgp12_RemotePeerAddress, 
              gbgp12_AutonomousSystem 
            }
    STATUS current
    DESCRIPTION
        "Notification of Event GBGP.12

        Message: 'The holdtime for peer $1/AS $2 has expired'

        Parameters list:
              $1: gbgp12_RemotePeerAddress
              $2: gbgp12_AutonomousSystem

        The holdtime for a given BGP peer has expired."
    ::= { gbgpNotificationsPrefix 12 }

gbgpNotification13 NOTIFICATION-TYPE
    STATUS current
    DESCRIPTION
        "Notification of Event GBGP.13

        Message: 'BGP subsystem aborted'

        BGP subsystem was killed due to an unexpected error."
    ::= { gbgpNotificationsPrefix 13 }

gbgpNotification14 NOTIFICATION-TYPE
    OBJECTS { 
              gbgp14_Dest, 
              gbgp14_Mask,
              gbgp14_BGPPeer 
            }
    STATUS current
    DESCRIPTION
        "Notification of Event GBGP.14

        Message: 'Del route $1/$2 $3 from RT DB'

        Parameters list:
              $1: gbgp14_Dest
              $2: gbgp14_Mask
              $3: gbgp14_BGPPeer

        Deleting route from BGP routing Database."
    ::= { gbgpNotificationsPrefix 14 }

gbgpNotification15 NOTIFICATION-TYPE
    OBJECTS { 
              gbgp15_Dest, 
              gbgp15_Mask,
              gbgp15_NextHop 
            }
    STATUS current
    DESCRIPTION
        "Notification of Event GBGP.15

        Message: 'Add route $1/$2 $3'

        Parameters list:
              $1: gbgp15_Dest
              $2: gbgp15_Mask
              $3: gbgp15_NextHop

        Adding route to BGP routing Database."
    ::= { gbgpNotificationsPrefix 15 }

gbgpNotification16 NOTIFICATION-TYPE
    OBJECTS { 
              gbgp16_Dest, 
              gbgp16_Mask 
            }
    STATUS current
    DESCRIPTION
        "Notification of Event GBGP.16

        Message: 'Add direct rte $1/$2'

        Parameters list:
              $1: gbgp16_Dest
              $2: gbgp16_Mask

        Adding direct route to BGP routing Database."
    ::= { gbgpNotificationsPrefix 16 }

gbgpNotification17 NOTIFICATION-TYPE
    STATUS current
    DESCRIPTION
        "Notification of Event GBGP.17

        Message: 'BGP restart command issued'

        A restart BGP command has been issued from the system console."
    ::= { gbgpNotificationsPrefix 17 }

gbgpNotification18 NOTIFICATION-TYPE
    OBJECTS { 
              gbgp18_RemotePeer 
            }
    STATUS current
    DESCRIPTION
        "Notification of Event GBGP.18

        Message: 'Trying to connect to $1'

        Parameters list:
              $1: gbgp18_RemotePeer

        BGP subsystem is trying to connect to a remote peer."
    ::= { gbgpNotificationsPrefix 18 }

gbgpNotification19 NOTIFICATION-TYPE
    OBJECTS { 
              gbgp19_fromto, 
              gbgp19_RemoteAS,
              gbgp19_code,
              gbgp19_subcode 
            }
    STATUS current
    DESCRIPTION
        "Notification of Event GBGP.19

        Message: 'notification message $1 $2: $3/$4'

        Parameters list:
              $1: gbgp19_fromto
              $2: gbgp19_RemoteAS
              $3: gbgp19_code
              $4: gbgp19_subcode

        A notification message has been sent or received."
    ::= { gbgpNotificationsPrefix 19 }

gbgpNotification20 NOTIFICATION-TYPE
    OBJECTS { 
              gbgp20_RemotePeer, 
              gbgp20_cause 
            }
    STATUS current
    DESCRIPTION
        "Notification of Event GBGP.20

        Message: 'Peer $1 is idle. Cause $2'

        Parameters list:
              $1: gbgp20_RemotePeer
              $2: gbgp20_cause

        Changing state of peer to idled. The cause is printed at the end of
        the message."
    ::= { gbgpNotificationsPrefix 20 }

gbgpNotification21 NOTIFICATION-TYPE
    STATUS current
    DESCRIPTION
        "Notification of Event GBGP.21

        Message: 'Could not read config'

        Could not read BGP configuration."
    ::= { gbgpNotificationsPrefix 21 }

gbgpNotification22 NOTIFICATION-TYPE
    OBJECTS { 
              gbgp22_DiagnosticMessage 
            }
    STATUS current
    DESCRIPTION
        "Notification of Event GBGP.22

        Message: 'Error reading config: $1'

        Parameters list:
              $1: gbgp22_DiagnosticMessage

        The error printed occurred while reading the configuration."
    ::= { gbgpNotificationsPrefix 22 }

gbgpNotification23 NOTIFICATION-TYPE
    OBJECTS { 
              gbgp23_NumberOfComms, 
              gbgp23_Communities 
            }
    STATUS current
    DESCRIPTION
        "Notification of Event GBGP.23

        Message: 'Received update packet with $1 communitites: $2'

        Parameters list:
              $1: gbgp23_NumberOfComms
              $2: gbgp23_Communities

        An update packet has been received with community attributes."
    ::= { gbgpNotificationsPrefix 23 }

gbgpNotification24 NOTIFICATION-TYPE
    OBJECTS { 
              gbgp24_RouteDest, 
              gbgp24_RouteMask,
              gbgp24_Route-MapName 
            }
    STATUS current
    DESCRIPTION
        "Notification of Event GBGP.24

        Message: 'Discarded $1/$2 due to route-map with name $3'

        Parameters list:
              $1: gbgp24_RouteDest
              $2: gbgp24_RouteMask
              $3: gbgp24_Route-MapName

        A route received in an update packet has been discarded due to
        preconfigured route-map in/out policy for this neighbor."
    ::= { gbgpNotificationsPrefix 24 }

gbgpNotification25 NOTIFICATION-TYPE
    OBJECTS { 
              gbgp25_RouteDest, 
              gbgp25_RouteMask,
              gbgp25_OldLocalPref,
              gbgp25_NewLocalPref 
            }
    STATUS current
    DESCRIPTION
        "Notification of Event GBGP.25

        Message: 'Changed localpref of route $1/$2 from $3 to $4'

        Parameters list:
              $1: gbgp25_RouteDest
              $2: gbgp25_RouteMask
              $3: gbgp25_OldLocalPref
              $4: gbgp25_NewLocalPref

        The local pref value of a route received in an update packet
        has been changed due to a preconfigured route-map in/out policy
        for this neighbor."
    ::= { gbgpNotificationsPrefix 25 }

gbgpNotification26 NOTIFICATION-TYPE
    OBJECTS { 
              gbgp26_RouteMapName 
            }
    STATUS current
    DESCRIPTION
        "Notification of Event GBGP.26

        Message: 'Maximum number of communities exceeded applying route-map $1'

        Parameters list:
              $1: gbgp26_RouteMapName

        Could not apply the route-map policy: max number of communities per
        route exceeded."
    ::= { gbgpNotificationsPrefix 26 }

gbgpNotification27 NOTIFICATION-TYPE
    OBJECTS { 
              gbgp27_RouteDest, 
              gbgp27_RouteMask,
              gbgp27_OldMetric,
              gbgp27_NewMetric 
            }
    STATUS current
    DESCRIPTION
        "Notification of Event GBGP.27

        Message: 'Changed metric of route $1/$2 from $3 to $4'

        Parameters list:
              $1: gbgp27_RouteDest
              $2: gbgp27_RouteMask
              $3: gbgp27_OldMetric
              $4: gbgp27_NewMetric

        The metric value of a route received in an update packet
        has been changed due to a preconfigured route-map in/out policy
        for this neighbor."
    ::= { gbgpNotificationsPrefix 27 }

gbgpNotification28 NOTIFICATION-TYPE
    OBJECTS { 
              gbgp28_RemotePeerAddress, 
              gbgp28_AutonomousSystem 
            }
    STATUS current
    DESCRIPTION
        "Notification of Event GBGP.28

        Message: 'Backward status transition. Peer $1/AS $2'

        Parameters list:
              $1: gbgp28_RemotePeerAddress
              $2: gbgp28_AutonomousSystem

        The status of the specified peer has changed from a higher
        numbered status to a lower numbered status."
    ::= { gbgpNotificationsPrefix 28 }

gbgpNotification29 NOTIFICATION-TYPE
    OBJECTS { 
              gbgp29_RemotePeerAddress, 
              gbgp29_AutonomousSystem 
            }
    STATUS current
    DESCRIPTION
        "Notification of Event GBGP.29

        Message: 'The system disconnected from a configured BGP peer. Remote address is $1 AS $2'

        Parameters list:
              $1: gbgp29_RemotePeerAddress
              $2: gbgp29_AutonomousSystem

        A connection to a ESTABLISHED BGP peer has been lost. Possible causes
        are either a keepalive timer timeout or a TCP protocol error. The status
        of this peer is changed to ACTIVE."
    ::= { gbgpNotificationsPrefix 29 }

gbgpNotification30 NOTIFICATION-TYPE
    OBJECTS { 
              gbgp30_PacketType, 
              gbgp30_RemotePeerAddress,
              gbgp30_AutonomousSystem 
            }
    STATUS current
    DESCRIPTION
        "Notification of Event GBGP.30

        Message: 'Received $1 message from peer $2/AS $3'

        Parameters list:
              $1: gbgp30_PacketType
              $2: gbgp30_RemotePeerAddress
              $3: gbgp30_AutonomousSystem

        A valid incoming BGP message has been received from a peer.
        The type of message is shown, as well as the remote peer address and
        autonomous system."
    ::= { gbgpNotificationsPrefix 30 }

gbgpNotification31 NOTIFICATION-TYPE
    OBJECTS { 
              gbgp31_PacketType, 
              gbgp31_RemotePeerAddress,
              gbgp31_AutonomousSystem 
            }
    STATUS current
    DESCRIPTION
        "Notification of Event GBGP.31

        Message: 'Sending $1 message to peer $2/AS $3'

        Parameters list:
              $1: gbgp31_PacketType
              $2: gbgp31_RemotePeerAddress
              $3: gbgp31_AutonomousSystem

        A message is been sent to a remote peer.
        The type of message is shown, as well as the remote peer address and
        autonomous system."
    ::= { gbgpNotificationsPrefix 31 }

gbgpNotification32 NOTIFICATION-TYPE
    OBJECTS { 
              gbgp32_RemotePeerAddress, 
              gbgp32_AutonomousSystem 
            }
    STATUS current
    DESCRIPTION
        "Notification of Event GBGP.32

        Message: 'The system connected to BGP peer. Address is $1, AS is $2.'

        Parameters list:
              $1: gbgp32_RemotePeerAddress
              $2: gbgp32_AutonomousSystem

        A valid connection has been made to a configured BGP peer. Peer status
        is changed to ESTABLISHED."
    ::= { gbgpNotificationsPrefix 32 }

gbgpNotification33 NOTIFICATION-TYPE
    OBJECTS { 
              gbgp33_RouteDest, 
              gbgp33_RoutePrefixLen,
              gbgp33_NextHop,
              gbgp33_Preference,
              gbgp33_Metric,
              gbgp33_LocalPref 
            }
    STATUS current
    DESCRIPTION
        "Notification of Event GBGP.33

        Message: 'received route update $1/$2 $3 pref $4 metric $5 localpref $6'

        Parameters list:
              $1: gbgp33_RouteDest
              $2: gbgp33_RoutePrefixLen
              $3: gbgp33_NextHop
              $4: gbgp33_Preference
              $5: gbgp33_Metric
              $6: gbgp33_LocalPref

        An update message for the route shown has been received. This message
        does not mean that this route has been made active, it just means that
        the system has received information for this route from a BGP peer. This
        route will be processed, and, taking into account the
        configured preference rules, will be or not exported to the active
        routes table. To be able to see changes in the active RT, please
        use the IPv6 subsystem events."
    ::= { gbgpNotificationsPrefix 33 }

gbgpNotification34 NOTIFICATION-TYPE
    OBJECTS { 
              gbgp34_RouteDest, 
              gbgp34_RoutePrefixLen,
              gbgp34_NextHop,
              gbgp34_NextHopLocal,
              gbgp34_Preference,
              gbgp34_Metric,
              gbgp34_LocalPref 
            }
    STATUS current
    DESCRIPTION
        "Notification of Event GBGP.34

        Message: 'received route update $1/$2 $3 ($4) pref $5 metric $6 localpref $7'

        Parameters list:
              $1: gbgp34_RouteDest
              $2: gbgp34_RoutePrefixLen
              $3: gbgp34_NextHop
              $4: gbgp34_NextHopLocal
              $5: gbgp34_Preference
              $6: gbgp34_Metric
              $7: gbgp34_LocalPref

        An update message for the route shown has been received. This message
        does not mean that this route has been made active, it just means that
        the system has received information for this route from a BGP peer. This
        route will be processed, and, taking into account the
        configured preference rules, will be or not exported to the active
        routes table. To be able to see changes in the active RT, please
        use the IPv6 subsystem events."
    ::= { gbgpNotificationsPrefix 34 }

gbgpNotification35 NOTIFICATION-TYPE
    OBJECTS { 
              gbgp35_RouteDest, 
              gbgp35_RoutePrefixLen,
              gbgp35_BGPPeer 
            }
    STATUS current
    DESCRIPTION
        "Notification of Event GBGP.35

        Message: 'route $1/$2 from $3 is now unreachable'

        Parameters list:
              $1: gbgp35_RouteDest
              $2: gbgp35_RoutePrefixLen
              $3: gbgp35_BGPPeer

        An unreach message has been received for this route. This message
        does not mean that this route will be deleted from the active RT
        (it is possible that the route was not even made active when it
        was received). To be able to see changes in the active RT, please
        use the IPv6 subsystem events."
    ::= { gbgpNotificationsPrefix 35 }

gbgpNotification36 NOTIFICATION-TYPE
    OBJECTS { 
              gbgp36_RemotePeerAddress, 
              gbgp36_AutonomousSystem 
            }
    STATUS current
    DESCRIPTION
        "Notification of Event GBGP.36

        Message: 'The holdtime for peer $1/AS $2 has expired'

        Parameters list:
              $1: gbgp36_RemotePeerAddress
              $2: gbgp36_AutonomousSystem

        The holdtime for a given BGP peer has expired."
    ::= { gbgpNotificationsPrefix 36 }

gbgpNotification37 NOTIFICATION-TYPE
    OBJECTS { 
              gbgp37_Dest, 
              gbgp37_PrefixLen,
              gbgp37_NextHop 
            }
    STATUS current
    DESCRIPTION
        "Notification of Event GBGP.37

        Message: 'Add route $1/$2 $3'

        Parameters list:
              $1: gbgp37_Dest
              $2: gbgp37_PrefixLen
              $3: gbgp37_NextHop

        Adding route into BGP routing Database."
    ::= { gbgpNotificationsPrefix 37 }

gbgpNotification38 NOTIFICATION-TYPE
    OBJECTS { 
              gbgp38_Dest, 
              gbgp38_PrefixLen 
            }
    STATUS current
    DESCRIPTION
        "Notification of Event GBGP.38

        Message: 'Add direct rte $1/$2'

        Parameters list:
              $1: gbgp38_Dest
              $2: gbgp38_PrefixLen

        Adding direct route to BGP routing Database."
    ::= { gbgpNotificationsPrefix 38 }

gbgpNotification39 NOTIFICATION-TYPE
    OBJECTS { 
              gbgp39_RouteDest, 
              gbgp39_RoutePrefixLen,
              gbgp39_Route-MapName 
            }
    STATUS current
    DESCRIPTION
        "Notification of Event GBGP.39

        Message: 'Discarded $1/$2 due to route-map with name $3'

        Parameters list:
              $1: gbgp39_RouteDest
              $2: gbgp39_RoutePrefixLen
              $3: gbgp39_Route-MapName

        A route received in an update packet has been discarded due to
        preconfigured route-map in/out policy for this neighbor."
    ::= { gbgpNotificationsPrefix 39 }

gbgpNotification40 NOTIFICATION-TYPE
    OBJECTS { 
              gbgp40_RouteDest, 
              gbgp40_RoutePrefixLen,
              gbgp40_OldLocalPref,
              gbgp40_NewLocalPref 
            }
    STATUS current
    DESCRIPTION
        "Notification of Event GBGP.40

        Message: 'Changed localpref of route $1/$2 from $3 to $4'

        Parameters list:
              $1: gbgp40_RouteDest
              $2: gbgp40_RoutePrefixLen
              $3: gbgp40_OldLocalPref
              $4: gbgp40_NewLocalPref

        The local pref value of a route received in an update packet
        has been changed due to a preconfigured route-map in/out policy
        for this neighbor."
    ::= { gbgpNotificationsPrefix 40 }

gbgpNotification41 NOTIFICATION-TYPE
    OBJECTS { 
              gbgp41_RouteDest, 
              gbgp41_RoutePrefixLen,
              gbgp41_OldMetric,
              gbgp41_NewMetric 
            }
    STATUS current
    DESCRIPTION
        "Notification of Event GBGP.41

        Message: 'Changed metric of route $1/$2 from $3 to $4'

        Parameters list:
              $1: gbgp41_RouteDest
              $2: gbgp41_RoutePrefixLen
              $3: gbgp41_OldMetric
              $4: gbgp41_NewMetric

        The metric value of a route received in an update packet
        has been changed due to a preconfigured route-map in/out policy
        for this neighbor."
    ::= { gbgpNotificationsPrefix 41 }

gbgpNotification42 NOTIFICATION-TYPE
    OBJECTS { 
              gbgp42_RouteDest, 
              gbgp42_RoutePrefixLen,
              gbgp42_OldNexthop,
              gbgp42_NewNexthop,
              gbgp42_rtmapinout 
            }
    STATUS current
    DESCRIPTION
        "Notification of Event GBGP.42

        Message: 'Changed nexthop of route $1/$2 from $3 to $4 ($5)'

        Parameters list:
              $1: gbgp42_RouteDest
              $2: gbgp42_RoutePrefixLen
              $3: gbgp42_OldNexthop
              $4: gbgp42_NewNexthop
              $5: gbgp42_rtmapinout

        The nexthop value of a route received in an update packet
        has been changed due to a preconfigured route-map in/out policy
        for this neighbor."
    ::= { gbgpNotificationsPrefix 42 }

gbgpNotification43 NOTIFICATION-TYPE
    OBJECTS { 
              gbgp43_RouteDest, 
              gbgp43_RoutePrefixLen,
              gbgp43_NewNexthop,
              gbgp43_rtmapinout 
            }
    STATUS current
    DESCRIPTION
        "Notification of Event GBGP.43

        Message: 'Set nexthop of route $1/$2 to $3 ($4)'

        Parameters list:
              $1: gbgp43_RouteDest
              $2: gbgp43_RoutePrefixLen
              $3: gbgp43_NewNexthop
              $4: gbgp43_rtmapinout

        The nexthop value of a route transmitted in an update packet
        has been set due to a preconfigured route-map in/out policy
        for this neighbor."
    ::= { gbgpNotificationsPrefix 43 }

gbgpNotification44 NOTIFICATION-TYPE
    OBJECTS { 
              gbgp44_RouteDest, 
              gbgp44_RouteMask,
              gbgp44_OldNexthop,
              gbgp44_NewNexthop,
              gbgp44_rtmapinout 
            }
    STATUS current
    DESCRIPTION
        "Notification of Event GBGP.44

        Message: 'Changed nexthop of route $1/$2 from $3 to $4 ($5)'

        Parameters list:
              $1: gbgp44_RouteDest
              $2: gbgp44_RouteMask
              $3: gbgp44_OldNexthop
              $4: gbgp44_NewNexthop
              $5: gbgp44_rtmapinout

        The nexthop value of a route received in an update packet
        has been changed due to a preconfigured route-map in/out policy
        for this neighbor."
    ::= { gbgpNotificationsPrefix 44 }

gbgpNotification45 NOTIFICATION-TYPE
    OBJECTS { 
              gbgp45_RouteDest, 
              gbgp45_RouteMask,
              gbgp45_NewNexthop,
              gbgp45_rtmapinout 
            }
    STATUS current
    DESCRIPTION
        "Notification of Event GBGP.45

        Message: 'Set nexthop of route $1/$2 to $3 ($4)'

        Parameters list:
              $1: gbgp45_RouteDest
              $2: gbgp45_RouteMask
              $3: gbgp45_NewNexthop
              $4: gbgp45_rtmapinout

        The nexthop value of a route transmitted in an update packet
        has been set due to a preconfigured route-map in/out policy
        for this neighbor."
    ::= { gbgpNotificationsPrefix 45 }

gbgpNotification46 NOTIFICATION-TYPE
    OBJECTS { 
              gbgp46_RemotePeerAddress, 
              gbgp46_AutonomousSystem 
            }
    STATUS current
    DESCRIPTION
        "Notification of Event GBGP.46

        Message: 'Backward status transition. Peer $1/AS $2'

        Parameters list:
              $1: gbgp46_RemotePeerAddress
              $2: gbgp46_AutonomousSystem

        The status of the specified peer has changed from a higher
        numbered status to a lower numbered status."
    ::= { gbgpNotificationsPrefix 46 }

gbgpNotification47 NOTIFICATION-TYPE
    OBJECTS { 
              gbgp47_Error_msg, 
              gbgp47_RemotePeerAddress,
              gbgp47_AutonomousSystem 
            }
    STATUS current
    DESCRIPTION
        "Notification of Event GBGP.47

        Message: 'Received Update Error: $1 (Peer $2/AS $3)'

        Parameters list:
              $1: gbgp47_Error_msg
              $2: gbgp47_RemotePeerAddress
              $3: gbgp47_AutonomousSystem

        The update received contains an invalid field."
    ::= { gbgpNotificationsPrefix 47 }

gbgpNotification48 NOTIFICATION-TYPE
    OBJECTS { 
              gbgp48_opt_param, 
              gbgp48_opt_param_str,
              gbgp48_RemotePeerAddress 
            }
    STATUS current
    DESCRIPTION
        "Notification of Event GBGP.48

        Message: 'Received Open with optional parameter $1 ($2) (Peer $3)'

        Parameters list:
              $1: gbgp48_opt_param
              $2: gbgp48_opt_param_str
              $3: gbgp48_RemotePeerAddress

        Received an open msg with an optional parameter."
    ::= { gbgpNotificationsPrefix 48 }

gbgpNotification49 NOTIFICATION-TYPE
    OBJECTS { 
              gbgp49_capab_code, 
              gbgp49_capab_len,
              gbgp49_RemotePeerAddress 
            }
    STATUS current
    DESCRIPTION
        "Notification of Event GBGP.49

        Message: 'Received Open with Capability code $1 lenght $2 (Peer $3)'

        Parameters list:
              $1: gbgp49_capab_code
              $2: gbgp49_capab_len
              $3: gbgp49_RemotePeerAddress

        Received an open msg with capability in the optional paramater."
    ::= { gbgpNotificationsPrefix 49 }

gbgpNotification50 NOTIFICATION-TYPE
    OBJECTS { 
              gbgp50_afi, 
              gbgp50_safi,
              gbgp50_RemotePeerAddress 
            }
    STATUS current
    DESCRIPTION
        "Notification of Event GBGP.50

        Message: 'Received Open with MultiProtocol Extension Capability for afi/safi: $1/$2 (Peer $3)'

        Parameters list:
              $1: gbgp50_afi
              $2: gbgp50_safi
              $3: gbgp50_RemotePeerAddress

        Received an open msg with MP_EXT capability."
    ::= { gbgpNotificationsPrefix 50 }

gbgpNotification51 NOTIFICATION-TYPE
    OBJECTS { 
              gbgp51_capab_code, 
              gbgp51_RemotePeerAddress 
            }
    STATUS current
    DESCRIPTION
        "Notification of Event GBGP.51

        Message: 'Received Open with no supported Capability code $1, ignoring capability (Peer $2)'

        Parameters list:
              $1: gbgp51_capab_code
              $2: gbgp51_RemotePeerAddress

        Received an open msg with an unsupported capability (ignoring)."
    ::= { gbgpNotificationsPrefix 51 }

gbgpNotification52 NOTIFICATION-TYPE
    OBJECTS { 
              gbgp52_Action, 
              gbgp52_Prefix,
              gbgp52_PrefixLen,
              gbgp52_Information,
              gbgp52_Origin 
            }
    STATUS current
    DESCRIPTION
        "Notification of Event GBGP.52

        Message: 'Receive route $1 $2/$3 ($4) from $5'

        Parameters list:
              $1: gbgp52_Action
              $2: gbgp52_Prefix
              $3: gbgp52_PrefixLen
              $4: gbgp52_Information
              $5: gbgp52_Origin

        When a route is received, there are four posible actions: install (ins),
        remove (rem), discard (dis) or idle (idl).
        - install : the route is installed in the BGP table and marked as usable
        (the preference is a positive integer).
        - remove : the route will be removed from the BGP table if already exists.
        - discard : the route won't be installed in the BGP table.
        - idle : the route will never be usable (the preference is a negative
        integer).
        Along with each action, an informative message is shown. If everything
        goes well, the message is 'ok'. Otherwise, a descriptive message will
        explain the cause of the error."
    ::= { gbgpNotificationsPrefix 52 }

gbgpNotification53 NOTIFICATION-TYPE
    OBJECTS { 
              gbgp53_RemotePeerName, 
              gbgp53_DataHexDump 
            }
    STATUS current
    DESCRIPTION
        "Notification of Event GBGP.53

        Message: 'Received raw data from peer $1: hex dump is $2'

        Parameters list:
              $1: gbgp53_RemotePeerName
              $2: gbgp53_DataHexDump

        Data has been received from the specified peer. The received data is
        shown in hexadecimal."
    ::= { gbgpNotificationsPrefix 53 }

gbgpNotification54 NOTIFICATION-TYPE
    OBJECTS { 
              gbgp54_RemotePeerName, 
              gbgp54_DataHexDump 
            }
    STATUS current
    DESCRIPTION
        "Notification of Event GBGP.54

        Message: 'Received invalid message from peer $1: hex dump is $2'

        Parameters list:
              $1: gbgp54_RemotePeerName
              $2: gbgp54_DataHexDump

        An invalid message has been received from the specified peer. The
        received message data is shown in hexadecimal."
    ::= { gbgpNotificationsPrefix 54 }

gbgpNotification55 NOTIFICATION-TYPE
    OBJECTS { 
              gbgp55_RemotePeerName, 
              gbgp55_DataHexDump 
            }
    STATUS current
    DESCRIPTION
        "Notification of Event GBGP.55

        Message: 'Received message from peer $1: hex dump is $2'

        Parameters list:
              $1: gbgp55_RemotePeerName
              $2: gbgp55_DataHexDump

        A message has been received from the specified peer. The received
        message data is shown in hexadecimal."
    ::= { gbgpNotificationsPrefix 55 }

gbgpNotification56 NOTIFICATION-TYPE
    OBJECTS { 
              gbgp56_RemotePeerName, 
              gbgp56_DataHexDump 
            }
    STATUS current
    DESCRIPTION
        "Notification of Event GBGP.56

        Message: 'Send message to peer $1: hex dump is $2'

        Parameters list:
              $1: gbgp56_RemotePeerName
              $2: gbgp56_DataHexDump

        A message is sent to the specified peer. The message data is shown in
        hexadecimal."
    ::= { gbgpNotificationsPrefix 56 }

gbgpNotification57 NOTIFICATION-TYPE
    OBJECTS { 
              gbgp57_RemotePeerName, 
              gbgp57_DataHexDump 
            }
    STATUS current
    DESCRIPTION
        "Notification of Event GBGP.57

        Message: 'Send raw data to peer $1: hex dump is $2'

        Parameters list:
              $1: gbgp57_RemotePeerName
              $2: gbgp57_DataHexDump

        Data has been sent to the specified peer. The data is shown in
        hexadecimal."
    ::= { gbgpNotificationsPrefix 57 }

gbgpNotification58 NOTIFICATION-TYPE
    OBJECTS { 
              gbgp58_afi, 
              gbgp58_safi,
              gbgp58_RemotePeerAddress 
            }
    STATUS current
    DESCRIPTION
        "Notification of Event GBGP.58

        Message: 'Received Open without Multiprotocol Extensions Capability for afi/safi $1/$2 (Peer $3)'

        Parameters list:
              $1: gbgp58_afi
              $2: gbgp58_safi
              $3: gbgp58_RemotePeerAddress

        Received an open message without Multiprotocol Extensions Capability for
        an AFI/SAFI which is needed to operate."
    ::= { gbgpNotificationsPrefix 58 }

gbgpNotification59 NOTIFICATION-TYPE
    OBJECTS { 
              gbgp59_restart_flags, 
              gbgp59_restart_time,
              gbgp59_RemotePeerAddress 
            }
    STATUS current
    DESCRIPTION
        "Notification of Event GBGP.59

        Message: 'Received Open with Graceful Restart Capability with Restart Flags $1 Time $2 (Peer $3)'

        Parameters list:
              $1: gbgp59_restart_flags
              $2: gbgp59_restart_time
              $3: gbgp59_RemotePeerAddress

        Received an open message with Graceful Restart Capability. The Restart
        Flags and Restart Time values are shown."
    ::= { gbgpNotificationsPrefix 59 }

gbgpNotification60 NOTIFICATION-TYPE
    OBJECTS { 
              gbgp60_afi, 
              gbgp60_safi,
              gbgp60_flags,
              gbgp60_RemotePeerAddress 
            }
    STATUS current
    DESCRIPTION
        "Notification of Event GBGP.60

        Message: 'Received Open with Graceful Restart Capability with afi/safi $1/$2 Flags 0x$3 (Peer $4)'

        Parameters list:
              $1: gbgp60_afi
              $2: gbgp60_safi
              $3: gbgp60_flags
              $4: gbgp60_RemotePeerAddress

        Received an open message with Graceful Restart Capability, with the
        Address Family specified by the afi/safi pair. The Address Family Flags
        are shown."
    ::= { gbgpNotificationsPrefix 60 }

gbgpNotification61 NOTIFICATION-TYPE
    OBJECTS { 
              gbgp61_afi, 
              gbgp61_safi,
              gbgp61_RemotePeerAddress 
            }
    STATUS current
    DESCRIPTION
        "Notification of Event GBGP.61

        Message: 'Send Update End-of-RIB marker for afi/safi $1/$2 (Peer $3)'

        Parameters list:
              $1: gbgp61_afi
              $2: gbgp61_safi
              $3: gbgp61_RemotePeerAddress

        An Update message conforming to the End-Of-RIB marker specification is
        sent for the Address Family specified by the afi/safi pair."
    ::= { gbgpNotificationsPrefix 61 }

gbgpNotification62 NOTIFICATION-TYPE
    OBJECTS { 
              gbgp62_afi, 
              gbgp62_safi,
              gbgp62_RemotePeerAddress 
            }
    STATUS current
    DESCRIPTION
        "Notification of Event GBGP.62

        Message: 'Received Update End-of-RIB marker for afi/safi $1/$2 (Peer $3)'

        Parameters list:
              $1: gbgp62_afi
              $2: gbgp62_safi
              $3: gbgp62_RemotePeerAddress

        An Update message conforming to the End-Of-RIB marker specification has
        been received for the Address Family specified by the afi/safi pair."
    ::= { gbgpNotificationsPrefix 62 }

gbgpNotification63 NOTIFICATION-TYPE
    STATUS current
    DESCRIPTION
        "Notification of Event GBGP.63

        Message: 'Out of memory error'

        The system is out of memory."
    ::= { gbgpNotificationsPrefix 63 }

gbgpNotification64 NOTIFICATION-TYPE
    OBJECTS { 
              gbgp64_restart_flags, 
              gbgp64_restart_time,
              gbgp64_RemotePeerAddress 
            }
    STATUS current
    DESCRIPTION
        "Notification of Event GBGP.64

        Message: 'Send Open with Graceful Restart Capability with Restart Flags $1 Time $2 (Peer $3)'

        Parameters list:
              $1: gbgp64_restart_flags
              $2: gbgp64_restart_time
              $3: gbgp64_RemotePeerAddress

        Send an open message with Graceful Restart Capability. The Restart
        Flags and Restart Time values are shown."
    ::= { gbgpNotificationsPrefix 64 }

gbgpNotification65 NOTIFICATION-TYPE
    OBJECTS { 
              gbgp65_afi, 
              gbgp65_safi,
              gbgp65_flags,
              gbgp65_RemotePeerAddress 
            }
    STATUS current
    DESCRIPTION
        "Notification of Event GBGP.65

        Message: 'Send Open with Graceful Restart Capability with afi/safi $1/$2 Flags 0x$3 (Peer $4)'

        Parameters list:
              $1: gbgp65_afi
              $2: gbgp65_safi
              $3: gbgp65_flags
              $4: gbgp65_RemotePeerAddress

        Send an open message with Graceful Restart Capability, with the
        Address Family specified by the afi/safi pair. The Address Family Flags
        are shown."
    ::= { gbgpNotificationsPrefix 65 }

gbgpNotification66 NOTIFICATION-TYPE
    OBJECTS { 
              gbgp66_RemotePeerAddress 
            }
    STATUS current
    DESCRIPTION
        "Notification of Event GBGP.66

        Message: 'Graceful Restart on close triggers backup and discards stale information (Peer $1)'

        Parameters list:
              $1: gbgp66_RemotePeerAddress

        A peer session is being closed, and a backup for Graceful Restart has
        been triggered. Stale information is discarded because Graceful Restart
        is disabled."
    ::= { gbgpNotificationsPrefix 66 }

gbgpNotification67 NOTIFICATION-TYPE
    OBJECTS { 
              gbgp67_stale_type, 
              gbgp67_RemotePeerAddress 
            }
    STATUS current
    DESCRIPTION
        "Notification of Event GBGP.67

        Message: 'Graceful Restart on close triggers backup with $1 stale information (Peer $2)'

        Parameters list:
              $1: gbgp67_stale_type
              $2: gbgp67_RemotePeerAddress

        A peer session is being closed, and a backup for Graceful Restart has
        been triggered. New stale information is generated from scratch or
        reinitializing old stale information as specified in stale_type."
    ::= { gbgpNotificationsPrefix 67 }

gbgpNotification68 NOTIFICATION-TYPE
    OBJECTS { 
              gbgp68_dest_addr, 
              gbgp68_dest_len,
              gbgp68_RemotePeerAddress 
            }
    STATUS current
    DESCRIPTION
        "Notification of Event GBGP.68

        Message: 'Graceful Restart stale route create $1/$2 (Peer $3)'

        Parameters list:
              $1: gbgp68_dest_addr
              $2: gbgp68_dest_len
              $3: gbgp68_RemotePeerAddress

        Graceful Restart has created a stale route to the specified destination
        network."
    ::= { gbgpNotificationsPrefix 68 }

gbgpNotification69 NOTIFICATION-TYPE
    OBJECTS { 
              gbgp69_speaker_type, 
              gbgp69_family_count,
              gbgp69_route_count,
              gbgp69_RemotePeerAddress 
            }
    STATUS current
    DESCRIPTION
        "Notification of Event GBGP.69

        Message: 'Graceful Restart backup stale information for $1 speaker with $2 address families and $3 routes (Peer $4)'

        Parameters list:
              $1: gbgp69_speaker_type
              $2: gbgp69_family_count
              $3: gbgp69_route_count
              $4: gbgp69_RemotePeerAddress

        Graceful Restart made a backup generating stale information for a
        receiving or restarting speaker (as specified in speaker_type) with the
        specified number of address families and routes."
    ::= { gbgpNotificationsPrefix 69 }

gbgpNotification70 NOTIFICATION-TYPE
    OBJECTS { 
              gbgp70_speaker_type, 
              gbgp70_RemotePeerAddress 
            }
    STATUS current
    DESCRIPTION
        "Notification of Event GBGP.70

        Message: 'Graceful Restart established session for $1peaker (Peer $2)'

        Parameters list:
              $1: gbgp70_speaker_type
              $2: gbgp70_RemotePeerAddress

        Graceful Restart detected the session establishment for a receiving or
        restarting speaker as specified in speaker_type."
    ::= { gbgpNotificationsPrefix 70 }

gbgpNotification71 NOTIFICATION-TYPE
    OBJECTS { 
              gbgp71_afi, 
              gbgp71_safi,
              gbgp71_RemotePeerAddress 
            }
    STATUS current
    DESCRIPTION
        "Notification of Event GBGP.71

        Message: 'Graceful Restart established restarting speaker not blocking afi/safi $1/$2 (Peer $3)'

        Parameters list:
              $1: gbgp71_afi
              $2: gbgp71_safi
              $3: gbgp71_RemotePeerAddress

        Graceful Restart detected the session establishment for a restarting
        speaker, but no graceful restart capability was received or it was
        received with the 'Restart State' bit set. This peer will not be waited
        for to stop deferring."
    ::= { gbgpNotificationsPrefix 71 }

gbgpNotification72 NOTIFICATION-TYPE
    OBJECTS { 
              gbgp72_dest_addr, 
              gbgp72_dest_len,
              gbgp72_RemotePeerAddress 
            }
    STATUS current
    DESCRIPTION
        "Notification of Event GBGP.72

        Message: 'Graceful Restart route defer $1/$2 (Peer $3)'

        Parameters list:
              $1: gbgp72_dest_addr
              $2: gbgp72_dest_len
              $3: gbgp72_RemotePeerAddress

        Graceful Restart has deferred a restarting speaker route received in an
        update message. The route destination network is specified."
    ::= { gbgpNotificationsPrefix 72 }

gbgpNotification73 NOTIFICATION-TYPE
    OBJECTS { 
              gbgp73_dest_addr, 
              gbgp73_dest_len,
              gbgp73_cause,
              gbgp73_RemotePeerAddress 
            }
    STATUS current
    DESCRIPTION
        "Notification of Event GBGP.73

        Message: 'Graceful Restart stale route delete $1/$2 cause $3 (Peer $4)'

        Parameters list:
              $1: gbgp73_dest_addr
              $2: gbgp73_dest_len
              $3: gbgp73_cause
              $4: gbgp73_RemotePeerAddress

        Graceful Restart has deleted a stale route. The route destination
        network is specified. Possible causes are: 'rx nlri' when
        the receiving speaker stale route is superseded by a nlri received on an
        update message; 'term' when the BGP process is terminating; 'rx eor'
        when the End-of-RIB marker has been received by a receiving speaker;
        'estab' when the receiving speaker BGP session has been established and
        no 'Forwarding State' bit has been received for an address family;
        'stop defer' when the restarting speaker stops deferring an address
        family."
    ::= { gbgpNotificationsPrefix 73 }

gbgpNotification74 NOTIFICATION-TYPE
    OBJECTS { 
              gbgp74_RemotePeerAddress 
            }
    STATUS current
    DESCRIPTION
        "Notification of Event GBGP.74

        Message: 'Graceful Restart stale information timeout (Peer $1)'

        Parameters list:
              $1: gbgp74_RemotePeerAddress

        Graceful Restart stale information has timed out for the specified peer."
    ::= { gbgpNotificationsPrefix 74 }

gbgpNotification75 NOTIFICATION-TYPE
    OBJECTS { 
              gbgp75_cause, 
              gbgp75_RemotePeerAddress 
            }
    STATUS current
    DESCRIPTION
        "Notification of Event GBGP.75

        Message: 'Graceful Restart stale information delete with cause $1 (Peer $2)'

        Parameters list:
              $1: gbgp75_cause
              $2: gbgp75_RemotePeerAddress

        Graceful Restart stale information is deleted. The cause is specified."
    ::= { gbgpNotificationsPrefix 75 }

gbgpNotification76 NOTIFICATION-TYPE
    OBJECTS { 
              gbgp76_cause, 
              gbgp76_RemotePeerAddress 
            }
    STATUS current
    DESCRIPTION
        "Notification of Event GBGP.76

        Message: 'Graceful Restart stale peer delete with cause $1 (Peer $2)'

        Parameters list:
              $1: gbgp76_cause
              $2: gbgp76_RemotePeerAddress

        Graceful Restart stale peer is deleted. This is an idle unconfigured
        peer which lost the stale iformation. The cause is specified."
    ::= { gbgpNotificationsPrefix 76 }

gbgpNotification77 NOTIFICATION-TYPE
    OBJECTS { 
              gbgp77_afi, 
              gbgp77_safi,
              gbgp77_RemotePeerAddress 
            }
    STATUS current
    DESCRIPTION
        "Notification of Event GBGP.77

        Message: 'Graceful Restart initial update deferred for afi/safi $1/$2 (Peer $3)'

        Parameters list:
              $1: gbgp77_afi
              $2: gbgp77_safi
              $3: gbgp77_RemotePeerAddress

        Graceful Restart initial update has been deferred for the specified
        address family."
    ::= { gbgpNotificationsPrefix 77 }

gbgpNotification78 NOTIFICATION-TYPE
    OBJECTS { 
              gbgp78_afi, 
              gbgp78_safi,
              gbgp78_RemotePeerAddress 
            }
    STATUS current
    DESCRIPTION
        "Notification of Event GBGP.78

        Message: 'Graceful Restart initial update with eor for afi/safi $1/$2 (Peer $3)'

        Parameters list:
              $1: gbgp78_afi
              $2: gbgp78_safi
              $3: gbgp78_RemotePeerAddress

        Graceful Restart initial update with End-of-RIB marker has been started
        for the specified address family."
    ::= { gbgpNotificationsPrefix 78 }

gbgpNotification79 NOTIFICATION-TYPE
    OBJECTS { 
              gbgp79_timeout_seconds 
            }
    STATUS current
    DESCRIPTION
        "Notification of Event GBGP.79

        Message: 'Graceful Restart selection deferral started with timeout $1'

        Parameters list:
              $1: gbgp79_timeout_seconds

        Graceful Restart selection deferral started for all address families.
        The selection deferral timer has been started with the specified
        timeout."
    ::= { gbgpNotificationsPrefix 79 }

gbgpNotification80 NOTIFICATION-TYPE
    STATUS current
    DESCRIPTION
        "Notification of Event GBGP.80

        Message: 'Graceful Restart selection deferral terminated'

        Graceful Restart selection deferral has terminated because the BGP
        process is shut down."
    ::= { gbgpNotificationsPrefix 80 }

gbgpNotification81 NOTIFICATION-TYPE
    STATUS current
    DESCRIPTION
        "Notification of Event GBGP.81

        Message: 'Graceful Restart selection deferral timeout'

        Graceful Restart selection deferral timer has expired."
    ::= { gbgpNotificationsPrefix 81 }

gbgpNotification82 NOTIFICATION-TYPE
    STATUS current
    DESCRIPTION
        "Notification of Event GBGP.82

        Message: 'Graceful Restart selection deferral ended'

        Graceful Restart selection deferral ended for all families."
    ::= { gbgpNotificationsPrefix 82 }

gbgpNotification83 NOTIFICATION-TYPE
    OBJECTS { 
              gbgp83_afi, 
              gbgp83_safi 
            }
    STATUS current
    DESCRIPTION
        "Notification of Event GBGP.83

        Message: 'Graceful Restart selection deferral ended for afi/safi $1/$2'

        Parameters list:
              $1: gbgp83_afi
              $2: gbgp83_safi

        Graceful Restart selection deferral ended for the specified address
        family."
    ::= { gbgpNotificationsPrefix 83 }

gbgpNotification84 NOTIFICATION-TYPE
    OBJECTS { 
              gbgp84_dest_addr, 
              gbgp84_dest_len,
              gbgp84_RemotePeerAddress 
            }
    STATUS current
    DESCRIPTION
        "Notification of Event GBGP.84

        Message: 'Graceful Restart route undefer $1/$2 (Peer $3)'

        Parameters list:
              $1: gbgp84_dest_addr
              $2: gbgp84_dest_len
              $3: gbgp84_RemotePeerAddress

        Graceful Restart has stopped deferring a restarting speaker route. The
        route destination network is specified."
    ::= { gbgpNotificationsPrefix 84 }

gbgpNotification85 NOTIFICATION-TYPE
    OBJECTS { 
              gbgp85_RemotePeerAddress 
            }
    STATUS current
    DESCRIPTION
        "Notification of Event GBGP.85

        Message: 'Graceful Restart peer deferral started (Peer $1)'

        Parameters list:
              $1: gbgp85_RemotePeerAddress

        Graceful Restart peer has started address family deferral."
    ::= { gbgpNotificationsPrefix 85 }

gbgpNotification86 NOTIFICATION-TYPE
    OBJECTS { 
              gbgp86_RemotePeerAddress 
            }
    STATUS current
    DESCRIPTION
        "Notification of Event GBGP.86

        Message: 'Graceful Restart peer deferral stopped (Peer $1)'

        Parameters list:
              $1: gbgp86_RemotePeerAddress

        Graceful Restart peer has stopped address family deferral."
    ::= { gbgpNotificationsPrefix 86 }

gbgpNotification87 NOTIFICATION-TYPE
    OBJECTS { 
              gbgp87_RouteDest, 
              gbgp87_MaskLenght,
              gbgp87_NewOrigin 
            }
    STATUS current
    DESCRIPTION
        "Notification of Event GBGP.87

        Message: 'Changed origin of route $1/$2 to $3'

        Parameters list:
              $1: gbgp87_RouteDest
              $2: gbgp87_MaskLenght
              $3: gbgp87_NewOrigin

        The local origin value of a route received in an update packet
        has been changed due to a preconfigured route-map in/out policy
        for this neighbor."
    ::= { gbgpNotificationsPrefix 87 }

gbgpNotification88 NOTIFICATION-TYPE
    OBJECTS { 
              gbgp88_maximum_prefixes, 
              gbgp88_current_prefixes,
              gbgp88_RemotePeerAddress,
              gbgp88_AutonomousSystem 
            }
    STATUS current
    DESCRIPTION
        "Notification of Event GBGP.88

        Message: 'Peer prefix database overflow maximum $1 current $2 (Peer $3/AS $4)'

        Parameters list:
              $1: gbgp88_maximum_prefixes
              $2: gbgp88_current_prefixes
              $3: gbgp88_RemotePeerAddress
              $4: gbgp88_AutonomousSystem

        The peer prefix database is above the maximum-prefix configured limit.
        Both this limit and the current prefix count are shown."
    ::= { gbgpNotificationsPrefix 88 }


END
