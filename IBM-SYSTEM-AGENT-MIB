IBM-SYSTEM-AGENT-MIB DEFINITIONS ::= BEGIN

IMPORTS
   OBJECT-TYPE
      FROM RFC-1212

   TRAP-TYPE
      FROM RFC-1215

   ibmSystemAgent,
   Boolean, Uint8, Sint8, Uint16, Sint16, Uint32,
   Sint32, Uint64, Sint64, Real32, Real64, String, Datetime
      FROM IBM-SYSTEM-MIB;

--
-- Primitive types
--
Boolean  ::= INTEGER (0..1)
Uint8    ::= INTEGER (0..255)
Sint8    ::= INTEGER (-128..127)
Uint16   ::= INTEGER (0..65535)
Sint16   ::= INTEGER (-32767..32766)
Uint32   ::= INTEGER (0..4294967295)
Sint32   ::= INTEGER (-2147483647..2147483646)
Uint64   ::= OCTET STRING
Sint64   ::= OCTET STRING
Real32   ::= INTEGER (-1..1)
Real64   ::= INTEGER (-1..1)
String   ::= OCTET STRING
Datetime ::= OCTET STRING


ibmSystemHTTPConfigurationTable OBJECT-TYPE
   SYNTAX         SEQUENCE OF IbmSystemHTTPConfigurationEntry
   ACCESS         not-accessible
   STATUS         mandatory
   DESCRIPTION    ""
   REFERENCE      "IBMPSG_HTTPConfiguration"
::= { ibmSystemAgent 2 }

ibmSystemHTTPConfigurationEntry OBJECT-TYPE
   SYNTAX         IbmSystemHTTPConfigurationEntry
   ACCESS         not-accessible
   STATUS         mandatory
   DESCRIPTION    ""
   INDEX          { ibmSystemHTTPConfigurationKeyIndex }
::= { ibmSystemHTTPConfigurationTable 1 }

IbmSystemHTTPConfigurationEntry ::= SEQUENCE
{
   ibmSystemHTTPConfigurationKeyIndex String,
   ibmSystemHTTPConfigurationSettingId String,
   ibmSystemHTTPConfigurationPort Uint16
}

ibmSystemHTTPConfigurationKeyIndex OBJECT-TYPE
   SYNTAX         String
   ACCESS         read-write
   STATUS         mandatory
   DESCRIPTION    ""
   REFERENCE      "IBMPSG_HTTPConfiguration.KeyIndex"
::= { ibmSystemHTTPConfigurationEntry 1 }

ibmSystemHTTPConfigurationSettingId OBJECT-TYPE
   SYNTAX         String
   ACCESS         read-write
   STATUS         mandatory
   DESCRIPTION    ""
   REFERENCE      "IBMPSG_HTTPConfiguration.SettingId"
::= { ibmSystemHTTPConfigurationEntry 2 }

ibmSystemHTTPConfigurationPort OBJECT-TYPE
   SYNTAX         Uint16
   ACCESS         read-write
   STATUS         mandatory
   DESCRIPTION    ""
   REFERENCE      "IBMPSG_HTTPConfiguration.Port"
::= { ibmSystemHTTPConfigurationEntry 3 }

END
