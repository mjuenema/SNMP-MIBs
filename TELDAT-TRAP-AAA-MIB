-- file automatically created


TELDAT-TRAP-AAA-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


aaaTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the AAA event subsystem."
    REVISION "201401200930Z"
    DESCRIPTION "Initial implementation"
        ::= { telEventTraps 226 }


aaaEventsGroup	OBJECT IDENTIFIER	::= { aaaTrapsMIB 1 }

aaaNotifications	OBJECT IDENTIFIER	::= { aaaTrapsMIB 2 }
aaaNotificationsPrefix	OBJECT IDENTIFIER	::= { aaaNotifications 0 }

aaaEventObjects1 OBJECT-IDENTITY
    STATUS current
    DESCRIPTION
        "Event AAA.1
        Generic abnormal internal error message."
    ::= { aaaEventsGroup 1 }

aaa1_message OBJECT-TYPE
    SYNTAX DisplayString
    MAX-ACCESS accessible-for-notify
    STATUS current
    DESCRIPTION
        "Parameter 'message' in event AAA.1"
    ::= { aaaEventObjects1 1 }

aaaEventObjects2 OBJECT-IDENTITY
    STATUS current
    DESCRIPTION
        "Event AAA.2
        Generic usual internal error message."
    ::= { aaaEventsGroup 2 }

aaa2_message OBJECT-TYPE
    SYNTAX DisplayString
    MAX-ACCESS accessible-for-notify
    STATUS current
    DESCRIPTION
        "Parameter 'message' in event AAA.2"
    ::= { aaaEventObjects2 1 }

aaaEventObjects3 OBJECT-IDENTITY
    STATUS current
    DESCRIPTION
        "Event AAA.3
        Generic abnormal external error message."
    ::= { aaaEventsGroup 3 }

aaa3_message OBJECT-TYPE
    SYNTAX DisplayString
    MAX-ACCESS accessible-for-notify
    STATUS current
    DESCRIPTION
        "Parameter 'message' in event AAA.3"
    ::= { aaaEventObjects3 1 }

aaaEventObjects4 OBJECT-IDENTITY
    STATUS current
    DESCRIPTION
        "Event AAA.4
        Generic usual external error message."
    ::= { aaaEventsGroup 4 }

aaa4_message OBJECT-TYPE
    SYNTAX DisplayString
    MAX-ACCESS accessible-for-notify
    STATUS current
    DESCRIPTION
        "Parameter 'message' in event AAA.4"
    ::= { aaaEventObjects4 1 }

aaaEventObjects5 OBJECT-IDENTITY
    STATUS current
    DESCRIPTION
        "Event AAA.5
        Generic comment on abnormal information message."
    ::= { aaaEventsGroup 5 }

aaa5_message OBJECT-TYPE
    SYNTAX DisplayString
    MAX-ACCESS accessible-for-notify
    STATUS current
    DESCRIPTION
        "Parameter 'message' in event AAA.5"
    ::= { aaaEventObjects5 1 }

aaaEventObjects6 OBJECT-IDENTITY
    STATUS current
    DESCRIPTION
        "Event AAA.6
        Generic comment on usual information message."
    ::= { aaaEventsGroup 6 }

aaa6_message OBJECT-TYPE
    SYNTAX DisplayString
    MAX-ACCESS accessible-for-notify
    STATUS current
    DESCRIPTION
        "Parameter 'message' in event AAA.6"
    ::= { aaaEventObjects6 1 }

aaaEventObjects7 OBJECT-IDENTITY
    STATUS current
    DESCRIPTION
        "Event AAA.7
        Generic packet trace message."
    ::= { aaaEventsGroup 7 }

aaa7_message OBJECT-TYPE
    SYNTAX DisplayString
    MAX-ACCESS accessible-for-notify
    STATUS current
    DESCRIPTION
        "Parameter 'message' in event AAA.7"
    ::= { aaaEventObjects7 1 }

aaaEventObjects8 OBJECT-IDENTITY
    STATUS current
    DESCRIPTION
        "Event AAA.8
        Generic abnormal operation trace message."
    ::= { aaaEventsGroup 8 }

aaa8_message OBJECT-TYPE
    SYNTAX DisplayString
    MAX-ACCESS accessible-for-notify
    STATUS current
    DESCRIPTION
        "Parameter 'message' in event AAA.8"
    ::= { aaaEventObjects8 1 }

aaaEventObjects9 OBJECT-IDENTITY
    STATUS current
    DESCRIPTION
        "Event AAA.9
        Generic usual operation trace message."
    ::= { aaaEventsGroup 9 }

aaa9_message OBJECT-TYPE
    SYNTAX DisplayString
    MAX-ACCESS accessible-for-notify
    STATUS current
    DESCRIPTION
        "Parameter 'message' in event AAA.9"
    ::= { aaaEventObjects9 1 }

aaaEventObjects10 OBJECT-IDENTITY
    STATUS current
    DESCRIPTION
        "Event AAA.10
        The generic event level is wrong."
    ::= { aaaEventsGroup 10 }

aaa10_event_level OBJECT-TYPE
    SYNTAX Integer32
    MAX-ACCESS accessible-for-notify
    STATUS current
    DESCRIPTION
        "Parameter 'event_level' in event AAA.10"
    ::= { aaaEventObjects10 1 }

aaa10_message OBJECT-TYPE
    SYNTAX DisplayString
    MAX-ACCESS accessible-for-notify
    STATUS current
    DESCRIPTION
        "Parameter 'message' in event AAA.10"
    ::= { aaaEventObjects10 2 }

aaaEventObjects11 OBJECT-IDENTITY
    STATUS current
    DESCRIPTION
        "Event AAA.11
        AAA authentication has been initilized by the specified service"
    ::= { aaaEventsGroup 11 }

aaa11_module OBJECT-TYPE
    SYNTAX DisplayString
    MAX-ACCESS accessible-for-notify
    STATUS current
    DESCRIPTION
        "Parameter 'module' in event AAA.11"
    ::= { aaaEventObjects11 1 }

aaa11_service OBJECT-TYPE
    SYNTAX DisplayString
    MAX-ACCESS accessible-for-notify
    STATUS current
    DESCRIPTION
        "Parameter 'service' in event AAA.11"
    ::= { aaaEventObjects11 2 }

aaa11_privLvl OBJECT-TYPE
    SYNTAX DisplayString
    MAX-ACCESS accessible-for-notify
    STATUS current
    DESCRIPTION
        "Parameter 'privLvl' in event AAA.11"
    ::= { aaaEventObjects11 3 }

aaaEventObjects12 OBJECT-IDENTITY
    STATUS current
    DESCRIPTION
        "Event AAA.12
        We are looking for the method with number methodNumber."
    ::= { aaaEventsGroup 12 }

aaa12_methodNumber OBJECT-TYPE
    SYNTAX Integer32
    MAX-ACCESS accessible-for-notify
    STATUS current
    DESCRIPTION
        "Parameter 'methodNumber' in event AAA.12"
    ::= { aaaEventObjects12 1 }

aaa12_service OBJECT-TYPE
    SYNTAX DisplayString
    MAX-ACCESS accessible-for-notify
    STATUS current
    DESCRIPTION
        "Parameter 'service' in event AAA.12"
    ::= { aaaEventObjects12 2 }

aaa12_module OBJECT-TYPE
    SYNTAX DisplayString
    MAX-ACCESS accessible-for-notify
    STATUS current
    DESCRIPTION
        "Parameter 'module' in event AAA.12"
    ::= { aaaEventObjects12 3 }

aaa12_privLvl OBJECT-TYPE
    SYNTAX DisplayString
    MAX-ACCESS accessible-for-notify
    STATUS current
    DESCRIPTION
        "Parameter 'privLvl' in event AAA.12"
    ::= { aaaEventObjects12 4 }

aaaEventObjects13 OBJECT-IDENTITY
    STATUS current
    DESCRIPTION
        "Event AAA.13
        The specified service has not got associated methods list."
    ::= { aaaEventsGroup 13 }

aaa13_service OBJECT-TYPE
    SYNTAX DisplayString
    MAX-ACCESS accessible-for-notify
    STATUS current
    DESCRIPTION
        "Parameter 'service' in event AAA.13"
    ::= { aaaEventObjects13 1 }

aaa13_module OBJECT-TYPE
    SYNTAX DisplayString
    MAX-ACCESS accessible-for-notify
    STATUS current
    DESCRIPTION
        "Parameter 'module' in event AAA.13"
    ::= { aaaEventObjects13 2 }

aaa13_privLvl OBJECT-TYPE
    SYNTAX DisplayString
    MAX-ACCESS accessible-for-notify
    STATUS current
    DESCRIPTION
        "Parameter 'privLvl' in event AAA.13"
    ::= { aaaEventObjects13 3 }

aaa13_default OBJECT-TYPE
    SYNTAX DisplayString
    MAX-ACCESS accessible-for-notify
    STATUS current
    DESCRIPTION
        "Parameter 'default' in event AAA.13"
    ::= { aaaEventObjects13 4 }

aaaEventObjects14 OBJECT-IDENTITY
    STATUS current
    DESCRIPTION
        "Event AAA.14
        The specified service has got an associated methods list."
    ::= { aaaEventsGroup 14 }

aaa14_methodsList OBJECT-TYPE
    SYNTAX DisplayString
    MAX-ACCESS accessible-for-notify
    STATUS current
    DESCRIPTION
        "Parameter 'methodsList' in event AAA.14"
    ::= { aaaEventObjects14 1 }

aaa14_service OBJECT-TYPE
    SYNTAX DisplayString
    MAX-ACCESS accessible-for-notify
    STATUS current
    DESCRIPTION
        "Parameter 'service' in event AAA.14"
    ::= { aaaEventObjects14 2 }

aaa14_module OBJECT-TYPE
    SYNTAX DisplayString
    MAX-ACCESS accessible-for-notify
    STATUS current
    DESCRIPTION
        "Parameter 'module' in event AAA.14"
    ::= { aaaEventObjects14 3 }

aaa14_privLvl OBJECT-TYPE
    SYNTAX DisplayString
    MAX-ACCESS accessible-for-notify
    STATUS current
    DESCRIPTION
        "Parameter 'privLvl' in event AAA.14"
    ::= { aaaEventObjects14 4 }

aaaEventObjects15 OBJECT-IDENTITY
    STATUS current
    DESCRIPTION
        "Event AAA.15
        The specified Methods list doesn't exist."
    ::= { aaaEventsGroup 15 }

aaa15_methodsList OBJECT-TYPE
    SYNTAX DisplayString
    MAX-ACCESS accessible-for-notify
    STATUS current
    DESCRIPTION
        "Parameter 'methodsList' in event AAA.15"
    ::= { aaaEventObjects15 1 }

aaaEventObjects16 OBJECT-IDENTITY
    STATUS current
    DESCRIPTION
        "Event AAA.16
        The specified Methods list exists."
    ::= { aaaEventsGroup 16 }

aaa16_methodsList OBJECT-TYPE
    SYNTAX DisplayString
    MAX-ACCESS accessible-for-notify
    STATUS current
    DESCRIPTION
        "Parameter 'methodsList' in event AAA.16"
    ::= { aaaEventObjects16 1 }

aaaEventObjects17 OBJECT-IDENTITY
    STATUS current
    DESCRIPTION
        "Event AAA.17
        Found the specified servers group."
    ::= { aaaEventsGroup 17 }

aaa17_groupName OBJECT-TYPE
    SYNTAX DisplayString
    MAX-ACCESS accessible-for-notify
    STATUS current
    DESCRIPTION
        "Parameter 'groupName' in event AAA.17"
    ::= { aaaEventObjects17 1 }

aaa17_numberOfServers OBJECT-TYPE
    SYNTAX Integer32
    MAX-ACCESS accessible-for-notify
    STATUS current
    DESCRIPTION
        "Parameter 'numberOfServers' in event AAA.17"
    ::= { aaaEventObjects17 2 }

aaaEventObjects18 OBJECT-IDENTITY
    STATUS current
    DESCRIPTION
        "Event AAA.18
        The specified server ID doesn't exist."
    ::= { aaaEventsGroup 18 }

aaa18_serverID OBJECT-TYPE
    SYNTAX DisplayString
    MAX-ACCESS accessible-for-notify
    STATUS current
    DESCRIPTION
        "Parameter 'serverID' in event AAA.18"
    ::= { aaaEventObjects18 1 }

aaaEventObjects19 OBJECT-IDENTITY
    STATUS current
    DESCRIPTION
        "Event AAA.19
        Found a method."
    ::= { aaaEventsGroup 19 }

aaa19_methodType OBJECT-TYPE
    SYNTAX DisplayString
    MAX-ACCESS accessible-for-notify
    STATUS current
    DESCRIPTION
        "Parameter 'methodType' in event AAA.19"
    ::= { aaaEventObjects19 1 }

aaa19_methodsList OBJECT-TYPE
    SYNTAX DisplayString
    MAX-ACCESS accessible-for-notify
    STATUS current
    DESCRIPTION
        "Parameter 'methodsList' in event AAA.19"
    ::= { aaaEventObjects19 2 }

aaaEventObjects20 OBJECT-IDENTITY
    STATUS current
    DESCRIPTION
        "Event AAA.20
        Showing a method."
    ::= { aaaEventsGroup 20 }

aaa20_methodType OBJECT-TYPE
    SYNTAX DisplayString
    MAX-ACCESS accessible-for-notify
    STATUS current
    DESCRIPTION
        "Parameter 'methodType' in event AAA.20"
    ::= { aaaEventObjects20 1 }

aaa20_serverInfo OBJECT-TYPE
    SYNTAX DisplayString
    MAX-ACCESS accessible-for-notify
    STATUS current
    DESCRIPTION
        "Parameter 'serverInfo' in event AAA.20"
    ::= { aaaEventObjects20 2 }

aaaEventObjects21 OBJECT-IDENTITY
    STATUS current
    DESCRIPTION
        "Event AAA.21
        The required method not found for this service."
    ::= { aaaEventsGroup 21 }

aaa21_methodNumber OBJECT-TYPE
    SYNTAX Integer32
    MAX-ACCESS accessible-for-notify
    STATUS current
    DESCRIPTION
        "Parameter 'methodNumber' in event AAA.21"
    ::= { aaaEventObjects21 1 }

aaa21_service OBJECT-TYPE
    SYNTAX DisplayString
    MAX-ACCESS accessible-for-notify
    STATUS current
    DESCRIPTION
        "Parameter 'service' in event AAA.21"
    ::= { aaaEventObjects21 2 }

aaa21_module OBJECT-TYPE
    SYNTAX DisplayString
    MAX-ACCESS accessible-for-notify
    STATUS current
    DESCRIPTION
        "Parameter 'module' in event AAA.21"
    ::= { aaaEventObjects21 3 }

aaa21_privLvl OBJECT-TYPE
    SYNTAX DisplayString
    MAX-ACCESS accessible-for-notify
    STATUS current
    DESCRIPTION
        "Parameter 'privLvl' in event AAA.21"
    ::= { aaaEventObjects21 4 }

aaaEventObjects22 OBJECT-IDENTITY
    STATUS current
    DESCRIPTION
        "Event AAA.22
        The specified service is not configured to use the module."
    ::= { aaaEventsGroup 22 }

aaa22_service OBJECT-TYPE
    SYNTAX DisplayString
    MAX-ACCESS accessible-for-notify
    STATUS current
    DESCRIPTION
        "Parameter 'service' in event AAA.22"
    ::= { aaaEventObjects22 1 }

aaa22_module OBJECT-TYPE
    SYNTAX DisplayString
    MAX-ACCESS accessible-for-notify
    STATUS current
    DESCRIPTION
        "Parameter 'module' in event AAA.22"
    ::= { aaaEventObjects22 2 }

aaa22_privLvl OBJECT-TYPE
    SYNTAX DisplayString
    MAX-ACCESS accessible-for-notify
    STATUS current
    DESCRIPTION
        "Parameter 'privLvl' in event AAA.22"
    ::= { aaaEventObjects22 3 }

aaaEventObjects24 OBJECT-IDENTITY
    STATUS current
    DESCRIPTION
        "Event AAA.24
        A user logged in successfully via specified protocol (console, telnet,
        ssh, etc.)"
    ::= { aaaEventsGroup 24 }

aaa24_protocol OBJECT-TYPE
    SYNTAX DisplayString
    MAX-ACCESS accessible-for-notify
    STATUS current
    DESCRIPTION
        "Parameter 'protocol' in event AAA.24"
    ::= { aaaEventObjects24 1 }

aaa24_user_name OBJECT-TYPE
    SYNTAX DisplayString
    MAX-ACCESS accessible-for-notify
    STATUS current
    DESCRIPTION
        "Parameter 'user_name' in event AAA.24"
    ::= { aaaEventObjects24 2 }

aaa24_source_id OBJECT-TYPE
    SYNTAX DisplayString
    MAX-ACCESS accessible-for-notify
    STATUS current
    DESCRIPTION
        "Parameter 'source_id' in event AAA.24"
    ::= { aaaEventObjects24 3 }

aaaEventObjects25 OBJECT-IDENTITY
    STATUS current
    DESCRIPTION
        "Event AAA.25
        A user login attempt failed via specified protocol (console, telnet,
        ssh, etc.)"
    ::= { aaaEventsGroup 25 }

aaa25_protocol OBJECT-TYPE
    SYNTAX DisplayString
    MAX-ACCESS accessible-for-notify
    STATUS current
    DESCRIPTION
        "Parameter 'protocol' in event AAA.25"
    ::= { aaaEventObjects25 1 }

aaa25_user_name OBJECT-TYPE
    SYNTAX DisplayString
    MAX-ACCESS accessible-for-notify
    STATUS current
    DESCRIPTION
        "Parameter 'user_name' in event AAA.25"
    ::= { aaaEventObjects25 2 }

aaa25_source_id OBJECT-TYPE
    SYNTAX DisplayString
    MAX-ACCESS accessible-for-notify
    STATUS current
    DESCRIPTION
        "Parameter 'source_id' in event AAA.25"
    ::= { aaaEventObjects25 3 }

aaaEventObjects26 OBJECT-IDENTITY
    STATUS current
    DESCRIPTION
        "Event AAA.26
        The process for this module was successful"
    ::= { aaaEventsGroup 26 }

aaa26_service OBJECT-TYPE
    SYNTAX DisplayString
    MAX-ACCESS accessible-for-notify
    STATUS current
    DESCRIPTION
        "Parameter 'service' in event AAA.26"
    ::= { aaaEventObjects26 1 }

aaa26_module OBJECT-TYPE
    SYNTAX DisplayString
    MAX-ACCESS accessible-for-notify
    STATUS current
    DESCRIPTION
        "Parameter 'module' in event AAA.26"
    ::= { aaaEventObjects26 2 }

aaa26_privLvl OBJECT-TYPE
    SYNTAX DisplayString
    MAX-ACCESS accessible-for-notify
    STATUS current
    DESCRIPTION
        "Parameter 'privLvl' in event AAA.26"
    ::= { aaaEventObjects26 3 }

aaaEventObjects27 OBJECT-IDENTITY
    STATUS current
    DESCRIPTION
        "Event AAA.27
        The process for this module was unsuccessful"
    ::= { aaaEventsGroup 27 }

aaa27_service OBJECT-TYPE
    SYNTAX DisplayString
    MAX-ACCESS accessible-for-notify
    STATUS current
    DESCRIPTION
        "Parameter 'service' in event AAA.27"
    ::= { aaaEventObjects27 1 }

aaa27_module OBJECT-TYPE
    SYNTAX DisplayString
    MAX-ACCESS accessible-for-notify
    STATUS current
    DESCRIPTION
        "Parameter 'module' in event AAA.27"
    ::= { aaaEventObjects27 2 }

aaa27_privLvl OBJECT-TYPE
    SYNTAX DisplayString
    MAX-ACCESS accessible-for-notify
    STATUS current
    DESCRIPTION
        "Parameter 'privLvl' in event AAA.27"
    ::= { aaaEventObjects27 3 }

aaaEventObjects28 OBJECT-IDENTITY
    STATUS current
    DESCRIPTION
        "Event AAA.28
        Looking for a method in a methods list"
    ::= { aaaEventsGroup 28 }

aaa28_service1 OBJECT-TYPE
    SYNTAX DisplayString
    MAX-ACCESS accessible-for-notify
    STATUS current
    DESCRIPTION
        "Parameter 'service1' in event AAA.28"
    ::= { aaaEventObjects28 1 }

aaa28_module1 OBJECT-TYPE
    SYNTAX DisplayString
    MAX-ACCESS accessible-for-notify
    STATUS current
    DESCRIPTION
        "Parameter 'module1' in event AAA.28"
    ::= { aaaEventObjects28 2 }

aaa28_service2 OBJECT-TYPE
    SYNTAX DisplayString
    MAX-ACCESS accessible-for-notify
    STATUS current
    DESCRIPTION
        "Parameter 'service2' in event AAA.28"
    ::= { aaaEventObjects28 3 }

aaa28_module2 OBJECT-TYPE
    SYNTAX DisplayString
    MAX-ACCESS accessible-for-notify
    STATUS current
    DESCRIPTION
        "Parameter 'module2' in event AAA.28"
    ::= { aaaEventObjects28 4 }

aaaEventObjects29 OBJECT-IDENTITY
    STATUS current
    DESCRIPTION
        "Event AAA.29
        The method was found in the methods list"
    ::= { aaaEventsGroup 29 }

aaa29_service1 OBJECT-TYPE
    SYNTAX DisplayString
    MAX-ACCESS accessible-for-notify
    STATUS current
    DESCRIPTION
        "Parameter 'service1' in event AAA.29"
    ::= { aaaEventObjects29 1 }

aaa29_module1 OBJECT-TYPE
    SYNTAX DisplayString
    MAX-ACCESS accessible-for-notify
    STATUS current
    DESCRIPTION
        "Parameter 'module1' in event AAA.29"
    ::= { aaaEventObjects29 2 }

aaa29_service2 OBJECT-TYPE
    SYNTAX DisplayString
    MAX-ACCESS accessible-for-notify
    STATUS current
    DESCRIPTION
        "Parameter 'service2' in event AAA.29"
    ::= { aaaEventObjects29 3 }

aaa29_module2 OBJECT-TYPE
    SYNTAX DisplayString
    MAX-ACCESS accessible-for-notify
    STATUS current
    DESCRIPTION
        "Parameter 'module2' in event AAA.29"
    ::= { aaaEventObjects29 4 }

aaa29_position OBJECT-TYPE
    SYNTAX Integer32
    MAX-ACCESS accessible-for-notify
    STATUS current
    DESCRIPTION
        "Parameter 'position' in event AAA.29"
    ::= { aaaEventObjects29 5 }

aaaEventObjects30 OBJECT-IDENTITY
    STATUS current
    DESCRIPTION
        "Event AAA.30
        The method was not found in the methods list"
    ::= { aaaEventsGroup 30 }

aaa30_service1 OBJECT-TYPE
    SYNTAX DisplayString
    MAX-ACCESS accessible-for-notify
    STATUS current
    DESCRIPTION
        "Parameter 'service1' in event AAA.30"
    ::= { aaaEventObjects30 1 }

aaa30_module1 OBJECT-TYPE
    SYNTAX DisplayString
    MAX-ACCESS accessible-for-notify
    STATUS current
    DESCRIPTION
        "Parameter 'module1' in event AAA.30"
    ::= { aaaEventObjects30 2 }

aaa30_service2 OBJECT-TYPE
    SYNTAX DisplayString
    MAX-ACCESS accessible-for-notify
    STATUS current
    DESCRIPTION
        "Parameter 'service2' in event AAA.30"
    ::= { aaaEventObjects30 3 }

aaa30_module2 OBJECT-TYPE
    SYNTAX DisplayString
    MAX-ACCESS accessible-for-notify
    STATUS current
    DESCRIPTION
        "Parameter 'module2' in event AAA.30"
    ::= { aaaEventObjects30 4 }

aaaEventObjects31 OBJECT-IDENTITY
    STATUS current
    DESCRIPTION
        "Event AAA.31
        There isn't method used"
    ::= { aaaEventsGroup 31 }

aaa31_service1 OBJECT-TYPE
    SYNTAX DisplayString
    MAX-ACCESS accessible-for-notify
    STATUS current
    DESCRIPTION
        "Parameter 'service1' in event AAA.31"
    ::= { aaaEventObjects31 1 }

aaa31_module1 OBJECT-TYPE
    SYNTAX DisplayString
    MAX-ACCESS accessible-for-notify
    STATUS current
    DESCRIPTION
        "Parameter 'module1' in event AAA.31"
    ::= { aaaEventObjects31 2 }

aaa31_service2 OBJECT-TYPE
    SYNTAX DisplayString
    MAX-ACCESS accessible-for-notify
    STATUS current
    DESCRIPTION
        "Parameter 'service2' in event AAA.31"
    ::= { aaaEventObjects31 3 }

aaa31_module2 OBJECT-TYPE
    SYNTAX DisplayString
    MAX-ACCESS accessible-for-notify
    STATUS current
    DESCRIPTION
        "Parameter 'module2' in event AAA.31"
    ::= { aaaEventObjects31 4 }

aaaEventObjects32 OBJECT-IDENTITY
    STATUS current
    DESCRIPTION
        "Event AAA.32
        The attribute has been established"
    ::= { aaaEventsGroup 32 }

aaa32_attribute OBJECT-TYPE
    SYNTAX DisplayString
    MAX-ACCESS accessible-for-notify
    STATUS current
    DESCRIPTION
        "Parameter 'attribute' in event AAA.32"
    ::= { aaaEventObjects32 1 }

aaa32_service OBJECT-TYPE
    SYNTAX DisplayString
    MAX-ACCESS accessible-for-notify
    STATUS current
    DESCRIPTION
        "Parameter 'service' in event AAA.32"
    ::= { aaaEventObjects32 2 }

aaaEventObjects33 OBJECT-IDENTITY
    STATUS current
    DESCRIPTION
        "Event AAA.33
        The attribute couldn't be established"
    ::= { aaaEventsGroup 33 }

aaa33_attribute OBJECT-TYPE
    SYNTAX DisplayString
    MAX-ACCESS accessible-for-notify
    STATUS current
    DESCRIPTION
        "Parameter 'attribute' in event AAA.33"
    ::= { aaaEventObjects33 1 }

aaa33_service OBJECT-TYPE
    SYNTAX DisplayString
    MAX-ACCESS accessible-for-notify
    STATUS current
    DESCRIPTION
        "Parameter 'service' in event AAA.33"
    ::= { aaaEventObjects33 2 }

aaaEventObjects34 OBJECT-IDENTITY
    STATUS current
    DESCRIPTION
        "Event AAA.34
        The AVP value is wrong"
    ::= { aaaEventsGroup 34 }

aaa34_value OBJECT-TYPE
    SYNTAX DisplayString
    MAX-ACCESS accessible-for-notify
    STATUS current
    DESCRIPTION
        "Parameter 'value' in event AAA.34"
    ::= { aaaEventObjects34 1 }

aaa34_attribute OBJECT-TYPE
    SYNTAX DisplayString
    MAX-ACCESS accessible-for-notify
    STATUS current
    DESCRIPTION
        "Parameter 'attribute' in event AAA.34"
    ::= { aaaEventObjects34 2 }

aaaEventObjects35 OBJECT-IDENTITY
    STATUS current
    DESCRIPTION
        "Event AAA.35
        There's no local function defined for the service"
    ::= { aaaEventsGroup 35 }

aaa35_service OBJECT-TYPE
    SYNTAX DisplayString
    MAX-ACCESS accessible-for-notify
    STATUS current
    DESCRIPTION
        "Parameter 'service' in event AAA.35"
    ::= { aaaEventObjects35 1 }

aaa35_module OBJECT-TYPE
    SYNTAX DisplayString
    MAX-ACCESS accessible-for-notify
    STATUS current
    DESCRIPTION
        "Parameter 'module' in event AAA.35"
    ::= { aaaEventObjects35 2 }

aaaEventObjects36 OBJECT-IDENTITY
    STATUS current
    DESCRIPTION
        "Event AAA.36
        The specified server is not responding"
    ::= { aaaEventsGroup 36 }

aaa36_sever OBJECT-TYPE
    SYNTAX IpAddress
    MAX-ACCESS accessible-for-notify
    STATUS current
    DESCRIPTION
        "Parameter 'sever' in event AAA.36"
    ::= { aaaEventObjects36 1 }

aaa36_port OBJECT-TYPE
    SYNTAX Integer32
    MAX-ACCESS accessible-for-notify
    STATUS current
    DESCRIPTION
        "Parameter 'port' in event AAA.36"
    ::= { aaaEventObjects36 2 }

aaaEventObjects38 OBJECT-IDENTITY
    STATUS current
    DESCRIPTION
        "Event AAA.38
        Accounting request has been received from the accounting dispatcher queue"
    ::= { aaaEventsGroup 38 }

aaa38_request_type OBJECT-TYPE
    SYNTAX DisplayString
    MAX-ACCESS accessible-for-notify
    STATUS current
    DESCRIPTION
        "Parameter 'request_type' in event AAA.38"
    ::= { aaaEventObjects38 1 }

aaaEventObjects39 OBJECT-IDENTITY
    STATUS current
    DESCRIPTION
        "Event AAA.39
        Accounting dispatcher task not created. Request could not be sent"
    ::= { aaaEventsGroup 39 }

aaa39_state OBJECT-TYPE
    SYNTAX DisplayString
    MAX-ACCESS accessible-for-notify
    STATUS current
    DESCRIPTION
        "Parameter 'state' in event AAA.39"
    ::= { aaaEventObjects39 1 }

aaa39_type OBJECT-TYPE
    SYNTAX DisplayString
    MAX-ACCESS accessible-for-notify
    STATUS current
    DESCRIPTION
        "Parameter 'type' in event AAA.39"
    ::= { aaaEventObjects39 2 }

aaaEventObjects40 OBJECT-IDENTITY
    STATUS current
    DESCRIPTION
        "Event AAA.40
        Accounting request has been sent to the accounting dispatcher queue"
    ::= { aaaEventsGroup 40 }

aaa40_type OBJECT-TYPE
    SYNTAX DisplayString
    MAX-ACCESS accessible-for-notify
    STATUS current
    DESCRIPTION
        "Parameter 'type' in event AAA.40"
    ::= { aaaEventObjects40 1 }

aaaEventObjects41 OBJECT-IDENTITY
    STATUS current
    DESCRIPTION
        "Event AAA.41
        Accounting dispatcher task has been created"
    ::= { aaaEventsGroup 41 }

aaa41_ptr OBJECT-TYPE
    SYNTAX Integer32
    MAX-ACCESS accessible-for-notify
    STATUS current
    DESCRIPTION
        "Parameter 'ptr' in event AAA.41"
    ::= { aaaEventObjects41 1 }

aaaEventObjects42 OBJECT-IDENTITY
    STATUS current
    DESCRIPTION
        "Event AAA.42
        Current configuration has blocked the request"
    ::= { aaaEventsGroup 42 }

aaa42_service OBJECT-TYPE
    SYNTAX DisplayString
    MAX-ACCESS accessible-for-notify
    STATUS current
    DESCRIPTION
        "Parameter 'service' in event AAA.42"
    ::= { aaaEventObjects42 1 }

aaa42_module OBJECT-TYPE
    SYNTAX DisplayString
    MAX-ACCESS accessible-for-notify
    STATUS current
    DESCRIPTION
        "Parameter 'module' in event AAA.42"
    ::= { aaaEventObjects42 2 }

aaa42_action OBJECT-TYPE
    SYNTAX DisplayString
    MAX-ACCESS accessible-for-notify
    STATUS current
    DESCRIPTION
        "Parameter 'action' in event AAA.42"
    ::= { aaaEventObjects42 3 }

aaaEventObjects43 OBJECT-IDENTITY
    STATUS current
    DESCRIPTION
        "Event AAA.43
        The accounting request has been queued"
    ::= { aaaEventsGroup 43 }

aaa43_service OBJECT-TYPE
    SYNTAX DisplayString
    MAX-ACCESS accessible-for-notify
    STATUS current
    DESCRIPTION
        "Parameter 'service' in event AAA.43"
    ::= { aaaEventObjects43 1 }

aaa43_module OBJECT-TYPE
    SYNTAX DisplayString
    MAX-ACCESS accessible-for-notify
    STATUS current
    DESCRIPTION
        "Parameter 'module' in event AAA.43"
    ::= { aaaEventObjects43 2 }

aaa43_action OBJECT-TYPE
    SYNTAX DisplayString
    MAX-ACCESS accessible-for-notify
    STATUS current
    DESCRIPTION
        "Parameter 'action' in event AAA.43"
    ::= { aaaEventObjects43 3 }

aaa43_id OBJECT-TYPE
    SYNTAX Integer32
    MAX-ACCESS accessible-for-notify
    STATUS current
    DESCRIPTION
        "Parameter 'id' in event AAA.43"
    ::= { aaaEventObjects43 4 }

aaa43_userName OBJECT-TYPE
    SYNTAX DisplayString
    MAX-ACCESS accessible-for-notify
    STATUS current
    DESCRIPTION
        "Parameter 'userName' in event AAA.43"
    ::= { aaaEventObjects43 5 }

aaa43_port OBJECT-TYPE
    SYNTAX DisplayString
    MAX-ACCESS accessible-for-notify
    STATUS current
    DESCRIPTION
        "Parameter 'port' in event AAA.43"
    ::= { aaaEventObjects43 6 }

aaa43_remoteAddr OBJECT-TYPE
    SYNTAX DisplayString
    MAX-ACCESS accessible-for-notify
    STATUS current
    DESCRIPTION
        "Parameter 'remoteAddr' in event AAA.43"
    ::= { aaaEventObjects43 7 }

aaaEventObjects44 OBJECT-IDENTITY
    STATUS current
    DESCRIPTION
        "Event AAA.44
        The accounting request has been queued"
    ::= { aaaEventsGroup 44 }

aaa44_service OBJECT-TYPE
    SYNTAX DisplayString
    MAX-ACCESS accessible-for-notify
    STATUS current
    DESCRIPTION
        "Parameter 'service' in event AAA.44"
    ::= { aaaEventObjects44 1 }

aaa44_module OBJECT-TYPE
    SYNTAX DisplayString
    MAX-ACCESS accessible-for-notify
    STATUS current
    DESCRIPTION
        "Parameter 'module' in event AAA.44"
    ::= { aaaEventObjects44 2 }

aaa44_action OBJECT-TYPE
    SYNTAX DisplayString
    MAX-ACCESS accessible-for-notify
    STATUS current
    DESCRIPTION
        "Parameter 'action' in event AAA.44"
    ::= { aaaEventObjects44 3 }

aaa44_id OBJECT-TYPE
    SYNTAX Integer32
    MAX-ACCESS accessible-for-notify
    STATUS current
    DESCRIPTION
        "Parameter 'id' in event AAA.44"
    ::= { aaaEventObjects44 4 }

aaa44_avpNumber OBJECT-TYPE
    SYNTAX Integer32
    MAX-ACCESS accessible-for-notify
    STATUS current
    DESCRIPTION
        "Parameter 'avpNumber' in event AAA.44"
    ::= { aaaEventObjects44 5 }

aaa44_avpString OBJECT-TYPE
    SYNTAX DisplayString
    MAX-ACCESS accessible-for-notify
    STATUS current
    DESCRIPTION
        "Parameter 'avpString' in event AAA.44"
    ::= { aaaEventObjects44 6 }

aaaEventObjects45 OBJECT-IDENTITY
    STATUS current
    DESCRIPTION
        "Event AAA.45
        The accounting dispatcher is ready, it is waiting for requests"
    ::= { aaaEventsGroup 45 }

aaa45_ptr OBJECT-TYPE
    SYNTAX Integer32
    MAX-ACCESS accessible-for-notify
    STATUS current
    DESCRIPTION
        "Parameter 'ptr' in event AAA.45"
    ::= { aaaEventObjects45 1 }

aaaEventObjects46 OBJECT-IDENTITY
    STATUS current
    DESCRIPTION
        "Event AAA.46
        Accounting request could not be sent"
    ::= { aaaEventsGroup 46 }

aaa46_reason OBJECT-TYPE
    SYNTAX DisplayString
    MAX-ACCESS accessible-for-notify
    STATUS current
    DESCRIPTION
        "Parameter 'reason' in event AAA.46"
    ::= { aaaEventObjects46 1 }

aaaEventObjects48 OBJECT-IDENTITY
    STATUS current
    DESCRIPTION
        "Event AAA.48
        The path of the command will be used"
    ::= { aaaEventsGroup 48 }

aaa48_service OBJECT-TYPE
    SYNTAX DisplayString
    MAX-ACCESS accessible-for-notify
    STATUS current
    DESCRIPTION
        "Parameter 'service' in event AAA.48"
    ::= { aaaEventObjects48 1 }

aaa48_module OBJECT-TYPE
    SYNTAX DisplayString
    MAX-ACCESS accessible-for-notify
    STATUS current
    DESCRIPTION
        "Parameter 'module' in event AAA.48"
    ::= { aaaEventObjects48 2 }


aaaNotification1 NOTIFICATION-TYPE
    OBJECTS { 
              aaa1_message 
            }
    STATUS current
    DESCRIPTION
        "Notification of Event AAA.1

        Message: '$1'

        Parameters list:
              $1: aaa1_message

        Generic abnormal internal error message."
    ::= { aaaNotificationsPrefix 1 }

aaaNotification2 NOTIFICATION-TYPE
    OBJECTS { 
              aaa2_message 
            }
    STATUS current
    DESCRIPTION
        "Notification of Event AAA.2

        Message: '$1'

        Parameters list:
              $1: aaa2_message

        Generic usual internal error message."
    ::= { aaaNotificationsPrefix 2 }

aaaNotification3 NOTIFICATION-TYPE
    OBJECTS { 
              aaa3_message 
            }
    STATUS current
    DESCRIPTION
        "Notification of Event AAA.3

        Message: '$1'

        Parameters list:
              $1: aaa3_message

        Generic abnormal external error message."
    ::= { aaaNotificationsPrefix 3 }

aaaNotification4 NOTIFICATION-TYPE
    OBJECTS { 
              aaa4_message 
            }
    STATUS current
    DESCRIPTION
        "Notification of Event AAA.4

        Message: '$1'

        Parameters list:
              $1: aaa4_message

        Generic usual external error message."
    ::= { aaaNotificationsPrefix 4 }

aaaNotification5 NOTIFICATION-TYPE
    OBJECTS { 
              aaa5_message 
            }
    STATUS current
    DESCRIPTION
        "Notification of Event AAA.5

        Message: '$1'

        Parameters list:
              $1: aaa5_message

        Generic comment on abnormal information message."
    ::= { aaaNotificationsPrefix 5 }

aaaNotification6 NOTIFICATION-TYPE
    OBJECTS { 
              aaa6_message 
            }
    STATUS current
    DESCRIPTION
        "Notification of Event AAA.6

        Message: '$1'

        Parameters list:
              $1: aaa6_message

        Generic comment on usual information message."
    ::= { aaaNotificationsPrefix 6 }

aaaNotification7 NOTIFICATION-TYPE
    OBJECTS { 
              aaa7_message 
            }
    STATUS current
    DESCRIPTION
        "Notification of Event AAA.7

        Message: '$1'

        Parameters list:
              $1: aaa7_message

        Generic packet trace message."
    ::= { aaaNotificationsPrefix 7 }

aaaNotification8 NOTIFICATION-TYPE
    OBJECTS { 
              aaa8_message 
            }
    STATUS current
    DESCRIPTION
        "Notification of Event AAA.8

        Message: '$1'

        Parameters list:
              $1: aaa8_message

        Generic abnormal operation trace message."
    ::= { aaaNotificationsPrefix 8 }

aaaNotification9 NOTIFICATION-TYPE
    OBJECTS { 
              aaa9_message 
            }
    STATUS current
    DESCRIPTION
        "Notification of Event AAA.9

        Message: '$1'

        Parameters list:
              $1: aaa9_message

        Generic usual operation trace message."
    ::= { aaaNotificationsPrefix 9 }

aaaNotification10 NOTIFICATION-TYPE
    OBJECTS { 
              aaa10_event_level, 
              aaa10_message 
            }
    STATUS current
    DESCRIPTION
        "Notification of Event AAA.10

        Message: 'Bad generic event level ($1) ($2)'

        Parameters list:
              $1: aaa10_event_level
              $2: aaa10_message

        The generic event level is wrong."
    ::= { aaaNotificationsPrefix 10 }

aaaNotification11 NOTIFICATION-TYPE
    OBJECTS { 
              aaa11_module, 
              aaa11_service,
              aaa11_privLvl 
            }
    STATUS current
    DESCRIPTION
        "Notification of Event AAA.11

        Message: 'Module '$1' initialized from '$2', level $3'

        Parameters list:
              $1: aaa11_module
              $2: aaa11_service
              $3: aaa11_privLvl

        AAA authentication has been initilized by the specified service"
    ::= { aaaNotificationsPrefix 11 }

aaaNotification12 NOTIFICATION-TYPE
    OBJECTS { 
              aaa12_methodNumber, 
              aaa12_service,
              aaa12_module,
              aaa12_privLvl 
            }
    STATUS current
    DESCRIPTION
        "Notification of Event AAA.12

        Message: 'Looking for method $1 for '$2 $3' level $4'

        Parameters list:
              $1: aaa12_methodNumber
              $2: aaa12_service
              $3: aaa12_module
              $4: aaa12_privLvl

        We are looking for the method with number methodNumber."
    ::= { aaaNotificationsPrefix 12 }

aaaNotification13 NOTIFICATION-TYPE
    OBJECTS { 
              aaa13_service, 
              aaa13_module,
              aaa13_privLvl,
              aaa13_default 
            }
    STATUS current
    DESCRIPTION
        "Notification of Event AAA.13

        Message: 'No methods list associated with '$1 $2' level $3. Using '$4''

        Parameters list:
              $1: aaa13_service
              $2: aaa13_module
              $3: aaa13_privLvl
              $4: aaa13_default

        The specified service has not got associated methods list."
    ::= { aaaNotificationsPrefix 13 }

aaaNotification14 NOTIFICATION-TYPE
    OBJECTS { 
              aaa14_methodsList, 
              aaa14_service,
              aaa14_module,
              aaa14_privLvl 
            }
    STATUS current
    DESCRIPTION
        "Notification of Event AAA.14

        Message: 'Methods list '$1' associated with '$2 $3' level $4'

        Parameters list:
              $1: aaa14_methodsList
              $2: aaa14_service
              $3: aaa14_module
              $4: aaa14_privLvl

        The specified service has got an associated methods list."
    ::= { aaaNotificationsPrefix 14 }

aaaNotification15 NOTIFICATION-TYPE
    OBJECTS { 
              aaa15_methodsList 
            }
    STATUS current
    DESCRIPTION
        "Notification of Event AAA.15

        Message: 'Methods list '$1' doesn't exist'

        Parameters list:
              $1: aaa15_methodsList

        The specified Methods list doesn't exist."
    ::= { aaaNotificationsPrefix 15 }

aaaNotification16 NOTIFICATION-TYPE
    OBJECTS { 
              aaa16_methodsList 
            }
    STATUS current
    DESCRIPTION
        "Notification of Event AAA.16

        Message: 'Found methods list '$1''

        Parameters list:
              $1: aaa16_methodsList

        The specified Methods list exists."
    ::= { aaaNotificationsPrefix 16 }

aaaNotification17 NOTIFICATION-TYPE
    OBJECTS { 
              aaa17_groupName, 
              aaa17_numberOfServers 
            }
    STATUS current
    DESCRIPTION
        "Notification of Event AAA.17

        Message: 'Found servers group '$1' with $2 server[s]'

        Parameters list:
              $1: aaa17_groupName
              $2: aaa17_numberOfServers

        Found the specified servers group."
    ::= { aaaNotificationsPrefix 17 }

aaaNotification18 NOTIFICATION-TYPE
    OBJECTS { 
              aaa18_serverID 
            }
    STATUS current
    DESCRIPTION
        "Notification of Event AAA.18

        Message: 'Server ID '$1' doesn't exist'

        Parameters list:
              $1: aaa18_serverID

        The specified server ID doesn't exist."
    ::= { aaaNotificationsPrefix 18 }

aaaNotification19 NOTIFICATION-TYPE
    OBJECTS { 
              aaa19_methodType, 
              aaa19_methodsList 
            }
    STATUS current
    DESCRIPTION
        "Notification of Event AAA.19

        Message: 'Found '$1' method in methods list '$2''

        Parameters list:
              $1: aaa19_methodType
              $2: aaa19_methodsList

        Found a method."
    ::= { aaaNotificationsPrefix 19 }

aaaNotification20 NOTIFICATION-TYPE
    OBJECTS { 
              aaa20_methodType, 
              aaa20_serverInfo 
            }
    STATUS current
    DESCRIPTION
        "Notification of Event AAA.20

        Message: 'Using method '$1' ($2)'

        Parameters list:
              $1: aaa20_methodType
              $2: aaa20_serverInfo

        Showing a method."
    ::= { aaaNotificationsPrefix 20 }

aaaNotification21 NOTIFICATION-TYPE
    OBJECTS { 
              aaa21_methodNumber, 
              aaa21_service,
              aaa21_module,
              aaa21_privLvl 
            }
    STATUS current
    DESCRIPTION
        "Notification of Event AAA.21

        Message: 'No method $1 found for '$2 $3' level $4'

        Parameters list:
              $1: aaa21_methodNumber
              $2: aaa21_service
              $3: aaa21_module
              $4: aaa21_privLvl

        The required method not found for this service."
    ::= { aaaNotificationsPrefix 21 }

aaaNotification22 NOTIFICATION-TYPE
    OBJECTS { 
              aaa22_service, 
              aaa22_module,
              aaa22_privLvl 
            }
    STATUS current
    DESCRIPTION
        "Notification of Event AAA.22

        Message: ''$1' is not configured to use '$2' level $3'

        Parameters list:
              $1: aaa22_service
              $2: aaa22_module
              $3: aaa22_privLvl

        The specified service is not configured to use the module."
    ::= { aaaNotificationsPrefix 22 }

aaaNotification23 NOTIFICATION-TYPE
    STATUS current
    DESCRIPTION
        "Notification of Event AAA.23

        Message: 'No local access restriction'

        There is no local access restriction."
    ::= { aaaNotificationsPrefix 23 }

aaaNotification24 NOTIFICATION-TYPE
    OBJECTS { 
              aaa24_protocol, 
              aaa24_user_name,
              aaa24_source_id 
            }
    STATUS current
    DESCRIPTION
        "Notification of Event AAA.24

        Message: 'Login successful via $1 user $2 from source $3'

        Parameters list:
              $1: aaa24_protocol
              $2: aaa24_user_name
              $3: aaa24_source_id

        A user logged in successfully via specified protocol (console, telnet,
        ssh, etc.)"
    ::= { aaaNotificationsPrefix 24 }

aaaNotification25 NOTIFICATION-TYPE
    OBJECTS { 
              aaa25_protocol, 
              aaa25_user_name,
              aaa25_source_id 
            }
    STATUS current
    DESCRIPTION
        "Notification of Event AAA.25

        Message: 'Login failed via $1 user $2 from source $3'

        Parameters list:
              $1: aaa25_protocol
              $2: aaa25_user_name
              $3: aaa25_source_id

        A user login attempt failed via specified protocol (console, telnet,
        ssh, etc.)"
    ::= { aaaNotificationsPrefix 25 }

aaaNotification26 NOTIFICATION-TYPE
    OBJECTS { 
              aaa26_service, 
              aaa26_module,
              aaa26_privLvl 
            }
    STATUS current
    DESCRIPTION
        "Notification of Event AAA.26

        Message: ''$1 $2' level $3: successful'

        Parameters list:
              $1: aaa26_service
              $2: aaa26_module
              $3: aaa26_privLvl

        The process for this module was successful"
    ::= { aaaNotificationsPrefix 26 }

aaaNotification27 NOTIFICATION-TYPE
    OBJECTS { 
              aaa27_service, 
              aaa27_module,
              aaa27_privLvl 
            }
    STATUS current
    DESCRIPTION
        "Notification of Event AAA.27

        Message: ''$1 $2' level $3: unsuccessful'

        Parameters list:
              $1: aaa27_service
              $2: aaa27_module
              $3: aaa27_privLvl

        The process for this module was unsuccessful"
    ::= { aaaNotificationsPrefix 27 }

aaaNotification28 NOTIFICATION-TYPE
    OBJECTS { 
              aaa28_service1, 
              aaa28_module1,
              aaa28_service2,
              aaa28_module2 
            }
    STATUS current
    DESCRIPTION
        "Notification of Event AAA.28

        Message: 'Checking if the method used in '$1 $2' is valid for '$3 $4''

        Parameters list:
              $1: aaa28_service1
              $2: aaa28_module1
              $3: aaa28_service2
              $4: aaa28_module2

        Looking for a method in a methods list"
    ::= { aaaNotificationsPrefix 28 }

aaaNotification29 NOTIFICATION-TYPE
    OBJECTS { 
              aaa29_service1, 
              aaa29_module1,
              aaa29_service2,
              aaa29_module2,
              aaa29_position 
            }
    STATUS current
    DESCRIPTION
        "Notification of Event AAA.29

        Message: 'Method used in '$1 $2' is valid for '$3 $4' (position $5)'

        Parameters list:
              $1: aaa29_service1
              $2: aaa29_module1
              $3: aaa29_service2
              $4: aaa29_module2
              $5: aaa29_position

        The method was found in the methods list"
    ::= { aaaNotificationsPrefix 29 }

aaaNotification30 NOTIFICATION-TYPE
    OBJECTS { 
              aaa30_service1, 
              aaa30_module1,
              aaa30_service2,
              aaa30_module2 
            }
    STATUS current
    DESCRIPTION
        "Notification of Event AAA.30

        Message: 'Method used in '$1 $2' doesn't exist for '$3 $4''

        Parameters list:
              $1: aaa30_service1
              $2: aaa30_module1
              $3: aaa30_service2
              $4: aaa30_module2

        The method was not found in the methods list"
    ::= { aaaNotificationsPrefix 30 }

aaaNotification31 NOTIFICATION-TYPE
    OBJECTS { 
              aaa31_service1, 
              aaa31_module1,
              aaa31_service2,
              aaa31_module2 
            }
    STATUS current
    DESCRIPTION
        "Notification of Event AAA.31

        Message: 'Method used in '$1 $2' cannot be used for '$3 $4''

        Parameters list:
              $1: aaa31_service1
              $2: aaa31_module1
              $3: aaa31_service2
              $4: aaa31_module2

        There isn't method used"
    ::= { aaaNotificationsPrefix 31 }

aaaNotification32 NOTIFICATION-TYPE
    OBJECTS { 
              aaa32_attribute, 
              aaa32_service 
            }
    STATUS current
    DESCRIPTION
        "Notification of Event AAA.32

        Message: 'Attribute '$1' has been established for '$2''

        Parameters list:
              $1: aaa32_attribute
              $2: aaa32_service

        The attribute has been established"
    ::= { aaaNotificationsPrefix 32 }

aaaNotification33 NOTIFICATION-TYPE
    OBJECTS { 
              aaa33_attribute, 
              aaa33_service 
            }
    STATUS current
    DESCRIPTION
        "Notification of Event AAA.33

        Message: 'Attribute '$1' couldn't be established for '$2''

        Parameters list:
              $1: aaa33_attribute
              $2: aaa33_service

        The attribute couldn't be established"
    ::= { aaaNotificationsPrefix 33 }

aaaNotification34 NOTIFICATION-TYPE
    OBJECTS { 
              aaa34_value, 
              aaa34_attribute 
            }
    STATUS current
    DESCRIPTION
        "Notification of Event AAA.34

        Message: 'Invalid value '$1' for attribute '$2''

        Parameters list:
              $1: aaa34_value
              $2: aaa34_attribute

        The AVP value is wrong"
    ::= { aaaNotificationsPrefix 34 }

aaaNotification35 NOTIFICATION-TYPE
    OBJECTS { 
              aaa35_service, 
              aaa35_module 
            }
    STATUS current
    DESCRIPTION
        "Notification of Event AAA.35

        Message: 'No local function defined for '$1 $2''

        Parameters list:
              $1: aaa35_service
              $2: aaa35_module

        There's no local function defined for the service"
    ::= { aaaNotificationsPrefix 35 }

aaaNotification36 NOTIFICATION-TYPE
    OBJECTS { 
              aaa36_sever, 
              aaa36_port 
            }
    STATUS current
    DESCRIPTION
        "Notification of Event AAA.36

        Message: 'Server $1:$2 is not responding'

        Parameters list:
              $1: aaa36_sever
              $2: aaa36_port

        The specified server is not responding"
    ::= { aaaNotificationsPrefix 36 }

aaaNotification37 NOTIFICATION-TYPE
    STATUS current
    DESCRIPTION
        "Notification of Event AAA.37

        Message: 'No Radius authorization request needed, using authentication request'

        No Radius authorization request needed, using the authentication request"
    ::= { aaaNotificationsPrefix 37 }

aaaNotification38 NOTIFICATION-TYPE
    OBJECTS { 
              aaa38_request_type 
            }
    STATUS current
    DESCRIPTION
        "Notification of Event AAA.38

        Message: 'Received '$1' request from accounting dispatcher queue'

        Parameters list:
              $1: aaa38_request_type

        Accounting request has been received from the accounting dispatcher queue"
    ::= { aaaNotificationsPrefix 38 }

aaaNotification39 NOTIFICATION-TYPE
    OBJECTS { 
              aaa39_state, 
              aaa39_type 
            }
    STATUS current
    DESCRIPTION
        "Notification of Event AAA.39

        Message: 'Accounting dispatcher task state: '$1'. Request '$2' could not be sent'

        Parameters list:
              $1: aaa39_state
              $2: aaa39_type

        Accounting dispatcher task not created. Request could not be sent"
    ::= { aaaNotificationsPrefix 39 }

aaaNotification40 NOTIFICATION-TYPE
    OBJECTS { 
              aaa40_type 
            }
    STATUS current
    DESCRIPTION
        "Notification of Event AAA.40

        Message: 'Request '$1' sent to accounting dispatcher queue'

        Parameters list:
              $1: aaa40_type

        Accounting request has been sent to the accounting dispatcher queue"
    ::= { aaaNotificationsPrefix 40 }

aaaNotification41 NOTIFICATION-TYPE
    OBJECTS { 
              aaa41_ptr 
            }
    STATUS current
    DESCRIPTION
        "Notification of Event AAA.41

        Message: 'Accounting dispatcher task created (0x$1)'

        Parameters list:
              $1: aaa41_ptr

        Accounting dispatcher task has been created"
    ::= { aaaNotificationsPrefix 41 }

aaaNotification42 NOTIFICATION-TYPE
    OBJECTS { 
              aaa42_service, 
              aaa42_module,
              aaa42_action 
            }
    STATUS current
    DESCRIPTION
        "Notification of Event AAA.42

        Message: 'Current configuration has blocked '$1 $2 $3' request'

        Parameters list:
              $1: aaa42_service
              $2: aaa42_module
              $3: aaa42_action

        Current configuration has blocked the request"
    ::= { aaaNotificationsPrefix 42 }

aaaNotification43 NOTIFICATION-TYPE
    OBJECTS { 
              aaa43_service, 
              aaa43_module,
              aaa43_action,
              aaa43_id,
              aaa43_userName,
              aaa43_port,
              aaa43_remoteAddr 
            }
    STATUS current
    DESCRIPTION
        "Notification of Event AAA.43

        Message: 'Queuing '$1 $2 $3' request $4 (user '$5', port '$6', rem_addr '$7')'

        Parameters list:
              $1: aaa43_service
              $2: aaa43_module
              $3: aaa43_action
              $4: aaa43_id
              $5: aaa43_userName
              $6: aaa43_port
              $7: aaa43_remoteAddr

        The accounting request has been queued"
    ::= { aaaNotificationsPrefix 43 }

aaaNotification44 NOTIFICATION-TYPE
    OBJECTS { 
              aaa44_service, 
              aaa44_module,
              aaa44_action,
              aaa44_id,
              aaa44_avpNumber,
              aaa44_avpString 
            }
    STATUS current
    DESCRIPTION
        "Notification of Event AAA.44

        Message: 'Queuing '$1 $2 $3' request $4 (AVP[$5] '$6')'

        Parameters list:
              $1: aaa44_service
              $2: aaa44_module
              $3: aaa44_action
              $4: aaa44_id
              $5: aaa44_avpNumber
              $6: aaa44_avpString

        The accounting request has been queued"
    ::= { aaaNotificationsPrefix 44 }

aaaNotification45 NOTIFICATION-TYPE
    OBJECTS { 
              aaa45_ptr 
            }
    STATUS current
    DESCRIPTION
        "Notification of Event AAA.45

        Message: 'Accounting dispatcher ready, waiting for requests (0x$1)'

        Parameters list:
              $1: aaa45_ptr

        The accounting dispatcher is ready, it is waiting for requests"
    ::= { aaaNotificationsPrefix 45 }

aaaNotification46 NOTIFICATION-TYPE
    OBJECTS { 
              aaa46_reason 
            }
    STATUS current
    DESCRIPTION
        "Notification of Event AAA.46

        Message: 'Accounting request could not be sent: $1'

        Parameters list:
              $1: aaa46_reason

        Accounting request could not be sent"
    ::= { aaaNotificationsPrefix 46 }

aaaNotification47 NOTIFICATION-TYPE
    STATUS current
    DESCRIPTION
        "Notification of Event AAA.47

        Message: 'No local authorization restriction'

        There is no local authorization restriction."
    ::= { aaaNotificationsPrefix 47 }

aaaNotification48 NOTIFICATION-TYPE
    OBJECTS { 
              aaa48_service, 
              aaa48_module 
            }
    STATUS current
    DESCRIPTION
        "Notification of Event AAA.48

        Message: ''$1 $2' will use the path of the command'

        Parameters list:
              $1: aaa48_service
              $2: aaa48_module

        The path of the command will be used"
    ::= { aaaNotificationsPrefix 48 }


END
