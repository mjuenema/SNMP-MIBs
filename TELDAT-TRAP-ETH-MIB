-- file automatically created


TELDAT-TRAP-ETH-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ethTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ETH event subsystem."
    REVISION "201401200930Z"
    DESCRIPTION "Initial implementation"
        ::= { telEventTraps 81 }


ethEventsGroup	OBJECT IDENTIFIER	::= { ethTrapsMIB 1 }

ethNotifications	OBJECT IDENTIFIER	::= { ethTrapsMIB 2 }
ethNotificationsPrefix	OBJECT IDENTIFIER	::= { ethNotifications 0 }

ethEventObjects1 OBJECT-IDENTITY
    STATUS current
    DESCRIPTION
        "Event ETH.1
        A broadcast packet was received with an unknown or unsupported Ethernet
        type field."
    ::= { ethEventsGroup 1 }

eth1_packet_type OBJECT-TYPE
    SYNTAX Integer32
    MAX-ACCESS accessible-for-notify
    STATUS current
    DESCRIPTION
        "Parameter 'packet_type' in event ETH.1"
    ::= { ethEventObjects1 1 }

eth1_source_Ethernet_address OBJECT-TYPE
    SYNTAX DisplayString
    MAX-ACCESS accessible-for-notify
    STATUS current
    DESCRIPTION
        "Parameter 'source_Ethernet_address' in event ETH.1"
    ::= { ethEventObjects1 2 }

eth1_destination_Ethernet_address OBJECT-TYPE
    SYNTAX DisplayString
    MAX-ACCESS accessible-for-notify
    STATUS current
    DESCRIPTION
        "Parameter 'destination_Ethernet_address' in event ETH.1"
    ::= { ethEventObjects1 3 }

eth1_interface OBJECT-TYPE
    SYNTAX DisplayString
    MAX-ACCESS accessible-for-notify
    STATUS current
    DESCRIPTION
        "Parameter 'interface' in event ETH.1"
    ::= { ethEventObjects1 4 }

ethEventObjects2 OBJECT-IDENTITY
    STATUS current
    DESCRIPTION
        "Event ETH.2
        A non-broadcast packet was received with an unknown or unsupported
        Ethernet type field."
    ::= { ethEventsGroup 2 }

eth2_packet_type OBJECT-TYPE
    SYNTAX Integer32
    MAX-ACCESS accessible-for-notify
    STATUS current
    DESCRIPTION
        "Parameter 'packet_type' in event ETH.2"
    ::= { ethEventObjects2 1 }

eth2_source_Ethernet_address OBJECT-TYPE
    SYNTAX DisplayString
    MAX-ACCESS accessible-for-notify
    STATUS current
    DESCRIPTION
        "Parameter 'source_Ethernet_address' in event ETH.2"
    ::= { ethEventObjects2 2 }

eth2_destination_Ethernet_address OBJECT-TYPE
    SYNTAX DisplayString
    MAX-ACCESS accessible-for-notify
    STATUS current
    DESCRIPTION
        "Parameter 'destination_Ethernet_address' in event ETH.2"
    ::= { ethEventObjects2 3 }

eth2_interface OBJECT-TYPE
    SYNTAX DisplayString
    MAX-ACCESS accessible-for-notify
    STATUS current
    DESCRIPTION
        "Parameter 'interface' in event ETH.2"
    ::= { ethEventObjects2 4 }

ethEventObjects3 OBJECT-IDENTITY
    STATUS current
    DESCRIPTION
        "Event ETH.3
        A broadcast packet was received with a type field that indicated 802.3
        but was shorter than data length claimed in the 802.3 header."
    ::= { ethEventsGroup 3 }

eth3_actual_length OBJECT-TYPE
    SYNTAX Integer32
    MAX-ACCESS accessible-for-notify
    STATUS current
    DESCRIPTION
        "Parameter 'actual_length' in event ETH.3"
    ::= { ethEventObjects3 1 }

eth3_claimed_length OBJECT-TYPE
    SYNTAX Integer32
    MAX-ACCESS accessible-for-notify
    STATUS current
    DESCRIPTION
        "Parameter 'claimed_length' in event ETH.3"
    ::= { ethEventObjects3 2 }

eth3_source_Ethernet_address OBJECT-TYPE
    SYNTAX DisplayString
    MAX-ACCESS accessible-for-notify
    STATUS current
    DESCRIPTION
        "Parameter 'source_Ethernet_address' in event ETH.3"
    ::= { ethEventObjects3 3 }

eth3_destination_Ethernet_address OBJECT-TYPE
    SYNTAX DisplayString
    MAX-ACCESS accessible-for-notify
    STATUS current
    DESCRIPTION
        "Parameter 'destination_Ethernet_address' in event ETH.3"
    ::= { ethEventObjects3 4 }

eth3_interface OBJECT-TYPE
    SYNTAX DisplayString
    MAX-ACCESS accessible-for-notify
    STATUS current
    DESCRIPTION
        "Parameter 'interface' in event ETH.3"
    ::= { ethEventObjects3 5 }

ethEventObjects4 OBJECT-IDENTITY
    STATUS current
    DESCRIPTION
        "Event ETH.4
        A non-broadcast packet was received with a type field that indicated
        802.3 but was shorter than data length claimed in the 802.3 header."
    ::= { ethEventsGroup 4 }

eth4_actual_length OBJECT-TYPE
    SYNTAX Integer32
    MAX-ACCESS accessible-for-notify
    STATUS current
    DESCRIPTION
        "Parameter 'actual_length' in event ETH.4"
    ::= { ethEventObjects4 1 }

eth4_claimed_length OBJECT-TYPE
    SYNTAX Integer32
    MAX-ACCESS accessible-for-notify
    STATUS current
    DESCRIPTION
        "Parameter 'claimed_length' in event ETH.4"
    ::= { ethEventObjects4 2 }

eth4_source_Ethernet_address OBJECT-TYPE
    SYNTAX DisplayString
    MAX-ACCESS accessible-for-notify
    STATUS current
    DESCRIPTION
        "Parameter 'source_Ethernet_address' in event ETH.4"
    ::= { ethEventObjects4 3 }

eth4_destination_Ethernet_address OBJECT-TYPE
    SYNTAX DisplayString
    MAX-ACCESS accessible-for-notify
    STATUS current
    DESCRIPTION
        "Parameter 'destination_Ethernet_address' in event ETH.4"
    ::= { ethEventObjects4 4 }

eth4_interface OBJECT-TYPE
    SYNTAX DisplayString
    MAX-ACCESS accessible-for-notify
    STATUS current
    DESCRIPTION
        "Parameter 'interface' in event ETH.4"
    ::= { ethEventObjects4 5 }

ethEventObjects5 OBJECT-IDENTITY
    STATUS current
    DESCRIPTION
        "Event ETH.5
        A DECnet packet was received with a length field that was larger than
        the actual length of the packet."
    ::= { ethEventsGroup 5 }

eth5_actual_length OBJECT-TYPE
    SYNTAX Integer32
    MAX-ACCESS accessible-for-notify
    STATUS current
    DESCRIPTION
        "Parameter 'actual_length' in event ETH.5"
    ::= { ethEventObjects5 1 }

eth5_claimed_length OBJECT-TYPE
    SYNTAX Integer32
    MAX-ACCESS accessible-for-notify
    STATUS current
    DESCRIPTION
        "Parameter 'claimed_length' in event ETH.5"
    ::= { ethEventObjects5 2 }

eth5_source_Ethernet_address OBJECT-TYPE
    SYNTAX DisplayString
    MAX-ACCESS accessible-for-notify
    STATUS current
    DESCRIPTION
        "Parameter 'source_Ethernet_address' in event ETH.5"
    ::= { ethEventObjects5 3 }

eth5_destination_Ethernet_address OBJECT-TYPE
    SYNTAX DisplayString
    MAX-ACCESS accessible-for-notify
    STATUS current
    DESCRIPTION
        "Parameter 'destination_Ethernet_address' in event ETH.5"
    ::= { ethEventObjects5 4 }

eth5_interface OBJECT-TYPE
    SYNTAX DisplayString
    MAX-ACCESS accessible-for-notify
    STATUS current
    DESCRIPTION
        "Parameter 'interface' in event ETH.5"
    ::= { ethEventObjects5 5 }

ethEventObjects6 OBJECT-IDENTITY
    STATUS current
    DESCRIPTION
        "Event ETH.6
        An ethernet packet was received with protocol identifier not supported.
        It will be discarded."
    ::= { ethEventsGroup 6 }

eth6_protocol OBJECT-TYPE
    SYNTAX DisplayString
    MAX-ACCESS accessible-for-notify
    STATUS current
    DESCRIPTION
        "Parameter 'protocol' in event ETH.6"
    ::= { ethEventObjects6 1 }

eth6_source_Ethernet_address OBJECT-TYPE
    SYNTAX DisplayString
    MAX-ACCESS accessible-for-notify
    STATUS current
    DESCRIPTION
        "Parameter 'source_Ethernet_address' in event ETH.6"
    ::= { ethEventObjects6 2 }

eth6_destination_Ethernet_address OBJECT-TYPE
    SYNTAX Integer32
    MAX-ACCESS accessible-for-notify
    STATUS current
    DESCRIPTION
        "Parameter 'destination_Ethernet_address' in event ETH.6"
    ::= { ethEventObjects6 3 }

eth6_interface OBJECT-TYPE
    SYNTAX DisplayString
    MAX-ACCESS accessible-for-notify
    STATUS current
    DESCRIPTION
        "Parameter 'interface' in event ETH.6"
    ::= { ethEventObjects6 4 }

ethEventObjects7 OBJECT-IDENTITY
    STATUS current
    DESCRIPTION
        "Event ETH.7
        A SNAP 802.3 packet was received with protocol identifier not supported.
        It will be discarded."
    ::= { ethEventsGroup 7 }

eth7_protocol OBJECT-TYPE
    SYNTAX DisplayString
    MAX-ACCESS accessible-for-notify
    STATUS current
    DESCRIPTION
        "Parameter 'protocol' in event ETH.7"
    ::= { ethEventObjects7 1 }

eth7_source_Ethernet_address OBJECT-TYPE
    SYNTAX DisplayString
    MAX-ACCESS accessible-for-notify
    STATUS current
    DESCRIPTION
        "Parameter 'source_Ethernet_address' in event ETH.7"
    ::= { ethEventObjects7 2 }

eth7_destination_Ethernet_address OBJECT-TYPE
    SYNTAX Integer32
    MAX-ACCESS accessible-for-notify
    STATUS current
    DESCRIPTION
        "Parameter 'destination_Ethernet_address' in event ETH.7"
    ::= { ethEventObjects7 3 }

eth7_interface OBJECT-TYPE
    SYNTAX DisplayString
    MAX-ACCESS accessible-for-notify
    STATUS current
    DESCRIPTION
        "Parameter 'interface' in event ETH.7"
    ::= { ethEventObjects7 4 }

ethEventObjects8 OBJECT-IDENTITY
    STATUS current
    DESCRIPTION
        "Event ETH.8
        An ethernet multicast packet was received and it was discarded because
        it not match registered multicast addresses on interface."
    ::= { ethEventsGroup 8 }

eth8_source_Ethernet_address OBJECT-TYPE
    SYNTAX DisplayString
    MAX-ACCESS accessible-for-notify
    STATUS current
    DESCRIPTION
        "Parameter 'source_Ethernet_address' in event ETH.8"
    ::= { ethEventObjects8 1 }

eth8_destination_Ethernet_address OBJECT-TYPE
    SYNTAX DisplayString
    MAX-ACCESS accessible-for-notify
    STATUS current
    DESCRIPTION
        "Parameter 'destination_Ethernet_address' in event ETH.8"
    ::= { ethEventObjects8 2 }

eth8_interface OBJECT-TYPE
    SYNTAX DisplayString
    MAX-ACCESS accessible-for-notify
    STATUS current
    DESCRIPTION
        "Parameter 'interface' in event ETH.8"
    ::= { ethEventObjects8 3 }

ethEventObjects9 OBJECT-IDENTITY
    STATUS current
    DESCRIPTION
        "Event ETH.9
        An ethernet unicast packet was received and it was discarded because
        it not match local unicast addresses."
    ::= { ethEventsGroup 9 }

eth9_source_Ethernet_address OBJECT-TYPE
    SYNTAX DisplayString
    MAX-ACCESS accessible-for-notify
    STATUS current
    DESCRIPTION
        "Parameter 'source_Ethernet_address' in event ETH.9"
    ::= { ethEventObjects9 1 }

eth9_destination_Ethernet_address OBJECT-TYPE
    SYNTAX DisplayString
    MAX-ACCESS accessible-for-notify
    STATUS current
    DESCRIPTION
        "Parameter 'destination_Ethernet_address' in event ETH.9"
    ::= { ethEventObjects9 2 }

eth9_interface OBJECT-TYPE
    SYNTAX DisplayString
    MAX-ACCESS accessible-for-notify
    STATUS current
    DESCRIPTION
        "Parameter 'interface' in event ETH.9"
    ::= { ethEventObjects9 3 }

ethEventObjects10 OBJECT-IDENTITY
    STATUS current
    DESCRIPTION
        "Event ETH.10
        An 802.2 LLC packet was received from the network with an inactive
        (unrecognized) DSAP."
    ::= { ethEventsGroup 10 }

eth10_DSAP OBJECT-TYPE
    SYNTAX Integer32
    MAX-ACCESS accessible-for-notify
    STATUS current
    DESCRIPTION
        "Parameter 'DSAP' in event ETH.10"
    ::= { ethEventObjects10 1 }

eth10_source_Ethernet_address OBJECT-TYPE
    SYNTAX DisplayString
    MAX-ACCESS accessible-for-notify
    STATUS current
    DESCRIPTION
        "Parameter 'source_Ethernet_address' in event ETH.10"
    ::= { ethEventObjects10 2 }

eth10_destination_Ethernet_address OBJECT-TYPE
    SYNTAX DisplayString
    MAX-ACCESS accessible-for-notify
    STATUS current
    DESCRIPTION
        "Parameter 'destination_Ethernet_address' in event ETH.10"
    ::= { ethEventObjects10 3 }

eth10_interface OBJECT-TYPE
    SYNTAX DisplayString
    MAX-ACCESS accessible-for-notify
    STATUS current
    DESCRIPTION
        "Parameter 'interface' in event ETH.10"
    ::= { ethEventObjects10 4 }

ethEventObjects11 OBJECT-IDENTITY
    STATUS current
    DESCRIPTION
        "Event ETH.11
        A packet was received from the network that had an LLC but was not a
        Type 1 LLC."
    ::= { ethEventsGroup 11 }

eth11_LLC_control_type OBJECT-TYPE
    SYNTAX Integer32
    MAX-ACCESS accessible-for-notify
    STATUS current
    DESCRIPTION
        "Parameter 'LLC_control_type' in event ETH.11"
    ::= { ethEventObjects11 1 }

eth11_interface OBJECT-TYPE
    SYNTAX DisplayString
    MAX-ACCESS accessible-for-notify
    STATUS current
    DESCRIPTION
        "Parameter 'interface' in event ETH.11"
    ::= { ethEventObjects11 2 }

ethEventObjects12 OBJECT-IDENTITY
    STATUS current
    DESCRIPTION
        "Event ETH.12
        An LLC response was received from the network."
    ::= { ethEventsGroup 12 }

eth12_LLC_SSAP OBJECT-TYPE
    SYNTAX Integer32
    MAX-ACCESS accessible-for-notify
    STATUS current
    DESCRIPTION
        "Parameter 'LLC_SSAP' in event ETH.12"
    ::= { ethEventObjects12 1 }

eth12_interface OBJECT-TYPE
    SYNTAX DisplayString
    MAX-ACCESS accessible-for-notify
    STATUS current
    DESCRIPTION
        "Parameter 'interface' in event ETH.12"
    ::= { ethEventObjects12 2 }

ethEventObjects13 OBJECT-IDENTITY
    STATUS current
    DESCRIPTION
        "Event ETH.13
        An LLC XID packet was received from the network."
    ::= { ethEventsGroup 13 }

eth13_LLC_SSAP OBJECT-TYPE
    SYNTAX Integer32
    MAX-ACCESS accessible-for-notify
    STATUS current
    DESCRIPTION
        "Parameter 'LLC_SSAP' in event ETH.13"
    ::= { ethEventObjects13 1 }

eth13_interface OBJECT-TYPE
    SYNTAX DisplayString
    MAX-ACCESS accessible-for-notify
    STATUS current
    DESCRIPTION
        "Parameter 'interface' in event ETH.13"
    ::= { ethEventObjects13 2 }

ethEventObjects14 OBJECT-IDENTITY
    STATUS current
    DESCRIPTION
        "Event ETH.14
        An LLC TEST packet was received from the network."
    ::= { ethEventsGroup 14 }

eth14_LLC_SSAP OBJECT-TYPE
    SYNTAX Integer32
    MAX-ACCESS accessible-for-notify
    STATUS current
    DESCRIPTION
        "Parameter 'LLC_SSAP' in event ETH.14"
    ::= { ethEventObjects14 1 }

eth14_interface OBJECT-TYPE
    SYNTAX DisplayString
    MAX-ACCESS accessible-for-notify
    STATUS current
    DESCRIPTION
        "Parameter 'interface' in event ETH.14"
    ::= { ethEventObjects14 2 }

ethEventObjects15 OBJECT-IDENTITY
    STATUS current
    DESCRIPTION
        "Event ETH.15
        A packet was received from the network that had an illegal control
        field or UI."
    ::= { ethEventsGroup 15 }

eth15_LLC_control_field OBJECT-TYPE
    SYNTAX Integer32
    MAX-ACCESS accessible-for-notify
    STATUS current
    DESCRIPTION
        "Parameter 'LLC_control_field' in event ETH.15"
    ::= { ethEventObjects15 1 }

eth15_interface OBJECT-TYPE
    SYNTAX DisplayString
    MAX-ACCESS accessible-for-notify
    STATUS current
    DESCRIPTION
        "Parameter 'interface' in event ETH.15"
    ::= { ethEventObjects15 2 }

ethEventObjects17 OBJECT-IDENTITY
    STATUS current
    DESCRIPTION
        "Event ETH.17
        An Ethernet Loopback Protocol (Configuration Testing Protocol) packet
        was received."
    ::= { ethEventsGroup 17 }

eth17_source_Ethernet_address OBJECT-TYPE
    SYNTAX DisplayString
    MAX-ACCESS accessible-for-notify
    STATUS current
    DESCRIPTION
        "Parameter 'source_Ethernet_address' in event ETH.17"
    ::= { ethEventObjects17 1 }

eth17_destination_Ethernet_address OBJECT-TYPE
    SYNTAX DisplayString
    MAX-ACCESS accessible-for-notify
    STATUS current
    DESCRIPTION
        "Parameter 'destination_Ethernet_address' in event ETH.17"
    ::= { ethEventObjects17 2 }

eth17_interface OBJECT-TYPE
    SYNTAX DisplayString
    MAX-ACCESS accessible-for-notify
    STATUS current
    DESCRIPTION
        "Parameter 'interface' in event ETH.17"
    ::= { ethEventObjects17 3 }

ethEventObjects18 OBJECT-IDENTITY
    STATUS current
    DESCRIPTION
        "Event ETH.18
        An Ethernet Loopback Protocol (Configuration Testing Protocol) packet
        had an odd skip-Count in the packet. It will be discarded."
    ::= { ethEventsGroup 18 }

eth18_count OBJECT-TYPE
    SYNTAX Integer32
    MAX-ACCESS accessible-for-notify
    STATUS current
    DESCRIPTION
        "Parameter 'count' in event ETH.18"
    ::= { ethEventObjects18 1 }

eth18_source_Ethernet_address OBJECT-TYPE
    SYNTAX DisplayString
    MAX-ACCESS accessible-for-notify
    STATUS current
    DESCRIPTION
        "Parameter 'source_Ethernet_address' in event ETH.18"
    ::= { ethEventObjects18 2 }

eth18_destination_Ethernet_address OBJECT-TYPE
    SYNTAX DisplayString
    MAX-ACCESS accessible-for-notify
    STATUS current
    DESCRIPTION
        "Parameter 'destination_Ethernet_address' in event ETH.18"
    ::= { ethEventObjects18 3 }

eth18_interface OBJECT-TYPE
    SYNTAX DisplayString
    MAX-ACCESS accessible-for-notify
    STATUS current
    DESCRIPTION
        "Parameter 'interface' in event ETH.18"
    ::= { ethEventObjects18 4 }

ethEventObjects19 OBJECT-IDENTITY
    STATUS current
    DESCRIPTION
        "Event ETH.19
        An Ethernet Loopback Protocol (Configuration Testing Protocol) packet
        did not have a function code of forward(2). It will be discarded."
    ::= { ethEventsGroup 19 }

eth19_function OBJECT-TYPE
    SYNTAX Integer32
    MAX-ACCESS accessible-for-notify
    STATUS current
    DESCRIPTION
        "Parameter 'function' in event ETH.19"
    ::= { ethEventObjects19 1 }

eth19_source_Ethernet_address OBJECT-TYPE
    SYNTAX DisplayString
    MAX-ACCESS accessible-for-notify
    STATUS current
    DESCRIPTION
        "Parameter 'source_Ethernet_address' in event ETH.19"
    ::= { ethEventObjects19 2 }

eth19_destination_Ethernet_address OBJECT-TYPE
    SYNTAX DisplayString
    MAX-ACCESS accessible-for-notify
    STATUS current
    DESCRIPTION
        "Parameter 'destination_Ethernet_address' in event ETH.19"
    ::= { ethEventObjects19 3 }

eth19_interface OBJECT-TYPE
    SYNTAX DisplayString
    MAX-ACCESS accessible-for-notify
    STATUS current
    DESCRIPTION
        "Parameter 'interface' in event ETH.19"
    ::= { ethEventObjects19 4 }

ethEventObjects20 OBJECT-IDENTITY
    STATUS current
    DESCRIPTION
        "Event ETH.20
        An Ethernet Loopback Protocol (Configuration Testing Protocol) packet
        has a forward address that is a multicast. It will be discarded."
    ::= { ethEventsGroup 20 }

eth20_forward_Ethernet_address OBJECT-TYPE
    SYNTAX DisplayString
    MAX-ACCESS accessible-for-notify
    STATUS current
    DESCRIPTION
        "Parameter 'forward_Ethernet_address' in event ETH.20"
    ::= { ethEventObjects20 1 }

eth20_source_Ethernet_address OBJECT-TYPE
    SYNTAX DisplayString
    MAX-ACCESS accessible-for-notify
    STATUS current
    DESCRIPTION
        "Parameter 'source_Ethernet_address' in event ETH.20"
    ::= { ethEventObjects20 2 }

eth20_destination_Ethernet_address OBJECT-TYPE
    SYNTAX DisplayString
    MAX-ACCESS accessible-for-notify
    STATUS current
    DESCRIPTION
        "Parameter 'destination_Ethernet_address' in event ETH.20"
    ::= { ethEventObjects20 3 }

eth20_interface OBJECT-TYPE
    SYNTAX DisplayString
    MAX-ACCESS accessible-for-notify
    STATUS current
    DESCRIPTION
        "Parameter 'interface' in event ETH.20"
    ::= { ethEventObjects20 4 }

ethEventObjects21 OBJECT-IDENTITY
    STATUS current
    DESCRIPTION
        "Event ETH.21
        An Ethernet Loopback Protocol (Configuration Testing Protocol) packet
        is being forwarded to the specified next hop."
    ::= { ethEventsGroup 21 }

eth21_source_Ethernet_address OBJECT-TYPE
    SYNTAX DisplayString
    MAX-ACCESS accessible-for-notify
    STATUS current
    DESCRIPTION
        "Parameter 'source_Ethernet_address' in event ETH.21"
    ::= { ethEventObjects21 1 }

eth21_destination_Ethernet_address OBJECT-TYPE
    SYNTAX DisplayString
    MAX-ACCESS accessible-for-notify
    STATUS current
    DESCRIPTION
        "Parameter 'destination_Ethernet_address' in event ETH.21"
    ::= { ethEventObjects21 2 }

eth21_interface OBJECT-TYPE
    SYNTAX DisplayString
    MAX-ACCESS accessible-for-notify
    STATUS current
    DESCRIPTION
        "Parameter 'interface' in event ETH.21"
    ::= { ethEventObjects21 3 }

ethEventObjects22 OBJECT-IDENTITY
    STATUS current
    DESCRIPTION
        "Event ETH.22
        An Ethernet Loopback Protocol (Configuration Testing Protocol) packet
        could not be forwarded to the specified address, for reason specified
        by code."
    ::= { ethEventsGroup 22 }

eth22_forward_Ethernet_address OBJECT-TYPE
    SYNTAX DisplayString
    MAX-ACCESS accessible-for-notify
    STATUS current
    DESCRIPTION
        "Parameter 'forward_Ethernet_address' in event ETH.22"
    ::= { ethEventObjects22 1 }

eth22_code OBJECT-TYPE
    SYNTAX Integer32
    MAX-ACCESS accessible-for-notify
    STATUS current
    DESCRIPTION
        "Parameter 'code' in event ETH.22"
    ::= { ethEventObjects22 2 }

eth22_interface OBJECT-TYPE
    SYNTAX DisplayString
    MAX-ACCESS accessible-for-notify
    STATUS current
    DESCRIPTION
        "Parameter 'interface' in event ETH.22"
    ::= { ethEventObjects22 3 }

ethEventObjects23 OBJECT-IDENTITY
    STATUS current
    DESCRIPTION
        "Event ETH.23
        An LLC response (XID or TEST) could not be transmitted to the specified
        address, for the reason specified by code."
    ::= { ethEventsGroup 23 }

eth23_destination_Ethernet_address OBJECT-TYPE
    SYNTAX DisplayString
    MAX-ACCESS accessible-for-notify
    STATUS current
    DESCRIPTION
        "Parameter 'destination_Ethernet_address' in event ETH.23"
    ::= { ethEventObjects23 1 }

eth23_code OBJECT-TYPE
    SYNTAX Integer32
    MAX-ACCESS accessible-for-notify
    STATUS current
    DESCRIPTION
        "Parameter 'code' in event ETH.23"
    ::= { ethEventObjects23 2 }

eth23_interface OBJECT-TYPE
    SYNTAX DisplayString
    MAX-ACCESS accessible-for-notify
    STATUS current
    DESCRIPTION
        "Parameter 'interface' in event ETH.23"
    ::= { ethEventObjects23 3 }

ethEventObjects24 OBJECT-IDENTITY
    STATUS current
    DESCRIPTION
        "Event ETH.24
        A DECnet MOP packet was received with a length field that was larger
        than the actual length of the packet."
    ::= { ethEventsGroup 24 }

eth24_actual_length OBJECT-TYPE
    SYNTAX Integer32
    MAX-ACCESS accessible-for-notify
    STATUS current
    DESCRIPTION
        "Parameter 'actual_length' in event ETH.24"
    ::= { ethEventObjects24 1 }

eth24_claimed_length OBJECT-TYPE
    SYNTAX Integer32
    MAX-ACCESS accessible-for-notify
    STATUS current
    DESCRIPTION
        "Parameter 'claimed_length' in event ETH.24"
    ::= { ethEventObjects24 2 }

eth24_source_Ethernet_address OBJECT-TYPE
    SYNTAX DisplayString
    MAX-ACCESS accessible-for-notify
    STATUS current
    DESCRIPTION
        "Parameter 'source_Ethernet_address' in event ETH.24"
    ::= { ethEventObjects24 3 }

eth24_destination_Ethernet_address OBJECT-TYPE
    SYNTAX DisplayString
    MAX-ACCESS accessible-for-notify
    STATUS current
    DESCRIPTION
        "Parameter 'destination_Ethernet_address' in event ETH.24"
    ::= { ethEventObjects24 4 }

eth24_interface OBJECT-TYPE
    SYNTAX DisplayString
    MAX-ACCESS accessible-for-notify
    STATUS current
    DESCRIPTION
        "Parameter 'interface' in event ETH.24"
    ::= { ethEventObjects24 5 }

ethEventObjects25 OBJECT-IDENTITY
    STATUS current
    DESCRIPTION
        "Event ETH.25
        An Ethernet Loopback Protocol (Configuration Testing Protocol) packet
        had askipCount in the packet that points to beyond the end of the
        packet. It will be discarded."
    ::= { ethEventsGroup 25 }

eth25_count OBJECT-TYPE
    SYNTAX Integer32
    MAX-ACCESS accessible-for-notify
    STATUS current
    DESCRIPTION
        "Parameter 'count' in event ETH.25"
    ::= { ethEventObjects25 1 }

eth25_source_Ethernet_address OBJECT-TYPE
    SYNTAX DisplayString
    MAX-ACCESS accessible-for-notify
    STATUS current
    DESCRIPTION
        "Parameter 'source_Ethernet_address' in event ETH.25"
    ::= { ethEventObjects25 2 }

eth25_destination_Ethernet_address OBJECT-TYPE
    SYNTAX DisplayString
    MAX-ACCESS accessible-for-notify
    STATUS current
    DESCRIPTION
        "Parameter 'destination_Ethernet_address' in event ETH.25"
    ::= { ethEventObjects25 3 }

eth25_interface OBJECT-TYPE
    SYNTAX DisplayString
    MAX-ACCESS accessible-for-notify
    STATUS current
    DESCRIPTION
        "Parameter 'interface' in event ETH.25"
    ::= { ethEventObjects25 4 }

ethEventObjects26 OBJECT-IDENTITY
    STATUS current
    DESCRIPTION
        "Event ETH.26
        A vlan frame has been received whose virtual lan id is not supported.
        Frame is dropped."
    ::= { ethEventsGroup 26 }

eth26_vlan_id OBJECT-TYPE
    SYNTAX Integer32
    MAX-ACCESS accessible-for-notify
    STATUS current
    DESCRIPTION
        "Parameter 'vlan_id' in event ETH.26"
    ::= { ethEventObjects26 1 }

eth26_interface OBJECT-TYPE
    SYNTAX DisplayString
    MAX-ACCESS accessible-for-notify
    STATUS current
    DESCRIPTION
        "Parameter 'interface' in event ETH.26"
    ::= { ethEventObjects26 2 }

ethEventObjects27 OBJECT-IDENTITY
    STATUS current
    DESCRIPTION
        "Event ETH.27
        A QinQ packet was received on a ethernet interface"
    ::= { ethEventsGroup 27 }

eth27_etype_length OBJECT-TYPE
    SYNTAX Integer32
    MAX-ACCESS accessible-for-notify
    STATUS current
    DESCRIPTION
        "Parameter 'etype_length' in event ETH.27"
    ::= { ethEventObjects27 1 }

eth27_vid OBJECT-TYPE
    SYNTAX Integer32
    MAX-ACCESS accessible-for-notify
    STATUS current
    DESCRIPTION
        "Parameter 'vid' in event ETH.27"
    ::= { ethEventObjects27 2 }

eth27_source_Ethernet_address OBJECT-TYPE
    SYNTAX DisplayString
    MAX-ACCESS accessible-for-notify
    STATUS current
    DESCRIPTION
        "Parameter 'source_Ethernet_address' in event ETH.27"
    ::= { ethEventObjects27 3 }

eth27_destination_Ethernet_address OBJECT-TYPE
    SYNTAX DisplayString
    MAX-ACCESS accessible-for-notify
    STATUS current
    DESCRIPTION
        "Parameter 'destination_Ethernet_address' in event ETH.27"
    ::= { ethEventObjects27 4 }

eth27_interface OBJECT-TYPE
    SYNTAX DisplayString
    MAX-ACCESS accessible-for-notify
    STATUS current
    DESCRIPTION
        "Parameter 'interface' in event ETH.27"
    ::= { ethEventObjects27 5 }

ethEventObjects41 OBJECT-IDENTITY
    STATUS current
    DESCRIPTION
        "Event ETH.41
        The selftest for the Ethernet Am79C960 card has reported an error during
        selftest. The phases are 'Inicialization' and 'Operational Test'."
    ::= { ethEventsGroup 41 }

eth41_selftest_phase OBJECT-TYPE
    SYNTAX DisplayString
    MAX-ACCESS accessible-for-notify
    STATUS current
    DESCRIPTION
        "Parameter 'selftest_phase' in event ETH.41"
    ::= { ethEventObjects41 1 }

eth41_error_condition OBJECT-TYPE
    SYNTAX DisplayString
    MAX-ACCESS accessible-for-notify
    STATUS current
    DESCRIPTION
        "Parameter 'error_condition' in event ETH.41"
    ::= { ethEventObjects41 2 }

eth41_interface OBJECT-TYPE
    SYNTAX DisplayString
    MAX-ACCESS accessible-for-notify
    STATUS current
    DESCRIPTION
        "Parameter 'interface' in event ETH.41"
    ::= { ethEventObjects41 3 }

ethEventObjects43 OBJECT-IDENTITY
    STATUS current
    DESCRIPTION
        "Event ETH.43
        The 82596 chip on the interface card has failed to clear the command
        field for this interface. The interface will be re-initialized."
    ::= { ethEventsGroup 43 }

eth43_interface OBJECT-TYPE
    SYNTAX DisplayString
    MAX-ACCESS accessible-for-notify
    STATUS current
    DESCRIPTION
        "Parameter 'interface' in event ETH.43"
    ::= { ethEventObjects43 1 }

ethEventObjects44 OBJECT-IDENTITY
    STATUS current
    DESCRIPTION
        "Event ETH.44
        An incorrect command field has been sent to the driver. The interface
        will be re-initialized."
    ::= { ethEventsGroup 44 }

eth44_command OBJECT-TYPE
    SYNTAX Integer32
    MAX-ACCESS accessible-for-notify
    STATUS current
    DESCRIPTION
        "Parameter 'command' in event ETH.44"
    ::= { ethEventObjects44 1 }

eth44_interface OBJECT-TYPE
    SYNTAX DisplayString
    MAX-ACCESS accessible-for-notify
    STATUS current
    DESCRIPTION
        "Parameter 'interface' in event ETH.44"
    ::= { ethEventObjects44 2 }

ethEventObjects45 OBJECT-IDENTITY
    STATUS current
    DESCRIPTION
        "Event ETH.45
        The selftest for the Ethernet card has reported an error during selftest.
        The phases are:
        'Reset board', 'Check reset done', 'Check reset delay',
        'Init SCB', 'Init SCB delay', 'Init SCB completion',
        'Read hardware address', 'Set bus throttle timers',
        'Internal loopback', 'Set hardware address', 'Enable receive',
        'Internal loopback (output)', 'Check internal loopback data',
        'External loopback', 'External loopback delay',
        'External loopback (output)', 'Check External loopback data',
        'Network loopback', 'Network loopback', Network loopback delay',
        'Network loopback (output)', 'Check network looback data',
        'Clear loopback' and 'Operational test'."
    ::= { ethEventsGroup 45 }

eth45_selftest_phase OBJECT-TYPE
    SYNTAX DisplayString
    MAX-ACCESS accessible-for-notify
    STATUS current
    DESCRIPTION
        "Parameter 'selftest_phase' in event ETH.45"
    ::= { ethEventObjects45 1 }

eth45_error_condition OBJECT-TYPE
    SYNTAX DisplayString
    MAX-ACCESS accessible-for-notify
    STATUS current
    DESCRIPTION
        "Parameter 'error_condition' in event ETH.45"
    ::= { ethEventObjects45 2 }

eth45_interface OBJECT-TYPE
    SYNTAX DisplayString
    MAX-ACCESS accessible-for-notify
    STATUS current
    DESCRIPTION
        "Parameter 'interface' in event ETH.45"
    ::= { ethEventObjects45 3 }

ethEventObjects46 OBJECT-IDENTITY
    STATUS current
    DESCRIPTION
        "Event ETH.46
        This message is generated when an IPX packet is received in a data-link
        encapsulation (frame) other than the one configured for IPX on this
        interface. The packet will be ignored. The received_encapsultaion are
        one of the 'ETHERNET_802.3','ETHERNET_II','ETHERNET_802.2', or
        'ETHERNET_SNAP'. ETHERNET_802.3 is also known as 'Novell', and
        ETHERNET_II is also known as 'Ethernet'."
    ::= { ethEventsGroup 46 }

eth46_received_encapsulation OBJECT-TYPE
    SYNTAX DisplayString
    MAX-ACCESS accessible-for-notify
    STATUS current
    DESCRIPTION
        "Parameter 'received_encapsulation' in event ETH.46"
    ::= { ethEventObjects46 1 }

eth46_configured_encapsulation OBJECT-TYPE
    SYNTAX DisplayString
    MAX-ACCESS accessible-for-notify
    STATUS current
    DESCRIPTION
        "Parameter 'configured_encapsulation' in event ETH.46"
    ::= { ethEventObjects46 2 }

eth46_interface OBJECT-TYPE
    SYNTAX DisplayString
    MAX-ACCESS accessible-for-notify
    STATUS current
    DESCRIPTION
        "Parameter 'interface' in event ETH.46"
    ::= { ethEventObjects46 3 }

ethEventObjects47 OBJECT-IDENTITY
    STATUS current
    DESCRIPTION
        "Event ETH.47
        The self-test for the SCC Ethernet port has reported an error during
        self-test. The phases are 'Reset port', 'Set media selection',
        'Set hardware address', 'Network loopback', 'Enable receive',
        'Network loopback (output)', 'Check network loopback data',
        'Clear loopback', 'Set multicast addresses' and 'Operational Test'."
    ::= { ethEventsGroup 47 }

eth47_selftest_phase OBJECT-TYPE
    SYNTAX DisplayString
    MAX-ACCESS accessible-for-notify
    STATUS current
    DESCRIPTION
        "Parameter 'selftest_phase' in event ETH.47"
    ::= { ethEventObjects47 1 }

eth47_error_condition OBJECT-TYPE
    SYNTAX DisplayString
    MAX-ACCESS accessible-for-notify
    STATUS current
    DESCRIPTION
        "Parameter 'error_condition' in event ETH.47"
    ::= { ethEventObjects47 2 }

eth47_interface OBJECT-TYPE
    SYNTAX DisplayString
    MAX-ACCESS accessible-for-notify
    STATUS current
    DESCRIPTION
        "Parameter 'interface' in event ETH.47"
    ::= { ethEventObjects47 3 }

ethEventObjects48 OBJECT-IDENTITY
    STATUS current
    DESCRIPTION
        "Event ETH.48
        A Ethernet frame was received. Current software does not support
        Ethernet interface. Frame will be discarded."
    ::= { ethEventsGroup 48 }

eth48_source_MAC_address OBJECT-TYPE
    SYNTAX DisplayString
    MAX-ACCESS accessible-for-notify
    STATUS current
    DESCRIPTION
        "Parameter 'source_MAC_address' in event ETH.48"
    ::= { ethEventObjects48 1 }

eth48_destination_MAC_address OBJECT-TYPE
    SYNTAX DisplayString
    MAX-ACCESS accessible-for-notify
    STATUS current
    DESCRIPTION
        "Parameter 'destination_MAC_address' in event ETH.48"
    ::= { ethEventObjects48 2 }

eth48_interface OBJECT-TYPE
    SYNTAX DisplayString
    MAX-ACCESS accessible-for-notify
    STATUS current
    DESCRIPTION
        "Parameter 'interface' in event ETH.48"
    ::= { ethEventObjects48 3 }

ethEventObjects49 OBJECT-IDENTITY
    STATUS current
    DESCRIPTION
        "Event ETH.49
        Error computing LAN interface MAC address due to wrong serial number."
    ::= { ethEventsGroup 49 }

eth49_interface OBJECT-TYPE
    SYNTAX DisplayString
    MAX-ACCESS accessible-for-notify
    STATUS current
    DESCRIPTION
        "Parameter 'interface' in event ETH.49"
    ::= { ethEventObjects49 1 }

ethEventObjects50 OBJECT-IDENTITY
    STATUS current
    DESCRIPTION
        "Event ETH.50
        Switch port up."
    ::= { ethEventsGroup 50 }

eth50_port OBJECT-TYPE
    SYNTAX Integer32
    MAX-ACCESS accessible-for-notify
    STATUS current
    DESCRIPTION
        "Parameter 'port' in event ETH.50"
    ::= { ethEventObjects50 1 }

eth50_speed OBJECT-TYPE
    SYNTAX Integer32
    MAX-ACCESS accessible-for-notify
    STATUS current
    DESCRIPTION
        "Parameter 'speed' in event ETH.50"
    ::= { ethEventObjects50 2 }

eth50_mode OBJECT-TYPE
    SYNTAX Integer32
    MAX-ACCESS accessible-for-notify
    STATUS current
    DESCRIPTION
        "Parameter 'mode' in event ETH.50"
    ::= { ethEventObjects50 3 }

eth50_ifcname OBJECT-TYPE
    SYNTAX DisplayString
    MAX-ACCESS accessible-for-notify
    STATUS current
    DESCRIPTION
        "Parameter 'ifcname' in event ETH.50"
    ::= { ethEventObjects50 4 }

ethEventObjects51 OBJECT-IDENTITY
    STATUS current
    DESCRIPTION
        "Event ETH.51
        Switch port down."
    ::= { ethEventsGroup 51 }

eth51_port OBJECT-TYPE
    SYNTAX Integer32
    MAX-ACCESS accessible-for-notify
    STATUS current
    DESCRIPTION
        "Parameter 'port' in event ETH.51"
    ::= { ethEventObjects51 1 }

eth51_ifcname OBJECT-TYPE
    SYNTAX DisplayString
    MAX-ACCESS accessible-for-notify
    STATUS current
    DESCRIPTION
        "Parameter 'ifcname' in event ETH.51"
    ::= { ethEventObjects51 2 }

ethEventObjects52 OBJECT-IDENTITY
    STATUS current
    DESCRIPTION
        "Event ETH.52
        POE port on."
    ::= { ethEventsGroup 52 }

eth52_port OBJECT-TYPE
    SYNTAX Integer32
    MAX-ACCESS accessible-for-notify
    STATUS current
    DESCRIPTION
        "Parameter 'port' in event ETH.52"
    ::= { ethEventObjects52 1 }

eth52_class_string OBJECT-TYPE
    SYNTAX DisplayString
    MAX-ACCESS accessible-for-notify
    STATUS current
    DESCRIPTION
        "Parameter 'class_string' in event ETH.52"
    ::= { ethEventObjects52 2 }

eth52_ifcname OBJECT-TYPE
    SYNTAX DisplayString
    MAX-ACCESS accessible-for-notify
    STATUS current
    DESCRIPTION
        "Parameter 'ifcname' in event ETH.52"
    ::= { ethEventObjects52 3 }

ethEventObjects53 OBJECT-IDENTITY
    STATUS current
    DESCRIPTION
        "Event ETH.53
        POE port off."
    ::= { ethEventsGroup 53 }

eth53_port OBJECT-TYPE
    SYNTAX Integer32
    MAX-ACCESS accessible-for-notify
    STATUS current
    DESCRIPTION
        "Parameter 'port' in event ETH.53"
    ::= { ethEventObjects53 1 }

eth53_ifcname OBJECT-TYPE
    SYNTAX DisplayString
    MAX-ACCESS accessible-for-notify
    STATUS current
    DESCRIPTION
        "Parameter 'ifcname' in event ETH.53"
    ::= { ethEventObjects53 2 }

ethEventObjects54 OBJECT-IDENTITY
    STATUS current
    DESCRIPTION
        "Event ETH.54
        POE port detection error."
    ::= { ethEventsGroup 54 }

eth54_port OBJECT-TYPE
    SYNTAX Integer32
    MAX-ACCESS accessible-for-notify
    STATUS current
    DESCRIPTION
        "Parameter 'port' in event ETH.54"
    ::= { ethEventObjects54 1 }

eth54_error_string OBJECT-TYPE
    SYNTAX DisplayString
    MAX-ACCESS accessible-for-notify
    STATUS current
    DESCRIPTION
        "Parameter 'error_string' in event ETH.54"
    ::= { ethEventObjects54 2 }

eth54_ifcname OBJECT-TYPE
    SYNTAX DisplayString
    MAX-ACCESS accessible-for-notify
    STATUS current
    DESCRIPTION
        "Parameter 'ifcname' in event ETH.54"
    ::= { ethEventObjects54 3 }


ethNotification1 NOTIFICATION-TYPE
    OBJECTS { 
              eth1_packet_type, 
              eth1_source_Ethernet_address,
              eth1_destination_Ethernet_address,
              eth1_interface 
            }
    STATUS current
    DESCRIPTION
        "Notification of Event ETH.1

        Message: 'broadcast packet received with unknown Ethernet type $1 from host $2 to $3 interface $4'

        Parameters list:
              $1: eth1_packet_type
              $2: eth1_source_Ethernet_address
              $3: eth1_destination_Ethernet_address
              $4: eth1_interface

        A broadcast packet was received with an unknown or unsupported Ethernet
        type field."
    ::= { ethNotificationsPrefix 1 }

ethNotification2 NOTIFICATION-TYPE
    OBJECTS { 
              eth2_packet_type, 
              eth2_source_Ethernet_address,
              eth2_destination_Ethernet_address,
              eth2_interface 
            }
    STATUS current
    DESCRIPTION
        "Notification of Event ETH.2

        Message: 'packet received with unknown Ethernet type field $1 from host $2 to $3 interface $4'

        Parameters list:
              $1: eth2_packet_type
              $2: eth2_source_Ethernet_address
              $3: eth2_destination_Ethernet_address
              $4: eth2_interface

        A non-broadcast packet was received with an unknown or unsupported
        Ethernet type field."
    ::= { ethNotificationsPrefix 2 }

ethNotification3 NOTIFICATION-TYPE
    OBJECTS { 
              eth3_actual_length, 
              eth3_claimed_length,
              eth3_source_Ethernet_address,
              eth3_destination_Ethernet_address,
              eth3_interface 
            }
    STATUS current
    DESCRIPTION
        "Notification of Event ETH.3

        Message: 'broadcast packet received with a bad 802.3 length field actual $1 claimed $2 from $3 to $4 interface $5'

        Parameters list:
              $1: eth3_actual_length
              $2: eth3_claimed_length
              $3: eth3_source_Ethernet_address
              $4: eth3_destination_Ethernet_address
              $5: eth3_interface

        A broadcast packet was received with a type field that indicated 802.3
        but was shorter than data length claimed in the 802.3 header."
    ::= { ethNotificationsPrefix 3 }

ethNotification4 NOTIFICATION-TYPE
    OBJECTS { 
              eth4_actual_length, 
              eth4_claimed_length,
              eth4_source_Ethernet_address,
              eth4_destination_Ethernet_address,
              eth4_interface 
            }
    STATUS current
    DESCRIPTION
        "Notification of Event ETH.4

        Message: 'packet received with a bad 802.3 length field actual $1 claimed $2 from $3 to $4 interface $5'

        Parameters list:
              $1: eth4_actual_length
              $2: eth4_claimed_length
              $3: eth4_source_Ethernet_address
              $4: eth4_destination_Ethernet_address
              $5: eth4_interface

        A non-broadcast packet was received with a type field that indicated
        802.3 but was shorter than data length claimed in the 802.3 header."
    ::= { ethNotificationsPrefix 4 }

ethNotification5 NOTIFICATION-TYPE
    OBJECTS { 
              eth5_actual_length, 
              eth5_claimed_length,
              eth5_source_Ethernet_address,
              eth5_destination_Ethernet_address,
              eth5_interface 
            }
    STATUS current
    DESCRIPTION
        "Notification of Event ETH.5

        Message: 'DECnet packet received with a bad length actual $1 claimed $2 from $3 to $4 interface $5'

        Parameters list:
              $1: eth5_actual_length
              $2: eth5_claimed_length
              $3: eth5_source_Ethernet_address
              $4: eth5_destination_Ethernet_address
              $5: eth5_interface

        A DECnet packet was received with a length field that was larger than
        the actual length of the packet."
    ::= { ethNotificationsPrefix 5 }

ethNotification6 NOTIFICATION-TYPE
    OBJECTS { 
              eth6_protocol, 
              eth6_source_Ethernet_address,
              eth6_destination_Ethernet_address,
              eth6_interface 
            }
    STATUS current
    DESCRIPTION
        "Notification of Event ETH.6

        Message: 'Ethernet packet received from $1 to $2 with protocol $3 not supported.Frame is discarded interface $4'

        Parameters list:
              $1: eth6_protocol
              $2: eth6_source_Ethernet_address
              $3: eth6_destination_Ethernet_address
              $4: eth6_interface

        An ethernet packet was received with protocol identifier not supported.
        It will be discarded."
    ::= { ethNotificationsPrefix 6 }

ethNotification7 NOTIFICATION-TYPE
    OBJECTS { 
              eth7_protocol, 
              eth7_source_Ethernet_address,
              eth7_destination_Ethernet_address,
              eth7_interface 
            }
    STATUS current
    DESCRIPTION
        "Notification of Event ETH.7

        Message: 'SNAP 802.3 packet received from $1 to $2 with protocol $3 not supported.Frame is discarded interface $4'

        Parameters list:
              $1: eth7_protocol
              $2: eth7_source_Ethernet_address
              $3: eth7_destination_Ethernet_address
              $4: eth7_interface

        A SNAP 802.3 packet was received with protocol identifier not supported.
        It will be discarded."
    ::= { ethNotificationsPrefix 7 }

ethNotification8 NOTIFICATION-TYPE
    OBJECTS { 
              eth8_source_Ethernet_address, 
              eth8_destination_Ethernet_address,
              eth8_interface 
            }
    STATUS current
    DESCRIPTION
        "Notification of Event ETH.8

        Message: 'Ethernet multicast packet received from $1 to $2 is filtered interface $3'

        Parameters list:
              $1: eth8_source_Ethernet_address
              $2: eth8_destination_Ethernet_address
              $3: eth8_interface

        An ethernet multicast packet was received and it was discarded because
        it not match registered multicast addresses on interface."
    ::= { ethNotificationsPrefix 8 }

ethNotification9 NOTIFICATION-TYPE
    OBJECTS { 
              eth9_source_Ethernet_address, 
              eth9_destination_Ethernet_address,
              eth9_interface 
            }
    STATUS current
    DESCRIPTION
        "Notification of Event ETH.9

        Message: 'Ethernet unicast packet received from $1 to $2 is filtered interface $3'

        Parameters list:
              $1: eth9_source_Ethernet_address
              $2: eth9_destination_Ethernet_address
              $3: eth9_interface

        An ethernet unicast packet was received and it was discarded because
        it not match local unicast addresses."
    ::= { ethNotificationsPrefix 9 }

ethNotification10 NOTIFICATION-TYPE
    OBJECTS { 
              eth10_DSAP, 
              eth10_source_Ethernet_address,
              eth10_destination_Ethernet_address,
              eth10_interface 
            }
    STATUS current
    DESCRIPTION
        "Notification of Event ETH.10

        Message: '802.2 LLC packet received with unknown DSAP $1 from host $2 to $3 interface $4'

        Parameters list:
              $1: eth10_DSAP
              $2: eth10_source_Ethernet_address
              $3: eth10_destination_Ethernet_address
              $4: eth10_interface

        An 802.2 LLC packet was received from the network with an inactive
        (unrecognized) DSAP."
    ::= { ethNotificationsPrefix 10 }

ethNotification11 NOTIFICATION-TYPE
    OBJECTS { 
              eth11_LLC_control_type, 
              eth11_interface 
            }
    STATUS current
    DESCRIPTION
        "Notification of Event ETH.11

        Message: '802.2 LLC packet received, not Type 1 $1 interface $2'

        Parameters list:
              $1: eth11_LLC_control_type
              $2: eth11_interface

        A packet was received from the network that had an LLC but was not a
        Type 1 LLC."
    ::= { ethNotificationsPrefix 11 }

ethNotification12 NOTIFICATION-TYPE
    OBJECTS { 
              eth12_LLC_SSAP, 
              eth12_interface 
            }
    STATUS current
    DESCRIPTION
        "Notification of Event ETH.12

        Message: 'LLC RESPONSE packet received $1 interface $2'

        Parameters list:
              $1: eth12_LLC_SSAP
              $2: eth12_interface

        An LLC response was received from the network."
    ::= { ethNotificationsPrefix 12 }

ethNotification13 NOTIFICATION-TYPE
    OBJECTS { 
              eth13_LLC_SSAP, 
              eth13_interface 
            }
    STATUS current
    DESCRIPTION
        "Notification of Event ETH.13

        Message: 'LLC XID packet received $1 interface $2'

        Parameters list:
              $1: eth13_LLC_SSAP
              $2: eth13_interface

        An LLC XID packet was received from the network."
    ::= { ethNotificationsPrefix 13 }

ethNotification14 NOTIFICATION-TYPE
    OBJECTS { 
              eth14_LLC_SSAP, 
              eth14_interface 
            }
    STATUS current
    DESCRIPTION
        "Notification of Event ETH.14

        Message: 'LLC TEST packet received $1 interface $2'

        Parameters list:
              $1: eth14_LLC_SSAP
              $2: eth14_interface

        An LLC TEST packet was received from the network."
    ::= { ethNotificationsPrefix 14 }

ethNotification15 NOTIFICATION-TYPE
    OBJECTS { 
              eth15_LLC_control_field, 
              eth15_interface 
            }
    STATUS current
    DESCRIPTION
        "Notification of Event ETH.15

        Message: 'packet received with unrecognized control field $1 interface $2'

        Parameters list:
              $1: eth15_LLC_control_field
              $2: eth15_interface

        A packet was received from the network that had an illegal control
        field or UI."
    ::= { ethNotificationsPrefix 15 }

ethNotification16 NOTIFICATION-TYPE
    STATUS current
    DESCRIPTION
        "Notification of Event ETH.16

        Message: '----'

        Reserved for possible future use."
    ::= { ethNotificationsPrefix 16 }

ethNotification17 NOTIFICATION-TYPE
    OBJECTS { 
              eth17_source_Ethernet_address, 
              eth17_destination_Ethernet_address,
              eth17_interface 
            }
    STATUS current
    DESCRIPTION
        "Notification of Event ETH.17

        Message: 'Loopback Protocol frame received from $1 to $2, interface $3'

        Parameters list:
              $1: eth17_source_Ethernet_address
              $2: eth17_destination_Ethernet_address
              $3: eth17_interface

        An Ethernet Loopback Protocol (Configuration Testing Protocol) packet
        was received."
    ::= { ethNotificationsPrefix 17 }

ethNotification18 NOTIFICATION-TYPE
    OBJECTS { 
              eth18_count, 
              eth18_source_Ethernet_address,
              eth18_destination_Ethernet_address,
              eth18_interface 
            }
    STATUS current
    DESCRIPTION
        "Notification of Event ETH.18

        Message: 'Loopback Protocol, odd skipCount $1 from $2 to $3, interface $4'

        Parameters list:
              $1: eth18_count
              $2: eth18_source_Ethernet_address
              $3: eth18_destination_Ethernet_address
              $4: eth18_interface

        An Ethernet Loopback Protocol (Configuration Testing Protocol) packet
        had an odd skip-Count in the packet. It will be discarded."
    ::= { ethNotificationsPrefix 18 }

ethNotification19 NOTIFICATION-TYPE
    OBJECTS { 
              eth19_function, 
              eth19_source_Ethernet_address,
              eth19_destination_Ethernet_address,
              eth19_interface 
            }
    STATUS current
    DESCRIPTION
        "Notification of Event ETH.19

        Message: 'Loopback Protocol, function $1 not Forward Data from $2 to $3, interface $4'

        Parameters list:
              $1: eth19_function
              $2: eth19_source_Ethernet_address
              $3: eth19_destination_Ethernet_address
              $4: eth19_interface

        An Ethernet Loopback Protocol (Configuration Testing Protocol) packet
        did not have a function code of forward(2). It will be discarded."
    ::= { ethNotificationsPrefix 19 }

ethNotification20 NOTIFICATION-TYPE
    OBJECTS { 
              eth20_forward_Ethernet_address, 
              eth20_source_Ethernet_address,
              eth20_destination_Ethernet_address,
              eth20_interface 
            }
    STATUS current
    DESCRIPTION
        "Notification of Event ETH.20

        Message: 'Loopback Protocol, multicast forward address $1 from $2 to $3, interface $4'

        Parameters list:
              $1: eth20_forward_Ethernet_address
              $2: eth20_source_Ethernet_address
              $3: eth20_destination_Ethernet_address
              $4: eth20_interface

        An Ethernet Loopback Protocol (Configuration Testing Protocol) packet
        has a forward address that is a multicast. It will be discarded."
    ::= { ethNotificationsPrefix 20 }

ethNotification21 NOTIFICATION-TYPE
    OBJECTS { 
              eth21_source_Ethernet_address, 
              eth21_destination_Ethernet_address,
              eth21_interface 
            }
    STATUS current
    DESCRIPTION
        "Notification of Event ETH.21

        Message: 'Loopback Protocol, forwarding from $1 to $2, interface $3'

        Parameters list:
              $1: eth21_source_Ethernet_address
              $2: eth21_destination_Ethernet_address
              $3: eth21_interface

        An Ethernet Loopback Protocol (Configuration Testing Protocol) packet
        is being forwarded to the specified next hop."
    ::= { ethNotificationsPrefix 21 }

ethNotification22 NOTIFICATION-TYPE
    OBJECTS { 
              eth22_forward_Ethernet_address, 
              eth22_code,
              eth22_interface 
            }
    STATUS current
    DESCRIPTION
        "Notification of Event ETH.22

        Message: 'Loopback Protocol, forward to $1 discarded, for reason $2, interface $3'

        Parameters list:
              $1: eth22_forward_Ethernet_address
              $2: eth22_code
              $3: eth22_interface

        An Ethernet Loopback Protocol (Configuration Testing Protocol) packet
        could not be forwarded to the specified address, for reason specified
        by code."
    ::= { ethNotificationsPrefix 22 }

ethNotification23 NOTIFICATION-TYPE
    OBJECTS { 
              eth23_destination_Ethernet_address, 
              eth23_code,
              eth23_interface 
            }
    STATUS current
    DESCRIPTION
        "Notification of Event ETH.23

        Message: 'LLC response to $1 discarded, for reason $2, interface $3'

        Parameters list:
              $1: eth23_destination_Ethernet_address
              $2: eth23_code
              $3: eth23_interface

        An LLC response (XID or TEST) could not be transmitted to the specified
        address, for the reason specified by code."
    ::= { ethNotificationsPrefix 23 }

ethNotification24 NOTIFICATION-TYPE
    OBJECTS { 
              eth24_actual_length, 
              eth24_claimed_length,
              eth24_source_Ethernet_address,
              eth24_destination_Ethernet_address,
              eth24_interface 
            }
    STATUS current
    DESCRIPTION
        "Notification of Event ETH.24

        Message: 'DECnet MOP packet received with a bad length actual $1 claimed $2 from $3 to $4 interface $5'

        Parameters list:
              $1: eth24_actual_length
              $2: eth24_claimed_length
              $3: eth24_source_Ethernet_address
              $4: eth24_destination_Ethernet_address
              $5: eth24_interface

        A DECnet MOP packet was received with a length field that was larger
        than the actual length of the packet."
    ::= { ethNotificationsPrefix 24 }

ethNotification25 NOTIFICATION-TYPE
    OBJECTS { 
              eth25_count, 
              eth25_source_Ethernet_address,
              eth25_destination_Ethernet_address,
              eth25_interface 
            }
    STATUS current
    DESCRIPTION
        "Notification of Event ETH.25

        Message: 'Loopback Protocol, bad skipCount $1 from $2 to $3, interface $4'

        Parameters list:
              $1: eth25_count
              $2: eth25_source_Ethernet_address
              $3: eth25_destination_Ethernet_address
              $4: eth25_interface

        An Ethernet Loopback Protocol (Configuration Testing Protocol) packet
        had askipCount in the packet that points to beyond the end of the
        packet. It will be discarded."
    ::= { ethNotificationsPrefix 25 }

ethNotification26 NOTIFICATION-TYPE
    OBJECTS { 
              eth26_vlan_id, 
              eth26_interface 
            }
    STATUS current
    DESCRIPTION
        "Notification of Event ETH.26

        Message: 'VLAN vid $1 not supported. Frame discarded, interface $2'

        Parameters list:
              $1: eth26_vlan_id
              $2: eth26_interface

        A vlan frame has been received whose virtual lan id is not supported.
        Frame is dropped."
    ::= { ethNotificationsPrefix 26 }

ethNotification27 NOTIFICATION-TYPE
    OBJECTS { 
              eth27_etype_length, 
              eth27_vid,
              eth27_source_Ethernet_address,
              eth27_destination_Ethernet_address,
              eth27_interface 
            }
    STATUS current
    DESCRIPTION
        "Notification of Event ETH.27

        Message: 'QinQ packet received etype/length field $1 vid $2 from $3 to $4 interface $5'

        Parameters list:
              $1: eth27_etype_length
              $2: eth27_vid
              $3: eth27_source_Ethernet_address
              $4: eth27_destination_Ethernet_address
              $5: eth27_interface

        A QinQ packet was received on a ethernet interface"
    ::= { ethNotificationsPrefix 27 }

ethNotification28 NOTIFICATION-TYPE
    STATUS current
    DESCRIPTION
        "Notification of Event ETH.28

        Message: '----'

        Reserved for possible future use."
    ::= { ethNotificationsPrefix 28 }

ethNotification29 NOTIFICATION-TYPE
    STATUS current
    DESCRIPTION
        "Notification of Event ETH.29

        Message: '----'

        Reserved for possible future use."
    ::= { ethNotificationsPrefix 29 }

ethNotification30 NOTIFICATION-TYPE
    STATUS current
    DESCRIPTION
        "Notification of Event ETH.30

        Message: '----'

        Reserved for possible future use."
    ::= { ethNotificationsPrefix 30 }

ethNotification31 NOTIFICATION-TYPE
    STATUS current
    DESCRIPTION
        "Notification of Event ETH.31

        Message: '----'

        Reserved for possible future use."
    ::= { ethNotificationsPrefix 31 }

ethNotification32 NOTIFICATION-TYPE
    STATUS current
    DESCRIPTION
        "Notification of Event ETH.32

        Message: '----'

        Reserved for possible future use."
    ::= { ethNotificationsPrefix 32 }

ethNotification33 NOTIFICATION-TYPE
    STATUS current
    DESCRIPTION
        "Notification of Event ETH.33

        Message: '----'

        Reserved for possible future use."
    ::= { ethNotificationsPrefix 33 }

ethNotification34 NOTIFICATION-TYPE
    STATUS current
    DESCRIPTION
        "Notification of Event ETH.34

        Message: '----'

        Reserved for possible future use."
    ::= { ethNotificationsPrefix 34 }

ethNotification35 NOTIFICATION-TYPE
    STATUS current
    DESCRIPTION
        "Notification of Event ETH.35

        Message: '----'

        Reserved for possible future use."
    ::= { ethNotificationsPrefix 35 }

ethNotification36 NOTIFICATION-TYPE
    STATUS current
    DESCRIPTION
        "Notification of Event ETH.36

        Message: '----'

        Reserved for possible future use."
    ::= { ethNotificationsPrefix 36 }

ethNotification37 NOTIFICATION-TYPE
    STATUS current
    DESCRIPTION
        "Notification of Event ETH.37

        Message: '----'

        Reserved for possible future use."
    ::= { ethNotificationsPrefix 37 }

ethNotification38 NOTIFICATION-TYPE
    STATUS current
    DESCRIPTION
        "Notification of Event ETH.38

        Message: '----'

        Reserved for possible future use."
    ::= { ethNotificationsPrefix 38 }

ethNotification39 NOTIFICATION-TYPE
    STATUS current
    DESCRIPTION
        "Notification of Event ETH.39

        Message: '----'

        Reserved for possible future use."
    ::= { ethNotificationsPrefix 39 }

ethNotification40 NOTIFICATION-TYPE
    STATUS current
    DESCRIPTION
        "Notification of Event ETH.40

        Message: '----'

        Reserved for possible future use."
    ::= { ethNotificationsPrefix 40 }

ethNotification41 NOTIFICATION-TYPE
    OBJECTS { 
              eth41_selftest_phase, 
              eth41_error_condition,
              eth41_interface 
            }
    STATUS current
    DESCRIPTION
        "Notification of Event ETH.41

        Message: 'Ethernet self-test phase $1 failed: $2 interface $3'

        Parameters list:
              $1: eth41_selftest_phase
              $2: eth41_error_condition
              $3: eth41_interface

        The selftest for the Ethernet Am79C960 card has reported an error during
        selftest. The phases are 'Inicialization' and 'Operational Test'."
    ::= { ethNotificationsPrefix 41 }

ethNotification42 NOTIFICATION-TYPE
    STATUS current
    DESCRIPTION
        "Notification of Event ETH.42

        Message: 'Unable to get buf for ethernet packet.'

        A buffer to set an Ethernet, or to copy an Ethernet packet couldn't
        be gotten because a buffer shortage."
    ::= { ethNotificationsPrefix 42 }

ethNotification43 NOTIFICATION-TYPE
    OBJECTS { 
              eth43_interface 
            }
    STATUS current
    DESCRIPTION
        "Notification of Event ETH.43

        Message: 'CMD596 Command Timeout. Interface $1 being restarted.'

        Parameters list:
              $1: eth43_interface

        The 82596 chip on the interface card has failed to clear the command
        field for this interface. The interface will be re-initialized."
    ::= { ethNotificationsPrefix 43 }

ethNotification44 NOTIFICATION-TYPE
    OBJECTS { 
              eth44_command, 
              eth44_interface 
            }
    STATUS current
    DESCRIPTION
        "Notification of Event ETH.44

        Message: 'I5IOCTL Bad Command $1. Interface $2 being restarted.'

        Parameters list:
              $1: eth44_command
              $2: eth44_interface

        An incorrect command field has been sent to the driver. The interface
        will be re-initialized."
    ::= { ethNotificationsPrefix 44 }

ethNotification45 NOTIFICATION-TYPE
    OBJECTS { 
              eth45_selftest_phase, 
              eth45_error_condition,
              eth45_interface 
            }
    STATUS current
    DESCRIPTION
        "Notification of Event ETH.45

        Message: 'Ethernet self-test phase $1 failed: $2 interface $3'

        Parameters list:
              $1: eth45_selftest_phase
              $2: eth45_error_condition
              $3: eth45_interface

        The selftest for the Ethernet card has reported an error during selftest.
        The phases are:
        'Reset board', 'Check reset done', 'Check reset delay',
        'Init SCB', 'Init SCB delay', 'Init SCB completion',
        'Read hardware address', 'Set bus throttle timers',
        'Internal loopback', 'Set hardware address', 'Enable receive',
        'Internal loopback (output)', 'Check internal loopback data',
        'External loopback', 'External loopback delay',
        'External loopback (output)', 'Check External loopback data',
        'Network loopback', 'Network loopback', Network loopback delay',
        'Network loopback (output)', 'Check network looback data',
        'Clear loopback' and 'Operational test'."
    ::= { ethNotificationsPrefix 45 }

ethNotification46 NOTIFICATION-TYPE
    OBJECTS { 
              eth46_received_encapsulation, 
              eth46_configured_encapsulation,
              eth46_interface 
            }
    STATUS current
    DESCRIPTION
        "Notification of Event ETH.46

        Message: 'IPX pkt in $1 encapsulation ignored, using encapsulation $2 on interface $3'

        Parameters list:
              $1: eth46_received_encapsulation
              $2: eth46_configured_encapsulation
              $3: eth46_interface

        This message is generated when an IPX packet is received in a data-link
        encapsulation (frame) other than the one configured for IPX on this
        interface. The packet will be ignored. The received_encapsultaion are
        one of the 'ETHERNET_802.3','ETHERNET_II','ETHERNET_802.2', or
        'ETHERNET_SNAP'. ETHERNET_802.3 is also known as 'Novell', and
        ETHERNET_II is also known as 'Ethernet'."
    ::= { ethNotificationsPrefix 46 }

ethNotification47 NOTIFICATION-TYPE
    OBJECTS { 
              eth47_selftest_phase, 
              eth47_error_condition,
              eth47_interface 
            }
    STATUS current
    DESCRIPTION
        "Notification of Event ETH.47

        Message: 'Ethernet port self-test phase $1 failed: $2 interface $3'

        Parameters list:
              $1: eth47_selftest_phase
              $2: eth47_error_condition
              $3: eth47_interface

        The self-test for the SCC Ethernet port has reported an error during
        self-test. The phases are 'Reset port', 'Set media selection',
        'Set hardware address', 'Network loopback', 'Enable receive',
        'Network loopback (output)', 'Check network loopback data',
        'Clear loopback', 'Set multicast addresses' and 'Operational Test'."
    ::= { ethNotificationsPrefix 47 }

ethNotification48 NOTIFICATION-TYPE
    OBJECTS { 
              eth48_source_MAC_address, 
              eth48_destination_MAC_address,
              eth48_interface 
            }
    STATUS current
    DESCRIPTION
        "Notification of Event ETH.48

        Message: 'Received frame from $1 to $2. Ethernet is not supported so frame is discarded interface $3'

        Parameters list:
              $1: eth48_source_MAC_address
              $2: eth48_destination_MAC_address
              $3: eth48_interface

        A Ethernet frame was received. Current software does not support
        Ethernet interface. Frame will be discarded."
    ::= { ethNotificationsPrefix 48 }

ethNotification49 NOTIFICATION-TYPE
    OBJECTS { 
              eth49_interface 
            }
    STATUS current
    DESCRIPTION
        "Notification of Event ETH.49

        Message: 'Error computing MAC address. Default MAC address is taken interface $1'

        Parameters list:
              $1: eth49_interface

        Error computing LAN interface MAC address due to wrong serial number."
    ::= { ethNotificationsPrefix 49 }

ethNotification50 NOTIFICATION-TYPE
    OBJECTS { 
              eth50_port, 
              eth50_speed,
              eth50_mode,
              eth50_ifcname 
            }
    STATUS current
    DESCRIPTION
        "Notification of Event ETH.50

        Message: 'port $1 up, speed=$2, mode=$3, intf $4'

        Parameters list:
              $1: eth50_port
              $2: eth50_speed
              $3: eth50_mode
              $4: eth50_ifcname

        Switch port up."
    ::= { ethNotificationsPrefix 50 }

ethNotification51 NOTIFICATION-TYPE
    OBJECTS { 
              eth51_port, 
              eth51_ifcname 
            }
    STATUS current
    DESCRIPTION
        "Notification of Event ETH.51

        Message: 'port $1 down, intf $2'

        Parameters list:
              $1: eth51_port
              $2: eth51_ifcname

        Switch port down."
    ::= { ethNotificationsPrefix 51 }

ethNotification52 NOTIFICATION-TYPE
    OBJECTS { 
              eth52_port, 
              eth52_class_string,
              eth52_ifcname 
            }
    STATUS current
    DESCRIPTION
        "Notification of Event ETH.52

        Message: 'port $1 type $2 power on, intf $3'

        Parameters list:
              $1: eth52_port
              $2: eth52_class_string
              $3: eth52_ifcname

        POE port on."
    ::= { ethNotificationsPrefix 52 }

ethNotification53 NOTIFICATION-TYPE
    OBJECTS { 
              eth53_port, 
              eth53_ifcname 
            }
    STATUS current
    DESCRIPTION
        "Notification of Event ETH.53

        Message: 'port $1 power off, intf $2'

        Parameters list:
              $1: eth53_port
              $2: eth53_ifcname

        POE port off."
    ::= { ethNotificationsPrefix 53 }

ethNotification54 NOTIFICATION-TYPE
    OBJECTS { 
              eth54_port, 
              eth54_error_string,
              eth54_ifcname 
            }
    STATUS current
    DESCRIPTION
        "Notification of Event ETH.54

        Message: 'port $1 detection error cause $2 on intf $3'

        Parameters list:
              $1: eth54_port
              $2: eth54_error_string
              $3: eth54_ifcname

        POE port detection error."
    ::= { ethNotificationsPrefix 54 }


END
