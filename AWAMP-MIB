-- ********************************************************************
-- * AwAMP Management Information Base
-- * SNMP v2c version of AWAMP-MIB.my
-- ********************************************************************

AWAMP-MIB DEFINITIONS ::= BEGIN

IMPORTS
    MODULE-IDENTITY, 
    OBJECT-TYPE,
    NOTIFICATION-TYPE, 
    enterprises,
    Integer32,
    IpAddress
    	FROM SNMPv2-SMI
    DisplayString,
    MacAddress,
    TruthValue
	FROM SNMPv2-TC
    MODULE-COMPLIANCE, OBJECT-GROUP, NOTIFICATION-GROUP
        FROM SNMPv2-CONF;


-- ********************************************************************
-- *  MODULE IDENTITY
-- ********************************************************************
awamp MODULE-IDENTITY
    LAST-UPDATED "201112200000Z" -- December 20, 2011 
    ORGANIZATION "Aruba Networks, Inc."
    CONTACT-INFO    
	 "Primary Author: Paul Gray
	 
         postal:    Aruba Networks, Inc.
                    1344 Crossman Ave
                    Sunnyvale, CA 94402
         phone:     +1 408-227-4500
         email:     paul@arubanetworks.com
           web:     http://www.arubanetworks.com/"
    DESCRIPTION
		"The MIB module for AirWave entities .
      	iso(1).org(3).dod(6).internet(1).private(4).
      	enterprises(1).airwave(12028).awamp(4)"

    REVISION "201112200000Z" -- December 20, 2011
    DESCRIPTION "Derek made compliant with level 6 of smilint."

    REVISION "201106210000Z" -- June 21, 2011
    DESCRIPTION "Dhana and Mike added rogueAPDetectedDetail."

    REVISION "200802280000Z" -- February 28, 2008
    DESCRIPTION "Sam and Peter added a RFID not heard for trap."

    REVISION "200304170001Z" -- April 17, 2003
    DESCRIPTION "Paul added internal HP Traps."

    REVISION "200304170000Z" -- April 17, 2003
    DESCRIPTION "Paul - Initial creation."

	::= { enterprises 12028 4 }

airwave		OBJECT IDENTIFIER ::= { enterprises 12028 }

-- ********************************************************************
-- *  Major sections 
-- ********************************************************************
--  Airwave Management Platform (awampsystem) Attributes
--          DEFINED AS "The awampSystem object class provides all
--          standard information to support operation of an AirWave 
--          Management Platform.";

awampSystem OBJECT IDENTIFIER ::=         {awamp 10}

--  Airwave Management Platform 802.11 (awc802dot11) Attributes 
--          DEFINED AS "The awc802dot11 object class provides all 
--          standard information to support configuration of the 802.11
--          protocol. This class also provides various statistics of
--          802.11 stations.";

awamp802dot11 OBJECT IDENTIFIER ::=       {awamp 11}

--  Airwave Management Platform Event Traps (awampEvent) Attributes 
--          DEFINED AS "The awampEvent object class provides all 
--          standard information to support traps, alerts, triggers.";

awampEvent OBJECT IDENTIFIER ::= {awamp 15}
awampEventPrefix OBJECT IDENTIFIER ::= {awampEvent 0}
awampEventObject OBJECT IDENTIFIER ::= {awampEvent 1}

-- ********************************************************************
-- *  Definitions  
-- ********************************************************************
awampApName OBJECT-TYPE
                SYNTAX DisplayString
                MAX-ACCESS read-only
                STATUS current
                DESCRIPTION 
                        "The AP Name"
        ::= { awamp 101 }

awampGroupName OBJECT-TYPE
                SYNTAX DisplayString
                MAX-ACCESS read-only
                STATUS current
                DESCRIPTION 
                        "The Group Name"
        ::= { awamp 102 }

awampAPEthMAC OBJECT-TYPE
                SYNTAX MacAddress
                MAX-ACCESS read-only
                STATUS current
                DESCRIPTION 
                        "IEEE Unique Identifier"
        ::= { awamp 103 }	

awampAPIP OBJECT-TYPE
                SYNTAX IpAddress
                MAX-ACCESS read-only
                STATUS current
                DESCRIPTION 
                        "IP Address of the AP (Eth0)"
        ::= { awamp 104 }

awampAPMFG OBJECT-TYPE
                SYNTAX DisplayString
                MAX-ACCESS read-only
                STATUS current
                DESCRIPTION 
                        "AP MFG"
        ::= { awamp 105 }

awampAPModel OBJECT-TYPE
                SYNTAX DisplayString
                MAX-ACCESS read-only
                STATUS current
                DESCRIPTION 
                        "AP Model"
        ::= { awamp 106 }

awampAPFirmware OBJECT-TYPE
                SYNTAX DisplayString
                MAX-ACCESS read-only
                STATUS current
                DESCRIPTION 
                        "AP Firmware"
        ::= { awamp 107 }

awampROCommString OBJECT-TYPE
                SYNTAX DisplayString
                MAX-ACCESS read-only
                STATUS current
                DESCRIPTION 
                        "Read Only Community String (not currently used)"
        ::= { awamp 108 }

awampHPOVHostName OBJECT-TYPE
                SYNTAX DisplayString
                MAX-ACCESS read-only
                STATUS current
                DESCRIPTION 
                        "Hostname of the AP"
        ::= { awamp 109 }

awampHPOVSYSID  OBJECT-TYPE
                SYNTAX DisplayString
                MAX-ACCESS read-only
                STATUS current
                DESCRIPTION 
                        "Hp OpenView Object Id"
        ::= { awamp 110 }

awampHPOVMAC1  OBJECT-TYPE
                SYNTAX MacAddress
                MAX-ACCESS read-only
                STATUS current
                DESCRIPTION  
                        "First Radio MAC on AP"
        ::= { awamp 111 }

awampHPOVIP1 OBJECT-TYPE
                SYNTAX IpAddress
                MAX-ACCESS read-only
                STATUS current
                DESCRIPTION 
                        "First Radio IP AP"
        ::= { awamp 112 }

awampHPOVMAC2  OBJECT-TYPE
                SYNTAX MacAddress
                MAX-ACCESS read-only
                STATUS current
                DESCRIPTION  
                        "Second Radio MAC on AP"
        ::= { awamp 113 }

awampHPOVIP2 OBJECT-TYPE
                SYNTAX IpAddress
                MAX-ACCESS read-only
                STATUS current
                DESCRIPTION 
                        "Second Radio IP AP"
        ::= { awamp 114 }

awampHPOVsysName OBJECT-TYPE
                SYNTAX DisplayString
                MAX-ACCESS read-only
                STATUS current
                DESCRIPTION 
                        "Hostname of the AP"
        ::= { awamp 115 }


awampHPOVsysDescr OBJECT-TYPE
                SYNTAX DisplayString
                MAX-ACCESS read-only
                STATUS current
                DESCRIPTION 
                        "Hostname of the AP"
        ::= { awamp 116 }


-- ********************************************************************
-- *  awampEvent parameter definitions 
-- ********************************************************************
awampEventID OBJECT-TYPE
                SYNTAX Integer32
                MAX-ACCESS read-only
                STATUS current
                DESCRIPTION 
                        "Random number AMP assigns to the event."
        ::= { awampEventObject 101 }

awampEventSeverityCode OBJECT-TYPE
                SYNTAX Integer32
                MAX-ACCESS read-only
                STATUS current
                DESCRIPTION 
                        "Level 1-6"
        ::= { awampEventObject 102 }

awampEventDescription OBJECT-TYPE
                SYNTAX DisplayString
                MAX-ACCESS read-only
                STATUS current
                DESCRIPTION 
                        "Concatenated String produced from AMP."
        ::= { awampEventObject 103 }

awampEventAPIPOld OBJECT-TYPE
                SYNTAX IpAddress
                MAX-ACCESS read-only
                STATUS current
                DESCRIPTION 
                        "Old IP of the AP when AMP changes and
                         sends trap to HPOV."
        ::= { awampEventObject 104 }

awampEventAPMngURL OBJECT-TYPE
                SYNTAX DisplayString
                MAX-ACCESS read-only
                STATUS current
                DESCRIPTION 
                        "URL to manage AP on AMP from HPOV."
        ::= { awampEventObject 105 }

awampEventAPMonURL OBJECT-TYPE
                SYNTAX DisplayString
                MAX-ACCESS read-only
                STATUS current
                DESCRIPTION 
                        "URL to monitor AP on AMP from HPOV."
        ::= { awampEventObject 106 }

awampEventGroupMngURL OBJECT-TYPE
                SYNTAX DisplayString
                MAX-ACCESS read-only
                STATUS current
                DESCRIPTION 
                        "URL to manage Group on AMP from HPOV."
        ::= { awampEventObject 107 }

awampEventGroupMonURL OBJECT-TYPE
                SYNTAX DisplayString
                MAX-ACCESS read-only
                STATUS current
                DESCRIPTION 
                        "URL to monitor Group on AMP from HPOV."
        ::= { awampEventObject 108 }

awampEventAPICON OBJECT-TYPE
                SYNTAX DisplayString
                MAX-ACCESS read-only
                STATUS current
                DESCRIPTION 
                        "Name of ICON to display on HPOV screen"
        ::= { awampEventObject 109 }

awampEventRogueSSID OBJECT-TYPE
                SYNTAX DisplayString
                MAX-ACCESS read-only
                STATUS current
                DESCRIPTION
                        "SSID of detected Rogue AP."
        ::= { awampEventObject 110 }

awampEventRogueLANManufacturer OBJECT-TYPE
                SYNTAX DisplayString
                MAX-ACCESS read-only
                STATUS current
                DESCRIPTION
                        "Manufacturer of LAN of detected Rogue AP."
        ::= { awampEventObject 111 }

awampEventRogueRadioManufacturer OBJECT-TYPE
                SYNTAX DisplayString
                MAX-ACCESS read-only
                STATUS current
                DESCRIPTION
                        "Manufacturer of radio detected Rogue AP."
        ::= { awampEventObject 112 }

awampEventRogueIsWired OBJECT-TYPE
                SYNTAX TruthValue
                MAX-ACCESS read-only
                STATUS current
                DESCRIPTION
                        "Detected Rogue AP was discovered on the wired network."
        ::= { awampEventObject 113 }

awampEventRogueIsWireless OBJECT-TYPE
                SYNTAX TruthValue
                MAX-ACCESS read-only
                STATUS current
                DESCRIPTION
                        "Detected Rogue AP was discovered on the wireless network."
        ::= { awampEventObject 114 }

awampEventRogueClassifyingRule OBJECT-TYPE
                SYNTAX DisplayString
                MAX-ACCESS read-only
                STATUS current
                DESCRIPTION
                        "Rule used to classify detected rogue AP."
        ::= { awampEventObject 115 }

awampEventRogueDiscoveringAgent OBJECT-TYPE
                SYNTAX DisplayString
                MAX-ACCESS read-only
                STATUS current
                DESCRIPTION
                        "The discovering agent that last detected the rogue AP."
        ::= { awampEventObject 116 }

awampEventRogueDiscoveringAgentFolder OBJECT-TYPE
                SYNTAX DisplayString
                MAX-ACCESS read-only
                STATUS current
                DESCRIPTION
                        "The folder name of the discovering agent that last detected the rogue AP."
        ::= { awampEventObject 117 }

awampEventRogueClientMac OBJECT-TYPE
                SYNTAX DisplayString
                MAX-ACCESS read-only
                STATUS current
                DESCRIPTION
                    "MAC Address of client connected to rogue ap."
          ::= { awampEventObject 118 }

awampEventRogueName OBJECT-TYPE
                SYNTAX DisplayString
                MAX-ACCESS read-only
                STATUS current
                DESCRIPTION
                    "SSID to which the client is connected on rogue ap."
          ::= { awampEventObject 119 }

-- ********************************************************************
-- *  Fault Traps generated by the AMP 
-- *  (1.3.6.1.4.12028.4.15.0.)
-- ********************************************************************
tooManyDevAssocAMP NOTIFICATION-TYPE
	OBJECTS { awampEventID, 
                awampEventSeverityCode,
                awampEventDescription }
    STATUS	current
    DESCRIPTION
	"This trap is sent when too many devices are
	simultaneously associated with AMP for a period of time."
    ::= { awampEventPrefix 1 }

tooManyDevAssocGroup NOTIFICATION-TYPE
	OBJECTS { awampEventID,
                awampEventSeverityCode,
                awampEventDescription }
    STATUS	current
    DESCRIPTION
	"This trap is sent when too many devices are 
	simultaneously associated with a Group for a period of time."
    ::= { awampEventPrefix 2 }

tooManyDevAssocAp NOTIFICATION-TYPE
	OBJECTS { awampEventID,
                awampEventSeverityCode,
                awampEventDescription,
		    awampAPIP }
    STATUS	current
    DESCRIPTION
	"This trap is sent when too many devices are associated 
	simultaneously associated with an AP for a period of time. "
    ::= { awampEventPrefix 3 }

toomuchBWAMP NOTIFICATION-TYPE
	OBJECTS { awampEventID, 
                awampEventSeverityCode,
                awampEventDescription }
    STATUS	current
    DESCRIPTION
	"This trap is sent when there is too much BW being 
	used on the WLAN for a period of time."
    ::= { awampEventPrefix 4 }

toomuchBWGroup NOTIFICATION-TYPE
	OBJECTS { awampEventID, 
                awampEventSeverityCode,
                awampEventDescription }
    STATUS	current
    DESCRIPTION
	"This trap is sent when there is too much BW being 
	used by a Group for a period of time."
    ::= { awampEventPrefix 5 }

toomuchBWAP NOTIFICATION-TYPE
	OBJECTS { awampEventID, 
                awampEventSeverityCode,
                awampEventDescription,
		    awampAPIP }
    STATUS	current
    DESCRIPTION
	"This trap is sent when there is too much BW being 
	used on an AP for a period of time."
    ::= { awampEventPrefix 6 }

toomuchBWClient NOTIFICATION-TYPE
	OBJECTS { awampEventID, 
                awampEventSeverityCode,
                awampEventDescription }
    STATUS	current
    DESCRIPTION
	"This trap is sent when there is too much BW being 
	used by a Client for a period of time."
    ::= { awampEventPrefix 7 }

toomanyRoamsClient NOTIFICATION-TYPE
	OBJECTS { awampEventID, 
                awampEventSeverityCode,
                awampEventDescription }
    STATUS	current
    DESCRIPTION
	"This trap is sent when Client roams too frequently   
	for a period of time."
    ::= { awampEventPrefix 8 }

poorSignalAP NOTIFICATION-TYPE
	OBJECTS { awampEventID, 
                awampEventSeverityCode,
                awampEventDescription,
                awampAPIP }
    STATUS	current
    DESCRIPTION
	"This trap is sent when an AP has poor Signal
	quality for a period of time."
    ::= { awampEventPrefix 9 }

nonAMPAPChange NOTIFICATION-TYPE
	OBJECTS { awampEventID, 
                awampEventSeverityCode,
                awampEventDescription,
		    awampAPIP }
    STATUS	current
    DESCRIPTION
	"This trap is sent when an AP Changes configuration
	without the AMP's knowledge"
    ::= { awampEventPrefix 10 }

unauthenticatedClient NOTIFICATION-TYPE
	OBJECTS { awampEventID, 
                awampEventSeverityCode,
                awampEventDescription }
    STATUS	current
    DESCRIPTION
	"This trap is sent when Client is associated with
	WLAN for a period of time without authenticating."
    ::= { awampEventPrefix 11 }

rogueAPDetected NOTIFICATION-TYPE
	OBJECTS { awampEventID, 
                awampEventSeverityCode,
                awampEventDescription }   
    STATUS	current
    DESCRIPTION
	"This trap is sent when the AMP classifies a
       Rogue AP."
    ::= { awampEventPrefix 12 }
    
downAP NOTIFICATION-TYPE
	OBJECTS { awampEventID, 
                awampEventSeverityCode,
                awampEventDescription,
                awampAPIP }   
    STATUS	current
    DESCRIPTION
	"This trap is sent when the AP is down
         (for instance, a missed SNMP Ping or SNMP Get)."
    ::= { awampEventPrefix 13 }

discoveredAP NOTIFICATION-TYPE
	OBJECTS { awampEventID, 
                awampEventSeverityCode,
                awampEventDescription,
                awampAPIP }   
    STATUS	current
    DESCRIPTION
	"This trap is sent when AP is discovered by AMP.
         Note that this only applies to AP discovery,
         not authorization. (A Config trap is sent when
         the AP is authorized."
    ::= { awampEventPrefix 14 }
    
upAP NOTIFICATION-TYPE
	OBJECTS { awampEventID, 
                awampEventSeverityCode,
                awampEventDescription,
                awampAPIP }   
    STATUS	current
    DESCRIPTION
	"This trap is sent when AP is detected as UP after being
         marked DOWN by the AMP."
    ::= { awampEventPrefix 15 }

downRadio NOTIFICATION-TYPE
	OBJECTS { awampEventID, 
                awampEventSeverityCode,
                awampEventDescription,
                awampAPIP }   
    STATUS	current
    DESCRIPTION
	"This trap is sent when the radio of an AP is not operating."
    ::= { awampEventPrefix 16 }

clientAssociate NOTIFICATION-TYPE
	OBJECTS { awampEventID, 
                awampEventSeverityCode,
                awampEventDescription,
                awampAPIP }   
    STATUS	current
    DESCRIPTION
	"This trap is sent when a watched client mac address
        associates to an AP."
    ::= { awampEventPrefix 17 }  

authIssueClient NOTIFICATION-TYPE
	OBJECTS { awampEventID, 
                awampEventSeverityCode,
                awampEventDescription }   
    STATUS	current
    DESCRIPTION
	"This trap is sent when a client experiences too many 
        authentication failures."
    ::= { awampEventPrefix 18 }

authIssueAP NOTIFICATION-TYPE
	OBJECTS { awampEventID,
                awampEventSeverityCode,
                awampEventDescription,
                awampAPIP }
    STATUS	current
    DESCRIPTION
	"This trap is sent when an AP experiences too many
        authentication failures."
    ::= { awampEventPrefix 19 }

authIssueAMP NOTIFICATION-TYPE
	OBJECTS { awampEventID,
                awampEventSeverityCode,
                awampEventDescription }
    STATUS	current
    DESCRIPTION
	"This trap is sent when AMP detects too many
        authentication failures."
    ::= { awampEventPrefix 20 }

idsEventAP NOTIFICATION-TYPE
	OBJECTS { awampEventID,
                awampEventSeverityCode,
                awampEventDescription,
                awampAPIP }
    STATUS	current
    DESCRIPTION
	"This trap is sent when AMP receives too many IDS
        events from an AP."
    ::= { awampEventPrefix 21 }

rfidTagNotHeard NOTIFICATION-TYPE
        OBJECTS { awampEventID,
                  awampEventSeverityCode,
                  awampEventDescription }
    STATUS      current
    DESCRIPTION
        "This trap is sent when an RFID tag is not heard for
        a certain period of time."
    ::= { awampEventPrefix 22 }

dot11Counters NOTIFICATION-TYPE
        OBJECTS { awampEventID,
                  awampEventSeverityCode,
                  awampEventDescription }
    STATUS      current
    DESCRIPTION
        "This trap is sent when a Dot11 counter trigger fires."
    ::= { awampEventPrefix 23 }

qosCounters NOTIFICATION-TYPE
        OBJECTS { awampEventID,
                  awampEventSeverityCode,
                  awampEventDescription }
    STATUS      current
    DESCRIPTION
        "This trap is sent when a QOS counter trigger fires."
    ::= { awampEventPrefix 24 }

deviceResources NOTIFICATION-TYPE
        OBJECTS { awampEventID,
                  awampEventSeverityCode,
                  awampEventDescription }
    STATUS      current
    DESCRIPTION
        "This trap is sent when a Device Resources trigger fires."
    ::= { awampEventPrefix 25 }

diskUsage NOTIFICATION-TYPE
	OBJECTS { awampEventID,
                awampEventSeverityCode,
                awampEventDescription }
    STATUS	current
    DESCRIPTION
	"This trap is sent when a Disk Usage trigger fires."
    ::= { awampEventPrefix 26 }

managedAmpDown NOTIFICATION-TYPE
	OBJECTS { awampEventID,
                awampEventSeverityCode,
                awampEventDescription }
    STATUS	current
    DESCRIPTION
	"This trap is sent when a Managed AMP Down trigger fires."
    ::= { awampEventPrefix 27 }

watchedAmpDown NOTIFICATION-TYPE
	OBJECTS { awampEventID,
                awampEventSeverityCode,
                awampEventDescription }
    STATUS	current
    DESCRIPTION
	"This trap is sent when a Watched AMP Down trigger fires."
    ::= { awampEventPrefix 28 }

interfaceBandwidth NOTIFICATION-TYPE
	OBJECTS { awampEventID,
                awampEventSeverityCode,
                awampEventDescription }
    STATUS	current
    DESCRIPTION
	"This trap is sent when an Interface Bandwidth trigger fires."
    ::= { awampEventPrefix 29 }

radioUtilization NOTIFICATION-TYPE
	OBJECTS { awampEventID,
                awampEventSeverityCode,
                awampEventDescription }
    STATUS	current
    DESCRIPTION
	"This trap is sent when a Radio Utilization trigger fires."
    ::= { awampEventPrefix 30 }

deviceEvent NOTIFICATION-TYPE
	OBJECTS { awampEventID,
                awampEventSeverityCode,
                awampEventDescription }
    STATUS	current
    DESCRIPTION
	"This trap is sent when a Device Event trigger fires."
    ::= { awampEventPrefix 31 }

rogueAPDetectedDetail NOTIFICATION-TYPE
	OBJECTS { awampEventID,
                awampEventSeverityCode,
                awampEventDescription,
                awampEventRogueSSID,
                awampEventRogueRadioManufacturer,
                awampEventRogueIsWired,
                awampEventRogueIsWireless,
                awampEventRogueClassifyingRule,
                awampEventRogueDiscoveringAgent,
                awampEventRogueDiscoveringAgentFolder }
    STATUS	current
    DESCRIPTION
	"This trap is sent when the AMP classifies a
       Rogue AP. It includes more details: SSID, Manufacturer,
       Wired (boolean), Wireless (boolean), Classifying Rule Name,
       Last Discovering Agent, and AP Folder Name."
    ::= { awampEventPrefix 32 }

ipv4LinkLocalAddresses NOTIFICATION-TYPE
	OBJECTS { awampEventID,
                awampEventSeverityCode,
                awampEventDescription }
    STATUS	current
    DESCRIPTION
	"This trap is sent when a IPv4 Link-Local Addresses trigger fires."
    ::= { awampEventPrefix 33 }

vpnUserConnect NOTIFICATION-TYPE
	OBJECTS { awampEventID, 
                awampEventSeverityCode,
                awampEventDescription,
                awampAPIP }   
    STATUS	current
    DESCRIPTION
	"This trap is sent when a new VPN user 
        connects to a controller."
    ::= { awampEventPrefix 34 }

clientOnRogueAP NOTIFICATION-TYPE
	OBJECTS { awampEventID,
                awampEventSeverityCode,
                awampEventDescription,
                awampAPIP,
                awampEventRogueClientMac,
                awampEventRogueSSID,
                awampEventRogueName }
    STATUS	current
    DESCRIPTION
	"This trap is sent when a new client is discovered
        on Rogue AP. It includes more details: Client MAC,
        Rogue SSID and Rogue Device Name."
    ::= { awampEventPrefix 35 }

vpnUserAssociate NOTIFICATION-TYPE
	OBJECTS { awampEventID, 
                awampEventSeverityCode,
                awampEventDescription,
                awampAPIP }   
    STATUS	current
    DESCRIPTION
	"This trap is sent when a watched VPN username 
        associates to a controller."
    ::= { awampEventPrefix 36 }

toomuchBWVPNUser NOTIFICATION-TYPE
	OBJECTS { awampEventID,
                awampEventSeverityCode,
                awampEventDescription,
                awampAPIP }
    STATUS	current
    DESCRIPTION
	"This trap is sent when a new VPN user
        connects to a controller."
    ::= { awampEventPrefix 37 }

toomuchGoodputClient NOTIFICATION-TYPE
	OBJECTS { awampEventID,
                awampEventSeverityCode,
                awampEventDescription }
    STATUS	current
    DESCRIPTION
        "This trap is sent when there is too much Goodput being
	used by a Client for a period of time."
    ::= { awampEventPrefix 38 }

speedClient NOTIFICATION-TYPE
	OBJECTS { awampEventID,
                awampEventSeverityCode,
                awampEventDescription }
    STATUS	current
    DESCRIPTION
	"This trap is sent when speed of a Client is
         below (or above) a threshold for a period of time."
    ::= { awampEventPrefix 39 }

noisefloorRadio NOTIFICATION-TYPE
	OBJECTS { awampEventID,
                awampEventSeverityCode,
                awampEventDescription }
    STATUS	current
    DESCRIPTION
	"This trap is sent when noise floor of AP is
         below (or above) a threshold for a period of time."
    ::= { awampEventPrefix 40 }

genericTrap NOTIFICATION-TYPE
	OBJECTS { awampEventID, 
                awampEventSeverityCode,
                awampEventDescription,
                awampAPIP }
    STATUS	current
    DESCRIPTION
	"This trap will catch things not defined."
    ::= { awampEventPrefix 50 }

internalAMLUnknown NOTIFICATION-TYPE
	OBJECTS { awampEventID, 
                awampEventSeverityCode,
                awampEventDescription,
                awampAPIP }
    STATUS	current
    DESCRIPTION
	"This is an internal trap designed for AML
	 running on the NNM.  It allows the AML to 
	 dynamically accept severity codes from the AMP.
	 Because HP OpenView statically defines these in
	 trapd.conf per trap, we are creating an internal
	 for each severity level to work around issue.
	 Represents Blue and level 1"
    ::= { awampEventPrefix 51 }    

internalAMLNormal NOTIFICATION-TYPE
	OBJECTS { awampEventID, 
                awampEventSeverityCode,
                awampEventDescription,
                awampAPIP }
    STATUS	current
    DESCRIPTION
	"This is an internal trap designed for AML
	 running on the NNM.  It allows the AML to 
	 dynamically accept severity codes from the AMP.
	 Because HP OpenView statically defines these in
	 trapd.conf per trap, we are creating an internal
	 for each severity level to work around issue.
	 Represents Green and level 2"
    ::= { awampEventPrefix 52 }   

internalAMLMinor NOTIFICATION-TYPE
	OBJECTS { awampEventID, 
                awampEventSeverityCode,
                awampEventDescription,
                awampAPIP }
    STATUS	current
    DESCRIPTION
	"This is an internal trap designed for AML
	 running on the NNM.  It allows the AML to 
	 dynamically accept severity codes from the AMP.
	 Because HP OpenView statically defines these in
	 trapd.conf per trap, we are creating an internal
	 for each severity level to work around issue.
	 Represents yellow and level 3"
    ::= { awampEventPrefix 53 } 

internalAMLCritcal NOTIFICATION-TYPE
	OBJECTS { awampEventID, 
                awampEventSeverityCode,
                awampEventDescription,
                awampAPIP }
    STATUS	current
    DESCRIPTION
	"This is an internal trap designed for AML
	 running on the NNM.  It allows the AML to 
	 dynamically accept severity codes from the AMP.
	 Because HP OpenView statically defines these in
	 trapd.conf per trap, we are creating an internal
	 for each severity level to work around issue.
	 Represents Red and level 4"
    ::= { awampEventPrefix 54 } 

internalAMLWarning NOTIFICATION-TYPE
	OBJECTS { awampEventID, 
                awampEventSeverityCode,
                awampEventDescription,
                awampAPIP }
    STATUS	current
    DESCRIPTION
	"This is an internal trap designed for AML
	 running on the NNM.  It allows the AML to 
	 dynamically accept severity codes from the AMP.
	 Because HP OpenView statically defines these in
	 trapd.conf per trap, we are creating an internal
	 for each severity level to work around issue.
	 Represents Cyan and level 6"
    ::= { awampEventPrefix 56 } 
    
internalAMLMajor NOTIFICATION-TYPE
	OBJECTS { awampEventID, 
                awampEventSeverityCode,
                awampEventDescription,
                awampAPIP }
    STATUS	current
    DESCRIPTION
	"This is an internal trap designed for AML
	 running on the NNM.  It allows the AML to 
	 dynamically accept severity codes from the AMP.
	 Because HP OpenView statically defines these in
	 trapd.conf per trap, we are creating an internal
	 for each severity level to work around issue.
	 Represents Orange and level 7"
    ::= { awampEventPrefix 57 }     

uplinkDevice NOTIFICATION-TYPE
	OBJECTS { awampEventID, 
                awampEventSeverityCode,
                awampEventDescription,
                awampAPIP }   
    STATUS	current
    DESCRIPTION
	"This trap is sent when the device uplink status is changed."
    ::= { awampEventPrefix 58 }

upRadio NOTIFICATION-TYPE
	OBJECTS { awampEventID,
                awampEventSeverityCode,
                awampEventDescription,
                awampAPIP }
    STATUS	current
    DESCRIPTION
	"This trap is sent when the radio of an AP is detected as UP
         after being marked DOWN."
    ::= { awampEventPrefix 59 }
    
-- ********************************************************************
-- *  Config Traps generated by the AMP 
-- *  (1.3.6.1.4.12028.4.15.)
-- ********************************************************************
configAlert NOTIFICATION-TYPE
	OBJECTS { awampAPIP,
                awampEventAPIPOld,
                awampAPEthMAC,
                awampEventAPMngURL,
                awampEventAPMonURL,
                awampGroupName,
		    awampEventGroupMngURL,
		    awampEventGroupMonURL,
                awampEventAPICON,
                awampAPMFG,
                awampAPModel,
                awampAPFirmware,
		    awampApName }
    STATUS	current
    DESCRIPTION
      "This trap is sent every time a new device is discovered
      and authenticated on the AMP.  Also sent upon change to
	IP, Name, Firmware, Group Association."
    ::= { awampEventPrefix 200 }

--
-- conformance information
--

awampConformance OBJECT IDENTIFIER ::= { awamp 2 }

awampCompliances OBJECT IDENTIFIER ::= { awampConformance 1 }
awampGroups      OBJECT IDENTIFIER ::= { awampConformance 2 }

-- compliance statements

awampCompliance MODULE-COMPLIANCE
   STATUS  current
   DESCRIPTION
        "The compliance statement for the AirWave AMP."
   MODULE  -- this module
   MANDATORY-GROUPS { awampInfoGroup, awampEventGroup, awampNotificationGroup }
   ::= { awampCompliances 1 }

awampInfoGroup OBJECT-GROUP
   OBJECTS   { -- these are defined in this module
               awampApName,
               awampGroupName,
               awampAPEthMAC,
               awampAPIP,
               awampAPMFG,
               awampAPModel,
               awampAPFirmware,
               awampROCommString,
               awampHPOVHostName,
               awampHPOVSYSID,
               awampHPOVMAC1,
               awampHPOVIP1,
               awampHPOVMAC2,
               awampHPOVIP2,
               awampHPOVsysName,
               awampHPOVsysDescr }
   STATUS    current
   DESCRIPTION
        "The group of objects providing AMP information."
   ::= { awampGroups 1 }

awampEventGroup OBJECT-GROUP
    OBJECTS  { -- these are defined in this module
               awampEventID,
               awampEventSeverityCode,
               awampEventDescription,
               awampEventAPIPOld,
               awampEventAPMngURL,
               awampEventAPMonURL,
               awampEventGroupMngURL,
               awampEventGroupMonURL,
               awampEventAPICON,
               awampEventRogueSSID,
               awampEventRogueLANManufacturer,
               awampEventRogueRadioManufacturer,
               awampEventRogueIsWired,
               awampEventRogueIsWireless,
               awampEventRogueClassifyingRule,
               awampEventRogueDiscoveringAgent,
               awampEventRogueDiscoveringAgentFolder,
               awampEventRogueClientMac,
               awampEventRogueName }
    STATUS   current
    DESCRIPTION
         "The group of objects providing AMP events."
    ::= { awampGroups 2 }

awampNotificationGroup NOTIFICATION-GROUP
    NOTIFICATIONS  { -- these are defined in this module
               tooManyDevAssocAMP,
               tooManyDevAssocGroup,
               tooManyDevAssocAp,
               toomuchBWAMP,
               toomuchBWGroup,
               toomuchBWAP,
               toomuchBWClient,
               toomanyRoamsClient,
               poorSignalAP,
               nonAMPAPChange,
               unauthenticatedClient,
               rogueAPDetected,
               downAP,
               discoveredAP,
               upAP,
               downRadio,
               clientAssociate,
               authIssueClient,
               authIssueAP,
               authIssueAMP,
               idsEventAP,
               rfidTagNotHeard,
               dot11Counters,
               qosCounters,
               deviceResources,
               diskUsage,
               managedAmpDown,
               watchedAmpDown,
               interfaceBandwidth,
               radioUtilization,
               deviceEvent,
               rogueAPDetectedDetail,
               ipv4LinkLocalAddresses,
               vpnUserConnect,
               clientOnRogueAP,
               vpnUserAssociate,
               toomuchBWVPNUser,
               toomuchGoodputClient,
               speedClient,
               noisefloorRadio,
               genericTrap,
               internalAMLUnknown,
               internalAMLNormal,
               internalAMLMinor,
               internalAMLCritcal,
               internalAMLWarning,
               internalAMLMajor,
               uplinkDevice,
               upRadio,
               configAlert }
    STATUS   current
    DESCRIPTION
         "The group of objects providing AMP notifications."
    ::= { awampGroups 3 }

END
