-- *****************************************************************************
-- Juniper-UNI-ATM-MIB
--
-- Juniper Networks Enterprise MIB
--   ATM MIB
--
-- Copyright (c) 1999 Redstone Communications, Inc.
-- Copyright (c) 1999, 2002 Unisphere Networks, Inc.
-- Copyright (c) 2002, 2004 Juniper Networks, Inc.
--   All Rights Reserved.
-- *****************************************************************************

Juniper-UNI-ATM-MIB  DEFINITIONS ::= BEGIN

IMPORTS
    MODULE-IDENTITY, OBJECT-IDENTITY, OBJECT-TYPE, NOTIFICATION-TYPE, Integer32,
    Unsigned32, Counter64, Counter32, IpAddress, TimeTicks
        FROM SNMPv2-SMI
    TEXTUAL-CONVENTION, RowStatus, TruthValue, TimeStamp, DisplayString
        FROM SNMPv2-TC
    SnmpAdminString
        FROM SNMP-FRAMEWORK-MIB
    MODULE-COMPLIANCE, OBJECT-GROUP, NOTIFICATION-GROUP
        FROM SNMPv2-CONF
    InterfaceIndex, InterfaceIndexOrZero, ifIndex
        FROM IF-MIB
    AtmVpIdentifier, AtmVcIdentifier, AtmVorXAdminStatus, AtmAddr
        FROM ATM-TC-MIB
    atmVplVpi, atmVclVpi, atmVclVci
        FROM ATM-MIB
    atmfM4VpTestObject, atmfM4VpTestId, atmfM4VpTestType, atmfM4VpTestResult,
    atmfM4VcTestObject, atmfM4VcTestId, atmfM4VcTestType, atmfM4VcTestResult,
    atmfM4VpTestCode, atmfM4VcTestCode
        FROM ATM-FORUM-SNMP-M4-MIB
    juniMibs
        FROM Juniper-MIBs
    JuniNextIfIndex, JuniEnable, JuniInterfaceLocationType,
    JuniInterfaceLocationValue
        FROM Juniper-TC;

juniAtmMIB  MODULE-IDENTITY
    LAST-UPDATED "200412081522Z"  -- 08-Dec-04 10:22 AM EST
    ORGANIZATION "Juniper Networks, Inc."
    CONTACT-INFO
        "       Juniper Networks, Inc.
        Postal: 10 Technology Park Drive
                Westford, MA  01886-3146
                USA
        Tel:    +1 978 589 5800
        Email:  mib@Juniper.net"
    DESCRIPTION
        "The ATM MIB for the Juniper enterprise."
    -- Revision History
    REVISION    "200412081522Z"  -- 08-Dec-04 10:22 AM EST  - JUNOSe x.y
    DESCRIPTION
        "Added aal0 and aal5 values to juniAtmSubIfVccType enumeration.
         Added ATM Martini cell aggregation configuration objects.
         Added profile override support.
         Added bulk-configuration modification support."
    REVISION    "200312301507Z"  -- 25-Feb-04 03:23 PM EST - JUNOSe 6.0
    DESCRIPTION
        "Added second generation E-series platform support:
            Imported JuniInterfaceLocationType and JuniInterfaceLocationValue
            from Juniper-TC to replace JuniAtmLocationType and
            JuniAtmLocationValue textual conventions, respectively."
    REVISION    "200402252023Z"  -- 25-Feb-04 03:23 PM EST  - JUNOSe 5.3
    DESCRIPTION
        "Added support to export the subinterface description to the line
         cards.  Added advisory receive support for subinterfaces."
    REVISION    "200309192201Z"  -- 19-Sep-03 06:01 PM EDT  - JUNOSe 5.2
    DESCRIPTION
        "Added JuniAtmLocationType and JuniAtmLocationValue textual conventions.
         Added juniAtmSubIfLocationType and juniAtmSubIfLocationTable."
    REVISION    "200307141537Z"  -- 14-Jul-03 11:37 AM EDT  - JUNOSe 5.1
    DESCRIPTION
        "Added F4 flow OAM circuit support.
         Added ATM VP description support.
         Added bulk circuit configuration support.
         Corrected enumeration values for UNI signalling versions."
    REVISION    "200301151932Z"  -- 15-Jan-03 02:32 PM EST  - JUNOSe 5.0
    DESCRIPTION
        "Replaced Unisphere names with Juniper names.
         Changed the juniAtmVcPingProbeCount Range to match CLI.
         Added null value for juniAtmSubIfVccType."
    REVISION    "200208091403Z"  -- 09-Aug-02 10:03 AM EDT  - JUNOSe 4.1
    DESCRIPTION
        "Added receive bandwith support to CAC.
         Added E164 public addressing support.
         Added PNNI RCC table support.
         Added ATM1483 interface MTU config support."
    REVISION    "200208091340Z"  -- 09-Aug-02 09:40 AM EDT  - JUNOSe 4.0
    DESCRIPTION
        "Added support for CAC used bandwidth.
         Added ATM switched virtual connection (SVC) support.
         Added juniAtmSubIfAddress to the juniAtmSubIfTable."
    REVISION    "200201241400Z"  -- 24-Jan-02 09:00 AM EST  - JUNOSe 3.4
    DESCRIPTION
        "Added support for connection admission control (CAC)."
    REVISION    "200112141804Z"  -- 14-Dec-01 01:04 PM EST  - JUNOSe 3.3
    DESCRIPTION
        "Added support from ATM traffic shaping."
    REVISION    "200111261639Z"  -- 26-Nov-01 11:39 AM EST  - JUNOSe 3.2
    DESCRIPTION
        "Added support for NBMA map lists.
         Added support for ATM ping.
         Changed juniAtmSubIfVccVcd and juniAtmIfIlmiVcd ranges to
         (0..2147483647).
         Added range to juniAtmIfCapabilityMaxVcd.
         Added rtVbr service catagory to juniAtmSubIfVccTable.
         Added support for OAM cell filter.
         Added PVC counter for reveived unknown protocol."
    REVISION    "200011271951Z"  -- 27-Nov-00 02:51 PM EST  - JUNOSe 3.0
    DESCRIPTION
        "Added autoconfig value for juniAtmSubIfVccType.
         Added in/out summary cell counters.
         Added juniVpTunnelServiceCategory to juniAtmVpTunnelTable.
         Added support for atm interface capability traversal."
    REVISION    "200008020000Z"  -- 02-Aug-00               - JUNOSe 2.3
    DESCRIPTION
        "Added the juniAtmCircuitOamTable."
    REVISION    "200005120000Z"  -- 12-May-00               - JUNOSe 2.0
    DESCRIPTION
        "Added the juniAtmVpTunnelTable."
    REVISION    "200001130000Z"  -- 13-Jan-00               - JUNOSe 1.3
    DESCRIPTION
        "Added the juniAtmPvcStatisticsTable."
    REVISION      "9908040000Z"  -- 04-Aug-99               - JUNOSe 1.1
    DESCRIPTION
        "Initial version of this MIB module."
    ::= { juniMibs 8 }


-- +++++++++++++++++++++++++++++++++++++++++++++++++++++++++++++++++++++++++++++
-- Textual conventions
-- +++++++++++++++++++++++++++++++++++++++++++++++++++++++++++++++++++++++++++++
JuniAtmNbmaMapName  ::= TEXTUAL-CONVENTION
    DISPLAY-HINT "32a"
    STATUS      current
    DESCRIPTION
        "An administratively assigned map name.  Represents textual information
        taken from the NVT ASCII character set.  The name must be unique per
        system."
    REFERENCE
        "RFC 854: NVT ASCII character set.  See SNMPv2-TC.DisplayString
        DESCRIPTION for a summary."
    SYNTAX      OCTET STRING (SIZE(1..32))

JuniAtmNbmaMapNameOrNull  ::= TEXTUAL-CONVENTION
    DISPLAY-HINT "32a"
    STATUS      current
    DESCRIPTION
        "An administratively assigned map name.  Represents textual information
        taken from the NVT ASCII character set.  The name must be unique per
        system.

        Differs from JuniAtmNbmaMapName in that it permits a zero-length
        string."
    REFERENCE
        "RFC 854: NVT ASCII character set.  See SNMPv2-TC.DisplayString
        DESCRIPTION for a summary."
    SYNTAX      OCTET STRING (SIZE(0..32))

JuniAtmLocationType  ::= TEXTUAL-CONVENTION
    STATUS      obsolete
    DESCRIPTION
        "Obsolete description of the platform-dependent interpretation of a
        JuniAtmLocationValue object.  This textual convention has been relpaced
        by Juniper-TC.JuniInterfaceLocationType."
    SYNTAX      INTEGER {
                    unknown(0),
                    slotPort(1) }

JuniAtmLocationValue  ::= TEXTUAL-CONVENTION
    STATUS      obsolete
    DESCRIPTION
        "Obsolete value of a platform-dependent interface location, represented
        as an OCTET STRING.  A corresponding JuniAtmLocationType object
        identified the mapping of octets to location elements, e.g. 'slot.port'.
        This textual convention has been replaced by
        Juniper-TC.JuniInterfaceLocationValue."
    SYNTAX      OCTET STRING (SIZE(1..16))


-- +++++++++++++++++++++++++++++++++++++++++++++++++++++++++++++++++++++++++++++
-- Managed objects
-- +++++++++++++++++++++++++++++++++++++++++++++++++++++++++++++++++++++++++++++
juniAtmObjects     OBJECT IDENTIFIER ::= { juniAtmMIB 1 }

--
-- This MIB contains managed objects for each of three interface layers:  ATM;
-- AAL5; and ATM Subinterface.  For each of these layers, management objects are
-- provided to query for an available interface index, and to create/delete
-- interfaces of that type.  Creating/deleting these interface types using this
-- MIB has the side effect of creating/deleting corresponding entries in the
-- Interface MIB ifTable/ifXTable, and in the Juniper Enterprise Interface MIB
-- juniIfTable.
--
juniAtmIfLayer        OBJECT IDENTIFIER ::= { juniAtmObjects 1 }
juniAtmAal5IfLayer    OBJECT IDENTIFIER ::= { juniAtmObjects 2 }
juniAtmSubIfLayer     OBJECT IDENTIFIER ::= { juniAtmObjects 3 }
juniAtmNbma           OBJECT IDENTIFIER ::= { juniAtmObjects 4 }
juniAtmPing           OBJECT IDENTIFIER ::= { juniAtmObjects 5 }
juniAtmLocation       OBJECT IDENTIFIER ::= { juniAtmObjects 6 }


-- /////////////////////////////////////////////////////////////////////////////
--
-- ATM LAYER
--
-- /////////////////////////////////////////////////////////////////////////////
--
-- IfIndex selection for creating new ATM interfaces
--
juniAtmNextIfIndex OBJECT-TYPE
    SYNTAX      JuniNextIfIndex
    MAX-ACCESS  read-only
    STATUS      current
    DESCRIPTION
        "Coordinate ifIndex value allocation for entries in juniAtmIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { juniAtmIfLayer 1 }

--
-- The ATM Interface Table
--
juniAtmIfTable OBJECT-TYPE
    SYNTAX      SEQUENCE OF JuniAtmIfEntry
    MAX-ACCESS  not-accessible
    STATUS      current
    DESCRIPTION
        "This table contains entries for ATM interfaces present in the system."
    ::= { juniAtmIfLayer 2 }

juniAtmIfEntry OBJECT-TYPE
    SYNTAX      JuniAtmIfEntry
    MAX-ACCESS  not-accessible
    STATUS      current
    DESCRIPTION
        "Each entry describes the characteristics of an ATM interface.
        Creating/deleting entries in this table causes corresponding entries for
        be created/deleted in ifTable/ifXTable/juniIfTable."
    INDEX     { juniAtmIfIndex }
    ::= { juniAtmIfTable 1 }

JuniAtmIfEntry ::= SEQUENCE {
    juniAtmIfIndex                       InterfaceIndex,
    juniAtmIfRowStatus                   RowStatus,
    juniAtmIfLowerIfIndex                InterfaceIndexOrZero,
    juniAtmIfIlmiVpi                     AtmVpIdentifier,
    juniAtmIfIlmiVci                     AtmVcIdentifier,
    juniAtmIfIlmiVcd                     Integer32,
    juniAtmIfIlmiPollFrequency           Integer32,
    juniAtmIfIlmiAdminState              INTEGER,
    juniAtmIfUniVersion                  INTEGER,
    juniAtmIfOamCellRxAdminState         INTEGER,
    juniAtmIfInCells                     Counter64,
    juniAtmIfOutCells                    Counter64,
    juniAtmIfVcCount                     Integer32,
    juniAtmIfMapGroup                    JuniAtmNbmaMapNameOrNull,
    juniAtmIfCacAdminState               JuniEnable,
    juniAtmIfCacUbrWeight                Integer32,
    juniAtmIfCacSubscriptionBandwidth    Integer32,
    juniAtmIfCacAvailableBandwidth       Integer32,
    juniAtmIfCacAvailableBandwidthRx     Integer32,
    juniAtmIfE164Autoconversion          INTEGER,
    juniAtmIfE164Gateway                 INTEGER,
    juniAtmIfE164OneToOneAddrTrans       INTEGER,
    juniAtmIfOamCellFilter               INTEGER,
    juniAtmIfCacUsedBandwidthUpper       Unsigned32,
    juniAtmIfCacUsedBandwidthLower       Unsigned32 }

juniAtmIfIndex OBJECT-TYPE
    SYNTAX      InterfaceIndex
    MAX-ACCESS  not-accessible
    STATUS      current
    DESCRIPTION
        "The ifIndex of the ATM interface.  When creating entries in this table,
        suitable values for this object are determined by reading
        juniAtmNextIfIndex."
    ::= { juniAtmIfEntry 1 }

juniAtmIfRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            juniAtmIfRowStatus
            juniAtmIfLowerIfIndex

        In addition, when creating an entry the following condition must hold:
            A value for juniAtmIfIndex must have been determined previously, by
            reading juniAtmNextIfIndex.

        A corresponding entry in ifTable/ifXTable/juniIfTable is created or
        destroyed as a result of creating/destroying an entry in this table."
    ::= { juniAtmIfEntry 2 }

juniAtmIfLowerIfIndex OBJECT-TYPE
    SYNTAX      InterfaceIndexOrZero
    MAX-ACCESS  read-create
    STATUS      current
    DESCRIPTION
        "The ifIndex of an interface over which this ATM interface is to be
        layered.  A value of zero indicates no layering.  An implementation may
        choose to require that a nonzero value be configured at entry creation."
    ::= { juniAtmIfEntry 3 }

juniAtmIfIlmiVpi OBJECT-TYPE
    SYNTAX      AtmVpIdentifier
    MAX-ACCESS  read-create
    STATUS      current
    DESCRIPTION
        "The VPI of the ILMI of a major ATM interface."
    DEFVAL    { 0 }
    ::= { juniAtmIfEntry 4 }

juniAtmIfIlmiVci OBJECT-TYPE
    SYNTAX      AtmVcIdentifier
    MAX-ACCESS  read-create
    STATUS      current
    DESCRIPTION
        "The VCI of the ILMI of a major ATM interface."
    DEFVAL    { 16 }
    ::= { juniAtmIfEntry 5 }

juniAtmIfIlmiVcd OBJECT-TYPE
    SYNTAX      Integer32 (0..2147483647)
    MAX-ACCESS  read-create
    STATUS      current
    DESCRIPTION
        "An integer identifier for the ILMI, used in conjunction with the
        command-line interface.

        The value must be unique among VCs configured on the same ATM
        interface."
    DEFVAL    { 0 }
    ::= { juniAtmIfEntry 6 }

juniAtmIfIlmiPollFrequency OBJECT-TYPE
    SYNTAX      Integer32 (0..65535)
    UNITS       "seconds"
    MAX-ACCESS  read-create
    STATUS      current
    DESCRIPTION
        "The amount of time in seconds between successive transmissions of ILMI
        messages on this interface for the purpose of detecting loss of ILMI
        connectivity.  The distinguished value zero disables ILMI connectivity
        procedures on this interface."
    ::= { juniAtmIfEntry 7 }

juniAtmIfIlmiAdminState OBJECT-TYPE
    SYNTAX      INTEGER {
                    disabled(0),
                    enabled(1) }
    MAX-ACCESS  read-create
    STATUS      current
    DESCRIPTION
        "The administrative status of ILMI in the ATM interface."
    ::= { juniAtmIfEntry 8 }

juniAtmIfUniVersion OBJECT-TYPE
    SYNTAX      INTEGER {
                    uniVersionAutoConfig(0),
                    version3Dot0(1),
                    version3Dot1(2),
                    version4Dot0(3) }
    MAX-ACCESS  read-create
    STATUS      current
    DESCRIPTION
        "Use to specify the User Network Interface (UNI) the router should use
        when ILMI link auto determination is unsuccesful or ILMI is disabled."
    ::= { juniAtmIfEntry 9 }

juniAtmIfOamCellRxAdminState OBJECT-TYPE
    SYNTAX      INTEGER {
                    oamCellAdminStateDisabled(0),
                    oamCellAdminStateEnabled(1) }
    MAX-ACCESS  read-create
    STATUS      current
    DESCRIPTION
        "Use to specify the OAM Cell Receive Administrative state on this
        interface."
    DEFVAL { oamCellAdminStateEnabled }
    ::= { juniAtmIfEntry 10 }

juniAtmIfInCells OBJECT-TYPE
    SYNTAX      Counter64
    MAX-ACCESS  read-only
    STATUS      current
    DESCRIPTION
        "The total number of cells received on this major interface."
    ::= { juniAtmIfEntry 11 }

juniAtmIfOutCells OBJECT-TYPE
    SYNTAX      Counter64
    MAX-ACCESS  read-only
    STATUS      current
    DESCRIPTION
        "The total number of cells transmitted on this major interface."
    ::= { juniAtmIfEntry 12 }

juniAtmIfVcCount  OBJECT-TYPE
    SYNTAX      Integer32 (0..268431360)
    MAX-ACCESS  read-only
    STATUS      current
    DESCRIPTION
        "The total number of circuits configured on this interface."
    ::= { juniAtmIfEntry 13 }

juniAtmIfMapGroup OBJECT-TYPE
    SYNTAX      JuniAtmNbmaMapNameOrNull
    MAX-ACCESS  read-create
    STATUS      current
    DESCRIPTION
        "The NBMA map group this interface is associated with."
    DEFVAL    { "" }
    ::= { juniAtmIfEntry 14 }

juniAtmIfCacAdminState OBJECT-TYPE
    SYNTAX      JuniEnable
    MAX-ACCESS  read-create
    STATUS      current
    DESCRIPTION
        "The administrative staus of CAC on this ATM major interface."
    DEFVAL    { disable }
    ::= { juniAtmIfEntry 15 }

juniAtmIfCacUbrWeight OBJECT-TYPE
    SYNTAX      Integer32 (0..2147483647)
    UNITS       "kbps"
    MAX-ACCESS  read-create
    STATUS      current
    DESCRIPTION
        "The bandwidth associated with every UBR and UBR with PCR connection
        configured on the ATM major interface.  This value is used for CAC
        computation.  The units are kilo-bits per second (kbps)."
    DEFVAL    { 0 }
    ::= { juniAtmIfEntry 16 }

juniAtmIfCacSubscriptionBandwidth OBJECT-TYPE
    SYNTAX      Integer32 (0..2147483647)
    UNITS       "kbps"
    MAX-ACCESS  read-create
    STATUS      current
    DESCRIPTION
        "The subscribed bandwidth of the ATM major interface.  If this value is
        not specified or set to 0, the effective port bandwidth is used.  When a
        Get operation is performed the current effective bandwidth is returned.
        The units are kilo-bits per second (kbps)."
    DEFVAL    { 0 }
    ::= { juniAtmIfEntry 17 }

juniAtmIfCacAvailableBandwidth OBJECT-TYPE
    SYNTAX      Integer32 (0..2147483647)
    UNITS       "kbps"
    MAX-ACCESS  read-only
    STATUS      current
    DESCRIPTION
        "The available bandwidth in Tx direction of the ATM major interface.  As
        connections are added or deleted on the interface, this value is
        updated.  The units are kilo-bits per second (kbps)."
    ::= { juniAtmIfEntry 18 }

juniAtmIfCacAvailableBandwidthRx OBJECT-TYPE
    SYNTAX      Integer32 (0..2147483647)
    UNITS       "kbps"
    MAX-ACCESS  read-only
    STATUS      deprecated
    DESCRIPTION
        "The available bandwidth in Rx direction of the ATM major interface.  As
        connections are added or deleted on the interface, this value is
        updated.  The units are kilo-bits per second (kbps)."
    ::= { juniAtmIfEntry 19 }

juniAtmIfE164Autoconversion OBJECT-TYPE
    SYNTAX      INTEGER {
                    disabled(0),
                    enabled(1) }
    MAX-ACCESS  read-create
    STATUS      deprecated
    DESCRIPTION
        "The status of E164 autoconversion feature in the ATM interface."
    ::= { juniAtmIfEntry 20 }

juniAtmIfE164Gateway OBJECT-TYPE
    SYNTAX      INTEGER {
                    disabled(0),
                    enabled(1) }
    MAX-ACCESS  read-create
    STATUS      deprecated
    DESCRIPTION
        "The status of E164 gateway feature in the ATM interface."
    ::= { juniAtmIfEntry 21 }

juniAtmIfE164OneToOneAddrTrans OBJECT-TYPE
    SYNTAX      INTEGER {
                    disabled(0),
                    enabled(1) }
    MAX-ACCESS  read-create
    STATUS      deprecated
    DESCRIPTION
        "The status of E164 one-to-one address translation feature in the ATM
        interface."
    ::= { juniAtmIfEntry 22 }

juniAtmIfOamCellFilter OBJECT-TYPE
    SYNTAX      INTEGER {
                    oamCellFilterAll(0),
                    oamCellFilterAlarm(1) }
    MAX-ACCESS  read-create
    STATUS      current
    DESCRIPTION
        "The type of OAM cells to discard when juniAtmIfOamCellRxAdminState is
        set to oamCellAdminStateDisabled.  The value oamCellFilterAlarm discards
        received OAM AIS and RDI cells.  The value oamCellFilterAll discards all
        received OAM cells.  Note that when juniAtmIfOamCellRxAdminState is set
        to oamCellAdminStateEnabled, this object has no effect."
    DEFVAL    { oamCellFilterAll }
    ::= { juniAtmIfEntry 23 }

juniAtmIfCacUsedBandwidthUpper OBJECT-TYPE
    SYNTAX       Unsigned32
    MAX-ACCESS   read-only
    STATUS       current
    DESCRIPTION
        "The most significant 32 bits of the CAC used bandwidth on the ATM major
        interface.  The least significant 32 bits of the CAC used bandwidth are
        specified by juniAtmIfCacUsedBandwidthLower."
    ::= { juniAtmIfEntry 24 }

juniAtmIfCacUsedBandwidthLower OBJECT-TYPE
    SYNTAX       Unsigned32
    MAX-ACCESS   read-only
    STATUS       current
    DESCRIPTION
        "The least significant 32 bits of the CAC used bandwidth on the ATM
        major interface.  The most significant 32 bits of the CAC used bandwidth
        are specified by juniAtmIfCacUsedBandwidthUpper."
    ::= { juniAtmIfEntry 25 }


--
-- The ATM VPI/VCI Statistics Table
--
juniAtmPvcStatisticsTable OBJECT-TYPE
    SYNTAX      SEQUENCE OF JuniAtmPvcStatisticsEntry
    MAX-ACCESS  not-accessible
    STATUS      current
    DESCRIPTION
        "This table contains statistics for PVC entries."
    ::= { juniAtmIfLayer 3 }

juniAtmPvcStatisticsEntry OBJECT-TYPE
    SYNTAX      JuniAtmPvcStatisticsEntry
    MAX-ACCESS  not-accessible
    STATUS      current
    DESCRIPTION
        "Each entry provides statistics on an ATM PVC."
    INDEX     { juniAtmPvcStatsIfIndex,
                juniAtmPvcStatsVpi,
                juniAtmPvcStatsVci }
    ::= { juniAtmPvcStatisticsTable 1 }

JuniAtmPvcStatisticsEntry ::= SEQUENCE {
    juniAtmPvcStatsIfIndex                       InterfaceIndex,
    juniAtmPvcStatsVpi                           AtmVpIdentifier,
    juniAtmPvcStatsVci                           AtmVcIdentifier,
    juniAtmPvcStatsInCells                       Counter64,
    juniAtmPvcStatsInCellOctets                  Counter64,
    juniAtmPvcStatsInPackets                     Counter64,
    juniAtmPvcStatsInPacketOctets                Counter64,
    juniAtmPvcStatsOutCells                      Counter64,
    juniAtmPvcStatsOutCellOctets                 Counter64,
    juniAtmPvcStatsOutPackets                    Counter64,
    juniAtmPvcStatsOutPacketOctets               Counter64,
    juniAtmPvcStatsInCellErrors                  Counter32,
    juniAtmPvcStatsinPacketErrors                Counter32,
    juniAtmPvcStatsOutCellErrors                 Counter32,
    juniAtmPvcStatsOutPacketErrors               Counter32,
    juniAtmPvcStatsInPacketDiscards              Counter32,
    juniAtmPvcStatsInPacketOctetDiscards         Counter32,
    juniAtmPvcStatsInPacketUnknownProtocol       Counter32 }

juniAtmPvcStatsIfIndex OBJECT-TYPE
    SYNTAX      InterfaceIndex
    MAX-ACCESS  not-accessible
    STATUS      current
    DESCRIPTION
        "The ifIndex of the ATM interface."
    ::= { juniAtmPvcStatisticsEntry 1 }

juniAtmPvcStatsVpi OBJECT-TYPE
    SYNTAX      AtmVpIdentifier
    MAX-ACCESS  not-accessible
    STATUS      current
    DESCRIPTION
        "The VPI of the ATM VCC used by this ATM interface and PVC."
    ::= { juniAtmPvcStatisticsEntry 2 }

juniAtmPvcStatsVci OBJECT-TYPE
    SYNTAX      AtmVcIdentifier
    MAX-ACCESS  not-accessible
    STATUS      current
    DESCRIPTION
        "The VCI of the ATM VCC used by this ATM interface and PVC."
    ::= { juniAtmPvcStatisticsEntry 3 }

juniAtmPvcStatsInCells OBJECT-TYPE
    SYNTAX      Counter64
    MAX-ACCESS  read-only
    STATUS      current
    DESCRIPTION
        "Received cells."
    ::= { juniAtmPvcStatisticsEntry 4 }

juniAtmPvcStatsInCellOctets OBJECT-TYPE
    SYNTAX      Counter64
    MAX-ACCESS  read-only
    STATUS      current
    DESCRIPTION
        "Received cells octets."
    ::= { juniAtmPvcStatisticsEntry 5 }

juniAtmPvcStatsInPackets OBJECT-TYPE
    SYNTAX      Counter64
    MAX-ACCESS  read-only
    STATUS      current
    DESCRIPTION
        "Received AAL PDUs."
    ::= { juniAtmPvcStatisticsEntry 6 }

juniAtmPvcStatsInPacketOctets OBJECT-TYPE
    SYNTAX      Counter64
    MAX-ACCESS  read-only
    STATUS      current
    DESCRIPTION
        "Received AAL PDU octets."
    ::= { juniAtmPvcStatisticsEntry 7 }

juniAtmPvcStatsOutCells OBJECT-TYPE
    SYNTAX      Counter64
    MAX-ACCESS  read-only
    STATUS      current
    DESCRIPTION
        "Transmitted cells."
    ::= { juniAtmPvcStatisticsEntry 8 }

juniAtmPvcStatsOutCellOctets OBJECT-TYPE
    SYNTAX      Counter64
    MAX-ACCESS  read-only
    STATUS      current
    DESCRIPTION
        "Transmitted cell octets."
    ::= { juniAtmPvcStatisticsEntry 9 }

juniAtmPvcStatsOutPackets OBJECT-TYPE
    SYNTAX      Counter64
    MAX-ACCESS  read-only
    STATUS      current
    DESCRIPTION
        "Transmitted AAL PDUs."
    ::= { juniAtmPvcStatisticsEntry 10 }

juniAtmPvcStatsOutPacketOctets OBJECT-TYPE
    SYNTAX      Counter64
    MAX-ACCESS  read-only
    STATUS      current
    DESCRIPTION
        "Transmitted AAL PDU octets."
    ::= { juniAtmPvcStatisticsEntry 11 }

juniAtmPvcStatsInCellErrors OBJECT-TYPE
    SYNTAX      Counter32
    MAX-ACCESS  read-only
    STATUS      current
    DESCRIPTION
        "Received cells dropped due to errors."
    ::= { juniAtmPvcStatisticsEntry 12 }

juniAtmPvcStatsinPacketErrors OBJECT-TYPE
    SYNTAX      Counter32
    MAX-ACCESS  read-only
    STATUS      current
    DESCRIPTION
        "Received packets dropped due to errors."
    ::= { juniAtmPvcStatisticsEntry 13 }

juniAtmPvcStatsOutCellErrors OBJECT-TYPE
    SYNTAX      Counter32
    MAX-ACCESS  read-only
    STATUS      current
    DESCRIPTION
        "Cells not transmitted due to errors."
    ::= { juniAtmPvcStatisticsEntry 14 }

juniAtmPvcStatsOutPacketErrors OBJECT-TYPE
    SYNTAX      Counter32
    MAX-ACCESS  read-only
    STATUS      current
    DESCRIPTION
        "Packets not transmitted due to errors."
    ::= { juniAtmPvcStatisticsEntry 15 }

juniAtmPvcStatsInPacketDiscards OBJECT-TYPE
    SYNTAX      Counter32
    MAX-ACCESS  read-only
    STATUS      current
    DESCRIPTION
        "Received packets w/o errors discarded."
    ::= { juniAtmPvcStatisticsEntry 16 }

juniAtmPvcStatsInPacketOctetDiscards OBJECT-TYPE
    SYNTAX      Counter32
    MAX-ACCESS  read-only
    STATUS      current
    DESCRIPTION
        "Received bytes w/o errors discarded."
    ::= { juniAtmPvcStatisticsEntry 17 }

juniAtmPvcStatsInPacketUnknownProtocol OBJECT-TYPE
    SYNTAX      Counter32
    MAX-ACCESS  read-only
    STATUS      current
    DESCRIPTION
        "Received packets that are discarded because the interface can not
        discern or is not configured to support this protocol."
    ::= { juniAtmPvcStatisticsEntry 18 }

--
-- The ATM Virtual Path Tunnel Table
--
juniAtmVpTunnelTable OBJECT-TYPE
    SYNTAX      SEQUENCE OF JuniAtmVpTunnelEntry
    MAX-ACCESS  not-accessible
    STATUS      current
    DESCRIPTION
        "This table contains entries for ATM VP Tunnels present in the system."
    ::= { juniAtmIfLayer 4 }

juniAtmVpTunnelEntry OBJECT-TYPE
    SYNTAX      JuniAtmVpTunnelEntry
    MAX-ACCESS  not-accessible
    STATUS      current
    DESCRIPTION
        "Each entry describes the characteristics of an ATM VP Tunnel."
    INDEX     { juniAtmVpTunnelIfIndex,
                juniAtmVpTunnelVpi }
    ::= { juniAtmVpTunnelTable 1 }

JuniAtmVpTunnelEntry ::= SEQUENCE {
    juniAtmVpTunnelIfIndex           InterfaceIndex,
    juniAtmVpTunnelVpi               AtmVpIdentifier,
    juniAtmVpTunnelKbps              Integer32,
    juniAtmVpTunnelRowStatus         RowStatus,
    juniAtmVpTunnelServiceCategory   INTEGER }

juniAtmVpTunnelIfIndex OBJECT-TYPE
    SYNTAX      InterfaceIndex
    MAX-ACCESS  not-accessible
    STATUS      current
    DESCRIPTION
        "The ifIndex of the ATM interface.  The value of this object is the same
        as the juniAtmIfIndex object in the juniAtmIfTable.

        Entries in this table cannot be created unless the underlying ATM
        interface entry is created first in the juniAtmIfTable."
    ::= { juniAtmVpTunnelEntry 1 }

juniAtmVpTunnelVpi OBJECT-TYPE
    SYNTAX      AtmVpIdentifier
    MAX-ACCESS  not-accessible
    STATUS      current
    DESCRIPTION
        "The VPI value for this VP tunnel entry."
    ::= { juniAtmVpTunnelEntry 2 }

juniAtmVpTunnelKbps OBJECT-TYPE
    SYNTAX      Integer32 (0..2147483647)
    UNITS       "kbps"
    MAX-ACCESS  read-create
    STATUS      current
    DESCRIPTION
        "The tunnel rate in kilobits per second (kbps) for this entry."
    ::= { juniAtmVpTunnelEntry 3 }

juniAtmVpTunnelRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            juniAtmVpTunnelRowStatus
            juniAtmVpTunnelKbps

        In addition, when creating an entry the following condition must hold:
            A correponding juniAtmVpTunnelIfIndex value must have been created
            in the juniAtmIfTable previously."
    ::= { juniAtmVpTunnelEntry 4 }

juniAtmVpTunnelServiceCategory OBJECT-TYPE
    SYNTAX      INTEGER {
                    nrtVbr(1),
                    cbr(2) }
    MAX-ACCESS  read-create
    STATUS      current
    DESCRIPTION
        "The ATM service category for the tunnel."
    ::= { juniAtmVpTunnelEntry 5 }


--
-- The ATM Interface Capability Table
--
juniAtmIfCapabilityTable OBJECT-TYPE
    SYNTAX      SEQUENCE OF JuniAtmIfCapabilityEntry
    MAX-ACCESS  not-accessible
    STATUS      current
    DESCRIPTION
        "This table contains entries for ATM interfaces present in the system."
    ::= { juniAtmIfLayer 5 }

juniAtmIfCapabilityEntry OBJECT-TYPE
    SYNTAX      JuniAtmIfCapabilityEntry
    MAX-ACCESS  not-accessible
    STATUS      current
    DESCRIPTION
        "Each entry describes the capabilities of an ATM interface.  A
        management client can use this table to determine differences in the
        configurable level of support across entries in this table."
    INDEX     { juniAtmIfCapabilityIndex }
    ::= { juniAtmIfCapabilityTable 1 }

JuniAtmIfCapabilityEntry ::= SEQUENCE {
    juniAtmIfCapabilityIndex             InterfaceIndex,
    juniAtmIfCapabilityTrafficShaping    TruthValue,
    juniAtmIfCapabilityOam               TruthValue,
    juniAtmIfCapabilityDefaultVcPerVp    Integer32,
    juniAtmIfCapabilityNumVpiVciBits     Integer32,
    juniAtmIfCapabilityMaxVcd            Integer32,
    juniAtmIfCapabilityMaxVpi            AtmVpIdentifier,
    juniAtmIfCapabilityMaxVci            AtmVcIdentifier,
    juniAtmIfCapabilityOamCellFilter     TruthValue }

juniAtmIfCapabilityIndex OBJECT-TYPE
    SYNTAX      InterfaceIndex
    MAX-ACCESS  not-accessible
    STATUS      current
    DESCRIPTION
        "The ifIndex of the ATM interface.  The value of this object is the same
        as juniAtmIfIndex in the juniAtmIfTable."
    ::= { juniAtmIfCapabilityEntry 1 }

juniAtmIfCapabilityTrafficShaping OBJECT-TYPE
    SYNTAX      TruthValue
    MAX-ACCESS  read-only
    STATUS      current
    DESCRIPTION
        "Indicates whether traffic shaping is supported on this interface;
        true(1) indicates that it is, false(2) indicates that it is not."
    ::= { juniAtmIfCapabilityEntry 2 }

juniAtmIfCapabilityOam OBJECT-TYPE
    SYNTAX      TruthValue
    MAX-ACCESS  read-only
    STATUS      current
    DESCRIPTION
        "Indicates whether OAM is supported on this interface; true(1) indicates
        that it is, false(2) indicates that it is not."
    ::= { juniAtmIfCapabilityEntry 3 }

juniAtmIfCapabilityDefaultVcPerVp OBJECT-TYPE
    SYNTAX      Integer32 (0..65536)
    MAX-ACCESS  read-only
    STATUS      current
    DESCRIPTION
        "The default number of VCs per VP for this interface."
    ::= { juniAtmIfCapabilityEntry 4 }

juniAtmIfCapabilityNumVpiVciBits OBJECT-TYPE
    SYNTAX      Integer32 (8..28)
    MAX-ACCESS  read-only
    STATUS      current
    DESCRIPTION
        "The total range of bits used for constructing VPI/VCI identifiers for
        this interface."
    ::= { juniAtmIfCapabilityEntry 5 }

juniAtmIfCapabilityMaxVcd OBJECT-TYPE
    SYNTAX      Integer32 (0..2147483647)
    MAX-ACCESS  read-only
    STATUS      current
    DESCRIPTION
       "The maximum configurable value for a VCD on this interface."
    ::= { juniAtmIfCapabilityEntry 6 }

juniAtmIfCapabilityMaxVpi OBJECT-TYPE
    SYNTAX      AtmVpIdentifier
    MAX-ACCESS  read-only
    STATUS      current
    DESCRIPTION
        "The maximum configurable value for a VPI on this interface."
    ::= { juniAtmIfCapabilityEntry 7 }

juniAtmIfCapabilityMaxVci OBJECT-TYPE
    SYNTAX      AtmVcIdentifier
    MAX-ACCESS  read-only
    STATUS      current
    DESCRIPTION
        "The maximum configurable value for a VCI on this interface."
    ::= { juniAtmIfCapabilityEntry 8 }

juniAtmIfCapabilityOamCellFilter OBJECT-TYPE
    SYNTAX      TruthValue
    MAX-ACCESS  read-only
    STATUS      current
    DESCRIPTION
        "Indicates whether OAM cell filter is supported on this interface;
        true(1) indicates that it is, false(2) indicates that it is not."
    ::= { juniAtmIfCapabilityEntry 9 }


--
-- The juniAtmIfSvcSignallingTable extends the juniAtmIfTable for ATM switched
-- virtual connections (SVCs).
--
juniAtmIfSvcSignallingTable OBJECT-TYPE
    SYNTAX      SEQUENCE OF JuniAtmIfSvcSignallingEntry
    MAX-ACCESS  not-accessible
    STATUS      current
    DESCRIPTION
        "This table contains entries for extending the juniAtmIfTable for
        configuring signalling information for switched virtual connection
        (SVC)."
    ::= { juniAtmIfLayer 6 }

juniAtmIfSvcSignallingEntry OBJECT-TYPE
    SYNTAX      JuniAtmIfSvcSignallingEntry
    MAX-ACCESS  not-accessible
    STATUS      current
    DESCRIPTION
        "Each entry provides configuration parameters for ATM signalling on the
        interface."
    INDEX     { juniAtmIfIndex }
    ::= { juniAtmIfSvcSignallingTable 1 }

JuniAtmIfSvcSignallingEntry ::= SEQUENCE {
    juniAtmIfSvcSignallingVpi            AtmVpIdentifier,
    juniAtmIfSvcSignallingVci            AtmVcIdentifier,
    juniAtmIfSvcSignallingVcd            Integer32,
    juniAtmIfSvcSignallingAdminStatus    AtmVorXAdminStatus }

juniAtmIfSvcSignallingVpi OBJECT-TYPE
    SYNTAX      AtmVpIdentifier
    MAX-ACCESS  read-write
    STATUS      current
    DESCRIPTION
        "The VPI identifier of the ATM circuit used for signalling for this
        interface."
    DEFVAL    { 0 }
    ::= { juniAtmIfSvcSignallingEntry 1 }

juniAtmIfSvcSignallingVci OBJECT-TYPE
    SYNTAX      AtmVcIdentifier
    MAX-ACCESS  read-write
    STATUS      current
    DESCRIPTION
        "The VCI identifier of the ATM circuit used for signalling for this
        interface."
    DEFVAL    { 5 }
    ::= { juniAtmIfSvcSignallingEntry 2 }

juniAtmIfSvcSignallingVcd OBJECT-TYPE
    SYNTAX      Integer32 (0..2147483647)
    MAX-ACCESS  read-write
    STATUS      current
    DESCRIPTION
        "An integer identifier for the ATM circuit used for signalling on this
        interface."
    DEFVAL    { 0 }
    ::= { juniAtmIfSvcSignallingEntry 3 }

juniAtmIfSvcSignallingAdminStatus OBJECT-TYPE
    SYNTAX      AtmVorXAdminStatus
    MAX-ACCESS  read-write
    STATUS      current
    DESCRIPTION
        "The administrative status of signalling on the ATM interface."
    ::= { juniAtmIfSvcSignallingEntry 4 }


--
-- The juniAtmIfPnniRccTable extends the juniAtmIfTable for PNNI Routing
-- Control Channel
--
juniAtmIfPnniRccTable OBJECT-TYPE
    SYNTAX      SEQUENCE OF JuniAtmIfPnniRccEntry
    MAX-ACCESS  not-accessible
    STATUS      current
    DESCRIPTION
        "This table contains entries for extending the juniAtmIfTable for
        configuring PNNI RCC information."
    ::= { juniAtmIfLayer 7 }

juniAtmIfPnniRccEntry OBJECT-TYPE
    SYNTAX      JuniAtmIfPnniRccEntry
    MAX-ACCESS  not-accessible
    STATUS      current
    DESCRIPTION
        "Each entry provides configuration parameters for PNNI RCC on the
        interface."
    INDEX     { juniAtmIfIndex }
    ::= { juniAtmIfPnniRccTable 1 }

JuniAtmIfPnniRccEntry ::= SEQUENCE {
    juniAtmIfPnniRccVpi            AtmVpIdentifier,
    juniAtmIfPnniRccVci            AtmVcIdentifier,
    juniAtmIfPnniRccVcd            Integer32,
    juniAtmIfPnniRccAdminStatus    AtmVorXAdminStatus }

juniAtmIfPnniRccVpi OBJECT-TYPE
    SYNTAX      AtmVpIdentifier
    MAX-ACCESS  read-write
    STATUS      current
    DESCRIPTION
        "The VPI identifier of the ATM circuit used for PNNI RCC on this
        interface."
    DEFVAL    { 0 }
    ::= { juniAtmIfPnniRccEntry 1 }

juniAtmIfPnniRccVci OBJECT-TYPE
    SYNTAX      AtmVcIdentifier
    MAX-ACCESS  read-write
    STATUS      current
    DESCRIPTION
        "The VCI identifier of the ATM circuit used for PNNI RCC on this
        interface."
    DEFVAL    { 18 }
    ::= { juniAtmIfPnniRccEntry 2 }

juniAtmIfPnniRccVcd OBJECT-TYPE
    SYNTAX      Integer32 (0..2147483647)
    MAX-ACCESS  read-write
    STATUS      current
    DESCRIPTION
        "An integer identifier for the ATM circuit used for PNNI RCC on this
        interface."
    DEFVAL    { 0 }
    ::= { juniAtmIfPnniRccEntry 3 }

juniAtmIfPnniRccAdminStatus OBJECT-TYPE
    SYNTAX      AtmVorXAdminStatus
    MAX-ACCESS  read-write
    STATUS      current
    DESCRIPTION
        "The administrative status of PNNI on the ATM interface."
    ::= { juniAtmIfPnniRccEntry 4 }


--
-- The juniAtmOamF4FlowEndToEndConfigTable
--
juniAtmOamF4FlowEndToEndCfgTable OBJECT-TYPE
    SYNTAX      SEQUENCE OF JuniAtmOamF4FlowEndToEndCfgEntry
    MAX-ACCESS  not-accessible
    STATUS      current
    DESCRIPTION
        "This table contains entries for F4 OAM end-to-end flows configured."
    ::= { juniAtmIfLayer 8 }

juniAtmOamF4FlowEndToEndCfgEntry OBJECT-TYPE
    SYNTAX      JuniAtmOamF4FlowEndToEndCfgEntry
    MAX-ACCESS  not-accessible
    STATUS      current
    DESCRIPTION
        "Each entry provides configuration parameters for one F4 OAM end-to-end
        flow configured for each VPI."
    INDEX     { juniAtmOamF4FlowEndToEndIfIndex,
                juniAtmOamF4FlowEndToEndVpi }
    ::= { juniAtmOamF4FlowEndToEndCfgTable 1 }

JuniAtmOamF4FlowEndToEndCfgEntry ::= SEQUENCE {
    juniAtmOamF4FlowEndToEndIfIndex       InterfaceIndex,
    juniAtmOamF4FlowEndToEndVpi           Integer32,
    juniAtmOamF4FlowEndToEndLoopbackTimer Integer32,
    juniAtmOamF4FlowEndToEndCCSink        TruthValue,
    juniAtmOamF4FlowEndToEndCCSource      TruthValue,
    juniAtmOamF4FlowEndToEndRowStatus     RowStatus }

juniAtmOamF4FlowEndToEndIfIndex OBJECT-TYPE
    SYNTAX      InterfaceIndex
    MAX-ACCESS  not-accessible
    STATUS      current
    DESCRIPTION
        "The ifIndex of the ATM interface to configure the F4 OAM end-to-end
        flow."
    ::= { juniAtmOamF4FlowEndToEndCfgEntry 1 }

juniAtmOamF4FlowEndToEndVpi OBJECT-TYPE
    SYNTAX      Integer32 (0..255)
    MAX-ACCESS  not-accessible
    STATUS      current
    DESCRIPTION
        "Select the VPI for F4 OAM end-to-end flow configuration."
    ::= { juniAtmOamF4FlowEndToEndCfgEntry 2 }

juniAtmOamF4FlowEndToEndLoopbackTimer OBJECT-TYPE
    SYNTAX      Integer32 (-1..600)
    UNITS       "seconds"
    MAX-ACCESS  read-create
    STATUS      current
    DESCRIPTION
        "Configure the timer for sending the F4 flow end-to-end loopback OAM
        cells. Setting this value will enable sending the F4 end cells on the
        circuit.  It is not allowed to set the value to -1 and whenever it is
        read as -1 that means sending end loopback is not enabled.  Setting the
        loopback timer, other than -1, will enable sending the end cells."
    DEFVAL    { -1 }
    ::= { juniAtmOamF4FlowEndToEndCfgEntry 3 }

juniAtmOamF4FlowEndToEndCCSink OBJECT-TYPE
    SYNTAX      TruthValue
    MAX-ACCESS  read-create
    STATUS      current
    DESCRIPTION
        "Enable/Disable F4 flow end-to-end continuity check sink end point for
        this VP."
    DEFVAL    { false }
    ::= { juniAtmOamF4FlowEndToEndCfgEntry 4 }

juniAtmOamF4FlowEndToEndCCSource OBJECT-TYPE
    SYNTAX      TruthValue
    MAX-ACCESS  read-create
    STATUS      current
    DESCRIPTION
        "Enable/Disable F4 flow end-to-end continuity check source end point for
        this VP."
    DEFVAL    { false }
    ::= { juniAtmOamF4FlowEndToEndCfgEntry 5 }

juniAtmOamF4FlowEndToEndRowStatus OBJECT-TYPE
    SYNTAX      RowStatus
    MAX-ACCESS  read-create
    STATUS      current
    DESCRIPTION
        "Controls creation/deletion of entries in this table according to the
        RowStatus textual convention, constrained to support the following
        values only:
            createAndGo
            destroy

        To create/delete an entry in this table, the following entry objects
        MUST be explicitly configured:
            juniAtmOamF4FlowEndToEndRowStatus

        F4 OAM end loopback and CC tests are mutually exclusive, enabling one
        will disable the other automatically.  So, it is not allowed either at
        the circuit creation time or after the circuit creation to issue a
        request to enable end-to-end loopback and CC tests simultaneouly.
        Enabling/disabling CC sink and source is one time operation.  To
        re-enable either CC source and sink in way different to earlier, both
        has to be disabled from the previous."
    ::= { juniAtmOamF4FlowEndToEndCfgEntry 6 }


--
-- The juniAtmOamF4FlowSegmentConfigTable
--
juniAtmOamF4FlowSegmentCfgTable OBJECT-TYPE
    SYNTAX      SEQUENCE OF JuniAtmOamF4FlowSegmentCfgEntry
    MAX-ACCESS  not-accessible
    STATUS      current
    DESCRIPTION
        "This table contains entries for F4 OAM Segment flows configured."
    ::= { juniAtmIfLayer 9 }

juniAtmOamF4FlowSegmentCfgEntry OBJECT-TYPE
    SYNTAX      JuniAtmOamF4FlowSegmentCfgEntry
    MAX-ACCESS  not-accessible
    STATUS      current
    DESCRIPTION
        "Each entry provides configuration parameters for one F4 OAM Segment
        flow configured for each VPI."
    INDEX     { juniAtmOamF4FlowSegmentIfIndex,
                juniAtmOamF4FlowSegmentVpi }
    ::= { juniAtmOamF4FlowSegmentCfgTable 1 }

JuniAtmOamF4FlowSegmentCfgEntry ::= SEQUENCE {
    juniAtmOamF4FlowSegmentIfIndex       InterfaceIndex,
    juniAtmOamF4FlowSegmentVpi           Integer32,
    juniAtmOamF4FlowSegmentCCSink        TruthValue,
    juniAtmOamF4FlowSegmentCCSource      TruthValue,
    juniAtmOamF4FlowSegmentRowStatus     RowStatus }

juniAtmOamF4FlowSegmentIfIndex OBJECT-TYPE
    SYNTAX      InterfaceIndex
    MAX-ACCESS  not-accessible
    STATUS      current
    DESCRIPTION
        "The ifIndex of the ATM interface to configure the F4 OAM segment flow."
    ::= { juniAtmOamF4FlowSegmentCfgEntry 1 }

juniAtmOamF4FlowSegmentVpi OBJECT-TYPE
    SYNTAX      Integer32 (0..255)
    MAX-ACCESS  not-accessible
    STATUS      current
    DESCRIPTION
        "Select the VPI for F4 OAM segment flow configuration."
    ::= { juniAtmOamF4FlowSegmentCfgEntry 2 }

juniAtmOamF4FlowSegmentCCSink OBJECT-TYPE
    SYNTAX      TruthValue
    MAX-ACCESS  read-create
    STATUS      current
    DESCRIPTION
        "Enable/Disable F4 flow segment continuity check sink end point for
        this VP."
    DEFVAL    { false }
    ::= { juniAtmOamF4FlowSegmentCfgEntry 3 }

juniAtmOamF4FlowSegmentCCSource OBJECT-TYPE
    SYNTAX      TruthValue
    MAX-ACCESS  read-create
    STATUS      current
    DESCRIPTION
        "Enable/Disable F4 flow segment continuity check source end point for
        this VP."
    DEFVAL    { false }
    ::= { juniAtmOamF4FlowSegmentCfgEntry 4 }

juniAtmOamF4FlowSegmentRowStatus OBJECT-TYPE
    SYNTAX      RowStatus
    MAX-ACCESS  read-create
    STATUS      current
    DESCRIPTION
        "Controls creation/deletion of entries in this table according to the
        RowStatus textual convention, constrained to support the following
        values only:
            createAndGo
            destroy

        To create/delete an entry in this table, the following entry objects
        MUST be explicitly configured:
            juniAtmOamF4FlowSegmentRowStatus

        Enabling/disabling CC sink and source is one time operation.  To
        re-enable either CC source and sink in way different to earlier, both
        has to be disabled from the previous.  F4 OAM segment loopback test is
        not supported."
    ::= { juniAtmOamF4FlowSegmentCfgEntry 5 }


--
-- juniAtmVpDescrTable
--
juniAtmVpDescrTable OBJECT-TYPE
    SYNTAX      SEQUENCE OF JuniAtmVpDescrEntry
    MAX-ACCESS  not-accessible
    STATUS      current
    DESCRIPTION
        "This table contains entries for ATM VP Description present in the
        system.  The user can configure a description of up to 32 characters for
        every VP in the ATM interface.  A row exists for every VP on the ATM
        interface.  These rows get created as soon as the ATM major interface
        created."
    ::= { juniAtmIfLayer 10 }

juniAtmVpDescrEntry OBJECT-TYPE
    SYNTAX      JuniAtmVpDescrEntry
    MAX-ACCESS  not-accessible
    STATUS      current
    DESCRIPTION
        "Each entry contains the description of the VP."
    INDEX     { ifIndex,
                atmVplVpi }
    ::= { juniAtmVpDescrTable 1 }

JuniAtmVpDescrEntry ::= SEQUENCE {
    juniAtmVpDescription     SnmpAdminString }

juniAtmVpDescription OBJECT-TYPE
    SYNTAX      SnmpAdminString (SIZE(0..32))
    MAX-ACCESS  read-write
    STATUS      current
    DESCRIPTION
        "The description for this VP.  The default value of this object is null
        string."
    DEFVAL    { "" }
    ::= { juniAtmVpDescrEntry 1 }


--
-- The juniAtmF4FlowOamEndToEndStatsTable
--
juniAtmF4FlowOamEndToEndStatsTable OBJECT-TYPE
    SYNTAX      SEQUENCE OF JuniAtmF4FlowOamEndToEndStatsEntry
    MAX-ACCESS  not-accessible
    STATUS      current
    DESCRIPTION
        "This table contains entries for F4 flow EndToEnd OAM circuits stats."
    ::= { juniAtmIfLayer 11 }

juniAtmF4FlowOamEndToEndStatsEntry OBJECT-TYPE
    SYNTAX      JuniAtmF4FlowOamEndToEndStatsEntry
    MAX-ACCESS  not-accessible
    STATUS      current
    DESCRIPTION
        "Each entry provides stats for one F4 OAM circuit for each VPI."
    INDEX     { juniAtmOamF4FlowEndToEndIfIndex,
                juniAtmOamF4FlowEndToEndVpi }
    ::= { juniAtmF4FlowOamEndToEndStatsTable 1 }

JuniAtmF4FlowOamEndToEndStatsEntry ::= SEQUENCE {
    juniAtmF4FlowInOamEndAisCells             Counter32,
    juniAtmF4FlowInOamEndRdiCells             Counter32,
    juniAtmF4FlowInOamEndCCCells              Counter32,
    juniAtmF4FlowInOamEndCCActDeActCells      Counter32,
    juniAtmF4FlowInOamEndLoopbackCells        Counter32,
    juniAtmF4FlowOutEndRdiCells               Counter32,
    juniAtmF4FlowOutEndCCCells                Counter32,
    juniAtmF4FlowOutEndCCActDeActCells        Counter32,
    juniAtmF4FlowOutEndToEndLoopbackCells     Counter32,
    juniAtmF4FlowEndActualLoopbackFreq        Integer32,
    juniAtmF4FlowEndLastTimeChanged           TimeTicks,
    juniAtmF4FlowOamEndVpOperationState       INTEGER,
    juniAtmF4FlowOamEndVpAdminState           INTEGER,
    juniAtmF4FlowEndInOamCells                Counter32,
    juniAtmF4FlowEndOutOamCells               Counter32,
    juniAtmF4FlowEndInOamCellsDropped         Counter32 }

juniAtmF4FlowInOamEndAisCells OBJECT-TYPE
    SYNTAX      Counter32
    UNITS       "cells"
    MAX-ACCESS  read-only
    STATUS      current
    DESCRIPTION
        "Received end-to-end OAM F4 AIS cells."
    ::= { juniAtmF4FlowOamEndToEndStatsEntry 1 }

juniAtmF4FlowInOamEndRdiCells OBJECT-TYPE
    SYNTAX      Counter32
    UNITS       "cells"
    MAX-ACCESS  read-only
    STATUS      current
    DESCRIPTION
        "Received end-to-end OAM F4 RDI cells."
    ::= { juniAtmF4FlowOamEndToEndStatsEntry 2 }

juniAtmF4FlowInOamEndCCCells OBJECT-TYPE
    SYNTAX      Counter32
    UNITS       "cells"
    MAX-ACCESS  read-only
    STATUS      current
    DESCRIPTION
        "Received end-to-end OAM F4 CC cells."
    ::= { juniAtmF4FlowOamEndToEndStatsEntry 3 }

juniAtmF4FlowInOamEndCCActDeActCells OBJECT-TYPE
    SYNTAX      Counter32
    UNITS       "cells"
    MAX-ACCESS  read-only
    STATUS      current
    DESCRIPTION
        "Received end-to-end OAM F4 activation/de-activation cells."
    ::= { juniAtmF4FlowOamEndToEndStatsEntry 4 }

juniAtmF4FlowInOamEndLoopbackCells OBJECT-TYPE
    SYNTAX      Counter32
    UNITS       "cells"
    MAX-ACCESS  read-only
    STATUS      current
    DESCRIPTION
        "Received end-to-end F4 OAM loopback cells."
    ::= { juniAtmF4FlowOamEndToEndStatsEntry 5 }

juniAtmF4FlowOutEndRdiCells OBJECT-TYPE
    SYNTAX      Counter32
    UNITS       "cells"
    MAX-ACCESS  read-only
    STATUS      current
    DESCRIPTION
        "Transmitted end-to-end OAM F4 RDI cells."
    ::= { juniAtmF4FlowOamEndToEndStatsEntry 6 }

juniAtmF4FlowOutEndCCCells OBJECT-TYPE
    SYNTAX      Counter32
    UNITS       "cells"
    MAX-ACCESS  read-only
    STATUS      current
    DESCRIPTION
        "Transmitted end-to-end OAM F4 CC cells."
    ::= { juniAtmF4FlowOamEndToEndStatsEntry 7 }

juniAtmF4FlowOutEndCCActDeActCells OBJECT-TYPE
    SYNTAX      Counter32
    UNITS       "cells"
    MAX-ACCESS  read-only
    STATUS      current
    DESCRIPTION
        "Transmitted end-to-end OAM F4 activation/de-activation cells."
    ::= { juniAtmF4FlowOamEndToEndStatsEntry 8 }

juniAtmF4FlowOutEndToEndLoopbackCells OBJECT-TYPE
    SYNTAX      Counter32
    UNITS       "cells"
    MAX-ACCESS  read-only
    STATUS      current
    DESCRIPTION
        "Transmitted end-to-end OAM F4 loopback cells."
    ::= { juniAtmF4FlowOamEndToEndStatsEntry 9 }

juniAtmF4FlowEndActualLoopbackFreq OBJECT-TYPE
    SYNTAX      Integer32 (0..65535)
    UNITS       "seconds"
    MAX-ACCESS  read-only
    STATUS      current
    DESCRIPTION
        "Actual end-to-end loopback Frequecy calculated for OAM cells
        transmission."
    ::= { juniAtmF4FlowOamEndToEndStatsEntry 10 }

juniAtmF4FlowEndLastTimeChanged OBJECT-TYPE
    SYNTAX      TimeTicks
    MAX-ACCESS  read-only
    STATUS      current
    DESCRIPTION
        "Last time end-to-end F4 OAM flow got changed."
    ::= { juniAtmF4FlowOamEndToEndStatsEntry 11 }

juniAtmF4FlowOamEndVpOperationState OBJECT-TYPE
    SYNTAX      INTEGER {
                    vcAisState(0),
                    vcRdiState(1),
                    vcDownRetry(2),
                    vcUpRetry(3),
                    vcUp(4),
                    vcDown(5),
                    vcNotManaged(6),
                    vpAisState(7),
                    vpRdiState(8),
                    vcInVpRdiState(9),
                    vcInVpAisState(10),
                    vcSegmentAisState(11),
                    vcSegRdiState(12) }
    MAX-ACCESS  read-only
    STATUS      current
    DESCRIPTION
        "Represents the F4 end-to-end OAM flow VP operation states.  It can take
        one of the following operational state values:
            vcAisState        - AIS cell received or underlying physical layer
                                reporting transmission path AIS.
            vcRdiState        - RDI cell received.
            vcDownRetry       - OAM loopback failed, using retry frequency to
                                verify that the VC is really down.
            vcUpRetry         - OAM loopback successful, using retry frequency
                                to verify that the VC is really up.
            vcUp              - OAM loopback successful after up retry
                                verification.
            vcDown            - OAM loopback failed after down retry
                                verification.
            vcNotManaged      - No verification via loopback cells being
                                performed.
            vpAisState        - State when F4 AIS cell is received.
            vpRdiState        - State when F4 RDI cell is received.
            vcInVpRdiState    - The data vc is down as a result of VP failure
                                thorugh F4 Rdi oam cell.
            vcInVpAisState    - The data vc is down as a result of VP failure
                                through F4  Ais oam cell.
            vcSegmentAisState - Segment AIS cell received.
            vcSegRdiState     - Segment RDI cell received."
    ::= { juniAtmF4FlowOamEndToEndStatsEntry 12 }

juniAtmF4FlowOamEndVpAdminState OBJECT-TYPE
    SYNTAX      INTEGER {
                    down(0),
                    up(1) }
    MAX-ACCESS  read-only
    STATUS      current
    DESCRIPTION
         "End-to-end VP admin state."
    ::= { juniAtmF4FlowOamEndToEndStatsEntry 13 }

juniAtmF4FlowEndInOamCells OBJECT-TYPE
    SYNTAX      Counter32
    UNITS       "cells"
    MAX-ACCESS  read-only
    STATUS      current
    DESCRIPTION
        "Received end-to-end OAM F4 loopback cells."
    ::= { juniAtmF4FlowOamEndToEndStatsEntry 14 }

juniAtmF4FlowEndOutOamCells OBJECT-TYPE
    SYNTAX      Counter32
    UNITS       "cells"
    MAX-ACCESS  read-only
    STATUS      current
    DESCRIPTION
        "Transmitted end-to-end OAM F4 loopback cells."
    ::= { juniAtmF4FlowOamEndToEndStatsEntry 15 }

juniAtmF4FlowEndInOamCellsDropped OBJECT-TYPE
    SYNTAX      Counter32
    UNITS       "cells"
    MAX-ACCESS  read-only
    STATUS      current
    DESCRIPTION
        "Received end-to-end OAM cells that were dropped."
    ::= { juniAtmF4FlowOamEndToEndStatsEntry 16 }


--
-- The juniAtmF4FlowOamSegmentStatsTable
--
juniAtmF4FlowOamSegmentStatsTable OBJECT-TYPE
    SYNTAX      SEQUENCE OF JuniAtmF4FlowOamSegmentStatsEntry
    MAX-ACCESS  not-accessible
    STATUS      current
    DESCRIPTION
        "This table contains entries for F4 flow Segment OAM circuits stats."
    ::= { juniAtmIfLayer 12 }

juniAtmF4FlowOamSegmentStatsEntry OBJECT-TYPE
    SYNTAX      JuniAtmF4FlowOamSegmentStatsEntry
    MAX-ACCESS  not-accessible
    STATUS      current
    DESCRIPTION
        "Each entry provides stats for one F4 OAM circuit for each VPI."
    INDEX     { juniAtmOamF4FlowSegmentIfIndex,
                juniAtmOamF4FlowSegmentVpi }
    ::= { juniAtmF4FlowOamSegmentStatsTable 1 }

JuniAtmF4FlowOamSegmentStatsEntry ::= SEQUENCE {
    juniAtmF4FlowInOamSegmentAisCells             Counter32,
    juniAtmF4FlowInOamSegmentRdiCells             Counter32,
    juniAtmF4FlowInOamSegmentCCCells              Counter32,
    juniAtmF4FlowInOamSegmentCCActDeActCells      Counter32,
    juniAtmF4FlowInOamSegmentLoopbackCells        Counter32,
    juniAtmF4FlowOutSegmentRdiCells               Counter32,
    juniAtmF4FlowOutSegmentCCCells                Counter32,
    juniAtmF4FlowOutSegmentCCActDeActCells        Counter32,
    juniAtmF4FlowOutSegmentLoopbackCells          Counter32,
    juniAtmF4FlowSegmentLastTimeChanged           TimeTicks,
    juniAtmF4FlowOamSegmentVpOperationState       INTEGER,
    juniAtmF4FlowOamSegmentVpAdminState           INTEGER,
    juniAtmF4FlowSegmentInOamCells                Counter32,
    juniAtmF4FlowSegmentOutOamCells               Counter32,
    juniAtmF4FlowSegmentInOamCellsDropped         Counter32 }

juniAtmF4FlowInOamSegmentAisCells OBJECT-TYPE
    SYNTAX      Counter32
    UNITS       "cells"
    MAX-ACCESS  read-only
    STATUS      current
    DESCRIPTION
        "Received end-to-end OAM F4 AIS cells."
    ::= { juniAtmF4FlowOamSegmentStatsEntry 1 }

juniAtmF4FlowInOamSegmentRdiCells OBJECT-TYPE
    SYNTAX      Counter32
    UNITS       "cells"
    MAX-ACCESS  read-only
    STATUS      current
    DESCRIPTION
        "Received end-to-end OAM F4 RDI cells."
    ::= { juniAtmF4FlowOamSegmentStatsEntry 2 }

juniAtmF4FlowInOamSegmentCCCells OBJECT-TYPE
    SYNTAX      Counter32
    UNITS       "cells"
    MAX-ACCESS  read-only
    STATUS      current
    DESCRIPTION
        "Received end-to-end OAM F4 CC cells."
    ::= { juniAtmF4FlowOamSegmentStatsEntry 3 }

juniAtmF4FlowInOamSegmentCCActDeActCells OBJECT-TYPE
    SYNTAX      Counter32
    UNITS       "cells"
    MAX-ACCESS  read-only
    STATUS      current
    DESCRIPTION
        "Received end-to-end OAM F4 activation/de-activation cells."
    ::= { juniAtmF4FlowOamSegmentStatsEntry 4 }

juniAtmF4FlowInOamSegmentLoopbackCells OBJECT-TYPE
    SYNTAX      Counter32
    UNITS       "cells"
    MAX-ACCESS  read-only
    STATUS      current
    DESCRIPTION
        "Received end-to-end F4 OAM loopback cells."
    ::= { juniAtmF4FlowOamSegmentStatsEntry 5 }

juniAtmF4FlowOutSegmentRdiCells OBJECT-TYPE
    SYNTAX      Counter32
    UNITS       "cells"
    MAX-ACCESS  read-only
    STATUS      current
    DESCRIPTION
        "Transmitted end-to-end OAM F4 RDI cells."
    ::= { juniAtmF4FlowOamSegmentStatsEntry 6 }

juniAtmF4FlowOutSegmentCCCells OBJECT-TYPE
    SYNTAX      Counter32
    UNITS       "cells"
    MAX-ACCESS  read-only
    STATUS      current
    DESCRIPTION
        "Transmitted end-to-end OAM F4 CC cells."
    ::= { juniAtmF4FlowOamSegmentStatsEntry 7 }

juniAtmF4FlowOutSegmentCCActDeActCells OBJECT-TYPE
    SYNTAX      Counter32
    UNITS       "cells"
    MAX-ACCESS  read-only
    STATUS      current
    DESCRIPTION
        "Transmitted end-to-end OAM F4 activation/de-activation cells."
    ::= { juniAtmF4FlowOamSegmentStatsEntry 8 }

juniAtmF4FlowOutSegmentLoopbackCells OBJECT-TYPE
    SYNTAX      Counter32
    UNITS       "cells"
    MAX-ACCESS  read-only
    STATUS      current
    DESCRIPTION
        "Transmitted end-to-end OAM F4 loopback cells."
    ::= { juniAtmF4FlowOamSegmentStatsEntry 9 }

juniAtmF4FlowSegmentLastTimeChanged OBJECT-TYPE
    SYNTAX      TimeTicks
    MAX-ACCESS  read-only
    STATUS      current
    DESCRIPTION
        "Last time end-to-end F4 OAM flow got changed."
    ::= { juniAtmF4FlowOamSegmentStatsEntry 10 }

juniAtmF4FlowOamSegmentVpOperationState OBJECT-TYPE
    SYNTAX      INTEGER {
                    vcAisState(0),
                    vcRdiState(1),
                    vcDownRetry(2),
                    vcUpRetry(3),
                    vcUp(4),
                    vcDown(5),
                    vcNotManaged(6),
                    vpAisState(7),
                    vpRdiState(8),
                    vcInVpRdiState(9),
                    vcInVpAisState(10),
                    vcSegmentAisState(11),
                    vcSegRdiState(12) }
    MAX-ACCESS  read-only
    STATUS      current
    DESCRIPTION
        "Represents the F4 end-to-end OAM flow VP operation states.  It can take
        one of the following operational state values:
            vcAisState        - AIS cell received or underlying physical layer
                                reporting transmission path AIS.
            vcRdiState        - RDI cell received.
            vcDownRetry       - OAM loopback failed, using retry frequency to
                                verify that the VC is really down.
            vcUpRetry         - OAM loopback successful, using retry frequency
                                to verify that the VC is really up.
            vcUp              - OAM loopback successful after up retry
                                verification.
            vcDown            - OAM loopback failed after down retry
                                verification.
            vcNotManaged      - No verification via loopback cells being
                                performed.
            vpAisState        - State when F4 AIS cell is received.
            vpRdiState        - State when F4 RDI cell is received.
            vcInVpRdiState    - The data vc is down as a result of VP failure
                                thorugh F4 Rdi oam cell.
            vcInVpAisState    - The data vc is down as a result of VP failure
                                through F4  Ais oam cell.
            vcSegmentAisState - Segment AIS cell received.
            vcSegRdiState     - Segment RDI cell received."
    ::= { juniAtmF4FlowOamSegmentStatsEntry 11 }

juniAtmF4FlowOamSegmentVpAdminState OBJECT-TYPE
    SYNTAX      INTEGER {
                    down(0),
                    up(1) }
    MAX-ACCESS  read-only
    STATUS      current
    DESCRIPTION
         "Segment VP admin state."
    ::= { juniAtmF4FlowOamSegmentStatsEntry 12 }

juniAtmF4FlowSegmentInOamCells OBJECT-TYPE
    SYNTAX      Counter32
    UNITS       "cells"
    MAX-ACCESS  read-only
    STATUS      current
    DESCRIPTION
        "Received end-to-end OAM F4 loopback cells."
    ::= { juniAtmF4FlowOamSegmentStatsEntry 13 }

juniAtmF4FlowSegmentOutOamCells OBJECT-TYPE
    SYNTAX      Counter32
    UNITS       "cells"
    MAX-ACCESS  read-only
    STATUS      current
    DESCRIPTION
        "Transmitted end-to-end OAM F4 loopback cells."
    ::= { juniAtmF4FlowOamSegmentStatsEntry 14 }

juniAtmF4FlowSegmentInOamCellsDropped OBJECT-TYPE
    SYNTAX      Counter32
    UNITS       "cells"
    MAX-ACCESS  read-only
    STATUS      current
    DESCRIPTION
        "Received end-to-end OAM cells that were dropped."
    ::= { juniAtmF4FlowOamSegmentStatsEntry 15 }


--
-- juniAtmMartiniTimeoutTimerTable
--
juniAtmMartiniTimeoutTimerTable OBJECT-TYPE
    SYNTAX      SEQUENCE OF JuniAtmMartiniTimeoutTimerEntry
    MAX-ACCESS  not-accessible
    STATUS      current
    DESCRIPTION
        "This table contains entries for ATM Martini cell aggregation timeout
        detection.  The user can configure timeout values for three timers.
        A row exists for every separate timer supported.  These rows get created 
        as soon as the ERX system comes up."
    ::= { juniAtmIfLayer 13 }

juniAtmMartiniTimeoutTimerEntry OBJECT-TYPE
    SYNTAX      JuniAtmMartiniTimeoutTimerEntry
    MAX-ACCESS  not-accessible
    STATUS      current
    DESCRIPTION
        "Each entry contains the timeout value of ATM Martini 
        cell aggregation timer."
    INDEX     { juniAtmMartiniTimeoutTimerIndex }
    ::= { juniAtmMartiniTimeoutTimerTable 1 }

JuniAtmMartiniTimeoutTimerEntry ::= SEQUENCE {
    juniAtmMartiniTimeoutTimerIndex       INTEGER,
    juniAtmMartiniTimeoutTimerValue       Integer32 }

juniAtmMartiniTimeoutTimerIndex OBJECT-TYPE
    SYNTAX      INTEGER {
                        timer1(1),
                        timer2(2),
                        timer3(3) }
    MAX-ACCESS  not-accessible
    STATUS      current
    DESCRIPTION
        "The ATM Martini cell aggregation timeout timer identifier."
    ::= { juniAtmMartiniTimeoutTimerEntry 1 }

juniAtmMartiniTimeoutTimerValue OBJECT-TYPE
    SYNTAX      Integer32 (100..4095)
    MAX-ACCESS  read-write
    STATUS      current
    DESCRIPTION
        "The ATM Martini cell aggregation timeout timer value in microseconds."
    DEFVAL    { 100 }
    ::= { juniAtmMartiniTimeoutTimerEntry 2 }

-- /////////////////////////////////////////////////////////////////////////////
--
-- AAL5 LAYER
--
-- /////////////////////////////////////////////////////////////////////////////
--
-- IfIndex selection for creating new ATM AAL5 interfaces
--
juniAtmAal5NextIfIndex OBJECT-TYPE
    SYNTAX      JuniNextIfIndex
    MAX-ACCESS  read-only
    STATUS      current
    DESCRIPTION
        "Coordinate ifIndex value allocation for entries in juniAtmAal5IfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { juniAtmAal5IfLayer 1 }


--
-- The ATM AAL5 Interface Table
--
juniAtmAal5IfTable OBJECT-TYPE
    SYNTAX      SEQUENCE OF JuniAtmAal5IfEntry
    MAX-ACCESS  not-accessible
    STATUS      current
    DESCRIPTION
        "This table contains entries for ATM AAL5 interfaces present in the
        system."
    ::= { juniAtmAal5IfLayer 2 }

juniAtmAal5IfEntry OBJECT-TYPE
    SYNTAX      JuniAtmAal5IfEntry
    MAX-ACCESS  not-accessible
    STATUS      current
    DESCRIPTION
        "Each entry describes the characteristics of an ATM AAL5 interface.
        Creating/deleting entries in this table causes corresponding entries for
        be created/deleted in ifTable/ifXTable/juniIfTable."
    INDEX     { juniAtmAal5IfIndex }
    ::= { juniAtmAal5IfTable 1 }

JuniAtmAal5IfEntry ::= SEQUENCE {
    juniAtmAal5IfIndex           InterfaceIndex,
    juniAtmAal5IfRowStatus       RowStatus,
    juniAtmAal5IfLowerIfIndex    InterfaceIndexOrZero }

juniAtmAal5IfIndex OBJECT-TYPE
    SYNTAX      InterfaceIndex
    MAX-ACCESS  not-accessible
    STATUS      current
    DESCRIPTION
        "The ifIndex of the ATM AAL5 interface.  When creating entries in this
        table, suitable values for this object are determined by reading
        juniAtmAal5NextIfIndex."
    ::= { juniAtmAal5IfEntry 1 }

juniAtmAal5IfRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            juniAtmAal5IfRowStatus
            juniAtmAal5IfLowerIfIndex

        In addition, when creating an entry the following condition must hold:
            A value for juniAtmAal5IfIndex must have been determined previously,
            by reading juniAtmAal5NextIfIndex.

        A corresponding entry in ifTable/ifXTable/juniIfTable is created or
        destroyed as a result of creating/destroying an entry in this table."
    ::= { juniAtmAal5IfEntry 2 }

juniAtmAal5IfLowerIfIndex OBJECT-TYPE
    SYNTAX      InterfaceIndexOrZero
    MAX-ACCESS  read-create
    STATUS      current
    DESCRIPTION
        "The ifIndex of an ATM interface over which this ATM AAL5 interface is
        to be layered.  A value of zero indicates no layering.  An
        implementation may choose to require that a nonzero value be configured
        at entry creation."
    ::= { juniAtmAal5IfEntry 3 }


--
-- ATM Bulk Circuites Name Table
--
juniAtmBulkCircuitsNameTable OBJECT-TYPE
    SYNTAX      SEQUENCE OF JuniAtmBulkCircuitsNameEntry
    MAX-ACCESS  not-accessible
    STATUS      current
    DESCRIPTION
        "The entries in this table provide mappings of ATM bulk virtual circuit
        range names to local integer identifiers for those profiles.  These
        integers are used as indexes into other MIB tables containing profile
        configuration parameters associated with the same profile name."
    ::= { juniAtmAal5IfLayer 3 }

juniAtmBulkCircuitsNameEntry OBJECT-TYPE
    SYNTAX      JuniAtmBulkCircuitsNameEntry
    MAX-ACCESS  not-accessible
    STATUS      current
    DESCRIPTION
        "A mapping of a ATM bulk virtual circuit range name to an integer
        identifier for that name."
    INDEX     { juniAtmBulkCircuitsNameAal5IfIndex,
                juniAtmBulkCircuitsNameName }
    ::= { juniAtmBulkCircuitsNameTable 1 }

JuniAtmBulkCircuitsNameEntry ::= SEQUENCE {
    juniAtmBulkCircuitsNameAal5IfIndex        InterfaceIndex,
    juniAtmBulkCircuitsNameName               DisplayString,
    juniAtmBulkCircuitsNameRowStatus          RowStatus,
    juniAtmBulkCircuitsNameId                 Unsigned32 }

juniAtmBulkCircuitsNameAal5IfIndex OBJECT-TYPE
    SYNTAX      InterfaceIndex
    MAX-ACCESS  not-accessible
    STATUS      current
    DESCRIPTION
        "The ifIndex of the ATM AAL5 interface."
    ::= { juniAtmBulkCircuitsNameEntry 1 }

juniAtmBulkCircuitsNameName OBJECT-TYPE
    SYNTAX      DisplayString (SIZE(1..80))
    MAX-ACCESS  not-accessible
    STATUS      current
    DESCRIPTION
        "The ATM bulk virtual circuit range name uniquely identifying this
        entry."
    ::= { juniAtmBulkCircuitsNameEntry 2 }

juniAtmBulkCircuitsNameRowStatus OBJECT-TYPE
    SYNTAX      RowStatus
    MAX-ACCESS  read-create
    STATUS      current
    DESCRIPTION
        "Controls creation/deletion of entries in this table.  Only the values
        'createAndGo' and 'destroy' may be SET.

        Creating an entry in this table creates corresponding entry in
        juniAtmBulkCircuitsIdTable. Deleting an entry in this table deletes
        corresponding entries in juniAtmBulkCircuitsIdTable, 
        juniAtmBulkCircuitsTable and juniAtmProfileOverrideAssignIfCircuitTable."
    ::= { juniAtmBulkCircuitsNameEntry 3 }

juniAtmBulkCircuitsNameId OBJECT-TYPE
    SYNTAX      Unsigned32
    MAX-ACCESS  read-only
    STATUS      current
    DESCRIPTION
        "The integer identifier associated with this ATM bulk virtual circuit
        range name.

        This value of this identifier is assigned by the device when an entry in
        this table is created."
    ::= { juniAtmBulkCircuitsNameEntry 4 }


--
-- ATM Bulk Circuits ID Table
--
juniAtmBulkCircuitsIdTable OBJECT-TYPE
    SYNTAX      SEQUENCE OF JuniAtmBulkCircuitsIdEntry
    MAX-ACCESS  not-accessible
    STATUS      current
    DESCRIPTION
        "Provides inverse mapping of ATM bulk virtual circuit IDs to ATM bulk
        virtual circuit names."
    ::= { juniAtmAal5IfLayer 4 }

juniAtmBulkCircuitsIdEntry OBJECT-TYPE
    SYNTAX      JuniAtmBulkCircuitsIdEntry
    MAX-ACCESS  not-accessible
    STATUS      current
    DESCRIPTION
        "A mapping of an integer identifier to a ATM bulk virtual circuit name."
    INDEX     { juniAtmBulkCircuitsIdAal5IfIndex,
                juniAtmBulkCircuitsIdId }
    ::= { juniAtmBulkCircuitsIdTable 1 }

JuniAtmBulkCircuitsIdEntry ::= SEQUENCE {
    juniAtmBulkCircuitsIdAal5IfIndex        InterfaceIndex,
    juniAtmBulkCircuitsIdId                 Unsigned32,
    juniAtmBulkCircuitsIdName               DisplayString,
    juniAtmBulkCircuitsIdNextInstance       Unsigned32 }

juniAtmBulkCircuitsIdAal5IfIndex OBJECT-TYPE
    SYNTAX      InterfaceIndex
    MAX-ACCESS  not-accessible
    STATUS      current
    DESCRIPTION
        "The ifIndex of the ATM AAL5 interface."
    ::= { juniAtmBulkCircuitsIdEntry 1 }

juniAtmBulkCircuitsIdId OBJECT-TYPE
    SYNTAX      Unsigned32
    MAX-ACCESS  not-accessible
    STATUS      current
    DESCRIPTION
        "The integer identifier associated with this ATM bulk virtual circuit
        name."
    ::= { juniAtmBulkCircuitsIdEntry 2 }

juniAtmBulkCircuitsIdName OBJECT-TYPE
    SYNTAX      DisplayString (SIZE(1..80))
    MAX-ACCESS  read-only
    STATUS      current
    DESCRIPTION
        "The ATM bulk virtual circuit name having the associated identifier."
    ::= { juniAtmBulkCircuitsIdEntry 3 }

juniAtmBulkCircuitsIdNextInstance OBJECT-TYPE
    SYNTAX      Unsigned32
    MAX-ACCESS  read-only
    STATUS      current
    DESCRIPTION
        "The next available instance value for juniAtmBulkCircuitsEntry."
    ::= { juniAtmBulkCircuitsIdEntry 4 }


--
-- ATM Bulk Circuits Table
--
juniAtmBulkCircuitsTable OBJECT-TYPE
    SYNTAX      SEQUENCE OF JuniAtmBulkCircuitsEntry
    MAX-ACCESS  not-accessible
    STATUS      current
    DESCRIPTION
        "This table contains bulk virtual circuit range parameters."
    ::= { juniAtmAal5IfLayer 5 }

juniAtmBulkCircuitsEntry OBJECT-TYPE
    SYNTAX      JuniAtmBulkCircuitsEntry
    MAX-ACCESS  not-accessible
    STATUS      current
    DESCRIPTION
        "Each entry describes the characteristics of VC range."
    INDEX     { juniAtmBulkCircuitsAal5IfIndex,
                juniAtmBulkCircuitsId,
                juniAtmBulkCircuitsInstance }
    ::= { juniAtmBulkCircuitsTable 1 }

JuniAtmBulkCircuitsEntry ::= SEQUENCE {
    juniAtmBulkCircuitsAal5IfIndex  InterfaceIndex,
    juniAtmBulkCircuitsId           Unsigned32,
    juniAtmBulkCircuitsInstance     Unsigned32,
    juniAtmBulkCircuitsRowStatus    RowStatus,
    juniAtmBulkCircuitsMinVpi       AtmVpIdentifier,
    juniAtmBulkCircuitsMaxVpi       AtmVpIdentifier,
    juniAtmBulkCircuitsMinVci       AtmVcIdentifier,
    juniAtmBulkCircuitsMaxVci       AtmVcIdentifier,
    juniAtmBulkCircuitsAdminState   JuniEnable }

juniAtmBulkCircuitsAal5IfIndex OBJECT-TYPE
    SYNTAX      InterfaceIndex
    MAX-ACCESS  not-accessible
    STATUS      current
    DESCRIPTION
        "The ifIndex of the ATM AAL5 interface on which this bulk virtual
        circuit sub-range is created."
    ::= { juniAtmBulkCircuitsEntry 1 }

juniAtmBulkCircuitsId OBJECT-TYPE
    SYNTAX      Unsigned32
    MAX-ACCESS  not-accessible
    STATUS      current
    DESCRIPTION
        "The integer identifier associated with this ATM bulk virtual circuit
        name."
    ::= { juniAtmBulkCircuitsEntry 2 }

juniAtmBulkCircuitsInstance OBJECT-TYPE
    SYNTAX      Unsigned32
    MAX-ACCESS  not-accessible
    STATUS      current
    DESCRIPTION
        "The unique identifier of the ATM bulk virtual circuit sub-range."
    ::= { juniAtmBulkCircuitsEntry 3 }

juniAtmBulkCircuitsRowStatus OBJECT-TYPE
    SYNTAX      RowStatus
    MAX-ACCESS  read-create
    STATUS      current
    DESCRIPTION
        "Controls creation/deletion of entries in this table.  Only the values
        'createAndGo' and 'destroy' may be SET.

        Since none of the VPI/VCI minimum and maximum values have default
        values, all these values must be specified before setting RowStatus to
        'createAndGo'.  The VPI/VCI minimum and maximum values can only be
        configured upon creation.

        Deleting an entry in this table deletes corresponding entries in 
        juniAtmProfileOverrideAssignIfCircuitTable."
    ::= { juniAtmBulkCircuitsEntry 4 }

juniAtmBulkCircuitsMinVpi OBJECT-TYPE
    SYNTAX      AtmVpIdentifier
    MAX-ACCESS  read-create
    STATUS      current
    DESCRIPTION
        "The minimum value of VPI for this circuit sub-range. This value must
        be less than or equal to the value of juniAtmBulkCircuitsMaxVpi."
    ::= { juniAtmBulkCircuitsEntry 5 }

juniAtmBulkCircuitsMaxVpi OBJECT-TYPE
    SYNTAX      AtmVpIdentifier
    MAX-ACCESS  read-create
    STATUS      current
    DESCRIPTION
        "The maximum value of VPI for this cicuit sub-range. This value must
        be equal to or greater than the value of juniAtmBulkCircuitsMinVpi."
    ::= { juniAtmBulkCircuitsEntry 6 }

juniAtmBulkCircuitsMinVci OBJECT-TYPE
    SYNTAX      AtmVcIdentifier
    MAX-ACCESS  read-create
    STATUS      current
    DESCRIPTION
        "The minimum value of VCI for this circuit sub-range. This value must
        be less than or equal to the value of juniAtmBulkCircuitsMaxVci."
    ::= { juniAtmBulkCircuitsEntry 7 }

juniAtmBulkCircuitsMaxVci OBJECT-TYPE
    SYNTAX      AtmVcIdentifier
    MAX-ACCESS  read-create
    STATUS      current
    DESCRIPTION
        "The maximum value of VCI for this circuit sub-range. This value must
        be equal to or greater than the value of juniAtmBulkCircuitsMinVci."
    ::= { juniAtmBulkCircuitsEntry 8 }

juniAtmBulkCircuitsAdminState OBJECT-TYPE
    SYNTAX      JuniEnable
    MAX-ACCESS  read-create
    STATUS      current
    DESCRIPTION
        "The administrative status of this circuit sub-range."
    DEFVAL      { enable }
    ::= { juniAtmBulkCircuitsEntry 9 }



--
-- Assign overriding profile to interface/vpi/vci.
--
juniAtmProfileOverrideAssignIfCircuitTable OBJECT-TYPE
    SYNTAX      SEQUENCE OF JuniAtmProfileOverrideAssignIfCircuitEntry
    MAX-ACCESS  not-accessible
    STATUS      current
    DESCRIPTION
        "Table providing overriding profile assignment to a circuit configured 
        as part of bulk-configuration. Circuit is identified by interface index 
        and vpi, vci.

        The entries in this table specify which profile to use when creating and
        configuring a dynamic interface above a circuit specified by vpi and 
        vci.

        This entry is effective when the circuit specified by 
        juniAtmProfileOverrideAssignIfCircuitAal5Index, 
        juniAtmProfileOverrideAssignIfCircuitRangeId,             
        juniAtmProfileOverrideAssignIfCircuitVpi, 
        juniAtmProfileOverrideAssignIfCircuitVci 
		is part of bulk-configuration."
    ::= { juniAtmAal5IfLayer 6 }

juniAtmProfileOverrideAssignIfCircuitEntry OBJECT-TYPE
    SYNTAX      JuniAtmProfileOverrideAssignIfCircuitEntry
    MAX-ACCESS  not-accessible
    STATUS      current
    DESCRIPTION
	    "An assignment of a profile to a circuit configured as part of 
        bulk-configuration on an AAL5 interface."
    INDEX     { juniAtmProfileOverrideAssignIfCircuitAal5Index,
                juniAtmProfileOverrideAssignIfCircuitRangeId,
                juniAtmProfileOverrideAssignIfCircuitVpi,
                juniAtmProfileOverrideAssignIfCircuitVci }
    ::= { juniAtmProfileOverrideAssignIfCircuitTable 1 }

JuniAtmProfileOverrideAssignIfCircuitEntry ::= SEQUENCE {
    juniAtmProfileOverrideAssignIfCircuitAal5Index           InterfaceIndex,
    juniAtmProfileOverrideAssignIfCircuitRangeId             Unsigned32,
    juniAtmProfileOverrideAssignIfCircuitVpi                 AtmVpIdentifier,
    juniAtmProfileOverrideAssignIfCircuitVci                 AtmVcIdentifier,
    juniAtmProfileOverrideAssignIfCircuitRowStatus           RowStatus,
    juniAtmProfileOverrideAssignIfCircuitProfileId           Unsigned32,
    juniAtmProfileOverrideAssignIfCircuitOperStatus          INTEGER }

juniAtmProfileOverrideAssignIfCircuitAal5Index OBJECT-TYPE
    SYNTAX      InterfaceIndex
    MAX-ACCESS  not-accessible
    STATUS      current
    DESCRIPTION
        "The ifIndex of the AAL5 interface to which the profile is assigned."
    ::= { juniAtmProfileOverrideAssignIfCircuitEntry 1 }

juniAtmProfileOverrideAssignIfCircuitRangeId  OBJECT-TYPE
    SYNTAX      Unsigned32
    MAX-ACCESS  not-accessible
    STATUS      current
    DESCRIPTION
        "The integer identifier associated with the ATM bulk circuit 
        configuration." 
    ::= { juniAtmProfileOverrideAssignIfCircuitEntry 2 }    

juniAtmProfileOverrideAssignIfCircuitVpi OBJECT-TYPE
    SYNTAX      AtmVpIdentifier
    MAX-ACCESS  not-accessible
    STATUS      current
    DESCRIPTION
        "The VPI value of the circuit to which the profile is assigned."
    ::= { juniAtmProfileOverrideAssignIfCircuitEntry 3 }

juniAtmProfileOverrideAssignIfCircuitVci OBJECT-TYPE
    SYNTAX      AtmVcIdentifier
    MAX-ACCESS  not-accessible
    STATUS      current
    DESCRIPTION
        "The VCI value of the circuit to which the profile is assigned." 
    ::= { juniAtmProfileOverrideAssignIfCircuitEntry 4 }


juniAtmProfileOverrideAssignIfCircuitRowStatus OBJECT-TYPE
    SYNTAX      RowStatus
    MAX-ACCESS  read-create
    STATUS      current
    DESCRIPTION
        "Controls creation/deletion of entries in this table.  Only the values
        'createAndGo' and 'destroy' may be SET.

        Since the VPI, VCI and profileId values do not have any default
        values, all these values must be specified before setting RowStatus to
        'createAndGo'.  The VPI, VCI and profileId values can only be
        configured upon creation.  None of these values can be modified except
        by deleting the entry."
    ::= { juniAtmProfileOverrideAssignIfCircuitEntry 5 }

juniAtmProfileOverrideAssignIfCircuitProfileId OBJECT-TYPE
    SYNTAX      Unsigned32
    MAX-ACCESS  read-create
    STATUS      current
    DESCRIPTION
        "The ID of the profile assigned to the circuit configured as part of 
        bulk-configuration. Circuit is identified by interface index and vpi, 
        vci."
    ::= { juniAtmProfileOverrideAssignIfCircuitEntry 6 }

juniAtmProfileOverrideAssignIfCircuitOperStatus OBJECT-TYPE
    SYNTAX      INTEGER {
                    inactive(0),
                    active(1)
                }
    MAX-ACCESS  read-only
    STATUS      current
    DESCRIPTION 
        "The operational status of the profile override assignment identified
        by this entry.

        It returns inactive(0), if a static ATM circuit with identical VPI/VCI 
        values is present on the same ATM interface. In this case, this
        profile override will not be used to configure upper dynamic 
        interfaces.

        It returns active(1), if no static ATM circuit with identical VPI/VCI 
        values is present on the same ATM interface. In this case, this 
        profile override will be used to configure upper dynamic interfaces."
     ::= { juniAtmProfileOverrideAssignIfCircuitEntry 7 } 


-- /////////////////////////////////////////////////////////////////////////////
--
-- ATM SUBINTERFACE LAYER
--
-- /////////////////////////////////////////////////////////////////////////////
--
-- IfIndex selection for creating new ATM Subinterfaces
--
juniAtmSubIfNextIfIndex OBJECT-TYPE
    SYNTAX      JuniNextIfIndex
    MAX-ACCESS  read-only
    STATUS      current
    DESCRIPTION
        "Coordinate ifIndex value allocation for entries in juniAtmSubIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { juniAtmSubIfLayer 1 }

--
-- The ATM Subinterface Table
--
juniAtmSubIfTable OBJECT-TYPE
    SYNTAX      SEQUENCE OF JuniAtmSubIfEntry
    MAX-ACCESS  not-accessible
    STATUS      current
    DESCRIPTION
        "This table contains entries for ATM Subinterfaces present in the
        system."
    ::= { juniAtmSubIfLayer 2 }

juniAtmSubIfEntry OBJECT-TYPE
    SYNTAX      JuniAtmSubIfEntry
    MAX-ACCESS  not-accessible
    STATUS      current
    DESCRIPTION
        "Each entry describes the characteristics of an ATM Subinterface.
        Creating/deleting entries in this table causes corresponding entries for
        be created/deleted in ifTable/ifXTable/juniIfTable."
    INDEX     { juniAtmSubIfIndex }
    ::= { juniAtmSubIfTable 1 }

JuniAtmSubIfEntry ::= SEQUENCE {
    juniAtmSubIfIndex                     InterfaceIndex,
    juniAtmSubIfRowStatus                 RowStatus,
    juniAtmSubIfDistinguisher             Integer32,
    juniAtmSubIfLowerIfIndex              InterfaceIndexOrZero,
    juniAtmSubIfNbma                      TruthValue,
    juniAtmSubIfAddress                   AtmAddr,
    juniAtmSubIfMtu                       Integer32,
    juniAtmSubIfAdvisoryRxSpeed           Integer32,
    juniAtmSubIfMartiniMaxCellsPerPacket  Integer32,
    juniAtmSubIfMartiniTimeoutTimerId     Integer32
 }

juniAtmSubIfIndex OBJECT-TYPE
    SYNTAX      InterfaceIndex
    MAX-ACCESS  not-accessible
    STATUS      current
    DESCRIPTION
        "The ifIndex of the ATM Subinterface.  When creating entries in this
        table, suitable values for this object are determined by reading
        juniAtmSubNextIfIndex."
    ::= { juniAtmSubIfEntry 1 }

juniAtmSubIfRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            juniAtmSubIfRowStatus
            juniAtmSubIfLowerIndex

        In addition, when creating an entry the following condition must hold:
            A value for juniAtmSubIfIndex must have been determined previously,
            by reading juniAtmSubIfNextIfIndex.

        A corresponding entry in ifTable/ifXTable/juniIfTable is created or
        destroyed as a result of creating/destroying an entry in this table."
    ::= { juniAtmSubIfEntry 2 }

juniAtmSubIfDistinguisher OBJECT-TYPE
    SYNTAX      Integer32 (0..2147483647)
    MAX-ACCESS  read-create
    STATUS      current
    DESCRIPTION
        "An integer identifier for the subinterface, used in conjunction with
        the command-line interface.  It is provided here for cross-reference
        purposes only.

        The value must be unique among subinterfaces configured on the same
        underlying ATM adaptation layer.  The upper bound for the value is
        further constrained to be identical with the maximum number of
        subinterfaces supported by the lower interface.

        If this object is not configured, a value will be allocated internally
        and can be queried after table entry creation has succeeded."
    ::= { juniAtmSubIfEntry 3 }

juniAtmSubIfLowerIfIndex OBJECT-TYPE
    SYNTAX      InterfaceIndexOrZero
    MAX-ACCESS  read-create
    STATUS      current
    DESCRIPTION
        "The ifIndex of an ATM AAL5 interface over which this ATM subinterface
        is to be layered.  A value of zero indicates no layering.  An
        implementation may choose to require that a nonzero value be configured
        at entry creation."
    ::= { juniAtmSubIfEntry 4 }

juniAtmSubIfNbma OBJECT-TYPE
    SYNTAX      TruthValue
    MAX-ACCESS  read-create
    STATUS      current
    DESCRIPTION
        "The NBMA administrative setting.  Setting this value of this object to
        true(1) will enable multipoint access on this interface.  Setting the
        value to false(2), will enable point to point access on this interface."
    DEFVAL    { false }
    ::= { juniAtmSubIfEntry 5 }

juniAtmSubIfAddress OBJECT-TYPE
    SYNTAX      AtmAddr (SIZE(0|7|20))
    MAX-ACCESS  read-create
    STATUS      current
    DESCRIPTION
        "Specifies the local ATM NSAP address of the circuit.  A GET operation
        returns a full 20-octet NSAP.  A SET operation only requires 7 octets,
        since the prefix can be implied."
    DEFVAL    { ''H }
    ::= { juniAtmSubIfEntry 6 }

juniAtmSubIfMtu OBJECT-TYPE
    SYNTAX      Integer32 (0..2147483647)
    MAX-ACCESS  read-create
    STATUS      current
    DESCRIPTION
        "The size of the largest packet which can be sent/received on the
        interface, specified in octets."
    DEFVAL    { 9180 }
       ::= { juniAtmSubIfEntry 7 }

juniAtmSubIfAdvisoryRxSpeed OBJECT-TYPE
    SYNTAX      Integer32 (0..2147483647)
    MAX-ACCESS  read-create
    STATUS      current
    DESCRIPTION
        "Advisory receive speed, in kilobits per second (kbps),
        of this subinterface. This object has no impact on
        forwarding performance but may be used as a hint for
        underlying circuit receive speed."
    DEFVAL    { 0 }
       ::= { juniAtmSubIfEntry 8 }

juniAtmSubIfMartiniMaxCellsPerPacket OBJECT-TYPE
    SYNTAX      Integer32 (1..190)
    MAX-ACCESS  read-create
    STATUS      current
    DESCRIPTION
        "The number of cells that can be aggregated in a single ATM Martini
        packet in cell-relay mode."
    DEFVAL    { 1 }
       ::= { juniAtmSubIfEntry 9 }

juniAtmSubIfMartiniTimeoutTimerId OBJECT-TYPE
    SYNTAX      Integer32 (1..3)
    MAX-ACCESS  read-create
    STATUS      current
    DESCRIPTION
        "The timer identifier used to abandon cell aggregation when no
        cells are supplied for transmission in ATM Martini cell-relay mode."
    DEFVAL    { 1 }
       ::= { juniAtmSubIfEntry 10 }


--
-- The ATM Subinterface VCC Table
--
juniAtmSubIfVccTable OBJECT-TYPE
    SYNTAX      SEQUENCE OF JuniAtmSubIfVccEntry
    MAX-ACCESS  not-accessible
    STATUS      current
    DESCRIPTION
        "This table contains entries for ATM VCCs configured on ATM
        subinterfaces present in the system.

        An implementation may constrain the number of VCCs permitted to be
        configured per ATM Subinterface; in particular, an implementation may
        restrict each ATM Subinterface to have a single VCC.

        Attributes in this entry can only be configured at entry creation, and
        remain fixed for the lifetime of the entry."
    ::= { juniAtmSubIfLayer 3 }

juniAtmSubIfVccEntry OBJECT-TYPE
    SYNTAX      JuniAtmSubIfVccEntry
    MAX-ACCESS  not-accessible
    STATUS      current
    DESCRIPTION
        "Each entry describes the characteristics of an ATM subinterface VCC."
    INDEX     { juniAtmSubIfIndex,
                juniAtmSubIfVccVpi,
                juniAtmSubIfVccVci }
    ::= { juniAtmSubIfVccTable 1 }

JuniAtmSubIfVccEntry ::= SEQUENCE {
    juniAtmSubIfVccVpi               AtmVpIdentifier,
    juniAtmSubIfVccVci               AtmVcIdentifier,
    juniAtmSubIfVccRowStatus         RowStatus,
    juniAtmSubIfVccVcd               Integer32,
    juniAtmSubIfVccType              INTEGER,
    juniAtmSubIfVccServiceCategory   INTEGER,
    juniAtmSubIfVccPcr               Integer32,
    juniAtmSubIfVccScr               Integer32,
    juniAtmSubIfVccMbs               Integer32,
    juniAtmSubIfInverseArp           TruthValue,
    juniAtmSubIfInverseArpRefresh    Integer32 }

juniAtmSubIfVccVpi OBJECT-TYPE
    SYNTAX      AtmVpIdentifier
    MAX-ACCESS  not-accessible
    STATUS      current
    DESCRIPTION
        "The VPI of the ATM VCC used by this subinterface."
    ::= { juniAtmSubIfVccEntry 1 }

juniAtmSubIfVccVci OBJECT-TYPE
    SYNTAX      AtmVcIdentifier
    MAX-ACCESS  not-accessible
    STATUS      current
    DESCRIPTION
        "The VCI of the ATM VCC used by this subinterface."
    ::= { juniAtmSubIfVccEntry 2 }

juniAtmSubIfVccRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            juniAtmSubIfVccRowStatus

        In addition, when creating an entry the following conditions must hold:
            The ATM Subinterface identified by juniAtmSubIfIndex must exist.

            A positive value configured for juniAtmSubIfVccVcd must not already
            be assigned to an existing VCC.

            For each value of juniAtmSubIfVccServiceCategory, additional
            dependent objects in the entry require configuration as identified
            here:

            juniAtmSubIfVccServiceCategory    Requires configuration of:
            ------------------------------------------------------------
            ubr                             <none>

            ubrPcr                          juniAtmSubIfVccPcr

            nrtVbr                          juniAtmSubIfVccPcr
                                            juniAtmSubIfVccScr
                                            juniAtmSubIfVccMbs

            cbr                             juniAtmSubIfVccPcr

            rtVbr                           juniAtmSubIfVccPcr
                                            juniAtmSubIfVccScr
                                            juniAtmSubIfVccMbs
            ------------------------------------------------------------

        Attributes in this entry can only be configured at entry creation,
        and remain fixed for the lifetime of the entry."
    ::= { juniAtmSubIfVccEntry 3 }

juniAtmSubIfVccVcd OBJECT-TYPE
    SYNTAX      Integer32 (0..2147483647)
    MAX-ACCESS  read-create
    STATUS      current
    DESCRIPTION
        "An integer identifier for the circuit, used in conjunction with the
        command-line interface.  It is provided here for cross-reference
        purposes only.

        The value must be unique among VCCs configured on the same underlying
        ATM interface.

        If this object is not configured, or is configured with a value of zero,
        a value will be allocated internally and can be queried after table
        entry creation has succeeded."
    ::= { juniAtmSubIfVccEntry 4 }

juniAtmSubIfVccType OBJECT-TYPE
    SYNTAX      INTEGER {
                    rfc1483VcMux(0),
                    rfc1483Llc(1),
                    autoconfig(2),
                    aal5(3),
                    aal0(4) }
    MAX-ACCESS  read-create
    STATUS      current
    DESCRIPTION
        "Specifies the encapsulation used by the circuit to carry IP datagrams.
        Encapsulations are as specified in RFC1483 Multiprotocol Interconnect
        over ATM.  The 'autoconfig' value will recognize both VcMux and LLC
        formats.  The 'aal5' and 'aal0' values are used for encapsulation methods
        for transport of ATM frames and cells over IP and MPLS networks when no
        encapsulation method is specified."
    DEFVAL    { rfc1483VcMux }
    ::= { juniAtmSubIfVccEntry 5 }

juniAtmSubIfVccServiceCategory OBJECT-TYPE
    SYNTAX      INTEGER {
                    ubr(0),
                    ubrPcr(1),
                    nrtVbr(2),
                    cbr(3),
                    rtVbr(4) }
    MAX-ACCESS  read-create
    STATUS      current
    DESCRIPTION
        "Service category for this circuit:
            ubr         Unspecified Bit Rate (best effort).
            ubrPcr      Unspecified Bit Rate with Peak Cell Rate limit.
            nrtVbr      Non-RealTime Variable Bit Rate.
            cbr         Constant Bit Rate.
            rtVbr       Realtime Variable Bit Rate."
    DEFVAL    { ubr }
    ::= { juniAtmSubIfVccEntry 6 }

juniAtmSubIfVccPcr OBJECT-TYPE
    SYNTAX      Integer32 (0..2147483647)
    UNITS       "kbps"
    MAX-ACCESS  read-create
    STATUS      current
    DESCRIPTION
        "Peak Cell Rate, in kilobits per second (kbps), of this circuit.

        This parameter is only required when juniAtmSubIfVccServiceCategory is
        configured to have one of the following values:
            ubrPcr
            nrtVbr
            cbr
            rtVbr "
    DEFVAL    { 0 }
    ::= { juniAtmSubIfVccEntry 7 }

juniAtmSubIfVccScr OBJECT-TYPE
    SYNTAX      Integer32 (0..2147483647)
    UNITS       "kbps"
    MAX-ACCESS  read-create
    STATUS      current
    DESCRIPTION
        "Sustained Cell Rate, in kilobits per second (kbps), of this circuit.

        This parameter is only required when juniAtmSubIfVccServiceCategory is
        configured to have the following value:
            nrtVbr
            rtVbr "
    DEFVAL    { 0 }
    ::= { juniAtmSubIfVccEntry 8 }

juniAtmSubIfVccMbs OBJECT-TYPE
    SYNTAX      Integer32 (0..16777215)
    UNITS       "cells"
    MAX-ACCESS  read-create
    STATUS      current
    DESCRIPTION
        "Maximum Burst Size, in cells, of this circuit.

        This parameter is only required when juniAtmSubIfVccServiceCategory is
        configured to have the following value:
            nrtVbr
            rtVbr "
    DEFVAL    { 0 }
    ::= { juniAtmSubIfVccEntry 9 }

juniAtmSubIfInverseArp OBJECT-TYPE
    SYNTAX      TruthValue
    MAX-ACCESS  read-create
    STATUS      current
    DESCRIPTION
        "Enables the inverse ARP protocol on this VCC; true(1) enables the
        protocol, false(2) disables it."
    ::= { juniAtmSubIfVccEntry 10 }

juniAtmSubIfInverseArpRefresh OBJECT-TYPE
    SYNTAX      Integer32 (0..60)
    UNITS       "minutes"
    MAX-ACCESS  read-create
    STATUS      current
    DESCRIPTION
       "The refresh rate in minutes between inverse ARP protocol messages."
    ::= { juniAtmSubIfVccEntry 11 }


--
-- The ATM OAM Table
--
juniAtmCircuitOamTable OBJECT-TYPE
    SYNTAX      SEQUENCE OF JuniAtmCircuitOamEntry
    MAX-ACCESS  not-accessible
    STATUS      current
    DESCRIPTION
        "This table contains circuit OAM data for a PVC."
    ::= { juniAtmSubIfLayer 4 }

juniAtmCircuitOamEntry OBJECT-TYPE
    SYNTAX      JuniAtmCircuitOamEntry
    MAX-ACCESS  not-accessible
    STATUS      current
    DESCRIPTION
        "Each entry provides OAM data on an ATM PVC."
    INDEX     { juniAtmCircuitOamIfIndex,
                juniAtmCircuitOamVpi,
                juniAtmCircuitOamVci }
    ::= { juniAtmCircuitOamTable 1 }

JuniAtmCircuitOamEntry ::= SEQUENCE {
    juniAtmCircuitOamIfIndex                     InterfaceIndex,
    juniAtmCircuitOamVpi                         AtmVpIdentifier,
    juniAtmCircuitOamVci                         AtmVcIdentifier,
    juniAtmCircuitOamAdminStatus                 INTEGER,
    juniAtmCircuitOamLoopbackOperStatus          INTEGER,
    juniAtmCircuitVcOamOperStatus                INTEGER,
    juniAtmCircuitOamLoopbackFrequency           Integer32,
    juniAtmCircuitInOamF5Cells                   Counter32,
    juniAtmCircuitInOamCellsDropped              Counter32,
    juniAtmCircuitOutOamF5Cells                  Counter32,
    juniAtmCircuitInOamF5EndToEndLoopbackCells   Counter32,
    juniAtmCircuitInOamF5SegmentLoopbackCells    Counter32,
    juniAtmCircuitInOamF5AisCells                Counter32,
    juniAtmCircuitInOamF5RdiCells                Counter32,
    juniAtmCircuitOutOamF5EndToEndLoopbackCells  Counter32,
    juniAtmCircuitOutOamF5SegmentLoopbackCells   Counter32,
    juniAtmCircuitOutOamF5RdiCells               Counter32 }

juniAtmCircuitOamIfIndex OBJECT-TYPE
    SYNTAX      InterfaceIndex
    MAX-ACCESS  not-accessible
    STATUS      current
    DESCRIPTION
        "The ifIndex of the ATM subinterface."
    ::= { juniAtmCircuitOamEntry 1 }

juniAtmCircuitOamVpi OBJECT-TYPE
    SYNTAX      AtmVpIdentifier
    MAX-ACCESS  not-accessible
    STATUS      current
    DESCRIPTION
        "The VPI of the ATM VCC used by this ATM interface and PVC."
    ::= { juniAtmCircuitOamEntry 2 }

juniAtmCircuitOamVci OBJECT-TYPE
    SYNTAX      AtmVcIdentifier
    MAX-ACCESS  not-accessible
    STATUS      current
    DESCRIPTION
        "The VCI of the ATM VCC used by this ATM interface and PVC."
    ::= { juniAtmCircuitOamEntry 3 }

juniAtmCircuitOamAdminStatus OBJECT-TYPE
    SYNTAX      INTEGER {
                    oamAdminStateDisabled(1),
                    oamAdminStateEnabled(2) }
    MAX-ACCESS  read-write
    STATUS      current
    DESCRIPTION
        "The administrative state of OAM for the interface identified by this
        entry."
    DEFVAL    { oamAdminStateDisabled }
    ::= { juniAtmCircuitOamEntry 4 }

juniAtmCircuitOamLoopbackOperStatus OBJECT-TYPE
    SYNTAX      INTEGER {
                    oamOperStatusNotSupported(0),
                    oamOperStatusDisabled(1),
                    oamOperStatusSent(2),
                    oamOperStatusReceived(3),
                    oamOperStatusFailed(4) }
    MAX-ACCESS  read-only
    STATUS      current
    DESCRIPTION
        "The operational status of OAM for the interface identified by this
        entry.
            oamOperStatusNotSupported(0) - OAM not supported on this interface
            oamOperStatusDisabled(1)     - VC integrity disabled
            oamOperStatusSent(2)         - Loopback sent, awaiting response
            oamOperStatusReceived(3)     - Loopback response received, awaiting
                                           frequency
            oamOperStatusFailed(4)       - Loopback response not received, or
                                           invalid response received"
    ::= { juniAtmCircuitOamEntry 5 }

juniAtmCircuitVcOamOperStatus OBJECT-TYPE
    SYNTAX      INTEGER {
                    oamVcOperStateAisState(0),
                    oamVcOperStateRdiState(1),
                    oamVcOperStateDownRetry(2),
                    oamVcOperStateUpRetry(3),
                    oamVcOperStateUp(4),
                    oamVcOperStateDown(5),
                    oamVcOperStateNotManaged(6),
                    oamVcOperStateVpAis(7),
                    oamVcOperStateVpRdi(8),
                    oamVcOperStateVcInVpRdi(9),
                    oamVcoperStateVcInVpAis(10),
                    oamVcOperStateSegAis(11),
                    oamVcOperStateSegRdi(12),
                    oamVcOperStateGenAis(13)}
    MAX-ACCESS  read-only
    STATUS      current
    DESCRIPTION
        "The OAM VC operational status of this entry.
            oamVcOperStateAisState(0)  - AIS cell received or underlying
                                         physical layer reporting transmission
                                         path AIS
            oamVcOperStateRdiState(1)  - RDI cell received
            oamVcOperStateDownRetry(2) - OAM loopback failed, using retry
                                         frequency to verify that the VC is
                                         really down
            oamVcOperStateUpRetry(3)   - OAM loopback successful, using retry
                                         frequency to verify that the VC is
                                         really up
            oamVcOperStateUp(4)        - OAM loopback successful after up retry
                                         verification
            oamVcOperStateDown(5)      - OAM loopback failed after down retry
                                         verification
            oamVcOperStateNotManaged(6)- No verification via loopback cells
                                         being performed
            oamVcOperStateVpAis(7)     - F4 AIS cell received
            oamVcOperStateVpRdi(8)     - F4 RDI cell received
            oamVcOperStateVcInVpRdi(9) - F4 RDI cell received; path failure
            oamVcOperStateVcInVpAis(10)- F4 AIS cell received; path failure
            oamVcOperStateSegAis(11)   - Segment AIS cell received
            oamVcOperStateSegRdi(12)   - Segment RDI cell received
            oamVcOperStateGenAis(13)   - Connection failure; generating AIS cells."
    ::= { juniAtmCircuitOamEntry 6 }

juniAtmCircuitOamLoopbackFrequency OBJECT-TYPE
    SYNTAX      Integer32 (0..600)
    UNITS       "seconds"
    MAX-ACCESS  read-write
    STATUS      current
    DESCRIPTION
        "The OAM loopback frequency for the interface identified by this entry."
    DEFVAL    { 10 }
    ::= { juniAtmCircuitOamEntry 7 }

juniAtmCircuitInOamF5Cells OBJECT-TYPE
    SYNTAX      Counter32
    UNITS       "cells"
    MAX-ACCESS  read-only
    STATUS      current
    DESCRIPTION
        "Received OAM F5 cells."
    ::= { juniAtmCircuitOamEntry 8 }

juniAtmCircuitInOamCellsDropped OBJECT-TYPE
    SYNTAX      Counter32
    UNITS       "cells"
    MAX-ACCESS  read-only
    STATUS      current
    DESCRIPTION
        "Received OAM cells that were dropped."
    ::= { juniAtmCircuitOamEntry 9 }

juniAtmCircuitOutOamF5Cells OBJECT-TYPE
    SYNTAX      Counter32
    UNITS       "cells"
    MAX-ACCESS  read-only
    STATUS      current
    DESCRIPTION
        "Transmitted OAM F5 cells."
    ::= { juniAtmCircuitOamEntry 10 }

juniAtmCircuitInOamF5EndToEndLoopbackCells OBJECT-TYPE
    SYNTAX      Counter32
    UNITS       "cells"
    MAX-ACCESS  read-only
    STATUS      current
    DESCRIPTION
        "Received OAM F5 end-to-end loopback cells."
    ::= { juniAtmCircuitOamEntry 11 }

juniAtmCircuitInOamF5SegmentLoopbackCells OBJECT-TYPE
    SYNTAX      Counter32
    UNITS       "cells"
    MAX-ACCESS  read-only
    STATUS      current
    DESCRIPTION
        "Received OAM F5 segment loopback cells."
    ::= { juniAtmCircuitOamEntry 12 }

juniAtmCircuitInOamF5AisCells OBJECT-TYPE
    SYNTAX      Counter32
    UNITS       "cells"
    MAX-ACCESS  read-only
    STATUS      current
    DESCRIPTION
        "Received OAM F5 AIS cells."
    ::= { juniAtmCircuitOamEntry 13 }

juniAtmCircuitInOamF5RdiCells OBJECT-TYPE
    SYNTAX      Counter32
    UNITS       "cells"
    MAX-ACCESS  read-only
    STATUS      current
    DESCRIPTION
        "Received OAM F5 RDI cells."
    ::= { juniAtmCircuitOamEntry 14 }

juniAtmCircuitOutOamF5EndToEndLoopbackCells OBJECT-TYPE
    SYNTAX      Counter32
    UNITS       "cells"
    MAX-ACCESS  read-only
    STATUS      current
    DESCRIPTION
        "Transmitted OAM F5 end-to-end loopback cells."
    ::= { juniAtmCircuitOamEntry 15 }

juniAtmCircuitOutOamF5SegmentLoopbackCells OBJECT-TYPE
    SYNTAX      Counter32
    UNITS       "cells"
    MAX-ACCESS  read-only
    STATUS      current
    DESCRIPTION
        "Transmitted OAM F5 segment loopback cells."
    ::= { juniAtmCircuitOamEntry 16 }

juniAtmCircuitOutOamF5RdiCells OBJECT-TYPE
    SYNTAX      Counter32
    UNITS       "cells"
    MAX-ACCESS  read-only
    STATUS      current
    DESCRIPTION
        "Transmitted OAM F5 RDI cells."
    ::= { juniAtmCircuitOamEntry 17 }


--
-- The ATM Subinterface VCC Traffic Shaping Table
--
juniAtmSubIfVccTrafficShapingTable OBJECT-TYPE
    SYNTAX      SEQUENCE OF JuniAtmSubIfVccTrafficShapingEntry
    MAX-ACCESS  not-accessible
    STATUS      current
    DESCRIPTION
        "This table contains entries for traffic shaping of ATM VCCs configured
        on ATM subinterfaces present in the system.  This table augments the
        juniAtmSubIfVccTable only for VCCs that support traffic shapping.

        Attributes in this entry can only be configured at entry creation, and
        remain fixed for the lifetime of the entry."
    ::= { juniAtmSubIfLayer 5 }

juniAtmSubIfVccTrafficShapingEntry OBJECT-TYPE
    SYNTAX      JuniAtmSubIfVccTrafficShapingEntry
    MAX-ACCESS  not-accessible
    STATUS      current
    DESCRIPTION
        "Each entry describes the traffic shping characteristics of an ATM
        subinterface VCC."
    AUGMENTS  { juniAtmSubIfVccEntry }
    ::= { juniAtmSubIfVccTrafficShapingTable 1 }

JuniAtmSubIfVccTrafficShapingEntry ::= SEQUENCE {
    juniAtmSubIfVccTrafficShapingCdvt            Unsigned32,
    juniAtmSubIfVccTrafficShapingClp0            TruthValue,
    juniAtmSubIfVccTrafficShapingTagging         TruthValue,
    juniAtmSubIfVccTrafficShapingPoliceObserve   TruthValue,
    juniAtmSubIfVccTrafficShapingPacketShaping   TruthValue }

juniAtmSubIfVccTrafficShapingCdvt OBJECT-TYPE
    SYNTAX      Unsigned32
    UNITS       "tenths of a microsecond"
    MAX-ACCESS  read-create
    STATUS      current
    DESCRIPTION
        "The network cell delay variation tolerance (CDVT) in tenths of a
        microsecond."
    ::= { juniAtmSubIfVccTrafficShapingEntry 1 }

juniAtmSubIfVccTrafficShapingClp0 OBJECT-TYPE
    SYNTAX      TruthValue
    MAX-ACCESS  read-create
    STATUS      current
    DESCRIPTION
        "Specifies whether or not only CLP0 cells are to be policed according to
        the traffic contract.  CLP1 cells are forwarded on a best-effort basis
        CLP-significant model for (VBR.2, VBR.3 conformance).  Applicable only
        for VBR circuits."
    ::= { juniAtmSubIfVccTrafficShapingEntry 2 }

juniAtmSubIfVccTrafficShapingTagging OBJECT-TYPE
    SYNTAX      TruthValue
    MAX-ACCESS  read-create
    STATUS      current
    DESCRIPTION
        "Specifies whether or not CLP0 cells should be tagged for SCR policing
        (VBR.3 conformance).  Applicable only for VBR circuits."
    ::= { juniAtmSubIfVccTrafficShapingEntry 3 }

juniAtmSubIfVccTrafficShapingPoliceObserve OBJECT-TYPE
    SYNTAX      TruthValue
    MAX-ACCESS  read-create
    STATUS      current
    DESCRIPTION
        "Specifies whether of not no policing action is to be taken (note the
        double negative; if true(1) then no policing action will be taken; if
        false(2) then policing action will be taken).  Regardless of the state
        of this object, all counters will be incremented."
    ::= { juniAtmSubIfVccTrafficShapingEntry 4 }

juniAtmSubIfVccTrafficShapingPacketShaping OBJECT-TYPE
    SYNTAX      TruthValue
    MAX-ACCESS  read-create
    STATUS      current
    DESCRIPTION
        "Specifies whether of not to shape output traffic on a packet boundary."
    ::= { juniAtmSubIfVccTrafficShapingEntry 5 }


--
-- The juniAtmSubIfSvcConfigTable for ATM switched
-- virtual connections (SVCs).
--
juniAtmSubIfSvcConfigTable OBJECT-TYPE
    SYNTAX      SEQUENCE OF JuniAtmSubIfSvcConfigEntry
    MAX-ACCESS  not-accessible
    STATUS      current
    DESCRIPTION
        "This table contains entries for extending the juniAtmSubIfTable to
        configure switched virtual connection (SVC) on the subinterfaces."
    ::= { juniAtmSubIfLayer 6 }

juniAtmSubIfSvcConfigEntry OBJECT-TYPE
    SYNTAX      JuniAtmSubIfSvcConfigEntry
    MAX-ACCESS  not-accessible
    STATUS      current
    DESCRIPTION
        "Each entry provides configuration parameters for an ATM SVC on the
        subinterface."
    INDEX     { juniAtmSubIfIndex }
    ::= { juniAtmSubIfSvcConfigTable 1 }

JuniAtmSubIfSvcConfigEntry ::= SEQUENCE {
    juniAtmSubIfSvcRowStatus             RowStatus,
    juniAtmSubIfSvcConfigDestAtmAddress  AtmAddr,
    juniAtmSubIfSvcConfigCircuitType     INTEGER,
    juniAtmSubIfSvcConfigServiceCategory INTEGER,
    juniAtmSubIfSvcConfigPcr             Unsigned32,
    juniAtmSubIfSvcConfigScr             Unsigned32,
    juniAtmSubIfSvcConfigMbs             Unsigned32,
    juniAtmSubIfSvcConfigCdvt            Unsigned32,
    juniAtmSubIfSvcConfigClp0            TruthValue,
    juniAtmSubIfSvcConfigTagging         TruthValue,
    juniAtmSubIfSvcConfigObserve         TruthValue,
    juniAtmSubIfSvcConfigPacketDiscard   TruthValue,
    juniAtmSubIfSvcConfigDestE164Address AtmAddr }

juniAtmSubIfSvcRowStatus OBJECT-TYPE
    SYNTAX      RowStatus
    MAX-ACCESS  read-create
    STATUS      current
    DESCRIPTION
        "Controls creation/deletion of entries in this table according to the
        RowStatus textual convention, constrained to support the following
        values only:
            createAndGo
            destroy "
    ::= { juniAtmSubIfSvcConfigEntry 1 }

juniAtmSubIfSvcConfigDestAtmAddress OBJECT-TYPE
    SYNTAX      AtmAddr (SIZE(20))
    MAX-ACCESS  read-create
    STATUS      current
    DESCRIPTION
        "Specifies the destination ATM NSAP address of the circuit."
    ::= { juniAtmSubIfSvcConfigEntry 2 }

juniAtmSubIfSvcConfigCircuitType OBJECT-TYPE
    SYNTAX      INTEGER {
                    rfc1483VcMux(0),
                    rfc1483Llc(1) }
    MAX-ACCESS  read-create
    STATUS      current
    DESCRIPTION
        "Specifies the encapsulation used by the circuit to carry IP datagrams.
        Encapsulations are as specified in RFC1483 Multiprotocol Interconnect
        over ATM."
    DEFVAL    { rfc1483VcMux }
    ::= { juniAtmSubIfSvcConfigEntry 3 }

juniAtmSubIfSvcConfigServiceCategory OBJECT-TYPE
    SYNTAX      INTEGER {
                    ubr(0),
                    ubrPcr(1),
                    nrtVbr(2),
                    cbr(3),
                    rtVbr(4) }
    MAX-ACCESS  read-create
    STATUS      current
    DESCRIPTION
        "Service category for this circuit:
            ubr         Unspecified Bit Rate (best effort).
            ubrPcr      Unspecified Bit Rate with Peak Cell Rate limit.
            nrtVbr      Non-RealTime Variable Bit Rate.
            cbr         Constant Bit Rate.
            rtVbr       Realtime Variable Bit Rate."
    DEFVAL    { ubr }
    ::= { juniAtmSubIfSvcConfigEntry 4 }

juniAtmSubIfSvcConfigPcr OBJECT-TYPE
    SYNTAX      Unsigned32
    UNITS       "kbps"
    MAX-ACCESS  read-create
    STATUS      current
    DESCRIPTION
        "Peak Cell Rate, in kilo-bits per second (kbps), of this circuit."
    DEFVAL    { 0 }
    ::= { juniAtmSubIfSvcConfigEntry 5 }

juniAtmSubIfSvcConfigScr OBJECT-TYPE
    SYNTAX      Unsigned32
    UNITS       "kbps"
    MAX-ACCESS  read-create
    STATUS      current
    DESCRIPTION
        "Sustained Cell Rate, in kilo-bits per second (kbps), of this circuit."
    DEFVAL    { 0 }
    ::= { juniAtmSubIfSvcConfigEntry 6 }

juniAtmSubIfSvcConfigMbs OBJECT-TYPE
    SYNTAX      Unsigned32
    UNITS       "cells"
    MAX-ACCESS  read-create
    STATUS      current
    DESCRIPTION
        "Maximum Burst Size, in cells, of this circuit."
    DEFVAL    { 0 }
    ::= { juniAtmSubIfSvcConfigEntry 7 }

juniAtmSubIfSvcConfigCdvt OBJECT-TYPE
    SYNTAX      Unsigned32
    UNITS       "100us"
    MAX-ACCESS  read-create
    STATUS      obsolete
    DESCRIPTION
        "Specify the network Cell Delay Variation Tolerance."
    ::= { juniAtmSubIfSvcConfigEntry 8 }

juniAtmSubIfSvcConfigClp0 OBJECT-TYPE
    SYNTAX      TruthValue
    MAX-ACCESS  read-create
    STATUS      current
    DESCRIPTION
        "Specify that only CLP0 cells are to be policed according to the traffic
        contract.  CLP1 cells are forwarded on a best-effort basis
        CLP-significant model for (VBR.2, VBR.3 conformance)."
    ::= { juniAtmSubIfSvcConfigEntry 9 }

juniAtmSubIfSvcConfigTagging OBJECT-TYPE
    SYNTAX      TruthValue
    MAX-ACCESS  read-create
    STATUS      current
    DESCRIPTION
        "Specify that CLP0 cells should be tagged for SCR policing (VBR.3
        conformance)."
    ::= { juniAtmSubIfSvcConfigEntry 10 }

juniAtmSubIfSvcConfigObserve OBJECT-TYPE
    SYNTAX      TruthValue
    MAX-ACCESS  read-create
    STATUS      obsolete
    DESCRIPTION
        "Specify that no policing action is to be taken; only counters are
        incremented."
    ::= { juniAtmSubIfSvcConfigEntry 11 }

juniAtmSubIfSvcConfigPacketDiscard OBJECT-TYPE
    SYNTAX      TruthValue
    MAX-ACCESS  read-create
    STATUS      current
    DESCRIPTION
        "Enable early packet Discard  for this circuit."
    ::= { juniAtmSubIfSvcConfigEntry 12 }

juniAtmSubIfSvcConfigDestE164Address OBJECT-TYPE
    SYNTAX      AtmAddr (SIZE(0|8))
    MAX-ACCESS  read-create
    STATUS      current
    DESCRIPTION
        "Specifies the destination ATM E164 address of the circuit."
    ::= { juniAtmSubIfSvcConfigEntry 13 }

juniAtmSubIfDescriptionExport OBJECT-TYPE
    SYNTAX      TruthValue
    MAX-ACCESS  read-write
    STATUS      current
    DESCRIPTION
        "Enabling of this object will program the subinterface description down
        to the applicable line card.  Note, the subinterface description sent
        down to the line card is a truncated version (32 bytes) of the ifAlias."
    DEFVAL    { false }
    ::= { juniAtmSubIfLayer 7 }


--
-- The ATM NBMA table
--
juniAtmNbmaMapTable OBJECT-TYPE
    SYNTAX      SEQUENCE OF JuniAtmNbmaMapEntry
    MAX-ACCESS  not-accessible
    STATUS      current
    DESCRIPTION
        "This table contains entries for ATM NBMA maps."
    ::= { juniAtmNbma 1 }

juniAtmNbmaMapEntry OBJECT-TYPE
    SYNTAX      JuniAtmNbmaMapEntry
    MAX-ACCESS  not-accessible
    STATUS      current
    DESCRIPTION
        "Each entry describes the characteristics of an ATM NBMA map."
    INDEX     { juniAtmNbmaMapName,
                juniAtmNbmaMapVcd }
    ::= { juniAtmNbmaMapTable 1 }

JuniAtmNbmaMapEntry ::= SEQUENCE {
    juniAtmNbmaMapName       JuniAtmNbmaMapName,
    juniAtmNbmaMapVcd        Integer32,
    juniAtmNbmaMapIpAddress  IpAddress,
    juniAtmNbmaMapVpi        AtmVpIdentifier,
    juniAtmNbmaMapVci        AtmVcIdentifier,
    juniAtmNbmaMapIfIndex    InterfaceIndexOrZero,
    juniAtmNbmaMapBroadcast  TruthValue,
    juniAtmNbmaMapRowStatus  RowStatus }

juniAtmNbmaMapName OBJECT-TYPE
    SYNTAX      JuniAtmNbmaMapName
    MAX-ACCESS  not-accessible
    STATUS      current
    DESCRIPTION
        "The NBMA map name."
    ::= { juniAtmNbmaMapEntry 1 }

juniAtmNbmaMapVcd OBJECT-TYPE
    SYNTAX      Integer32 (0..2147483647)
    MAX-ACCESS  not-accessible
    STATUS      current
    DESCRIPTION
        "An integer identifier for the ATM circuit, used in conjunction with the
        command-line interface.

        The value must be unique among VCs configured on the same ATM
        interface."
    ::= { juniAtmNbmaMapEntry 2 }

juniAtmNbmaMapIpAddress OBJECT-TYPE
    SYNTAX      IpAddress
    MAX-ACCESS  read-create
    STATUS      current
    DESCRIPTION
        "The IP address associated with this entry."
    ::= { juniAtmNbmaMapEntry 3 }

juniAtmNbmaMapVpi OBJECT-TYPE
    SYNTAX      AtmVpIdentifier
    MAX-ACCESS  read-only
    STATUS      current
    DESCRIPTION
        "The VPI identifier of the ATM circuit."
    ::= { juniAtmNbmaMapEntry 4 }

juniAtmNbmaMapVci OBJECT-TYPE
    SYNTAX      AtmVcIdentifier
    MAX-ACCESS  read-only
    STATUS      current
    DESCRIPTION
        "The VCI identifier of the ATM circuit."
    ::= { juniAtmNbmaMapEntry 5 }

juniAtmNbmaMapIfIndex OBJECT-TYPE
    SYNTAX      InterfaceIndexOrZero
    MAX-ACCESS  read-only
    STATUS      current
    DESCRIPTION
        "The ifIndex of the ATM major interface associated with this entry.
         The value of this object will be zero when the map is not applied
         to an interface. "
    ::= { juniAtmNbmaMapEntry 6 }

juniAtmNbmaMapBroadcast OBJECT-TYPE
    SYNTAX      TruthValue
    MAX-ACCESS  read-create
    STATUS      current
    DESCRIPTION
        "The broadcast enable/disable setting for this entry.  The value true(1)
        enable broadcast support; disable(2) disabled broadcast support for this
        entry."
    ::= { juniAtmNbmaMapEntry 7 }

juniAtmNbmaMapRowStatus OBJECT-TYPE
    SYNTAX      RowStatus
    MAX-ACCESS  read-create
    STATUS      current
    DESCRIPTION
        "Controls creation/deletion of entries in this table according to the
        RowStatus textual convention, constrained to support the following
        values only:
            createAndGo
            destroy

        Additional notes to aid the network manager:
         - NBMA maps are not supported on dynamic interface.
         - NBMA maps can only be applied to a single major ATM interface at a
           time.
         - NBMA maps cannot be deleted unless the map is removed from the ATM
           interface (juniAtmNbmaMapIfIndex = 0).
         - The values of juniAtmNbmaMapVpi, juniAtmNbmaMapVci and
           juniAtmNbmaMapIfIndex are zero until the map is applied to a major
           ATM interface.
         - To create an entry in this table, the following objects must be
           present in the set PDU:
               juniAtmNbmaMapIpAddress
               juniAtmNbmaMapBroadcast
               juniAtmNbmaMapRowStatus
         - Once created, only the following objects can be modified:
               juniAtmNbmaMapBroadcast "
    ::= { juniAtmNbmaMapEntry 8 }

juniAtmNbmaMapListTable OBJECT-TYPE
    SYNTAX      SEQUENCE OF JuniAtmNbmaMapListEntry
    MAX-ACCESS  not-accessible
    STATUS      current
    DESCRIPTION
        "This table contains entries for ATM NBMA map lists."
    ::= { juniAtmNbma 2 }

juniAtmNbmaMapListEntry OBJECT-TYPE
    SYNTAX      JuniAtmNbmaMapListEntry
    MAX-ACCESS  not-accessible
    STATUS      current
    DESCRIPTION
        "Each entry describes the characteristics of an ATM NBMA map."
    INDEX     { IMPLIED juniAtmNbmaMapListName }
    ::= { juniAtmNbmaMapListTable 1 }

JuniAtmNbmaMapListEntry ::= SEQUENCE {
    juniAtmNbmaMapListName       JuniAtmNbmaMapName,
    juniAtmNbmaMapListRowStatus  RowStatus }

juniAtmNbmaMapListName OBJECT-TYPE
    SYNTAX      JuniAtmNbmaMapName
    MAX-ACCESS  not-accessible
    STATUS      current
    DESCRIPTION
        "The NBMA Map List name."
    ::= { juniAtmNbmaMapListEntry 1 }

juniAtmNbmaMapListRowStatus OBJECT-TYPE
    SYNTAX      RowStatus
    MAX-ACCESS  read-create
    STATUS      current
    DESCRIPTION
        "Controls creation/deletion of entries in this table according to the
        RowStatus textual convention, constrained to support the following
        values only:
            createAndGo
            destroy "
    ::= { juniAtmNbmaMapListEntry 2 }


--
-- The ATM ping tests.
--

--
-- ATM ping test types.
--
juniAtmPingTestTypes  OBJECT IDENTIFIER
    ::= { juniAtmPing 1 }

juniAtmPingTestOamSeg  OBJECT-IDENTITY
    STATUS    current
    DESCRIPTION
        "This identifies an OAM Ping (multiple loopbacks) Test on a VPL, VPC,
        VCL, or VCC termination point, using segment OAM cells.

        The test type must have appended to it a code that uniquely identifies
        an intermediate point responsible for looping back each cell.  If this
        is absent, the loopbacks are performed at the end of the segment or
        connection.

        E.g., the OID { juniAtmPingTestOamSeg 5 } identifies that the loopbacks
        should be performed at the intermediate point labeled 5."
    ::= { juniAtmPingTestTypes 1 }

juniAtmPingTestOamE2E  OBJECT-IDENTITY
    STATUS    current
    DESCRIPTION
        "This identifies an OAM Ping (multiple loopbacks) Test on a VPL, VPC,
        VCL, or VCC termination point, using end-to-end OAM cells."
    ::= { juniAtmPingTestTypes 2 }


--
-- The juniAtmVpPingTable extends the ATM-FORUM-SNMP-M4-MIB.atmM4VpTestTable.
--
juniAtmVpPingTable OBJECT-TYPE
    SYNTAX      SEQUENCE OF JuniAtmVpPingEntry
    MAX-ACCESS  not-accessible
    STATUS      current
    DESCRIPTION
        "This table contains entries for extending the ATM-FORUM-SNMP-M4-MIB
        atmM4VpTestTable to do ping (multiple loopback) type testing."
    ::= { juniAtmPing 2 }

juniAtmVpPingEntry OBJECT-TYPE
    SYNTAX      JuniAtmVpPingEntry
    MAX-ACCESS  not-accessible
    STATUS      current
    DESCRIPTION
        "Each entry describes the characteristics, status and results of the
        most recent ATM ping test."
    INDEX     { ifIndex,
                atmVplVpi,
                atmfM4VpTestObject }
    ::= { juniAtmVpPingTable 1 }

JuniAtmVpPingEntry ::= SEQUENCE {
    juniAtmVpPingProbeCount          Unsigned32,
    juniAtmVpPingTimeOut             Unsigned32,
    juniAtmVpPingCtlTrapGeneration   BITS,
    juniAtmVpPingSentProbes          Unsigned32,
    juniAtmVpPingProbeResponses      Unsigned32,
    juniAtmVpPingStartTime           TimeStamp,
    juniAtmVpPingMinRtt              Unsigned32,
    juniAtmVpPingMaxRtt              Unsigned32,
    juniAtmVpPingAverageRtt          Unsigned32 }

juniAtmVpPingProbeCount OBJECT-TYPE
    SYNTAX      Unsigned32 (1..32)
    UNITS       "probes"
    MAX-ACCESS  read-write
    STATUS      current
    DESCRIPTION
        "The number of ping probes (OAM cells) to be sent to complete the test."
    DEFVAL    { 5 }
    ::= { juniAtmVpPingEntry 1 }

juniAtmVpPingTimeOut OBJECT-TYPE
    SYNTAX      Unsigned32 (1..5)
    UNITS       "seconds"
    MAX-ACCESS  read-write
    STATUS      current
    DESCRIPTION
        "Specifies the time-out value, in seconds, for a remote ping operation."
    DEFVAL    { 5 }
    ::= { juniAtmVpPingEntry 2 }

juniAtmVpPingCtlTrapGeneration OBJECT-TYPE
    SYNTAX      BITS {
                    testCompletion(0) }
    MAX-ACCESS  read-write
    STATUS      current
    DESCRIPTION
        "The value of this object determines when and if to generate a
        notification for this entry:

        testCompletion(0) - Generate a juniPingTestCompleted notification.

        The value of this object defaults to zero, indicating that no
        notification has been selected."
    DEFVAL    { { } }
    ::= { juniAtmVpPingEntry 3 }

juniAtmVpPingSentProbes OBJECT-TYPE
    SYNTAX      Unsigned32
    UNITS       "probes"
    MAX-ACCESS  read-only
    STATUS      current
    DESCRIPTION
        "The number of ping probes (OAM cells) that have been sent thus far for
        this test.  The value of this object MUST be set to zero when the
        atmfM4VpTestStatus object transitions from notInUse(0) to inUse(1)."
    DEFVAL    { 0 }
    ::= { juniAtmVpPingEntry 4 }

juniAtmVpPingProbeResponses OBJECT-TYPE
    SYNTAX      Unsigned32
    UNITS       "probes"
    MAX-ACCESS  read-only
    STATUS      current
    DESCRIPTION
        "The number of ping responses that have been received thus far for this
        test.  The value of this object MUST be set to zero when the
        atmfM4VpTestStatus object transitions from notInUse(0) to inUse(1)."
    DEFVAL    { 0 }
    ::= { juniAtmVpPingEntry 5 }

juniAtmVpPingStartTime OBJECT-TYPE
    SYNTAX      TimeStamp
    MAX-ACCESS  read-only
    STATUS      current
    DESCRIPTION
        "The time (sysUpTime) when the test started."
    DEFVAL    { 0 }
    ::= { juniAtmVpPingEntry 6 }

juniAtmVpPingMinRtt OBJECT-TYPE
    SYNTAX      Unsigned32
    UNITS       "milliseconds"
    MAX-ACCESS  read-only
    STATUS      current
    DESCRIPTION
        "The shortest round-trip-time (RTT) for the pings that have received
        responses.  The value of this object MUST be set to zero when the
        atmfM4VpTestStatus object transitions from notInUse(0) to inUse(1).  A
        value of zero for this object implies that no ping responses have been
        received for the current test."
    ::= { juniAtmVpPingEntry 7 }

juniAtmVpPingMaxRtt OBJECT-TYPE
    SYNTAX      Unsigned32
    UNITS       "milliseconds"
    MAX-ACCESS  read-only
    STATUS      current
    DESCRIPTION
        "The longest round-trip-time (RTT) for the pings that have received
        responses.  The value of this object MUST be set to zero when the
        atmfM4VpTestStatus object transitions from notInUse(0) to inUse(1).  A
        value of zero for this object implies that no ping responses have been
        received for the current test."
    ::= { juniAtmVpPingEntry 8 }

juniAtmVpPingAverageRtt OBJECT-TYPE
    SYNTAX      Unsigned32
    UNITS       "milliseconds"
    MAX-ACCESS  read-only
    STATUS      current
    DESCRIPTION
        "The average round-trip-time (RTT) for all the pings that have received
        responses.  The value of this object MUST be set to zero when the
        atmfM4VpTestStatus object transitions from notInUse(0) to inUse(1).  A
        value of zero for this object implies that no ping responses have been
        received for the current test."
    ::= { juniAtmVpPingEntry 9 }


--
-- The juniAtmVcPingTable extends the ATM-FORUM-SNMP-M4-MIB.atmM4VcTestTable.
--
juniAtmVcPingTable OBJECT-TYPE
    SYNTAX      SEQUENCE OF JuniAtmVcPingEntry
    MAX-ACCESS  not-accessible
    STATUS      current
    DESCRIPTION
        "This table contains entries for extending the ATM-FORUM-SNMP-M4-MIB
        atmM4VcTestTable to do ping (multiple loopback) type testing."
    ::= { juniAtmPing 3 }

juniAtmVcPingEntry OBJECT-TYPE
    SYNTAX      JuniAtmVcPingEntry
    MAX-ACCESS  not-accessible
    STATUS      current
    DESCRIPTION
        "Each entry describes the characteristics, status and results of the
        most recent ATM ping test."
    INDEX     { ifIndex,
                atmVclVpi,
                atmVclVci,
                atmfM4VcTestObject }
    ::= { juniAtmVcPingTable 1 }

JuniAtmVcPingEntry ::= SEQUENCE {
    juniAtmVcPingProbeCount          Unsigned32,
    juniAtmVcPingTimeOut             Unsigned32,
    juniAtmVcPingCtlTrapGeneration   BITS,
    juniAtmVcPingSentProbes          Unsigned32,
    juniAtmVcPingProbeResponses      Unsigned32,
    juniAtmVcPingStartTime           TimeStamp,
    juniAtmVcPingMinRtt              Unsigned32,
    juniAtmVcPingMaxRtt              Unsigned32,
    juniAtmVcPingAverageRtt          Unsigned32 }

juniAtmVcPingProbeCount OBJECT-TYPE
    SYNTAX      Unsigned32 (1..32)
    UNITS       "probes"
    MAX-ACCESS  read-write
    STATUS      current
    DESCRIPTION
        "The number of ping probes (OAM cells) to be sent to complete the test."
    DEFVAL    { 5 }
    ::= { juniAtmVcPingEntry 1 }

juniAtmVcPingTimeOut OBJECT-TYPE
    SYNTAX      Unsigned32 (1..5)
    UNITS       "seconds"
    MAX-ACCESS  read-write
    STATUS      current
    DESCRIPTION
        "Specifies the time-out value, in seconds, for a remote ping operation."
    DEFVAL    { 5 }
    ::= { juniAtmVcPingEntry 2 }

juniAtmVcPingCtlTrapGeneration OBJECT-TYPE
    SYNTAX      BITS {
                    testCompletion(0) }
    MAX-ACCESS  read-write
    STATUS      current
    DESCRIPTION
        "The value of this object determines when and if to generate a
        notification for this entry:
            testCompletion(0) - Generate a juniPingTestCompleted notification.

        The value of this object defaults to zero, indicating that no
        notification has been selected."
    DEFVAL    { { } }
    ::= { juniAtmVcPingEntry 3 }

juniAtmVcPingSentProbes OBJECT-TYPE
    SYNTAX      Unsigned32
    UNITS       "probes"
    MAX-ACCESS  read-only
    STATUS      current
    DESCRIPTION
        "The number of ping probes (OAM cells) that have been sent thus far for
        this test.  The value of this object MUST be set to zero when the
        atmfM4VcTestStatus object transitions from notInUse(0) to inUse(1)."
    DEFVAL    { 0 }
    ::= { juniAtmVcPingEntry 4 }

juniAtmVcPingProbeResponses OBJECT-TYPE
    SYNTAX      Unsigned32
    UNITS       "probes"
    MAX-ACCESS  read-only
    STATUS      current
    DESCRIPTION
        "The number of ping responses that have been received thus far for this
        test.  The value of this object MUST be set to zero when the
        atmfM4VcTestStatus object transitions from notInUse(0) to inUse(1)."
    DEFVAL    { 0 }
    ::= { juniAtmVcPingEntry 5 }

juniAtmVcPingStartTime OBJECT-TYPE
    SYNTAX      TimeStamp
    MAX-ACCESS  read-only
    STATUS      current
    DESCRIPTION
        "The time (sysUpTime) when the test started."
    DEFVAL    { 0 }
    ::= { juniAtmVcPingEntry 6 }

juniAtmVcPingMinRtt OBJECT-TYPE
    SYNTAX      Unsigned32
    UNITS       "milliseconds"
    MAX-ACCESS  read-only
    STATUS      current
    DESCRIPTION
        "The shortest round-trip-time (RTT) for the pings that have received
        responses.  The value of this object MUST be set to zero when the
        atmfM4VcTestStatus object transitions from notInUse(0) to inUse(1).  A
        value of zero for this object implies that no ping responses have been
        received for the current test."
    ::= { juniAtmVcPingEntry 7 }

juniAtmVcPingMaxRtt OBJECT-TYPE
    SYNTAX      Unsigned32
    UNITS       "milliseconds"
    MAX-ACCESS  read-only
    STATUS      current
    DESCRIPTION
        "The longest round-trip-time (RTT) for the pings that have received
        responses.  The value of this object MUST be set to zero when the
        atmfM4VcTestStatus object transitions from notInUse(0) to inUse(1).  A
        value of zero for this object implies that no ping responses have been
        received for the current test."
    ::= { juniAtmVcPingEntry 8 }

juniAtmVcPingAverageRtt OBJECT-TYPE
    SYNTAX      Unsigned32
    UNITS       "milliseconds"
    MAX-ACCESS  read-only
    STATUS      current
    DESCRIPTION
        "The average round-trip-time (RTT) for all the pings that have received
        responses.  The value of this object MUST be set to zero when the
        atmfM4VcTestStatus object transitions from notInUse(0) to inUse(1).  A
        value of zero for this object implies that no ping responses have been
        received for the current test."
    ::= { juniAtmVcPingEntry 9 }


-- +++++++++++++++++++++++++++++++++++++++++++++++++++++++++++++++++++++++++++++
-- ATM ping test codes.
-- +++++++++++++++++++++++++++++++++++++++++++++++++++++++++++++++++++++++++++++
juniAtmPingTestCode  OBJECT IDENTIFIER ::= { juniAtmPing 4 }

juniAtmPingTestCodeOamDisabled  OBJECT-IDENTITY
    STATUS      current
    DESCRIPTION
        "This test code indicates that the ATM ping operation cannot be
        initiated or is aborted because the juniAtmIfOamCellRxAdminState is set
        to disabled."
    ::= { juniAtmPingTestCode 1 }

juniAtmPingTestCodeCircuitDown  OBJECT-IDENTITY
    STATUS      current
    DESCRIPTION
        "This test code indicates that the ATM ping operation cannot be
        initiated or is aborted because the operational status of the ATM
        circuit is down."
    ::= { juniAtmPingTestCode 2 }

juniAtmPingTestCodeStopped  OBJECT-IDENTITY
    STATUS      current
    DESCRIPTION
        "This test code indicates that the ATM ping operation is
        administratively stopped by an External Management."
    ::= { juniAtmPingTestCode 3 }

juniAtmPingTestCodeOamVcOperState  OBJECT-IDENTITY
    STATUS      current
    DESCRIPTION
        "This test code indicates that the ATM ping operation cannot be
        initiated or is aborted because the circuit is down because of a OAM
        fault condition.  This is possible if juniAtmCircuitVcOamOperStatus is
        one of the following:
            oamVcOperStateAisState(0)  - AIS cell received or underlying
                                         physical layer reporting transmission
                                         path AIS.
            oamVcOperStateRdiState(1)  - RDI cell received."
    ::= { juniAtmPingTestCode 4 }

juniAtmPingTestCodeMaxPingCountReached  OBJECT-IDENTITY
    STATUS      current
    DESCRIPTION
        "This test code indicates that the ping operation cannot be initiated as
        the maximum number of ping possible on this interfaces exceeds the
        allowable limit."
    ::= { juniAtmPingTestCode 5 }

juniAtmPingTestCodeInvalidParams  OBJECT-IDENTITY
    STATUS      current
    DESCRIPTION
        "This Test Code identities the Ping operation cannot be initiated as one
        or more of the Ping Parameters is Invalid."
    ::= { juniAtmPingTestCode 6 }


-- +++++++++++++++++++++++++++++++++++++++++++++++++++++++++++++++++++++++++++++
-- ATM Subinterface information by interface location
-- +++++++++++++++++++++++++++++++++++++++++++++++++++++++++++++++++++++++++++++
juniAtmSubIfLocationType OBJECT-TYPE
    SYNTAX      JuniInterfaceLocationType
    MAX-ACCESS  read-only
    STATUS      current
    DESCRIPTION
        "Describes the interpretation of JuniInterfaceLocationValue object
        values into platform-dependent interface location components, e.g.,
        'slot.port' on an ERX."
    ::= { juniAtmLocation 1 }

juniAtmSubIfLocationTable OBJECT-TYPE
    SYNTAX      SEQUENCE OF JuniAtmSubIfLocationEntry
    MAX-ACCESS  not-accessible
    STATUS      current
    DESCRIPTION
        "The entries in this table report the ifIndex of ATM Subinterfaces by
        location."
    ::= { juniAtmLocation 2 }

juniAtmSubIfLocationEntry OBJECT-TYPE
    SYNTAX      JuniAtmSubIfLocationEntry
    MAX-ACCESS  not-accessible
    STATUS      current
    DESCRIPTION
        "A specification of ATM subinterfaces by location."
    INDEX     { juniAtmSubIfLocationIndex,
                juniAtmSubIfDistinguisher }
    ::= { juniAtmSubIfLocationTable 1 }

JuniAtmSubIfLocationEntry ::= SEQUENCE {
    juniAtmSubIfLocationIndex       JuniInterfaceLocationValue,
    juniAtmSubIfLocationIfIndex     InterfaceIndex }

juniAtmSubIfLocationIndex OBJECT-TYPE
    SYNTAX      JuniInterfaceLocationValue
    MAX-ACCESS  not-accessible
    STATUS      current
    DESCRIPTION
        "The value of a platform interface location."
    ::= { juniAtmSubIfLocationEntry 1 }

juniAtmSubIfLocationIfIndex OBJECT-TYPE
    SYNTAX      InterfaceIndex
    MAX-ACCESS  read-only
    STATUS      current
    DESCRIPTION
        "The ifIndex value of this subinterface."
    ::= { juniAtmSubIfLocationEntry 2 }


-- +++++++++++++++++++++++++++++++++++++++++++++++++++++++++++++++++++++++++++++
-- Notification control objects
-- +++++++++++++++++++++++++++++++++++++++++++++++++++++++++++++++++++++++++++++
-- No global notification controls are defined.  Placeholder follows.
-- juniAtmTrapControl      OBJECT IDENTIFIER ::= { juniAtmMIB 2 }

-- +++++++++++++++++++++++++++++++++++++++++++++++++++++++++++++++++++++++++++++
-- Notifications
-- +++++++++++++++++++++++++++++++++++++++++++++++++++++++++++++++++++++++++++++
-- The following two OBJECT IDENTIFIERS are used to define SNMPv2
-- Notifications that are easily translated into SNMPv1 Traps.

juniAtmTraps            OBJECT IDENTIFIER ::= { juniAtmMIB 3 }
juniAtmTrapPrefix       OBJECT IDENTIFIER ::= { juniAtmTraps 0 }

juniAtmVpPingTestCompleted NOTIFICATION-TYPE
    OBJECTS {
        atmfM4VpTestId,
        atmfM4VpTestType,
        atmfM4VpTestResult,
        juniAtmVpPingProbeCount,
        juniAtmVpPingSentProbes,
        juniAtmVpPingProbeResponses,
        juniAtmVpPingMinRtt,
        juniAtmVpPingMaxRtt,
        juniAtmVpPingAverageRtt,
        atmfM4VpTestCode }
    STATUS      current
    DESCRIPTION
        "Generated at the completion of a AtmfM4VpTest when the corresponding
        juniAtmVpPingCtlTrapGeneration object has the testCompletion(0) bit
        set."
    ::= { juniAtmTrapPrefix 1 }

juniAtmVcPingTestCompleted NOTIFICATION-TYPE
    OBJECTS {
        atmfM4VcTestId,
        atmfM4VcTestType,
        atmfM4VcTestResult,
        juniAtmVcPingProbeCount,
        juniAtmVcPingSentProbes,
        juniAtmVcPingProbeResponses,
        juniAtmVcPingMinRtt,
        juniAtmVcPingMaxRtt,
        juniAtmVcPingAverageRtt,
        atmfM4VcTestCode }
    STATUS      current
    DESCRIPTION
        "Generated at the completion of a AtmfM4VcTest when the corresponding
        juniAtmVcPingCtlTrapGeneration object has the testCompletion(0) bit
        set."
    ::= { juniAtmTrapPrefix 2 }


-- +++++++++++++++++++++++++++++++++++++++++++++++++++++++++++++++++++++++++++++
-- Conformance information
-- +++++++++++++++++++++++++++++++++++++++++++++++++++++++++++++++++++++++++++++
juniAtmConformance OBJECT IDENTIFIER ::= { juniAtmMIB 4 }
juniAtmCompliances OBJECT IDENTIFIER ::= { juniAtmConformance 1 }
juniAtmGroups      OBJECT IDENTIFIER ::= { juniAtmConformance 2 }

--
-- compliance statements
--
juniAtmCompliance  MODULE-COMPLIANCE
    STATUS      obsolete
    DESCRIPTION
        "Obsolete compliance statement for entities which implement the Juniper
        ATM MIB.  This statement became obsolete when support was added for NBMA
        map lists and ATM ping."
    MODULE   -- this module
        MANDATORY-GROUPS {
            juniAtmGroup,
            juniAtmAal5Group,
            juniAtmSubIfGroup }
        GROUP       juniAtmVpTunnelGroup
            DESCRIPTION
                "The juniAtmVpTunnelGroup is mandatory only for entities that
                support a VP Tunnel functionality."
    ::= { juniAtmCompliances 1 }                                   -- JUNOSe 3.0

juniAtmCompliance2  MODULE-COMPLIANCE
    STATUS      obsolete
    DESCRIPTION
        "Obsolete compliance statement for entities which implement the Juniper
        ATM MIB.  This statement became obsolete when support was added for
        traffic shapping on VCC subinterfaces."
    MODULE   -- this module
        MANDATORY-GROUPS {
            juniAtmGroup2,
            juniAtmAal5Group,
            juniAtmSubIfGroup2,
            juniAtmVpPingControlGroup,
            juniAtmVcPingControlGroup,
            juniAtmPingTrapGroup }
        GROUP       juniAtmVpTunnelGroup
            DESCRIPTION
                "The juniAtmVpTunnelGroup is mandatory only for entities that
                support a VP Tunnel functionality."
        GROUP       juniAtmNbmaMapGroup
            DESCRIPTION
                "The juniAtmNbmaMapGroup is mandatory only for entities that
                support NBMA interfaces over ATM."
    ::= { juniAtmCompliances 2 }                                   -- JUNOSe 3.2

juniAtmCompliance3  MODULE-COMPLIANCE
    STATUS      obsolete
    DESCRIPTION
        "Obsolete compliance statement for entities which implement the Juniper
        ATM MIB.  This statement became obsolete when support was added for
        connection admission control (CAC)."
    MODULE   -- this module
        MANDATORY-GROUPS {
            juniAtmGroup2,
            juniAtmAal5Group,
            juniAtmSubIfGroup2,
            juniAtmVpPingControlGroup,
            juniAtmVcPingControlGroup,
            juniAtmPingTrapGroup }
        GROUP       juniAtmVpTunnelGroup
            DESCRIPTION
                "The juniAtmVpTunnelGroup is mandatory only for entities that
                support a VP Tunnel functionality."
        GROUP       juniAtmNbmaMapGroup
            DESCRIPTION
                "The juniAtmNbmaMapGroup is mandatory only for entities that
                support NBMA interfaces over ATM."
        GROUP       juniAtmTrafficShapingGroup
            DESCRIPTION
                "The juniAtmTrafficShapingGroup is mandatory only for entities
                that support ATM traffic shaping."
    ::= { juniAtmCompliances 3 }                                   -- JUNOSe 3.3

juniAtmCompliance4  MODULE-COMPLIANCE
    STATUS      obsolete
    DESCRIPTION
        "Obsolete compliance statement for entities which implement the Juniper
        ATM MIB.  This statement became obsolete when ATM SVC, CAC used
        bandwidth and sub-interface address objects were added."
    MODULE   -- this module
        MANDATORY-GROUPS {
            juniAtmGroup3,
            juniAtmAal5Group,
            juniAtmSubIfGroup2,
            juniAtmVpPingControlGroup,
            juniAtmVcPingControlGroup,
            juniAtmPingTrapGroup }
        GROUP       juniAtmVpTunnelGroup
            DESCRIPTION
                "The juniAtmVpTunnelGroup is mandatory only for entities that
                support a VP Tunnel functionality."
        GROUP       juniAtmNbmaMapGroup
            DESCRIPTION
                "The juniAtmNbmaMapGroup is mandatory only for entities that
                support NBMA interfaces over ATM."
        GROUP       juniAtmTrafficShapingGroup
            DESCRIPTION
                "The juniAtmTrafficShapingGroup is mandatory only for entities
                that support ATM traffic shaping."
    ::= { juniAtmCompliances 4 }                                   -- JUNOSe 3.4

juniAtmCompliance5  MODULE-COMPLIANCE
    STATUS      obsolete
    DESCRIPTION
        "Obsolete compliance statement for entities which implement the Juniper
        ATM MIB.  This statement became obsolete when CAC recieve bandwith and
        E164 public addressing support was added."
    MODULE   -- this module
        MANDATORY-GROUPS {
            juniAtmGroup4,
            juniAtmAal5Group,
            juniAtmSubIfGroup3,
            juniAtmVpPingControlGroup,
            juniAtmVcPingControlGroup,
            juniAtmPingTrapGroup,
            juniAtmSvcGroup }
        GROUP       juniAtmVpTunnelGroup
            DESCRIPTION
                "The juniAtmVpTunnelGroup is mandatory only for entities that
                support a VP Tunnel functionality."
        GROUP       juniAtmNbmaMapGroup
            DESCRIPTION
                "The juniAtmNbmaMapGroup is mandatory only for entities that
                support NBMA interfaces over ATM."
        GROUP       juniAtmTrafficShapingGroup
            DESCRIPTION
                "The juniAtmTrafficShapingGroup is mandatory only for entities
                that support ATM traffic shaping."
    ::= { juniAtmCompliances 5 }                                   -- JUNOSe 4.0

juniAtmCompliance6  MODULE-COMPLIANCE
    STATUS      obsolete
    DESCRIPTION
        "Obsolete compliance statement for entities which implement the Juniper
        ATM MIB.  This statement became obsolete when F4 flow OAM circuit config
        and stats tables were added to the Juniper ATM MIB."
    MODULE   -- this module
        MANDATORY-GROUPS {
            juniAtmGroup5,
            juniAtmAal5Group,
            juniAtmSubIfGroup4,
            juniAtmVpPingControlGroup,
            juniAtmVcPingControlGroup,
            juniAtmPingTrapGroup,
            juniAtmSvcGroup2 }
        GROUP       juniAtmVpTunnelGroup
            DESCRIPTION
                "The juniAtmVpTunnelGroup is mandatory only for entities that
                support a VP Tunnel functionality."
        GROUP       juniAtmNbmaMapGroup
            DESCRIPTION
                "The juniAtmNbmaMapGroup is mandatory only for entities that
                support NBMA interfaces over ATM."
        GROUP       juniAtmTrafficShapingGroup
            DESCRIPTION
                "The juniAtmTrafficShapingGroup is mandatory only for entities
                that support ATM traffic shaping."
        GROUP       juniAtmPnniGroup
            DESCRIPTION
                "The juniAtmPnniGroup is mandatory only for entities that
                support PNNI routing for ATM networks."
    ::= { juniAtmCompliances 6 }                                   -- JUNOSe 4.1

juniAtmCompliance7  MODULE-COMPLIANCE
    STATUS      obsolete
    DESCRIPTION
        "Obsolete compliance statement for entities which implement the Juniper
        ATM MIB.  This statement became obsolete when the juniAtmLocationGroup
        was added."
    MODULE   -- this module
        MANDATORY-GROUPS {
            juniAtmGroup6,
            juniAtmAal5Group,
            juniAtmSubIfGroup4,
            juniAtmVpPingControlGroup,
            juniAtmVcPingControlGroup,
            juniAtmPingTrapGroup,
            juniAtmSvcGroup2,
            juniAtmF4OamCircuitGroup }
        GROUP       juniAtmVpTunnelGroup
            DESCRIPTION
                "The juniAtmVpTunnelGroup is mandatory only for entities that
                support a VP Tunnel functionality."
        GROUP       juniAtmNbmaMapGroup
            DESCRIPTION
                "The juniAtmNbmaMapGroup is mandatory only for entities that
                support NBMA interfaces over ATM."
        GROUP       juniAtmTrafficShapingGroup
            DESCRIPTION
                "The juniAtmTrafficShapingGroup is mandatory only for entities
                that support ATM traffic shaping."
        GROUP       juniAtmPnniGroup
            DESCRIPTION
                "The juniAtmPnniGroup is mandatory only for entities that
                support PNNI routing for ATM networks."
    ::= { juniAtmCompliances 7 }                                   -- JUNOSe 5.1

juniAtmCompliance8  MODULE-COMPLIANCE
    STATUS      obsolete
    DESCRIPTION
        "Obsolete compliance statement for entities which implement the Juniper
        ATM MIB.  This statement became obsolete when support was added to
        export the subinterface description to the line cards."
    MODULE   -- this module
        MANDATORY-GROUPS {
            juniAtmGroup6,
            juniAtmAal5Group,
            juniAtmSubIfGroup4,
            juniAtmVpPingControlGroup,
            juniAtmVcPingControlGroup,
            juniAtmPingTrapGroup,
            juniAtmSvcGroup2,
            juniAtmF4OamCircuitGroup }
        GROUP       juniAtmVpTunnelGroup
            DESCRIPTION
                "The juniAtmVpTunnelGroup is mandatory only for entities that
                support a VP Tunnel functionality."
        GROUP       juniAtmNbmaMapGroup
            DESCRIPTION
                "The juniAtmNbmaMapGroup is mandatory only for entities that
                support NBMA interfaces over ATM."
        GROUP       juniAtmTrafficShapingGroup
            DESCRIPTION
                "The juniAtmTrafficShapingGroup is mandatory only for entities
                that support ATM traffic shaping."
        GROUP       juniAtmPnniGroup
            DESCRIPTION
                "The juniAtmPnniGroup is mandatory only for entities that
                support PNNI routing for ATM networks."
        GROUP       juniAtmLocationGroup
            DESCRIPTION
                "The juniAtmLocationGroup is mandatory only for entities that
                support slot and port interface location information"
    ::= { juniAtmCompliances 8 }                                   -- JUNOSe 5.2

juniAtmCompliance9  MODULE-COMPLIANCE
    STATUS      obsolete
    DESCRIPTION
        "Obsolete compliance statement for entities which implement the Juniper
        ATM MIB.  This statement was obsoleted when the juniAtmMartiniGroup was
        added."
    MODULE   -- this module
        MANDATORY-GROUPS {
            juniAtmGroup6,
            juniAtmAal5Group,
            juniAtmSubIfGroup5,
            juniAtmVpPingControlGroup,
            juniAtmVcPingControlGroup,
            juniAtmPingTrapGroup,
            juniAtmSvcGroup2,
            juniAtmF4OamCircuitGroup }
        GROUP       juniAtmVpTunnelGroup
            DESCRIPTION
                "The juniAtmVpTunnelGroup is mandatory only for entities that
                support a VP Tunnel functionality."
        GROUP       juniAtmNbmaMapGroup
            DESCRIPTION
                "The juniAtmNbmaMapGroup is mandatory only for entities that
                support NBMA interfaces over ATM."
        GROUP       juniAtmTrafficShapingGroup
            DESCRIPTION
                "The juniAtmTrafficShapingGroup is mandatory only for entities
                that support ATM traffic shaping."
        GROUP       juniAtmPnniGroup
            DESCRIPTION
                "The juniAtmPnniGroup is mandatory only for entities that
                support PNNI routing for ATM networks."
        GROUP       juniAtmLocationGroup
            DESCRIPTION
                "The juniAtmLocationGroup is mandatory only for entities that
                support slot and port interface location information"
    ::= { juniAtmCompliances 9 }                                   -- JUNOSe 5.3

juniAtmCompliance10  MODULE-COMPLIANCE
    STATUS      obsolete
    DESCRIPTION
        "Obsolete compliance statement for entities which implement the Juniper
        ATM MIB.  This statement became obsolete when 
        juniAtmIfCacAvailableBandwidthRx, juniAtmIfE164Autoconversion, 
        juniAtmIfE164Gateway, and juniAtmIfE164OneToOneAddrTrans were deprecated."
    MODULE   -- this module
        MANDATORY-GROUPS {
            juniAtmGroup6,
            juniAtmAal5Group,
            juniAtmSubIfGroup5,
            juniAtmVpPingControlGroup,
            juniAtmVcPingControlGroup,
            juniAtmPingTrapGroup,
            juniAtmSvcGroup2,
            juniAtmF4OamCircuitGroup }
        GROUP       juniAtmVpTunnelGroup
            DESCRIPTION
                "The juniAtmVpTunnelGroup is mandatory only for entities that
                support a VP Tunnel functionality."
        GROUP       juniAtmNbmaMapGroup
            DESCRIPTION
                "The juniAtmNbmaMapGroup is mandatory only for entities that
                support NBMA interfaces over ATM."
        GROUP       juniAtmTrafficShapingGroup
            DESCRIPTION
                "The juniAtmTrafficShapingGroup is mandatory only for entities
                that support ATM traffic shaping."
        GROUP       juniAtmPnniGroup
            DESCRIPTION
                "The juniAtmPnniGroup is mandatory only for entities that
                support PNNI routing for ATM networks."
        GROUP       juniAtmLocationGroup
            DESCRIPTION
                "The juniAtmLocationGroup is mandatory only for entities that
                support slot and port interface location information"
        GROUP       juniAtmMartiniGroup
            DESCRIPTION
                "The juniAtmMartiniGroup is mandatory only for entities that
                support ATM Martini cell aggregation configuration"
    ::= { juniAtmCompliances 10 }                                  -- JUNOSe 6.0

juniAtmCompliance11  MODULE-COMPLIANCE
    STATUS      obsolete
    DESCRIPTION
        "Obsolete compliance statement for entities which implement the Juniper
        ATM MIB.  This statement became obsolete when juniAtmGroup8 was 
        added."
    MODULE   -- this module
        MANDATORY-GROUPS {
            juniAtmGroup7,
            juniAtmAal5Group,
            juniAtmSubIfGroup5,
            juniAtmVpPingControlGroup,
            juniAtmVcPingControlGroup,
            juniAtmPingTrapGroup,
            juniAtmSvcGroup2,
            juniAtmF4OamCircuitGroup }
        GROUP       juniAtmVpTunnelGroup
            DESCRIPTION
                "The juniAtmVpTunnelGroup is mandatory only for entities that
                support a VP Tunnel functionality."
        GROUP       juniAtmNbmaMapGroup
            DESCRIPTION
                "The juniAtmNbmaMapGroup is mandatory only for entities that
                support NBMA interfaces over ATM."
        GROUP       juniAtmTrafficShapingGroup
            DESCRIPTION
                "The juniAtmTrafficShapingGroup is mandatory only for entities
                that support ATM traffic shaping."
        GROUP       juniAtmPnniGroup
            DESCRIPTION
                "The juniAtmPnniGroup is mandatory only for entities that
                support PNNI routing for ATM networks."
        GROUP       juniAtmLocationGroup
            DESCRIPTION
                "The juniAtmLocationGroup is mandatory only for entities that
                support slot and port interface location information"
        GROUP       juniAtmMartiniGroup
            DESCRIPTION
                "The juniAtmMartiniGroup is mandatory only for entities that
                support ATM Martini cell aggregation configuration"
    ::= { juniAtmCompliances 11 }                                   -- JUNOSe 6.1

juniAtmCompliance12  MODULE-COMPLIANCE
    STATUS      current
    DESCRIPTION
        "The compliance statement for entities which implement the Juniper ATM
        MIB."
    MODULE   -- this module
        MANDATORY-GROUPS {
            juniAtmGroup8,
            juniAtmAal5Group,
            juniAtmSubIfGroup5,
            juniAtmVpPingControlGroup,
            juniAtmVcPingControlGroup,
            juniAtmPingTrapGroup,
            juniAtmSvcGroup2,
            juniAtmF4OamCircuitGroup }
        GROUP       juniAtmVpTunnelGroup
            DESCRIPTION
                "The juniAtmVpTunnelGroup is mandatory only for entities that
                support a VP Tunnel functionality."
        GROUP       juniAtmNbmaMapGroup
            DESCRIPTION
                "The juniAtmNbmaMapGroup is mandatory only for entities that
                support NBMA interfaces over ATM."
        GROUP       juniAtmTrafficShapingGroup
            DESCRIPTION
                "The juniAtmTrafficShapingGroup is mandatory only for entities
                that support ATM traffic shaping."
        GROUP       juniAtmPnniGroup
            DESCRIPTION
                "The juniAtmPnniGroup is mandatory only for entities that
                support PNNI routing for ATM networks."
        GROUP       juniAtmLocationGroup
            DESCRIPTION
                "The juniAtmLocationGroup is mandatory only for entities that
                support slot and port interface location information"
        GROUP       juniAtmMartiniGroup
            DESCRIPTION
                "The juniAtmMartiniGroup is mandatory only for entities that
                support ATM Martini cell aggregation configuration"
    ::= { juniAtmCompliances 12 }                                  -- JUNOSe 7.0

--
-- units of conformance
--
juniAtmGroup  OBJECT-GROUP
    OBJECTS {
        juniAtmNextIfIndex,

        juniAtmIfRowStatus,
        juniAtmIfLowerIfIndex,
        juniAtmIfIlmiVpi,
        juniAtmIfIlmiVci,
        juniAtmIfIlmiVcd,
        juniAtmIfIlmiPollFrequency,
        juniAtmIfIlmiAdminState,
        juniAtmIfUniVersion,
        juniAtmIfOamCellRxAdminState,
        juniAtmIfInCells,
        juniAtmIfOutCells,
        juniAtmIfVcCount,
        juniAtmPvcStatsInCells,
        juniAtmPvcStatsInCellOctets,
        juniAtmPvcStatsInPackets,
        juniAtmPvcStatsInPacketOctets,
        juniAtmPvcStatsOutCells,
        juniAtmPvcStatsOutCellOctets,
        juniAtmPvcStatsOutPackets,
        juniAtmPvcStatsOutPacketOctets,
        juniAtmPvcStatsInCellErrors,
        juniAtmPvcStatsinPacketErrors,
        juniAtmPvcStatsOutCellErrors,
        juniAtmPvcStatsOutPacketErrors,
        juniAtmPvcStatsInPacketDiscards,
        juniAtmPvcStatsInPacketOctetDiscards,
        juniAtmIfCapabilityTrafficShaping,
        juniAtmIfCapabilityOam,
        juniAtmIfCapabilityDefaultVcPerVp,
        juniAtmIfCapabilityNumVpiVciBits,
        juniAtmIfCapabilityMaxVcd,
        juniAtmIfCapabilityMaxVpi,
        juniAtmIfCapabilityMaxVci }
    STATUS      obsolete
    DESCRIPTION
        "Obsolete collection of objects providing management of ATM interfaces
        in a Juniper product.  This group became obsolete when the
        juniAtmIfMapGroup object was added."
    ::= { juniAtmGroups 1 }                                        -- JUNOSe 3.0

juniAtmAal5Group  OBJECT-GROUP
    OBJECTS {
        juniAtmAal5NextIfIndex,

        juniAtmAal5IfRowStatus,
        juniAtmAal5IfLowerIfIndex }
    STATUS      current
    DESCRIPTION
        "A collection of objects providing management of AAL5 interfaces in a
        Juniper product."
    ::= { juniAtmGroups 2 }                                        -- JUNOSe 3.0

juniAtmSubIfGroup  OBJECT-GROUP
    OBJECTS {
        juniAtmSubIfNextIfIndex,

        juniAtmSubIfRowStatus,
        juniAtmSubIfDistinguisher,
        juniAtmSubIfLowerIfIndex,

        juniAtmSubIfVccRowStatus,
        juniAtmSubIfVccVcd,
        juniAtmSubIfVccType,
        juniAtmSubIfVccServiceCategory,
        juniAtmSubIfVccPcr,
        juniAtmSubIfVccScr,
        juniAtmSubIfVccMbs,

        juniAtmCircuitOamAdminStatus,
        juniAtmCircuitOamLoopbackOperStatus,
        juniAtmCircuitVcOamOperStatus,
        juniAtmCircuitOamLoopbackFrequency,
        juniAtmCircuitInOamF5Cells,
        juniAtmCircuitInOamCellsDropped,
        juniAtmCircuitOutOamF5Cells,
        juniAtmCircuitInOamF5EndToEndLoopbackCells,
        juniAtmCircuitInOamF5SegmentLoopbackCells,
        juniAtmCircuitInOamF5AisCells,
        juniAtmCircuitInOamF5RdiCells,
        juniAtmCircuitOutOamF5EndToEndLoopbackCells,
        juniAtmCircuitOutOamF5SegmentLoopbackCells,
        juniAtmCircuitOutOamF5RdiCells }
    STATUS      obsolete
    DESCRIPTION
        "Obsolete collection of objects providing management of ATM
        subinterfaces in a Juniper product.  This group became obsolete when
        juniAtmSubIfNbma, juniAtmSubIfInverseArp, and
        juniAtmSubIfInverseArpRefresh were added."
    ::= { juniAtmGroups 3 }                                        -- JUNOSe 3.0

juniAtmVpTunnelGroup  OBJECT-GROUP
    OBJECTS {
        juniAtmVpTunnelKbps,
        juniAtmVpTunnelRowStatus,
        juniAtmVpTunnelServiceCategory }
    STATUS      current
    DESCRIPTION
        "A collection of objects providing management of VP tunnels in a Juniper
        product."
    ::= { juniAtmGroups 4 }                                        -- JUNOSe 3.0

juniAtmNbmaMapGroup  OBJECT-GROUP
    OBJECTS {
        juniAtmNbmaMapIpAddress,
        juniAtmNbmaMapVpi,
        juniAtmNbmaMapVci,
        juniAtmNbmaMapIfIndex,
        juniAtmNbmaMapBroadcast,
        juniAtmNbmaMapRowStatus,
        juniAtmNbmaMapListRowStatus }
    STATUS      current
    DESCRIPTION
        "A collection of object providing management of NBMA in a Juniper
        product."
    ::= { juniAtmGroups 5 }                                        -- JUNOSe 3.2

juniAtmSubIfGroup2  OBJECT-GROUP
    OBJECTS {
        juniAtmSubIfNextIfIndex,

        juniAtmSubIfRowStatus,
        juniAtmSubIfDistinguisher,
        juniAtmSubIfLowerIfIndex,
        juniAtmSubIfNbma,

        juniAtmSubIfVccRowStatus,
        juniAtmSubIfVccVcd,
        juniAtmSubIfVccType,
        juniAtmSubIfVccServiceCategory,
        juniAtmSubIfVccPcr,
        juniAtmSubIfVccScr,
        juniAtmSubIfVccMbs,
        juniAtmSubIfInverseArp,
        juniAtmSubIfInverseArpRefresh,

        juniAtmCircuitOamAdminStatus,
        juniAtmCircuitOamLoopbackOperStatus,
        juniAtmCircuitVcOamOperStatus,
        juniAtmCircuitOamLoopbackFrequency,
        juniAtmCircuitInOamF5Cells,
        juniAtmCircuitInOamCellsDropped,
        juniAtmCircuitOutOamF5Cells,
        juniAtmCircuitInOamF5EndToEndLoopbackCells,
        juniAtmCircuitInOamF5SegmentLoopbackCells,
        juniAtmCircuitInOamF5AisCells,
        juniAtmCircuitInOamF5RdiCells,
        juniAtmCircuitOutOamF5EndToEndLoopbackCells,
        juniAtmCircuitOutOamF5SegmentLoopbackCells,
        juniAtmCircuitOutOamF5RdiCells }
    STATUS      obsolete
    DESCRIPTION
        "Obsolete collection of objects providing management of ATM
        subinterfaces in a Juniper product.  This group became obsolete when
        juniAtmSubIfAddress was added."
    ::= { juniAtmGroups 6 }                                        -- JUNOSe 3.2

juniAtmVpPingControlGroup  OBJECT-GROUP
    OBJECTS {
        juniAtmVpPingProbeCount,
        juniAtmVpPingTimeOut,
        juniAtmVpPingCtlTrapGeneration,
        juniAtmVpPingSentProbes,
        juniAtmVpPingProbeResponses,
        juniAtmVpPingStartTime,
        juniAtmVpPingMinRtt,
        juniAtmVpPingMaxRtt,
        juniAtmVpPingAverageRtt }
    STATUS      current
    DESCRIPTION
        "A collection of object providing management of ATM VPL Ping testing in
        a Juniper product."
    ::= { juniAtmGroups 7 }                                        -- JUNOSe 3.2

juniAtmVcPingControlGroup  OBJECT-GROUP
    OBJECTS {
        juniAtmVcPingProbeCount,
        juniAtmVcPingTimeOut,
        juniAtmVcPingCtlTrapGeneration,
        juniAtmVcPingSentProbes,
        juniAtmVcPingProbeResponses,
        juniAtmVcPingStartTime,
        juniAtmVcPingMinRtt,
        juniAtmVcPingMaxRtt,
        juniAtmVcPingAverageRtt }
    STATUS      current
    DESCRIPTION
        "A collection of object providing management of ATM VCL Ping testing in
        a Juniper product."
    ::= { juniAtmGroups 8 }                                        -- JUNOSe 3.2

juniAtmPingTrapGroup  NOTIFICATION-GROUP
    NOTIFICATIONS {
        juniAtmVpPingTestCompleted,
        juniAtmVcPingTestCompleted }
    STATUS      current
    DESCRIPTION
        "A collection of notifications supporting ATM Ping testing in a Juniper
        product."
    ::= { juniAtmGroups 9 }                                        -- JUNOSe 3.2

juniAtmGroup2  OBJECT-GROUP
    OBJECTS {
        juniAtmNextIfIndex,

        juniAtmIfRowStatus,
        juniAtmIfLowerIfIndex,
        juniAtmIfIlmiVpi,
        juniAtmIfIlmiVci,
        juniAtmIfIlmiVcd,
        juniAtmIfIlmiPollFrequency,
        juniAtmIfIlmiAdminState,
        juniAtmIfUniVersion,
        juniAtmIfOamCellRxAdminState,
        juniAtmIfInCells,
        juniAtmIfOutCells,
        juniAtmIfVcCount,
        juniAtmIfMapGroup,
        juniAtmIfOamCellFilter,

        juniAtmPvcStatsInCells,
        juniAtmPvcStatsInCellOctets,
        juniAtmPvcStatsInPackets,
        juniAtmPvcStatsInPacketOctets,
        juniAtmPvcStatsOutCells,
        juniAtmPvcStatsOutCellOctets,
        juniAtmPvcStatsOutPackets,
        juniAtmPvcStatsOutPacketOctets,
        juniAtmPvcStatsInCellErrors,
        juniAtmPvcStatsinPacketErrors,
        juniAtmPvcStatsOutCellErrors,
        juniAtmPvcStatsOutPacketErrors,
        juniAtmPvcStatsInPacketDiscards,
        juniAtmPvcStatsInPacketOctetDiscards,
        juniAtmPvcStatsInPacketUnknownProtocol,

        juniAtmIfCapabilityTrafficShaping,
        juniAtmIfCapabilityOam,
        juniAtmIfCapabilityDefaultVcPerVp,
        juniAtmIfCapabilityNumVpiVciBits,
        juniAtmIfCapabilityMaxVcd,
        juniAtmIfCapabilityMaxVpi,
        juniAtmIfCapabilityMaxVci,
        juniAtmIfCapabilityOamCellFilter }
    STATUS      obsolete
    DESCRIPTION
        "Obsolete collection of objects providing management of ATM interfaces
        in a Juniper product.  This group became obsolete when support was
        added for connection admission control (CAC)."
    ::= { juniAtmGroups 10 }                                       -- JUNOSe 3.2

juniAtmTrafficShapingGroup  OBJECT-GROUP
    OBJECTS {
        juniAtmSubIfVccTrafficShapingCdvt,
        juniAtmSubIfVccTrafficShapingClp0,
        juniAtmSubIfVccTrafficShapingTagging,
        juniAtmSubIfVccTrafficShapingPoliceObserve,
        juniAtmSubIfVccTrafficShapingPacketShaping }
    STATUS      current
    DESCRIPTION
        "A collection of objects providing management of ATM traffic shaping in
        a Juniper product."
    ::= { juniAtmGroups 11 }                                       -- JUNOSe 3.3

juniAtmGroup3  OBJECT-GROUP
    OBJECTS {
        juniAtmNextIfIndex,

        juniAtmIfRowStatus,
        juniAtmIfLowerIfIndex,
        juniAtmIfIlmiVpi,
        juniAtmIfIlmiVci,
        juniAtmIfIlmiVcd,
        juniAtmIfIlmiPollFrequency,
        juniAtmIfIlmiAdminState,
        juniAtmIfUniVersion,
        juniAtmIfOamCellRxAdminState,
        juniAtmIfInCells,
        juniAtmIfOutCells,
        juniAtmIfVcCount,
        juniAtmIfMapGroup,
        juniAtmIfCacAdminState,
        juniAtmIfCacUbrWeight,
        juniAtmIfCacSubscriptionBandwidth,
        juniAtmIfCacAvailableBandwidth,
        juniAtmIfOamCellFilter,

        juniAtmPvcStatsInCells,
        juniAtmPvcStatsInCellOctets,
        juniAtmPvcStatsInPackets,
        juniAtmPvcStatsInPacketOctets,
        juniAtmPvcStatsOutCells,
        juniAtmPvcStatsOutCellOctets,
        juniAtmPvcStatsOutPackets,
        juniAtmPvcStatsOutPacketOctets,
        juniAtmPvcStatsInCellErrors,
        juniAtmPvcStatsinPacketErrors,
        juniAtmPvcStatsOutCellErrors,
        juniAtmPvcStatsOutPacketErrors,
        juniAtmPvcStatsInPacketDiscards,
        juniAtmPvcStatsInPacketOctetDiscards,
        juniAtmPvcStatsInPacketUnknownProtocol,

        juniAtmIfCapabilityTrafficShaping,
        juniAtmIfCapabilityOam,
        juniAtmIfCapabilityDefaultVcPerVp,
        juniAtmIfCapabilityNumVpiVciBits,
        juniAtmIfCapabilityMaxVcd,
        juniAtmIfCapabilityMaxVpi,
        juniAtmIfCapabilityMaxVci,
        juniAtmIfCapabilityOamCellFilter }
    STATUS      obsolete
    DESCRIPTION
        "Obsolete collection of objects providing management of ATM interfaces
        in a Juniper product.  This group became obsolete when support was added
        for connection admission control (CAC) used bandwidth."
    ::= { juniAtmGroups 12 }                                       -- JUNOSe 3.4

juniAtmGroup4  OBJECT-GROUP
    OBJECTS {
        juniAtmNextIfIndex,

        juniAtmIfRowStatus,
        juniAtmIfLowerIfIndex,
        juniAtmIfIlmiVpi,
        juniAtmIfIlmiVci,
        juniAtmIfIlmiVcd,
        juniAtmIfIlmiPollFrequency,
        juniAtmIfIlmiAdminState,
        juniAtmIfUniVersion,
        juniAtmIfOamCellRxAdminState,
        juniAtmIfInCells,
        juniAtmIfOutCells,
        juniAtmIfVcCount,
        juniAtmIfMapGroup,
        juniAtmIfCacAdminState,
        juniAtmIfCacUbrWeight,
        juniAtmIfCacSubscriptionBandwidth,
        juniAtmIfCacAvailableBandwidth,
        juniAtmIfOamCellFilter,
        juniAtmIfCacUsedBandwidthUpper,
        juniAtmIfCacUsedBandwidthLower,

        juniAtmPvcStatsInCells,
        juniAtmPvcStatsInCellOctets,
        juniAtmPvcStatsInPackets,
        juniAtmPvcStatsInPacketOctets,
        juniAtmPvcStatsOutCells,
        juniAtmPvcStatsOutCellOctets,
        juniAtmPvcStatsOutPackets,
        juniAtmPvcStatsOutPacketOctets,
        juniAtmPvcStatsInCellErrors,
        juniAtmPvcStatsinPacketErrors,
        juniAtmPvcStatsOutCellErrors,
        juniAtmPvcStatsOutPacketErrors,
        juniAtmPvcStatsInPacketDiscards,
        juniAtmPvcStatsInPacketOctetDiscards,
        juniAtmPvcStatsInPacketUnknownProtocol,

        juniAtmIfCapabilityTrafficShaping,
        juniAtmIfCapabilityOam,
        juniAtmIfCapabilityDefaultVcPerVp,
        juniAtmIfCapabilityNumVpiVciBits,
        juniAtmIfCapabilityMaxVcd,
        juniAtmIfCapabilityMaxVpi,
        juniAtmIfCapabilityMaxVci,
        juniAtmIfCapabilityOamCellFilter }
    STATUS      obsolete
    DESCRIPTION
        "Obsolete collection of objects providing management of ATM interfaces
        in a Juniper product.  This group became obsolete when CAC recieve
        bandwith and E164 public addressing objects were added."
    ::= { juniAtmGroups 13 }                                       -- JUNOSe 4.0

juniAtmSvcGroup  OBJECT-GROUP
    OBJECTS {
        juniAtmIfSvcSignallingVpi,
        juniAtmIfSvcSignallingVci,
        juniAtmIfSvcSignallingVcd,
        juniAtmIfSvcSignallingAdminStatus,

        juniAtmSubIfSvcRowStatus,
        juniAtmSubIfSvcConfigDestAtmAddress,
        juniAtmSubIfSvcConfigCircuitType,
        juniAtmSubIfSvcConfigServiceCategory,
        juniAtmSubIfSvcConfigPcr,
        juniAtmSubIfSvcConfigScr,
        juniAtmSubIfSvcConfigMbs,
        juniAtmSubIfSvcConfigCdvt,
        juniAtmSubIfSvcConfigClp0,
        juniAtmSubIfSvcConfigTagging,
        juniAtmSubIfSvcConfigObserve,
        juniAtmSubIfSvcConfigPacketDiscard }
    STATUS      obsolete
    DESCRIPTION
        "Obsolete collection of objects providing management of ATM SVC
        interfaces in a Juniper product.  This group became obsolete when E164
        public addressing support was added."
    ::= { juniAtmGroups 14 }                                       -- JUNOSe 4.0

juniAtmSubIfGroup3  OBJECT-GROUP
    OBJECTS {
        juniAtmSubIfNextIfIndex,

        juniAtmSubIfRowStatus,
        juniAtmSubIfDistinguisher,
        juniAtmSubIfLowerIfIndex,
        juniAtmSubIfNbma,
        juniAtmSubIfAddress,

        juniAtmSubIfVccRowStatus,
        juniAtmSubIfVccVcd,
        juniAtmSubIfVccType,
        juniAtmSubIfVccServiceCategory,
        juniAtmSubIfVccPcr,
        juniAtmSubIfVccScr,
        juniAtmSubIfVccMbs,
        juniAtmSubIfInverseArp,
        juniAtmSubIfInverseArpRefresh,

        juniAtmCircuitOamAdminStatus,
        juniAtmCircuitOamLoopbackOperStatus,
        juniAtmCircuitVcOamOperStatus,
        juniAtmCircuitOamLoopbackFrequency,
        juniAtmCircuitInOamF5Cells,
        juniAtmCircuitInOamCellsDropped,
        juniAtmCircuitOutOamF5Cells,
        juniAtmCircuitInOamF5EndToEndLoopbackCells,
        juniAtmCircuitInOamF5SegmentLoopbackCells,
        juniAtmCircuitInOamF5AisCells,
        juniAtmCircuitInOamF5RdiCells,
        juniAtmCircuitOutOamF5EndToEndLoopbackCells,
        juniAtmCircuitOutOamF5SegmentLoopbackCells,
        juniAtmCircuitOutOamF5RdiCells }
    STATUS      obsolete
    DESCRIPTION
        "Obsolete collection of objects providing management of ATM
        subinterfaces in a Juniper product.  This group became obsolete when
        juniAtmSubIfMtu was added."
    ::= { juniAtmGroups 15 }                                       -- JUNOSe 4.0

juniAtmGroup5  OBJECT-GROUP
    OBJECTS {
        juniAtmNextIfIndex,

        juniAtmIfRowStatus,
        juniAtmIfLowerIfIndex,
        juniAtmIfIlmiVpi,
        juniAtmIfIlmiVci,
        juniAtmIfIlmiVcd,
        juniAtmIfIlmiPollFrequency,
        juniAtmIfIlmiAdminState,
        juniAtmIfUniVersion,
        juniAtmIfOamCellRxAdminState,
        juniAtmIfInCells,
        juniAtmIfOutCells,
        juniAtmIfVcCount,
        juniAtmIfMapGroup,
        juniAtmIfCacAdminState,
        juniAtmIfCacUbrWeight,
        juniAtmIfCacSubscriptionBandwidth,
        juniAtmIfCacAvailableBandwidth,
        juniAtmIfCacAvailableBandwidthRx,
        juniAtmIfE164Autoconversion,
        juniAtmIfE164Gateway,
        juniAtmIfE164OneToOneAddrTrans,

        juniAtmPvcStatsInCells,
        juniAtmPvcStatsInCellOctets,
        juniAtmPvcStatsInPackets,
        juniAtmPvcStatsInPacketOctets,
        juniAtmPvcStatsOutCells,
        juniAtmPvcStatsOutCellOctets,
        juniAtmPvcStatsOutPackets,
        juniAtmPvcStatsOutPacketOctets,
        juniAtmPvcStatsInCellErrors,
        juniAtmPvcStatsinPacketErrors,
        juniAtmPvcStatsOutCellErrors,
        juniAtmPvcStatsOutPacketErrors,
        juniAtmPvcStatsInPacketDiscards,
        juniAtmPvcStatsInPacketOctetDiscards,
        juniAtmPvcStatsInPacketUnknownProtocol,

        juniAtmIfCapabilityTrafficShaping,
        juniAtmIfCapabilityOam,
        juniAtmIfCapabilityDefaultVcPerVp,
        juniAtmIfCapabilityNumVpiVciBits,
        juniAtmIfCapabilityMaxVcd,
        juniAtmIfCapabilityMaxVpi,
        juniAtmIfCapabilityMaxVci }
    STATUS      obsolete
    DESCRIPTION
        "Obsolete collection of objects providing management of ATM interfaces
        in a Juniper product.  This group became obsolete when ATM VP
        description support was added."
    ::= { juniAtmGroups 16 }                                       -- JUNOSe 4.1

juniAtmSvcGroup2  OBJECT-GROUP
    OBJECTS {
        juniAtmIfSvcSignallingVpi,
        juniAtmIfSvcSignallingVci,
        juniAtmIfSvcSignallingVcd,
        juniAtmIfSvcSignallingAdminStatus,

        juniAtmSubIfSvcRowStatus,
        juniAtmSubIfSvcConfigDestAtmAddress,
        juniAtmSubIfSvcConfigCircuitType,
        juniAtmSubIfSvcConfigServiceCategory,
        juniAtmSubIfSvcConfigPcr,
        juniAtmSubIfSvcConfigScr,
        juniAtmSubIfSvcConfigMbs,
        juniAtmSubIfSvcConfigClp0,
        juniAtmSubIfSvcConfigTagging,
        juniAtmSubIfSvcConfigPacketDiscard,
        juniAtmSubIfSvcConfigDestE164Address }
    STATUS      current
    DESCRIPTION
        "A collection of objects providing management of ATM SVC interfaces in a
        Juniper product."
    ::= { juniAtmGroups 17 }                                       -- JUNOSe 4.1

juniAtmPnniGroup  OBJECT-GROUP
    OBJECTS {
        juniAtmIfPnniRccVpi,
        juniAtmIfPnniRccVci,
        juniAtmIfPnniRccVcd,
        juniAtmIfPnniRccAdminStatus }
    STATUS      current
    DESCRIPTION
        "A collection of objects providing management of PNNI Routing Control
        Channels in a Juniper product."
    ::= { juniAtmGroups 18 }                                       -- JUNOSe 4.1

juniAtmSubIfGroup4  OBJECT-GROUP
    OBJECTS {
        juniAtmSubIfNextIfIndex,

        juniAtmSubIfRowStatus,
        juniAtmSubIfDistinguisher,
        juniAtmSubIfLowerIfIndex,
        juniAtmSubIfNbma,
        juniAtmSubIfAddress,
        juniAtmSubIfMtu,

        juniAtmSubIfVccRowStatus,
        juniAtmSubIfVccVcd,
        juniAtmSubIfVccType,
        juniAtmSubIfVccServiceCategory,
        juniAtmSubIfVccPcr,
        juniAtmSubIfVccScr,
        juniAtmSubIfVccMbs,
        juniAtmSubIfInverseArp,
        juniAtmSubIfInverseArpRefresh,

        juniAtmCircuitOamAdminStatus,
        juniAtmCircuitOamLoopbackOperStatus,
        juniAtmCircuitVcOamOperStatus,
        juniAtmCircuitOamLoopbackFrequency,
        juniAtmCircuitInOamF5Cells,
        juniAtmCircuitInOamCellsDropped,
        juniAtmCircuitOutOamF5Cells,
        juniAtmCircuitInOamF5EndToEndLoopbackCells,
        juniAtmCircuitInOamF5SegmentLoopbackCells,
        juniAtmCircuitInOamF5AisCells,
        juniAtmCircuitInOamF5RdiCells,
        juniAtmCircuitOutOamF5EndToEndLoopbackCells,
        juniAtmCircuitOutOamF5SegmentLoopbackCells,
        juniAtmCircuitOutOamF5RdiCells }
    STATUS      obsolete
    DESCRIPTION
        "Obsolete collection of objects providing management of ATM
        subinterfaces in a Juniper product.  This group became obsolete when
        support was added to export the subinterface description to the line
        cards."
    ::= { juniAtmGroups 19 }                                       -- JUNOSe 4.1

juniAtmF4OamCircuitGroup  OBJECT-GROUP
    OBJECTS {
--      End-to-end configs
        juniAtmOamF4FlowEndToEndLoopbackTimer,
        juniAtmOamF4FlowEndToEndCCSink,
        juniAtmOamF4FlowEndToEndCCSource,
        juniAtmOamF4FlowEndToEndRowStatus,
--      Segment configs
        juniAtmOamF4FlowSegmentCCSink,
        juniAtmOamF4FlowSegmentCCSource,
        juniAtmOamF4FlowSegmentRowStatus,

--      End-to-end stats
        juniAtmF4FlowInOamEndAisCells,
        juniAtmF4FlowInOamEndRdiCells,
        juniAtmF4FlowInOamEndCCCells,
        juniAtmF4FlowInOamEndCCActDeActCells,
        juniAtmF4FlowInOamEndLoopbackCells,
        juniAtmF4FlowOutEndRdiCells,
        juniAtmF4FlowOutEndCCCells,
        juniAtmF4FlowOutEndCCActDeActCells,
        juniAtmF4FlowOutEndToEndLoopbackCells,
        juniAtmF4FlowEndActualLoopbackFreq,
        juniAtmF4FlowEndLastTimeChanged,
        juniAtmF4FlowOamEndVpOperationState,
        juniAtmF4FlowOamEndVpAdminState,
        juniAtmF4FlowEndInOamCells,
        juniAtmF4FlowEndOutOamCells,
        juniAtmF4FlowEndInOamCellsDropped,
--      Segment stats
        juniAtmF4FlowInOamSegmentAisCells,
        juniAtmF4FlowInOamSegmentRdiCells,
        juniAtmF4FlowInOamSegmentCCCells,
        juniAtmF4FlowInOamSegmentCCActDeActCells,
        juniAtmF4FlowInOamSegmentLoopbackCells,
        juniAtmF4FlowOutSegmentRdiCells,
        juniAtmF4FlowOutSegmentCCCells,
        juniAtmF4FlowOutSegmentCCActDeActCells,
        juniAtmF4FlowOutSegmentLoopbackCells,
        juniAtmF4FlowSegmentLastTimeChanged,
        juniAtmF4FlowOamSegmentVpOperationState,
        juniAtmF4FlowOamSegmentVpAdminState,
        juniAtmF4FlowSegmentInOamCells,
        juniAtmF4FlowSegmentOutOamCells,
        juniAtmF4FlowSegmentInOamCellsDropped }
    STATUS      current
    DESCRIPTION
        "A collection of objects providing management of ATM F4 flow OAM
        circuits in a Juniper product."
    ::= { juniAtmGroups 20 }                                       -- JUNOSe 4.1

juniAtmGroup6  OBJECT-GROUP
    OBJECTS {
        juniAtmNextIfIndex,

        juniAtmIfRowStatus,
        juniAtmIfLowerIfIndex,
        juniAtmIfIlmiVpi,
        juniAtmIfIlmiVci,
        juniAtmIfIlmiVcd,
        juniAtmIfIlmiPollFrequency,
        juniAtmIfIlmiAdminState,
        juniAtmIfUniVersion,
        juniAtmIfOamCellRxAdminState,
        juniAtmIfInCells,
        juniAtmIfOutCells,
        juniAtmIfVcCount,
        juniAtmIfMapGroup,
        juniAtmIfCacAdminState,
        juniAtmIfCacUbrWeight,
        juniAtmIfCacSubscriptionBandwidth,
        juniAtmIfCacAvailableBandwidth,
        juniAtmIfCacAvailableBandwidthRx,
        juniAtmIfE164Autoconversion,
        juniAtmIfE164Gateway,
        juniAtmIfE164OneToOneAddrTrans,

        juniAtmPvcStatsInCells,
        juniAtmPvcStatsInCellOctets,
        juniAtmPvcStatsInPackets,
        juniAtmPvcStatsInPacketOctets,
        juniAtmPvcStatsOutCells,
        juniAtmPvcStatsOutCellOctets,
        juniAtmPvcStatsOutPackets,
        juniAtmPvcStatsOutPacketOctets,
        juniAtmPvcStatsInCellErrors,
        juniAtmPvcStatsinPacketErrors,
        juniAtmPvcStatsOutCellErrors,
        juniAtmPvcStatsOutPacketErrors,
        juniAtmPvcStatsInPacketDiscards,
        juniAtmPvcStatsInPacketOctetDiscards,
        juniAtmPvcStatsInPacketUnknownProtocol,

        juniAtmIfCapabilityTrafficShaping,
        juniAtmIfCapabilityOam,
        juniAtmIfCapabilityDefaultVcPerVp,
        juniAtmIfCapabilityNumVpiVciBits,
        juniAtmIfCapabilityMaxVcd,
        juniAtmIfCapabilityMaxVpi,
        juniAtmIfCapabilityMaxVci,

        juniAtmVpDescription,
        juniAtmBulkCircuitsNameRowStatus,
        juniAtmBulkCircuitsNameId,
        juniAtmBulkCircuitsIdName,
        juniAtmBulkCircuitsIdNextInstance,
        juniAtmBulkCircuitsRowStatus,
        juniAtmBulkCircuitsMinVpi,
        juniAtmBulkCircuitsMaxVpi,
        juniAtmBulkCircuitsMinVci,
        juniAtmBulkCircuitsMaxVci }
    STATUS      obsolete
    DESCRIPTION
        "Obsolete collection of objects providing management of ATM interfaces 
        in a Juniper product. This group became obsolete when bulk-configuration
        profile override support was added."
    ::= { juniAtmGroups 21 }                                       -- JUNOSe 5.1

juniAtmLocationGroup  OBJECT-GROUP
    OBJECTS {
        juniAtmSubIfLocationType,
        juniAtmSubIfLocationIfIndex }
    STATUS      current
    DESCRIPTION
        "A collection of objects providing interface location information in a
        Juniper product."
    ::= { juniAtmGroups 22 }                                       -- JUNOSe 5.2

juniAtmSubIfGroup5  OBJECT-GROUP
    OBJECTS {
        juniAtmSubIfNextIfIndex,

        juniAtmSubIfRowStatus,
        juniAtmSubIfDistinguisher,
        juniAtmSubIfLowerIfIndex,
        juniAtmSubIfNbma,
        juniAtmSubIfAddress,
        juniAtmSubIfMtu,
        juniAtmSubIfAdvisoryRxSpeed,

        juniAtmSubIfVccRowStatus,
        juniAtmSubIfVccVcd,
        juniAtmSubIfVccType,
        juniAtmSubIfVccServiceCategory,
        juniAtmSubIfVccPcr,
        juniAtmSubIfVccScr,
        juniAtmSubIfVccMbs,
        juniAtmSubIfInverseArp,
        juniAtmSubIfInverseArpRefresh,

        juniAtmCircuitOamAdminStatus,
        juniAtmCircuitOamLoopbackOperStatus,
        juniAtmCircuitVcOamOperStatus,
        juniAtmCircuitOamLoopbackFrequency,
        juniAtmCircuitInOamF5Cells,
        juniAtmCircuitInOamCellsDropped,
        juniAtmCircuitOutOamF5Cells,
        juniAtmCircuitInOamF5EndToEndLoopbackCells,
        juniAtmCircuitInOamF5SegmentLoopbackCells,
        juniAtmCircuitInOamF5AisCells,
        juniAtmCircuitInOamF5RdiCells,
        juniAtmCircuitOutOamF5EndToEndLoopbackCells,
        juniAtmCircuitOutOamF5SegmentLoopbackCells,
        juniAtmCircuitOutOamF5RdiCells,

        juniAtmSubIfDescriptionExport }
    STATUS      current
    DESCRIPTION
        "A collection of objects providing management of ATM subinterfaces in a
        Juniper product."
    ::= { juniAtmGroups 23 }   

juniAtmMartiniGroup  OBJECT-GROUP
    OBJECTS {
        juniAtmMartiniTimeoutTimerValue,
        
        juniAtmSubIfMartiniMaxCellsPerPacket,
        juniAtmSubIfMartiniTimeoutTimerId }
    STATUS      current
    DESCRIPTION
        "A collection of objects providing ATM Martini cell aggregation
        configuration."
    ::= { juniAtmGroups 24 } 

juniAtmGroup7  OBJECT-GROUP
    OBJECTS {
        juniAtmNextIfIndex,

        juniAtmIfRowStatus,
        juniAtmIfLowerIfIndex,
        juniAtmIfIlmiVpi,
        juniAtmIfIlmiVci,
        juniAtmIfIlmiVcd,
        juniAtmIfIlmiPollFrequency,
        juniAtmIfIlmiAdminState,
        juniAtmIfUniVersion,
        juniAtmIfOamCellRxAdminState,
        juniAtmIfInCells,
        juniAtmIfOutCells,
        juniAtmIfVcCount,
        juniAtmIfMapGroup,
        juniAtmIfCacAdminState,
        juniAtmIfCacUbrWeight,
        juniAtmIfCacSubscriptionBandwidth,
        juniAtmIfCacAvailableBandwidth,
        juniAtmIfCacAvailableBandwidthRx,
        juniAtmIfE164Autoconversion,
        juniAtmIfE164Gateway,
        juniAtmIfE164OneToOneAddrTrans,

        juniAtmPvcStatsInCells,
        juniAtmPvcStatsInCellOctets,
        juniAtmPvcStatsInPackets,
        juniAtmPvcStatsInPacketOctets,
        juniAtmPvcStatsOutCells,
        juniAtmPvcStatsOutCellOctets,
        juniAtmPvcStatsOutPackets,
        juniAtmPvcStatsOutPacketOctets,
        juniAtmPvcStatsInCellErrors,
        juniAtmPvcStatsinPacketErrors,
        juniAtmPvcStatsOutCellErrors,
        juniAtmPvcStatsOutPacketErrors,
        juniAtmPvcStatsInPacketDiscards,
        juniAtmPvcStatsInPacketOctetDiscards,
        juniAtmPvcStatsInPacketUnknownProtocol,

        juniAtmIfCapabilityTrafficShaping,
        juniAtmIfCapabilityOam,
        juniAtmIfCapabilityDefaultVcPerVp,
        juniAtmIfCapabilityNumVpiVciBits,
        juniAtmIfCapabilityMaxVcd,
        juniAtmIfCapabilityMaxVpi,
        juniAtmIfCapabilityMaxVci,

        juniAtmVpDescription,
        juniAtmBulkCircuitsNameRowStatus,
        juniAtmBulkCircuitsNameId,
        juniAtmBulkCircuitsIdName,
        juniAtmBulkCircuitsIdNextInstance,
        juniAtmBulkCircuitsRowStatus,
        juniAtmBulkCircuitsMinVpi,
        juniAtmBulkCircuitsMaxVpi,
        juniAtmBulkCircuitsMinVci,
        juniAtmBulkCircuitsMaxVci,
        juniAtmBulkCircuitsAdminState,

    	juniAtmProfileOverrideAssignIfCircuitRowStatus,
    	juniAtmProfileOverrideAssignIfCircuitProfileId,
		juniAtmProfileOverrideAssignIfCircuitOperStatus }
    STATUS      obsolete
    DESCRIPTION
        "A collection of objects providing management of ATM interfaces in a
        Juniper product."
    ::= { juniAtmGroups 25 }                                       -- JUNOSe 6.1


juniAtmGroup8  OBJECT-GROUP
    OBJECTS {
        juniAtmNextIfIndex,

        juniAtmIfRowStatus,
        juniAtmIfLowerIfIndex,
        juniAtmIfIlmiVpi,
        juniAtmIfIlmiVci,
        juniAtmIfIlmiVcd,
        juniAtmIfIlmiPollFrequency,
        juniAtmIfIlmiAdminState,
        juniAtmIfUniVersion,
        juniAtmIfOamCellRxAdminState,
        juniAtmIfInCells,
        juniAtmIfOutCells,
        juniAtmIfVcCount,
        juniAtmIfMapGroup,
        juniAtmIfCacAdminState,
        juniAtmIfCacUbrWeight,
        juniAtmIfCacSubscriptionBandwidth,
        juniAtmIfCacAvailableBandwidth,

        juniAtmPvcStatsInCells,
        juniAtmPvcStatsInCellOctets,
        juniAtmPvcStatsInPackets,
        juniAtmPvcStatsInPacketOctets,
        juniAtmPvcStatsOutCells,
        juniAtmPvcStatsOutCellOctets,
        juniAtmPvcStatsOutPackets,
        juniAtmPvcStatsOutPacketOctets,
        juniAtmPvcStatsInCellErrors,
        juniAtmPvcStatsinPacketErrors,
        juniAtmPvcStatsOutCellErrors,
        juniAtmPvcStatsOutPacketErrors,
        juniAtmPvcStatsInPacketDiscards,
        juniAtmPvcStatsInPacketOctetDiscards,
        juniAtmPvcStatsInPacketUnknownProtocol,

        juniAtmIfCapabilityTrafficShaping,
        juniAtmIfCapabilityOam,
        juniAtmIfCapabilityDefaultVcPerVp,
        juniAtmIfCapabilityNumVpiVciBits,
        juniAtmIfCapabilityMaxVcd,
        juniAtmIfCapabilityMaxVpi,
        juniAtmIfCapabilityMaxVci,

        juniAtmVpDescription,
        juniAtmBulkCircuitsNameRowStatus,
        juniAtmBulkCircuitsNameId,
        juniAtmBulkCircuitsIdName,
        juniAtmBulkCircuitsIdNextInstance,
        juniAtmBulkCircuitsRowStatus,
        juniAtmBulkCircuitsMinVpi,
        juniAtmBulkCircuitsMaxVpi,
        juniAtmBulkCircuitsMinVci,
        juniAtmBulkCircuitsMaxVci,
        juniAtmBulkCircuitsAdminState,

    	juniAtmProfileOverrideAssignIfCircuitRowStatus,
    	juniAtmProfileOverrideAssignIfCircuitProfileId,
	juniAtmProfileOverrideAssignIfCircuitOperStatus }
    STATUS      current
    DESCRIPTION
        "A collection of objects providing management of ATM interfaces in a
        Juniper product."
    ::= { juniAtmGroups 26 }                                       -- JUNOSe 7.0


END
