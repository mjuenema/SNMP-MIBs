-- file automatically created


TELDAT-TRAP-MRTE-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


mrteTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the MRTE event subsystem."
    REVISION "201401200930Z"
    DESCRIPTION "Initial implementation"
        ::= { telEventTraps 239 }


mrteEventsGroup	OBJECT IDENTIFIER	::= { mrteTrapsMIB 1 }

mrteNotifications	OBJECT IDENTIFIER	::= { mrteTrapsMIB 2 }
mrteNotificationsPrefix	OBJECT IDENTIFIER	::= { mrteNotifications 0 }

mrteEventObjects1 OBJECT-IDENTITY
    STATUS current
    DESCRIPTION
        "Event MRTE.1
        Multicast packet to be forwarded."
    ::= { mrteEventsGroup 1 }

mrte1_source-address OBJECT-TYPE
    SYNTAX IpAddress
    MAX-ACCESS accessible-for-notify
    STATUS current
    DESCRIPTION
        "Parameter 'source-address' in event MRTE.1"
    ::= { mrteEventObjects1 1 }

mrte1_destination-address OBJECT-TYPE
    SYNTAX IpAddress
    MAX-ACCESS accessible-for-notify
    STATUS current
    DESCRIPTION
        "Parameter 'destination-address' in event MRTE.1"
    ::= { mrteEventObjects1 2 }

mrte1_incoming-interface OBJECT-TYPE
    SYNTAX DisplayString
    MAX-ACCESS accessible-for-notify
    STATUS current
    DESCRIPTION
        "Parameter 'incoming-interface' in event MRTE.1"
    ::= { mrteEventObjects1 3 }

mrte1_ttl OBJECT-TYPE
    SYNTAX Integer32
    MAX-ACCESS accessible-for-notify
    STATUS current
    DESCRIPTION
        "Parameter 'ttl' in event MRTE.1"
    ::= { mrteEventObjects1 4 }

mrteEventObjects2 OBJECT-IDENTITY
    STATUS current
    DESCRIPTION
        "Event MRTE.2
        MFC entry not found at first lookup"
    ::= { mrteEventsGroup 2 }

mrte2_source-address OBJECT-TYPE
    SYNTAX IpAddress
    MAX-ACCESS accessible-for-notify
    STATUS current
    DESCRIPTION
        "Parameter 'source-address' in event MRTE.2"
    ::= { mrteEventObjects2 1 }

mrte2_destination-address OBJECT-TYPE
    SYNTAX IpAddress
    MAX-ACCESS accessible-for-notify
    STATUS current
    DESCRIPTION
        "Parameter 'destination-address' in event MRTE.2"
    ::= { mrteEventObjects2 2 }

mrteEventObjects3 OBJECT-IDENTITY
    STATUS current
    DESCRIPTION
        "Event MRTE.3
        Multicast packet to be sent."
    ::= { mrteEventsGroup 3 }

mrte3_source-address OBJECT-TYPE
    SYNTAX IpAddress
    MAX-ACCESS accessible-for-notify
    STATUS current
    DESCRIPTION
        "Parameter 'source-address' in event MRTE.3"
    ::= { mrteEventObjects3 1 }

mrte3_destination-address OBJECT-TYPE
    SYNTAX IpAddress
    MAX-ACCESS accessible-for-notify
    STATUS current
    DESCRIPTION
        "Parameter 'destination-address' in event MRTE.3"
    ::= { mrteEventObjects3 2 }

mrte3_outgoing-interface OBJECT-TYPE
    SYNTAX DisplayString
    MAX-ACCESS accessible-for-notify
    STATUS current
    DESCRIPTION
        "Parameter 'outgoing-interface' in event MRTE.3"
    ::= { mrteEventObjects3 3 }

mrteEventObjects4 OBJECT-IDENTITY
    STATUS current
    DESCRIPTION
        "Event MRTE.4
        Generic error message"
    ::= { mrteEventsGroup 4 }

mrte4_error-string OBJECT-TYPE
    SYNTAX DisplayString
    MAX-ACCESS accessible-for-notify
    STATUS current
    DESCRIPTION
        "Parameter 'error-string' in event MRTE.4"
    ::= { mrteEventObjects4 1 }

mrteEventObjects5 OBJECT-IDENTITY
    STATUS current
    DESCRIPTION
        "Event MRTE.5
        Generic unexpected info message"
    ::= { mrteEventsGroup 5 }

mrte5_message OBJECT-TYPE
    SYNTAX DisplayString
    MAX-ACCESS accessible-for-notify
    STATUS current
    DESCRIPTION
        "Parameter 'message' in event MRTE.5"
    ::= { mrteEventObjects5 1 }

mrteEventObjects6 OBJECT-IDENTITY
    STATUS current
    DESCRIPTION
        "Event MRTE.6
        Common or very frequent info message"
    ::= { mrteEventsGroup 6 }

mrte6_message OBJECT-TYPE
    SYNTAX DisplayString
    MAX-ACCESS accessible-for-notify
    STATUS current
    DESCRIPTION
        "Parameter 'message' in event MRTE.6"
    ::= { mrteEventObjects6 1 }


mrteNotification1 NOTIFICATION-TYPE
    OBJECTS { 
              mrte1_source-address, 
              mrte1_destination-address,
              mrte1_incoming-interface,
              mrte1_ttl 
            }
    STATUS current
    DESCRIPTION
        "Notification of Event MRTE.1

        Message: 'forward packet from $1 to $2, received at incoming interface $3 ttl $4'

        Parameters list:
              $1: mrte1_source-address
              $2: mrte1_destination-address
              $3: mrte1_incoming-interface
              $4: mrte1_ttl

        Multicast packet to be forwarded."
    ::= { mrteNotificationsPrefix 1 }

mrteNotification2 NOTIFICATION-TYPE
    OBJECTS { 
              mrte2_source-address, 
              mrte2_destination-address 
            }
    STATUS current
    DESCRIPTION
        "Notification of Event MRTE.2

        Message: 'MFC entry not found from $1 to $2. Trying to create it.'

        Parameters list:
              $1: mrte2_source-address
              $2: mrte2_destination-address

        MFC entry not found at first lookup"
    ::= { mrteNotificationsPrefix 2 }

mrteNotification3 NOTIFICATION-TYPE
    OBJECTS { 
              mrte3_source-address, 
              mrte3_destination-address,
              mrte3_outgoing-interface 
            }
    STATUS current
    DESCRIPTION
        "Notification of Event MRTE.3

        Message: 'Send packet from $1 to $2, through outgoing interface $3'

        Parameters list:
              $1: mrte3_source-address
              $2: mrte3_destination-address
              $3: mrte3_outgoing-interface

        Multicast packet to be sent."
    ::= { mrteNotificationsPrefix 3 }

mrteNotification4 NOTIFICATION-TYPE
    OBJECTS { 
              mrte4_error-string 
            }
    STATUS current
    DESCRIPTION
        "Notification of Event MRTE.4

        Message: '$1'

        Parameters list:
              $1: mrte4_error-string

        Generic error message"
    ::= { mrteNotificationsPrefix 4 }

mrteNotification5 NOTIFICATION-TYPE
    OBJECTS { 
              mrte5_message 
            }
    STATUS current
    DESCRIPTION
        "Notification of Event MRTE.5

        Message: '$1'

        Parameters list:
              $1: mrte5_message

        Generic unexpected info message"
    ::= { mrteNotificationsPrefix 5 }

mrteNotification6 NOTIFICATION-TYPE
    OBJECTS { 
              mrte6_message 
            }
    STATUS current
    DESCRIPTION
        "Notification of Event MRTE.6

        Message: '$1'

        Parameters list:
              $1: mrte6_message

        Common or very frequent info message"
    ::= { mrteNotificationsPrefix 6 }


END
