-- ==================================================================
-- Copyright (C) 2005 by HUAWEI-3COM TECHNOLOGIES. All rights reserved.
--
-- Description: H3C L2VPN PWE3(Pseudo Wire Emulation Edge-to-Edge) MIB
-- Reference:
-- Version: V1.0
-- History:
-- V1.0 2007-03-31 Created by Lixufu ID: 05023
-- ==================================================================
A3COM-HUAWEI-L2VPN-PWE3-MIB DEFINITIONS ::= BEGIN

IMPORTS
		h3cCommon
	FROM A3COM-HUAWEI-OID-MIB
		IpAddress, Integer32, Unsigned32, OBJECT-TYPE, MODULE-IDENTITY,
		NOTIFICATION-TYPE
	FROM SNMPv2-SMI
		TruthValue, RowStatus, TEXTUAL-CONVENTION
	FROM SNMPv2-TC;

h3cL2VpnPwe3 MODULE-IDENTITY
	LAST-UPDATED "200703310000Z"       -- March 31, 2007 at 00:00 GMT
	ORGANIZATION
		"Huawei 3Com Technologies Co., Ltd."
	CONTACT-INFO
		"Platform Team Huawei 3Com Technologies Co., Ltd.
		 Hai-Dian District Beijing P.R. China
		 Http://www.huawei-3com.com
		 Zip:100085"
	DESCRIPTION
		"This MIB contains objects to manage PWE3."
	::= { h3cCommon 78 }

H3cL2VpnVcEncapsType ::=  TEXTUAL-CONVENTION
	STATUS      current
	DESCRIPTION
		"An indication of the L2Vpn's VC encapsulation type:
		Frame Relay DLCI ( Martini Mode ) (1)
		ATM AAL5 SDU VCC transport (2)
		ATM transparent cell transport (3)
		Ethernet Tagged Mode (4)
		Ethernet (5)
		HDLC (6)
		PPP (7)
		SONET/SDH Circuit Emulation Service Over MPLS (CEM) (8)
		ATM n-to-one VCC cell transport (9)
		ATM n-to-one VPC cell transport (10)
		IP Layer2 Transport (11)
		ATM one-to-one VCC Cell Mode (12)
		ATM one-to-one VPC Cell Mode (13)
		ATM AAL5 PDU VCC transport (14)
		Frame-Relay Port mode (15)
		SONET/SDH Circuit Emulation over Packet (CEP) (16)
		Structure-agnostic E1 over Packet (SAE1oP)  (17)
		Structure-agnostic T1 (DS1) over Packet (SAT1oP)  (18)
		Structure-agnostic E3 over Packet (SAE3oP) (19)
		Structure-agnostic T3 (DS3) over Packet (SAT3oP) (20)
		CESoPSN basic mode (21)
		TDMoIP basic mode (22)
		CESoPSN TDM with CAS (23)
		TDMoIP TDM with CAS (24)
		Frame Relay DLCI (25)
		IP-interworking (64)
		unknown (255)
		"
	SYNTAX      INTEGER
		{
			frameRelayDlciMartini(1),
			atmAal5SduVccTransport(2),
			atmTransparentCellTransport(3),
			ethernetTagged(4),
			ethernet(5),
			hdlc(6),
			ppp(7),
			cem(8),
			atmN2OneVccCellTransport(9),
			atmN2OneVpcCellTransport(10),
			ipLayer2Transport(11),
			atmOne2OneVccCellMode(12),
			atmOne2OneVpcCellMode(13),
			atmAal5PduVccTransport(14),
			frameRelayPortMode(15),
			cep(16),
			saE1oP(17),
			saT1oP(18),
			saE3oP(19),
			saT3oP(20),
			cESoPsnBasicMode(21),
			tDMoIPbasicMode(22),
			l2VpnCESoPSNTDMwithCAS(23),
			l2VpnTDMoIPTDMwithCAS(24),
			frameRelayDlci(25),
			ipInterworking(64),
			unknown(255)
		}

-- ==================================================================
--
-- ======================= definition begin =========================
--
-- ==================================================================
h3cL2VpnPwe3ScalarGroup OBJECT IDENTIFIER ::= { h3cL2VpnPwe3 1 }

h3cPwVcTrapOpen OBJECT-TYPE
	SYNTAX      TruthValue
	MAX-ACCESS  read-write
	STATUS      current
	DESCRIPTION
		"Whether pwe3 trap is globally enabled.
		false: disable;
		true: enable."
	DEFVAL  { false }
	::= { h3cL2VpnPwe3ScalarGroup 1 }

h3cL2VpnPwe3Table OBJECT IDENTIFIER ::= { h3cL2VpnPwe3 2 }

h3cPwVcTable OBJECT-TYPE
	SYNTAX      SEQUENCE OF H3cPwVcEntry
	MAX-ACCESS  not-accessible
	STATUS      current
	DESCRIPTION
		"This table is the VC configuration table. Users
		can create or delete a VC by it."
	::= { h3cL2VpnPwe3Table 1 }

h3cPwVcEntry OBJECT-TYPE
	SYNTAX      H3cPwVcEntry
	MAX-ACCESS  not-accessible
	STATUS      current
	DESCRIPTION
		"Provides the information of a VC entry."
	INDEX
		{
			h3cPwVcIndex
		}
	::= { h3cPwVcTable 1 }

H3cPwVcEntry ::= SEQUENCE
	{
		h3cPwVcIndex            Integer32,
		h3cPwVcID               Unsigned32,
		h3cPwVcType             H3cL2VpnVcEncapsType,
		h3cPwVcPeerAddr         IpAddress,
		h3cPwVcMtu              Unsigned32,
		hwPwVcCfgType           INTEGER,
		h3cPwVcInboundLabel     Unsigned32,
		h3cPwVcOutboundLabel    Unsigned32,
		h3cPwVcIfIndex          Unsigned32,
		h3cPwVcAcStatus         INTEGER,
		h3cPwVcStatus           INTEGER,
		h3cPwVcRowStatus        RowStatus
	}

h3cPwVcIndex OBJECT-TYPE
	SYNTAX      Integer32
	MAX-ACCESS  not-accessible
	STATUS      current
	DESCRIPTION
		"Index for the conceptual row identifying a PW within
		this PW Emulation table."
	::= { h3cPwVcEntry 1 }

h3cPwVcID OBJECT-TYPE
	SYNTAX      Unsigned32
	MAX-ACCESS  read-create
	STATUS      current
	DESCRIPTION
		"Used in the outgoing PW ID field within the 'Virtual
		Circuit FEC Element'."
	::= { h3cPwVcEntry 2 }

h3cPwVcType OBJECT-TYPE
	SYNTAX      H3cL2VpnVcEncapsType
	MAX-ACCESS  read-create
	STATUS      current
	DESCRIPTION
		"Indication of the L2Vpn's VC encapsulation type."
	::= { h3cPwVcEntry 3 }

h3cPwVcPeerAddr OBJECT-TYPE
	SYNTAX      IpAddress
	MAX-ACCESS  read-create
	STATUS      current
	DESCRIPTION
		"This object contain the value of the peer ip address
		of the Martini VLL PW."
	::= { h3cPwVcEntry 4 }

h3cPwVcMtu OBJECT-TYPE
	SYNTAX      Unsigned32
	MAX-ACCESS  read-create
	STATUS      current
	DESCRIPTION
		"If not equal zero, the optional Mtu object in the
		signaling protocol will be sent with this value,
		representing the locally supported MTU size over the
		interface (or the virtual interface) associated with the
		PW.
		The default value is 1500."
	::= { h3cPwVcEntry 5 }

hwPwVcCfgType OBJECT-TYPE
	SYNTAX      INTEGER
		{
			primary(1),
			backup(2),
			multiPort(3)
		}
	MAX-ACCESS  read-create
	STATUS      current
	DESCRIPTION
		"Indicates the type of the pw:
		1: primary;
		2: backup;
		3: multiPort."
	::= { h3cPwVcEntry 6 }

h3cPwVcInboundLabel OBJECT-TYPE
	SYNTAX      Unsigned32
	MAX-ACCESS  read-only
	STATUS      current
	DESCRIPTION
		"For Martini VLL, the value will be created by system
		automatically."
	::= { h3cPwVcEntry 7 }

h3cPwVcOutboundLabel OBJECT-TYPE
	SYNTAX      Unsigned32
	MAX-ACCESS  read-only
	STATUS      current
	DESCRIPTION
		"For Martini VLL, the value will be created by the peer
		automatically."
	::= { h3cPwVcEntry 8 }

h3cPwVcIfIndex OBJECT-TYPE
	SYNTAX      Unsigned32
	MAX-ACCESS  read-create
	STATUS      current
	DESCRIPTION
		"Index of the interface (or the virtual interface)
		associated with the PW."
	::= { h3cPwVcEntry 9 }

h3cPwVcAcStatus OBJECT-TYPE
	SYNTAX      INTEGER
		{
			down(1),
			up(2)
		}
	MAX-ACCESS  read-only
	STATUS      current
	DESCRIPTION
		"Local AC(Attachment Circuit) status:
		1: down;
		2: up."
	::= { h3cPwVcEntry 10 }

h3cPwVcStatus OBJECT-TYPE
	SYNTAX      INTEGER
		{
			down(1),
			up(2)
		}
	MAX-ACCESS  read-only
	STATUS      current
	DESCRIPTION
		"Indicates the status of the PW in the local node.
		1: down;
		2: up."
	::= { h3cPwVcEntry 11 }

h3cPwVcRowStatus OBJECT-TYPE
	SYNTAX      RowStatus
	MAX-ACCESS  read-create
	STATUS      current
	DESCRIPTION
		"This object is responsible for managing the creation,
		deletion and modification of rows, which support active
		status and CreatAndGo, destroy operation.
		To create a new row, h3cPwVcID, h3cPwVcType, h3cPwVcPeerAddr
		h3cPwVcMtu, hwPwVcCfgType and h3cPwVcIfIndex
		must be specified."
	::= { h3cPwVcEntry 12 }

h3cL2VpnPwe3Notifications OBJECT IDENTIFIER ::= { h3cL2VpnPwe3 3 }

h3cPwVcSwitchWtoP NOTIFICATION-TYPE
	OBJECTS
		{
			h3cPwVcID,
			h3cPwVcType,
			h3cPwVcPeerAddr,
			h3cPwVcID,
			h3cPwVcType,
			h3cPwVcPeerAddr
		}
	STATUS      current
	DESCRIPTION
		"This notification is generated when switch from working pseudo-wire to protect pseudo-wire happens. The first group of h3cPwVcID/h3cPwVcTypeh3cPwVcPeerAddr is parameter of the work pseudo-wire, and the second group of h3cPwVcID/h3cPwVcTypeh3cPwVcPeerAddr is parameter of the protect pseudo-wire."
	::= { h3cL2VpnPwe3Notifications 1 }

h3cPwVcSwitchPtoW NOTIFICATION-TYPE
	OBJECTS
		{
			h3cPwVcID,
			h3cPwVcType,
			h3cPwVcPeerAddr,
			h3cPwVcID,
			h3cPwVcType,
			h3cPwVcPeerAddr
		}
	STATUS      current
	DESCRIPTION
		"This notification is generated when switch from protect pseudo-wire to working pseudo-wire happens. The first group of h3cPwVcID/h3cPwVcTypeh3cPwVcPeerAddr is parameter of the protect pseudo-wire, and the second group of h3cPwVcID/h3cPwVcTypeh3cPwVcPeerAddr is parameter of the work PW."
	::= { h3cL2VpnPwe3Notifications 2 }

h3cPwVcDown NOTIFICATION-TYPE
	OBJECTS
		{
			h3cPwVcID,
			h3cPwVcType,
			h3cPwVcPeerAddr
		}
	STATUS      current
	DESCRIPTION
		"This notification indicates the Virtual Circuit (VC)'s state changes to down."
	::= { h3cL2VpnPwe3Notifications 3 }

h3cPwVcUp NOTIFICATION-TYPE
	OBJECTS
		{
			h3cPwVcID,
			h3cPwVcType,
			h3cPwVcPeerAddr
		}
	STATUS      current
	DESCRIPTION
		"This notification indicates the Virtual Circuit (VC)'s state changes to up."
	::= { h3cL2VpnPwe3Notifications 4 }

h3cPwVcDeleted NOTIFICATION-TYPE
	OBJECTS
		{
			h3cPwVcID,
			h3cPwVcType,
			h3cPwVcPeerAddr
		}
	STATUS      current
	DESCRIPTION
		"This notification indicates the Virtual Circuit (VC) is deleted."
	::= { h3cL2VpnPwe3Notifications 5 }

END
