-- file automatically created


TELDAT-TRAP-UDP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


udpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the UDP event subsystem."
    REVISION "201401200930Z"
    DESCRIPTION "Initial implementation"
        ::= { telEventTraps 13 }


udpEventsGroup	OBJECT IDENTIFIER	::= { udpTrapsMIB 1 }

udpNotifications	OBJECT IDENTIFIER	::= { udpTrapsMIB 2 }
udpNotificationsPrefix	OBJECT IDENTIFIER	::= { udpNotifications 0 }

udpEventObjects1 OBJECT-IDENTITY
    STATUS current
    DESCRIPTION
        "Event UDP.1
        This message is generated when a packet is discarded because UDP is not
        installed in the router. The packet was for the broadcast address."
    ::= { udpEventsGroup 1 }

udp1_source_ip_address OBJECT-TYPE
    SYNTAX IpAddress
    MAX-ACCESS accessible-for-notify
    STATUS current
    DESCRIPTION
        "Parameter 'source_ip_address' in event UDP.1"
    ::= { udpEventObjects1 1 }

udp1_destination_ip_address OBJECT-TYPE
    SYNTAX IpAddress
    MAX-ACCESS accessible-for-notify
    STATUS current
    DESCRIPTION
        "Parameter 'destination_ip_address' in event UDP.1"
    ::= { udpEventObjects1 2 }

udp1_port_number OBJECT-TYPE
    SYNTAX Integer32
    MAX-ACCESS accessible-for-notify
    STATUS current
    DESCRIPTION
        "Parameter 'port_number' in event UDP.1"
    ::= { udpEventObjects1 3 }

udpEventObjects2 OBJECT-IDENTITY
    STATUS current
    DESCRIPTION
        "Event UDP.2
        This message is generated when a packet is discarded because UDP is not
        installed in the router. The packet was addressed to the router."
    ::= { udpEventsGroup 2 }

udp2_source_ip_address OBJECT-TYPE
    SYNTAX IpAddress
    MAX-ACCESS accessible-for-notify
    STATUS current
    DESCRIPTION
        "Parameter 'source_ip_address' in event UDP.2"
    ::= { udpEventObjects2 1 }

udp2_destination_ip_address OBJECT-TYPE
    SYNTAX IpAddress
    MAX-ACCESS accessible-for-notify
    STATUS current
    DESCRIPTION
        "Parameter 'destination_ip_address' in event UDP.2"
    ::= { udpEventObjects2 2 }

udp2_port_number OBJECT-TYPE
    SYNTAX Integer32
    MAX-ACCESS accessible-for-notify
    STATUS current
    DESCRIPTION
        "Parameter 'port_number' in event UDP.2"
    ::= { udpEventObjects2 3 }

udpEventObjects3 OBJECT-IDENTITY
    STATUS current
    DESCRIPTION
        "Event UDP.3
        This message is generated when a packet is discarded because it had
        an UDP length greater than its IP length."
    ::= { udpEventsGroup 3 }

udp3_source_ip_address OBJECT-TYPE
    SYNTAX IpAddress
    MAX-ACCESS accessible-for-notify
    STATUS current
    DESCRIPTION
        "Parameter 'source_ip_address' in event UDP.3"
    ::= { udpEventObjects3 1 }

udp3_length OBJECT-TYPE
    SYNTAX Integer32
    MAX-ACCESS accessible-for-notify
    STATUS current
    DESCRIPTION
        "Parameter 'length' in event UDP.3"
    ::= { udpEventObjects3 2 }

udpEventObjects4 OBJECT-IDENTITY
    STATUS current
    DESCRIPTION
        "Event UDP.4
        This message is generated when a packet is discarded because it had
        a bad checksum."
    ::= { udpEventsGroup 4 }

udp4_calculated_checksum OBJECT-TYPE
    SYNTAX Integer32
    MAX-ACCESS accessible-for-notify
    STATUS current
    DESCRIPTION
        "Parameter 'calculated_checksum' in event UDP.4"
    ::= { udpEventObjects4 1 }

udp4_received_checksum OBJECT-TYPE
    SYNTAX Integer32
    MAX-ACCESS accessible-for-notify
    STATUS current
    DESCRIPTION
        "Parameter 'received_checksum' in event UDP.4"
    ::= { udpEventObjects4 2 }

udpEventObjects5 OBJECT-IDENTITY
    STATUS current
    DESCRIPTION
        "Event UDP.5
        This message is generated when a broadcast UDP packet is received"
    ::= { udpEventsGroup 5 }

udp5_incoming_interface OBJECT-TYPE
    SYNTAX DisplayString
    MAX-ACCESS accessible-for-notify
    STATUS current
    DESCRIPTION
        "Parameter 'incoming_interface' in event UDP.5"
    ::= { udpEventObjects5 1 }

udp5_source_ip_address OBJECT-TYPE
    SYNTAX IpAddress
    MAX-ACCESS accessible-for-notify
    STATUS current
    DESCRIPTION
        "Parameter 'source_ip_address' in event UDP.5"
    ::= { udpEventObjects5 2 }

udp5_source_udp_port OBJECT-TYPE
    SYNTAX Integer32
    MAX-ACCESS accessible-for-notify
    STATUS current
    DESCRIPTION
        "Parameter 'source_udp_port' in event UDP.5"
    ::= { udpEventObjects5 3 }

udp5_destination_ip_address OBJECT-TYPE
    SYNTAX IpAddress
    MAX-ACCESS accessible-for-notify
    STATUS current
    DESCRIPTION
        "Parameter 'destination_ip_address' in event UDP.5"
    ::= { udpEventObjects5 4 }

udp5_destination_udp_port OBJECT-TYPE
    SYNTAX Integer32
    MAX-ACCESS accessible-for-notify
    STATUS current
    DESCRIPTION
        "Parameter 'destination_udp_port' in event UDP.5"
    ::= { udpEventObjects5 5 }

udpEventObjects6 OBJECT-IDENTITY
    STATUS current
    DESCRIPTION
        "Event UDP.6
        This message is generated when a broadcast UDP packet is being forwarded
        to another destination address on the specified vrf."
    ::= { udpEventsGroup 6 }

udp6_next_hop OBJECT-TYPE
    SYNTAX IpAddress
    MAX-ACCESS accessible-for-notify
    STATUS current
    DESCRIPTION
        "Parameter 'next_hop' in event UDP.6"
    ::= { udpEventObjects6 1 }

udp6_vrf_next_hop OBJECT-TYPE
    SYNTAX DisplayString
    MAX-ACCESS accessible-for-notify
    STATUS current
    DESCRIPTION
        "Parameter 'vrf_next_hop' in event UDP.6"
    ::= { udpEventObjects6 2 }

udpEventObjects7 OBJECT-IDENTITY
    STATUS current
    DESCRIPTION
        "Event UDP.7
        This message is generated when a echo-responder service is waiting for
        data on a UDP port."
    ::= { udpEventsGroup 7 }

udp7_udp_port OBJECT-TYPE
    SYNTAX Integer32
    MAX-ACCESS accessible-for-notify
    STATUS current
    DESCRIPTION
        "Parameter 'udp_port' in event UDP.7"
    ::= { udpEventObjects7 1 }

udpEventObjects9 OBJECT-IDENTITY
    STATUS current
    DESCRIPTION
        "Event UDP.9
        This message is generated when an echo-request UDP packet is received"
    ::= { udpEventsGroup 9 }

udp9_client-address OBJECT-TYPE
    SYNTAX IpAddress
    MAX-ACCESS accessible-for-notify
    STATUS current
    DESCRIPTION
        "Parameter 'client-address' in event UDP.9"
    ::= { udpEventObjects9 1 }

udp9_client-port OBJECT-TYPE
    SYNTAX Integer32
    MAX-ACCESS accessible-for-notify
    STATUS current
    DESCRIPTION
        "Parameter 'client-port' in event UDP.9"
    ::= { udpEventObjects9 2 }

udp9_data-len OBJECT-TYPE
    SYNTAX Integer32
    MAX-ACCESS accessible-for-notify
    STATUS current
    DESCRIPTION
        "Parameter 'data-len' in event UDP.9"
    ::= { udpEventObjects9 3 }


udpNotification1 NOTIFICATION-TYPE
    OBJECTS { 
              udp1_source_ip_address, 
              udp1_destination_ip_address,
              udp1_port_number 
            }
    STATUS current
    DESCRIPTION
        "Notification of Event UDP.1

        Message: 'Packet from $1 for $2 port $3, no server'

        Parameters list:
              $1: udp1_source_ip_address
              $2: udp1_destination_ip_address
              $3: udp1_port_number

        This message is generated when a packet is discarded because UDP is not
        installed in the router. The packet was for the broadcast address."
    ::= { udpNotificationsPrefix 1 }

udpNotification2 NOTIFICATION-TYPE
    OBJECTS { 
              udp2_source_ip_address, 
              udp2_destination_ip_address,
              udp2_port_number 
            }
    STATUS current
    DESCRIPTION
        "Notification of Event UDP.2

        Message: 'Packet from $1 for $2 port $3, no server'

        Parameters list:
              $1: udp2_source_ip_address
              $2: udp2_destination_ip_address
              $3: udp2_port_number

        This message is generated when a packet is discarded because UDP is not
        installed in the router. The packet was addressed to the router."
    ::= { udpNotificationsPrefix 2 }

udpNotification3 NOTIFICATION-TYPE
    OBJECTS { 
              udp3_source_ip_address, 
              udp3_length 
            }
    STATUS current
    DESCRIPTION
        "Notification of Event UDP.3

        Message: 'Discarded packet from $1, bad length $2'

        Parameters list:
              $1: udp3_source_ip_address
              $2: udp3_length

        This message is generated when a packet is discarded because it had
        an UDP length greater than its IP length."
    ::= { udpNotificationsPrefix 3 }

udpNotification4 NOTIFICATION-TYPE
    OBJECTS { 
              udp4_calculated_checksum, 
              udp4_received_checksum 
            }
    STATUS current
    DESCRIPTION
        "Notification of Event UDP.4

        Message: 'Bad checksum - calculated $1, received $2'

        Parameters list:
              $1: udp4_calculated_checksum
              $2: udp4_received_checksum

        This message is generated when a packet is discarded because it had
        a bad checksum."
    ::= { udpNotificationsPrefix 4 }

udpNotification5 NOTIFICATION-TYPE
    OBJECTS { 
              udp5_incoming_interface, 
              udp5_source_ip_address,
              udp5_source_udp_port,
              udp5_destination_ip_address,
              udp5_destination_udp_port 
            }
    STATUS current
    DESCRIPTION
        "Notification of Event UDP.5

        Message: 'Broadcast packet received on interface $1 from $2 port $3 for $4 port $5'

        Parameters list:
              $1: udp5_incoming_interface
              $2: udp5_source_ip_address
              $3: udp5_source_udp_port
              $4: udp5_destination_ip_address
              $5: udp5_destination_udp_port

        This message is generated when a broadcast UDP packet is received"
    ::= { udpNotificationsPrefix 5 }

udpNotification6 NOTIFICATION-TYPE
    OBJECTS { 
              udp6_next_hop, 
              udp6_vrf_next_hop 
            }
    STATUS current
    DESCRIPTION
        "Notification of Event UDP.6

        Message: 'Broadcast packet forwarded to $1 on vrf $2'

        Parameters list:
              $1: udp6_next_hop
              $2: udp6_vrf_next_hop

        This message is generated when a broadcast UDP packet is being forwarded
        to another destination address on the specified vrf."
    ::= { udpNotificationsPrefix 6 }

udpNotification7 NOTIFICATION-TYPE
    OBJECTS { 
              udp7_udp_port 
            }
    STATUS current
    DESCRIPTION
        "Notification of Event UDP.7

        Message: 'Waiting for data on UPD PORT $1'

        Parameters list:
              $1: udp7_udp_port

        This message is generated when a echo-responder service is waiting for
        data on a UDP port."
    ::= { udpNotificationsPrefix 7 }

udpNotification8 NOTIFICATION-TYPE
    STATUS current
    DESCRIPTION
        "Notification of Event UDP.8

        Message: 'Service echo-responder UDP stopped'

        The service echo-responder UDP was stopped due to an user request."
    ::= { udpNotificationsPrefix 8 }

udpNotification9 NOTIFICATION-TYPE
    OBJECTS { 
              udp9_client-address, 
              udp9_client-port,
              udp9_data-len 
            }
    STATUS current
    DESCRIPTION
        "Notification of Event UDP.9

        Message: 'Received echo-request from $1 port $2, data len $3.'

        Parameters list:
              $1: udp9_client-address
              $2: udp9_client-port
              $3: udp9_data-len

        This message is generated when an echo-request UDP packet is received"
    ::= { udpNotificationsPrefix 9 }


END
