-- =====================================================================
-- == DIGI-DEVICE-INFO-MIB:                                           ==
-- == DIGI Connect Device Info Management Information Base            ==
-- ==                                                                 ==
-- ==   Digi International Part Number: 40002410_A                    ==
-- ==                                                                 ==
-- == (c) Copyright 2001-2004 Digi International, Inc.                ==
-- =====================================================================

DIGI-DEVICE-INFO-MIB DEFINITIONS ::= BEGIN

IMPORTS
digiDeviceInfo FROM DIGI-SMI
OBJECT-TYPE FROM RFC-1212;

--   digiDeviceInfo MODULE-IDENTITY
--       LAST-UPDATED "0201090100Z"
--       ORGANIZATION "Digi International Inc."
--       CONTACT-INFO
--               "        Michael Nicholson
--                Postal: Digi International Inc.
--		          11001 Bren Road East
--                        Minnetonka, MN 55343
--
--                   Tel: 952-912-3146
--                   Fax: 952-912-4952
--                E-mail: Mike.Nicholson@digi.com"
--       DESCRIPTION
--               "Digi Connect Device Info MIB"
--       ::= { digiConnect 1 }

-- === + Textual Conventions + =========================================
DisplayString ::= OCTET STRING

-- =====================================================================
-- =====================================================================
-- === + DEVICE INFO + =================================================
-- =====================================================================
-- =====================================================================

diProduct OBJECT-TYPE
    SYNTAX DisplayString
    ACCESS read-only
    STATUS mandatory
    DESCRIPTION
        "Digi product name"
::= { digiDeviceInfo 1 }

diPhysicalAddress OBJECT-TYPE
    SYNTAX DisplayString
    ACCESS read-only
    STATUS mandatory
    DESCRIPTION
        "This device's physical address"
::= { digiDeviceInfo 2 }

diFirmwareVersion OBJECT-TYPE
    SYNTAX DisplayString
    ACCESS read-only
    STATUS mandatory
    DESCRIPTION
        "Version of the currently loaded firmware"
::= { digiDeviceInfo 3 }

diBootVersion OBJECT-TYPE
    SYNTAX DisplayString
    ACCESS read-only
    STATUS mandatory
    DESCRIPTION
        "Version of the boot firmware"
::= { digiDeviceInfo 4 }

diPostVersion OBJECT-TYPE
    SYNTAX DisplayString
    ACCESS read-only
    STATUS mandatory
    DESCRIPTION
        "Version of the post firmware"
::= { digiDeviceInfo 5 }

diCpuUtilization OBJECT-TYPE
    SYNTAX INTEGER
    ACCESS read-only
    STATUS mandatory
    DESCRIPTION
         "Current percentaga of CPU utilization on this device"
::= { digiDeviceInfo 6 }

diUpTime OBJECT-TYPE
    SYNTAX DisplayString
    ACCESS read-only
    STATUS mandatory
    DESCRIPTION
        "Time in hours, minutes, and seconds that this device has been up"
::= { digiDeviceInfo 7 }

diTotalMemory OBJECT-TYPE
    SYNTAX INTEGER
    ACCESS read-only
    STATUS mandatory
    DESCRIPTION
        "Total number of bytes of memory in this device"
::= { digiDeviceInfo 8 }

diFreeMemory OBJECT-TYPE
    SYNTAX INTEGER
    ACCESS read-only
    STATUS mandatory
    DESCRIPTION
        "Total number of bytes of free memory in this device"
::= { digiDeviceInfo 9 }

diUsedMemory OBJECT-TYPE
    SYNTAX INTEGER
    ACCESS read-only
    STATUS mandatory
    DESCRIPTION
        "Total number of bytes of memory in use in this device"
::= { digiDeviceInfo 10 }

END
