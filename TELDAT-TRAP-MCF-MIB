-- file automatically created


TELDAT-TRAP-MCF-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


mcfTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the MCF event subsystem."
    REVISION "201401200930Z"
    DESCRIPTION "Initial implementation"
        ::= { telEventTraps 105 }


mcfEventsGroup	OBJECT IDENTIFIER	::= { mcfTrapsMIB 1 }

mcfNotifications	OBJECT IDENTIFIER	::= { mcfTrapsMIB 2 }
mcfNotificationsPrefix	OBJECT IDENTIFIER	::= { mcfNotifications 0 }

mcfEventObjects6 OBJECT-IDENTITY
    STATUS current
    DESCRIPTION
        "Event MCF.6
        The MAC Filter configured on at the given direction and interface
        has been successfully initialized and is in effect."
    ::= { mcfEventsGroup 6 }

mcf6_name OBJECT-TYPE
    SYNTAX DisplayString
    MAX-ACCESS accessible-for-notify
    STATUS current
    DESCRIPTION
        "Parameter 'name' in event MCF.6"
    ::= { mcfEventObjects6 1 }

mcfEventObjects7 OBJECT-IDENTITY
    STATUS current
    DESCRIPTION
        "Event MCF.7
        The specified MAC Filter has matched a frame on the given direction
        and interface. The frame was excluded from further processing."
    ::= { mcfEventsGroup 7 }

mcf7_filter OBJECT-TYPE
    SYNTAX DisplayString
    MAX-ACCESS accessible-for-notify
    STATUS current
    DESCRIPTION
        "Parameter 'filter' in event MCF.7"
    ::= { mcfEventObjects7 1 }

mcf7_source OBJECT-TYPE
    SYNTAX DisplayString
    MAX-ACCESS accessible-for-notify
    STATUS current
    DESCRIPTION
        "Parameter 'source' in event MCF.7"
    ::= { mcfEventObjects7 2 }

mcf7_dest OBJECT-TYPE
    SYNTAX DisplayString
    MAX-ACCESS accessible-for-notify
    STATUS current
    DESCRIPTION
        "Parameter 'dest' in event MCF.7"
    ::= { mcfEventObjects7 3 }

mcf7_interface OBJECT-TYPE
    SYNTAX DisplayString
    MAX-ACCESS accessible-for-notify
    STATUS current
    DESCRIPTION
        "Parameter 'interface' in event MCF.7"
    ::= { mcfEventObjects7 4 }

mcfEventObjects8 OBJECT-IDENTITY
    STATUS current
    DESCRIPTION
        "Event MCF.8
        The specified MAC Filter has matched a frame on the given direction
        and interface. The frame was included in further processing."
    ::= { mcfEventsGroup 8 }

mcf8_filter OBJECT-TYPE
    SYNTAX DisplayString
    MAX-ACCESS accessible-for-notify
    STATUS current
    DESCRIPTION
        "Parameter 'filter' in event MCF.8"
    ::= { mcfEventObjects8 1 }

mcf8_source OBJECT-TYPE
    SYNTAX DisplayString
    MAX-ACCESS accessible-for-notify
    STATUS current
    DESCRIPTION
        "Parameter 'source' in event MCF.8"
    ::= { mcfEventObjects8 2 }

mcf8_dest OBJECT-TYPE
    SYNTAX DisplayString
    MAX-ACCESS accessible-for-notify
    STATUS current
    DESCRIPTION
        "Parameter 'dest' in event MCF.8"
    ::= { mcfEventObjects8 3 }

mcf8_interface OBJECT-TYPE
    SYNTAX DisplayString
    MAX-ACCESS accessible-for-notify
    STATUS current
    DESCRIPTION
        "Parameter 'interface' in event MCF.8"
    ::= { mcfEventObjects8 4 }

mcfEventObjects9 OBJECT-IDENTITY
    STATUS current
    DESCRIPTION
        "Event MCF.9
        The specified MAC Filter has matched a frame on the given direction
        and interface. The frame was filtered according to the configured
        action."
    ::= { mcfEventsGroup 9 }

mcf9_filter OBJECT-TYPE
    SYNTAX DisplayString
    MAX-ACCESS accessible-for-notify
    STATUS current
    DESCRIPTION
        "Parameter 'filter' in event MCF.9"
    ::= { mcfEventObjects9 1 }

mcf9_tag OBJECT-TYPE
    SYNTAX Integer32
    MAX-ACCESS accessible-for-notify
    STATUS current
    DESCRIPTION
        "Parameter 'tag' in event MCF.9"
    ::= { mcfEventObjects9 2 }

mcf9_source OBJECT-TYPE
    SYNTAX DisplayString
    MAX-ACCESS accessible-for-notify
    STATUS current
    DESCRIPTION
        "Parameter 'source' in event MCF.9"
    ::= { mcfEventObjects9 3 }

mcf9_dest OBJECT-TYPE
    SYNTAX DisplayString
    MAX-ACCESS accessible-for-notify
    STATUS current
    DESCRIPTION
        "Parameter 'dest' in event MCF.9"
    ::= { mcfEventObjects9 4 }

mcf9_interface OBJECT-TYPE
    SYNTAX DisplayString
    MAX-ACCESS accessible-for-notify
    STATUS current
    DESCRIPTION
        "Parameter 'interface' in event MCF.9"
    ::= { mcfEventObjects9 5 }


mcfNotification1 NOTIFICATION-TYPE
    STATUS current
    DESCRIPTION
        "Notification of Event MCF.1

        Message: 'MAC Filtering enabled'

        The MAC Filtering database has been enabled."
    ::= { mcfNotificationsPrefix 1 }

mcfNotification2 NOTIFICATION-TYPE
    STATUS current
    DESCRIPTION
        "Notification of Event MCF.2

        Message: 'MAC Filtering disabled'

        The MAC Filtering database has been disabled."
    ::= { mcfNotificationsPrefix 2 }

mcfNotification3 NOTIFICATION-TYPE
    STATUS current
    DESCRIPTION
        "Notification of Event MCF.3

        Message: 'MAC Filtering no memory for initialization'

        The MAC Filtering database initilization has failed to allocate
        memory for the MAC Filter Control structures."
    ::= { mcfNotificationsPrefix 3 }

mcfNotification4 NOTIFICATION-TYPE
    STATUS current
    DESCRIPTION
        "Notification of Event MCF.4

        Message: 'MAC Filtering bad interface number given in initialization'

        The MAC Filtering database initilization has a non-existent interface
        configured with a filter."
    ::= { mcfNotificationsPrefix 4 }

mcfNotification5 NOTIFICATION-TYPE
    STATUS current
    DESCRIPTION
        "Notification of Event MCF.5

        Message: 'MAC Filtering database initialization error'

        The MAC Filtering database initilization has encountered an error
        in creating the filter database."
    ::= { mcfNotificationsPrefix 5 }

mcfNotification6 NOTIFICATION-TYPE
    OBJECTS { 
              mcf6_name 
            }
    STATUS current
    DESCRIPTION
        "Notification of Event MCF.6

        Message: 'MAC Filtering initialized filter at $1 successfully'

        Parameters list:
              $1: mcf6_name

        The MAC Filter configured on at the given direction and interface
        has been successfully initialized and is in effect."
    ::= { mcfNotificationsPrefix 6 }

mcfNotification7 NOTIFICATION-TYPE
    OBJECTS { 
              mcf7_filter, 
              mcf7_source,
              mcf7_dest,
              mcf7_interface 
            }
    STATUS current
    DESCRIPTION
        "Notification of Event MCF.7

        Message: 'MAC Filter $1 excludes frame $2->$3, interface $4'

        Parameters list:
              $1: mcf7_filter
              $2: mcf7_source
              $3: mcf7_dest
              $4: mcf7_interface

        The specified MAC Filter has matched a frame on the given direction
        and interface. The frame was excluded from further processing."
    ::= { mcfNotificationsPrefix 7 }

mcfNotification8 NOTIFICATION-TYPE
    OBJECTS { 
              mcf8_filter, 
              mcf8_source,
              mcf8_dest,
              mcf8_interface 
            }
    STATUS current
    DESCRIPTION
        "Notification of Event MCF.8

        Message: 'MAC Filter $1 includes frame $2->$3, interface $4'

        Parameters list:
              $1: mcf8_filter
              $2: mcf8_source
              $3: mcf8_dest
              $4: mcf8_interface

        The specified MAC Filter has matched a frame on the given direction
        and interface. The frame was included in further processing."
    ::= { mcfNotificationsPrefix 8 }

mcfNotification9 NOTIFICATION-TYPE
    OBJECTS { 
              mcf9_filter, 
              mcf9_tag,
              mcf9_source,
              mcf9_dest,
              mcf9_interface 
            }
    STATUS current
    DESCRIPTION
        "Notification of Event MCF.9

        Message: 'MAC Filter $1 tags($2) frame $3->$4, interface $5'

        Parameters list:
              $1: mcf9_filter
              $2: mcf9_tag
              $3: mcf9_source
              $4: mcf9_dest
              $5: mcf9_interface

        The specified MAC Filter has matched a frame on the given direction
        and interface. The frame was filtered according to the configured
        action."
    ::= { mcfNotificationsPrefix 9 }


END
