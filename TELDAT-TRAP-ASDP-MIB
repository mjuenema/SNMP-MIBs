-- file automatically created


TELDAT-TRAP-ASDP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


asdpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ASDP event subsystem."
    REVISION "201401200930Z"
    DESCRIPTION "Initial implementation"
        ::= { telEventTraps 145 }


asdpEventsGroup	OBJECT IDENTIFIER	::= { asdpTrapsMIB 1 }

asdpNotifications	OBJECT IDENTIFIER	::= { asdpTrapsMIB 2 }
asdpNotificationsPrefix	OBJECT IDENTIFIER	::= { asdpNotifications 0 }

asdpEventObjects1 OBJECT-IDENTITY
    STATUS current
    DESCRIPTION
        "Event ASDP.1
        Data has been received from TCP."
    ::= { asdpEventsGroup 1 }

asdp1_size OBJECT-TYPE
    SYNTAX Integer32
    MAX-ACCESS accessible-for-notify
    STATUS current
    DESCRIPTION
        "Parameter 'size' in event ASDP.1"
    ::= { asdpEventObjects1 1 }

asdp1_State OBJECT-TYPE
    SYNTAX Integer32
    MAX-ACCESS accessible-for-notify
    STATUS current
    DESCRIPTION
        "Parameter 'State' in event ASDP.1"
    ::= { asdpEventObjects1 2 }

asdp1_Interface OBJECT-TYPE
    SYNTAX DisplayString
    MAX-ACCESS accessible-for-notify
    STATUS current
    DESCRIPTION
        "Parameter 'Interface' in event ASDP.1"
    ::= { asdpEventObjects1 3 }

asdpEventObjects2 OBJECT-IDENTITY
    STATUS current
    DESCRIPTION
        "Event ASDP.2
        Data has been sent to TCP."
    ::= { asdpEventsGroup 2 }

asdp2_size OBJECT-TYPE
    SYNTAX Integer32
    MAX-ACCESS accessible-for-notify
    STATUS current
    DESCRIPTION
        "Parameter 'size' in event ASDP.2"
    ::= { asdpEventObjects2 1 }

asdp2_State OBJECT-TYPE
    SYNTAX Integer32
    MAX-ACCESS accessible-for-notify
    STATUS current
    DESCRIPTION
        "Parameter 'State' in event ASDP.2"
    ::= { asdpEventObjects2 2 }

asdp2_Interface OBJECT-TYPE
    SYNTAX DisplayString
    MAX-ACCESS accessible-for-notify
    STATUS current
    DESCRIPTION
        "Parameter 'Interface' in event ASDP.2"
    ::= { asdpEventObjects2 3 }

asdpEventObjects3 OBJECT-IDENTITY
    STATUS current
    DESCRIPTION
        "Event ASDP.3
        Data has been sent from ASDP interface handler through serial line."
    ::= { asdpEventsGroup 3 }

asdp3_size OBJECT-TYPE
    SYNTAX Integer32
    MAX-ACCESS accessible-for-notify
    STATUS current
    DESCRIPTION
        "Parameter 'size' in event ASDP.3"
    ::= { asdpEventObjects3 1 }

asdp3_State OBJECT-TYPE
    SYNTAX Integer32
    MAX-ACCESS accessible-for-notify
    STATUS current
    DESCRIPTION
        "Parameter 'State' in event ASDP.3"
    ::= { asdpEventObjects3 2 }

asdp3_Interface OBJECT-TYPE
    SYNTAX DisplayString
    MAX-ACCESS accessible-for-notify
    STATUS current
    DESCRIPTION
        "Parameter 'Interface' in event ASDP.3"
    ::= { asdpEventObjects3 3 }

asdpEventObjects4 OBJECT-IDENTITY
    STATUS current
    DESCRIPTION
        "Event ASDP.4
        Data has been received from serial line."
    ::= { asdpEventsGroup 4 }

asdp4_size OBJECT-TYPE
    SYNTAX Integer32
    MAX-ACCESS accessible-for-notify
    STATUS current
    DESCRIPTION
        "Parameter 'size' in event ASDP.4"
    ::= { asdpEventObjects4 1 }

asdp4_State OBJECT-TYPE
    SYNTAX Integer32
    MAX-ACCESS accessible-for-notify
    STATUS current
    DESCRIPTION
        "Parameter 'State' in event ASDP.4"
    ::= { asdpEventObjects4 2 }

asdp4_Interface OBJECT-TYPE
    SYNTAX DisplayString
    MAX-ACCESS accessible-for-notify
    STATUS current
    DESCRIPTION
        "Parameter 'Interface' in event ASDP.4"
    ::= { asdpEventObjects4 3 }

asdpEventObjects5 OBJECT-IDENTITY
    STATUS current
    DESCRIPTION
        "Event ASDP.5
        TCP input session has been established."
    ::= { asdpEventsGroup 5 }

asdp5_rem_ip OBJECT-TYPE
    SYNTAX IpAddress
    MAX-ACCESS accessible-for-notify
    STATUS current
    DESCRIPTION
        "Parameter 'rem_ip' in event ASDP.5"
    ::= { asdpEventObjects5 1 }

asdp5_rem_port OBJECT-TYPE
    SYNTAX Integer32
    MAX-ACCESS accessible-for-notify
    STATUS current
    DESCRIPTION
        "Parameter 'rem_port' in event ASDP.5"
    ::= { asdpEventObjects5 2 }

asdp5_State OBJECT-TYPE
    SYNTAX Integer32
    MAX-ACCESS accessible-for-notify
    STATUS current
    DESCRIPTION
        "Parameter 'State' in event ASDP.5"
    ::= { asdpEventObjects5 3 }

asdp5_Interface OBJECT-TYPE
    SYNTAX DisplayString
    MAX-ACCESS accessible-for-notify
    STATUS current
    DESCRIPTION
        "Parameter 'Interface' in event ASDP.5"
    ::= { asdpEventObjects5 4 }

asdpEventObjects6 OBJECT-IDENTITY
    STATUS current
    DESCRIPTION
        "Event ASDP.6
        TCP output session has been established."
    ::= { asdpEventsGroup 6 }

asdp6_State OBJECT-TYPE
    SYNTAX Integer32
    MAX-ACCESS accessible-for-notify
    STATUS current
    DESCRIPTION
        "Parameter 'State' in event ASDP.6"
    ::= { asdpEventObjects6 1 }

asdp6_Interface OBJECT-TYPE
    SYNTAX DisplayString
    MAX-ACCESS accessible-for-notify
    STATUS current
    DESCRIPTION
        "Parameter 'Interface' in event ASDP.6"
    ::= { asdpEventObjects6 2 }

asdpEventObjects7 OBJECT-IDENTITY
    STATUS current
    DESCRIPTION
        "Event ASDP.7
        TCP output session has been established."
    ::= { asdpEventsGroup 7 }

asdp7_State OBJECT-TYPE
    SYNTAX Integer32
    MAX-ACCESS accessible-for-notify
    STATUS current
    DESCRIPTION
        "Parameter 'State' in event ASDP.7"
    ::= { asdpEventObjects7 1 }

asdp7_Interface OBJECT-TYPE
    SYNTAX DisplayString
    MAX-ACCESS accessible-for-notify
    STATUS current
    DESCRIPTION
        "Parameter 'Interface' in event ASDP.7"
    ::= { asdpEventObjects7 2 }

asdpEventObjects8 OBJECT-IDENTITY
    STATUS current
    DESCRIPTION
        "Event ASDP.8
        Timer expired."
    ::= { asdpEventsGroup 8 }

asdp8_timer OBJECT-TYPE
    SYNTAX DisplayString
    MAX-ACCESS accessible-for-notify
    STATUS current
    DESCRIPTION
        "Parameter 'timer' in event ASDP.8"
    ::= { asdpEventObjects8 1 }

asdp8_State OBJECT-TYPE
    SYNTAX Integer32
    MAX-ACCESS accessible-for-notify
    STATUS current
    DESCRIPTION
        "Parameter 'State' in event ASDP.8"
    ::= { asdpEventObjects8 2 }

asdp8_Interface OBJECT-TYPE
    SYNTAX DisplayString
    MAX-ACCESS accessible-for-notify
    STATUS current
    DESCRIPTION
        "Parameter 'Interface' in event ASDP.8"
    ::= { asdpEventObjects8 3 }

asdpEventObjects9 OBJECT-IDENTITY
    STATUS current
    DESCRIPTION
        "Event ASDP.9
        Timer expired."
    ::= { asdpEventsGroup 9 }

asdp9_timer OBJECT-TYPE
    SYNTAX Integer32
    MAX-ACCESS accessible-for-notify
    STATUS current
    DESCRIPTION
        "Parameter 'timer' in event ASDP.9"
    ::= { asdpEventObjects9 1 }

asdp9_State OBJECT-TYPE
    SYNTAX Integer32
    MAX-ACCESS accessible-for-notify
    STATUS current
    DESCRIPTION
        "Parameter 'State' in event ASDP.9"
    ::= { asdpEventObjects9 2 }

asdp9_Interface OBJECT-TYPE
    SYNTAX DisplayString
    MAX-ACCESS accessible-for-notify
    STATUS current
    DESCRIPTION
        "Parameter 'Interface' in event ASDP.9"
    ::= { asdpEventObjects9 3 }

asdpEventObjects10 OBJECT-IDENTITY
    STATUS current
    DESCRIPTION
        "Event ASDP.10
        A TCP output session attempt has been made."
    ::= { asdpEventsGroup 10 }

asdp10_rem_ip OBJECT-TYPE
    SYNTAX IpAddress
    MAX-ACCESS accessible-for-notify
    STATUS current
    DESCRIPTION
        "Parameter 'rem_ip' in event ASDP.10"
    ::= { asdpEventObjects10 1 }

asdp10_rem_port OBJECT-TYPE
    SYNTAX Integer32
    MAX-ACCESS accessible-for-notify
    STATUS current
    DESCRIPTION
        "Parameter 'rem_port' in event ASDP.10"
    ::= { asdpEventObjects10 2 }

asdp10_State OBJECT-TYPE
    SYNTAX Integer32
    MAX-ACCESS accessible-for-notify
    STATUS current
    DESCRIPTION
        "Parameter 'State' in event ASDP.10"
    ::= { asdpEventObjects10 3 }

asdp10_Interface OBJECT-TYPE
    SYNTAX DisplayString
    MAX-ACCESS accessible-for-notify
    STATUS current
    DESCRIPTION
        "Parameter 'Interface' in event ASDP.10"
    ::= { asdpEventObjects10 4 }

asdpEventObjects11 OBJECT-IDENTITY
    STATUS current
    DESCRIPTION
        "Event ASDP.11
        Serial Line control state change."
    ::= { asdpEventsGroup 11 }

asdp11_Sig_state OBJECT-TYPE
    SYNTAX DisplayString
    MAX-ACCESS accessible-for-notify
    STATUS current
    DESCRIPTION
        "Parameter 'Sig_state' in event ASDP.11"
    ::= { asdpEventObjects11 1 }

asdp11_State OBJECT-TYPE
    SYNTAX Integer32
    MAX-ACCESS accessible-for-notify
    STATUS current
    DESCRIPTION
        "Parameter 'State' in event ASDP.11"
    ::= { asdpEventObjects11 2 }

asdp11_Interface OBJECT-TYPE
    SYNTAX DisplayString
    MAX-ACCESS accessible-for-notify
    STATUS current
    DESCRIPTION
        "Parameter 'Interface' in event ASDP.11"
    ::= { asdpEventObjects11 3 }

asdpEventObjects12 OBJECT-IDENTITY
    STATUS current
    DESCRIPTION
        "Event ASDP.12
        A TCP output session attempt has failed."
    ::= { asdpEventsGroup 12 }

asdp12_rem_ip OBJECT-TYPE
    SYNTAX IpAddress
    MAX-ACCESS accessible-for-notify
    STATUS current
    DESCRIPTION
        "Parameter 'rem_ip' in event ASDP.12"
    ::= { asdpEventObjects12 1 }

asdp12_rem_port OBJECT-TYPE
    SYNTAX Integer32
    MAX-ACCESS accessible-for-notify
    STATUS current
    DESCRIPTION
        "Parameter 'rem_port' in event ASDP.12"
    ::= { asdpEventObjects12 2 }

asdp12_State OBJECT-TYPE
    SYNTAX Integer32
    MAX-ACCESS accessible-for-notify
    STATUS current
    DESCRIPTION
        "Parameter 'State' in event ASDP.12"
    ::= { asdpEventObjects12 3 }

asdp12_Interface OBJECT-TYPE
    SYNTAX DisplayString
    MAX-ACCESS accessible-for-notify
    STATUS current
    DESCRIPTION
        "Parameter 'Interface' in event ASDP.12"
    ::= { asdpEventObjects12 4 }

asdpEventObjects13 OBJECT-IDENTITY
    STATUS current
    DESCRIPTION
        "Event ASDP.13
        An AT command has been received."
    ::= { asdpEventsGroup 13 }

asdp13_cmd OBJECT-TYPE
    SYNTAX DisplayString
    MAX-ACCESS accessible-for-notify
    STATUS current
    DESCRIPTION
        "Parameter 'cmd' in event ASDP.13"
    ::= { asdpEventObjects13 1 }

asdp13_Interface OBJECT-TYPE
    SYNTAX DisplayString
    MAX-ACCESS accessible-for-notify
    STATUS current
    DESCRIPTION
        "Parameter 'Interface' in event ASDP.13"
    ::= { asdpEventObjects13 2 }

asdpEventObjects14 OBJECT-IDENTITY
    STATUS current
    DESCRIPTION
        "Event ASDP.14
        An AT command is transmiting."
    ::= { asdpEventsGroup 14 }

asdp14_cmd OBJECT-TYPE
    SYNTAX DisplayString
    MAX-ACCESS accessible-for-notify
    STATUS current
    DESCRIPTION
        "Parameter 'cmd' in event ASDP.14"
    ::= { asdpEventObjects14 1 }

asdp14_Interface OBJECT-TYPE
    SYNTAX DisplayString
    MAX-ACCESS accessible-for-notify
    STATUS current
    DESCRIPTION
        "Parameter 'Interface' in event ASDP.14"
    ::= { asdpEventObjects14 2 }

asdpEventObjects15 OBJECT-IDENTITY
    STATUS current
    DESCRIPTION
        "Event ASDP.15
        Data has been received from TCP."
    ::= { asdpEventsGroup 15 }

asdp15_Peer OBJECT-TYPE
    SYNTAX Integer32
    MAX-ACCESS accessible-for-notify
    STATUS current
    DESCRIPTION
        "Parameter 'Peer' in event ASDP.15"
    ::= { asdpEventObjects15 1 }

asdp15_size OBJECT-TYPE
    SYNTAX Integer32
    MAX-ACCESS accessible-for-notify
    STATUS current
    DESCRIPTION
        "Parameter 'size' in event ASDP.15"
    ::= { asdpEventObjects15 2 }

asdp15_State OBJECT-TYPE
    SYNTAX Integer32
    MAX-ACCESS accessible-for-notify
    STATUS current
    DESCRIPTION
        "Parameter 'State' in event ASDP.15"
    ::= { asdpEventObjects15 3 }

asdp15_Interface OBJECT-TYPE
    SYNTAX DisplayString
    MAX-ACCESS accessible-for-notify
    STATUS current
    DESCRIPTION
        "Parameter 'Interface' in event ASDP.15"
    ::= { asdpEventObjects15 4 }

asdpEventObjects16 OBJECT-IDENTITY
    STATUS current
    DESCRIPTION
        "Event ASDP.16
        Data has been sent to TCP."
    ::= { asdpEventsGroup 16 }

asdp16_Peer OBJECT-TYPE
    SYNTAX Integer32
    MAX-ACCESS accessible-for-notify
    STATUS current
    DESCRIPTION
        "Parameter 'Peer' in event ASDP.16"
    ::= { asdpEventObjects16 1 }

asdp16_size OBJECT-TYPE
    SYNTAX Integer32
    MAX-ACCESS accessible-for-notify
    STATUS current
    DESCRIPTION
        "Parameter 'size' in event ASDP.16"
    ::= { asdpEventObjects16 2 }

asdp16_State OBJECT-TYPE
    SYNTAX Integer32
    MAX-ACCESS accessible-for-notify
    STATUS current
    DESCRIPTION
        "Parameter 'State' in event ASDP.16"
    ::= { asdpEventObjects16 3 }

asdp16_Interface OBJECT-TYPE
    SYNTAX DisplayString
    MAX-ACCESS accessible-for-notify
    STATUS current
    DESCRIPTION
        "Parameter 'Interface' in event ASDP.16"
    ::= { asdpEventObjects16 4 }

asdpEventObjects17 OBJECT-IDENTITY
    STATUS current
    DESCRIPTION
        "Event ASDP.17
        TCP output session has been established."
    ::= { asdpEventsGroup 17 }

asdp17_Peer OBJECT-TYPE
    SYNTAX Integer32
    MAX-ACCESS accessible-for-notify
    STATUS current
    DESCRIPTION
        "Parameter 'Peer' in event ASDP.17"
    ::= { asdpEventObjects17 1 }

asdp17_State OBJECT-TYPE
    SYNTAX Integer32
    MAX-ACCESS accessible-for-notify
    STATUS current
    DESCRIPTION
        "Parameter 'State' in event ASDP.17"
    ::= { asdpEventObjects17 2 }

asdp17_Interface OBJECT-TYPE
    SYNTAX DisplayString
    MAX-ACCESS accessible-for-notify
    STATUS current
    DESCRIPTION
        "Parameter 'Interface' in event ASDP.17"
    ::= { asdpEventObjects17 3 }

asdpEventObjects18 OBJECT-IDENTITY
    STATUS current
    DESCRIPTION
        "Event ASDP.18
        TCP output session has been established."
    ::= { asdpEventsGroup 18 }

asdp18_Peer OBJECT-TYPE
    SYNTAX Integer32
    MAX-ACCESS accessible-for-notify
    STATUS current
    DESCRIPTION
        "Parameter 'Peer' in event ASDP.18"
    ::= { asdpEventObjects18 1 }

asdp18_State OBJECT-TYPE
    SYNTAX Integer32
    MAX-ACCESS accessible-for-notify
    STATUS current
    DESCRIPTION
        "Parameter 'State' in event ASDP.18"
    ::= { asdpEventObjects18 2 }

asdp18_Interface OBJECT-TYPE
    SYNTAX DisplayString
    MAX-ACCESS accessible-for-notify
    STATUS current
    DESCRIPTION
        "Parameter 'Interface' in event ASDP.18"
    ::= { asdpEventObjects18 3 }

asdpEventObjects19 OBJECT-IDENTITY
    STATUS current
    DESCRIPTION
        "Event ASDP.19
        Timer expired."
    ::= { asdpEventsGroup 19 }

asdp19_Peer OBJECT-TYPE
    SYNTAX Integer32
    MAX-ACCESS accessible-for-notify
    STATUS current
    DESCRIPTION
        "Parameter 'Peer' in event ASDP.19"
    ::= { asdpEventObjects19 1 }

asdp19_timer OBJECT-TYPE
    SYNTAX Integer32
    MAX-ACCESS accessible-for-notify
    STATUS current
    DESCRIPTION
        "Parameter 'timer' in event ASDP.19"
    ::= { asdpEventObjects19 2 }

asdp19_State OBJECT-TYPE
    SYNTAX Integer32
    MAX-ACCESS accessible-for-notify
    STATUS current
    DESCRIPTION
        "Parameter 'State' in event ASDP.19"
    ::= { asdpEventObjects19 3 }

asdp19_Interface OBJECT-TYPE
    SYNTAX DisplayString
    MAX-ACCESS accessible-for-notify
    STATUS current
    DESCRIPTION
        "Parameter 'Interface' in event ASDP.19"
    ::= { asdpEventObjects19 4 }

asdpEventObjects20 OBJECT-IDENTITY
    STATUS current
    DESCRIPTION
        "Event ASDP.20
        Can't open UDP port to Rx DATA."
    ::= { asdpEventsGroup 20 }

asdp20_Peer OBJECT-TYPE
    SYNTAX Integer32
    MAX-ACCESS accessible-for-notify
    STATUS current
    DESCRIPTION
        "Parameter 'Peer' in event ASDP.20"
    ::= { asdpEventObjects20 1 }

asdp20_State OBJECT-TYPE
    SYNTAX Integer32
    MAX-ACCESS accessible-for-notify
    STATUS current
    DESCRIPTION
        "Parameter 'State' in event ASDP.20"
    ::= { asdpEventObjects20 2 }

asdp20_Interface OBJECT-TYPE
    SYNTAX DisplayString
    MAX-ACCESS accessible-for-notify
    STATUS current
    DESCRIPTION
        "Parameter 'Interface' in event ASDP.20"
    ::= { asdpEventObjects20 3 }

asdpEventObjects21 OBJECT-IDENTITY
    STATUS current
    DESCRIPTION
        "Event ASDP.21
        UDP port is open to Rx DATA."
    ::= { asdpEventsGroup 21 }

asdp21_Peer OBJECT-TYPE
    SYNTAX Integer32
    MAX-ACCESS accessible-for-notify
    STATUS current
    DESCRIPTION
        "Parameter 'Peer' in event ASDP.21"
    ::= { asdpEventObjects21 1 }

asdp21_Port OBJECT-TYPE
    SYNTAX Integer32
    MAX-ACCESS accessible-for-notify
    STATUS current
    DESCRIPTION
        "Parameter 'Port' in event ASDP.21"
    ::= { asdpEventObjects21 2 }

asdp21_State OBJECT-TYPE
    SYNTAX Integer32
    MAX-ACCESS accessible-for-notify
    STATUS current
    DESCRIPTION
        "Parameter 'State' in event ASDP.21"
    ::= { asdpEventObjects21 3 }

asdp21_Interface OBJECT-TYPE
    SYNTAX DisplayString
    MAX-ACCESS accessible-for-notify
    STATUS current
    DESCRIPTION
        "Parameter 'Interface' in event ASDP.21"
    ::= { asdpEventObjects21 4 }

asdpEventObjects22 OBJECT-IDENTITY
    STATUS current
    DESCRIPTION
        "Event ASDP.22
        Data has been received from UDP."
    ::= { asdpEventsGroup 22 }

asdp22_Peer OBJECT-TYPE
    SYNTAX Integer32
    MAX-ACCESS accessible-for-notify
    STATUS current
    DESCRIPTION
        "Parameter 'Peer' in event ASDP.22"
    ::= { asdpEventObjects22 1 }

asdp22_size OBJECT-TYPE
    SYNTAX Integer32
    MAX-ACCESS accessible-for-notify
    STATUS current
    DESCRIPTION
        "Parameter 'size' in event ASDP.22"
    ::= { asdpEventObjects22 2 }

asdp22_State OBJECT-TYPE
    SYNTAX Integer32
    MAX-ACCESS accessible-for-notify
    STATUS current
    DESCRIPTION
        "Parameter 'State' in event ASDP.22"
    ::= { asdpEventObjects22 3 }

asdp22_Interface OBJECT-TYPE
    SYNTAX DisplayString
    MAX-ACCESS accessible-for-notify
    STATUS current
    DESCRIPTION
        "Parameter 'Interface' in event ASDP.22"
    ::= { asdpEventObjects22 4 }

asdpEventObjects23 OBJECT-IDENTITY
    STATUS current
    DESCRIPTION
        "Event ASDP.23
        Data has been sent to UDP."
    ::= { asdpEventsGroup 23 }

asdp23_Peer OBJECT-TYPE
    SYNTAX Integer32
    MAX-ACCESS accessible-for-notify
    STATUS current
    DESCRIPTION
        "Parameter 'Peer' in event ASDP.23"
    ::= { asdpEventObjects23 1 }

asdp23_size OBJECT-TYPE
    SYNTAX Integer32
    MAX-ACCESS accessible-for-notify
    STATUS current
    DESCRIPTION
        "Parameter 'size' in event ASDP.23"
    ::= { asdpEventObjects23 2 }

asdp23_State OBJECT-TYPE
    SYNTAX Integer32
    MAX-ACCESS accessible-for-notify
    STATUS current
    DESCRIPTION
        "Parameter 'State' in event ASDP.23"
    ::= { asdpEventObjects23 3 }

asdp23_Interface OBJECT-TYPE
    SYNTAX DisplayString
    MAX-ACCESS accessible-for-notify
    STATUS current
    DESCRIPTION
        "Parameter 'Interface' in event ASDP.23"
    ::= { asdpEventObjects23 4 }

asdpEventObjects24 OBJECT-IDENTITY
    STATUS current
    DESCRIPTION
        "Event ASDP.24
        Overrun occurs sending data to UDP."
    ::= { asdpEventsGroup 24 }

asdp24_Peer OBJECT-TYPE
    SYNTAX Integer32
    MAX-ACCESS accessible-for-notify
    STATUS current
    DESCRIPTION
        "Parameter 'Peer' in event ASDP.24"
    ::= { asdpEventObjects24 1 }

asdp24_timer OBJECT-TYPE
    SYNTAX Integer32
    MAX-ACCESS accessible-for-notify
    STATUS current
    DESCRIPTION
        "Parameter 'timer' in event ASDP.24"
    ::= { asdpEventObjects24 2 }

asdp24_State OBJECT-TYPE
    SYNTAX Integer32
    MAX-ACCESS accessible-for-notify
    STATUS current
    DESCRIPTION
        "Parameter 'State' in event ASDP.24"
    ::= { asdpEventObjects24 3 }

asdp24_Interface OBJECT-TYPE
    SYNTAX DisplayString
    MAX-ACCESS accessible-for-notify
    STATUS current
    DESCRIPTION
        "Parameter 'Interface' in event ASDP.24"
    ::= { asdpEventObjects24 4 }

asdpEventObjects25 OBJECT-IDENTITY
    STATUS current
    DESCRIPTION
        "Event ASDP.25
        UDP port for recive data has been closed."
    ::= { asdpEventsGroup 25 }

asdp25_Peer OBJECT-TYPE
    SYNTAX Integer32
    MAX-ACCESS accessible-for-notify
    STATUS current
    DESCRIPTION
        "Parameter 'Peer' in event ASDP.25"
    ::= { asdpEventObjects25 1 }

asdp25_State OBJECT-TYPE
    SYNTAX Integer32
    MAX-ACCESS accessible-for-notify
    STATUS current
    DESCRIPTION
        "Parameter 'State' in event ASDP.25"
    ::= { asdpEventObjects25 2 }

asdp25_Interface OBJECT-TYPE
    SYNTAX DisplayString
    MAX-ACCESS accessible-for-notify
    STATUS current
    DESCRIPTION
        "Parameter 'Interface' in event ASDP.25"
    ::= { asdpEventObjects25 3 }


asdpNotification1 NOTIFICATION-TYPE
    OBJECTS { 
              asdp1_size, 
              asdp1_State,
              asdp1_Interface 
            }
    STATUS current
    DESCRIPTION
        "Notification of Event ASDP.1

        Message: 'Data received from TCP. Size:$1, State:$2, Ifc:$3'

        Parameters list:
              $1: asdp1_size
              $2: asdp1_State
              $3: asdp1_Interface

        Data has been received from TCP."
    ::= { asdpNotificationsPrefix 1 }

asdpNotification2 NOTIFICATION-TYPE
    OBJECTS { 
              asdp2_size, 
              asdp2_State,
              asdp2_Interface 
            }
    STATUS current
    DESCRIPTION
        "Notification of Event ASDP.2

        Message: 'Data sent to TCP. Size:$1, State:$2, Ifc:$3'

        Parameters list:
              $1: asdp2_size
              $2: asdp2_State
              $3: asdp2_Interface

        Data has been sent to TCP."
    ::= { asdpNotificationsPrefix 2 }

asdpNotification3 NOTIFICATION-TYPE
    OBJECTS { 
              asdp3_size, 
              asdp3_State,
              asdp3_Interface 
            }
    STATUS current
    DESCRIPTION
        "Notification of Event ASDP.3

        Message: 'Data sent to serial line. Size:$1, State:$2, Ifc:$3'

        Parameters list:
              $1: asdp3_size
              $2: asdp3_State
              $3: asdp3_Interface

        Data has been sent from ASDP interface handler through serial line."
    ::= { asdpNotificationsPrefix 3 }

asdpNotification4 NOTIFICATION-TYPE
    OBJECTS { 
              asdp4_size, 
              asdp4_State,
              asdp4_Interface 
            }
    STATUS current
    DESCRIPTION
        "Notification of Event ASDP.4

        Message: 'Data received from serial line. Size:$1, State:$2, Ifc:$3'

        Parameters list:
              $1: asdp4_size
              $2: asdp4_State
              $3: asdp4_Interface

        Data has been received from serial line."
    ::= { asdpNotificationsPrefix 4 }

asdpNotification5 NOTIFICATION-TYPE
    OBJECTS { 
              asdp5_rem_ip, 
              asdp5_rem_port,
              asdp5_State,
              asdp5_Interface 
            }
    STATUS current
    DESCRIPTION
        "Notification of Event ASDP.5

        Message: 'TCP input session from remote IP addr:$1, port:$2, State:$3, Ifc:$4'

        Parameters list:
              $1: asdp5_rem_ip
              $2: asdp5_rem_port
              $3: asdp5_State
              $4: asdp5_Interface

        TCP input session has been established."
    ::= { asdpNotificationsPrefix 5 }

asdpNotification6 NOTIFICATION-TYPE
    OBJECTS { 
              asdp6_State, 
              asdp6_Interface 
            }
    STATUS current
    DESCRIPTION
        "Notification of Event ASDP.6

        Message: 'TCP output session stablished. State:$1, Ifc$2'

        Parameters list:
              $1: asdp6_State
              $2: asdp6_Interface

        TCP output session has been established."
    ::= { asdpNotificationsPrefix 6 }

asdpNotification7 NOTIFICATION-TYPE
    OBJECTS { 
              asdp7_State, 
              asdp7_Interface 
            }
    STATUS current
    DESCRIPTION
        "Notification of Event ASDP.7

        Message: 'TCP session closed. State:$1, Ifc:$2'

        Parameters list:
              $1: asdp7_State
              $2: asdp7_Interface

        TCP output session has been established."
    ::= { asdpNotificationsPrefix 7 }

asdpNotification8 NOTIFICATION-TYPE
    OBJECTS { 
              asdp8_timer, 
              asdp8_State,
              asdp8_Interface 
            }
    STATUS current
    DESCRIPTION
        "Notification of Event ASDP.8

        Message: '$1 timer expired State:$2, Ifc:$3'

        Parameters list:
              $1: asdp8_timer
              $2: asdp8_State
              $3: asdp8_Interface

        Timer expired."
    ::= { asdpNotificationsPrefix 8 }

asdpNotification9 NOTIFICATION-TYPE
    OBJECTS { 
              asdp9_timer, 
              asdp9_State,
              asdp9_Interface 
            }
    STATUS current
    DESCRIPTION
        "Notification of Event ASDP.9

        Message: 'Tx data overrun sending to TCP, Size:$1, State:$2, Ifc:$3'

        Parameters list:
              $1: asdp9_timer
              $2: asdp9_State
              $3: asdp9_Interface

        Timer expired."
    ::= { asdpNotificationsPrefix 9 }

asdpNotification10 NOTIFICATION-TYPE
    OBJECTS { 
              asdp10_rem_ip, 
              asdp10_rem_port,
              asdp10_State,
              asdp10_Interface 
            }
    STATUS current
    DESCRIPTION
        "Notification of Event ASDP.10

        Message: 'TCP output session attempt to IP addr:$1, port:$2, State:$3, Ifc$4'

        Parameters list:
              $1: asdp10_rem_ip
              $2: asdp10_rem_port
              $3: asdp10_State
              $4: asdp10_Interface

        A TCP output session attempt has been made."
    ::= { asdpNotificationsPrefix 10 }

asdpNotification11 NOTIFICATION-TYPE
    OBJECTS { 
              asdp11_Sig_state, 
              asdp11_State,
              asdp11_Interface 
            }
    STATUS current
    DESCRIPTION
        "Notification of Event ASDP.11

        Message: 'Serial Line signal control $1. State:$2, Ifc:$3'

        Parameters list:
              $1: asdp11_Sig_state
              $2: asdp11_State
              $3: asdp11_Interface

        Serial Line control state change."
    ::= { asdpNotificationsPrefix 11 }

asdpNotification12 NOTIFICATION-TYPE
    OBJECTS { 
              asdp12_rem_ip, 
              asdp12_rem_port,
              asdp12_State,
              asdp12_Interface 
            }
    STATUS current
    DESCRIPTION
        "Notification of Event ASDP.12

        Message: 'TCP output session attempt has failed IP addr:$1, port:$2, State:$3, Ifc$4'

        Parameters list:
              $1: asdp12_rem_ip
              $2: asdp12_rem_port
              $3: asdp12_State
              $4: asdp12_Interface

        A TCP output session attempt has failed."
    ::= { asdpNotificationsPrefix 12 }

asdpNotification13 NOTIFICATION-TYPE
    OBJECTS { 
              asdp13_cmd, 
              asdp13_Interface 
            }
    STATUS current
    DESCRIPTION
        "Notification of Event ASDP.13

        Message: 'An AT command has been received $1, Ifc$2'

        Parameters list:
              $1: asdp13_cmd
              $2: asdp13_Interface

        An AT command has been received."
    ::= { asdpNotificationsPrefix 13 }

asdpNotification14 NOTIFICATION-TYPE
    OBJECTS { 
              asdp14_cmd, 
              asdp14_Interface 
            }
    STATUS current
    DESCRIPTION
        "Notification of Event ASDP.14

        Message: 'An AT command is transmiting $1, Ifc$2'

        Parameters list:
              $1: asdp14_cmd
              $2: asdp14_Interface

        An AT command is transmiting."
    ::= { asdpNotificationsPrefix 14 }

asdpNotification15 NOTIFICATION-TYPE
    OBJECTS { 
              asdp15_Peer, 
              asdp15_size,
              asdp15_State,
              asdp15_Interface 
            }
    STATUS current
    DESCRIPTION
        "Notification of Event ASDP.15

        Message: 'Data received from TCP. Peer:$1 Size:$2, State:$3, Ifc:$4'

        Parameters list:
              $1: asdp15_Peer
              $2: asdp15_size
              $3: asdp15_State
              $4: asdp15_Interface

        Data has been received from TCP."
    ::= { asdpNotificationsPrefix 15 }

asdpNotification16 NOTIFICATION-TYPE
    OBJECTS { 
              asdp16_Peer, 
              asdp16_size,
              asdp16_State,
              asdp16_Interface 
            }
    STATUS current
    DESCRIPTION
        "Notification of Event ASDP.16

        Message: 'Data sent to TCP. Peer:$1 Size:$2, State:$3, Ifc:$4'

        Parameters list:
              $1: asdp16_Peer
              $2: asdp16_size
              $3: asdp16_State
              $4: asdp16_Interface

        Data has been sent to TCP."
    ::= { asdpNotificationsPrefix 16 }

asdpNotification17 NOTIFICATION-TYPE
    OBJECTS { 
              asdp17_Peer, 
              asdp17_State,
              asdp17_Interface 
            }
    STATUS current
    DESCRIPTION
        "Notification of Event ASDP.17

        Message: 'TCP output session stablished. Peer:$1 State:$2, Ifc$3'

        Parameters list:
              $1: asdp17_Peer
              $2: asdp17_State
              $3: asdp17_Interface

        TCP output session has been established."
    ::= { asdpNotificationsPrefix 17 }

asdpNotification18 NOTIFICATION-TYPE
    OBJECTS { 
              asdp18_Peer, 
              asdp18_State,
              asdp18_Interface 
            }
    STATUS current
    DESCRIPTION
        "Notification of Event ASDP.18

        Message: 'TCP session closed. Peer:$1 State:$2, Ifc:$3'

        Parameters list:
              $1: asdp18_Peer
              $2: asdp18_State
              $3: asdp18_Interface

        TCP output session has been established."
    ::= { asdpNotificationsPrefix 18 }

asdpNotification19 NOTIFICATION-TYPE
    OBJECTS { 
              asdp19_Peer, 
              asdp19_timer,
              asdp19_State,
              asdp19_Interface 
            }
    STATUS current
    DESCRIPTION
        "Notification of Event ASDP.19

        Message: 'Tx data overrun sending to TCP, Peer:$1 Size:$2, State:$3, Ifc:$4'

        Parameters list:
              $1: asdp19_Peer
              $2: asdp19_timer
              $3: asdp19_State
              $4: asdp19_Interface

        Timer expired."
    ::= { asdpNotificationsPrefix 19 }

asdpNotification20 NOTIFICATION-TYPE
    OBJECTS { 
              asdp20_Peer, 
              asdp20_State,
              asdp20_Interface 
            }
    STATUS current
    DESCRIPTION
        "Notification of Event ASDP.20

        Message: 'Can't open UDP port, Peer:$1, State:$2, Ifc:$3'

        Parameters list:
              $1: asdp20_Peer
              $2: asdp20_State
              $3: asdp20_Interface

        Can't open UDP port to Rx DATA."
    ::= { asdpNotificationsPrefix 20 }

asdpNotification21 NOTIFICATION-TYPE
    OBJECTS { 
              asdp21_Peer, 
              asdp21_Port,
              asdp21_State,
              asdp21_Interface 
            }
    STATUS current
    DESCRIPTION
        "Notification of Event ASDP.21

        Message: 'UDP port OPEN. Peer:$1 port:$2 State:$3, Ifc$4'

        Parameters list:
              $1: asdp21_Peer
              $2: asdp21_Port
              $3: asdp21_State
              $4: asdp21_Interface

        UDP port is open to Rx DATA."
    ::= { asdpNotificationsPrefix 21 }

asdpNotification22 NOTIFICATION-TYPE
    OBJECTS { 
              asdp22_Peer, 
              asdp22_size,
              asdp22_State,
              asdp22_Interface 
            }
    STATUS current
    DESCRIPTION
        "Notification of Event ASDP.22

        Message: 'Data received from UDP. Peer:$1 Size:$2, State:$3, Ifc:$4'

        Parameters list:
              $1: asdp22_Peer
              $2: asdp22_size
              $3: asdp22_State
              $4: asdp22_Interface

        Data has been received from UDP."
    ::= { asdpNotificationsPrefix 22 }

asdpNotification23 NOTIFICATION-TYPE
    OBJECTS { 
              asdp23_Peer, 
              asdp23_size,
              asdp23_State,
              asdp23_Interface 
            }
    STATUS current
    DESCRIPTION
        "Notification of Event ASDP.23

        Message: 'Data sent to UDP. Peer:$1 Size:$2, State:$3, Ifc:$4'

        Parameters list:
              $1: asdp23_Peer
              $2: asdp23_size
              $3: asdp23_State
              $4: asdp23_Interface

        Data has been sent to UDP."
    ::= { asdpNotificationsPrefix 23 }

asdpNotification24 NOTIFICATION-TYPE
    OBJECTS { 
              asdp24_Peer, 
              asdp24_timer,
              asdp24_State,
              asdp24_Interface 
            }
    STATUS current
    DESCRIPTION
        "Notification of Event ASDP.24

        Message: 'Tx data overrun sending to UDP, Peer:$1 Size:$2, State:$3, Ifc:$4'

        Parameters list:
              $1: asdp24_Peer
              $2: asdp24_timer
              $3: asdp24_State
              $4: asdp24_Interface

        Overrun occurs sending data to UDP."
    ::= { asdpNotificationsPrefix 24 }

asdpNotification25 NOTIFICATION-TYPE
    OBJECTS { 
              asdp25_Peer, 
              asdp25_State,
              asdp25_Interface 
            }
    STATUS current
    DESCRIPTION
        "Notification of Event ASDP.25

        Message: 'UDP port is closed. Peer:$1 State:$2, Ifc:$3'

        Parameters list:
              $1: asdp25_Peer
              $2: asdp25_State
              $3: asdp25_Interface

        UDP port for recive data has been closed."
    ::= { asdpNotificationsPrefix 25 }


END
