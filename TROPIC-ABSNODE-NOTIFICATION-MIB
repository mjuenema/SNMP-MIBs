TROPIC-ABSNODE-NOTIFICATION-MIB DEFINITIONS ::= BEGIN

-- (c) Copyright 2016 Nokia.  All rights reserved.
-- This software is the confidential and proprietary property of
-- Nokia and may only be used in accordance with the
-- terms of the license agreement provided with this software.

 IMPORTS
      tnNotificationObjs,
      tnTrapTime,
      tnTrapObjectIDType,
      tnTrapObjectID,
      tnTrapCategory,
      tnTrapDescr,
      tnTrapData,
      tnTrapServiceAffecting,
      tnTrapEntityType,
      tnTrapCondition                         FROM TROPIC-NOTIFICATION-MIB
      MODULE-IDENTITY,
      NOTIFICATION-TYPE                       FROM SNMPv2-SMI
      tnAbsNodeMIBModules                       FROM TROPIC-GLOBAL-REG;

  tnAbsNodeNotificationMIBModule MODULE-IDENTITY
      LAST-UPDATED    "201602261200Z"
      ORGANIZATION    "Alcatel-Lucent"
      CONTACT-INFO    "Alcatel-Lucent
                       Postal: 600 March Rd.
                       Kanata, Ontario
                       Canada K2K 2E6

                       Phone: +1 613 591 3600
                       Fax:   +1 613 591 3680"

      DESCRIPTION "Abstract Node Notifications."

      REVISION    "201602261200Z"
      DESCRIPTION "Initial version."

      ::= { tnAbsNodeMIBModules 2 }

---------------------------------------------------------------------------
-- Top Level Components of This MIB
---------------------------------------------------------------------------
  tnNotificationsAbsNode         OBJECT IDENTIFIER ::= { tnNotificationObjs 9 } -- !! see TROPIC-NOTIFICATION-MIB for already used ids
  tnAlarmNotificationsAbsNode    OBJECT IDENTIFIER ::= { tnNotificationsAbsNode 1 }
  tnEventNotificationsAbsNode    OBJECT IDENTIFIER ::= { tnNotificationsAbsNode 2 }

-- **************************************************************************
-- Extensions for TROPIC-TC MIB
--   1. TnEntityType - Add absNodeSubnode, absNodeTeLink, absNodeOtsPort, absNodeIfGroup, absNodeOtLinePort
--   2. TnCondition  - Add: ABSNODEOPSTATEUP, ABSNODEOPSTATEDOWN, ABSNODEOPSTATEDEG, ABSNODESHELFUNAVAIL
--
-- Extensions for TROPIC-NOTIFICATION-MIB
--   1. Valid gmpls objectIdTypes:
--      absNodeSubnodeObjectId     == 128  ????? 
--      absNodeTeLinkObjectId      == 129  ????? 
--      absNodeOtsPortObjectId     == 130  ????? 
--      absNodeIfGroupObjectId     == 131  ????? 
--      absNodeOtLineObjectId      == 132  ????? 
--
--   2. tnTrapObjectId values
--
--        switch(objectIdType){
--              case absNodeSubnodeObjectId:
--                      subnodeId = objectId;
--                      break;
--
--              case absNodeTeLinkObjectId:
--                      teLinkId = objectId;
--                      break;
--
--              case absNodeOtsPortObjectId:
--                      otsPortId = objectId
--                      break;
--
--              case absNodeIfGroupObjectId:
--                      ifGroupId = objectId;
--                      break;
--
--              case absNodeOtLineObjectId:
--                      otLineId = objectId;
--                      break;
--        }

-- ------------------------------------------------------------
-- Abstract Node alarms
-- ------------------------------------------------------------
    tnAbsNodeRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    ""
        ::= { tnAlarmNotificationsAbsNode 1 }

    tnAbsNodeClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    ""
        ::= { tnAlarmNotificationsAbsNode 2 }

-- ------------------------------------------------------------
-- Abstract Node Events
-- ------------------------------------------------------------
    tnAbsNodeCreatedNotif NOTIFICATION-TYPE
        OBJECTS {
            tnTrapTime,
            tnTrapObjectIDType,
            tnTrapObjectID,
            tnTrapCategory,
            tnTrapDescr,
            tnTrapData
        }
        STATUS         current
        DESCRIPTION    ""
        ::= { tnEventNotificationsAbsNode 1 }

    tnAbsNodeDeletedNotif NOTIFICATION-TYPE
        OBJECTS {
            tnTrapTime,
            tnTrapObjectIDType,
            tnTrapObjectID,
            tnTrapCategory,
            tnTrapDescr,
            tnTrapData
        }
        STATUS         current
        DESCRIPTION    ""
        ::= { tnEventNotificationsAbsNode 2 }

    tnAbsNodeModifiedNotif NOTIFICATION-TYPE
        OBJECTS {
            tnTrapTime,
            tnTrapObjectIDType,
            tnTrapObjectID,
            tnTrapCategory,
            tnTrapDescr,
            tnTrapData
        }
        STATUS         current
        DESCRIPTION    ""
        ::= { tnEventNotificationsAbsNode 3 }

END -- DEFINITION OF TROPIC-ABSNODE-NOTIFICATION-MIB
