-- file automatically created


TELDAT-TRAP-ACAT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


acatTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ACAT event subsystem."
    REVISION "201401200930Z"
    DESCRIPTION "Initial implementation"
        ::= { telEventTraps 225 }


acatEventsGroup	OBJECT IDENTIFIER	::= { acatTrapsMIB 1 }

acatNotifications	OBJECT IDENTIFIER	::= { acatTrapsMIB 2 }
acatNotificationsPrefix	OBJECT IDENTIFIER	::= { acatNotifications 0 }

acatEventObjects1 OBJECT-IDENTITY
    STATUS current
    DESCRIPTION
        "Event ACAT.1
        Group enabled in configuration / has been disabled."
    ::= { acatEventsGroup 1 }

acat1_grp_index OBJECT-TYPE
    SYNTAX Integer32
    MAX-ACCESS accessible-for-notify
    STATUS current
    DESCRIPTION
        "Parameter 'grp_index' in event ACAT.1"
    ::= { acatEventObjects1 1 }

acat1_enable OBJECT-TYPE
    SYNTAX DisplayString
    MAX-ACCESS accessible-for-notify
    STATUS current
    DESCRIPTION
        "Parameter 'enable' in event ACAT.1"
    ::= { acatEventObjects1 2 }

acatEventObjects2 OBJECT-IDENTITY
    STATUS current
    DESCRIPTION
        "Event ACAT.2
        Not enough memory available for reservation."
    ::= { acatEventsGroup 2 }

acat2_module OBJECT-TYPE
    SYNTAX DisplayString
    MAX-ACCESS accessible-for-notify
    STATUS current
    DESCRIPTION
        "Parameter 'module' in event ACAT.2"
    ::= { acatEventObjects2 1 }

acatEventObjects3 OBJECT-IDENTITY
    STATUS current
    DESCRIPTION
        "Event ACAT.3
        An option from a group has been registered/unregistered at an interface to track its state."
    ::= { acatEventsGroup 3 }

acat3_grp_index OBJECT-TYPE
    SYNTAX Integer32
    MAX-ACCESS accessible-for-notify
    STATUS current
    DESCRIPTION
        "Parameter 'grp_index' in event ACAT.3"
    ::= { acatEventObjects3 1 }

acat3_opt_index OBJECT-TYPE
    SYNTAX Integer32
    MAX-ACCESS accessible-for-notify
    STATUS current
    DESCRIPTION
        "Parameter 'opt_index' in event ACAT.3"
    ::= { acatEventObjects3 2 }

acat3_register OBJECT-TYPE
    SYNTAX DisplayString
    MAX-ACCESS accessible-for-notify
    STATUS current
    DESCRIPTION
        "Parameter 'register' in event ACAT.3"
    ::= { acatEventObjects3 3 }

acat3_iface OBJECT-TYPE
    SYNTAX DisplayString
    MAX-ACCESS accessible-for-notify
    STATUS current
    DESCRIPTION
        "Parameter 'iface' in event ACAT.3"
    ::= { acatEventObjects3 4 }

acatEventObjects4 OBJECT-IDENTITY
    STATUS current
    DESCRIPTION
        "Event ACAT.4
        An option from a group has changed its state."
    ::= { acatEventsGroup 4 }

acat4_grp_index OBJECT-TYPE
    SYNTAX Integer32
    MAX-ACCESS accessible-for-notify
    STATUS current
    DESCRIPTION
        "Parameter 'grp_index' in event ACAT.4"
    ::= { acatEventObjects4 1 }

acat4_opt_index OBJECT-TYPE
    SYNTAX Integer32
    MAX-ACCESS accessible-for-notify
    STATUS current
    DESCRIPTION
        "Parameter 'opt_index' in event ACAT.4"
    ::= { acatEventObjects4 2 }

acat4_state OBJECT-TYPE
    SYNTAX DisplayString
    MAX-ACCESS accessible-for-notify
    STATUS current
    DESCRIPTION
        "Parameter 'state' in event ACAT.4"
    ::= { acatEventObjects4 3 }

acatEventObjects5 OBJECT-IDENTITY
    STATUS current
    DESCRIPTION
        "Event ACAT.5
        Consider if a new option should be chosen."
    ::= { acatEventsGroup 5 }

acat5_grp_index OBJECT-TYPE
    SYNTAX Integer32
    MAX-ACCESS accessible-for-notify
    STATUS current
    DESCRIPTION
        "Parameter 'grp_index' in event ACAT.5"
    ::= { acatEventObjects5 1 }

acatEventObjects6 OBJECT-IDENTITY
    STATUS current
    DESCRIPTION
        "Event ACAT.6
        Active priority in a group has been changed."
    ::= { acatEventsGroup 6 }

acat6_grp_index OBJECT-TYPE
    SYNTAX Integer32
    MAX-ACCESS accessible-for-notify
    STATUS current
    DESCRIPTION
        "Parameter 'grp_index' in event ACAT.6"
    ::= { acatEventObjects6 1 }

acat6_active_pri OBJECT-TYPE
    SYNTAX Integer32
    MAX-ACCESS accessible-for-notify
    STATUS current
    DESCRIPTION
        "Parameter 'active_pri' in event ACAT.6"
    ::= { acatEventObjects6 2 }

acatEventObjects7 OBJECT-IDENTITY
    STATUS current
    DESCRIPTION
        "Event ACAT.7
        No option was chosen."
    ::= { acatEventsGroup 7 }

acat7_grp_index OBJECT-TYPE
    SYNTAX Integer32
    MAX-ACCESS accessible-for-notify
    STATUS current
    DESCRIPTION
        "Parameter 'grp_index' in event ACAT.7"
    ::= { acatEventObjects7 1 }

acatEventObjects8 OBJECT-IDENTITY
    STATUS current
    DESCRIPTION
        "Event ACAT.8
        An option from a group has been activated / deactivated."
    ::= { acatEventsGroup 8 }

acat8_grp_index OBJECT-TYPE
    SYNTAX Integer32
    MAX-ACCESS accessible-for-notify
    STATUS current
    DESCRIPTION
        "Parameter 'grp_index' in event ACAT.8"
    ::= { acatEventObjects8 1 }

acat8_opt_index OBJECT-TYPE
    SYNTAX Integer32
    MAX-ACCESS accessible-for-notify
    STATUS current
    DESCRIPTION
        "Parameter 'opt_index' in event ACAT.8"
    ::= { acatEventObjects8 2 }

acat8_activation OBJECT-TYPE
    SYNTAX DisplayString
    MAX-ACCESS accessible-for-notify
    STATUS current
    DESCRIPTION
        "Parameter 'activation' in event ACAT.8"
    ::= { acatEventObjects8 3 }

acatEventObjects9 OBJECT-IDENTITY
    STATUS current
    DESCRIPTION
        "Event ACAT.9
        A group timer has been programmed."
    ::= { acatEventsGroup 9 }

acat9_grp_index OBJECT-TYPE
    SYNTAX Integer32
    MAX-ACCESS accessible-for-notify
    STATUS current
    DESCRIPTION
        "Parameter 'grp_index' in event ACAT.9"
    ::= { acatEventObjects9 1 }

acat9_type OBJECT-TYPE
    SYNTAX DisplayString
    MAX-ACCESS accessible-for-notify
    STATUS current
    DESCRIPTION
        "Parameter 'type' in event ACAT.9"
    ::= { acatEventObjects9 2 }

acat9_seconds OBJECT-TYPE
    SYNTAX Integer32
    MAX-ACCESS accessible-for-notify
    STATUS current
    DESCRIPTION
        "Parameter 'seconds' in event ACAT.9"
    ::= { acatEventObjects9 3 }

acatEventObjects10 OBJECT-IDENTITY
    STATUS current
    DESCRIPTION
        "Event ACAT.10
        A group timer has been stopped."
    ::= { acatEventsGroup 10 }

acat10_grp_index OBJECT-TYPE
    SYNTAX Integer32
    MAX-ACCESS accessible-for-notify
    STATUS current
    DESCRIPTION
        "Parameter 'grp_index' in event ACAT.10"
    ::= { acatEventObjects10 1 }

acat10_type OBJECT-TYPE
    SYNTAX DisplayString
    MAX-ACCESS accessible-for-notify
    STATUS current
    DESCRIPTION
        "Parameter 'type' in event ACAT.10"
    ::= { acatEventObjects10 2 }

acatEventObjects11 OBJECT-IDENTITY
    STATUS current
    DESCRIPTION
        "Event ACAT.11
        A group timer has expired."
    ::= { acatEventsGroup 11 }

acat11_grp_index OBJECT-TYPE
    SYNTAX Integer32
    MAX-ACCESS accessible-for-notify
    STATUS current
    DESCRIPTION
        "Parameter 'grp_index' in event ACAT.11"
    ::= { acatEventObjects11 1 }

acat11_type OBJECT-TYPE
    SYNTAX DisplayString
    MAX-ACCESS accessible-for-notify
    STATUS current
    DESCRIPTION
        "Parameter 'type' in event ACAT.11"
    ::= { acatEventObjects11 2 }

acatEventObjects12 OBJECT-IDENTITY
    STATUS current
    DESCRIPTION
        "Event ACAT.12
        RIP added offset changed / updated at sending/receiving in a group."
    ::= { acatEventsGroup 12 }

acat12_grp_index OBJECT-TYPE
    SYNTAX Integer32
    MAX-ACCESS accessible-for-notify
    STATUS current
    DESCRIPTION
        "Parameter 'grp_index' in event ACAT.12"
    ::= { acatEventObjects12 1 }

acat12_direction OBJECT-TYPE
    SYNTAX DisplayString
    MAX-ACCESS accessible-for-notify
    STATUS current
    DESCRIPTION
        "Parameter 'direction' in event ACAT.12"
    ::= { acatEventObjects12 2 }

acat12_offset OBJECT-TYPE
    SYNTAX Integer32
    MAX-ACCESS accessible-for-notify
    STATUS current
    DESCRIPTION
        "Parameter 'offset' in event ACAT.12"
    ::= { acatEventObjects12 3 }

acatEventObjects13 OBJECT-IDENTITY
    STATUS current
    DESCRIPTION
        "Event ACAT.13
        Default route via gateway has been installed/uninstalled."
    ::= { acatEventsGroup 13 }

acat13_grp_index OBJECT-TYPE
    SYNTAX Integer32
    MAX-ACCESS accessible-for-notify
    STATUS current
    DESCRIPTION
        "Parameter 'grp_index' in event ACAT.13"
    ::= { acatEventObjects13 1 }

acat13_opt_index OBJECT-TYPE
    SYNTAX Integer32
    MAX-ACCESS accessible-for-notify
    STATUS current
    DESCRIPTION
        "Parameter 'opt_index' in event ACAT.13"
    ::= { acatEventObjects13 2 }

acat13_gateway OBJECT-TYPE
    SYNTAX DisplayString
    MAX-ACCESS accessible-for-notify
    STATUS current
    DESCRIPTION
        "Parameter 'gateway' in event ACAT.13"
    ::= { acatEventObjects13 3 }

acat13_installation OBJECT-TYPE
    SYNTAX DisplayString
    MAX-ACCESS accessible-for-notify
    STATUS current
    DESCRIPTION
        "Parameter 'installation' in event ACAT.13"
    ::= { acatEventObjects13 4 }

acatEventObjects14 OBJECT-IDENTITY
    STATUS current
    DESCRIPTION
        "Event ACAT.14
        Dependence of RIP at some IP/iface has been added/removed."
    ::= { acatEventsGroup 14 }

acat14_grp_index OBJECT-TYPE
    SYNTAX Integer32
    MAX-ACCESS accessible-for-notify
    STATUS current
    DESCRIPTION
        "Parameter 'grp_index' in event ACAT.14"
    ::= { acatEventObjects14 1 }

acat14_opt_index OBJECT-TYPE
    SYNTAX Integer32
    MAX-ACCESS accessible-for-notify
    STATUS current
    DESCRIPTION
        "Parameter 'opt_index' in event ACAT.14"
    ::= { acatEventObjects14 2 }

acat14_inia OBJECT-TYPE
    SYNTAX DisplayString
    MAX-ACCESS accessible-for-notify
    STATUS current
    DESCRIPTION
        "Parameter 'inia' in event ACAT.14"
    ::= { acatEventObjects14 3 }

acat14_link OBJECT-TYPE
    SYNTAX DisplayString
    MAX-ACCESS accessible-for-notify
    STATUS current
    DESCRIPTION
        "Parameter 'link' in event ACAT.14"
    ::= { acatEventObjects14 4 }

acatEventObjects15 OBJECT-IDENTITY
    STATUS current
    DESCRIPTION
        "Event ACAT.15
        RIP has been reconfigured from ACAT changing its operation."
    ::= { acatEventsGroup 15 }

acat15_grp_index OBJECT-TYPE
    SYNTAX Integer32
    MAX-ACCESS accessible-for-notify
    STATUS current
    DESCRIPTION
        "Parameter 'grp_index' in event ACAT.15"
    ::= { acatEventObjects15 1 }

acat15_opt_index OBJECT-TYPE
    SYNTAX Integer32
    MAX-ACCESS accessible-for-notify
    STATUS current
    DESCRIPTION
        "Parameter 'opt_index' in event ACAT.15"
    ::= { acatEventObjects15 2 }

acat15_inia OBJECT-TYPE
    SYNTAX DisplayString
    MAX-ACCESS accessible-for-notify
    STATUS current
    DESCRIPTION
        "Parameter 'inia' in event ACAT.15"
    ::= { acatEventObjects15 3 }

acat15_rcv_allow OBJECT-TYPE
    SYNTAX DisplayString
    MAX-ACCESS accessible-for-notify
    STATUS current
    DESCRIPTION
        "Parameter 'rcv_allow' in event ACAT.15"
    ::= { acatEventObjects15 4 }

acat15_rcv_offset OBJECT-TYPE
    SYNTAX Integer32
    MAX-ACCESS accessible-for-notify
    STATUS current
    DESCRIPTION
        "Parameter 'rcv_offset' in event ACAT.15"
    ::= { acatEventObjects15 5 }

acat15_snd_allow OBJECT-TYPE
    SYNTAX DisplayString
    MAX-ACCESS accessible-for-notify
    STATUS current
    DESCRIPTION
        "Parameter 'snd_allow' in event ACAT.15"
    ::= { acatEventObjects15 6 }

acat15_snd_offset OBJECT-TYPE
    SYNTAX Integer32
    MAX-ACCESS accessible-for-notify
    STATUS current
    DESCRIPTION
        "Parameter 'snd_offset' in event ACAT.15"
    ::= { acatEventObjects15 7 }

acatEventObjects16 OBJECT-IDENTITY
    STATUS current
    DESCRIPTION
        "Event ACAT.16
        Cellular related LEDs have been associated to / disassociated from a cellular interface."
    ::= { acatEventsGroup 16 }

acat16_grp_index OBJECT-TYPE
    SYNTAX Integer32
    MAX-ACCESS accessible-for-notify
    STATUS current
    DESCRIPTION
        "Parameter 'grp_index' in event ACAT.16"
    ::= { acatEventObjects16 1 }

acat16_opt_index OBJECT-TYPE
    SYNTAX Integer32
    MAX-ACCESS accessible-for-notify
    STATUS current
    DESCRIPTION
        "Parameter 'opt_index' in event ACAT.16"
    ::= { acatEventObjects16 2 }

acat16_association OBJECT-TYPE
    SYNTAX DisplayString
    MAX-ACCESS accessible-for-notify
    STATUS current
    DESCRIPTION
        "Parameter 'association' in event ACAT.16"
    ::= { acatEventObjects16 3 }

acat16_cell_if OBJECT-TYPE
    SYNTAX DisplayString
    MAX-ACCESS accessible-for-notify
    STATUS current
    DESCRIPTION
        "Parameter 'cell_if' in event ACAT.16"
    ::= { acatEventObjects16 4 }


acatNotification1 NOTIFICATION-TYPE
    OBJECTS { 
              acat1_grp_index, 
              acat1_enable 
            }
    STATUS current
    DESCRIPTION
        "Notification of Event ACAT.1

        Message: 'Group $1 is $2'

        Parameters list:
              $1: acat1_grp_index
              $2: acat1_enable

        Group enabled in configuration / has been disabled."
    ::= { acatNotificationsPrefix 1 }

acatNotification2 NOTIFICATION-TYPE
    OBJECTS { 
              acat2_module 
            }
    STATUS current
    DESCRIPTION
        "Notification of Event ACAT.2

        Message: 'Not enough memory at $1'

        Parameters list:
              $1: acat2_module

        Not enough memory available for reservation."
    ::= { acatNotificationsPrefix 2 }

acatNotification3 NOTIFICATION-TYPE
    OBJECTS { 
              acat3_grp_index, 
              acat3_opt_index,
              acat3_register,
              acat3_iface 
            }
    STATUS current
    DESCRIPTION
        "Notification of Event ACAT.3

        Message: 'Group $1,  option $2. $3 at interface $4 tracking'

        Parameters list:
              $1: acat3_grp_index
              $2: acat3_opt_index
              $3: acat3_register
              $4: acat3_iface

        An option from a group has been registered/unregistered at an interface to track its state."
    ::= { acatNotificationsPrefix 3 }

acatNotification4 NOTIFICATION-TYPE
    OBJECTS { 
              acat4_grp_index, 
              acat4_opt_index,
              acat4_state 
            }
    STATUS current
    DESCRIPTION
        "Notification of Event ACAT.4

        Message: 'Group $1,  option $2. Its state has been set to $3'

        Parameters list:
              $1: acat4_grp_index
              $2: acat4_opt_index
              $3: acat4_state

        An option from a group has changed its state."
    ::= { acatNotificationsPrefix 4 }

acatNotification5 NOTIFICATION-TYPE
    OBJECTS { 
              acat5_grp_index 
            }
    STATUS current
    DESCRIPTION
        "Notification of Event ACAT.5

        Message: 'Group $1. Time to check if a new option should be chosen'

        Parameters list:
              $1: acat5_grp_index

        Consider if a new option should be chosen."
    ::= { acatNotificationsPrefix 5 }

acatNotification6 NOTIFICATION-TYPE
    OBJECTS { 
              acat6_grp_index, 
              acat6_active_pri 
            }
    STATUS current
    DESCRIPTION
        "Notification of Event ACAT.6

        Message: 'Group $1. Active priority set to $2'

        Parameters list:
              $1: acat6_grp_index
              $2: acat6_active_pri

        Active priority in a group has been changed."
    ::= { acatNotificationsPrefix 6 }

acatNotification7 NOTIFICATION-TYPE
    OBJECTS { 
              acat7_grp_index 
            }
    STATUS current
    DESCRIPTION
        "Notification of Event ACAT.7

        Message: 'Group $1. Can not choose any option'

        Parameters list:
              $1: acat7_grp_index

        No option was chosen."
    ::= { acatNotificationsPrefix 7 }

acatNotification8 NOTIFICATION-TYPE
    OBJECTS { 
              acat8_grp_index, 
              acat8_opt_index,
              acat8_activation 
            }
    STATUS current
    DESCRIPTION
        "Notification of Event ACAT.8

        Message: 'Group $1,  option $2. $3'

        Parameters list:
              $1: acat8_grp_index
              $2: acat8_opt_index
              $3: acat8_activation

        An option from a group has been activated / deactivated."
    ::= { acatNotificationsPrefix 8 }

acatNotification9 NOTIFICATION-TYPE
    OBJECTS { 
              acat9_grp_index, 
              acat9_type,
              acat9_seconds 
            }
    STATUS current
    DESCRIPTION
        "Notification of Event ACAT.9

        Message: 'Group $1. Timer of type $2 set to $3 seconds'

        Parameters list:
              $1: acat9_grp_index
              $2: acat9_type
              $3: acat9_seconds

        A group timer has been programmed."
    ::= { acatNotificationsPrefix 9 }

acatNotification10 NOTIFICATION-TYPE
    OBJECTS { 
              acat10_grp_index, 
              acat10_type 
            }
    STATUS current
    DESCRIPTION
        "Notification of Event ACAT.10

        Message: 'Group $1. Timer of type $2 stopped'

        Parameters list:
              $1: acat10_grp_index
              $2: acat10_type

        A group timer has been stopped."
    ::= { acatNotificationsPrefix 10 }

acatNotification11 NOTIFICATION-TYPE
    OBJECTS { 
              acat11_grp_index, 
              acat11_type 
            }
    STATUS current
    DESCRIPTION
        "Notification of Event ACAT.11

        Message: 'Group $1. Timer of type $2 has expired'

        Parameters list:
              $1: acat11_grp_index
              $2: acat11_type

        A group timer has expired."
    ::= { acatNotificationsPrefix 11 }

acatNotification12 NOTIFICATION-TYPE
    OBJECTS { 
              acat12_grp_index, 
              acat12_direction,
              acat12_offset 
            }
    STATUS current
    DESCRIPTION
        "Notification of Event ACAT.12

        Message: 'Group $1. RIP $2 added offset set to $3'

        Parameters list:
              $1: acat12_grp_index
              $2: acat12_direction
              $3: acat12_offset

        RIP added offset changed / updated at sending/receiving in a group."
    ::= { acatNotificationsPrefix 12 }

acatNotification13 NOTIFICATION-TYPE
    OBJECTS { 
              acat13_grp_index, 
              acat13_opt_index,
              acat13_gateway,
              acat13_installation 
            }
    STATUS current
    DESCRIPTION
        "Notification of Event ACAT.13

        Message: 'Group $1, option $2. Default route via gateway at $3 has been $4'

        Parameters list:
              $1: acat13_grp_index
              $2: acat13_opt_index
              $3: acat13_gateway
              $4: acat13_installation

        Default route via gateway has been installed/uninstalled."
    ::= { acatNotificationsPrefix 13 }

acatNotification14 NOTIFICATION-TYPE
    OBJECTS { 
              acat14_grp_index, 
              acat14_opt_index,
              acat14_inia,
              acat14_link 
            }
    STATUS current
    DESCRIPTION
        "Notification of Event ACAT.14

        Message: 'Group $1, option $2. RIP at $3 is $4'

        Parameters list:
              $1: acat14_grp_index
              $2: acat14_opt_index
              $3: acat14_inia
              $4: acat14_link

        Dependence of RIP at some IP/iface has been added/removed."
    ::= { acatNotificationsPrefix 14 }

acatNotification15 NOTIFICATION-TYPE
    OBJECTS { 
              acat15_grp_index, 
              acat15_opt_index,
              acat15_inia,
              acat15_rcv_allow,
              acat15_rcv_offset,
              acat15_snd_allow,
              acat15_snd_offset 
            }
    STATUS current
    DESCRIPTION
        "Notification of Event ACAT.15

        Message: 'Group $1, option $2. RIP at $3 has been reconfigured: receiving $4 (added offset $5), sending $6 (added offset $7)'

        Parameters list:
              $1: acat15_grp_index
              $2: acat15_opt_index
              $3: acat15_inia
              $4: acat15_rcv_allow
              $5: acat15_rcv_offset
              $6: acat15_snd_allow
              $7: acat15_snd_offset

        RIP has been reconfigured from ACAT changing its operation."
    ::= { acatNotificationsPrefix 15 }

acatNotification16 NOTIFICATION-TYPE
    OBJECTS { 
              acat16_grp_index, 
              acat16_opt_index,
              acat16_association,
              acat16_cell_if 
            }
    STATUS current
    DESCRIPTION
        "Notification of Event ACAT.16

        Message: 'Group $1, option $2. Cellular related LEDs have been $3 interface $4'

        Parameters list:
              $1: acat16_grp_index
              $2: acat16_opt_index
              $3: acat16_association
              $4: acat16_cell_if

        Cellular related LEDs have been associated to / disassociated from a cellular interface."
    ::= { acatNotificationsPrefix 16 }


END
