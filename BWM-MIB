BWM-MIB DEFINITIONS ::= BEGIN

-- Title:      RADWARE
--             This Private MIB supports the WSD/CSD/FP/LP
-- Version:    2.9
-- Date:       2/4/2001
-- By:         RMA (Radware MIB Authority)
-- E-mail:     US:            support@radware.com
--             International: support_int@radware.com
--
IMPORTS
       NetworkAddress,
       IpAddress,
       Counter,
       Gauge,
       enterprises
              FROM RFC1155-SMI
       Ipv6Address 
		FROM IPV6-TC
       Integer32
              FROM SNMPv2-SMI
       OBJECT-TYPE
              FROM RFC-1212
       DisplayString,
       ipAddrEntry
              FROM RFC1213-MIB
       TRAP-TYPE
              FROM RFC1215
       rsBWM,
       rndErrorDesc,
       rndErrorSeverity,
       TruthValue,
       RowStatus,
       FeatureStatus
              FROM RADWARE-MIB
       MacAddress
              FROM SNMPv2-TC
	   DpsSessionType
			  FROM GENERIC-MIB;

    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsBWMRulesTable OBJECT-TYPE
    SYNTAX SEQUENCE OF RsBWMRulesEntry
    ACCESS not-accessible
    STATUS  mandatory
    DESCRIPTION
      "Table containing the list of rules for classifer data base,
       these rules can be used to classify packets for bandwidth management,
       facs etc..."
    ::=  {rsBWM 1}

rsBWMRulesEntry OBJECT-TYPE
    SYNTAX RsBWMRulesEntry
    ACCESS not-accessible
    STATUS  mandatory
    DESCRIPTION
       "The row definition for this table."
    INDEX { rsBWMRulesName }
    ::=  { rsBWMRulesTable 1 }

RsBWMRulesEntry ::= SEQUENCE {
    rsBWMRulesIndex INTEGER,
    rsBWMRulesName DisplayString,
    rsBWMRulesDestination DisplayString,
    rsBWMRulesSource DisplayString,
    rsBWMRulesStatus  RowStatus,
    rsBWMRulesAction INTEGER,
    rsBWMRulesDirection INTEGER,
    rsBWMRulesPriority INTEGER,
    rsBWMRulesPhysicalPort INTEGER,
    rsBWMRulesType INTEGER,
    rsBWMRulesDescription DisplayString,
    rsBWMRulesGuaranteedBW Integer32,
    rsBWMRulesPolicyType INTEGER,
    rsBWMRulesPolicy DisplayString,
    rsBWMRulesOperationalStatus INTEGER,
    rsBWMRulesDSCPMarking INTEGER,
    rsBWMRulesReportBlockedPackets INTEGER,
    rsBWMRulesMaxBW Integer32,
    rsBWMRulesSpecific DisplayString,
    rsBWMRulesPhysicalPortGroup DisplayString,
    rsBWMRulesVLANTagGroup DisplayString,
    rsBWMRulesTrafficIdentification INTEGER,
    rsBWMRulesTrafficFlowMaxBW INTEGER,
    rsBWMRulesMaxConcurrentSessions INTEGER,
    rsBWMRulesTrafficIDCookieField DisplayString,
    rsBWMRulesPolicyGroup DisplayString,
    rsBWMRulesRadiusRule DisplayString
}

rsBWMRulesIndex OBJECT-TYPE
    SYNTAX INTEGER
    ACCESS  read-write
    STATUS  mandatory
    DESCRIPTION
       "This variable indicates the administrative index of a line it
       determines the order of the rules."
    ::=  { rsBWMRulesEntry 1 }

rsBWMRulesName OBJECT-TYPE
    SYNTAX DisplayString (SIZE(0..255))
    ACCESS  read-only
    STATUS  mandatory
    DESCRIPTION
      "The Name for the Rule must be unique."
    ::=  {rsBWMRulesEntry 2}

rsBWMRulesDestination OBJECT-TYPE
    SYNTAX DisplayString (SIZE(0..46))
    ACCESS  read-write
    STATUS  mandatory
    DESCRIPTION
      "The destination address / range of address for the packet, the name is
      defined in the Objects table or can be an IP address."
    DEFVAL { "any" }
    ::=  {rsBWMRulesEntry 3}

rsBWMRulesSource OBJECT-TYPE
    SYNTAX DisplayString (SIZE(0..46))
    ACCESS  read-write
    STATUS  mandatory
    DESCRIPTION
      "The source address / range of address for the packet, the name is
      defined in the Objects table or can be an IP address."
    DEFVAL { "any" }
    ::=  {rsBWMRulesEntry 4}

rsBWMRulesStatus OBJECT-TYPE
    SYNTAX RowStatus
    ACCESS  read-write
    STATUS  mandatory
    DESCRIPTION
       "This variable indicates the administrative status of this entry.
        Used to delete an entry of this table."
    ::=  { rsBWMRulesEntry 5 }

rsBWMRulesAction OBJECT-TYPE
    SYNTAX INTEGER {
          none(0),
          forward(1),
          block(2),
          blockAndReset(3),
          blockAndBiDirectionalReset(4),
          monitorHTTP(5),
          monitorHTTPS(6),
          monitorTCP(7) }
    ACCESS  read-write
    STATUS  mandatory
    DESCRIPTION
       "This variable indicates the action that the classifier / service
       must take on this entry."
    DEFVAL { 1 }
    ::=  { rsBWMRulesEntry 6 }

rsBWMRulesDirection OBJECT-TYPE
    SYNTAX INTEGER {
            	oneway(1),
		twoway(2),
		session(3)
    }
    ACCESS  read-write
    STATUS  mandatory
    DESCRIPTION
       "This variable indicates the direction of the incoming packet."
    DEFVAL { 2 }
    ::=  { rsBWMRulesEntry 7 }

rsBWMRulesPriority OBJECT-TYPE
    SYNTAX INTEGER
    ACCESS  read-write
    STATUS  mandatory
    DESCRIPTION
       "This variable indicates the priority for this entry."
    DEFVAL { 65535 }
    ::=  { rsBWMRulesEntry 8 }

rsBWMRulesPhysicalPort OBJECT-TYPE
    SYNTAX INTEGER
    ACCESS  read-write
    STATUS  mandatory
    DESCRIPTION
       "This variable indicates the port from which the packet arrived. (obsolete field)"
    DEFVAL  { 0 }
    ::=  { rsBWMRulesEntry 9 }

rsBWMRulesType OBJECT-TYPE
    SYNTAX INTEGER {
              facsBandwidth(1),
              counter(2),
              ids(3),
              chain(4) }
    ACCESS  read-write
    STATUS  mandatory
    DESCRIPTION
       "This variable indicates the type of rules (services) ."
    DEFVAL { 1 }
    ::=  { rsBWMRulesEntry 10 }

rsBWMRulesDescription OBJECT-TYPE
    SYNTAX DisplayString (SIZE(0..19))
    ACCESS  read-write
    STATUS  mandatory
    DESCRIPTION
      "Description."
    ::=  { rsBWMRulesEntry 11 }

rsBWMRulesGuaranteedBW OBJECT-TYPE
    SYNTAX Integer32
    ACCESS  read-write
    STATUS  mandatory
    DESCRIPTION
       "Bandwidth allocated for a certain rule."
    DEFVAL  { 0 }
    ::=  { rsBWMRulesEntry 12 }

rsBWMRulesPolicyType OBJECT-TYPE
    SYNTAX INTEGER {
              none(1),
              filter(2),
              group(3),
              policy(4)}
    ACCESS  read-write
    STATUS  mandatory
    DESCRIPTION
       "The type of policy - i.e. if this is a filter, group or policy."
    DEFVAL { 1 }
    ::=  { rsBWMRulesEntry 13 }

rsBWMRulesPolicy OBJECT-TYPE
    SYNTAX DisplayString (SIZE(0..29))
    ACCESS  read-write
    STATUS  mandatory
    DESCRIPTION
       "The name for the filter policy for the rule."
    ::=  { rsBWMRulesEntry 14 }

rsBWMRulesOperationalStatus OBJECT-TYPE
    SYNTAX INTEGER {
        active (1),
        inactive (2)
    }
    ACCESS  read-write
    STATUS  mandatory
    DESCRIPTION
       "This variable indicates if the rule is active or inactive.
        The active rule table contains only active rules."
    DEFVAL { 1 }
    ::= { rsBWMRulesEntry 15 }

rsBWMRulesDSCPMarking OBJECT-TYPE
    SYNTAX INTEGER (-1 | 0..63)
    ACCESS  read-write
    STATUS  mandatory
    DESCRIPTION
       "OLD parameter. no longer in use (moved to extensions). "
    DEFVAL { -1 }
    ::= { rsBWMRulesEntry 16 }

rsBWMRulesReportBlockedPackets OBJECT-TYPE
    SYNTAX INTEGER {
        disable (0),
        enable (1),
        securityEvent (2)
    }
    ACCESS  read-write
    STATUS  mandatory
    DESCRIPTION
       "This variable indicates if blocked packets are be reported."
    ::= { rsBWMRulesEntry 17 }

rsBWMRulesMaxBW OBJECT-TYPE
    SYNTAX Integer32
    ACCESS  read-write
    STATUS  mandatory
    DESCRIPTION
       "Maximum bandwidth allocated for a certain rule.The range is 0 - 8000000.Default value (2147483647) is translated to Unlimited"
    DEFVAL  { 2147483647 }
    ::=  { rsBWMRulesEntry 18 }

rsBWMRulesSpecific OBJECT-TYPE
    SYNTAX DisplayString (SIZE(0..19))
    ACCESS  read-write
    STATUS  mandatory
    DESCRIPTION
       "This variable indicates if there is additional data to the
       policy."
    ::= { rsBWMRulesEntry 19 }

rsBWMRulesPhysicalPortGroup OBJECT-TYPE
    SYNTAX DisplayString (SIZE(0..19))
    ACCESS  read-write
    STATUS  mandatory
    DESCRIPTION
       "The name of the physical port group for this rule."
    ::=  { rsBWMRulesEntry 20 }

rsBWMRulesVLANTagGroup OBJECT-TYPE
    SYNTAX DisplayString (SIZE(0..19))
    ACCESS  read-write
    STATUS  mandatory
    DESCRIPTION
        "The name of the VLAN tag group for this rule."
    ::= { rsBWMRulesEntry 21 }

rsBWMRulesTrafficIdentification OBJECT-TYPE
    SYNTAX INTEGER {
        none (0),
        client (1),
        session (2),
        connection (3),
        fullL4Session (4),
        sessionCookie (5)
    }
    ACCESS  read-write
    STATUS  mandatory
    DESCRIPTION
        "Not In Use."
    ::= { rsBWMRulesEntry 22 }

rsBWMRulesTrafficFlowMaxBW OBJECT-TYPE
    SYNTAX INTEGER
    ACCESS  read-write
    STATUS  mandatory
    DESCRIPTION
        "Not In Use"
    ::= { rsBWMRulesEntry 23 }

rsBWMRulesMaxConcurrentSessions OBJECT-TYPE
    SYNTAX INTEGER
    ACCESS  read-write
    STATUS  mandatory
    DESCRIPTION
        "Not In Use"
    ::= { rsBWMRulesEntry 24 }

rsBWMRulesTrafficIDCookieField OBJECT-TYPE
    SYNTAX DisplayString (SIZE(0..19))
    ACCESS  read-write
    STATUS  mandatory
    DESCRIPTION
        "Not In Use"
    ::= { rsBWMRulesEntry 25 }

rsBWMRulesPolicyGroup OBJECT-TYPE
    SYNTAX DisplayString (SIZE(0..19))
    ACCESS  read-write
    STATUS  mandatory
    DESCRIPTION
        "Group the policies for bandwidth sharing."
    ::= { rsBWMRulesEntry 26 }

rsBWMRulesRadiusRule OBJECT-TYPE
    SYNTAX DisplayString (SIZE(0..30))
    ACCESS  read-write
    STATUS  mandatory
    DESCRIPTION
      "The name of the radius relevant this session belongs to. This field is relevant only for cid. Radius' rules
	   names can be found in the Radius Rules Table"
    DEFVAL { "any" }
    ::=  {rsBWMRulesEntry 27}

rsBWMRulesIPObjectTable OBJECT-TYPE
    SYNTAX SEQUENCE OF RsBWMRulesIPObjectEntry
    ACCESS not-accessible
    STATUS  mandatory
    DESCRIPTION
      "Table containing the grouping for ranges."
    ::=  {rsBWM 2}

rsBWMRulesIPObjectEntry OBJECT-TYPE
    SYNTAX RsBWMRulesIPObjectEntry
    ACCESS not-accessible
    STATUS  mandatory
    DESCRIPTION
       "The row definition for this table."
    INDEX {rsBWMRulesIPObjectName,rsBWMRulesIPObjectSubIndex}
    ::=  { rsBWMRulesIPObjectTable 1 }

RsBWMRulesIPObjectEntry ::= SEQUENCE {
    rsBWMRulesIPObjectName DisplayString,
    rsBWMRulesIPObjectSubIndex INTEGER,
    rsBWMRulesIPObjectAddress IpAddress,
    rsBWMRulesIPObjectMask IpAddress,
    rsBWMRulesIPObjectFromIP IpAddress,
    rsBWMRulesIPObjectToIP IpAddress,
    rsBWMRulesIPObjectMode INTEGER,
    rsBWMRulesIPObjectStatus RowStatus
}

rsBWMRulesIPObjectName OBJECT-TYPE
    SYNTAX DisplayString (SIZE(0..19))
    ACCESS  read-only
    STATUS  mandatory
    DESCRIPTION
      "The Name for the IP Object Rule, must be unique."
    ::=  { rsBWMRulesIPObjectEntry 1 }

rsBWMRulesIPObjectSubIndex OBJECT-TYPE
    SYNTAX INTEGER
    ACCESS  read-only
    STATUS  mandatory
    DESCRIPTION
       "SubIndex."
    DEFVAL  { 0 }
    ::=  { rsBWMRulesIPObjectEntry 2 }

rsBWMRulesIPObjectAddress OBJECT-TYPE
    SYNTAX IpAddress
    ACCESS  read-write
    STATUS  mandatory
    DESCRIPTION
      "IP address"
    DEFVAL  { 0 }
    ::=  { rsBWMRulesIPObjectEntry 3 }

rsBWMRulesIPObjectMask OBJECT-TYPE
    SYNTAX IpAddress
    ACCESS  read-write
    STATUS  mandatory
    DESCRIPTION
      "IP address mask."
    DEFVAL  { 0 }
    ::=  { rsBWMRulesIPObjectEntry 4 }

rsBWMRulesIPObjectFromIP OBJECT-TYPE
    SYNTAX IpAddress
    ACCESS  read-write
    STATUS  mandatory
    DESCRIPTION
      "The from IP Address of the range."
    DEFVAL  { 0 }
    ::=  { rsBWMRulesIPObjectEntry 5 }

rsBWMRulesIPObjectToIP OBJECT-TYPE
    SYNTAX IpAddress
    ACCESS  read-write
    STATUS  mandatory
    DESCRIPTION
      "The to IP Address of the range."
    DEFVAL  { 0 }
    ::=  { rsBWMRulesIPObjectEntry 6 }

rsBWMRulesIPObjectMode OBJECT-TYPE
    SYNTAX INTEGER {
              ipMask(1),
              ipRange(2),
              dynamic(3)
    }
    ACCESS  read-write
    STATUS  mandatory
    DESCRIPTION
       "This variable indicates the mode of the entry. This is either
       a range or an IP address and mask."
--    DEFVAL  { 1 }
    ::=  { rsBWMRulesIPObjectEntry 7 }

rsBWMRulesIPObjectStatus OBJECT-TYPE
    SYNTAX RowStatus
    ACCESS  read-write
    STATUS  mandatory
    DESCRIPTION
       "This variable indicates the administrative status of this entry.
        Used to delete an entry of this table."
    ::=  { rsBWMRulesIPObjectEntry 8 }

rsBWMCBQMode  OBJECT-TYPE
    SYNTAX  INTEGER {
            cyclic(1),
            cbq(2)
    }
    ACCESS  read-write
    STATUS  mandatory
    DESCRIPTION
        "CBQ Mode."
    DEFVAL  { 1 }
    ::=  {rsBWM 3}

rsBWMActualQueueSize  OBJECT-TYPE
    SYNTAX  INTEGER
    ACCESS  read-only
    STATUS  mandatory
    DESCRIPTION
        "The current size of the queue."
    DEFVAL  { 0 }
    ::=  {rsBWM 4}

rsBWMAverageQueueSize  OBJECT-TYPE
    SYNTAX  INTEGER
    ACCESS  read-only
    STATUS  mandatory
    DESCRIPTION
        "The current average queue size."
    DEFVAL  { 0 }
    ::=  {rsBWM 5}

rsBWMQueueRedDropped  OBJECT-TYPE
    SYNTAX  INTEGER
    ACCESS  read-only
    STATUS  mandatory
    DESCRIPTION
        "The current red dropped packets."
    DEFVAL  { 0 }
    ::=  {rsBWM 6}

rsBWMPriorityTable OBJECT-TYPE
    SYNTAX SEQUENCE OF RsBWMPriorityEntry
    ACCESS not-accessible
    STATUS mandatory
    DESCRIPTION "The table for reading the packets sent via each priority"
    ::= {rsBWM 7}

rsBWMPriorityEntry OBJECT-TYPE
    SYNTAX RsBWMPriorityEntry
    ACCESS not-accessible
    STATUS mandatory
    DESCRIPTION "The row definition for the priority table"
    INDEX {rsBWMPriority}
    ::= {rsBWMPriorityTable 1}

RsBWMPriorityEntry ::= SEQUENCE {
    rsBWMPriority INTEGER,
    rsBWMPacketsSent INTEGER
}

rsBWMPriority OBJECT-TYPE
    SYNTAX INTEGER
    ACCESS read-only
    STATUS mandatory
    DESCRIPTION "The priority"
    ::= {rsBWMPriorityEntry 1}

rsBWMPacketsSent OBJECT-TYPE
    SYNTAX INTEGER
    ACCESS read-only
    STATUS mandatory
    DESCRIPTION "The number of packets sent via this priority"
    ::= {rsBWMPriorityEntry 2}

rsBWMRedMode OBJECT-TYPE
    SYNTAX INTEGER {
        none (1),
        global (2),
        weighted (3)
    }
    ACCESS  read-write
    STATUS  mandatory
    DESCRIPTION "The RED algorithm mode"
--  DEFVAL  { none }
    ::= {rsBWM 8}

rsBWMCurrentRulesTable OBJECT-TYPE
    SYNTAX SEQUENCE OF RsBWMCurrentRulesEntry
    ACCESS not-accessible
    STATUS  mandatory
    DESCRIPTION
      "Table containing the list of rules for classifer data base,
       these rules can be used to classify packets for bandwidth management,
       facs etc..."
    ::=  {rsBWM 9}

rsBWMCurrentRulesEntry OBJECT-TYPE
    SYNTAX RsBWMCurrentRulesEntry
    ACCESS not-accessible
    STATUS  mandatory
    DESCRIPTION
       "The row definition for this table."
    INDEX { rsBWMCurrentRulesName }
    ::=  { rsBWMCurrentRulesTable 1 }

RsBWMCurrentRulesEntry ::= SEQUENCE {
    rsBWMCurrentRulesIndex INTEGER,
    rsBWMCurrentRulesName DisplayString,
    rsBWMCurrentRulesDestination DisplayString,
    rsBWMCurrentRulesSource DisplayString,
    rsBWMCurrentRulesAction INTEGER,
    rsBWMCurrentRulesDirection INTEGER,
    rsBWMCurrentRulesPriority INTEGER,
    rsBWMCurrentRulesPhysicalPort INTEGER,
    rsBWMCurrentRulesType INTEGER,
    rsBWMCurrentRulesDescription DisplayString,
    rsBWMCurrentRulesGuaranteedBW Counter,
    rsBWMCurrentRulesMaxBW Counter,
    rsBWMCurrentRulesPolicyType INTEGER,
    rsBWMCurrentRulesPolicy DisplayString,
    rsBWMCurrentRulesDSCPMarking INTEGER,
    rsBWMCurrentRulesReportBlockedPackets INTEGER,
    rsBWMCurrentRulesSpecific DisplayString,
    rsBWMCurrentRulesPhysicalPortGroup DisplayString,
    rsBWMCurrentRulesVLANTagGroup DisplayString,
    rsBWMCurrentRulesTrafficIdentification INTEGER,
    rsBWMCurrentRulesTrafficFlowMaxBW INTEGER,
    rsBWMCurrentRulesMaxConcurrentSessions INTEGER,
    rsBWMCurrentRulesTrafficIDCookieField DisplayString,
    rsBWMCurrentRulesPolicyGroup DisplayString,
    rsBWMCurrentRulesRadiusRule DisplayString
}

rsBWMCurrentRulesIndex OBJECT-TYPE
    SYNTAX INTEGER
    ACCESS  read-only
    STATUS  mandatory
    DESCRIPTION
       "This variable indicates the administrative index of a line it
       determine the order of the rules."
    ::=  { rsBWMCurrentRulesEntry 1 }

rsBWMCurrentRulesName OBJECT-TYPE
    SYNTAX DisplayString (SIZE(0..255))
    ACCESS  read-only
    STATUS  mandatory
    DESCRIPTION
      "The Name for the Rule must be unique."
    ::=  {rsBWMCurrentRulesEntry 2}

rsBWMCurrentRulesDestination OBJECT-TYPE
    SYNTAX DisplayString (SIZE(0..46))
    ACCESS  read-only
    STATUS  mandatory
    DESCRIPTION
      "The destination address / range of address for the packet, the name is
      defined in the Objects table or can be an IP address."
    ::=  {rsBWMCurrentRulesEntry 3}

rsBWMCurrentRulesSource OBJECT-TYPE
    SYNTAX DisplayString (SIZE(0..46))
    ACCESS  read-only
    STATUS  mandatory
    DESCRIPTION
      "The source address / range of address for the packet, the name is
      defined in the Objects table or can be an IP address."
    ::=  {rsBWMCurrentRulesEntry 4}

rsBWMCurrentRulesAction OBJECT-TYPE
    SYNTAX INTEGER {
              none(0),
              forward(1),
              block(2),
              blockAndReset(3),
              blockAndBiDirectionalReset(4),
              monitorHTTP(5),
              monitorHTTPS(6),
              monitorTCP(7) }
    ACCESS  read-only
    STATUS  mandatory
    DESCRIPTION
       "This variable indicates the action that the classifier / service must
       take on this entry."
    ::=  { rsBWMCurrentRulesEntry 5 }

rsBWMCurrentRulesDirection OBJECT-TYPE
    SYNTAX INTEGER {
              oneway(1),
              twoway(2),
              session(3)
    }
    ACCESS read-only
    STATUS mandatory
    DESCRIPTION
       "This variable indicates the direction of the incoming packet."
    ::=  { rsBWMCurrentRulesEntry 6 }

rsBWMCurrentRulesPriority OBJECT-TYPE
    SYNTAX INTEGER
    ACCESS  read-only
    STATUS  mandatory
    DESCRIPTION
       "This variable indicates the priority for this entry."
    ::=  { rsBWMCurrentRulesEntry 7 }

rsBWMCurrentRulesPhysicalPort OBJECT-TYPE
    SYNTAX INTEGER
    ACCESS  read-only
    STATUS  mandatory
    DESCRIPTION
       "This variable indicates the port from which the packet arrived."
    ::=  { rsBWMCurrentRulesEntry 8 }

rsBWMCurrentRulesType OBJECT-TYPE
    SYNTAX INTEGER {
              facsBandwidth(1),
              counter(2),
              ids(3),
              chain(4) }
    ACCESS  read-only
    STATUS  mandatory
    DESCRIPTION
       "This variable indicates the type of rules (services) ."
    ::=  { rsBWMCurrentRulesEntry 9 }

rsBWMCurrentRulesDescription OBJECT-TYPE
    SYNTAX DisplayString (SIZE(0..19))
    ACCESS  read-only
    STATUS  mandatory
    DESCRIPTION
      "Description."
    ::=  { rsBWMCurrentRulesEntry 10 }

rsBWMCurrentRulesGuaranteedBW OBJECT-TYPE
    SYNTAX Counter
    ACCESS  read-only
    STATUS  mandatory
    DESCRIPTION
       "Bandwidth allocated for a certain rule."
    ::=  { rsBWMCurrentRulesEntry 11 }

rsBWMCurrentRulesMaxBW OBJECT-TYPE
    SYNTAX Counter
    ACCESS  read-only
    STATUS  mandatory
    DESCRIPTION
       "Maximum bandwidth allocated for a certain rule."
    ::=  { rsBWMCurrentRulesEntry 12 }

rsBWMCurrentRulesPolicyType OBJECT-TYPE
    SYNTAX INTEGER {
              none(1),
              filter(2),
              group(3),
              policy(4)}
    ACCESS  read-only
    STATUS  mandatory
    DESCRIPTION
       "The type of policy - i.e. if this is a filter, group or policy."
    DEFVAL  { 1 }
    ::=  { rsBWMCurrentRulesEntry 13 }

rsBWMCurrentRulesPolicy OBJECT-TYPE
    SYNTAX DisplayString (SIZE(0..29))
    ACCESS  read-only
    STATUS  mandatory
    DESCRIPTION
       "The name for the filter policy for the rule."
    ::=  { rsBWMCurrentRulesEntry 14 }

rsBWMCurrentRulesDSCPMarking OBJECT-TYPE
    SYNTAX INTEGER (-1 | 0..63)
    ACCESS  read-only
    STATUS  mandatory
    DESCRIPTION
       "OLD parameter. no longer in use (moved to extensions). "
    ::= { rsBWMCurrentRulesEntry 15 }

rsBWMCurrentRulesReportBlockedPackets OBJECT-TYPE
    SYNTAX INTEGER {
        disable (0),
        enable (1),
        securityEvent (2)
    }
    ACCESS  read-only
    STATUS  mandatory
    DESCRIPTION
       "This variable indicates if blocked packets are be reported."
    ::= { rsBWMCurrentRulesEntry 16 }

rsBWMCurrentRulesSpecific OBJECT-TYPE
    SYNTAX DisplayString (SIZE(0..19))
    ACCESS  read-only
    STATUS  mandatory
    DESCRIPTION
       "This variable indicates if there is additional data to the
       policy."
    ::= { rsBWMCurrentRulesEntry 17 }

rsBWMCurrentRulesPhysicalPortGroup OBJECT-TYPE
    SYNTAX DisplayString (SIZE(0..19))
    ACCESS  read-only
    STATUS  mandatory
    DESCRIPTION
       "The name of the physical port group for this rule."
    ::=  { rsBWMCurrentRulesEntry 18 }

rsBWMCurrentRulesVLANTagGroup OBJECT-TYPE
    SYNTAX DisplayString (SIZE(0..19))
    ACCESS  read-only
    STATUS  mandatory
    DESCRIPTION
        "The name of the VLAN tag group for this rule."
    ::= { rsBWMCurrentRulesEntry 19 }

rsBWMCurrentRulesTrafficIdentification OBJECT-TYPE
    SYNTAX INTEGER {
        none (0),
        client (1),
        session (2),
        connection (3),
        fullL4Session (4),
        sessionCookie (5)
    }
    ACCESS  read-only
    STATUS  mandatory
    DESCRIPTION
        "Not In Use."
    ::= { rsBWMCurrentRulesEntry 20 }

rsBWMCurrentRulesTrafficFlowMaxBW OBJECT-TYPE
    SYNTAX INTEGER
    ACCESS  read-only
    STATUS  mandatory
    DESCRIPTION
        "Not In Use."
    ::= { rsBWMCurrentRulesEntry 21 }

rsBWMCurrentRulesMaxConcurrentSessions OBJECT-TYPE
    SYNTAX INTEGER
    ACCESS  read-only
    STATUS  mandatory
    DESCRIPTION
        "Not In Use."
    ::= { rsBWMCurrentRulesEntry 22 }

rsBWMCurrentRulesTrafficIDCookieField OBJECT-TYPE
    SYNTAX DisplayString (SIZE(0..19))
    ACCESS  read-only
    STATUS  mandatory
    DESCRIPTION
        "Not In Use."
    ::= { rsBWMCurrentRulesEntry 23 }

rsBWMCurrentRulesPolicyGroup OBJECT-TYPE
    SYNTAX DisplayString (SIZE(0..19))
    ACCESS  read-only
    STATUS  mandatory
    DESCRIPTION
        "Group the policies for bandwidth sharing."
    ::= { rsBWMCurrentRulesEntry 24 }

rsBWMCurrentRulesRadiusRule OBJECT-TYPE
    SYNTAX DisplayString (SIZE(0..30))
    ACCESS  read-write
    STATUS  mandatory
    DESCRIPTION
      "The name of the radius relevant this session belongs to. This field is relevant only for cid. Radius' rules
	   names can be found in the Radius Rules Table"
    DEFVAL { "any" }
    ::=  {rsBWMCurrentRulesEntry 25}

rsBWMCurrentRulesIPObjectTable OBJECT-TYPE
    SYNTAX SEQUENCE OF RsBWMCurrentRulesIPObjectEntry
    ACCESS not-accessible
    STATUS  mandatory
    DESCRIPTION
      "Table containing the grouping for ranges."
    ::=  {rsBWM 10}

rsBWMCurrentRulesIPObjectEntry OBJECT-TYPE
    SYNTAX RsBWMCurrentRulesIPObjectEntry
    ACCESS not-accessible
    STATUS  mandatory
    DESCRIPTION
       "The row definition for this table."
    INDEX {rsBWMCurrentRulesIPObjectName,rsBWMCurrentRulesIPObjectSubIndex}
    ::=  { rsBWMCurrentRulesIPObjectTable 1 }

RsBWMCurrentRulesIPObjectEntry ::= SEQUENCE {
    rsBWMCurrentRulesIPObjectName DisplayString,
    rsBWMCurrentRulesIPObjectSubIndex INTEGER,
    rsBWMCurrentRulesIPObjectAddress IpAddress,
    rsBWMCurrentRulesIPObjectMask IpAddress,
    rsBWMCurrentRulesIPObjectFromIP IpAddress,
    rsBWMCurrentRulesIPObjectToIP IpAddress,
    rsBWMCurrentRulesIPObjectMode INTEGER
}

rsBWMCurrentRulesIPObjectName OBJECT-TYPE
    SYNTAX DisplayString (SIZE(0..19))
    ACCESS  read-only
    STATUS  mandatory
    DESCRIPTION
      "The Name for the IP Object Rule, must be unique."
    ::=  { rsBWMCurrentRulesIPObjectEntry 1 }

rsBWMCurrentRulesIPObjectSubIndex OBJECT-TYPE
    SYNTAX INTEGER
    ACCESS  read-only
    STATUS  mandatory
    DESCRIPTION
       "SubIndex."
    ::=  { rsBWMCurrentRulesIPObjectEntry 2 }

rsBWMCurrentRulesIPObjectAddress OBJECT-TYPE
    SYNTAX IpAddress
    ACCESS  read-only
    STATUS  mandatory
    DESCRIPTION
      "IP address"
    ::=  { rsBWMCurrentRulesIPObjectEntry 3 }

rsBWMCurrentRulesIPObjectMask OBJECT-TYPE
    SYNTAX IpAddress
    ACCESS  read-only
    STATUS  mandatory
    DESCRIPTION
      "IP address mask."
    ::=  { rsBWMCurrentRulesIPObjectEntry 4 }

rsBWMCurrentRulesIPObjectFromIP OBJECT-TYPE
    SYNTAX IpAddress
    ACCESS  read-only
    STATUS  mandatory
    DESCRIPTION
      "The from IP Address of the range."
    ::=  { rsBWMCurrentRulesIPObjectEntry 5 }

rsBWMCurrentRulesIPObjectToIP OBJECT-TYPE
    SYNTAX IpAddress
    ACCESS  read-only
    STATUS  mandatory
    DESCRIPTION
      "The to IP Address of the range."
    ::=  { rsBWMCurrentRulesIPObjectEntry 6 }

rsBWMCurrentRulesIPObjectMode OBJECT-TYPE
    SYNTAX INTEGER {
              ipMask(1),
              ipRange(2),
              dynamic(3)
    }
    ACCESS  read-only
    STATUS  mandatory
    DESCRIPTION
       "This variable indicates the mode of the entry. This is either
       a range or an IP address and mask."
    ::=  { rsBWMCurrentRulesIPObjectEntry 7 }

rsBWMClassificationMode OBJECT-TYPE
    SYNTAX INTEGER {
        policies(1),
        disabled(2),
        diffserv(3),
        tos(4)
    }
    ACCESS  read-write
    STATUS  mandatory
    DESCRIPTION "The rule classifiction mode"
    DEFVAL { 2 }
    ::= { rsBWM 11 }

rsBWMMaximumBandwidth OBJECT-TYPE
    SYNTAX Counter
    ACCESS  read-only
    STATUS  mandatory
    DESCRIPTION "The maximum output bandwidth of the device. This is in Bytes"
    ::= { rsBWM 12 }

rsBWMBandwidthBorrowingMode OBJECT-TYPE
    SYNTAX INTEGER {
        enable(1),
        disable(2)
    }
    ACCESS  read-write
    STATUS  mandatory
    DESCRIPTION "Whether or not rules are able to borrow bandwidth from
    other rules"
    ::= { rsBWM 13 }

rsBWMActions OBJECT-TYPE
    SYNTAX INTEGER {
        updateRules(1),
        defaultDSCPs(2)
    }
    ACCESS  read-write
    STATUS  mandatory
    DESCRIPTION "Allows the application to perform specific actions"
    ::= { rsBWM 14 }

rsBWMFilterEntryTable OBJECT-TYPE
    SYNTAX SEQUENCE OF RsBWMFilterEntry
    ACCESS not-accessible
    STATUS  mandatory
    DESCRIPTION
      "Table containing the filters."
    ::= { rsBWM 15 }

rsBWMFilterEntry OBJECT-TYPE
    SYNTAX RsBWMFilterEntry
    ACCESS not-accessible
    STATUS mandatory
    DESCRIPTION
       "The row definition for this table."
    INDEX { rsBWMFilterName }
    ::=  { rsBWMFilterEntryTable 1 }

RsBWMFilterEntry ::= SEQUENCE {
    rsBWMFilterName DisplayString,
    rsBWMFilterDescription DisplayString,
    rsBWMFilterProtocol INTEGER,
    rsBWMFilterDestinationPort INTEGER,
    rsBWMFilterSourceFromPort INTEGER,
    rsBWMFilterSourceToPort INTEGER,
    rsBWMFilterOMPCOffset INTEGER,
    rsBWMFilterOMPCMask OCTET STRING,
    rsBWMFilterOMPCPattern OCTET STRING,
    rsBWMFilterOMPCCondition INTEGER,
    rsBWMFilterOMPCLength INTEGER,
    rsBWMFilterContentOffset INTEGER,
    rsBWMFilterContent DisplayString,
    rsBWMFilterContentType INTEGER,
    rsBWMFilterType INTEGER,
    rsBWMFilterStatus RowStatus,
    rsBWMFilterContentEnd INTEGER,
    rsBWMFilterContentData DisplayString,
    rsBWMFilterContentCoding INTEGER,
    rsBWMFilterContentDataCoding INTEGER,
    rsBWMFilterOMPCOffsetBase INTEGER,
    rsBWMFilterDestinationMaxPort INTEGER,
    rsBWMFilterSourceAppPortGroup DisplayString,
    rsBWMFilterDestinationAppPortGroup DisplayString,
	rsBWMFilterSessionType DpsSessionType,
	rsBWMFilterSessionTypeDirection INTEGER
}

rsBWMFilterName OBJECT-TYPE
    SYNTAX DisplayString (SIZE(0..29))
    ACCESS read-only
    STATUS mandatory
    DESCRIPTION
      "The name of the filter object."
    ::=  { rsBWMFilterEntry 1 }

rsBWMFilterDescription OBJECT-TYPE
    SYNTAX DisplayString (SIZE(0..29))
    ACCESS read-write
    STATUS  mandatory
    DESCRIPTION
       "The description of the filter."
    ::=  { rsBWMFilterEntry 2 }

rsBWMFilterProtocol OBJECT-TYPE
    SYNTAX INTEGER {
        ip (1),
        tcp (2),
        udp (3),
        icmp (4),
        nonIp (5),
		icmpv6 (6),
        sctp(7)
    }
    ACCESS read-write
    STATUS  mandatory
    DESCRIPTION
      "The protocol for the filter."
    DEFVAL  { 1 }
    ::=  { rsBWMFilterEntry 3 }

rsBWMFilterDestinationPort OBJECT-TYPE
    SYNTAX INTEGER
    ACCESS read-write
    STATUS  mandatory
    DESCRIPTION
      "Obsolete mib field"
    ::=  { rsBWMFilterEntry 4 }

rsBWMFilterSourceFromPort OBJECT-TYPE
    SYNTAX INTEGER
    ACCESS read-write
    STATUS  mandatory
    DESCRIPTION
      "Obsolete mib field"
    ::=  { rsBWMFilterEntry 5 }

rsBWMFilterSourceToPort OBJECT-TYPE
    SYNTAX INTEGER
    ACCESS read-write
    STATUS  mandatory
    DESCRIPTION
      "Obsolete mib field"
    ::=  { rsBWMFilterEntry 6 }

rsBWMFilterOMPCOffset OBJECT-TYPE
    SYNTAX INTEGER
    ACCESS read-write
    STATUS  mandatory
    DESCRIPTION
      "The offset of the OMPC data."
    ::=  { rsBWMFilterEntry 7 }

rsBWMFilterOMPCMask OBJECT-TYPE
    SYNTAX OCTET STRING (SIZE(4))
    ACCESS read-write
    STATUS  mandatory
    DESCRIPTION
      "The mask for the OMPC object."
    DEFVAL { "00000000" }
    ::=  { rsBWMFilterEntry 8 }

rsBWMFilterOMPCPattern OBJECT-TYPE
    SYNTAX OCTET STRING (SIZE(4))
    ACCESS read-write
    STATUS  mandatory
    DESCRIPTION
      "The pattern for the OMPC data."
    DEFVAL { "00000000" }
    ::=  { rsBWMFilterEntry 9 }

rsBWMFilterOMPCCondition OBJECT-TYPE
    SYNTAX INTEGER {
        notApplicable (1),
        equal (2),
        notEqual (3),
        greaterThan (4),
        lessThan (5)
    }
    ACCESS read-write
    STATUS  mandatory
    DESCRIPTION
      "The condition for the OMPC data check."	
    DEFVAL { 1 }
    ::=  { rsBWMFilterEntry 10 }

rsBWMFilterOMPCLength OBJECT-TYPE
    SYNTAX INTEGER {
        oneByte (1),
        twoBytes (2),
        threeBytes (3),
        fourBytes (4),
        notApplicable (5)
    }
    ACCESS read-write
    STATUS  mandatory
    DESCRIPTION
      "The length of the OMPC."
    DEFVAL { 5 }
    ::=  { rsBWMFilterEntry 11 }

rsBWMFilterContentOffset OBJECT-TYPE
    SYNTAX INTEGER
    ACCESS read-write
    STATUS  mandatory
    DESCRIPTION
      "The offset for the content."
    ::=  { rsBWMFilterEntry 12 }

rsBWMFilterContent OBJECT-TYPE
    SYNTAX DisplayString (SIZE(0..255))
    ACCESS read-write
    STATUS  mandatory
    DESCRIPTION
      "The content to be checked."
    ::=  { rsBWMFilterEntry 13 }

rsBWMFilterContentType OBJECT-TYPE
    SYNTAX INTEGER {
        notApplicable (1), 
        url (2),           
        text(3),           
        hostname(4),       
        headertype(5),     
        expression(6),     
        maildomain(7),     
        mailto(8),         
        mailfrom(9),       
        mailsubject(10),   
        filetype(11),      
        cookiedata(12),    
        idsurl(13),        
        pop3user(14),      
        urilength(15),     
        ftp(16),           
        ftpcontent(17),    
        rpc(18),           
        dceRPC(19),
        genericUrl(20), 
        genericHeader(21),
        genericCookie(22),
        sipcallfrom(23),
        sipcallto(24),
        sipcaller(25)
    }                   
    ACCESS read-write   
    STATUS  mandatory
    DESCRIPTION
      "The type of content. In the case of URL only the url is checked. (No
      offset is used). In the case of text then the entire packet is checked.
      (will make use of the offset)."
    DEFVAL { 1 }
    ::=  { rsBWMFilterEntry 14 }

rsBWMFilterType OBJECT-TYPE
    SYNTAX INTEGER {
        regular (1),
        static (2),
        ids (3),
        idsStatic (4)
    }
    ACCESS read-write
    STATUS  mandatory
    DESCRIPTION
      "The type of object. This can be regular (user defined) or static
      (defined by the application). ids and idsStatic are obsolete."
    DEFVAL { 1 }
    ::=  { rsBWMFilterEntry 15 }

rsBWMFilterStatus OBJECT-TYPE
    SYNTAX RowStatus
    ACCESS read-write
    STATUS mandatory
    DESCRIPTION
      "The status of the object."
    ::=  { rsBWMFilterEntry 16 }

rsBWMFilterContentEnd OBJECT-TYPE
    SYNTAX INTEGER
    ACCESS read-write
    STATUS  mandatory
    DESCRIPTION
      "End of search data."
    ::=  { rsBWMFilterEntry 17 }

rsBWMFilterContentData OBJECT-TYPE
    SYNTAX DisplayString (SIZE(0..255))
    ACCESS read-write
    STATUS  mandatory
    DESCRIPTION
      "Additional content data, used for header type entries."
    ::=  { rsBWMFilterEntry 18 }

rsBWMFilterContentCoding OBJECT-TYPE
    SYNTAX INTEGER {
        notApplicable (1),
        caseInsensitive (2),
        caseSensitive (3),
        hex (4),
        international(5)
    }
    ACCESS read-write
    STATUS  mandatory
    DESCRIPTION
      "The type of content coding that is used."
    DEFVAL { 1 }
    ::=  { rsBWMFilterEntry 19 }

rsBWMFilterContentDataCoding OBJECT-TYPE
    SYNTAX INTEGER {
        notApplicable (1),
        caseInsensitive (2),
        caseSensitive (3),
        hex (4),
        international(5)
    }
    ACCESS read-write
    STATUS  mandatory
    DESCRIPTION
      "The type of content data coding that is used."
    DEFVAL { 1 }
    ::=  { rsBWMFilterEntry 20 }

rsBWMFilterOMPCOffsetBase OBJECT-TYPE
    SYNTAX INTEGER {
        none (0),
        ipHeader (1),
        ipData (2),
        tcpData (3),
        asn1 (4),
        ethernet (5),
        l4Header (6),
	ipv6Header (7)
    }
    ACCESS read-write
    STATUS  mandatory
    DESCRIPTION
      "The base of filter OMPC offset."
    ::=  { rsBWMFilterEntry 21 }

rsBWMFilterDestinationMaxPort OBJECT-TYPE
    SYNTAX INTEGER
    ACCESS read-write
    STATUS  mandatory
    DESCRIPTION
      "Obsolete mib field."
    ::=  { rsBWMFilterEntry 22 }

rsBWMFilterSourceAppPortGroup OBJECT-TYPE
    SYNTAX DisplayString (SIZE(0..29))
    ACCESS read-write
    STATUS  mandatory
    DESCRIPTION
      "The source port group."
    ::=  { rsBWMFilterEntry 23 }

rsBWMFilterDestinationAppPortGroup OBJECT-TYPE
    SYNTAX DisplayString (SIZE(0..29))
    ACCESS read-write
    STATUS  mandatory
    DESCRIPTION
      "The destination port group."
    ::=  { rsBWMFilterEntry 24 }

rsBWMFilterSessionType  OBJECT-TYPE
    SYNTAX DpsSessionType
    ACCESS read-write
    STATUS mandatory
    DESCRIPTION
      "The type of session for classification of dynamic protocols sessions."
    DEFVAL { 0 }
    ::=  { rsBWMFilterEntry 25 }

rsBWMFilterSessionTypeDirection  OBJECT-TYPE
    SYNTAX INTEGER {
        all (0),
        rqst (1),
        rply (2)
    }
    ACCESS read-write
    STATUS mandatory
    DESCRIPTION
      "The direction of the specific session type: reply or request."
    DEFVAL { 0 }
    ::=  { rsBWMFilterEntry 26 }

rsBWMCurrentFilterEntryTable OBJECT-TYPE
    SYNTAX SEQUENCE OF RsBWMCurrentFilterEntry
    ACCESS not-accessible
    STATUS  mandatory
    DESCRIPTION
      "Table containing the filters."
    ::= { rsBWM 16 }

rsBWMCurrentFilterEntry OBJECT-TYPE
    SYNTAX RsBWMCurrentFilterEntry
    ACCESS not-accessible
    STATUS mandatory
    DESCRIPTION
       "The row definition for this table."
    INDEX { rsBWMCurrentFilterName }
    ::=  { rsBWMCurrentFilterEntryTable 1 }

RsBWMCurrentFilterEntry ::= SEQUENCE {
    rsBWMCurrentFilterName DisplayString,
    rsBWMCurrentFilterDescription DisplayString,
    rsBWMCurrentFilterProtocol INTEGER,
    rsBWMCurrentFilterDestinationPort INTEGER,
    rsBWMCurrentFilterSourceFromPort INTEGER,
    rsBWMCurrentFilterSourceToPort INTEGER,
    rsBWMCurrentFilterOMPCOffset INTEGER,
    rsBWMCurrentFilterOMPCMask OCTET STRING,
    rsBWMCurrentFilterOMPCPattern OCTET STRING,
    rsBWMCurrentFilterOMPCCondition INTEGER,
    rsBWMCurrentFilterOMPCLength INTEGER,
    rsBWMCurrentFilterContentOffset INTEGER,
    rsBWMCurrentFilterContent DisplayString,
    rsBWMCurrentFilterContentType INTEGER,
    rsBWMCurrentFilterType INTEGER,
    rsBWMCurrentFilterContentEnd INTEGER,
    rsBWMCurrentFilterContentData DisplayString,
    rsBWMCurrentFilterContentCoding INTEGER,
    rsBWMCurrentFilterContentDataCoding INTEGER,
    rsBWMCurrentFilterOMPCOffsetBase INTEGER,
    rsBWMCurrentFilterDestinationMaxPort INTEGER,
    rsBWMCurrentFilterSourceAppPortGroup DisplayString,
    rsBWMCurrentFilterDestinationAppPortGroup DisplayString,
	rsBWMCurrentFilterSessionType DpsSessionType,
	rsBWMCurrentFilterSessionTypeDirection INTEGER
}

rsBWMCurrentFilterName OBJECT-TYPE
    SYNTAX DisplayString (SIZE(0..29))
    ACCESS read-only
    STATUS mandatory
    DESCRIPTION
      "The name of the filter object."
    ::=  { rsBWMCurrentFilterEntry 1 }

rsBWMCurrentFilterDescription OBJECT-TYPE
    SYNTAX DisplayString (SIZE(0..29))
    ACCESS read-only
    STATUS mandatory
    DESCRIPTION
       "The description of the filter."
    ::=  { rsBWMCurrentFilterEntry 2 }

rsBWMCurrentFilterProtocol OBJECT-TYPE
    SYNTAX INTEGER {
        ip (1),
        tcp (2),
        udp (3),
        icmp (4),
        nonIp (5),
		icmpv6 (6),
        sctp(7)
    }
    ACCESS read-only
    STATUS mandatory
    DESCRIPTION
      "The protocol for the filter."
    ::=  { rsBWMCurrentFilterEntry 3 }

rsBWMCurrentFilterDestinationPort OBJECT-TYPE
    SYNTAX INTEGER
    ACCESS read-only
    STATUS mandatory
    DESCRIPTION
      "The initial destination port."
    ::=  { rsBWMCurrentFilterEntry 4 }

rsBWMCurrentFilterSourceFromPort OBJECT-TYPE
    SYNTAX INTEGER
    ACCESS read-only
    STATUS mandatory
    DESCRIPTION
      "The starting source port."
    ::=  { rsBWMCurrentFilterEntry 5 }

rsBWMCurrentFilterSourceToPort OBJECT-TYPE
    SYNTAX INTEGER
    ACCESS read-only
    STATUS mandatory
    DESCRIPTION
       "The last valid source port."
    ::=  { rsBWMCurrentFilterEntry 6 }

rsBWMCurrentFilterOMPCOffset OBJECT-TYPE
    SYNTAX INTEGER
    ACCESS read-only
    STATUS mandatory
    DESCRIPTION
      "The offset of the OMPC data."
    ::=  { rsBWMCurrentFilterEntry 7 }

rsBWMCurrentFilterOMPCMask OBJECT-TYPE
    SYNTAX OCTET STRING (SIZE(4))
    ACCESS read-only
    STATUS mandatory
    DESCRIPTION
      "The mask for the OMPC object."
    ::=  { rsBWMCurrentFilterEntry 8 }

rsBWMCurrentFilterOMPCPattern OBJECT-TYPE
    SYNTAX OCTET STRING (SIZE(4))
    ACCESS read-only
    STATUS mandatory
    DESCRIPTION
      "The pattern for the OMPC data."
    ::=  { rsBWMCurrentFilterEntry 9 }

rsBWMCurrentFilterOMPCCondition OBJECT-TYPE
    SYNTAX INTEGER {
        notApplicable (1),
        equal (2),
        notEqual (3),
        greaterThan (4),
        lessThan (5)
    }
    ACCESS read-only
    STATUS mandatory
    DESCRIPTION
      "The condition for the OMPC data check."
    ::=  { rsBWMCurrentFilterEntry 10 }

rsBWMCurrentFilterOMPCLength OBJECT-TYPE
    SYNTAX INTEGER {
        oneByte (1),
        twoBytes (2),
        threeBytes (3),
        fourBytes (4),
        notApplicable (5)
    }
    ACCESS read-only
    STATUS mandatory
    DESCRIPTION
      "The length of the OMPC."
    ::=  { rsBWMCurrentFilterEntry 11 }

rsBWMCurrentFilterContentOffset OBJECT-TYPE
    SYNTAX INTEGER
    ACCESS read-only
    STATUS mandatory
    DESCRIPTION
      "The offset for the content."
    ::=  { rsBWMCurrentFilterEntry 12 }

rsBWMCurrentFilterContent OBJECT-TYPE
    SYNTAX DisplayString (SIZE(0..255))
    ACCESS read-only
    STATUS mandatory
    DESCRIPTION
      "The content to be checked."
    ::=  { rsBWMCurrentFilterEntry 13 }


rsBWMCurrentFilterContentType OBJECT-TYPE
    SYNTAX INTEGER {
        notApplicable (1), 
        url (2),           
        text(3),           
        hostname(4),       
        headertype(5),     
        expression(6),     
        maildomain(7),     
        mailto(8),         
        mailfrom(9),       
        mailsubject(10),   
        filetype(11),      
        cookiedata(12),    
        idsurl(13),        
        pop3user(14),      
        urilength(15),     
        ftp(16),           
        ftpcontent(17),    
        rpc(18),           
        dceRPC(19),
        genericUrl(20), 
        genericHeader(21),
        genericCookie(22),
        sipcallfrom(23),
        sipcallto(24),
        sipcaller(25)
    }
    ACCESS read-only
    STATUS mandatory
    DESCRIPTION
      "The type of content that is used."
    ::=  { rsBWMCurrentFilterEntry 14 }

rsBWMCurrentFilterType OBJECT-TYPE
    SYNTAX INTEGER {
        regular (1),
        static (2),
        ids (3),
        idsStatic (4)
    }
    ACCESS read-only
    STATUS mandatory
    DESCRIPTION
      "The type of object. This can be regular (user defined) or static
      (defined by the application). ids and idsStatic are obsolete."
    ::=  { rsBWMCurrentFilterEntry 15 }

rsBWMCurrentFilterContentEnd OBJECT-TYPE
    SYNTAX INTEGER
    ACCESS read-only
    STATUS mandatory
    DESCRIPTION
      "End of search data."
    ::=  { rsBWMCurrentFilterEntry 16 }

rsBWMCurrentFilterContentData OBJECT-TYPE
    SYNTAX DisplayString (SIZE(0..255))
    ACCESS read-only
    STATUS mandatory
    DESCRIPTION
      "Additional content data, used for header type entries."
    ::=  { rsBWMCurrentFilterEntry 17 }

rsBWMCurrentFilterContentCoding OBJECT-TYPE
    SYNTAX INTEGER {
        notApplicable (1),
        caseInsensitive (2),
        caseSensitive (3),
        hex (4),
        international(5)
    }
    ACCESS read-only
    STATUS mandatory
    DESCRIPTION
      "The type of content coding that is used."
    ::=  { rsBWMCurrentFilterEntry 18 }

rsBWMCurrentFilterContentDataCoding OBJECT-TYPE
    SYNTAX INTEGER {
        notApplicable (1),
        caseInsensitive (2),
        caseSensitive (3),
        hex (4),
        international(5)
    }
    ACCESS read-only
    STATUS mandatory
    DESCRIPTION
      "The type of content data coding that is used."
    ::=  { rsBWMCurrentFilterEntry 19 }

rsBWMCurrentFilterOMPCOffsetBase OBJECT-TYPE
    SYNTAX INTEGER {
        none (0),
        ipHeader (1),
        ipData (2),
        tcpData (3),
        asn1 (4),
        ethernet (5),
        l4Header (6),
	ipv6Header (7)
    }
    ACCESS read-only
    STATUS mandatory
    DESCRIPTION
      "The base of filter OMPC offset."
    ::=  { rsBWMCurrentFilterEntry 20 }

rsBWMCurrentFilterDestinationMaxPort OBJECT-TYPE
    SYNTAX INTEGER
    ACCESS read-only
    STATUS mandatory
    DESCRIPTION
      "The Maximal destination port of the range."
    ::=  { rsBWMCurrentFilterEntry 21 }

rsBWMCurrentFilterSourceAppPortGroup OBJECT-TYPE
    SYNTAX DisplayString (SIZE(0..29))
    ACCESS read-only
    STATUS mandatory
    DESCRIPTION
      "The source port group."
    ::=  { rsBWMCurrentFilterEntry 22 }

rsBWMCurrentFilterDestinationAppPortGroup OBJECT-TYPE
    SYNTAX DisplayString (SIZE(0..29))
    ACCESS read-only
    STATUS mandatory
    DESCRIPTION
      "The destination port group."
    ::=  { rsBWMCurrentFilterEntry 23 }

rsBWMCurrentFilterSessionType  OBJECT-TYPE
    SYNTAX DpsSessionType
    ACCESS read-only
    STATUS mandatory
    DESCRIPTION
      "The type of session for classification of dynamic protocols sessions."
    ::=  { rsBWMCurrentFilterEntry 24 }

rsBWMCurrentFilterSessionTypeDirection OBJECT-TYPE
    SYNTAX INTEGER {
        all (0),
        rqst (1),
        rply (2)
    }
    ACCESS read-only
    STATUS mandatory
    DESCRIPTION
      "The type of session for classification of dynamic protocols sessions."
    ::=  { rsBWMCurrentFilterEntry 25 }

rsBWMFilterGroupTable OBJECT-TYPE
    SYNTAX SEQUENCE OF RsBWMFilterGroup
    ACCESS not-accessible
    STATUS  mandatory
    DESCRIPTION
      "Table containing groups of filters."
    ::= { rsBWM 17 }

rsBWMFilterGroup OBJECT-TYPE
    SYNTAX RsBWMFilterGroup
    ACCESS not-accessible
    STATUS mandatory
    DESCRIPTION
       "The row definition for this table."
    INDEX { rsBWMFilterGroupName, rsBWMFilterEntryName }
    ::=  { rsBWMFilterGroupTable 1 }

RsBWMFilterGroup ::= SEQUENCE {
    rsBWMFilterGroupName DisplayString,
    rsBWMFilterEntryName DisplayString,
    rsBWMFilterGroupType INTEGER,
    rsBWMFilterGroupStatus RowStatus
}

rsBWMFilterGroupName OBJECT-TYPE
    SYNTAX DisplayString(SIZE(0..29))
    ACCESS read-only
    STATUS mandatory
    DESCRIPTION
      "The name of the group entry."
    ::=  { rsBWMFilterGroup 1 }

rsBWMFilterEntryName OBJECT-TYPE
    SYNTAX DisplayString(SIZE(0..29))
    ACCESS read-only
    STATUS mandatory
    DESCRIPTION
      "The name of the filter entry in the group."
    ::=  { rsBWMFilterGroup 2 }

rsBWMFilterGroupType OBJECT-TYPE
    SYNTAX INTEGER {
        regular (1),
        static (2),
        ids (3),
        idsStatic (4)
    }
    ACCESS read-write
    STATUS  mandatory
    DESCRIPTION
      "The type of object. This can be regular (user defined) or static
      (defined by the application). ids and idsStatic are obsolete."
    DEFVAL { 1 }
    ::=  { rsBWMFilterGroup 3 }

rsBWMFilterGroupStatus OBJECT-TYPE
    SYNTAX RowStatus
    ACCESS read-write
    STATUS mandatory
    DESCRIPTION
      "The status of the object."
    ::=  { rsBWMFilterGroup 4 }

rsBWMCurrentFilterGroupTable OBJECT-TYPE
    SYNTAX SEQUENCE OF RsBWMCurrentFilterGroup
    ACCESS not-accessible
    STATUS  mandatory
    DESCRIPTION
      "Table containing groups of filters."
    ::= { rsBWM 18 }

rsBWMCurrentFilterGroup OBJECT-TYPE
    SYNTAX RsBWMCurrentFilterGroup
    ACCESS not-accessible
    STATUS mandatory
    DESCRIPTION
       "The row definition for this table."
    INDEX { rsBWMCurrentFilterGroupName, 
            rsBWMCurrentFilterEntryName }
    ::=  { rsBWMCurrentFilterGroupTable 1 }

RsBWMCurrentFilterGroup ::= SEQUENCE {
    rsBWMCurrentFilterGroupName DisplayString,
    rsBWMCurrentFilterEntryName DisplayString,
    rsBWMCurrentFilterGroupType INTEGER
}

rsBWMCurrentFilterGroupName OBJECT-TYPE
    SYNTAX DisplayString(SIZE(0..29))
    ACCESS read-only
    STATUS mandatory
    DESCRIPTION
      "The name of the group entry."
    ::=  { rsBWMCurrentFilterGroup 1 }

rsBWMCurrentFilterEntryName OBJECT-TYPE
    SYNTAX DisplayString(SIZE(0..29))
    ACCESS read-only
    STATUS mandatory
    DESCRIPTION
      "The name of the filter entry in the group."
    ::=  { rsBWMCurrentFilterGroup 2 }

rsBWMCurrentFilterGroupType OBJECT-TYPE
    SYNTAX INTEGER {
        regular (1),
        static (2),
        ids (3),
        idsStatic (4)
    }
    ACCESS read-only
    STATUS mandatory
    DESCRIPTION
      "The type of object. This can be regular (user defined) or static
      (defined by the application). ids and idsStatic are obsolete."
    ::=  { rsBWMCurrentFilterGroup 3 }

rsBWMFilterPolicyTable OBJECT-TYPE
    SYNTAX SEQUENCE OF RsBWMFilterPolicyEntry
    ACCESS not-accessible
    STATUS  mandatory
    DESCRIPTION
      "Table containing the set of filters and group filters - used by
      rule."
    ::= { rsBWM 19 }

rsBWMFilterPolicyEntry OBJECT-TYPE
    SYNTAX RsBWMFilterPolicyEntry
    ACCESS not-accessible
    STATUS mandatory
    DESCRIPTION
       "The row definition for this table."
    INDEX { rsBWMFilterPolicyName, 
            rsBWMFilterPolicyEntryName }
    ::=  { rsBWMFilterPolicyTable 1 }

RsBWMFilterPolicyEntry ::= SEQUENCE {
    rsBWMFilterPolicyName DisplayString,
    rsBWMFilterPolicyEntryName DisplayString,
    rsBWMFilterPolicyType INTEGER,
    rsBWMFilterPolicyStatus RowStatus,
    rsBWMFilterPolicyEntryType INTEGER
}

rsBWMFilterPolicyName OBJECT-TYPE
    SYNTAX DisplayString(SIZE(0..29))
    ACCESS read-only
    STATUS mandatory
    DESCRIPTION
      "The name of the filter policy."
    ::=  { rsBWMFilterPolicyEntry 1 }

rsBWMFilterPolicyEntryName OBJECT-TYPE
    SYNTAX DisplayString(SIZE(0..29))
    ACCESS read-only
    STATUS mandatory
    DESCRIPTION
      "The name of the filter entry. This can either be a group or a
      filter. The device will resolve the type - i.e. filter or group."
    ::=  { rsBWMFilterPolicyEntry 2 }

rsBWMFilterPolicyType OBJECT-TYPE
    SYNTAX INTEGER {
        regular (1),
        static (2),
        ids (3),
        idsStatic (4)
    }
    ACCESS read-write
    STATUS  mandatory
    DESCRIPTION
      "Denotes the type of the filter policy. ids and idsStatic are obsolete."
    DEFVAL { 1 }
    ::=  { rsBWMFilterPolicyEntry 3 }

rsBWMFilterPolicyStatus OBJECT-TYPE
    SYNTAX RowStatus
    ACCESS read-write
    STATUS mandatory
    DESCRIPTION
      "The status of the object."
    ::=  { rsBWMFilterPolicyEntry 4 }

rsBWMFilterPolicyEntryType OBJECT-TYPE
    SYNTAX INTEGER {
        basic (1),
        advanced (2)
    }
    ACCESS read-write
    STATUS mandatory
    DESCRIPTION
      "Denotes the type of this filter in the policy."
    DEFVAL { 1 }
    ::=  { rsBWMFilterPolicyEntry 5 }

rsBWMCurrentFilterPolicyTable OBJECT-TYPE
    SYNTAX SEQUENCE OF RsBWMCurrentFilterPolicyEntry
    ACCESS not-accessible
    STATUS  mandatory
    DESCRIPTION
      "Table containing the current set of filters and group filters - used by
      rule."
    ::= { rsBWM 20 }

rsBWMCurrentFilterPolicyEntry OBJECT-TYPE
    SYNTAX RsBWMCurrentFilterPolicyEntry
    ACCESS not-accessible
    STATUS mandatory
    DESCRIPTION
       "The row definition for this table."
    INDEX { rsBWMCurrentFilterPolicyName, 
            rsBWMCurrentFilterPolicyEntryName }
    ::=  { rsBWMCurrentFilterPolicyTable 1 }

RsBWMCurrentFilterPolicyEntry ::= SEQUENCE {
    rsBWMCurrentFilterPolicyName DisplayString,
    rsBWMCurrentFilterPolicyEntryName DisplayString,
    rsBWMCurrentFilterPolicyType INTEGER,
	rsBWMCurrentFilterPolicyEntryType INTEGER
}

rsBWMCurrentFilterPolicyName OBJECT-TYPE
    SYNTAX DisplayString(SIZE(0..29))
    ACCESS read-only
    STATUS mandatory
    DESCRIPTION
      "The name of the filter policy."
    ::=  { rsBWMCurrentFilterPolicyEntry 1 }

rsBWMCurrentFilterPolicyEntryName OBJECT-TYPE
    SYNTAX DisplayString(SIZE(0..29))
    ACCESS read-only
    STATUS mandatory
    DESCRIPTION
      "The name of the filter entry. This can either be a group or a
      filter. The device will resolve the type - i.e. filter or group."
    ::=  { rsBWMCurrentFilterPolicyEntry 2 }

rsBWMCurrentFilterPolicyType OBJECT-TYPE
    SYNTAX INTEGER {
        regular (1),
        static (2),
        ids (3),
        idsStatic (4)
    }
    ACCESS read-only
    STATUS mandatory
    DESCRIPTION
      "Denotes the type of the filter policy. ids and idsStatic are obsolete."
    ::=  { rsBWMCurrentFilterPolicyEntry 3 }

rsBWMCurrentFilterPolicyEntryType OBJECT-TYPE
    SYNTAX INTEGER {
        basic (1),
        advanced (2)
    }
    ACCESS read-only
    STATUS mandatory
    DESCRIPTION
      "Denotes the type of this filter in the policy."
    ::=  { rsBWMCurrentFilterPolicyEntry 4 }

rsBWMApplicationClassification OBJECT-TYPE
    SYNTAX INTEGER {
        enable (1),
        disable (2)
    }
    ACCESS  read-write
    STATUS  mandatory
    DESCRIPTION "Defines the nature of the application classification.
    Enable entails that the client entry is classified and the rule is
    appended to the client table. Disable implies that the data will be
    classified in the forwarding table. That is, each packet for the
    client entry will be classified."
    ::= { rsBWM 21 }

rsBWMPortBandwidthEntryTable OBJECT-TYPE
    SYNTAX SEQUENCE OF RsBWMPortBandwidthEntry
    ACCESS not-accessible
    STATUS  mandatory
    DESCRIPTION
      "Table containing the bandwidth for each port."
    ::= { rsBWM 22 }

rsBWMPortBandwidthEntry OBJECT-TYPE
    SYNTAX RsBWMPortBandwidthEntry
    ACCESS not-accessible
    STATUS mandatory
    DESCRIPTION
       "The row definition for this table."
    INDEX { rsBWMPortIndex }
    ::=  { rsBWMPortBandwidthEntryTable 1 }

RsBWMPortBandwidthEntry ::= SEQUENCE {
    rsBWMPortIndex INTEGER,
    rsBWMPortBandwidth Integer32,
    rsBwmPortUsedBandwidth Integer32
}

rsBWMPortIndex OBJECT-TYPE
    SYNTAX INTEGER
    ACCESS read-only
    STATUS mandatory
    DESCRIPTION
      "The index of the bandwidths."
    ::=  { rsBWMPortBandwidthEntry 1 }

rsBWMPortBandwidth OBJECT-TYPE
    SYNTAX Integer32
    ACCESS read-write
    STATUS mandatory
    DESCRIPTION
      "The bandwidth of the specific port."
    ::=  { rsBWMPortBandwidthEntry 2 }

rsBwmPortUsedBandwidth OBJECT-TYPE
    SYNTAX Integer32
    ACCESS read-only
    STATUS mandatory
    DESCRIPTION
      "The bandwidth of the specific port."
    ::=  { rsBWMPortBandwidthEntry 3 }

rsBWMTuning OBJECT IDENTIFIER ::= { rsBWM 23 }

rsBWMPolicyTuning OBJECT IDENTIFIER ::= { rsBWMTuning 1 }

rsBWMPolicyEntries OBJECT-TYPE
    SYNTAX INTEGER
    ACCESS  read-only
    STATUS  mandatory
    DESCRIPTION
      "Maximum number of policy entries."
    ::= { rsBWMPolicyTuning 1 }

rsBWMPolicyEntriesAfterReset OBJECT-TYPE
    SYNTAX INTEGER
    ACCESS  read-write
    STATUS  mandatory
    DESCRIPTION
      "Future maximum maximum number of policy entries."
    ::=  { rsBWMPolicyTuning 2 }

rsBWMPolicyLeavesPercent OBJECT-TYPE
    SYNTAX INTEGER
    ACCESS  read-only
    STATUS  mandatory
    DESCRIPTION
      "Maximum number of policy leaves."
    ::= { rsBWMPolicyTuning 3 }

rsBWMPolicyLeavesPercentAfterReset OBJECT-TYPE
    SYNTAX INTEGER
    ACCESS  read-write
    STATUS  mandatory
    DESCRIPTION
      "Future maximum maximum number of policy leaves."
    ::=  { rsBWMPolicyTuning 4 }

rsBWMNetworkTuning OBJECT IDENTIFIER ::= { rsBWMTuning 2 }

rsBWMNetworkEntries OBJECT-TYPE
    SYNTAX INTEGER
    ACCESS  read-only
    STATUS  mandatory
    DESCRIPTION
      "Maximum number of network entries."
    ::= { rsBWMNetworkTuning 1 }

rsBWMNetworkEntriesAfterReset OBJECT-TYPE
    SYNTAX INTEGER
    ACCESS  read-write
    STATUS  mandatory
    DESCRIPTION
      "Future maximum maximum number of network entries."
    ::=  { rsBWMNetworkTuning 2 }

rsBWMFilterTuning OBJECT IDENTIFIER ::= { rsBWMTuning 3 }

rsBWMFilterEntries OBJECT-TYPE
    SYNTAX INTEGER
    ACCESS  read-only
    STATUS  mandatory
    DESCRIPTION
      "Maximum number of filter entries."
    ::= { rsBWMFilterTuning 1 }

rsBWMFilterEntriesAfterReset OBJECT-TYPE
    SYNTAX INTEGER
    ACCESS  read-write
    STATUS  mandatory
    DESCRIPTION
      "Future maximum maximum number of filter entries."
    ::=  { rsBWMFilterTuning 2 }

rsBWMAdvancedTuning OBJECT IDENTIFIER ::= { rsBWMTuning 4 }

rsBWMAdvancedEntries OBJECT-TYPE
    SYNTAX INTEGER
    ACCESS  read-only
    STATUS  mandatory
    DESCRIPTION
      "Maximum number of advanced entries."
    ::= { rsBWMAdvancedTuning 1 }

rsBWMAdvancedEntriesAfterReset OBJECT-TYPE
    SYNTAX INTEGER
    ACCESS  read-write
    STATUS  mandatory
    DESCRIPTION
      "Future maximum maximum number of advanced entries."
    ::=  { rsBWMAdvancedTuning 2 }

rsBWMGroupTuning OBJECT IDENTIFIER ::= { rsBWMTuning 5 }

rsBWMGroupEntries OBJECT-TYPE
    SYNTAX INTEGER
    ACCESS  read-only
    STATUS  mandatory
    DESCRIPTION
      "Maximum number of group entries."
    ::= { rsBWMGroupTuning 1 }

rsBWMGroupEntriesAfterReset OBJECT-TYPE
    SYNTAX INTEGER
    ACCESS  read-write
    STATUS  mandatory
    DESCRIPTION
      "Future maximum maximum number of group entries."
    ::=  { rsBWMGroupTuning 2 }

rsBWMDestinationTuning OBJECT IDENTIFIER ::= { rsBWMTuning 6 }
rsBWMDestinationEntries OBJECT-TYPE
    SYNTAX INTEGER
    ACCESS  read-only
    STATUS  mandatory
    DESCRIPTION
      "Maximum number of destination entries."
    ::= { rsBWMDestinationTuning 1 }

rsBWMDestinationEntriesAfterReset OBJECT-TYPE
    SYNTAX INTEGER
    ACCESS  read-write
    STATUS  mandatory
    DESCRIPTION
      "Future maximum maximum number of destination entries."
    ::=  { rsBWMDestinationTuning 2 }

rsBWMSessionTuning OBJECT IDENTIFIER ::= { rsBWMTuning 7 }

rsBWMSessionEntries OBJECT-TYPE
    SYNTAX INTEGER
    ACCESS  read-only
    STATUS  mandatory
    DESCRIPTION
      "Maximum number of session table."
    ::= { rsBWMSessionTuning 1 }

rsBWMSessionEntriesAfterReset OBJECT-TYPE
    SYNTAX INTEGER
    ACCESS  read-write
    STATUS  mandatory
    DESCRIPTION
      "Future maximum maximum number of session table entries."
    ::=  { rsBWMSessionTuning 2 }

rsBWMChainTuning OBJECT IDENTIFIER ::= { rsBWMTuning 8 }

rsBWMMaxChainPolicies OBJECT-TYPE
    SYNTAX INTEGER
    ACCESS  read-only
    STATUS  mandatory
    DESCRIPTION
      "Maximum number of chain (farm cluster) policies."
    ::= { rsBWMChainTuning 1 }

rsBWMMaxChainPoliciesAfterReset OBJECT-TYPE
    SYNTAX INTEGER
    ACCESS  read-write
    STATUS  mandatory
    DESCRIPTION
      "Future maximum number of chain (farm cluster) policies."
    ::=  { rsBWMChainTuning 2 }

rsBWMDSCPEntryTable OBJECT-TYPE
    SYNTAX SEQUENCE OF RsBWMDSCPEntry
    ACCESS not-accessible
    STATUS  mandatory
    DESCRIPTION
      "Table containing priority and bandwidth for each DSCP."
    ::= { rsBWM 24 }

rsBWMDSCPEntry OBJECT-TYPE
    SYNTAX RsBWMDSCPEntry
    ACCESS not-accessible
    STATUS mandatory
    DESCRIPTION
       "The row definition for this table."
    INDEX { rsBWMDSCP }
    ::=  { rsBWMDSCPEntryTable 1 }

RsBWMDSCPEntry ::= SEQUENCE {
    rsBWMDSCP INTEGER,
    rsBWMDSCPPriority INTEGER,
    rsBWMDSCPGuaranteedBW Integer32,
    rsBWMDSCPMaxBW Integer32
}

rsBWMDSCP OBJECT-TYPE
    SYNTAX INTEGER (0..63)
    ACCESS read-only
    STATUS mandatory
    DESCRIPTION
      "The DSCP - the value of DiffServ field in the IP header."
    ::=  { rsBWMDSCPEntry 1 }

rsBWMDSCPPriority OBJECT-TYPE
    SYNTAX INTEGER (65535 | 0..7)
    ACCESS read-write
    STATUS  mandatory
    DESCRIPTION
      "The priority of the packets with the specified DSCP."
    DEFVAL { 0 }
    ::=  { rsBWMDSCPEntry 2 }

rsBWMDSCPGuaranteedBW OBJECT-TYPE
    SYNTAX Integer32
    ACCESS read-write
    STATUS  mandatory
    DESCRIPTION
      "The bandwidth allocated for the specified DSCP."
    ::=  { rsBWMDSCPEntry 3 }

rsBWMDSCPMaxBW OBJECT-TYPE
    SYNTAX Integer32
    ACCESS read-write
    STATUS  mandatory
    DESCRIPTION
      "The maximum bandwidth for the specified DSCP."
    ::=  { rsBWMDSCPEntry 4 }

rsBWMCurrentDSCPEntryTable OBJECT-TYPE
    SYNTAX SEQUENCE OF RsBWMCurrentDSCPEntry
    ACCESS not-accessible
    STATUS  mandatory
    DESCRIPTION
      "Table containing priority and bandwidth for each DSCP."
    ::= { rsBWM 25 }

rsBWMCurrentDSCPEntry OBJECT-TYPE
    SYNTAX RsBWMCurrentDSCPEntry
    ACCESS not-accessible
    STATUS mandatory
    DESCRIPTION
       "The row definition for this table."
    INDEX { rsBWMCurrentDSCP }
    ::=  { rsBWMCurrentDSCPEntryTable 1 }

RsBWMCurrentDSCPEntry ::= SEQUENCE {
    rsBWMCurrentDSCP INTEGER,
    rsBWMCurrentDSCPPriority INTEGER,
    rsBWMCurrentDSCPGuaranteedBW Counter,
    rsBWMCurrentDSCPMaxBW Counter
}

rsBWMCurrentDSCP OBJECT-TYPE
    SYNTAX INTEGER (0..63)
    ACCESS read-only
    STATUS mandatory
    DESCRIPTION
      "The DSCP - the value of DiffServ field in the IP header."
    ::=  { rsBWMCurrentDSCPEntry 1 }

rsBWMCurrentDSCPPriority OBJECT-TYPE
    SYNTAX INTEGER (65535 | 0..7)
    ACCESS read-only
    STATUS mandatory
    DESCRIPTION
      "The priority of the packets with the specified DSCP."
    ::=  { rsBWMCurrentDSCPEntry 2 }

rsBWMCurrentDSCPGuaranteedBW OBJECT-TYPE
    SYNTAX Counter
    ACCESS read-only
    STATUS mandatory
    DESCRIPTION
      "The bandwidth allocated for the specified DSCP."
    ::=  { rsBWMCurrentDSCPEntry 3 }

rsBWMCurrentDSCPMaxBW OBJECT-TYPE
    SYNTAX Counter
    ACCESS read-only
    STATUS mandatory
    DESCRIPTION
      "The maximum bandwidth for the specified DSCP."
    ::=  { rsBWMCurrentDSCPEntry 4 }

rsBWMVersion OBJECT-TYPE
    SYNTAX DisplayString (SIZE(0..20))
    ACCESS  read-only
    STATUS  mandatory
    DESCRIPTION
        "The current QoS software version."
    ::= { rsBWM 26 }

rsBWMBwmPortOperationTable OBJECT-TYPE
    SYNTAX SEQUENCE OF RsBWMBwmPortOperationEntry
    ACCESS not-accessible
    STATUS  mandatory
    DESCRIPTION
      "Table containing the operation for each port."
    ::= { rsBWM 27 }

rsBWMBwmPortOperationEntry OBJECT-TYPE
    SYNTAX RsBWMBwmPortOperationEntry
    ACCESS not-accessible
    STATUS mandatory
    DESCRIPTION
       "The row definition for this table."
    INDEX { rsBWMBwmInboundPort, 
            rsBWMBwmOutboundPort }
    ::=  { rsBWMBwmPortOperationTable 1 }

RsBWMBwmPortOperationEntry ::= SEQUENCE {
     rsBWMBwmInboundPort INTEGER,
     rsBWMBwmOutboundPort INTEGER,
     rsBWMBwmDirection INTEGER,
     rsBWMBwmOperationStatus RowStatus
}

rsBWMBwmInboundPort OBJECT-TYPE
    SYNTAX INTEGER
    ACCESS read-only
    STATUS mandatory
    DESCRIPTION
      "The index of the inbound port."
    ::=  { rsBWMBwmPortOperationEntry 1 }

rsBWMBwmOutboundPort OBJECT-TYPE
    SYNTAX INTEGER
    ACCESS read-only
    STATUS mandatory
    DESCRIPTION
      "The index of the outbound port."
    ::=  { rsBWMBwmPortOperationEntry 2 }

rsBWMBwmDirection OBJECT-TYPE
    SYNTAX INTEGER {
              oneway(1),
              twoway(2) }
    ACCESS  read-write
    STATUS  mandatory
    DESCRIPTION
       "This variable indicates the direction of the incoming packet."
    DEFVAL { 1 }
    ::=  { rsBWMBwmPortOperationEntry 3 }

rsBWMBwmOperationStatus OBJECT-TYPE
    SYNTAX RowStatus
    ACCESS read-write
    STATUS mandatory
    DESCRIPTION
      "The status of the current entry. "
    ::=  { rsBWMBwmPortOperationEntry 4 }

rsBWMBwmVLANOperationTable OBJECT-TYPE
    SYNTAX SEQUENCE OF RsBWMBwmVLANOperationEntry
    ACCESS not-accessible
    STATUS  mandatory
    DESCRIPTION
      "Table containing the operation for each VLAN."
    ::= { rsBWM 28 }

rsBWMBwmVLANOperationEntry OBJECT-TYPE
    SYNTAX RsBWMBwmVLANOperationEntry
    ACCESS not-accessible
    STATUS mandatory
    DESCRIPTION
       "The row definition for this table."
    INDEX { rsBWMBwmVLAN}
    ::=  { rsBWMBwmVLANOperationTable 1 }

RsBWMBwmVLANOperationEntry ::= SEQUENCE {
     rsBWMBwmVLAN INTEGER,
     rsBWMBwmVLANOperationStatus RowStatus
}

rsBWMBwmVLAN OBJECT-TYPE
    SYNTAX INTEGER
    ACCESS read-only
    STATUS mandatory
    DESCRIPTION
      "The VLAN."
    ::=  { rsBWMBwmVLANOperationEntry 1 }

rsBWMBwmVLANOperationStatus OBJECT-TYPE
    SYNTAX RowStatus
    ACCESS read-write
    STATUS mandatory
    DESCRIPTION
      "The status of the current entry. "
    ::=  { rsBWMBwmVLANOperationEntry 2 }

rsBWMSessionAgingTime OBJECT-TYPE
    SYNTAX INTEGER
    ACCESS  read-write
    STATUS  mandatory
    DESCRIPTION
        "Obsolete mib id."
    ::= {rsBWM 29}

rsBWMStatisticsTable OBJECT-TYPE
    SYNTAX SEQUENCE OF RsBWMStatisticsEntry
    ACCESS not-accessible
    STATUS  mandatory
    DESCRIPTION
      "Table containing statistics data for rules"
    ::=  {rsBWM 30}

rsBWMStatisticsEntry OBJECT-TYPE
    SYNTAX RsBWMStatisticsEntry
    ACCESS not-accessible
    STATUS  mandatory
    DESCRIPTION
       "The row definition for this table."
    INDEX { rsBWMStatisticsPolicyName }
    ::=  { rsBWMStatisticsTable 1 }

RsBWMStatisticsEntry ::= SEQUENCE {
    rsBWMStatisticsPolicyName DisplayString,
    rsBWMStatisticsBandwidthUsedLastSec Counter,
    rsBWMStatisticsPacketNumberLastSec Counter,
    rsBWMStatisticsFullQueueFailuresBWLastSec Counter,
    rsBWMStatisticsAgedPacketsFailuresBWLastSec Counter,
    rsBWMStatisticsGuaranteedReachedLastSec TruthValue,
    rsBWMStatisticsMaximumReachedLastSec TruthValue,
    rsBWMStatisticsBandwidthUsedLastPeriod Counter,
    rsBWMStatisticsPeakBandwidthLastPeriod Counter,
    rsBWMStatisticsPacketNumberLastPeriod Counter,
    rsBWMStatisticsFullQueueFailuresBWLastPeriod Counter,
    rsBWMStatisticsAgedPacketsFailuresBWLastPeriod Counter,
    rsBWMStatisticsGuaranteedReachedCounterLastPeriod INTEGER,
    rsBWMStatisticsMaximumReachedCounterLastPeriod INTEGER,
    rsBWMStatisticsMatchedBandwidthLastSec Counter,
    rsBWMStatisticsMatchedBandwidthLastPeriod Counter,
    rsBWMStatisticsInboundBandwidthUsedLastSec Counter,
    rsBWMStatisticsInboundBandwidthUsedLastPeriod Counter,
    rsBWMStatisticsInboundMatchedBandwidthLastSec Counter,
    rsBWMStatisticsInboundMatchedBandwidthLastPeriod Counter,
    rsBWMStatisticsInboundPacketNumberLastSec Counter,
    rsBWMStatisticsInboundPacketNumberLastPeriod Counter,
    rsBWMStatisticsOutboundBandwidthUsedLastSec Counter,
    rsBWMStatisticsOutboundBandwidthUsedLastPeriod Counter,
    rsBWMStatisticsOutboundMatchedBandwidthLastSec Counter,
    rsBWMStatisticsOutboundMatchedBandwidthLastPeriod Counter,
    rsBWMStatisticsOutboundPacketNumberLastSec Counter,
    rsBWMStatisticsOutboundPacketNumberLastPeriod Counter,
    rsBWMStatisticsNewTCPConnectionsLastSec Counter,
    rsBWMStatisticsNewTCPConnectionsLastPeriod Counter,
    rsBWMStatisticsNewUDPConnectionsLastSec Counter,
    rsBWMStatisticsNewUDPConnectionsLastPeriod Counter,
    rsBWMStatisticsQueuedBWLastSec Counter,
    rsBWMStatisticsQueuedBWLastPeriod Counter
}

rsBWMStatisticsPolicyName OBJECT-TYPE
    SYNTAX DisplayString (SIZE(0..255))
    ACCESS  read-only
    STATUS  mandatory
    DESCRIPTION
      "The name of the rule."
    ::=  {rsBWMStatisticsEntry 1}

rsBWMStatisticsBandwidthUsedLastSec OBJECT-TYPE
    SYNTAX Counter
    ACCESS  read-only
    STATUS  mandatory
    DESCRIPTION
       "The bandwidth used by the rule in the last second."
    ::=  {rsBWMStatisticsEntry 2}

rsBWMStatisticsPacketNumberLastSec OBJECT-TYPE
    SYNTAX Counter
    ACCESS  read-only
    STATUS  mandatory
    DESCRIPTION
       "The number of packets that match the rule in the last second."
    ::=  {rsBWMStatisticsEntry 3}

rsBWMStatisticsFullQueueFailuresBWLastSec OBJECT-TYPE
    SYNTAX Counter
    ACCESS  read-only
    STATUS  mandatory
    DESCRIPTION
       "The amount of bandwidth that the device failed to allocate in the last second."
    ::=  {rsBWMStatisticsEntry 4}

rsBWMStatisticsAgedPacketsFailuresBWLastSec OBJECT-TYPE
    SYNTAX Counter
    ACCESS  read-only
    STATUS  mandatory
    DESCRIPTION
       "The amount of bandwidth that the device failed to allocate in the last second,
        since the packets were discarded because of aging."
    ::=  {rsBWMStatisticsEntry 5}

rsBWMStatisticsGuaranteedReachedLastSec OBJECT-TYPE
    SYNTAX TruthValue
    ACCESS  read-only
    STATUS  mandatory
    DESCRIPTION
       "Whether the guaranteed bandwidth threshold was reached in the last second."
    ::=  {rsBWMStatisticsEntry 6}

rsBWMStatisticsMaximumReachedLastSec OBJECT-TYPE
    SYNTAX TruthValue
    ACCESS  read-only
    STATUS  mandatory
    DESCRIPTION
       "The number of times the maximum bandwidth threshold was reached in the last second."
    ::=  {rsBWMStatisticsEntry 7}

rsBWMStatisticsBandwidthUsedLastPeriod OBJECT-TYPE
    SYNTAX Counter
    ACCESS  read-only
    STATUS  mandatory
    DESCRIPTION
       "The bandwidth used by the rule in the last sampling period
            defined in rsBWMStatisticsReportingPeriod."
    ::=  {rsBWMStatisticsEntry 8}

rsBWMStatisticsPeakBandwidthLastPeriod OBJECT-TYPE
    SYNTAX Counter
    ACCESS  read-only
    STATUS  mandatory
    DESCRIPTION
       "The highest bandwidth in the last sampling period defined in
            rsBWMStatisticsReportingPeriod."
    ::=  {rsBWMStatisticsEntry 9}

rsBWMStatisticsPacketNumberLastPeriod OBJECT-TYPE
    SYNTAX Counter
    ACCESS  read-only
    STATUS  mandatory
    DESCRIPTION
       "The number of packets that match the rule in the last sampling period
            defined in rsBWMStatisticsReportingPeriod."
    ::=  {rsBWMStatisticsEntry 10}

rsBWMStatisticsFullQueueFailuresBWLastPeriod OBJECT-TYPE
    SYNTAX Counter
    ACCESS  read-only
    STATUS  mandatory
    DESCRIPTION
       "The amount of bandwidth that the device failed to allocate in the last sampling
                period defined in rsBWMStatisticsReportingPeriod, because the queue was full."
    ::=  {rsBWMStatisticsEntry 11}

rsBWMStatisticsAgedPacketsFailuresBWLastPeriod OBJECT-TYPE
    SYNTAX Counter
    ACCESS  read-only
    STATUS  mandatory
    DESCRIPTION
       "The amount of bandwidth that the device failed to allocate in the last sampling
                period defined in rsBWMStatisticsReportingPeriod, since the packets were discarded
        because of aging."
    ::=  {rsBWMStatisticsEntry 12}

rsBWMStatisticsGuaranteedReachedCounterLastPeriod OBJECT-TYPE
    SYNTAX INTEGER
    ACCESS  read-only
    STATUS  mandatory
    DESCRIPTION
       "The number of times the guaranteed bandwidth threshold was reached in the last
            sampling period defined in rsBWMStatisticsReportingPeriod."
    ::=  {rsBWMStatisticsEntry 13}

rsBWMStatisticsMaximumReachedCounterLastPeriod OBJECT-TYPE
    SYNTAX INTEGER
    ACCESS  read-only
    STATUS  mandatory
    DESCRIPTION
       "The number of times the maximum bandwidth threshold was reached in the last
            sampling period defined in rsBWMStatisticsReportingPeriod."
    ::=  {rsBWMStatisticsEntry 14}

rsBWMStatisticsMatchedBandwidthLastSec OBJECT-TYPE
    SYNTAX Counter
    ACCESS  read-only
    STATUS  mandatory
    DESCRIPTION
           "The matched bandwidth in the last second."
    ::=  {rsBWMStatisticsEntry 15}

rsBWMStatisticsMatchedBandwidthLastPeriod OBJECT-TYPE
    SYNTAX Counter
    ACCESS  read-only
    STATUS  mandatory
    DESCRIPTION
           "The matched bandwidth in the last sampling period."
    ::=  {rsBWMStatisticsEntry 16}

rsBWMStatisticsInboundBandwidthUsedLastSec OBJECT-TYPE
    SYNTAX Counter
    ACCESS  read-only
    STATUS  mandatory
    DESCRIPTION
           "The inbound bandwidth used by the rule in the last second."
    ::=  {rsBWMStatisticsEntry 17}

rsBWMStatisticsInboundBandwidthUsedLastPeriod OBJECT-TYPE
    SYNTAX Counter
    ACCESS  read-only
    STATUS  mandatory
    DESCRIPTION
           "The inbound bandwidth used by the rule in the last sampling period."
    ::=  {rsBWMStatisticsEntry 18}

rsBWMStatisticsInboundMatchedBandwidthLastSec OBJECT-TYPE
    SYNTAX Counter
    ACCESS  read-only
    STATUS  mandatory
    DESCRIPTION
           "The inbound matched bandwidth in the last second."
    ::=  {rsBWMStatisticsEntry 19}

rsBWMStatisticsInboundMatchedBandwidthLastPeriod OBJECT-TYPE
    SYNTAX Counter
    ACCESS  read-only
    STATUS  mandatory
    DESCRIPTION
           "The inbound matched bandwidth in the last sampling period."
    ::=  {rsBWMStatisticsEntry 20}

rsBWMStatisticsInboundPacketNumberLastSec OBJECT-TYPE
    SYNTAX Counter
    ACCESS  read-only
    STATUS  mandatory
    DESCRIPTION
           "The number of inbound packets that match the rule in the last second."
    ::=  {rsBWMStatisticsEntry 21}
	
rsBWMStatisticsInboundPacketNumberLastPeriod OBJECT-TYPE
    SYNTAX Counter
    ACCESS  read-only
    STATUS  mandatory
    DESCRIPTION
           "The number of inbound packets that match the rule in the last sampling period."
    ::=  {rsBWMStatisticsEntry 22}
	
rsBWMStatisticsOutboundBandwidthUsedLastSec OBJECT-TYPE
    SYNTAX Counter
    ACCESS  read-only
    STATUS  mandatory
    DESCRIPTION
           "The outbound bandwidth used by the rule in the last second ."
    ::=  {rsBWMStatisticsEntry 23}
	
rsBWMStatisticsOutboundBandwidthUsedLastPeriod OBJECT-TYPE
    SYNTAX Counter
    ACCESS  read-only
    STATUS  mandatory
    DESCRIPTION
           "The outbound bandwidth used by the rule in the last sampling period."
    ::=  {rsBWMStatisticsEntry 24}
	
rsBWMStatisticsOutboundMatchedBandwidthLastSec OBJECT-TYPE
    SYNTAX Counter
    ACCESS  read-only
    STATUS  mandatory
    DESCRIPTION
           "The outbound matched bandwidth in the last second."
    ::=  {rsBWMStatisticsEntry 25}
	
rsBWMStatisticsOutboundMatchedBandwidthLastPeriod OBJECT-TYPE
    SYNTAX Counter
    ACCESS  read-only
    STATUS  mandatory
    DESCRIPTION
           "The outbound matched bandwidth in the last sampling period."
    ::=  {rsBWMStatisticsEntry 26}
	
rsBWMStatisticsOutboundPacketNumberLastSec OBJECT-TYPE
    SYNTAX Counter
    ACCESS  read-only
    STATUS  mandatory
    DESCRIPTION
           "The number of outbound packets that match the rule in the last second."
    ::=  {rsBWMStatisticsEntry 27}
	
rsBWMStatisticsOutboundPacketNumberLastPeriod OBJECT-TYPE
    SYNTAX Counter
    ACCESS  read-only
    STATUS  mandatory
    DESCRIPTION
           "The number of outbound packets that match the rule in the last sampling period."
    ::=  {rsBWMStatisticsEntry 28}
	
rsBWMStatisticsNewTCPConnectionsLastSec OBJECT-TYPE
    SYNTAX Counter
    ACCESS  read-only
    STATUS  mandatory
    DESCRIPTION
           "The number of new TCP connections in the last second."
    ::=  {rsBWMStatisticsEntry 29}
	
rsBWMStatisticsNewTCPConnectionsLastPeriod OBJECT-TYPE
    SYNTAX Counter
    ACCESS  read-only
    STATUS  mandatory
    DESCRIPTION
           "The number of new TCP connections in the last sampling period."
    ::=  {rsBWMStatisticsEntry 30}
	
rsBWMStatisticsNewUDPConnectionsLastSec OBJECT-TYPE
    SYNTAX Counter
    ACCESS  read-only
    STATUS  mandatory
    DESCRIPTION
           "The number of new UDP connections in the last second."
    ::=  {rsBWMStatisticsEntry 31}
	
rsBWMStatisticsNewUDPConnectionsLastPeriod OBJECT-TYPE
    SYNTAX Counter
    ACCESS  read-only
    STATUS  mandatory
    DESCRIPTION
           "The number of new UDP connections in the last sampling period."
    ::=  {rsBWMStatisticsEntry 32}


rsBWMStatisticsQueuedBWLastSec OBJECT-TYPE
    SYNTAX Counter
    ACCESS  read-only
    STATUS  mandatory
    DESCRIPTION
           "The amount of queued bandwidth in the last second."
    ::=  {rsBWMStatisticsEntry 33}

rsBWMStatisticsQueuedBWLastPeriod OBJECT-TYPE
    SYNTAX Counter
    ACCESS  read-only
    STATUS  mandatory
    DESCRIPTION
           "The amount of queued bandwidth in the last sampling period."
    ::=  {rsBWMStatisticsEntry 34}


rsBWMStatisticsMonitorPolicy OBJECT-TYPE
    SYNTAX INTEGER {
        enabled(1),
        disabled(2) }
    ACCESS  read-write
    STATUS  mandatory
    DESCRIPTION
        "This variable indicates whether the device will gather policies' statistics."
    DEFVAL  { 2 }
    ::=  {rsBWMStatisticsTable 2}

rsBWMStatisticsTableUseSRP OBJECT-TYPE
    SYNTAX TruthValue
    ACCESS  read-write
    STATUS  mandatory
    DESCRIPTION
        "This variable indicates whether the device will send the data to ConfigWare using SRP."
    DEFVAL  { false }
    ::=  {rsBWMStatisticsTable 3}

rsBWMStatisticsReportingPeriod OBJECT-TYPE
    SYNTAX INTEGER
    ACCESS  read-write
    STATUS  mandatory
    DESCRIPTION
        "This variable indicates reporting frequency (in seconds) using SRP for BWM."
    DEFVAL  { 60 }
    ::=  {rsBWMStatisticsTable 4}

rsBWMSamplingRatio OBJECT-TYPE
    SYNTAX INTEGER
    ACCESS  read-write
    STATUS  mandatory
    DESCRIPTION "Sampling ratio: one of how many packets is sampled."
    DEFVAL  {100}
    ::= {rsBWM 31}

rsBWMSamplerOverloadMode OBJECT-TYPE
    SYNTAX INTEGER {
        forward(1),
        discard(2)
    }
    ACCESS  read-write
    STATUS  mandatory
    DESCRIPTION "Overload mechanism mode: forward/discard excess traffic."
    DEFVAL  {forward}
    ::= {rsBWM 32}

rsBWMChainRulesTable OBJECT-TYPE
    SYNTAX SEQUENCE OF RsBWMChainRulesEntry
    ACCESS not-accessible
    STATUS  mandatory
    DESCRIPTION
      "Table containing the list of chain rules for classifer data base,
       these rules can be used to classify packets for chaining."
    ::=  {rsBWM 33}

rsBWMChainRulesEntry OBJECT-TYPE
    SYNTAX RsBWMChainRulesEntry
    ACCESS not-accessible
    STATUS  mandatory
    DESCRIPTION
       "The row definition for this table."
    INDEX { rsBWMChainRulesName }
    ::=  { rsBWMChainRulesTable 1 }

RsBWMChainRulesEntry ::= SEQUENCE {
    rsBWMChainRulesIndex INTEGER,
    rsBWMChainRulesName DisplayString,
    rsBWMChainRulesDestination DisplayString,
    rsBWMChainRulesSource DisplayString,
    rsBWMChainRulesStatus  RowStatus,
    rsBWMChainRulesDirection INTEGER,
    rsBWMChainRulesDescription DisplayString,
    rsBWMChainRulesPolicyType INTEGER,
    rsBWMChainRulesPolicy DisplayString,
    rsBWMChainRulesOperationalStatus INTEGER,
    rsBWMChainRulesSpecific DisplayString,
    rsBWMChainRulesPhysicalPortGroup DisplayString,
    rsBWMChainRulesVLANTagGroup DisplayString,
    rsBWMChainRulesDSCPMarking INTEGER,
    rsBWMChainRulesRadiusRule DisplayString
}

rsBWMChainRulesIndex OBJECT-TYPE
    SYNTAX INTEGER
    ACCESS  read-write
    STATUS  mandatory
    DESCRIPTION
       "This variable indicates the administrative index of a line it
       determines the order of the rules."
    DEFVAL { 1 }
    ::=  { rsBWMChainRulesEntry 1 }

rsBWMChainRulesName OBJECT-TYPE
    SYNTAX DisplayString (SIZE(0..255))
    ACCESS  read-only
    STATUS  mandatory
    DESCRIPTION
      "The Name for the Rule must be unique."
    ::=  {rsBWMChainRulesEntry 2}

rsBWMChainRulesDestination OBJECT-TYPE
    SYNTAX DisplayString (SIZE(0..46))
    ACCESS  read-write
    STATUS  mandatory
    DESCRIPTION
      "The destination address / range of address for the packet, the name is
      defined in the Objects table or can be an IP address."
    DEFVAL { "any" }
    ::=  {rsBWMChainRulesEntry 3}

rsBWMChainRulesSource OBJECT-TYPE
    SYNTAX DisplayString (SIZE(0..46))
    ACCESS  read-write
    STATUS  mandatory
    DESCRIPTION
      "The source address / range of address for the packet, the name is
      defined in the Objects table or can be an IP address."
    DEFVAL { "any" }
    ::=  {rsBWMChainRulesEntry 4}

rsBWMChainRulesStatus OBJECT-TYPE
    SYNTAX RowStatus
    ACCESS  read-write
    STATUS  mandatory
    DESCRIPTION
       "This variable indicates the administrative status of this entry.
        Used to delete an entry of this table."
    ::=  { rsBWMChainRulesEntry 5 }

rsBWMChainRulesDirection OBJECT-TYPE
    SYNTAX INTEGER {
              oneway(1),
              twoway(2) }
    ACCESS  read-write
    STATUS  mandatory
    DESCRIPTION
       "This variable indicates the direction of the incoming packet."
    DEFVAL { 1 }
    ::=  { rsBWMChainRulesEntry 6 }

rsBWMChainRulesDescription OBJECT-TYPE
    SYNTAX DisplayString (SIZE(0..19))
    ACCESS  read-write
    STATUS  mandatory
    DESCRIPTION
      "Description."
    ::=  { rsBWMChainRulesEntry 7 }

rsBWMChainRulesPolicyType OBJECT-TYPE
    SYNTAX INTEGER {
              none(1),
              filter(2),
              group(3),
              policy(4)}
    ACCESS  read-write
    STATUS  mandatory
    DESCRIPTION
       "The type of policy - i.e. if this is a filter, group or policy."
    DEFVAL  { 1 }
    ::=  { rsBWMChainRulesEntry 8 }

rsBWMChainRulesPolicy OBJECT-TYPE
    SYNTAX DisplayString (SIZE(0..29))
    ACCESS  read-write
    STATUS  mandatory
    DESCRIPTION
       "The name for the filter policy for the rule."
    ::=  { rsBWMChainRulesEntry 9 }

rsBWMChainRulesOperationalStatus OBJECT-TYPE
    SYNTAX INTEGER {
        active (1),
        inactive (2)
    }
    ACCESS  read-write
    STATUS  mandatory
    DESCRIPTION
       "This variable indicates if the rule is active or inactive.
        The active rule table contains only active rules."
    DEFVAL { 1 }
    ::= { rsBWMChainRulesEntry 10 }

rsBWMChainRulesSpecific OBJECT-TYPE
    SYNTAX DisplayString (SIZE(0..19))
    ACCESS  read-write
    STATUS  mandatory
    DESCRIPTION
       "This variable indicates if there is additional data to the
       policy."
    ::= { rsBWMChainRulesEntry 11 }

rsBWMChainRulesPhysicalPortGroup OBJECT-TYPE
    SYNTAX DisplayString (SIZE(0..19))
    ACCESS  read-write
    STATUS  mandatory
    DESCRIPTION
       "The name of the physical port group for this rule."
    ::=  { rsBWMChainRulesEntry 12 }

rsBWMChainRulesVLANTagGroup OBJECT-TYPE
    SYNTAX DisplayString (SIZE(0..19))
    ACCESS  read-write
    STATUS  mandatory
    DESCRIPTION
        "The name of the VLAN tag group for this rule."
    ::= { rsBWMChainRulesEntry 13 }

rsBWMChainRulesDSCPMarking OBJECT-TYPE
    SYNTAX INTEGER (-1 | 0..63)
    ACCESS  read-write
    STATUS  mandatory
    DESCRIPTION
       "This variable indicates the DSCP value to mark the ToS field in the IP header
        in the matching packets. If equals -1, the marking is not performed."
    DEFVAL { -1 }
    ::= { rsBWMChainRulesEntry 14 }

rsBWMChainRulesRadiusRule OBJECT-TYPE
    SYNTAX DisplayString (SIZE(0..30))
    ACCESS  read-write
    STATUS  mandatory
    DESCRIPTION
      "The name of the radius relevant this session belongs to. This field is relevant only for cid. Radius' rules
	   names can be found in the Radius Rules Table"
    DEFVAL { "any" }
    ::=  {rsBWMChainRulesEntry 15}

rsBWMCurrentChainRulesTable OBJECT-TYPE
    SYNTAX SEQUENCE OF RsBWMCurrentChainRulesEntry
    ACCESS not-accessible
    STATUS  mandatory
    DESCRIPTION
      "Table containing the list of chain rules for classifer data base,
       these rules can be used to classify packets for chaining."
    ::=  {rsBWM 34}

rsBWMCurrentChainRulesEntry OBJECT-TYPE
    SYNTAX RsBWMCurrentChainRulesEntry
    ACCESS not-accessible
    STATUS  mandatory
    DESCRIPTION
       "The row definition for this table."
    INDEX { rsBWMCurrentChainRulesName }
    ::=  { rsBWMCurrentChainRulesTable 1 }

RsBWMCurrentChainRulesEntry ::= SEQUENCE {
    rsBWMCurrentChainRulesIndex INTEGER,
    rsBWMCurrentChainRulesName DisplayString,
    rsBWMCurrentChainRulesDestination DisplayString,
    rsBWMCurrentChainRulesSource DisplayString,
    rsBWMCurrentChainRulesDirection INTEGER,
    rsBWMCurrentChainRulesDescription DisplayString,
    rsBWMCurrentChainRulesPolicyType INTEGER,
    rsBWMCurrentChainRulesPolicy DisplayString,
    rsBWMCurrentChainRulesSpecific DisplayString,
    rsBWMCurrentChainBandwidthLastSec Counter,
    rsBWMCurrentChainPacketsLastSec Counter,
    rsBWMCurrentChainRulesPhysicalPortGroup DisplayString,
    rsBWMCurrentChainRulesVLANTagGroup DisplayString,
    rsBWMCurrentChainRulesDSCPMarking INTEGER,
    rsBWMCurrentChainRulesRadiusRule DisplayString
}

rsBWMCurrentChainRulesIndex OBJECT-TYPE
    SYNTAX INTEGER
    ACCESS  read-only
    STATUS  mandatory
    DESCRIPTION
       "This variable indicates the administrative index of a line it
       determine the order of the rules."
    ::=  { rsBWMCurrentChainRulesEntry 1 }

rsBWMCurrentChainRulesName OBJECT-TYPE
    SYNTAX DisplayString (SIZE(0..255))
    ACCESS  read-only
    STATUS  mandatory
    DESCRIPTION
      "The Name for the Rule must be unique."
    ::=  {rsBWMCurrentChainRulesEntry 2}

rsBWMCurrentChainRulesDestination OBJECT-TYPE
    SYNTAX DisplayString (SIZE(0..46))
    ACCESS  read-only
    STATUS  mandatory
    DESCRIPTION
      "The destination address / range of address for the packet, the name is
      defined in the Objects table or can be an IP address."
    ::=  {rsBWMCurrentChainRulesEntry 3}

rsBWMCurrentChainRulesSource OBJECT-TYPE
    SYNTAX DisplayString (SIZE(0..46))
    ACCESS  read-only
    STATUS  mandatory
    DESCRIPTION
      "The source address / range of address for the packet, the name is
      defined in the Objects table or can be an IP address."
    ::=  {rsBWMCurrentChainRulesEntry 4}

rsBWMCurrentChainRulesDirection OBJECT-TYPE
    SYNTAX INTEGER {
              oneway(1),
              twoway(2) }
    ACCESS read-only
    STATUS mandatory
    DESCRIPTION
       "This variable indicates the direction of the incoming packet."
    ::=  { rsBWMCurrentChainRulesEntry 5 }

rsBWMCurrentChainRulesDescription OBJECT-TYPE
    SYNTAX DisplayString (SIZE(0..19))
    ACCESS  read-only
    STATUS  mandatory
    DESCRIPTION
      "Description."
    ::=  { rsBWMCurrentChainRulesEntry 6 }

rsBWMCurrentChainRulesPolicyType OBJECT-TYPE
    SYNTAX INTEGER {
              none(1),
              filter(2),
              group(3),
              policy(4)}
    ACCESS  read-only
    STATUS  mandatory
    DESCRIPTION
       "The type of policy - i.e. if this is a filter, group or policy."
    DEFVAL  { 1 }
    ::=  { rsBWMCurrentChainRulesEntry 7 }

rsBWMCurrentChainRulesPolicy OBJECT-TYPE
    SYNTAX DisplayString (SIZE(0..29))
    ACCESS  read-only
    STATUS  mandatory
    DESCRIPTION
       "The name for the filter policy for the rule."
    ::=  { rsBWMCurrentChainRulesEntry 8 }

rsBWMCurrentChainRulesSpecific OBJECT-TYPE
    SYNTAX DisplayString (SIZE(0..19))
    ACCESS  read-only
    STATUS  mandatory
    DESCRIPTION
       "This variable indicates if there is additional data to the
       policy."
    ::= { rsBWMCurrentChainRulesEntry 9 }

rsBWMCurrentChainBandwidthLastSec OBJECT-TYPE
    SYNTAX Counter
    ACCESS  read-only
    STATUS  mandatory
    DESCRIPTION
       "The bandwidth used by the policy in the last second."
    ::=  {rsBWMCurrentChainRulesEntry 10}

rsBWMCurrentChainPacketsLastSec OBJECT-TYPE
    SYNTAX Counter
    ACCESS  read-only
    STATUS  mandatory
    DESCRIPTION
       "The packets that matched the policy in the last second."
    ::=  {rsBWMCurrentChainRulesEntry 11}

rsBWMCurrentChainRulesPhysicalPortGroup OBJECT-TYPE
    SYNTAX DisplayString (SIZE(0..19))
    ACCESS  read-only
    STATUS  mandatory
    DESCRIPTION
       "This name of the physical port group for this rule."
    ::=  { rsBWMCurrentChainRulesEntry 12 }

rsBWMCurrentChainRulesVLANTagGroup OBJECT-TYPE
    SYNTAX DisplayString (SIZE(0..19))
    ACCESS  read-only
    STATUS  mandatory
    DESCRIPTION
        "The name of the VLAN tag group for this rule."
    ::=  { rsBWMCurrentChainRulesEntry 13 }

rsBWMCurrentChainRulesDSCPMarking OBJECT-TYPE
    SYNTAX INTEGER (-1 | 0..63)
    ACCESS  read-only
    STATUS  mandatory
    DESCRIPTION
       "This variable indicates the DSCP value to mark the ToS field in the IP header
        in the matching packets. If equals -1, the marking is not performed."
    ::= { rsBWMCurrentChainRulesEntry 14 }

rsBWMCurrentChainRulesRadiusRule OBJECT-TYPE
    SYNTAX DisplayString (SIZE(0..30))
    ACCESS  read-write
    STATUS  mandatory
    DESCRIPTION
      "The name of the radius rule this session belongs to. This field is relevant only for cid. Radius rules'
	   names can be found in the Radius Rules Table"
    DEFVAL { "any" }
    ::=  {rsBWMCurrentChainRulesEntry 15}

rsBWMPPCInboundPortOnlyTable OBJECT-TYPE
    SYNTAX SEQUENCE OF RsBWMPPCInboundPortOnlyEntry
    ACCESS not-accessible
    STATUS  mandatory
    DESCRIPTION
      "Table containing the operation for each inbound port (and not for port pairs)."
    ::= { rsBWM 35 }

rsBWMPPCInboundPortOnlyEntry OBJECT-TYPE
    SYNTAX RsBWMPPCInboundPortOnlyEntry
    ACCESS not-accessible
    STATUS mandatory
    DESCRIPTION
       "The row definition for this table."
    INDEX { rsBWMPPCInboundPort }
    ::=  { rsBWMPPCInboundPortOnlyTable 1 }

RsBWMPPCInboundPortOnlyEntry ::= SEQUENCE {
     rsBWMPPCInboundPort INTEGER,
     rsBWMPPCOperationStatus RowStatus
}

rsBWMPPCInboundPort OBJECT-TYPE
    SYNTAX INTEGER
    ACCESS read-only
    STATUS mandatory
    DESCRIPTION
      "The index of the inbound port."
    ::=  { rsBWMPPCInboundPortOnlyEntry 1 }

rsBWMPPCOperationStatus OBJECT-TYPE
    SYNTAX RowStatus
    ACCESS read-write
    STATUS mandatory
    DESCRIPTION
      "The status of the current entry. "
    ::=  { rsBWMPPCInboundPortOnlyEntry 2 }

rsBWMPhysicalPortGroupTable OBJECT-TYPE
    SYNTAX SEQUENCE OF RsBWMPhysicalPortGroupEntry
    ACCESS not-accessible
    STATUS  mandatory
    DESCRIPTION
      "Table containing the entries of physical port groups."
    ::= { rsBWM 36 }

rsBWMPhysicalPortGroupEntry OBJECT-TYPE
    SYNTAX RsBWMPhysicalPortGroupEntry
    ACCESS not-accessible
    STATUS mandatory
    DESCRIPTION
       "The row definition for this table."
    INDEX { rsBWMPhysicalPortGroupName,  
            rsBWMPhysicalPortGroupPort }
    ::=  { rsBWMPhysicalPortGroupTable 1 }

RsBWMPhysicalPortGroupEntry ::= SEQUENCE {
     rsBWMPhysicalPortGroupName DisplayString,
     rsBWMPhysicalPortGroupPort INTEGER,
     rsBWMPhysicalPortGroupOperationStatus RowStatus
}

rsBWMPhysicalPortGroupName OBJECT-TYPE
    SYNTAX DisplayString (SIZE(0..19))
    ACCESS read-only
    STATUS mandatory
    DESCRIPTION
      "The name of the entry."
    ::=  { rsBWMPhysicalPortGroupEntry 1 }

rsBWMPhysicalPortGroupPort OBJECT-TYPE
    SYNTAX INTEGER
    ACCESS read-only
    STATUS mandatory
    DESCRIPTION
      "The inbound port."
    ::=  { rsBWMPhysicalPortGroupEntry 2 }

rsBWMPhysicalPortGroupOperationStatus OBJECT-TYPE
    SYNTAX RowStatus
    ACCESS read-write
    STATUS mandatory
    DESCRIPTION
      "The status of the current entry. "
    ::=  { rsBWMPhysicalPortGroupEntry 3 }

rsBWMCurrentPhysicalPortGroupTable OBJECT-TYPE
    SYNTAX SEQUENCE OF RsBWMCurrentPhysicalPortGroupEntry
    ACCESS not-accessible
    STATUS  mandatory
    DESCRIPTION
      "Table containing the entries of current physical port groups."
    ::= { rsBWM 37 }

rsBWMCurrentPhysicalPortGroupEntry OBJECT-TYPE
    SYNTAX RsBWMCurrentPhysicalPortGroupEntry
    ACCESS not-accessible
    STATUS mandatory
    DESCRIPTION
       "The row definition for this table."
    INDEX { rsBWMCurrentPhysicalPortGroupName,  
            rsBWMCurrentPhysicalPortGroupPort }
    ::=  { rsBWMCurrentPhysicalPortGroupTable 1 }

RsBWMCurrentPhysicalPortGroupEntry ::= SEQUENCE {
     rsBWMCurrentPhysicalPortGroupName DisplayString,
     rsBWMCurrentPhysicalPortGroupPort INTEGER
}

rsBWMCurrentPhysicalPortGroupName OBJECT-TYPE
    SYNTAX DisplayString (SIZE(0..19))
    ACCESS read-only
    STATUS mandatory
    DESCRIPTION
      "The name of the entry."
    ::=  { rsBWMCurrentPhysicalPortGroupEntry 1 }

rsBWMCurrentPhysicalPortGroupPort OBJECT-TYPE
    SYNTAX INTEGER
    ACCESS read-only
    STATUS mandatory
    DESCRIPTION
      "The inbound port."
    ::=  { rsBWMCurrentPhysicalPortGroupEntry 2 }

rsBWMContentTuning OBJECT IDENTIFIER ::= { rsBWMTuning 9 }
rsBWMContentEntries OBJECT-TYPE
    SYNTAX INTEGER
    ACCESS  read-only
    STATUS  mandatory
    DESCRIPTION
      "Maximum number of content entries."
    ::= { rsBWMContentTuning 1 }

rsBWMContentEntriesAfterReset OBJECT-TYPE
    SYNTAX INTEGER
    ACCESS  read-write
    STATUS  mandatory
    DESCRIPTION
      "Future maximum maximum number of content entries."
    ::=  { rsBWMContentTuning 2 }

rsBWMNetworkIPTuning OBJECT IDENTIFIER ::= { rsBWMTuning 10 }

rsBWMNetworkIPHashEntries OBJECT-TYPE
    SYNTAX INTEGER
    ACCESS  read-only
    STATUS  mandatory
    DESCRIPTION
      "Maximum number of entries in discrete IPs hash per network."
    ::= { rsBWMNetworkIPTuning 1 }

rsBWMNetworkIPHashEntriesAfterReset OBJECT-TYPE
    SYNTAX INTEGER
    ACCESS  read-write
    STATUS  mandatory
    DESCRIPTION
      "Future maximum maximum number of entries in discrete IPs hash per network."
    ::=  { rsBWMNetworkIPTuning 2 }

rsBWMNetworkRangeTuning OBJECT IDENTIFIER ::= { rsBWMTuning 11 }

rsBWMNetworkRangeEntries OBJECT-TYPE
    SYNTAX INTEGER
    ACCESS  read-only
    STATUS  mandatory
    DESCRIPTION
      "Maximum number of ranges per network."
    ::= { rsBWMNetworkRangeTuning 1 }

rsBWMNetworkRangeEntriesAfterReset OBJECT-TYPE
    SYNTAX INTEGER
    ACCESS  read-write
    STATUS  mandatory
    DESCRIPTION
      "Future maximum maximum number of ranges per network."
    ::=  { rsBWMNetworkRangeTuning 2 }

rsBWMFarmRulesTable OBJECT-TYPE
    SYNTAX SEQUENCE OF RsBWMFarmRulesEntry
    ACCESS not-accessible
    STATUS  mandatory
    DESCRIPTION
      "Table containing the list of farm rules for classifer data base,
       these rules can be used to classify packets for farm."
    ::=  {rsBWM 38}

rsBWMFarmRulesEntry OBJECT-TYPE
    SYNTAX RsBWMFarmRulesEntry
    ACCESS not-accessible
    STATUS  mandatory
    DESCRIPTION
       "The row definition for this table."
    INDEX { rsBWMFarmRulesName }
    ::=  { rsBWMFarmRulesTable 1 }

RsBWMFarmRulesEntry ::= SEQUENCE {
    rsBWMFarmRulesIndex INTEGER,
    rsBWMFarmRulesName DisplayString,
    rsBWMFarmRulesDestination DisplayString,
    rsBWMFarmRulesSource DisplayString,
    rsBWMFarmRulesStatus  RowStatus,
    rsBWMFarmRulesDirection INTEGER,
    rsBWMFarmRulesDescription DisplayString,
    rsBWMFarmRulesPolicyType INTEGER,
    rsBWMFarmRulesPolicy DisplayString,
    rsBWMFarmRulesOperationalStatus INTEGER,
    rsBWMFarmRulesSpecific DisplayString,
    rsBWMFarmRulesPhysicalPortGroup DisplayString,
    rsBWMFarmRulesVLANTagGroup DisplayString,
    rsBWMFarmRulesDSCPMarking INTEGER
}

rsBWMFarmRulesIndex OBJECT-TYPE
    SYNTAX INTEGER
    ACCESS  read-write
    STATUS  mandatory
    DESCRIPTION
       "This variable indicates the administrative index of a line it
       determines the order of the rules."
    ::=  { rsBWMFarmRulesEntry 1 }

rsBWMFarmRulesName OBJECT-TYPE
    SYNTAX DisplayString (SIZE(0..255))
    ACCESS  read-only
    STATUS  mandatory
    DESCRIPTION
      "The Name for the Rule must be unique."
    ::=  {rsBWMFarmRulesEntry 2}

rsBWMFarmRulesDestination OBJECT-TYPE
    SYNTAX DisplayString (SIZE(0..46))
    ACCESS  read-write
    STATUS  mandatory
    DESCRIPTION
      "The destination address / range of address for the packet, the name is
      defined in the Objects table or can be an IP address."
    ::=  {rsBWMFarmRulesEntry 3}

rsBWMFarmRulesSource OBJECT-TYPE
    SYNTAX DisplayString (SIZE(0..46))
    ACCESS  read-write
    STATUS  mandatory
    DESCRIPTION
      "The source address / range of address for the packet, the name is
      defined in the Objects table or can be an IP address."
    ::=  {rsBWMFarmRulesEntry 4}

rsBWMFarmRulesStatus OBJECT-TYPE
    SYNTAX RowStatus
    ACCESS  read-write
    STATUS  mandatory
    DESCRIPTION
       "This variable indicates the administrative status of this entry.
        Used to delete an entry of this table."
    ::=  { rsBWMFarmRulesEntry 5 }

rsBWMFarmRulesDirection OBJECT-TYPE
    SYNTAX INTEGER {
              oneway(1),
              twoway(2) }
    ACCESS  read-write
    STATUS  mandatory
    DESCRIPTION
       "This variable indicates the direction of the incoming packet."
    DEFVAL { 2 }
    ::=  { rsBWMFarmRulesEntry 6 }

rsBWMFarmRulesDescription OBJECT-TYPE
    SYNTAX DisplayString (SIZE(0..19))
    ACCESS  read-write
    STATUS  mandatory
    DESCRIPTION
      "Description."
    ::=  { rsBWMFarmRulesEntry 7 }

rsBWMFarmRulesPolicyType OBJECT-TYPE
    SYNTAX INTEGER {
              none(1),
              filter(2),
              group(3),
              policy(4)}
    ACCESS  read-write
    STATUS  mandatory
    DESCRIPTION
       "The type of policy - i.e. if this is a filter, group or policy."
    DEFVAL  { 1 }
    ::=  { rsBWMFarmRulesEntry 8 }

rsBWMFarmRulesPolicy OBJECT-TYPE
    SYNTAX DisplayString (SIZE(0..29))
    ACCESS  read-write
    STATUS  mandatory
    DESCRIPTION
       "The name for the filter policy for the rule."
    ::=  { rsBWMFarmRulesEntry 9 }

rsBWMFarmRulesOperationalStatus OBJECT-TYPE
    SYNTAX INTEGER {
        active (1),
        inactive (2)
    }
    ACCESS  read-write
    STATUS  mandatory
    DESCRIPTION
       "This variable indicates if the rule is active or inactive.
        The active rule table contains only active rules."
    DEFVAL { 1 }
    ::= { rsBWMFarmRulesEntry 10 }

rsBWMFarmRulesSpecific OBJECT-TYPE
    SYNTAX DisplayString (SIZE(0..19))
    ACCESS  read-write
    STATUS  mandatory
    DESCRIPTION
       "This variable indicates if there is additional data to the
       policy."
    ::= { rsBWMFarmRulesEntry 11 }

rsBWMFarmRulesPhysicalPortGroup OBJECT-TYPE
    SYNTAX DisplayString (SIZE(0..19))
    ACCESS  read-write
    STATUS  mandatory
    DESCRIPTION
       "This name of the physical port group for this rule."
    ::=  { rsBWMFarmRulesEntry 12 }

rsBWMFarmRulesVLANTagGroup OBJECT-TYPE
    SYNTAX DisplayString (SIZE(0..19))
    ACCESS  read-write
    STATUS  mandatory
    DESCRIPTION
        "The name of the VLAN tag group for this rule."
    ::= { rsBWMFarmRulesEntry 13 }

rsBWMFarmRulesDSCPMarking OBJECT-TYPE
    SYNTAX INTEGER (-1 | 0..63)
    ACCESS  read-write
    STATUS  mandatory
    DESCRIPTION
       "This variable indicates the DSCP value to mark the ToS field in the IP header
        in the matching packets. If equals -1, the marking is not performed."
    ::= { rsBWMFarmRulesEntry 14 }

rsBWMCurrentFarmRulesTable OBJECT-TYPE
    SYNTAX SEQUENCE OF RsBWMCurrentFarmRulesEntry
    ACCESS not-accessible
    STATUS  mandatory
    DESCRIPTION
      "Table containing the list of chain rules for classifer data base,
       these rules can be used to classify packets for chaining."
    ::=  {rsBWM 39}

rsBWMCurrentFarmRulesEntry OBJECT-TYPE
    SYNTAX RsBWMCurrentFarmRulesEntry
    ACCESS not-accessible
    STATUS  mandatory
    DESCRIPTION
       "The row definition for this table."
    INDEX { rsBWMCurrentFarmRulesName }
    ::=  { rsBWMCurrentFarmRulesTable 1 }

RsBWMCurrentFarmRulesEntry ::= SEQUENCE {
    rsBWMCurrentFarmRulesIndex INTEGER,
    rsBWMCurrentFarmRulesName DisplayString,
    rsBWMCurrentFarmRulesDestination DisplayString,
    rsBWMCurrentFarmRulesSource DisplayString,
    rsBWMCurrentFarmRulesDirection INTEGER,
    rsBWMCurrentFarmRulesDescription DisplayString,
    rsBWMCurrentFarmRulesPolicyType INTEGER,
    rsBWMCurrentFarmRulesPolicy DisplayString,
    rsBWMCurrentFarmRulesSpecific DisplayString,
    rsBWMCurrentFarmBandwidthLastSec Counter,
    rsBWMCurrentFarmPacketsLastSec Counter,
    rsBWMCurrentFarmRulesPhysicalPortGroup DisplayString,
    rsBWMCurrentFarmRulesVLANTagGroup DisplayString,
    rsBWMCurrentFarmRulesDSCPMarking INTEGER
}

rsBWMCurrentFarmRulesIndex OBJECT-TYPE
    SYNTAX INTEGER
    ACCESS  read-only
    STATUS  mandatory
    DESCRIPTION
       "This variable indicates the administrative index of a line it
       determine the order of the rules."
    ::=  { rsBWMCurrentFarmRulesEntry 1 }

rsBWMCurrentFarmRulesName OBJECT-TYPE
    SYNTAX DisplayString (SIZE(0..255))
    ACCESS  read-only
    STATUS  mandatory
    DESCRIPTION
      "The Name for the Rule must be unique."
    ::=  {rsBWMCurrentFarmRulesEntry 2}

rsBWMCurrentFarmRulesDestination OBJECT-TYPE
    SYNTAX DisplayString (SIZE(0..46))
    ACCESS  read-only
    STATUS  mandatory
    DESCRIPTION
      "The destination address / range of address for the packet, the name is
      defined in the Objects table or can be an IP address."
    ::=  {rsBWMCurrentFarmRulesEntry 3}

rsBWMCurrentFarmRulesSource OBJECT-TYPE
    SYNTAX DisplayString (SIZE(0..46))
    ACCESS  read-only
    STATUS  mandatory
    DESCRIPTION
      "The source address / range of address for the packet, the name is
      defined in the Objects table or can be an IP address."
    ::=  {rsBWMCurrentFarmRulesEntry 4}

rsBWMCurrentFarmRulesDirection OBJECT-TYPE
    SYNTAX INTEGER {
              oneway(1),
              twoway(2) }
    ACCESS read-only
    STATUS mandatory
    DESCRIPTION
       "This variable indicates the direction of the incoming packet."
    ::=  { rsBWMCurrentFarmRulesEntry 5 }

rsBWMCurrentFarmRulesDescription OBJECT-TYPE
    SYNTAX DisplayString (SIZE(0..19))
    ACCESS  read-only
    STATUS  mandatory
    DESCRIPTION
      "Description."
    ::=  { rsBWMCurrentFarmRulesEntry 6 }

rsBWMCurrentFarmRulesPolicyType OBJECT-TYPE
    SYNTAX INTEGER {
              none(1),
              filter(2),
              group(3),
              policy(4)}
    ACCESS  read-only
    STATUS  mandatory
    DESCRIPTION
       "The type of policy - i.e. if this is a filter, group or policy."
    DEFVAL  { 1 }
    ::=  { rsBWMCurrentFarmRulesEntry 7 }

rsBWMCurrentFarmRulesPolicy OBJECT-TYPE
    SYNTAX DisplayString (SIZE(0..29))
    ACCESS  read-only
    STATUS  mandatory
    DESCRIPTION
       "The name for the filter policy for the rule."
    ::=  { rsBWMCurrentFarmRulesEntry 8 }

rsBWMCurrentFarmRulesSpecific OBJECT-TYPE
    SYNTAX DisplayString (SIZE(0..19))
    ACCESS  read-only
    STATUS  mandatory
    DESCRIPTION
       "This variable indicates if there is additional data to the
       policy."
    ::= { rsBWMCurrentFarmRulesEntry 9 }

rsBWMCurrentFarmBandwidthLastSec OBJECT-TYPE
    SYNTAX Counter
    ACCESS  read-only
    STATUS  mandatory
    DESCRIPTION
       "The bandwidth used by the policy in the last second."
    ::=  {rsBWMCurrentFarmRulesEntry 10}

rsBWMCurrentFarmPacketsLastSec OBJECT-TYPE
    SYNTAX Counter
    ACCESS  read-only
    STATUS  mandatory
    DESCRIPTION
       "The packets that matched the policy in the last second."
    ::=  {rsBWMCurrentFarmRulesEntry 11}

rsBWMCurrentFarmRulesPhysicalPortGroup OBJECT-TYPE
    SYNTAX DisplayString (SIZE(0..19))
    ACCESS  read-only
    STATUS  mandatory
    DESCRIPTION
       "This name of the physical port group for this rule."
    ::=  { rsBWMCurrentFarmRulesEntry 12 }

rsBWMCurrentFarmRulesVLANTagGroup OBJECT-TYPE
    SYNTAX DisplayString (SIZE(0..19))
    ACCESS  read-only
    STATUS  mandatory
    DESCRIPTION
        "The name of the VLAN tag group for this rule."
    ::=  { rsBWMCurrentFarmRulesEntry 13 }

rsBWMCurrentFarmRulesDSCPMarking OBJECT-TYPE
    SYNTAX INTEGER (-1 | 0..63)
    ACCESS  read-only
    STATUS  mandatory
    DESCRIPTION
       "This variable indicates the DSCP value to mark the ToS field in the IP header
        in the matching packets. If equals -1, the marking is not performed."
    ::= { rsBWMCurrentFarmRulesEntry 14 }

rsBWMDynamicNetworkTuning OBJECT IDENTIFIER ::= { rsBWMTuning 12 }

rsBWMDynamicNetworkEntries OBJECT-TYPE
    SYNTAX INTEGER
    ACCESS  read-only
    STATUS  mandatory
    DESCRIPTION
      "Maximum number of dynamic network entries."
    ::= { rsBWMDynamicNetworkTuning 1 }

rsBWMDynamicNetworkEntriesAfterReset OBJECT-TYPE
    SYNTAX INTEGER
    ACCESS  read-write
    STATUS  mandatory
    DESCRIPTION
      "Future maximum maximum number of dynamic network entries."
    ::=  { rsBWMDynamicNetworkTuning 2 }

rsBWMDynamicNetworkIPTuning OBJECT IDENTIFIER ::= { rsBWMTuning 13 }

rsBWMDynamicNetworkIPHashEntries OBJECT-TYPE
    SYNTAX INTEGER
    ACCESS  read-only
    STATUS  mandatory
    DESCRIPTION
      "Maximum number of entries in discrete IPs hash per dynamic network."
    ::= { rsBWMDynamicNetworkIPTuning 1 }

rsBWMDynamicNetworkIPHashEntriesAfterReset OBJECT-TYPE
    SYNTAX INTEGER
    ACCESS  read-write
    STATUS  mandatory
    DESCRIPTION
      "Future maximum maximum number of entries in discrete IPs hash per dynamic network."
    ::=  { rsBWMDynamicNetworkIPTuning 2 }

rsBWMDynamicNetworkRangeTuning OBJECT IDENTIFIER ::= { rsBWMTuning 14 }

rsBWMDynamicNetworkRangeEntries OBJECT-TYPE
    SYNTAX INTEGER
    ACCESS  read-only
    STATUS  mandatory
    DESCRIPTION
      "Maximum number of ranges per dynamic network."
    ::= { rsBWMDynamicNetworkRangeTuning 1 }

rsBWMDynamicNetworkRangeEntriesAfterReset OBJECT-TYPE
    SYNTAX INTEGER
    ACCESS  read-write
    STATUS  mandatory
    DESCRIPTION
      "Future maximum maximum number of ranges per dynamic network."
    ::=  { rsBWMDynamicNetworkRangeTuning 2 }

rsBWMOMPCHashTableOffset OBJECT-TYPE
    SYNTAX INTEGER
    ACCESS  read-write
    STATUS  mandatory
    DESCRIPTION "The offset of the OMPC hash table."
    ::= {rsBWM 40}

rsBWMOMPCHashTableMask OBJECT-TYPE
    SYNTAX OCTET STRING
    ACCESS  read-write
    STATUS  mandatory
    DESCRIPTION "The mask of the OMPC hash table."
    ::= {rsBWM 41}

rsBWMNoSaveMode OBJECT-TYPE
    SYNTAX INTEGER {
        enable(1),
        disable(2)
    }
    ACCESS  read-write
    STATUS  mandatory
    DESCRIPTION "Indicates if BWM data structures are stored in CDB (disable) or in cdbbuf(enable)."
    DEFVAL  {disable}
    ::= {rsBWM 42}


rsBWMStringSearchMode OBJECT-TYPE
    SYNTAX INTEGER {
        regular(1),
        parallel(2)
    }
    ACCESS  read-write
    STATUS  mandatory
    DESCRIPTION "Indicates if regular string search is used in the content module."
    ::= {rsBWM 46}

rsBWMMacGroupTuning OBJECT IDENTIFIER ::= { rsBWMTuning 15 }

rsBWMMacGroupEntries OBJECT-TYPE
    SYNTAX INTEGER
    ACCESS  read-only
    STATUS  mandatory
    DESCRIPTION
      "Maximum number of MAC address groups."
    ::= { rsBWMMacGroupTuning 1 }

rsBWMMacGroupEntriesAfterReset OBJECT-TYPE
    SYNTAX INTEGER
    ACCESS  read-write
    STATUS  mandatory
    DESCRIPTION
      "Future maximum number of MAC address groups."
    ::=  { rsBWMMacGroupTuning 2 }

rsBWMParallelStringSearchMemoryTuning OBJECT IDENTIFIER ::= { rsBWMTuning 18 }

rsBWMParallelStringSearchMemory OBJECT-TYPE
    SYNTAX INTEGER
    ACCESS  read-only
    STATUS  mandatory
    DESCRIPTION
      "Maximum memory size for Parallel String Search."
    ::= { rsBWMParallelStringSearchMemoryTuning 1 }

rsBWMParallelStringSearchMemoryAfterReset OBJECT-TYPE
    SYNTAX INTEGER
    ACCESS  read-write
    STATUS  mandatory
    DESCRIPTION
      "Future maximum memory size for Parallel String Search."
    ::=  { rsBWMParallelStringSearchMemoryTuning 2 }

rsBWMTrafficFlowBWTuning OBJECT IDENTIFIER ::= { rsBWMTuning 19 }

rsBWMTrafficFlowBWEntries OBJECT-TYPE
    SYNTAX INTEGER
    ACCESS  read-only
    STATUS  mandatory
    DESCRIPTION
      "Maximum number of entries in the table that keeps track of  sessions for BW per Traffic Flow Support."
    ::= { rsBWMTrafficFlowBWTuning 1 }

rsBWMTrafficFlowBWEntriesAfterReset OBJECT-TYPE
    SYNTAX INTEGER
    ACCESS  read-write
    STATUS  mandatory
    DESCRIPTION
      "Future maximum number of entries in the table that keeps track of  sessions for BW per Traffic Flow Support.."
    ::=  { rsBWMTrafficFlowBWTuning 2 }

rsBWMVLANTagGroupTable OBJECT-TYPE
    SYNTAX SEQUENCE OF RsBWMVLANTagGroupEntry
    ACCESS not-accessible
    STATUS  mandatory
    DESCRIPTION
        "Table for VLAN tag groups."
    ::=  {rsBWM 47}

rsBWMVLANTagGroupEntry OBJECT-TYPE
    SYNTAX RsBWMVLANTagGroupEntry
    ACCESS not-accessible
    STATUS  mandatory
    DESCRIPTION
        "The row definition for this table."
    INDEX { rsBWMVLANTagGroupName, 
            rsBWMVLANTagGroupVLANTag, 
            rsBWMVLANTagGroupVLANTagFrom }
    ::=  { rsBWMVLANTagGroupTable  1}

RsBWMVLANTagGroupEntry ::= SEQUENCE {
    rsBWMVLANTagGroupName DisplayString,
    rsBWMVLANTagGroupVLANTag INTEGER,
    rsBWMVLANTagGroupVLANTagFrom INTEGER,
    rsBWMVLANTagGroupVLANTagTo INTEGER,
    rsBWMVLANTagGroupMode INTEGER,
    rsBWMVLANTagGroupStatus RowStatus
}

rsBWMVLANTagGroupName OBJECT-TYPE
    SYNTAX DisplayString (SIZE(0..19))
    ACCESS  read-only
    STATUS  mandatory
    DESCRIPTION
        "The name of the VLAN tag group."
    ::=  { rsBWMVLANTagGroupEntry  1}

rsBWMVLANTagGroupVLANTag OBJECT-TYPE
    SYNTAX INTEGER
    ACCESS  read-only
    STATUS  mandatory
    DESCRIPTION
        "The value of VLAN tag in discrete mode."
    ::=  { rsBWMVLANTagGroupEntry  2}

rsBWMVLANTagGroupVLANTagFrom OBJECT-TYPE
    SYNTAX INTEGER
    ACCESS  read-only
    STATUS  mandatory
    DESCRIPTION
        "The 'from' part of the VLAN tag range."
    ::=  { rsBWMVLANTagGroupEntry  3}

rsBWMVLANTagGroupVLANTagTo OBJECT-TYPE
    SYNTAX INTEGER
    ACCESS  read-write
    STATUS  mandatory
    DESCRIPTION
        "The 'to' part of the VLAN tag range."
    DEFVAL { 65536 }
    ::=  { rsBWMVLANTagGroupEntry  4}

rsBWMVLANTagGroupMode OBJECT-TYPE
    SYNTAX INTEGER {
        discrete(1),
        range(2)
    }
    ACCESS  read-write
    STATUS  mandatory
    DESCRIPTION
        "The mode of the VLAN tag group: discrete or range."
    DEFVAL { discrete }
    ::=  { rsBWMVLANTagGroupEntry  5}

rsBWMVLANTagGroupStatus OBJECT-TYPE
    SYNTAX RowStatus
    ACCESS  read-write
    STATUS  mandatory
    DESCRIPTION
        "The row status of the entry."
    ::=  { rsBWMVLANTagGroupEntry  6}

rsBWMCurrentVLANTagGroupTable OBJECT-TYPE
    SYNTAX SEQUENCE OF RsBWMCurrentVLANTagGroupEntry
    ACCESS not-accessible
    STATUS  mandatory
    DESCRIPTION
        "Current table for VLAN tag groups."
    ::=  {rsBWM 48}

rsBWMCurrentVLANTagGroupEntry OBJECT-TYPE
    SYNTAX RsBWMCurrentVLANTagGroupEntry
    ACCESS not-accessible
    STATUS  mandatory
    DESCRIPTION
        "The row definition for this table."
    INDEX { rsBWMCurrentVLANTagGroupName, 
            rsBWMCurrentVLANTagGroupVLANTag, 
            rsBWMCurrentVLANTagGroupVLANTagFrom }
    ::=  { rsBWMCurrentVLANTagGroupTable  1}

RsBWMCurrentVLANTagGroupEntry ::= SEQUENCE {
    rsBWMCurrentVLANTagGroupName DisplayString,
    rsBWMCurrentVLANTagGroupVLANTag INTEGER,
    rsBWMCurrentVLANTagGroupVLANTagFrom INTEGER,
    rsBWMCurrentVLANTagGroupVLANTagTo INTEGER,
    rsBWMCurrentVLANTagGroupMode INTEGER
}

rsBWMCurrentVLANTagGroupName OBJECT-TYPE
    SYNTAX DisplayString (SIZE(0..19))
    ACCESS  read-only
    STATUS  mandatory
    DESCRIPTION
        "The name of the VLAN tag group."
    ::=  { rsBWMCurrentVLANTagGroupEntry  1}

rsBWMCurrentVLANTagGroupVLANTag OBJECT-TYPE
    SYNTAX INTEGER
    ACCESS  read-only
    STATUS  mandatory
    DESCRIPTION
        "The value of VLAN tag in discrete mode."
    ::=  { rsBWMCurrentVLANTagGroupEntry  2}

rsBWMCurrentVLANTagGroupVLANTagFrom OBJECT-TYPE
    SYNTAX INTEGER
    ACCESS  read-only
    STATUS  mandatory
    DESCRIPTION
        "The 'from' part of the VLAN tag range."
    ::=  { rsBWMCurrentVLANTagGroupEntry  3}

rsBWMCurrentVLANTagGroupVLANTagTo OBJECT-TYPE
    SYNTAX INTEGER
    ACCESS  read-only
    STATUS  mandatory
    DESCRIPTION
        "The 'to' part of the VLAN tag range."
    ::=  { rsBWMCurrentVLANTagGroupEntry  4}

rsBWMCurrentVLANTagGroupMode OBJECT-TYPE
    SYNTAX INTEGER {
    discrete(1),
    range(2)
    }
    ACCESS  read-only
    STATUS  mandatory
    DESCRIPTION
        "The mode of the VLAN tag group: discrete or range."
    ::=  { rsBWMCurrentVLANTagGroupEntry  5}

rsBWMMacGroupTable OBJECT-TYPE
    SYNTAX SEQUENCE OF RsBWMMacGroupEntry
    ACCESS not-accessible
    STATUS  mandatory
    DESCRIPTION
      "Table containing the groups of MAC addresses."
    ::=  {rsBWM 49}

rsBWMMacGroupEntry OBJECT-TYPE
    SYNTAX RsBWMMacGroupEntry
    ACCESS not-accessible
    STATUS  mandatory
    DESCRIPTION
       "The row definition for this table."
    INDEX {rsBWMMacGroupEntryName,
           rsBWMMacGroupEntryAddress}
    ::=  { rsBWMMacGroupTable 1 }

RsBWMMacGroupEntry ::= SEQUENCE {
    rsBWMMacGroupEntryName DisplayString,
    rsBWMMacGroupEntryAddress MacAddress,
    rsBWMMacGroupEntryStatus RowStatus
}

rsBWMMacGroupEntryName OBJECT-TYPE
    SYNTAX DisplayString (SIZE(0..19))
    ACCESS  read-only
    STATUS  mandatory
    DESCRIPTION
      "The Name for the MACs group."
    ::=  { rsBWMMacGroupEntry 1 }

rsBWMMacGroupEntryAddress OBJECT-TYPE
    SYNTAX MacAddress
    ACCESS  read-only
    STATUS  mandatory
    DESCRIPTION
      "the MAC address in the group."
    ::=  { rsBWMMacGroupEntry 2 }

rsBWMMacGroupEntryStatus OBJECT-TYPE
    SYNTAX RowStatus
    ACCESS  read-write
    STATUS  mandatory
    DESCRIPTION
       "This variable indicates the administrative status of this entry.
        Used to delete an entry of this table."
    ::=  { rsBWMMacGroupEntry 3 }


rsBWMMacGroupCurrentTable OBJECT-TYPE
    SYNTAX SEQUENCE OF RsBWMMacGroupCurrentEntry
    ACCESS not-accessible
    STATUS  mandatory
    DESCRIPTION
      "Table containing the current groups of MAC addresses."
    ::=  {rsBWM 50}

rsBWMMacGroupCurrentEntry OBJECT-TYPE
    SYNTAX RsBWMMacGroupCurrentEntry
    ACCESS not-accessible
    STATUS  mandatory
    DESCRIPTION
       "The row definition for this table."
    INDEX {rsBWMMacGroupCurrentEntryName,
           rsBWMMacGroupCurrentEntryAddress}
    ::=  { rsBWMMacGroupCurrentTable 1 }

RsBWMMacGroupCurrentEntry ::= SEQUENCE {
    rsBWMMacGroupCurrentEntryName DisplayString,
    rsBWMMacGroupCurrentEntryAddress MacAddress
}

rsBWMMacGroupCurrentEntryName OBJECT-TYPE
    SYNTAX DisplayString (SIZE(0..19))
    ACCESS  read-only
    STATUS  mandatory
    DESCRIPTION
      "The Name for the MACs group."
    ::=  { rsBWMMacGroupCurrentEntry 1 }

rsBWMMacGroupCurrentEntryAddress OBJECT-TYPE
    SYNTAX MacAddress
    ACCESS  read-only
    STATUS  mandatory
    DESCRIPTION
      "the MAC address in the group."
    ::=  { rsBWMMacGroupCurrentEntry 2 }

rsBWMQueueSize OBJECT-TYPE
    SYNTAX INTEGER
    ACCESS  read-write
    STATUS  mandatory
    DESCRIPTION
        "Enables the user to configure the queue size"
    DEFVAL  { 512 }
    ::=  {rsBWM 51}

rsBWMTrafficFlowBWAgingTime OBJECT-TYPE
    SYNTAX INTEGER
    ACCESS  read-write
    STATUS  mandatory
    DESCRIPTION
        "The aging time for the traffic flow BW table. After this number of seconds without activity, the session is deleted."
    ::= {rsBWM 52}

rsBWMServiceTable OBJECT-TYPE
    SYNTAX SEQUENCE OF RsBWMServiceEntry
    ACCESS not-accessible
    STATUS  mandatory
    DESCRIPTION
      "Table containing the available services."
    ::=  {rsBWM 53}

rsBWMServiceEntry OBJECT-TYPE
    SYNTAX RsBWMServiceEntry
    ACCESS not-accessible
    STATUS  mandatory
    DESCRIPTION
       "The row definition for this table."
    INDEX {rsBWMServiceTableType, 
           rsBWMServiceType, 
           rsBWMServiceName}
    ::=  {rsBWMServiceTable 1}

RsBWMServiceEntry ::= SEQUENCE {
    rsBWMServiceTableType INTEGER,
    rsBWMServiceType INTEGER,
    rsBWMServiceName DisplayString
}

rsBWMServiceTableType OBJECT-TYPE
    SYNTAX INTEGER {
        filterActive (1),
        filterModify (2),
        advancedActive (3),
        advancedModify (4),
        groupActive (5),
        groupModify (6)
    }
    ACCESS  read-only
    STATUS  mandatory
    DESCRIPTION
      "The specific table to access."
    ::=  {rsBWMServiceEntry 1}

rsBWMServiceType OBJECT-TYPE
    SYNTAX INTEGER {
        regular (1),
        static (2),
        ids (3),
        idsStatic (4)
    }
    ACCESS read-only
    STATUS  mandatory
    DESCRIPTION
       "The type of entry. ids and idsStatic are obsolete."
    ::=  {rsBWMServiceEntry 2}

rsBWMServiceName OBJECT-TYPE
    SYNTAX DisplayString (SIZE(0..29))
    ACCESS read-only
    STATUS mandatory
    DESCRIPTION
      "The filter or advanced or group name (of type rsBWMServiceType)."
    ::=  {rsBWMServiceEntry 3}

rsBWMPolicyGroupTable OBJECT-TYPE
    SYNTAX SEQUENCE OF RsBWMPolicyGroupEntry
    ACCESS not-accessible
    STATUS  mandatory
    DESCRIPTION
      "Table containing the available Policy groups."
    ::=  {rsBWM 54}

rsBWMPolicyGroupEntry OBJECT-TYPE
    SYNTAX RsBWMPolicyGroupEntry
    ACCESS not-accessible
    STATUS  mandatory
    DESCRIPTION
       "The row definition for this table."
    INDEX {rsBWMPolicyGroupEntryName}
    ::=  { rsBWMPolicyGroupTable 1 }

RsBWMPolicyGroupEntry ::= SEQUENCE {
    rsBWMPolicyGroupEntryName DisplayString,
    rsBWMPolicyGroupEntryStatus RowStatus
}

rsBWMPolicyGroupEntryName OBJECT-TYPE
    SYNTAX DisplayString (SIZE(0..19))
    ACCESS  read-only
    STATUS  mandatory
    DESCRIPTION
      "The Name for the Policy group."
    ::=  { rsBWMPolicyGroupEntry 1 }

rsBWMPolicyGroupEntryStatus OBJECT-TYPE
    SYNTAX RowStatus
    ACCESS  read-write
    STATUS  mandatory
    DESCRIPTION
       "This variable indicates the administrative status of this entry.
        Used to delete an entry of this table."
    ::=  { rsBWMPolicyGroupEntry 2 }

rsBWMPolicyGroupCurrentTable OBJECT-TYPE
    SYNTAX SEQUENCE OF RsBWMPolicyGroupCurrentEntry
    ACCESS not-accessible
    STATUS  mandatory
    DESCRIPTION
      "Table containing the current groups of classes."
    ::=  {rsBWM 55}

rsBWMPolicyGroupCurrentEntry OBJECT-TYPE
    SYNTAX RsBWMPolicyGroupCurrentEntry
    ACCESS not-accessible
    STATUS  mandatory
    DESCRIPTION
       "The row definition for this table."
    INDEX {rsBWMPolicyGroupCurrentEntryName}
    ::=  { rsBWMPolicyGroupCurrentTable 1 }

RsBWMPolicyGroupCurrentEntry ::= SEQUENCE {
    rsBWMPolicyGroupCurrentEntryName DisplayString
}

rsBWMPolicyGroupCurrentEntryName OBJECT-TYPE
    SYNTAX DisplayString (SIZE(0..19))
    ACCESS  read-only
    STATUS  mandatory
    DESCRIPTION
      "The Name for the Classs group."
    ::=  { rsBWMPolicyGroupCurrentEntry 1 }

rsBWMAppPortGroupEntryTable OBJECT-TYPE
    SYNTAX SEQUENCE OF RsBWMAppPortGroupEntry
    ACCESS not-accessible
    STATUS mandatory
    DESCRIPTION
      "Table containing the application port range."
    ::= { rsBWM 56 }

rsBWMAppPortGroupEntry OBJECT-TYPE
    SYNTAX RsBWMAppPortGroupEntry
    ACCESS not-accessible
    STATUS mandatory
    DESCRIPTION
       "The row definition for this table."
    INDEX { rsBWMAppPortGroupName, 
            rsBWMAppPortGroupFromPort, 
            rsBWMAppPortGroupToPort}
    ::=  { rsBWMAppPortGroupEntryTable 1 }

RsBWMAppPortGroupEntry ::= SEQUENCE {
    rsBWMAppPortGroupName DisplayString,
    rsBWMAppPortGroupFromPort INTEGER,
    rsBWMAppPortGroupToPort INTEGER,
    rsBWMAppPortGroupType INTEGER,
    rsBWMAppPortGroupStatus RowStatus
}

rsBWMAppPortGroupName OBJECT-TYPE
    SYNTAX DisplayString (SIZE(0..29))
    ACCESS read-write
    STATUS mandatory
    DESCRIPTION
      "The name of the application port range object."
    ::=  { rsBWMAppPortGroupEntry 1 }

rsBWMAppPortGroupFromPort OBJECT-TYPE
    SYNTAX INTEGER
    ACCESS read-write
    STATUS mandatory
    DESCRIPTION
      "The starting port."
    ::=  { rsBWMAppPortGroupEntry 2 }

rsBWMAppPortGroupToPort OBJECT-TYPE
    SYNTAX INTEGER
    ACCESS read-write
    STATUS mandatory
    DESCRIPTION
       "The last valid port."
    ::=  { rsBWMAppPortGroupEntry 3 }

rsBWMAppPortGroupType OBJECT-TYPE
    SYNTAX INTEGER {
        regular (1),
        static (2)
    }
    ACCESS read-write
    STATUS  mandatory
    DESCRIPTION
      "The type of object. This can be regular (user defined) or static
      (defined by the application)."
    DEFVAL { 1 }
    ::=  { rsBWMAppPortGroupEntry 4 }

rsBWMAppPortGroupStatus OBJECT-TYPE
    SYNTAX RowStatus
    ACCESS read-write
    STATUS mandatory
    DESCRIPTION
      "The status of the object."
    ::=  { rsBWMAppPortGroupEntry 5 }

rsBWMCurrentAppPortGroupEntryTable OBJECT-TYPE
    SYNTAX SEQUENCE OF RsBWMCurrentAppPortGroupEntry
    ACCESS not-accessible
    STATUS  mandatory
    DESCRIPTION
      "Table containing the application port range."
    ::= { rsBWM 57 }

rsBWMCurrentAppPortGroupEntry OBJECT-TYPE
    SYNTAX RsBWMCurrentAppPortGroupEntry
    ACCESS not-accessible
    STATUS mandatory
    DESCRIPTION
       "The row definition for this table."
    INDEX { rsBWMCurrentAppPortGroupName, 
            rsBWMCurrentAppPortGroupFromPort, 
            rsBWMCurrentAppPortGroupToPort}
    ::=  { rsBWMCurrentAppPortGroupEntryTable 1 }

RsBWMCurrentAppPortGroupEntry ::= SEQUENCE {
    rsBWMCurrentAppPortGroupName DisplayString,
    rsBWMCurrentAppPortGroupFromPort INTEGER,
    rsBWMCurrentAppPortGroupToPort INTEGER,
    rsBWMCurrentAppPortGroupType INTEGER
}

rsBWMCurrentAppPortGroupName OBJECT-TYPE
    SYNTAX DisplayString (SIZE(0..29))
    ACCESS read-only
    STATUS mandatory
    DESCRIPTION
      "The name of the application port range object."
    ::=  { rsBWMCurrentAppPortGroupEntry 1 }

rsBWMCurrentAppPortGroupFromPort OBJECT-TYPE
    SYNTAX INTEGER
    ACCESS read-only
    STATUS mandatory
    DESCRIPTION
      "The starting port."
    ::=  { rsBWMCurrentAppPortGroupEntry 2 }

rsBWMCurrentAppPortGroupToPort OBJECT-TYPE
    SYNTAX INTEGER
    ACCESS read-only
    STATUS mandatory
    DESCRIPTION
       "The last valid port."
    ::=  { rsBWMCurrentAppPortGroupEntry 3 }

rsBWMCurrentAppPortGroupType OBJECT-TYPE
    SYNTAX INTEGER {
        regular (1),
        static (2)
    }
    ACCESS read-only
    STATUS mandatory
    DESCRIPTION
      "The type of object. This can be regular (user defined) or static
      (defined by the application)."
    ::=  { rsBWMCurrentAppPortGroupEntry 4 }

rsBWMAppPortGroupTuning OBJECT IDENTIFIER ::= { rsBWMTuning 20 }

rsBWMAppPortGroupTuningEntries OBJECT-TYPE
    SYNTAX INTEGER
    ACCESS  read-only
    STATUS  mandatory
    DESCRIPTION
      "Maximum number of entries in application ports table."
    ::= { rsBWMAppPortGroupTuning 1 }

rsBWMAppPortGroupTuningEntriesAfterReset OBJECT-TYPE
    SYNTAX INTEGER
    ACCESS  read-write
    STATUS  mandatory
    DESCRIPTION
      "Future Maximum number of entries in application ports table."
    ::= { rsBWMAppPortGroupTuning 2 }

rsBWMDefaultGatewayClassificatiomMode OBJECT-TYPE
    SYNTAX INTEGER {
        enable (1),
        disable (2)
    }
    ACCESS  read-write
    STATUS  mandatory
    DESCRIPTION
        "If enabled, BWM classification will be performed only on traffic to/from 
		the configured default gateway."
    ::= { rsBWM 58 }

rsBWMFarmsClassifyListsTuning OBJECT IDENTIFIER ::= { rsBWMTuning 21 }

rsBWMFarmsClassifyListsTuningEntries OBJECT-TYPE
    SYNTAX INTEGER
    ACCESS  read-only
    STATUS  mandatory
    DESCRIPTION
      "Maximum number of entries in the farms classification lists table (each entry holds the relevant BWM policies for a pair of farms)."
    ::= { rsBWMFarmsClassifyListsTuning 1 }

rsBWMFarmsClassifyListsTuningEntriesAfterReset OBJECT-TYPE
    SYNTAX INTEGER
    ACCESS  read-write
    STATUS  mandatory
    DESCRIPTION
      "Future maximum number of entries in the farms classification lists table."
    ::= { rsBWMFarmsClassifyListsTuning 2 }

rsBWMExtRulesTable OBJECT-TYPE
    SYNTAX SEQUENCE OF RsBWMExtRulesEntry
    ACCESS not-accessible
    STATUS  mandatory
    DESCRIPTION
      "Table containing the extended list of rules for classifer data base"
    ::= { rsBWM 59 }

rsBWMExtRulesEntry OBJECT-TYPE
    SYNTAX RsBWMExtRulesEntry
    ACCESS not-accessible
    STATUS  mandatory
    DESCRIPTION
       "The row definition for this table."
    INDEX { rsBWMExtRulesName }
    ::= { rsBWMExtRulesTable 1 }

RsBWMExtRulesEntry ::= SEQUENCE {
    rsBWMExtRulesName DisplayString,
    rsBWMExtRulesFromFarm DisplayString,
    rsBWMExtRulesToFarm DisplayString,
    rsBWMExtRulesClassificationPoint INTEGER,
    rsBWMExtRulesTrafficIdentification INTEGER,
    rsBWMExtRulesTrafficFlowMaxBW INTEGER,
    rsBWMExtRulesMaxConcurrentSessions INTEGER,
    rsBWMExtRulesMaxRqstsPerSec INTEGER,
    rsBWMExtRulesTrafficIDCookieField DisplayString,
    rsBWMExtRulesStatus RowStatus,
    rsBWMExtRulesActivate DisplayString,
    rsBWMExtRulesInactivate DisplayString,
    rsBWMExtRulesForceBestFit INTEGER,
    rsBWMExtRulesPacketMarkingType INTEGER,
    rsBWMExtRulesPacketMarkingValue INTEGER,
    rsBWMExtRulesReportMaxBw INTEGER
}

rsBWMExtRulesName OBJECT-TYPE
    SYNTAX DisplayString (SIZE(0..255))
    ACCESS  read-only
    STATUS  mandatory
    DESCRIPTION
      "The Name for the Rule must be unique."
    ::= { rsBWMExtRulesEntry 1 }

rsBWMExtRulesFromFarm OBJECT-TYPE
    SYNTAX DisplayString (SIZE(0..19))
    ACCESS  read-write
    STATUS  mandatory
    DESCRIPTION
        "The source farm of the packet for classification."
    ::= { rsBWMExtRulesEntry 2 }

rsBWMExtRulesToFarm OBJECT-TYPE
    SYNTAX DisplayString (SIZE(0..19))
    ACCESS  read-write
    STATUS  mandatory
    DESCRIPTION
        "The destination farm of the packet for classification."
    ::= { rsBWMExtRulesEntry 3 }

rsBWMExtRulesClassificationPoint OBJECT-TYPE
    SYNTAX INTEGER {
        beforeChanges (1),
        afterChanges (2)
    }
    ACCESS  read-write
    STATUS  mandatory
    DESCRIPTION
        "Whether the classification will be performed on the original packet, or on the packet 
         after all changes."
    DEFVAL { 2 }
    ::= { rsBWMExtRulesEntry 4 }

rsBWMExtRulesTrafficIdentification OBJECT-TYPE
    SYNTAX INTEGER {
        none (0),
        client (1),
        session (2),
        connection (3),
        fullL4Session (4),
        sessionCookie (5),
        sipCallID (6)
    }
    ACCESS  read-write
    STATUS  mandatory
    DESCRIPTION
        "This variable indicates how a traffic flow is defined for this policy."
    ::= { rsBWMExtRulesEntry 5 }

rsBWMExtRulesTrafficFlowMaxBW OBJECT-TYPE
    SYNTAX INTEGER
    ACCESS  read-write
    STATUS  mandatory
    DESCRIPTION
        "Maximum bandwidth allocated for a certain traffic flow (session) that match this rule."
    ::= { rsBWMExtRulesEntry 6 }

rsBWMExtRulesMaxConcurrentSessions OBJECT-TYPE
    SYNTAX INTEGER
    ACCESS  read-write
    STATUS  mandatory
    DESCRIPTION
        "Maximum number of sessions that can be open simultaneously per traffic flow."
    ::= { rsBWMExtRulesEntry 7 }

rsBWMExtRulesMaxRqstsPerSec OBJECT-TYPE
    SYNTAX INTEGER
    ACCESS  read-write
    STATUS  mandatory
    DESCRIPTION
        "Maximum number of http requests that will be forwarded in a second for each traffic flow."
    ::= { rsBWMExtRulesEntry 8 }

rsBWMExtRulesTrafficIDCookieField OBJECT-TYPE
    SYNTAX DisplayString (SIZE(0..19))
    ACCESS  read-write
    STATUS  mandatory
    DESCRIPTION
        "The name of cookie field for Traafic Flow ID by cookie."
    ::= { rsBWMExtRulesEntry 9 }

rsBWMExtRulesStatus OBJECT-TYPE
    SYNTAX RowStatus
    ACCESS  read-write
    STATUS  mandatory
    DESCRIPTION
       "This variable indicates the administrative status of this entry.
        Used to delete an entry of this table."
    ::=  { rsBWMExtRulesEntry 10 }

rsBWMExtRulesActivate OBJECT-TYPE
    SYNTAX DisplayString (SIZE(0..29))
    ACCESS  read-write
    STATUS  mandatory
    DESCRIPTION
        "The name of the schedule that will activate the policy."
    ::= { rsBWMExtRulesEntry 11 }

rsBWMExtRulesInactivate OBJECT-TYPE
    SYNTAX DisplayString (SIZE(0..29))
    ACCESS  read-write
    STATUS  mandatory
    DESCRIPTION
        "The name of the schedule that will inactivate the policy."
    ::= { rsBWMExtRulesEntry 12 }

rsBWMExtRulesForceBestFit OBJECT-TYPE
    SYNTAX INTEGER {
	false(0),
	true(1)
    }
    ACCESS  read-write
    STATUS  mandatory
    DESCRIPTION
        "Whether to force session best fit on the policy while classification."
    ::= { rsBWMExtRulesEntry 13 }

rsBWMExtRulesPacketMarkingType OBJECT-TYPE
    SYNTAX INTEGER {
	none(1),
	dscp(2),
	tos(3)
    }
    ACCESS  read-write
    STATUS  mandatory
    DESCRIPTION
        "Type of packet marking for packets matching this policy. DSCP marking will set 6 low bits 
		 Tos marking will set bits 3-6."
    ::= { rsBWMExtRulesEntry 14 }

rsBWMExtRulesPacketMarkingValue OBJECT-TYPE
    SYNTAX INTEGER (-1 | 0..63)
    ACCESS  read-write
    STATUS  mandatory
    DESCRIPTION
        "Value of packet marking in the TOS field of the ip header. For DSCP 
        marking value should be 0-63. For TOS it should be 0-7"
    ::= { rsBWMExtRulesEntry 15 }

rsBWMExtRulesReportMaxBw OBJECT-TYPE
    SYNTAX INTEGER {
	false(0),
	true(1)
    }
    ACCESS  read-write
    STATUS  mandatory
    DESCRIPTION
        "Whether to report when the policy discards packets becasue of max bw limitations."
    ::= { rsBWMExtRulesEntry 16 }

rsBWMCurrentExtRulesTable OBJECT-TYPE
    SYNTAX SEQUENCE OF RsBWMCurrentExtRulesEntry
    ACCESS not-accessible
    STATUS  mandatory
    DESCRIPTION
      "Table containing the extended list of rules for classifer data base"
    ::= { rsBWM 60 }

rsBWMCurrentExtRulesEntry OBJECT-TYPE
    SYNTAX RsBWMCurrentExtRulesEntry
    ACCESS not-accessible
    STATUS  mandatory
    DESCRIPTION
       "The row definition for this table."
    INDEX { rsBWMCurrentExtRulesName }
    ::= { rsBWMCurrentExtRulesTable 1 }

RsBWMCurrentExtRulesEntry ::= SEQUENCE {
    rsBWMCurrentExtRulesName DisplayString,
    rsBWMCurrentExtRulesFromFarm DisplayString,
    rsBWMCurrentExtRulesToFarm DisplayString,
    rsBWMCurrentExtRulesClassificationPoint INTEGER,
    rsBWMCurrentExtRulesTrafficIdentification INTEGER,
    rsBWMCurrentExtRulesTrafficFlowMaxBW INTEGER,
    rsBWMCurrentExtRulesMaxConcurrentSessions INTEGER,
    rsBWMCurrentExtRulesMaxRqstsPerSec INTEGER,
    rsBWMCurrentExtRulesTrafficIDCookieField DisplayString,
    rsBWMCurrentExtRulesActivate DisplayString,
    rsBWMCurrentExtRulesInactivate DisplayString,
    rsBWMCurrentExtRulesForceBestFit INTEGER,
    rsBWMCurrentExtRulesPacketMarkingType INTEGER,
    rsBWMCurrentExtRulesPacketMarkingValue INTEGER,
    rsBWMCurrentExtRulesReportMaxBw INTEGER
}

rsBWMCurrentExtRulesName OBJECT-TYPE
    SYNTAX DisplayString (SIZE(0..255))
    ACCESS  read-only
    STATUS  mandatory
    DESCRIPTION
      "The Name for the Rule must be unique."
    ::= { rsBWMCurrentExtRulesEntry 1 }

rsBWMCurrentExtRulesFromFarm OBJECT-TYPE
    SYNTAX DisplayString (SIZE(0..19))
    ACCESS  read-only
    STATUS  mandatory
    DESCRIPTION
        "The source farm of the packet for classification."
    ::= { rsBWMCurrentExtRulesEntry 2 }

rsBWMCurrentExtRulesToFarm OBJECT-TYPE
    SYNTAX DisplayString (SIZE(0..19))
    ACCESS  read-only
    STATUS  mandatory
    DESCRIPTION
        "The destination farm of the packet for classification."
    ::= { rsBWMCurrentExtRulesEntry 3 }

rsBWMCurrentExtRulesClassificationPoint OBJECT-TYPE
    SYNTAX INTEGER {
        beforeChanges (1),
        afterChanges (2)
    }
    ACCESS  read-only
    STATUS  mandatory
    DESCRIPTION
        "Whether the classification will be performed on the original packet, or on the packet 
         after all changes."
    ::= { rsBWMCurrentExtRulesEntry 4 }

rsBWMCurrentExtRulesTrafficIdentification OBJECT-TYPE
    SYNTAX INTEGER {
        none (0),
        client (1),
        session (2),
        connection (3),
        fullL4Session (4),
        sessionCookie (5),
        sipCallID (6)
    }
    ACCESS  read-only
    STATUS  mandatory
    DESCRIPTION
        "This variable indicates how a traffic flow is defined for this policy."
    ::= { rsBWMCurrentExtRulesEntry 5 }

rsBWMCurrentExtRulesTrafficFlowMaxBW OBJECT-TYPE
    SYNTAX INTEGER
    ACCESS  read-only
    STATUS  mandatory
    DESCRIPTION
        "Maximum bandwidth allocated for a certain traffic flow (session) that match this rule."
    ::= { rsBWMCurrentExtRulesEntry 6}

rsBWMCurrentExtRulesMaxConcurrentSessions OBJECT-TYPE
    SYNTAX INTEGER
    ACCESS  read-only
    STATUS  mandatory
    DESCRIPTION
        "Maximum number of sessions that can be open simultaneously per traffic flow."
    ::= { rsBWMCurrentExtRulesEntry 7 }

rsBWMCurrentExtRulesMaxRqstsPerSec OBJECT-TYPE
    SYNTAX INTEGER
    ACCESS  read-only
    STATUS  mandatory
    DESCRIPTION
        "Maximum number of http requests that will be forwarded in a second for each traffic flow."
    ::= { rsBWMCurrentExtRulesEntry 8}

rsBWMCurrentExtRulesTrafficIDCookieField OBJECT-TYPE
    SYNTAX DisplayString (SIZE(0..19))
    ACCESS  read-only
    STATUS  mandatory
    DESCRIPTION
        "The name of cookie field for Traafic Flow ID by cookie."
    ::= { rsBWMCurrentExtRulesEntry 9 }

rsBWMCurrentExtRulesActivate OBJECT-TYPE
    SYNTAX DisplayString (SIZE(0..29))
    ACCESS  read-only
    STATUS  mandatory
    DESCRIPTION
        "The name of the schedule that will activate the policy."
    ::= { rsBWMCurrentExtRulesEntry 10 }

rsBWMCurrentExtRulesInactivate OBJECT-TYPE
    SYNTAX DisplayString (SIZE(0..29))
    ACCESS  read-only
    STATUS  mandatory
    DESCRIPTION
        "The name of the schedule that will inactivate the policy."
    ::= { rsBWMCurrentExtRulesEntry 11 }

rsBWMCurrentExtRulesForceBestFit OBJECT-TYPE
    SYNTAX INTEGER {
	false(0),
	true(1)
    }
    ACCESS  read-only
    STATUS  mandatory
    DESCRIPTION
        "Whether the policy is best fit for session while classification."
    ::= { rsBWMCurrentExtRulesEntry 12 }

rsBWMCurrentExtRulesPacketMarkingType OBJECT-TYPE
    SYNTAX INTEGER {
	none(1),
	dscp(2),
	tos(3)
    }
    ACCESS  read-only
    STATUS  mandatory
    DESCRIPTION
        "Type of packet marking for packets matching this policy. DSCP marking will set 6 low bits 
		 Tos marking will set bits 3-6."
    ::= { rsBWMCurrentExtRulesEntry 13 }

rsBWMCurrentExtRulesPacketMarkingValue OBJECT-TYPE
    SYNTAX INTEGER (-1 | 0..63)
    ACCESS  read-only
    STATUS  mandatory
    DESCRIPTION
        "Value of packet marking in the TOS field of the ip header. For DSCP 
        marking value should be 0-63. For TOS it should be 0-7"
    ::= { rsBWMCurrentExtRulesEntry 14 }

rsBWMCurrentExtRulesReportMaxBw OBJECT-TYPE
    SYNTAX INTEGER {
	false(0),
	true(1)
    }
    ACCESS  read-only
    STATUS  mandatory
    DESCRIPTION
        "Whether to report when the policy discards packets becasue of max bw limitations."
    ::= { rsBWMCurrentExtRulesEntry 15 }

rsBWMRulesTreeManager  OBJECT IDENTIFIER
    ::= { rsBWM 61 }

rsBWMRulesTreeName  OBJECT-TYPE
    SYNTAX DisplayString (SIZE(0..255))
    ACCESS  read-write
    STATUS  mandatory
    DESCRIPTION
      "The name for the subtree root."
    ::= { rsBWMRulesTreeManager 1 }

rsBWMRulesTreeNewParentName OBJECT-TYPE
    SYNTAX DisplayString (SIZE(0..255))
    ACCESS  read-write
    STATUS  mandatory
    DESCRIPTION
        "The new parent for the subtree."
    ::= { rsBWMRulesTreeManager 2 }

rsBWMRulesTreeAction  OBJECT-TYPE
    SYNTAX INTEGER {
	copy (1),
	move (2)
    }
    ACCESS read-write
    STATUS  mandatory
    DESCRIPTION
      "Rule tree advanced management."
    ::= { rsBWMRulesTreeManager 3 }


rsBWMTCPSessionClassification OBJECT-TYPE
    SYNTAX INTEGER {
        enable (1),
        disable (2)
    }
    ACCESS  read-write
    STATUS  mandatory
    DESCRIPTION "Indicates the mode of classification for a TCP session."
--  DEFVAL  { disable }
    ::= { rsBWM 62 }

rsBWMNetworkTable OBJECT-TYPE
    SYNTAX SEQUENCE OF RsBWMNetworkEntry
    ACCESS not-accessible
    STATUS  mandatory
    DESCRIPTION
      "Table containing the grouping for ranges."
    ::=  {rsBWM 63}

rsBWMNetworkEntry OBJECT-TYPE
    SYNTAX RsBWMNetworkEntry
    ACCESS not-accessible
    STATUS  mandatory
    DESCRIPTION
       "The row definition for this table."
    INDEX {rsBWMNetworkName,
           rsBWMNetworkSubIndex}
    ::=  { rsBWMNetworkTable 1 }

RsBWMNetworkEntry ::= SEQUENCE {
    rsBWMNetworkName DisplayString,
    rsBWMNetworkSubIndex INTEGER,
    rsBWMNetworkAddress Ipv6Address,
    rsBWMNetworkMask DisplayString,
    rsBWMNetworkFromIP Ipv6Address,
    rsBWMNetworkToIP Ipv6Address,
    rsBWMNetworkMode INTEGER,
    rsBWMNetworkStatus RowStatus
}

rsBWMNetworkName OBJECT-TYPE
    SYNTAX DisplayString (SIZE(0..20))
    ACCESS  read-only
    STATUS  mandatory
    DESCRIPTION
      "The Name for the IP Object Rule, must be unique."
    ::=  { rsBWMNetworkEntry 1 }

rsBWMNetworkSubIndex OBJECT-TYPE
    SYNTAX INTEGER
    ACCESS  read-only
    STATUS  mandatory
    DESCRIPTION
       "SubIndex."
    DEFVAL  { 0 }
    ::=  { rsBWMNetworkEntry 2 }

rsBWMNetworkAddress OBJECT-TYPE
    SYNTAX Ipv6Address
    ACCESS  read-write
    STATUS  mandatory
    DESCRIPTION
      "IP address"
    ::=  { rsBWMNetworkEntry 3 }

rsBWMNetworkMask OBJECT-TYPE
    SYNTAX DisplayString (SIZE(0..46))
    ACCESS  read-write
    STATUS  mandatory
    DESCRIPTION
      "IP address mask."
    ::=  { rsBWMNetworkEntry 4 }

rsBWMNetworkFromIP OBJECT-TYPE
    SYNTAX Ipv6Address
    ACCESS  read-write
    STATUS  mandatory
    DESCRIPTION
      "The from IP Address of the range."
    ::=  { rsBWMNetworkEntry 5 }

rsBWMNetworkToIP OBJECT-TYPE
    SYNTAX Ipv6Address
    ACCESS  read-write
    STATUS  mandatory
    DESCRIPTION
      "The to IP Address of the range."
    ::=  { rsBWMNetworkEntry 6 }

rsBWMNetworkMode OBJECT-TYPE
    SYNTAX INTEGER {
              ipMask(1),
              ipRange(2),
              dynamic(3)
    }
    ACCESS  read-write
    STATUS  mandatory
    DESCRIPTION
       "This variable indicates the mode of the entry. This is either
       a range or an IP address and mask."
--    DEFVAL  { 1 }
    ::=  { rsBWMNetworkEntry 7 }

rsBWMNetworkStatus OBJECT-TYPE
    SYNTAX RowStatus
    ACCESS  read-write
    STATUS  mandatory
    DESCRIPTION
       "This variable indicates the administrative status of this entry.
        Used to delete an entry of this table."
    ::=  { rsBWMNetworkEntry 8 }

rsBWMCurrentNetworkTable OBJECT-TYPE
    SYNTAX SEQUENCE OF RsBWMCurrentNetworkEntry
    ACCESS not-accessible
    STATUS  mandatory
    DESCRIPTION
      "Table containing the grouping for ranges."
    ::=  {rsBWM 64}

rsBWMCurrentNetworkEntry OBJECT-TYPE
    SYNTAX RsBWMCurrentNetworkEntry
    ACCESS not-accessible
    STATUS  mandatory
    DESCRIPTION
       "The row definition for this table."
    INDEX {rsBWMCurrentNetworkName,
           rsBWMCurrentNetworkSubIndex}
    ::=  { rsBWMCurrentNetworkTable 1 }

RsBWMCurrentNetworkEntry ::= SEQUENCE {
    rsBWMCurrentNetworkName DisplayString,
    rsBWMCurrentNetworkSubIndex INTEGER,
    rsBWMCurrentNetworkAddress Ipv6Address,
    rsBWMCurrentNetworkMask DisplayString,
    rsBWMCurrentNetworkFromIP Ipv6Address,
    rsBWMCurrentNetworkToIP Ipv6Address,
    rsBWMCurrentNetworkMode INTEGER
}

rsBWMCurrentNetworkName OBJECT-TYPE
    SYNTAX DisplayString (SIZE(0..20))
    ACCESS  read-only
    STATUS  mandatory
    DESCRIPTION
      "The Name for the IP Object Rule, must be unique."
    ::=  { rsBWMCurrentNetworkEntry 1 }

rsBWMCurrentNetworkSubIndex OBJECT-TYPE
    SYNTAX INTEGER
    ACCESS  read-only
    STATUS  mandatory
    DESCRIPTION
       "SubIndex."
    ::=  { rsBWMCurrentNetworkEntry 2 }

rsBWMCurrentNetworkAddress OBJECT-TYPE
    SYNTAX Ipv6Address
    ACCESS  read-only
    STATUS  mandatory
    DESCRIPTION
      "IP address"
    ::=  { rsBWMCurrentNetworkEntry 3 }

rsBWMCurrentNetworkMask OBJECT-TYPE
    SYNTAX DisplayString (SIZE(0..46))
    ACCESS  read-only
    STATUS  mandatory
    DESCRIPTION
      "IP address mask."
    ::=  { rsBWMCurrentNetworkEntry 4 }

rsBWMCurrentNetworkFromIP OBJECT-TYPE
    SYNTAX Ipv6Address
    ACCESS  read-only
    STATUS  mandatory
    DESCRIPTION
      "The from IP Address of the range."
    ::=  { rsBWMCurrentNetworkEntry 5 }

rsBWMCurrentNetworkToIP OBJECT-TYPE
    SYNTAX Ipv6Address
    ACCESS  read-only
    STATUS  mandatory
    DESCRIPTION
      "The to IP Address of the range."
    ::=  { rsBWMCurrentNetworkEntry 6 }

rsBWMCurrentNetworkMode OBJECT-TYPE
    SYNTAX INTEGER {
              ipMask(1),
              ipRange(2),
              dynamic(3)
    }
    ACCESS  read-only
    STATUS  mandatory
    DESCRIPTION
       "This variable indicates the mode of the entry. This is either
       a range or an IP address and mask."
    ::=  { rsBWMCurrentNetworkEntry 7 }


rsBWMStatisticsNewTable OBJECT-TYPE
    SYNTAX SEQUENCE OF RsBWMStatisticsNewEntry
    ACCESS not-accessible
    STATUS  mandatory
    DESCRIPTION
      "Table containing statistics data for the bwm policies (with integer key)"
    ::=  {rsBWM 65}

rsBWMStatisticsNewEntry OBJECT-TYPE
    SYNTAX RsBWMStatisticsNewEntry
    ACCESS not-accessible
    STATUS  mandatory
    DESCRIPTION
       "The row definition for this table."
    INDEX { rsBWMStatisticsPolicyKey }
    ::=  { rsBWMStatisticsNewTable 1 }

RsBWMStatisticsNewEntry ::= SEQUENCE {
    rsBWMStatisticsPolicyKey INTEGER,
    rsBWMStatisticsPolicyNameSec DisplayString,
    rsBWMStatisticsBandwidthUsedSecond Counter,
    rsBWMStatisticsPacketNumberSecond Counter,
    rsBWMStatisticsGuaranteedReachedSecond TruthValue,
    rsBWMStatisticsMaximumReachedSecond TruthValue,
    rsBWMStatisticsMatchedBandwidthSecond Counter,
    rsBWMStatisticsInboundBandwidthUsedSecond Counter,
    rsBWMStatisticsInboundMatchedBandwidthSecond Counter,
    rsBWMStatisticsInboundPacketNumberSecond Counter,
    rsBWMStatisticsOutboundBandwidthUsedSecond Counter,
    rsBWMStatisticsOutboundMatchedBandwidthSecond Counter,
    rsBWMStatisticsOutboundPacketNumberSecond Counter,
    rsBWMStatisticsNewTCPConnectionsSecond Counter,
    rsBWMStatisticsNewUDPConnectionsSecond Counter,
    rsBWMStatisticsQueuedBWSecond Counter,
    rsBWMStatisticsBandwidthUsedPeriod Counter,
    rsBWMStatisticsPeakBandwidthPeriod Counter,
    rsBWMStatisticsPacketNumberPeriod Counter,
    rsBWMStatisticsGuaranteedReachedCounterPeriod INTEGER,
    rsBWMStatisticsMaximumReachedCounterPeriod INTEGER,
    rsBWMStatisticsMatchedBandwidthPeriod Counter,
    rsBWMStatisticsInboundBandwidthUsedPeriod Counter,
    rsBWMStatisticsInboundMatchedBandwidthPeriod Counter,
    rsBWMStatisticsInboundPacketNumberPeriod Counter,
    rsBWMStatisticsOutboundBandwidthUsedPeriod Counter,
    rsBWMStatisticsOutboundMatchedBandwidthPeriod Counter,
    rsBWMStatisticsOutboundPacketNumberPeriod Counter,
    rsBWMStatisticsNewTCPConnectionsPeriod Counter,
    rsBWMStatisticsNewUDPConnectionsPeriod Counter,
    rsBWMStatisticsQueuedBWPeriod Counter
}

rsBWMStatisticsPolicyKey OBJECT-TYPE
    SYNTAX INTEGER
    ACCESS  read-only
    STATUS  mandatory
    DESCRIPTION
      "The name of the rule."
    ::=  {rsBWMStatisticsNewEntry 1}

rsBWMStatisticsPolicyNameSec OBJECT-TYPE
    SYNTAX DisplayString (SIZE(0..255))
    ACCESS  read-only
    STATUS  mandatory
    DESCRIPTION
      "The name of the rule."
    ::=  {rsBWMStatisticsNewEntry 2}

rsBWMStatisticsBandwidthUsedSecond OBJECT-TYPE
    SYNTAX Counter
    ACCESS  read-only
    STATUS  mandatory
    DESCRIPTION
       "The bandwidth used by the rule in the last second."
    ::=  {rsBWMStatisticsNewEntry 3}

rsBWMStatisticsPacketNumberSecond OBJECT-TYPE
    SYNTAX Counter
    ACCESS  read-only
    STATUS  mandatory
    DESCRIPTION
       "The number of packets that match the rule in the last second."
    ::=  {rsBWMStatisticsNewEntry 4}

rsBWMStatisticsGuaranteedReachedSecond OBJECT-TYPE
    SYNTAX TruthValue
    ACCESS  read-only
    STATUS  mandatory
    DESCRIPTION
       "Whether the guaranteed bandwidth threshold was reached in the last second."
    ::=  {rsBWMStatisticsNewEntry 5}

rsBWMStatisticsMaximumReachedSecond OBJECT-TYPE
    SYNTAX TruthValue
    ACCESS  read-only
    STATUS  mandatory
    DESCRIPTION
       "The number of times the maximum bandwidth threshold was reached in the last second."
    ::=  {rsBWMStatisticsNewEntry 6}

rsBWMStatisticsMatchedBandwidthSecond OBJECT-TYPE
    SYNTAX Counter
    ACCESS  read-only
    STATUS  mandatory
    DESCRIPTION
           "The matched bandwidth in the last second."
    ::=  {rsBWMStatisticsNewEntry 7}

rsBWMStatisticsInboundBandwidthUsedSecond OBJECT-TYPE
    SYNTAX Counter
    ACCESS  read-only
    STATUS  mandatory
    DESCRIPTION
           "The inbound bandwidth used by the rule in the last second."
    ::=  {rsBWMStatisticsNewEntry 8}

rsBWMStatisticsInboundMatchedBandwidthSecond OBJECT-TYPE
    SYNTAX Counter
    ACCESS  read-only
    STATUS  mandatory
    DESCRIPTION
           "The inbound matched bandwidth in the last second."
    ::=  {rsBWMStatisticsNewEntry 9}

rsBWMStatisticsInboundPacketNumberSecond OBJECT-TYPE
    SYNTAX Counter
    ACCESS  read-only
    STATUS  mandatory
    DESCRIPTION
           "The number of inbound packets that match the rule in the last second."
    ::=  {rsBWMStatisticsNewEntry 10}
	
rsBWMStatisticsOutboundBandwidthUsedSecond OBJECT-TYPE
    SYNTAX Counter
    ACCESS  read-only
    STATUS  mandatory
    DESCRIPTION
           "The outbound bandwidth used by the rule in the last second ."
    ::=  {rsBWMStatisticsNewEntry 11}
	
rsBWMStatisticsOutboundMatchedBandwidthSecond OBJECT-TYPE
    SYNTAX Counter
    ACCESS  read-only
    STATUS  mandatory
    DESCRIPTION
           "The outbound matched bandwidth in the last second."
    ::=  {rsBWMStatisticsNewEntry 12}
	

rsBWMStatisticsOutboundPacketNumberSecond OBJECT-TYPE
    SYNTAX Counter
    ACCESS  read-only
    STATUS  mandatory
    DESCRIPTION
           "The number of outbound packets that match the rule in the last second."
    ::=  {rsBWMStatisticsNewEntry 13}
	

rsBWMStatisticsNewTCPConnectionsSecond OBJECT-TYPE
    SYNTAX Counter
    ACCESS  read-only
    STATUS  mandatory
    DESCRIPTION
           "The number of new TCP connections in the last second."
    ::=  {rsBWMStatisticsNewEntry 14}
	
rsBWMStatisticsNewUDPConnectionsSecond OBJECT-TYPE
    SYNTAX Counter
    ACCESS  read-only
    STATUS  mandatory
    DESCRIPTION
           "The number of new UDP connections in the last second."
    ::=  {rsBWMStatisticsNewEntry 15}
	
rsBWMStatisticsQueuedBWSecond OBJECT-TYPE
    SYNTAX Counter
    ACCESS  read-only
    STATUS  mandatory
    DESCRIPTION
           "The amount of queued bandwidth in the last second."
    ::=  {rsBWMStatisticsNewEntry 16}

rsBWMStatisticsBandwidthUsedPeriod OBJECT-TYPE
    SYNTAX Counter
    ACCESS  read-only
    STATUS  mandatory
    DESCRIPTION
       "The bandwidth used by the rule in the last sampling period
            defined in rsBWMStatisticsReportingPeriod."
    ::=  {rsBWMStatisticsNewEntry 17}

rsBWMStatisticsPeakBandwidthPeriod OBJECT-TYPE
    SYNTAX Counter
    ACCESS  read-only
    STATUS  mandatory
    DESCRIPTION
       "The highest bandwidth in the last sampling period defined in
            rsBWMStatisticsReportingPeriod."
    ::=  {rsBWMStatisticsNewEntry 18}

rsBWMStatisticsPacketNumberPeriod OBJECT-TYPE
    SYNTAX Counter
    ACCESS  read-only
    STATUS  mandatory
    DESCRIPTION
       "The number of packets that match the rule in the last sampling period
            defined in rsBWMStatisticsReportingPeriod."
    ::=  {rsBWMStatisticsNewEntry 19}

rsBWMStatisticsGuaranteedReachedCounterPeriod OBJECT-TYPE
    SYNTAX INTEGER
    ACCESS  read-only
    STATUS  mandatory
    DESCRIPTION
       "The number of times the guaranteed bandwidth threshold was reached in the last
            sampling period defined in rsBWMStatisticsReportingPeriod."
    ::=  {rsBWMStatisticsNewEntry 20}

rsBWMStatisticsMaximumReachedCounterPeriod OBJECT-TYPE
    SYNTAX INTEGER
    ACCESS  read-only
    STATUS  mandatory
    DESCRIPTION
       "The number of times the maximum bandwidth threshold was reached in the last
            sampling period defined in rsBWMStatisticsReportingPeriod."
    ::=  {rsBWMStatisticsNewEntry 21}

rsBWMStatisticsMatchedBandwidthPeriod OBJECT-TYPE
    SYNTAX Counter
    ACCESS  read-only
    STATUS  mandatory
    DESCRIPTION
           "The matched bandwidth in the last sampling period."
    ::=  {rsBWMStatisticsNewEntry 22}

rsBWMStatisticsInboundBandwidthUsedPeriod OBJECT-TYPE
    SYNTAX Counter
    ACCESS  read-only
    STATUS  mandatory
    DESCRIPTION
           "The inbound bandwidth used by the rule in the last sampling period."
    ::=  {rsBWMStatisticsNewEntry 23}

rsBWMStatisticsInboundMatchedBandwidthPeriod OBJECT-TYPE
    SYNTAX Counter
    ACCESS  read-only
    STATUS  mandatory
    DESCRIPTION
           "The inbound matched bandwidth in the last sampling period."
    ::=  {rsBWMStatisticsNewEntry 24}

rsBWMStatisticsInboundPacketNumberPeriod OBJECT-TYPE
    SYNTAX Counter
    ACCESS  read-only
    STATUS  mandatory
    DESCRIPTION
           "The number of inbound packets that match the rule in the last sampling period."
    ::=  {rsBWMStatisticsNewEntry 25}
	
rsBWMStatisticsOutboundBandwidthUsedPeriod OBJECT-TYPE
    SYNTAX Counter
    ACCESS  read-only
    STATUS  mandatory
    DESCRIPTION
           "The outbound bandwidth used by the rule in the last sampling period."
    ::=  {rsBWMStatisticsNewEntry 26}
	
rsBWMStatisticsOutboundMatchedBandwidthPeriod OBJECT-TYPE
    SYNTAX Counter
    ACCESS  read-only
    STATUS  mandatory
    DESCRIPTION
           "The outbound matched bandwidth in the last sampling period."
    ::=  {rsBWMStatisticsNewEntry 27}
	
rsBWMStatisticsOutboundPacketNumberPeriod OBJECT-TYPE
    SYNTAX Counter
    ACCESS  read-only
    STATUS  mandatory
    DESCRIPTION
           "The number of outbound packets that match the rule in the last sampling period."
    ::=  {rsBWMStatisticsNewEntry 28}
	
rsBWMStatisticsNewTCPConnectionsPeriod OBJECT-TYPE
    SYNTAX Counter
    ACCESS  read-only
    STATUS  mandatory
    DESCRIPTION
           "The number of new TCP connections in the last sampling period."
    ::=  {rsBWMStatisticsNewEntry 29}
	
rsBWMStatisticsNewUDPConnectionsPeriod OBJECT-TYPE
    SYNTAX Counter
    ACCESS  read-only
    STATUS  mandatory
    DESCRIPTION
           "The number of new UDP connections in the last sampling period."
    ::=  {rsBWMStatisticsNewEntry 30}

rsBWMStatisticsQueuedBWPeriod OBJECT-TYPE
    SYNTAX Counter
    ACCESS  read-only
    STATUS  mandatory
    DESCRIPTION
           "The amount of queued bandwidth in the last sampling period."
    ::=  {rsBWMStatisticsNewEntry 31}

rsBWMPoliciesTable OBJECT-TYPE
    SYNTAX SEQUENCE OF RsBWMPolicyEntry
    ACCESS not-accessible
    STATUS  mandatory
    DESCRIPTION
      "Table containing the list of rules for classifer data base,
       these rules can be used to classify packets for bandwidth management,
	   this table has the same content as rsBWMRulesTable, but with a different key"
    ::=  {rsBWM 66}

rsBWMPolicyEntry OBJECT-TYPE
    SYNTAX RsBWMPolicyEntry
    ACCESS not-accessible
    STATUS  mandatory
    DESCRIPTION
       "The row definition for this table."
    INDEX { rsBWMPolicyKey }
    ::=  { rsBWMPoliciesTable 1 }

RsBWMPolicyEntry ::= SEQUENCE {
    rsBWMPolicyKey INTEGER,
    rsBWMPolicyName DisplayString,
    rsBWMPolicyIndex INTEGER,
    rsBWMPolicyDestination DisplayString,
    rsBWMPolicySource DisplayString,
    rsBWMPolicyAction INTEGER,
    rsBWMPolicyDirection INTEGER,
    rsBWMPolicyPriority INTEGER,
    rsBWMPolicyType INTEGER,
    rsBWMPolicyDescription DisplayString,
    rsBWMPolicyGuaranteedBW Integer32,
    rsBWMPolicyFilterType INTEGER,
    rsBWMPolicyFilter DisplayString,
    rsBWMPolicyOperationalStatus INTEGER,
    rsBWMPolicyReportBlockedPackets INTEGER,
    rsBWMPolicyMaxBW Integer32,
    rsBWMPolicyPhysicalPortGroup DisplayString,
    rsBWMPolicyVLANTagGroup DisplayString,
	rsBWMPolicySpecific DisplayString,
    rsBWMPolicyStatus  RowStatus,
    rsBWMPolicyRadiusRule DisplayString
}

rsBWMPolicyKey OBJECT-TYPE
    SYNTAX INTEGER
    ACCESS  read-write
    STATUS  mandatory
    DESCRIPTION
       "This is an integer key of this table. it has to be unique"
    ::=  { rsBWMPolicyEntry 1 }

rsBWMPolicyName OBJECT-TYPE
    SYNTAX DisplayString (SIZE(0..255))
    ACCESS  read-write
    STATUS  mandatory
    DESCRIPTION
      "The Name for the Rule must be unique."
    ::=  {rsBWMPolicyEntry 2}

rsBWMPolicyIndex OBJECT-TYPE
    SYNTAX INTEGER
    ACCESS  read-write
    STATUS  mandatory
    DESCRIPTION
       "This variable indicates the administrative index of a line it
       determines the order of the rules."
    ::=  { rsBWMPolicyEntry 3 }

rsBWMPolicyDestination OBJECT-TYPE
    SYNTAX DisplayString (SIZE(0..46))
    ACCESS  read-write
    STATUS  mandatory
    DESCRIPTION
      "The destination address / range of address for the packet, the name is
      defined in the Objects table or can be an IP address."
    DEFVAL { "any" }
    ::=  {rsBWMPolicyEntry 4}

rsBWMPolicySource OBJECT-TYPE
    SYNTAX DisplayString (SIZE(0..46))
    ACCESS  read-write
    STATUS  mandatory
    DESCRIPTION
      "The source address / range of address for the packet, the name is
      defined in the Objects table or can be an IP address."
    DEFVAL { "any" }
    ::=  {rsBWMPolicyEntry 5}

rsBWMPolicyAction OBJECT-TYPE
    SYNTAX INTEGER {
          none(0),
          forward(1),
          block(2),
          blockAndReset(3),
          blockAndBiDirectionalReset(4),
          monitorHTTP(5),
          monitorHTTPS(6),
          monitorTCP(7) }
    ACCESS  read-write
    STATUS  mandatory
    DESCRIPTION
       "This variable indicates the action that the classifier / service
       must take on this entry."
    DEFVAL { 1 }
    ::=  { rsBWMPolicyEntry 6 }

rsBWMPolicyDirection OBJECT-TYPE
    SYNTAX INTEGER {
              oneway(1),
              twoway(2),
              session(3)
    }
    ACCESS  read-write
    STATUS  mandatory
    DESCRIPTION
       "This variable indicates the direction of the incoming packet."
    DEFVAL { 2 }
    ::=  { rsBWMPolicyEntry 7 }

rsBWMPolicyPriority OBJECT-TYPE
    SYNTAX INTEGER
    ACCESS  read-write
    STATUS  mandatory
    DESCRIPTION
       "This variable indicates the priority for this entry."
    DEFVAL { 65535 }
    ::=  { rsBWMPolicyEntry 8 }

rsBWMPolicyType OBJECT-TYPE
    SYNTAX INTEGER {
              facsBandwidth(1),
              counter(2),
              ids(3),
              chain(4) }
    ACCESS  read-write
    STATUS  mandatory
    DESCRIPTION
       "This variable indicates the type of rules (services) ."
    DEFVAL { 1 }
    ::=  { rsBWMPolicyEntry 9 }

rsBWMPolicyDescription OBJECT-TYPE
    SYNTAX DisplayString (SIZE(0..20))
    ACCESS  read-write
    STATUS  mandatory
    DESCRIPTION
      "Description."
    ::=  { rsBWMPolicyEntry 10 }

rsBWMPolicyGuaranteedBW OBJECT-TYPE
    SYNTAX Integer32
    ACCESS  read-write
    STATUS  mandatory
    DESCRIPTION
       "Bandwidth allocated for a certain rule."
    DEFVAL  { 0 }
    ::=  { rsBWMPolicyEntry 11 }

rsBWMPolicyFilterType OBJECT-TYPE
    SYNTAX INTEGER {
              none(1),
              filter(2),
              group(3),
              policy(4)}
    ACCESS  read-write
    STATUS  mandatory
    DESCRIPTION
       "The type of policy - i.e. if this is a filter, group or policy."
    DEFVAL { 1 }
    ::=  { rsBWMPolicyEntry 12 }

rsBWMPolicyFilter OBJECT-TYPE
    SYNTAX DisplayString (SIZE(0..30))
    ACCESS  read-write
    STATUS  mandatory
    DESCRIPTION
       "The name for the filter policy for the rule."
    ::=  { rsBWMPolicyEntry 13 }

rsBWMPolicyOperationalStatus OBJECT-TYPE
    SYNTAX INTEGER {
        active (1),
        inactive (2)
    }
    ACCESS  read-write
    STATUS  mandatory
    DESCRIPTION
       "This variable indicates if the rule is active or inactive.
        The active rule table contains only active rules."
    DEFVAL { 1 }
    ::= { rsBWMPolicyEntry 14 }

rsBWMPolicyReportBlockedPackets OBJECT-TYPE
    SYNTAX INTEGER {
        disable (0),
        enable (1),
        securityEvent (2)
    }
    ACCESS  read-write
    STATUS  mandatory
    DESCRIPTION
       "This variable indicates if blocked packets are be reported."
    ::= { rsBWMPolicyEntry 15 }

rsBWMPolicyMaxBW OBJECT-TYPE
    SYNTAX Integer32
    ACCESS  read-write
    STATUS  mandatory
    DESCRIPTION
       "Maximum bandwidth allocated for a certain rule."
    DEFVAL  { 0 }
    ::=  { rsBWMPolicyEntry 16 }

rsBWMPolicyPhysicalPortGroup OBJECT-TYPE
    SYNTAX DisplayString (SIZE(0..20))
    ACCESS  read-write
    STATUS  mandatory
    DESCRIPTION
       "The name of the physical port group for this rule."
    ::=  { rsBWMPolicyEntry 17 }

rsBWMPolicyVLANTagGroup OBJECT-TYPE
    SYNTAX DisplayString (SIZE(0..20))
    ACCESS  read-write
    STATUS  mandatory
    DESCRIPTION
        "The name of the VLAN tag group for this rule."
    ::= { rsBWMPolicyEntry 18 }

rsBWMPolicySpecific OBJECT-TYPE
    SYNTAX DisplayString (SIZE(0..20))
    ACCESS  read-write
    STATUS  mandatory
    DESCRIPTION
       "This variable indicates if there is additional data to the
       policy."
    ::= { rsBWMPolicyEntry 19 }

rsBWMPolicyStatus OBJECT-TYPE
    SYNTAX RowStatus
    ACCESS  read-write
    STATUS  mandatory
    DESCRIPTION
       "This variable indicates the administrative status of this entry.
        Used to delete an entry of this table."
    ::=  { rsBWMPolicyEntry 20 }

rsBWMPolicyRadiusRule OBJECT-TYPE
    SYNTAX DisplayString (SIZE(0..30))
    ACCESS  read-write
    STATUS  mandatory
    DESCRIPTION
      "The name of the radius relevant this session belongs to. This field is relevant only for cid. Radius' rules
	   names can be found in the Radius Rules Table"
    DEFVAL { "any" }
    ::=  {rsBWMPolicyEntry 21}


rsBWMCurrentPoliciesTable OBJECT-TYPE
    SYNTAX SEQUENCE OF RsBWMCurrentPolicyEntry
    ACCESS not-accessible
    STATUS  mandatory
    DESCRIPTION
      "Table containing the list of rules for classifer data base,
       these rules can be used to classify packets for bandwidth management,
	   this table has the same content as rsBWMCurrentRulesTable, but with a different key"
    ::=  {rsBWM 67}

rsBWMCurrentPolicyEntry OBJECT-TYPE
    SYNTAX RsBWMCurrentPolicyEntry
    ACCESS not-accessible
    STATUS  mandatory
    DESCRIPTION
       "The row definition for this table."
    INDEX { rsBWMCurrentPolicyKey }
    ::=  { rsBWMCurrentPoliciesTable 1 }

RsBWMCurrentPolicyEntry ::= SEQUENCE {
    rsBWMCurrentPolicyKey INTEGER,
    rsBWMCurrentPolicyName DisplayString,
    rsBWMCurrentPolicyIndex INTEGER,
    rsBWMCurrentPolicyDestination DisplayString,
    rsBWMCurrentPolicySource DisplayString,
    rsBWMCurrentPolicyAction INTEGER,
    rsBWMCurrentPolicyDirection INTEGER,
    rsBWMCurrentPolicyPriority INTEGER,
    rsBWMCurrentPolicyType INTEGER,
    rsBWMCurrentPolicyDescription DisplayString,
    rsBWMCurrentPolicyGuaranteedBW Integer32,
    rsBWMCurrentPolicyFilterType INTEGER,
    rsBWMCurrentPolicyFilter DisplayString,
    rsBWMCurrentPolicyReportBlockedPackets INTEGER,
    rsBWMCurrentPolicyMaxBW Integer32,
    rsBWMCurrentPolicyPhysicalPortGroup DisplayString,
    rsBWMCurrentPolicyVLANTagGroup DisplayString,
    rsBWMCurrentPolicySpecific DisplayString,
    rsBWMCurrentPolicyRadiusRule DisplayString
}

rsBWMCurrentPolicyKey OBJECT-TYPE
    SYNTAX INTEGER
    ACCESS  read-write
    STATUS  mandatory
    DESCRIPTION
       "This is an integer key of this table. it has to be unique"
    ::=  { rsBWMCurrentPolicyEntry 1 }

rsBWMCurrentPolicyName OBJECT-TYPE
    SYNTAX DisplayString (SIZE(0..255))
    ACCESS  read-only
    STATUS  mandatory
    DESCRIPTION
      "The Name for the Rule must be unique."
    ::=  {rsBWMCurrentPolicyEntry 2}

rsBWMCurrentPolicyIndex OBJECT-TYPE
    SYNTAX INTEGER
    ACCESS  read-write
    STATUS  mandatory
    DESCRIPTION
       "This variable indicates the administrative index of a line it
       determines the order of the rules."
    ::=  { rsBWMCurrentPolicyEntry 3 }

rsBWMCurrentPolicyDestination OBJECT-TYPE
    SYNTAX DisplayString (SIZE(0..46))
    ACCESS  read-write
    STATUS  mandatory
    DESCRIPTION
      "The destination address / range of address for the packet, the name is
      defined in the Objects table or can be an IP address."
    DEFVAL { "any" }
    ::=  {rsBWMCurrentPolicyEntry 4}

rsBWMCurrentPolicySource OBJECT-TYPE
    SYNTAX DisplayString (SIZE(0..46))
    ACCESS  read-write
    STATUS  mandatory
    DESCRIPTION
      "The source address / range of address for the packet, the name is
      defined in the Objects table or can be an IP address."
    DEFVAL { "any" }
    ::=  {rsBWMCurrentPolicyEntry 5}

rsBWMCurrentPolicyAction OBJECT-TYPE
    SYNTAX INTEGER {
          none(0),
          forward(1),
          block(2),
          blockAndReset(3),
          blockAndBiDirectionalReset(4),
          monitorHTTP(5),
          monitorHTTPS(6),
          monitorTCP(7) }
    ACCESS  read-write
    STATUS  mandatory
    DESCRIPTION
       "This variable indicates the action that the classifier / service
       must take on this entry."
    DEFVAL { 1 }
    ::=  { rsBWMCurrentPolicyEntry 6 }

rsBWMCurrentPolicyDirection OBJECT-TYPE
    SYNTAX INTEGER {
              oneway(1),
              twoway(2),
              session(3)
    }
    ACCESS  read-write
    STATUS  mandatory
    DESCRIPTION
       "This variable indicates the direction of the incoming packet."
    DEFVAL { 2 }
    ::=  { rsBWMCurrentPolicyEntry 7 }

rsBWMCurrentPolicyPriority OBJECT-TYPE
    SYNTAX INTEGER
    ACCESS  read-write
    STATUS  mandatory
    DESCRIPTION
       "This variable indicates the priority for this entry."
    DEFVAL { 65535 }
    ::=  { rsBWMCurrentPolicyEntry 8 }

rsBWMCurrentPolicyType OBJECT-TYPE
    SYNTAX INTEGER {
              facsBandwidth(1),
              counter(2),
              ids(3),
              chain(4) }
    ACCESS  read-write
    STATUS  mandatory
    DESCRIPTION
       "This variable indicates the type of rules (services) ."
    DEFVAL { 1 }
    ::=  { rsBWMCurrentPolicyEntry 9 }

rsBWMCurrentPolicyDescription OBJECT-TYPE
    SYNTAX DisplayString (SIZE(0..20))
    ACCESS  read-write
    STATUS  mandatory
    DESCRIPTION
      "Description."
    ::=  { rsBWMCurrentPolicyEntry 10 }

rsBWMCurrentPolicyGuaranteedBW OBJECT-TYPE
    SYNTAX Integer32
    ACCESS  read-write
    STATUS  mandatory
    DESCRIPTION
       "Bandwidth allocated for a certain rule."
    DEFVAL  { 0 }
    ::=  { rsBWMCurrentPolicyEntry 11 }

rsBWMCurrentPolicyFilterType OBJECT-TYPE
    SYNTAX INTEGER {
              none(1),
              filter(2),
              group(3),
              policy(4)}
    ACCESS  read-write
    STATUS  mandatory
    DESCRIPTION
       "The type of policy - i.e. if this is a filter, group or policy."
    DEFVAL { 1 }
    ::=  { rsBWMCurrentPolicyEntry 12 }

rsBWMCurrentPolicyFilter OBJECT-TYPE
    SYNTAX DisplayString (SIZE(0..30))
    ACCESS  read-write
    STATUS  mandatory
    DESCRIPTION
       "The name for the filter policy for the rule."
    ::=  { rsBWMCurrentPolicyEntry 13 }

rsBWMCurrentPolicyReportBlockedPackets OBJECT-TYPE
    SYNTAX INTEGER {
        disable (0),
        enable (1),
        securityEvent (2)
    }
    ACCESS  read-write
    STATUS  mandatory
    DESCRIPTION
       "This variable indicates if blocked packets are be reported."
    ::= { rsBWMCurrentPolicyEntry 14 }

rsBWMCurrentPolicyMaxBW OBJECT-TYPE
    SYNTAX Integer32
    ACCESS  read-write
    STATUS  mandatory
    DESCRIPTION
       "Maximum bandwidth allocated for a certain rule."
    DEFVAL  { 0 }
    ::=  { rsBWMCurrentPolicyEntry 15 }

rsBWMCurrentPolicyPhysicalPortGroup OBJECT-TYPE
    SYNTAX DisplayString (SIZE(0..20))
    ACCESS  read-write
    STATUS  mandatory
    DESCRIPTION
       "The name of the physical port group for this rule."
    ::=  { rsBWMCurrentPolicyEntry 16 }

rsBWMCurrentPolicyVLANTagGroup OBJECT-TYPE
    SYNTAX DisplayString (SIZE(0..20))
    ACCESS  read-write
    STATUS  mandatory
    DESCRIPTION
        "The name of the VLAN tag group for this rule."
    ::= { rsBWMCurrentPolicyEntry 17 }

rsBWMCurrentPolicySpecific OBJECT-TYPE
    SYNTAX DisplayString (SIZE(0..20))
    ACCESS  read-write
    STATUS  mandatory
    DESCRIPTION
       "This variable indicates if there is additional data to the
       policy."
    ::= { rsBWMCurrentPolicyEntry 18 }

rsBWMCurrentPolicyRadiusRule OBJECT-TYPE
    SYNTAX DisplayString (SIZE(0..30))
    ACCESS  read-write
    STATUS  mandatory
    DESCRIPTION
      "The name of the radius relevant this session belongs to. This field is relevant only for cid. Radius' rules
	   names can be found in the Radius Rules Table"
    DEFVAL { "any" }
    ::=  {rsBWMCurrentPolicyEntry 19}

rsBWMExtPoliciesTable OBJECT-TYPE
    SYNTAX SEQUENCE OF RsBWMExtPolicyEntry
    ACCESS not-accessible
    STATUS  mandatory
    DESCRIPTION
      "Table containing the extended list of rules for classifer data base.
	  This table has the same content as rsBWMExtRulesTable, but the key is an integer"
    ::= { rsBWM 68 }

rsBWMExtPolicyEntry OBJECT-TYPE
    SYNTAX RsBWMExtPolicyEntry
    ACCESS not-accessible
    STATUS  mandatory
    DESCRIPTION
       "The row definition for this table."
    INDEX { rsBWMExtPolicyKey }
    ::= { rsBWMExtPoliciesTable 1 }

RsBWMExtPolicyEntry ::= SEQUENCE {
    rsBWMExtPolicyKey INTEGER,
    rsBWMExtPolicyName DisplayString,
    rsBWMExtPolicyFromFarm DisplayString,
    rsBWMExtPolicyToFarm DisplayString,
    rsBWMExtPolicyClassificationPoint INTEGER,
    rsBWMExtPolicyTrafficIdentification INTEGER,
    rsBWMExtPolicyTrafficFlowMaxBW INTEGER,
    rsBWMExtPolicyMaxConcurrentSessions INTEGER,
    rsBWMExtPolicyMaxRqstsPerSec INTEGER,
    rsBWMExtPolicyTrafficIDCookieField DisplayString,
    rsBWMExtPolicyStatus RowStatus,
    rsBWMExtPolicyActivate DisplayString,
    rsBWMExtPolicyInactivate DisplayString,
    rsBWMExtPolicyForceBestFit INTEGER,
    rsBWMExtPolicyPacketMarkingType INTEGER,
    rsBWMExtPolicyPacketMarkingValue INTEGER,
    rsBWMExtPolicyReportMaxBw INTEGER
}

rsBWMExtPolicyKey OBJECT-TYPE
    SYNTAX INTEGER
    ACCESS  read-only
    STATUS  mandatory
    DESCRIPTION
      "The key of this table."
    ::= { rsBWMExtPolicyEntry 1 }

rsBWMExtPolicyName OBJECT-TYPE
    SYNTAX DisplayString (SIZE(0..255))
    ACCESS  read-write
    STATUS  mandatory
    DESCRIPTION
      "The Name for the Rule must be unique."
    ::= { rsBWMExtPolicyEntry 2 }

rsBWMExtPolicyFromFarm OBJECT-TYPE
    SYNTAX DisplayString (SIZE(0..19))
    ACCESS  read-write
    STATUS  mandatory
    DESCRIPTION
        "The source farm of the packet for classification."
    ::= { rsBWMExtPolicyEntry 3 }

rsBWMExtPolicyToFarm OBJECT-TYPE
    SYNTAX DisplayString (SIZE(0..19))
    ACCESS  read-write
    STATUS  mandatory
    DESCRIPTION
        "The destination farm of the packet for classification."
    ::= { rsBWMExtPolicyEntry 4 }

rsBWMExtPolicyClassificationPoint OBJECT-TYPE
    SYNTAX INTEGER {
        beforeChanges (1),
        afterChanges (2)
    }
    ACCESS  read-write
    STATUS  mandatory
    DESCRIPTION
        "Whether the classification will be performed on the original packet, or on the packet 
         after all changes."
    DEFVAL { 2 }
    ::= { rsBWMExtPolicyEntry 5 }

rsBWMExtPolicyTrafficIdentification OBJECT-TYPE
    SYNTAX INTEGER {
        none (0),
        client (1),
        session (2),
        connection (3),
        fullL4Session (4),
        sessionCookie (5),
        sipCallID (6)
    }
    ACCESS  read-write
    STATUS  mandatory
    DESCRIPTION
        "This variable indicates how a traffic flow is defined for this policy."
    ::= { rsBWMExtPolicyEntry 6 }

rsBWMExtPolicyTrafficFlowMaxBW OBJECT-TYPE
    SYNTAX INTEGER
    ACCESS  read-write
    STATUS  mandatory
    DESCRIPTION
        "Maximum bandwidth allocated for a certain traffic flow (session) that match this rule."
    ::= { rsBWMExtPolicyEntry 7 }

rsBWMExtPolicyMaxConcurrentSessions OBJECT-TYPE
    SYNTAX INTEGER
    ACCESS  read-write
    STATUS  mandatory
    DESCRIPTION
        "Maximum number of sessions that can be open simultaneously per traffic flow."
    ::= { rsBWMExtPolicyEntry 8 }

rsBWMExtPolicyMaxRqstsPerSec OBJECT-TYPE
    SYNTAX INTEGER
    ACCESS  read-write
    STATUS  mandatory
    DESCRIPTION
        "Maximum number of http requests that will be forwarded in a second for each traffic flow."
    ::= { rsBWMExtPolicyEntry 9 }

rsBWMExtPolicyTrafficIDCookieField OBJECT-TYPE
    SYNTAX DisplayString (SIZE(0..20))
    ACCESS  read-write
    STATUS  mandatory
    DESCRIPTION
        "The name of cookie field for Traafic Flow ID by cookie."
    ::= { rsBWMExtPolicyEntry 10 }

rsBWMExtPolicyStatus OBJECT-TYPE
    SYNTAX RowStatus
    ACCESS  read-write
    STATUS  mandatory
    DESCRIPTION
       "This variable indicates the administrative status of this entry.
        Used to delete an entry of this table."
    ::=  { rsBWMExtPolicyEntry 11 }

rsBWMExtPolicyActivate OBJECT-TYPE
    SYNTAX DisplayString (SIZE(0..29))
    ACCESS  read-write
    STATUS  mandatory
    DESCRIPTION
        "The name of the schedule that will activate the policy."
    ::= { rsBWMExtPolicyEntry 12 }

rsBWMExtPolicyInactivate OBJECT-TYPE
    SYNTAX DisplayString (SIZE(0..29))
    ACCESS  read-write
    STATUS  mandatory
    DESCRIPTION
        "The name of the schedule that will inactivate the policy."
    ::= { rsBWMExtPolicyEntry 13 }

rsBWMExtPolicyForceBestFit OBJECT-TYPE
    SYNTAX INTEGER {
	false(0),
	true(1)
    }
    ACCESS  read-write
    STATUS  mandatory
    DESCRIPTION
        "Whether to force session best fit on the policy while classification."
    ::= { rsBWMExtPolicyEntry 14 }

rsBWMExtPolicyPacketMarkingType OBJECT-TYPE
    SYNTAX INTEGER {
	none(1),
	dscp(2),
	tos(3)
    }
    ACCESS  read-write
    STATUS  mandatory
    DESCRIPTION
        "Type of packet marking for packets matching this policy. DSCP marking will set 6 low bits 
		 Tos marking will set bits 3-6."
    ::= { rsBWMExtPolicyEntry 15 }

rsBWMExtPolicyPacketMarkingValue OBJECT-TYPE
    SYNTAX INTEGER (-1 | 0..63)
    ACCESS  read-write
    STATUS  mandatory
    DESCRIPTION
        "Value of packet marking in the TOS field of the ip header. For DSCP 
        marking value should be 0-63. For TOS it should be 0-7"
    ::= { rsBWMExtPolicyEntry 16 }

rsBWMExtPolicyReportMaxBw OBJECT-TYPE
    SYNTAX INTEGER {
	false(0),
	true(1)
    }
    ACCESS  read-write
    STATUS  mandatory
    DESCRIPTION
        "Whether to report when the policy discards packets becasue of max bw limitations."
    ::= { rsBWMExtPolicyEntry 17 }

rsBWMCurrentExtPoliciesTable OBJECT-TYPE
    SYNTAX SEQUENCE OF RsBWMCurrentExtPolicyEntry
    ACCESS not-accessible
    STATUS  mandatory
    DESCRIPTION
      "Table containing the extended list of rules for classifer data base"
    ::= { rsBWM 69 }

rsBWMCurrentExtPolicyEntry OBJECT-TYPE
    SYNTAX RsBWMCurrentExtPolicyEntry
    ACCESS not-accessible
    STATUS  mandatory
    DESCRIPTION
       "The row definition for this table."
    INDEX { rsBWMCurrentExtPolicyKey }
    ::= { rsBWMCurrentExtPoliciesTable 1 }

RsBWMCurrentExtPolicyEntry ::= SEQUENCE {
    rsBWMCurrentExtPolicyKey INTEGER,
    rsBWMCurrentExtPolicyName DisplayString,
    rsBWMCurrentExtPolicyFromFarm DisplayString,
    rsBWMCurrentExtPolicyToFarm DisplayString,
    rsBWMCurrentExtPolicyClassificationPoint INTEGER,
    rsBWMCurrentExtPolicyTrafficIdentification INTEGER,
    rsBWMCurrentExtPolicyTrafficFlowMaxBW INTEGER,
    rsBWMCurrentExtPolicyMaxConcurrentSessions INTEGER,
    rsBWMCurrentExtPolicyMaxRqstsPerSec INTEGER,
    rsBWMCurrentExtPolicyTrafficIDCookieField DisplayString,
    rsBWMCurrentExtPolicyActivate DisplayString,
    rsBWMCurrentExtPolicyInactivate DisplayString,
    rsBWMCurrentExtPolicyForceBestFit INTEGER,
    rsBWMCurrentExtPolicyPacketMarkingType INTEGER,
    rsBWMCurrentExtPolicyPacketMarkingValue INTEGER,
    rsBWMCurrentExtPolicyReportMaxBw INTEGER
}

rsBWMCurrentExtPolicyKey OBJECT-TYPE
    SYNTAX INTEGER
    ACCESS  read-only
    STATUS  mandatory
    DESCRIPTION
      "The key for this table."
    ::= { rsBWMCurrentExtPolicyEntry 1 }

rsBWMCurrentExtPolicyName OBJECT-TYPE
    SYNTAX DisplayString (SIZE(0..255))
    ACCESS  read-only
    STATUS  mandatory
    DESCRIPTION
      "The Name for the Rule must be unique."
    ::= { rsBWMCurrentExtPolicyEntry 2 }

rsBWMCurrentExtPolicyFromFarm OBJECT-TYPE
    SYNTAX DisplayString (SIZE(0..19))
    ACCESS  read-only
    STATUS  mandatory
    DESCRIPTION
        "The source farm of the packet for classification."
    ::= { rsBWMCurrentExtPolicyEntry 3 }

rsBWMCurrentExtPolicyToFarm OBJECT-TYPE
    SYNTAX DisplayString (SIZE(0..19))
    ACCESS  read-only
    STATUS  mandatory
    DESCRIPTION
        "The destination farm of the packet for classification."
    ::= { rsBWMCurrentExtPolicyEntry 4 }

rsBWMCurrentExtPolicyClassificationPoint OBJECT-TYPE
    SYNTAX INTEGER {
        beforeChanges (1),
        afterChanges (2)
    }
    ACCESS  read-only
    STATUS  mandatory
    DESCRIPTION
        "Whether the classification will be performed on the original packet, or on the packet 
         after all changes."
    ::= { rsBWMCurrentExtPolicyEntry 5 }

rsBWMCurrentExtPolicyTrafficIdentification OBJECT-TYPE
    SYNTAX INTEGER {
        none (0),
        client (1),
        session (2),
        connection (3),
        fullL4Session (4),
        sessionCookie (5),
        sipCallID (6)
    }
    ACCESS  read-only
    STATUS  mandatory
    DESCRIPTION
        "This variable indicates how a traffic flow is defined for this policy."
    ::= { rsBWMCurrentExtPolicyEntry 6 }

rsBWMCurrentExtPolicyTrafficFlowMaxBW OBJECT-TYPE
    SYNTAX INTEGER
    ACCESS  read-only
    STATUS  mandatory
    DESCRIPTION
        "Maximum bandwidth allocated for a certain traffic flow (session) that match this rule."
    ::= { rsBWMCurrentExtPolicyEntry 7}

rsBWMCurrentExtPolicyMaxConcurrentSessions OBJECT-TYPE
    SYNTAX INTEGER
    ACCESS  read-only
    STATUS  mandatory
    DESCRIPTION
        "Maximum number of sessions that can be open simultaneously per traffic flow."
    ::= { rsBWMCurrentExtPolicyEntry 8}

rsBWMCurrentExtPolicyMaxRqstsPerSec OBJECT-TYPE
    SYNTAX INTEGER
    ACCESS  read-only
    STATUS  mandatory
    DESCRIPTION
        "Maximum number of http requests that will be forwarded in a second for each traffic flow."
    ::= { rsBWMCurrentExtPolicyEntry 9}

rsBWMCurrentExtPolicyTrafficIDCookieField OBJECT-TYPE
    SYNTAX DisplayString (SIZE(0..20))
    ACCESS  read-only
    STATUS  mandatory
    DESCRIPTION
        "The name of cookie field for Traafic Flow ID by cookie."
    ::= { rsBWMCurrentExtPolicyEntry 10}

rsBWMCurrentExtPolicyActivate OBJECT-TYPE
    SYNTAX DisplayString (SIZE(0..29))
    ACCESS  read-only
    STATUS  mandatory
    DESCRIPTION
        "The name of the schedule that will activate the policy."
    ::= { rsBWMCurrentExtPolicyEntry 11 }

rsBWMCurrentExtPolicyInactivate OBJECT-TYPE
    SYNTAX DisplayString (SIZE(0..29))
    ACCESS  read-only
    STATUS  mandatory
    DESCRIPTION
        "The name of the schedule that will inactivate the policy."
    ::= { rsBWMCurrentExtPolicyEntry 12 }

rsBWMCurrentExtPolicyForceBestFit OBJECT-TYPE
    SYNTAX INTEGER {
	false(0),
	true(1)
    }
    ACCESS  read-only
    STATUS  mandatory
    DESCRIPTION
        "Whether the policy is best fit for session while classification."
    ::= { rsBWMCurrentExtPolicyEntry 13 }

rsBWMCurrentExtPolicyPacketMarkingType OBJECT-TYPE
    SYNTAX INTEGER {
	none(1),
	dscp(2),
	tos(3)
    }
    ACCESS  read-only
    STATUS  mandatory
    DESCRIPTION
        "Type of packet marking for packets matching this policy. DSCP marking will set 6 low bits 
		 Tos marking will set bits 3-6."
    ::= { rsBWMCurrentExtPolicyEntry 14 }

rsBWMCurrentExtPolicyPacketMarkingValue OBJECT-TYPE
    SYNTAX INTEGER (-1 | 0..63)
    ACCESS  read-only
    STATUS  mandatory
    DESCRIPTION
        "Value of packet marking in the TOS field of the ip header. For DSCP 
        marking value should be 0-63. For TOS it should be 0-7"
    ::= { rsBWMCurrentExtPolicyEntry 15 }

rsBWMCurrentExtPolicyReportMaxBw OBJECT-TYPE
    SYNTAX INTEGER {
	false(0),
	true(1)
    }
    ACCESS  read-only
    STATUS  mandatory
    DESCRIPTION
        "Whether to report when the policy discards packets becasue of max bw limitations."
    ::= { rsBWMCurrentExtPolicyEntry 16 }

rsBWMMaxPacketsForClassification OBJECT-TYPE
    SYNTAX INTEGER (0..100)
    ACCESS  read-write
    STATUS  mandatory
    DESCRIPTION "Indicates the maximum number of data packets per session that will 
	be used for the classification of a session (in per session mode)."
    ::= { rsBWM 70 }

rsBWMACL OBJECT IDENTIFIER ::= { rsBWM 71 }

rsBWMACLModifyPoliciesTable OBJECT-TYPE
    SYNTAX SEQUENCE OF RsBWMACLModifyPolicyEntry
    ACCESS not-accessible
    STATUS  mandatory
    DESCRIPTION
      "Table containing the list of modified policies for the ACL module"
    ::=  {rsBWMACL 1}

rsBWMACLModifyPolicyEntry OBJECT-TYPE
    SYNTAX RsBWMACLModifyPolicyEntry
    ACCESS not-accessible
    STATUS  mandatory
    DESCRIPTION
       "The row definition for this table."
    INDEX { rsBWMACLModifyPolicyName }
    ::=  { rsBWMACLModifyPoliciesTable 1 }

RsBWMACLModifyPolicyEntry ::= SEQUENCE {
    rsBWMACLModifyPolicyName DisplayString,
    rsBWMACLModifyPolicyIndex INTEGER,
    rsBWMACLModifyPolicyDescription DisplayString,
    rsBWMACLModifyPolicyDestination DisplayString,
    rsBWMACLModifyPolicySource DisplayString,
    rsBWMACLModifyPolicyService DisplayString,
    rsBWMACLModifyPolicyVLANTagGroup DisplayString,
    rsBWMACLModifyPolicyPortGroup DisplayString,
	rsBWMACLModifyPolicyActivate DisplayString,
	rsBWMACLModifyPolicyInactivate DisplayString,
    rsBWMACLModifyPolicyAction INTEGER,
    rsBWMACLModifyPolicyProtocol INTEGER,
    rsBWMACLModifyPolicyIcmpFlags DisplayString,
    rsBWMACLModifyPolicyClassificationPoint INTEGER,
    rsBWMACLModifyPolicyOperationalStatus INTEGER,
    rsBWMACLModifyPolicyStatus  RowStatus,
    rsBWMACLModifyPolicyPacketReportStatus INTEGER
}

rsBWMACLModifyPolicyName OBJECT-TYPE
    SYNTAX DisplayString (SIZE(0..255))
    ACCESS  read-only
    STATUS  mandatory
    DESCRIPTION
      "The name of the policy."
    ::=  {rsBWMACLModifyPolicyEntry 1}

rsBWMACLModifyPolicyIndex OBJECT-TYPE
    SYNTAX INTEGER (0..2147483647)
    ACCESS  read-write
    STATUS  mandatory
    DESCRIPTION
       "This variable indicates the administrative index of a line it
       determines the order of the policies."
    ::=  { rsBWMACLModifyPolicyEntry 2 }

rsBWMACLModifyPolicyDescription OBJECT-TYPE
    SYNTAX DisplayString (SIZE(0..19))
    ACCESS  read-write
    STATUS  mandatory
    DESCRIPTION
      "Description."
    ::=  { rsBWMACLModifyPolicyEntry 3 }

rsBWMACLModifyPolicyDestination OBJECT-TYPE
    SYNTAX DisplayString (SIZE(0..46))
    ACCESS  read-write
    STATUS  mandatory
    DESCRIPTION
      "The destination address / range of address for the packet, the name is
      defined in the networks table or can be an IP address."
    DEFVAL { "any" }
    ::=  {rsBWMACLModifyPolicyEntry 4}

rsBWMACLModifyPolicySource OBJECT-TYPE
    SYNTAX DisplayString (SIZE(0..46))
    ACCESS  read-write
    STATUS  mandatory
    DESCRIPTION
      "The source address / range of address for the packet, the name is
      defined in the networks table or can be an IP address."
    DEFVAL { "any" }
    ::=  {rsBWMACLModifyPolicyEntry 5}

rsBWMACLModifyPolicyService OBJECT-TYPE
    SYNTAX DisplayString (SIZE(0..19))
    ACCESS  read-write
    STATUS  mandatory
    DESCRIPTION
      "The name of the service used for classification."
    ::=  {rsBWMACLModifyPolicyEntry 6}

rsBWMACLModifyPolicyVLANTagGroup OBJECT-TYPE
    SYNTAX DisplayString (SIZE(0..19))
    ACCESS  read-write
    STATUS  mandatory
    DESCRIPTION
        "The name of the VLAN tag group for this policy."
    ::= { rsBWMACLModifyPolicyEntry 7 }

rsBWMACLModifyPolicyPortGroup OBJECT-TYPE
    SYNTAX DisplayString (SIZE(0..19))
    ACCESS  read-write
    STATUS  mandatory
    DESCRIPTION
        "The name of the physical port group for this policy."
    ::= { rsBWMACLModifyPolicyEntry 8 }

rsBWMACLModifyPolicyActivate OBJECT-TYPE
    SYNTAX DisplayString (SIZE(0..29))
    ACCESS  read-write
    STATUS  mandatory
    DESCRIPTION
        "The name of the schedule that will activate the policy."
    ::= { rsBWMACLModifyPolicyEntry 9 }

rsBWMACLModifyPolicyInactivate OBJECT-TYPE
    SYNTAX DisplayString (SIZE(0..29))
    ACCESS  read-write
    STATUS  mandatory
    DESCRIPTION
        "The name of the schedule that will inactivate the policy."
    ::= { rsBWMACLModifyPolicyEntry 10 }

rsBWMACLModifyPolicyAction OBJECT-TYPE
    SYNTAX INTEGER {
          accept(1),
          drop(2),
          dropAndResetSource(3)
    }
    ACCESS  read-write
    STATUS  mandatory
    DESCRIPTION
       "This variable indicates the action that the ACL must take on this entry."
    DEFVAL { 2 }
    ::=  { rsBWMACLModifyPolicyEntry 11 }

rsBWMACLModifyPolicyProtocol OBJECT-TYPE
    SYNTAX INTEGER {
	    tcp (1),
        udp (2),
        icmp (3),
        other (4),
        any (5),
        gre (6),
        sctp (7),
        l2tp (8),
        gtp (9),
        ipinip (10)
	}
    ACCESS  read-write
    STATUS  mandatory
    DESCRIPTION
       "This variable indicates the protocol this policy refers to."
    DEFVAL { 5 }
    ::=  { rsBWMACLModifyPolicyEntry 12 }

rsBWMACLModifyPolicyIcmpFlags OBJECT-TYPE
    SYNTAX DisplayString (SIZE(0..20))
    ACCESS  read-write
    STATUS  mandatory
    DESCRIPTION
       "This variable marks the icmp message types this policy refers to."
    DEFVAL { "11111111111111111111" }
    ::=  { rsBWMACLModifyPolicyEntry 13 }
	
rsBWMACLModifyPolicyClassificationPoint OBJECT-TYPE
    SYNTAX INTEGER {
        beforeChanges (1),
        afterChanges (2)
    }
    ACCESS  read-write
    STATUS  mandatory
    DESCRIPTION
        "Whether the classification will be performed on the original packet, or on the packet 
         after all changes."
    DEFVAL { 1 }
    ::= { rsBWMACLModifyPolicyEntry 14 }

rsBWMACLModifyPolicyOperationalStatus OBJECT-TYPE
    SYNTAX INTEGER {
        active (1),
        inactive (2)
    }
    ACCESS  read-write
    STATUS  mandatory
    DESCRIPTION
       "This variable indicates if the rule is active or inactive.
        The active rule table contains only active rules."
    DEFVAL { 1 }
    ::= { rsBWMACLModifyPolicyEntry 15 }

rsBWMACLModifyPolicyStatus OBJECT-TYPE
    SYNTAX RowStatus
    ACCESS  read-write
    STATUS  mandatory
    DESCRIPTION
       "This variable indicates the administrative status of this entry.
        Used to delete an entry of this table."
    ::=  { rsBWMACLModifyPolicyEntry 16 }
    
rsBWMACLModifyPolicyPacketReportStatus OBJECT-TYPE
    SYNTAX INTEGER {
        enable (1),
        disable (2)
    }
    ACCESS  read-write
    STATUS  mandatory
    DESCRIPTION
       "This value determines whether the device issues a trap when the data matches the policy."
    DEFVAL { 2 }
    ::= { rsBWMACLModifyPolicyEntry 17 }

rsBWMACLActualPoliciesTable OBJECT-TYPE
    SYNTAX SEQUENCE OF RsBWMACLActualPolicyEntry
    ACCESS not-accessible
    STATUS  mandatory
    DESCRIPTION
      "Table containing the list of actual policies for the ACL module"
    ::=  {rsBWMACL 2}

rsBWMACLActualPolicyEntry OBJECT-TYPE
    SYNTAX RsBWMACLActualPolicyEntry
    ACCESS not-accessible
    STATUS  mandatory
    DESCRIPTION
       "The row definition for this table."
    INDEX { rsBWMACLActualPolicyName }
    ::=  { rsBWMACLActualPoliciesTable 1 }

RsBWMACLActualPolicyEntry ::= SEQUENCE {
    rsBWMACLActualPolicyName DisplayString,
    rsBWMACLActualPolicyIndex INTEGER,
    rsBWMACLActualPolicyDescription DisplayString,
    rsBWMACLActualPolicyDestination DisplayString,
    rsBWMACLActualPolicySource DisplayString,
    rsBWMACLActualPolicyService DisplayString,
    rsBWMACLActualPolicyVLANTagGroup DisplayString,
    rsBWMACLActualPolicyPortGroup DisplayString,
	rsBWMACLActualPolicyActivate DisplayString,
	rsBWMACLActualPolicyInactivate DisplayString,
    rsBWMACLActualPolicyAction INTEGER,
    rsBWMACLActualPolicyProtocol INTEGER,
    rsBWMACLActualPolicyIcmpFlags DisplayString,
	rsBWMACLActualPolicyClassificationPoint INTEGER,
    rsBWMACLActualPolicyOperationalStatus INTEGER,
    rsBWMACLActualPolicyPacketReportStatus INTEGER
}

rsBWMACLActualPolicyName OBJECT-TYPE
    SYNTAX DisplayString (SIZE(0..255))
    ACCESS  read-only
    STATUS  mandatory
    DESCRIPTION
      "The name of the policy."
    ::=  {rsBWMACLActualPolicyEntry 1}

rsBWMACLActualPolicyIndex OBJECT-TYPE
    SYNTAX INTEGER
    ACCESS  read-only
    STATUS  mandatory
    DESCRIPTION
       "This variable indicates the administrative index of a line it
       determines the order of the policies."
    ::=  { rsBWMACLActualPolicyEntry 2 }

rsBWMACLActualPolicyDescription OBJECT-TYPE
    SYNTAX DisplayString (SIZE(0..19))
    ACCESS  read-only
    STATUS  mandatory
    DESCRIPTION
      "Description."
    ::=  { rsBWMACLActualPolicyEntry 3 }

rsBWMACLActualPolicyDestination OBJECT-TYPE
    SYNTAX DisplayString (SIZE(0..46))
    ACCESS  read-only
    STATUS  mandatory
    DESCRIPTION
      "The destination address / range of address for the packet, the name is
      defined in the networks table or can be an IP address."
    ::=  {rsBWMACLActualPolicyEntry 4}

rsBWMACLActualPolicySource OBJECT-TYPE
    SYNTAX DisplayString (SIZE(0..46))
    ACCESS  read-only
    STATUS  mandatory
    DESCRIPTION
      "The source address / range of address for the packet, the name is
      defined in the networks table or can be an IP address."
    ::=  {rsBWMACLActualPolicyEntry 5}

rsBWMACLActualPolicyService OBJECT-TYPE
    SYNTAX DisplayString (SIZE(0..19))
    ACCESS  read-only
    STATUS  mandatory
    DESCRIPTION
      "The name of the service used for classification."
    ::=  {rsBWMACLActualPolicyEntry 6}

rsBWMACLActualPolicyVLANTagGroup OBJECT-TYPE
    SYNTAX DisplayString (SIZE(0..19))
    ACCESS  read-only
    STATUS  mandatory
    DESCRIPTION
        "The name of the VLAN tag group for this policy."
    ::= { rsBWMACLActualPolicyEntry 7 }

rsBWMACLActualPolicyPortGroup OBJECT-TYPE
    SYNTAX DisplayString (SIZE(0..19))
    ACCESS  read-only
    STATUS  mandatory
    DESCRIPTION
        "The name of the physical port group for this policy."
    ::= { rsBWMACLActualPolicyEntry 8 }

rsBWMACLActualPolicyActivate OBJECT-TYPE
    SYNTAX DisplayString (SIZE(0..29))
    ACCESS  read-only
    STATUS  mandatory
    DESCRIPTION
        "The name of the schedule that will activate the policy."
    ::= { rsBWMACLActualPolicyEntry 9 }

rsBWMACLActualPolicyInactivate OBJECT-TYPE
    SYNTAX DisplayString (SIZE(0..29))
    ACCESS  read-only
    STATUS  mandatory
    DESCRIPTION
        "The name of the schedule that will inactivate the policy."
    ::= { rsBWMACLActualPolicyEntry 10 }

rsBWMACLActualPolicyAction OBJECT-TYPE
    SYNTAX INTEGER {
          accept(1),
          drop(2),
          dropAndResetSource(3)
	}
    ACCESS  read-only
    STATUS  mandatory
    DESCRIPTION
       "This variable indicates the action that the ACL must take on this entry."
    ::=  { rsBWMACLActualPolicyEntry 11 }

rsBWMACLActualPolicyProtocol OBJECT-TYPE
    SYNTAX INTEGER {
	    tcp (1),
        udp (2),
        icmp (3),
        other (4),
        any (5),
        gre (6),
        sctp (7),
        l2tp (8),
        gtp (9),
        ipinip (10)
	}
    ACCESS  read-only
    STATUS  mandatory
    DESCRIPTION
       "This variable indicates the protocol this policy refers to."
    ::=  { rsBWMACLActualPolicyEntry 12 }

rsBWMACLActualPolicyIcmpFlags OBJECT-TYPE
    SYNTAX DisplayString (SIZE(0..20))
    ACCESS  read-only
    STATUS  mandatory
    DESCRIPTION
       "This variable marks the icmp message types this policy refers to."
    ::=  { rsBWMACLActualPolicyEntry 13 }
		
rsBWMACLActualPolicyClassificationPoint OBJECT-TYPE
    SYNTAX INTEGER {
        beforeChanges (1),
        afterChanges (2)
    }
    ACCESS  read-only
    STATUS  mandatory
    DESCRIPTION
        "Whether the classification will be performed on the original packet, or on the packet 
         after all changes."
    ::= { rsBWMACLActualPolicyEntry 14 }

rsBWMACLActualPolicyOperationalStatus OBJECT-TYPE
    SYNTAX INTEGER {
        active (1),
        inactive (2)
    }
    ACCESS  read-only
    STATUS  mandatory
    DESCRIPTION
       "This variable indicates if the rule is active or inactive.
        The active rule table contains only active rules."
    ::= { rsBWMACLActualPolicyEntry 15 }
    
rsBWMACLActualPolicyPacketReportStatus OBJECT-TYPE
    SYNTAX INTEGER {
        enable (1),
        disable (2)
    }
    ACCESS  read-only
    STATUS  mandatory
    DESCRIPTION
       "This value determines whether the device issues a trap when the data matches the policy."
    ::= { rsBWMACLActualPolicyEntry 16 }

rsBWMACLStatus OBJECT-TYPE
    SYNTAX FeatureStatus
    ACCESS  read-write
    STATUS  mandatory
    DESCRIPTION "The status of the ACL module."
    ::=  { rsBWMACL 3 }

rsBWMACLLearningPeriod OBJECT-TYPE
    SYNTAX INTEGER (0..2147483647)
    ACCESS  read-write
    STATUS  mandatory
    DESCRIPTION "The learning period of the ACL in seconds."
    DEFVAL { 1800 }
    ::=  { rsBWMACL 4 }

rsBWMACLTCPHandshakeTimeout OBJECT-TYPE
    SYNTAX INTEGER (1..600)
    ACCESS  read-write
    STATUS  mandatory
    DESCRIPTION "The timeout of tcp sessions in the handshake state."
    DEFVAL { 60 }
    ::=  { rsBWMACL 5 }

rsBWMACLTCPEstablishedTimeout OBJECT-TYPE
    SYNTAX INTEGER (60..7200)
    ACCESS  read-write
    STATUS  mandatory
    DESCRIPTION "The timeout of tcp sessions in the established state."
    DEFVAL { 3600 }
    ::=  { rsBWMACL 6 }

rsBWMACLTCPFinTimeout OBJECT-TYPE
    SYNTAX INTEGER (1..600)
    ACCESS  read-write
    STATUS  mandatory
    DESCRIPTION "The timeout of tcp sessions in the fin state."
    DEFVAL { 120 }
    ::=  { rsBWMACL 7 }

rsBWMACLTCPRstTimeout OBJECT-TYPE
    SYNTAX INTEGER (1..600)
    ACCESS  read-write
    STATUS  mandatory
    DESCRIPTION "The timeout of tcp sessions in the reset state."
    DEFVAL { 30 }
    ::=  { rsBWMACL 8 }

rsBWMACLTCPMidSessMode OBJECT-TYPE
    SYNTAX INTEGER {
		drop (1),
		allow (2)
	}
	ACCESS  read-write
    STATUS  mandatory
    DESCRIPTION "The action taken for tcp mid session packets."
    DEFVAL { 1 }
    ::=  { rsBWMACL 9 }

rsBWMACLTCPRstValidationMode OBJECT-TYPE
    SYNTAX INTEGER {
		drop (1),
		allow (2),
		reportOnly (3)
	}
	ACCESS  read-write
    STATUS  mandatory
    DESCRIPTION "The action taken for invalid reset packets."
    DEFVAL { 1 }
    ::=  { rsBWMACL 10 }

rsBWMACLUDPTimeout OBJECT-TYPE
    SYNTAX INTEGER (1..3600)
    ACCESS  read-write
    STATUS  mandatory
    DESCRIPTION "The timeout of udp sessions."
    DEFVAL { 600 }
    ::=  { rsBWMACL 11 }

rsBWMACLICMPTimeout OBJECT-TYPE
    SYNTAX INTEGER (1..300)
    ACCESS  read-write
    STATUS  mandatory
    DESCRIPTION "The timeout of icmp sessions."
    DEFVAL { 60 }
    ::=  { rsBWMACL 12 }

rsBWMACLOtherTimeout OBJECT-TYPE
    SYNTAX INTEGER (1..7200)
    ACCESS  read-write
    STATUS  mandatory
    DESCRIPTION "The timeout of other sessions (not tcp, udp, gre, l2tp, gtp, sctp or icmp)."
    DEFVAL { 600 }
    ::=  { rsBWMACL 13 }

rsBWMACLSummaryReportsTable OBJECT-TYPE
    SYNTAX SEQUENCE OF RsBWMACLSummaryReportsEntry
    ACCESS not-accessible
    STATUS  mandatory
    DESCRIPTION
      "Table containing the summary reports of each ACL policy"
    ::=  {rsBWMACL 14}

rsBWMACLSummaryReportsEntry OBJECT-TYPE
    SYNTAX RsBWMACLSummaryReportsEntry
    ACCESS not-accessible
    STATUS  mandatory
    DESCRIPTION
       "The row definition for this table."
    INDEX { rsBWMACLSummaryReportsPolicyName }
    ::=  { rsBWMACLSummaryReportsTable 1 }

RsBWMACLSummaryReportsEntry ::= SEQUENCE {
    rsBWMACLSummaryReportsPolicyName DisplayString,
    rsBWMACLSummaryReportsTCPAllow INTEGER,
    rsBWMACLSummaryReportsTCPDrop INTEGER,
    rsBWMACLSummaryReportsUDPAllow INTEGER,
    rsBWMACLSummaryReportsUDPDrop INTEGER,
    rsBWMACLSummaryReportsICMPAllow INTEGER,
    rsBWMACLSummaryReportsICMPDrop INTEGER,
    rsBWMACLSummaryReportsOtherAllow INTEGER,
    rsBWMACLSummaryReportsOtherDrop INTEGER,
    rsBWMACLSummaryReportsTCPMidSess INTEGER,
    rsBWMACLSummaryReportsTCPRstInvalid INTEGER,
    rsBWMACLSummaryReportsTCPHandshakeViolation INTEGER,
    rsBWMACLSummaryReportsICMPSmurf INTEGER,
    rsBWMACLSummaryReportsICMPPacketAnomaly INTEGER,
    rsBWMACLSummaryReportsGREAllow INTEGER,
    rsBWMACLSummaryReportsGREDrop INTEGER,
    rsBWMACLSummaryReportsSCTPAllow INTEGER,
    rsBWMACLSummaryReportsSCTPDrop INTEGER,
    rsBWMACLSummaryReportsL2TPAllow INTEGER,
    rsBWMACLSummaryReportsL2TPDrop INTEGER,
    rsBWMACLSummaryReportsGTPAllow INTEGER,
    rsBWMACLSummaryReportsGTPDrop INTEGER,
    rsBWMACLSummaryReportsIPinIPAllow INTEGER,
    rsBWMACLSummaryReportsIPinIPDrop INTEGER        
}

rsBWMACLSummaryReportsPolicyName OBJECT-TYPE
    SYNTAX DisplayString (SIZE(0..255))
    ACCESS  read-only
    STATUS  mandatory
    DESCRIPTION
      "The name of the policy."
    ::=  {rsBWMACLSummaryReportsEntry 1}

rsBWMACLSummaryReportsTCPAllow OBJECT-TYPE
    SYNTAX INTEGER
    ACCESS  read-only
    STATUS  mandatory
    DESCRIPTION
       "The number of TCP allowed sessions last period"
    ::=  { rsBWMACLSummaryReportsEntry 2 }

rsBWMACLSummaryReportsTCPDrop OBJECT-TYPE
    SYNTAX INTEGER
    ACCESS  read-only
    STATUS  mandatory
    DESCRIPTION
       "The number of TCP dropped sessions last period"
    ::=  { rsBWMACLSummaryReportsEntry 3 }

rsBWMACLSummaryReportsUDPAllow OBJECT-TYPE
    SYNTAX INTEGER
    ACCESS  read-only
    STATUS  mandatory
    DESCRIPTION
       "The number of UDP allowed sessions last period"
    ::=  { rsBWMACLSummaryReportsEntry 4 }

rsBWMACLSummaryReportsUDPDrop OBJECT-TYPE
    SYNTAX INTEGER
    ACCESS  read-only
    STATUS  mandatory
    DESCRIPTION
       "The number of UDP dropped sessions last period"
    ::=  { rsBWMACLSummaryReportsEntry 5 }

rsBWMACLSummaryReportsICMPAllow OBJECT-TYPE
    SYNTAX INTEGER
    ACCESS  read-only
    STATUS  mandatory
    DESCRIPTION
       "The number of ICMP allowed messaged last period"
    ::=  { rsBWMACLSummaryReportsEntry 6 }

rsBWMACLSummaryReportsICMPDrop OBJECT-TYPE
    SYNTAX INTEGER
    ACCESS  read-only
    STATUS  mandatory
    DESCRIPTION
       "The number of ICMP dropped messages last period"
    ::=  { rsBWMACLSummaryReportsEntry 7 }

rsBWMACLSummaryReportsOtherAllow OBJECT-TYPE
    SYNTAX INTEGER
    ACCESS  read-only
    STATUS  mandatory
    DESCRIPTION
       "The number of other porotocols allowed sessions last period"
    ::=  { rsBWMACLSummaryReportsEntry 8 }

rsBWMACLSummaryReportsOtherDrop OBJECT-TYPE
    SYNTAX INTEGER
    ACCESS  read-only
    STATUS  mandatory
    DESCRIPTION
       "The number of other protocols dropped sessions last period"
    ::=  { rsBWMACLSummaryReportsEntry 9 }

rsBWMACLSummaryReportsTCPMidSess OBJECT-TYPE
    SYNTAX INTEGER
    ACCESS  read-only
    STATUS  mandatory
    DESCRIPTION
       "The number of mid flow TCP sessions last period"
    ::=  { rsBWMACLSummaryReportsEntry 10 }

rsBWMACLSummaryReportsTCPRstInvalid OBJECT-TYPE
    SYNTAX INTEGER
    ACCESS  read-only
    STATUS  mandatory
    DESCRIPTION
       "The number of invalid TCP reset packets last period"
    ::=  { rsBWMACLSummaryReportsEntry 11 }

rsBWMACLSummaryReportsTCPHandshakeViolation OBJECT-TYPE
    SYNTAX INTEGER
    ACCESS  read-only
    STATUS  mandatory
    DESCRIPTION
       "The number of invalid TCP handshakes"
    ::=  { rsBWMACLSummaryReportsEntry 12 }

rsBWMACLSummaryReportsICMPSmurf OBJECT-TYPE
    SYNTAX INTEGER
    ACCESS  read-only
    STATUS  mandatory
    DESCRIPTION
       "The number of ICMP smurf packets (reply message arriving without a request message) last period"
    ::=  { rsBWMACLSummaryReportsEntry 13 }

rsBWMACLSummaryReportsICMPPacketAnomaly OBJECT-TYPE
    SYNTAX INTEGER
    ACCESS  read-only
    STATUS  mandatory
    DESCRIPTION
       "The number of abnormal ICMP packets"
    ::=  { rsBWMACLSummaryReportsEntry 14 }
    
rsBWMACLSummaryReportsGREAllow OBJECT-TYPE
    SYNTAX INTEGER
    ACCESS  read-only
    STATUS  mandatory
    DESCRIPTION
       "The number of GRE allowed sessions last period"
    ::=  { rsBWMACLSummaryReportsEntry 15 }

rsBWMACLSummaryReportsGREDrop OBJECT-TYPE
    SYNTAX INTEGER
    ACCESS  read-only
    STATUS  mandatory
    DESCRIPTION
       "The number of GRE dropped sessions last period"
    ::=  { rsBWMACLSummaryReportsEntry 16 }
    
rsBWMACLSummaryReportsSCTPAllow OBJECT-TYPE
    SYNTAX INTEGER
    ACCESS  read-only
    STATUS  mandatory
    DESCRIPTION
       "The number of SCTP allowed sessions last period"
    ::=  { rsBWMACLSummaryReportsEntry 17 }

rsBWMACLSummaryReportsSCTPDrop OBJECT-TYPE
    SYNTAX INTEGER
    ACCESS  read-only
    STATUS  mandatory
    DESCRIPTION
       "The number of SCTP dropped sessions last period"
    ::=  { rsBWMACLSummaryReportsEntry 18 }
    
rsBWMACLSummaryReportsL2TPAllow OBJECT-TYPE
    SYNTAX INTEGER
    ACCESS  read-only
    STATUS  mandatory
    DESCRIPTION
       "The number of L2TP allowed sessions last period"
    ::=  { rsBWMACLSummaryReportsEntry 19 }

rsBWMACLSummaryReportsL2TPDrop OBJECT-TYPE
    SYNTAX INTEGER
    ACCESS  read-only
    STATUS  mandatory
    DESCRIPTION
       "The number of L2TP dropped sessions last period"
    ::=  { rsBWMACLSummaryReportsEntry 20 }    

rsBWMACLSummaryReportsGTPAllow OBJECT-TYPE
    SYNTAX INTEGER
    ACCESS  read-only
    STATUS  mandatory
    DESCRIPTION
       "The number of GTP allowed sessions last period"
    ::=  { rsBWMACLSummaryReportsEntry 21 }

rsBWMACLSummaryReportsGTPDrop OBJECT-TYPE
    SYNTAX INTEGER
    ACCESS  read-only
    STATUS  mandatory
    DESCRIPTION
       "The number of GTP dropped sessions last period"
    ::=  { rsBWMACLSummaryReportsEntry 22 } 

rsBWMACLSummaryReportsIPinIPAllow OBJECT-TYPE
    SYNTAX INTEGER
    ACCESS  read-only
    STATUS  mandatory
    DESCRIPTION
       "The number of IPinIP allowed sessions last period"
    ::=  { rsBWMACLSummaryReportsEntry 23 }

rsBWMACLSummaryReportsIPinIPDrop OBJECT-TYPE
    SYNTAX INTEGER
    ACCESS  read-only
    STATUS  mandatory
    DESCRIPTION
       "The number of IPinIP dropped sessions last period"
    ::=  { rsBWMACLSummaryReportsEntry 24 } 
rsBWMACLReportMaxTraps OBJECT-TYPE
    SYNTAX INTEGER (1..100)
    ACCESS  read-write
    STATUS  mandatory
    DESCRIPTION "Maximum number of ACL detailed report traps sent per second."
    DEFVAL { 10 }
    ::=  { rsBWMACL 15 }

rsBWMACLReportPeriod OBJECT-TYPE
    SYNTAX INTEGER (1..600)
    ACCESS  read-write
    STATUS  mandatory
    DESCRIPTION "ACL reports period for summary reports and for sending SRP."
    DEFVAL { 60 }
    ::=  { rsBWMACL 16 }

rsBWMACLReportSendSrp OBJECT-TYPE
    SYNTAX TruthValue
    ACCESS  read-write
    STATUS  mandatory
    DESCRIPTION "Whether the ACL module send summary reports via SRP or not."
    DEFVAL { 2 }
    ::=  { rsBWMACL 17 }

rsBWMACLDetailedReportType OBJECT-TYPE
    SYNTAX INTEGER {
		disable (1),
		drop    (2),
		allow   (3),
		all     (4)
	}
    ACCESS  read-write
    STATUS  mandatory
    DESCRIPTION "The type of detailed reports the ACL will send."
    DEFVAL { 4 }
    ::=  { rsBWMACL 18 }

rsBWMACLGRETimeout OBJECT-TYPE
    SYNTAX INTEGER (1..7200)
    ACCESS  read-write
    STATUS  mandatory
    DESCRIPTION "The timeout of gre sessions."
    DEFVAL { 3600 }
    ::=  { rsBWMACL 19 }
    
rsBWMACLSCTPTimeout OBJECT-TYPE
    SYNTAX INTEGER (1..7200)
    ACCESS  read-write
    STATUS  mandatory
    DESCRIPTION "The timeout of sctp sessions."
    DEFVAL { 3600 }
    ::=  { rsBWMACL 20 }
    
rsBWMACLAllowICMPSmurf OBJECT-TYPE
    SYNTAX TruthValue
    ACCESS  read-write
    STATUS  mandatory
    DESCRIPTION "An indication whether ICMP smurf checks should be ignored."
    DEFVAL { false }
    ::=  { rsBWMACL 21 }
	
rsBWMACLL2TPTimeout OBJECT-TYPE
    SYNTAX INTEGER (1..7200)
    ACCESS  read-write
    STATUS  mandatory
    DESCRIPTION "The timeout of l2tp sessions."
    DEFVAL { 3600 }
    ::=  { rsBWMACL 22 }
    
rsBWMACLGTPTimeout OBJECT-TYPE
    SYNTAX INTEGER (1..7200)
    ACCESS  read-write
    STATUS  mandatory
    DESCRIPTION "The timeout of gtp sessions."
    DEFVAL { 3600 }
    ::=  { rsBWMACL 23 }   
	
rsBWMACLPacketTraceStatus OBJECT-TYPE
    SYNTAX FeatureStatus
    ACCESS  read-write
    STATUS  mandatory
    DESCRIPTION "The status of the ACL packet trace."
    ::=  { rsBWMACL 24 }

rsBWMACLIPinIPTimeout OBJECT-TYPE
    SYNTAX INTEGER (1..7200)
    ACCESS  read-write
    STATUS  mandatory
    DESCRIPTION "The timeout of Ip in Ip sessions."
    DEFVAL { 3600 }
    ::=  { rsBWMACL 25 }   

rsBWMACLDefaultAction OBJECT-TYPE
    SYNTAX INTEGER {
          accept (1),
          drop (2),
          current (3)
	}
    ACCESS  read-write
    STATUS  mandatory
    DESCRIPTION "The action set for the default policy after reboot"
    DEFVAL { 3 }
    ::=  { rsBWMACL 26 }

    	
-- Application-specific traps for BWM
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------

rsBWMPacketBlocked TRAP-TYPE
        ENTERPRISE rsBWM
        VARIABLES  { rndErrorDesc, rndErrorSeverity }
        DESCRIPTION
             "This trap is sent to inform the user about blocked packets."
        ::=  1

rsBWMTrafficFlowBWTablesFull   TRAP-TYPE
       ENTERPRISE  rsBWM
       VARIABLES  { rndErrorDesc, rndErrorSeverity }
       DESCRIPTION
             "This trap is sent to inform the user about one of the tables for BW per traffic flow support being full."
       ::=  2

rsBWMFilterCreationFailed TRAP-TYPE
       ENTERPRISE  rsBWM
       VARIABLES  { rndErrorDesc, rndErrorSeverity }
       DESCRIPTION
             "This trap is sent to inform the user that BWM filter creation failed."
       ::=  3

rsBWMNoDefaultGatewayForClassification   TRAP-TYPE
       ENTERPRISE  rsBWM
        VARIABLES  { rndErrorDesc, rndErrorSeverity }
        DESCRIPTION
             "This trap is sent to inform the user that default gateway is needed for classification but is not configured."
       ::=  4

rsBWMAttackReportTrap   TRAP-TYPE
       ENTERPRISE  rsBWM
        VARIABLES  { rndErrorDesc, rndErrorSeverity }
        DESCRIPTION
             "This trap is sent to inform the user of an attack detected by 
             the BWM."
       ::=  5

END
