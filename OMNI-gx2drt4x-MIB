OMNI-gx2drt4x-MIB DEFINITIONS ::= BEGIN

    IMPORTS
	IpAddress, TimeTicks            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Drt4x
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



      -- This MIB module uses the extended OBJECT-TYPE macro as
      -- defined in RFC1212 and the TRAP-TYPE macro as defined
      -- in RFC 1215.

      -- *********************************************************************
      -- *                                                                   *  
      -- * REVISION history:                                                 *
      -- *	      MIB at Rev 0 to support Firmware at Rev A, March 10, 2005  * 
      -- *                                                                   *
      -- *********************************************************************
      --DESCRIPTION
      
      	--    OMNISTAR Digital Return Transmitter 4X Module MIB MODULE

	-- This MIB module defines information for management of HFC networks
		-- 
		-- The MIB module assumes that all generic (static) network element
		-- information is defined in a different module such as the HFC module
		-- The MIB consists of two groups:
		-- the device type descriptor subgroup and 
		-- gx2drt4x Network Elements subgroup.
		-- The device type descriptor subgroup is used to define 
		-- parameters specific to gx2drt4x device type.
		-- These parameters are common across all network elements
		-- from gx2drt4x device type.
		--
		-- The gx2drt4x Network Elements subgroup is
		-- a list of gx2drt4x type elements in the
		-- current network topology with nominal
		-- and current parameter values for the
		-- individual network elements; the individual
		-- network elements are identified by  
		-- index from hfcCommonTable.
		-- That implies what hfcCommonTableIndex and
		-- gx2drt4xTableIndex are equal for each individual
		-- network element.
		-- This table is an extension of the hfcCommonTable
		-- for all elements of gx2Lmc type.
		--
		-- Both groups are mandatory for management of gx2Lmc devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2drt4x Device Descriptor subgroup.

		-- The device type descriptor subgroup is used to define 
		-- parameters specific to gx2drt4x device type.
		-- These parameters are common across all network elements
		-- from gx2drt4x device type.


		 gx2drt4xDescriptor OBJECT IDENTIFIER ::= {gx2Drt4x 1}



--*****************************************************************************
		--              gx2drt4x Table
		
		-- Contains a list of all gx2drt4x type devices in
		-- the network. Each device is characterized with
		-- current network topology information, with nominal
		-- and current parameter values for the
		-- individual network elements;
		--
		-- The individual network elements indentified by  
		-- index from hfcCommonTable.
		-- That implies what hfcCommonTableIndex and
		-- gx2drt4xTableIndex are equal for each individual
		-- nettwork element.
		-- This table should be used as an extension of the hfcCommonTable
		-- for all elements of gx2drt4x type.


	       gx2drt4xAnalogTable                    OBJECT-TYPE
			 SYNTAX             SEQUENCE OF Gx2drt4xAnalogEntry
			 ACCESS             not-accessible
			 STATUS             mandatory
			 DESCRIPTION
			 "This table contains Gx2drt4x specific analog parameters with
			  nominal,limits and current values."
			 ::= { gx2Drt4x 2 }


	       gx2drt4xAnalogEntry               OBJECT-TYPE
			 SYNTAX             Gx2drt4xAnalogEntry
			 ACCESS             not-accessible
			 STATUS             mandatory
			 DESCRIPTION
			 "This list contains the analog parameters and descriptions."
			 INDEX { gx2drt4xAnalogTableIndex }
			 ::= { gx2drt4xAnalogTable  1}

--*****************************************************************************
	       gx2drt4xDigitalTable                    OBJECT-TYPE
			 SYNTAX             SEQUENCE OF Gx2drt4xDigitalEntry
			 ACCESS             not-accessible
			 STATUS             mandatory
			 DESCRIPTION
			 "This table contains gx2drt4x specific digital parameters with
			  nominal and current values."
			 ::= { gx2Drt4x 3 }

	       gx2drt4xDigitalEntry               OBJECT-TYPE
			 SYNTAX             Gx2drt4xDigitalEntry
			 ACCESS             not-accessible
			 STATUS             mandatory
			 DESCRIPTION
			 "This list contains digital parameters and descriptions."
			 INDEX { gx2drt4xDigitalTableIndex }
			 ::= { gx2drt4xDigitalTable  2}

--*****************************************************************************
	       gx2drt4xStatusTable                    OBJECT-TYPE
			 SYNTAX             SEQUENCE OF Gx2drt4xStatusEntry
			 ACCESS             not-accessible
			 STATUS             mandatory
			 DESCRIPTION
			 "This table contains gx2drt4x specific status parameters with
			  nominal and current values."
			 ::= { gx2Drt4x 4 }

	       gx2drt4xStatusEntry               OBJECT-TYPE
			 SYNTAX             Gx2drt4xStatusEntry
			 ACCESS             not-accessible
			 STATUS             mandatory
			 DESCRIPTION
			 "This list contains Status parameters and descriptions."
			 INDEX { gx2drt4xStatusTableIndex }
			 ::= { gx2drt4xStatusTable  3}

--*****************************************************************************
	       gx2drt4xFactoryTable                    OBJECT-TYPE
			 SYNTAX             SEQUENCE OF Gx2drt4xFactoryEntry
			 ACCESS             not-accessible
			 STATUS             mandatory
			 DESCRIPTION
			 "This table contains gx2drt4x specific factory setting parameters with
			  nominal and current values."
			 ::= { gx2Drt4x 5 }

	       gx2drt4xFactoryEntry               OBJECT-TYPE
			 SYNTAX             Gx2drt4xFactoryEntry
			 ACCESS             not-accessible
			 STATUS             mandatory
			 DESCRIPTION
			 "This list contains Factory setting parameters and descriptions."
			 INDEX { gx2drt4xFactoryTableIndex }
			 ::= { gx2drt4xFactoryTable  4}

--*****************************************************************************
	      Gx2drt4xAnalogEntry    ::= SEQUENCE  
	       {
		gx2drt4xAnalogTableIndex      	INTEGER,
		
		drt4xlabelRFAAttenuation		DisplayString (SIZE (0..80)),
		drt4xuomRFAAttenuation			DisplayString (SIZE (0..80)),
		drt4xmajorHighRFAAttenuation		Float,
		drt4xmajorLowRFAAttenuation		Float, 
		drt4xminorHighRFAAttenuation		Float,
		drt4xminorLowRFAAttenuation		Float, 
		drt4xvalueRFAAttenuation		Float, 
		drt4xstateFlagRFAAttenuation		INTEGER,
		drt4xminValueRFAAttenuation		Float,
		drt4xmaxValueRFAAttenuation 		Float,
		drt4xalarmStateRFAAttenuation		INTEGER,
		
		drt4xlabelRFBAttenuation			DisplayString (SIZE (0..80)),
		drt4xuomRFBAttenuation			DisplayString (SIZE (0..80)),
		drt4xmajorHighRFBAttenuation		Float, 
		drt4xmajorLowRFBAttenuation		Float, 
		drt4xminorHighRFBAttenuation		Float,
		drt4xminorLowRFBAttenuation		Float, 
		drt4xvalueRFBAttenuation		Float, 
		drt4xstateFlagRFBAttenuation		INTEGER,
		drt4xminValueRFBAttenuation		Float,
		drt4xmaxValueRFBAttenuation 		Float,
		drt4xalarmStateRFBAttenuation		INTEGER,
  
		drt4xlabelRFCAttenuation			DisplayString (SIZE (0..80)),
		drt4xuomRFCAttenuation			DisplayString (SIZE (0..80)),
		drt4xmajorHighRFCAttenuation		Float, 
		drt4xmajorLowRFCAttenuation		Float, 
		drt4xminorHighRFCAttenuation		Float,
		drt4xminorLowRFCAttenuation		Float, 
		drt4xvalueRFCAttenuation		Float, 
		drt4xstateFlagRFCAttenuation		INTEGER,
		drt4xminValueRFCAttenuation		Float,
		drt4xmaxValueRFCAttenuation 		Float,
		drt4xalarmStateRFCAttenuation		INTEGER,
		
		drt4xlabelRFDAttenuation		DisplayString (SIZE (0..80)),
		drt4xuomRFDAttenuation			DisplayString (SIZE (0..80)),
		drt4xmajorHighRFDAttenuation		Float, 
		drt4xmajorLowRFDAttenuation		Float, 
		drt4xminorHighRFDAttenuation		Float,
		drt4xminorLowRFDAttenuation		Float, 
		drt4xvalueRFDAttenuation		Float, 
		drt4xstateFlagRFDAttenuation		INTEGER,
		drt4xminValueRFDAttenuation		Float,
		drt4xmaxValueRFDAttenuation 		Float,
		drt4xalarmStateRFDAttenuation		INTEGER,

		drt4xlabelLaserPowerMonitor		DisplayString (SIZE (0..80)),
		drt4xuomLaserPowerMonitor		DisplayString (SIZE (0..80)),
		drt4xmajorHighLaserPowerMonitor	Float, 
		drt4xmajorLowLaserPowerMonitor	Float, 
		drt4xminorHighLaserPowerMonitor	Float,
		drt4xminorLowLaserPowerMonitor	Float, 
		drt4xvalueLaserPowerMonitor   	Float, 
		drt4xstateFlagLaserPowerMonitor	INTEGER,
		drt4xminValueLaserPowerMonitor	Float,
		drt4xmaxValueLaserPowerMonitor 	Float,
		drt4xalarmStateLaserPowerMonitor  	INTEGER,	
		                   
            drt4xlabelLaserBiasCurrent		DisplayString (SIZE (0..80)),
		drt4xuomLaserBiasCurrent		DisplayString (SIZE (0..80)),
		drt4xmajorHighLaserBiasCurrent	Float, 
		drt4xmajorLowLaserBiasCurrent		Float, 
		drt4xminorHighLaserBiasCurrent	Float,
		drt4xminorLowLaserBiasCurrent		Float, 
		drt4xvalueLaserBiasCurrent		Float, 
		drt4xstateFlagLaserBiasCurrent	INTEGER,
		drt4xminValueLaserBiasCurrent		Float,
		drt4xmaxValueLaserBiasCurrent 	Float,
		drt4xalarmStateLaserBiasCurrent	INTEGER,
                 
		drt4xlabelLaserTECTemperature		DisplayString (SIZE (0..80)),
		drt4xuomLaserTECTemperature		DisplayString (SIZE (0..80)),
		drt4xmajorHighLaserTECTemperature	Float, 
		drt4xmajorLowLaserTECTemperature	Float, 
		drt4xminorHighLaserTECTemperature	Float,
		drt4xminorLowLaserTECTemperature	Float, 
		drt4xvalueLaserTECTemperature		Float, 
		drt4xstateFlagLaserTECTemperature	INTEGER,
		drt4xminValueLaserTECTemperature	Float,
		drt4xmaxValueLaserTECTemperature 	Float,
		drt4xalarmStateLaserTECTemperature	INTEGER, 
		
		drt4xlabelLaserTECCurrent		DisplayString (SIZE (0..80)),
		drt4xuomLaserTECCurrent			DisplayString (SIZE (0..80)),
		drt4xmajorHighLaserTECCurrent		Float, 
		drt4xmajorLowLaserTECCurrent		Float, 
		drt4xminorHighLaserTECCurrent		Float,
		drt4xminorLowLaserTECCurrent		Float, 
		drt4xvalueLaserTECCurrent		Float, 
		drt4xstateFlagLaserTECCurrent		INTEGER,
		drt4xminValueLaserTECCurrent		Float,
		drt4xmaxValueLaserTECCurrent 		Float,
		drt4xalarmStateLaserTECCurrent	INTEGER, 
		
		drt4xlabel12VCurrent			DisplayString (SIZE (0..80)),
		drt4xuom12VCurrent			DisplayString (SIZE (0..80)),
		drt4xmajorHigh12VCurrent		Float, 
		drt4xmajorLow12VCurrent			Float, 
		drt4xminorHigh12VCurrent		Float,
		drt4xminorLow12VCurrent			Float, 
		drt4xvalue12VCurrent			Float, 
		drt4xstateFlag12VCurrent		INTEGER,
		drt4xminValue12VCurrent			Float,
		drt4xmaxValue12VCurrent 		Float,
		drt4xalarmState12VCurrent		INTEGER, 
		
		drt4xlabelModTemp				DisplayString (SIZE (0..80)),
		drt4xuomModTemp				DisplayString (SIZE (0..80)),
		drt4xmajorHighModTemp			Float, 
		drt4xmajorLowModTemp			Float, 
		drt4xminorHighModTemp			Float,
		drt4xminorLowModTemp			Float, 
		drt4xvalueModTemp				Float, 
		drt4xstateFlagModTemp			INTEGER,
		drt4xminValueModTemp			Float,
		drt4xmaxValueModTemp			Float,
		drt4xalarmStateModTemp			INTEGER,    
			
		drt4xlabelFanCurrent			DisplayString (SIZE (0..80)),
		drt4xuomFanCurrent			DisplayString (SIZE (0..80)),
		drt4xmajorHighFanCurrent		Float, 
		drt4xmajorLowFanCurrent			Float, 
		drt4xminorHighFanCurrent		Float,
		drt4xminorLowFanCurrent			Float, 
		drt4xvalueFanCurrent			Float, 
		drt4xstateFlagFanCurrent		INTEGER,
		drt4xminValueFanCurrent			Float,
		drt4xmaxValueFanCurrent 		Float,
		drt4xalarmStateFanCurrent		INTEGER
				
		}

		-- ****************  Digital Parameters ***********************
	     Gx2drt4xDigitalEntry    ::= SEQUENCE  
	     {
		gx2drt4xDigitalTableIndex         	INTEGER,    
		               	    							         
        	drt4xlabelBaseITUChannel  	    	DisplayString (SIZE (0..80)),
		drt4xenumBaseITUChannel       	DisplayString (SIZE (0..80)),
		drt4xvalueBaseITUChannel	   	INTEGER,
		drt4xstateflagBaseITUChannel    	INTEGER,
		
		drt4xlabelITUChannelSetting  	    	DisplayString (SIZE (0..80)),
		drt4xenumITUChannelSetting          DisplayString (SIZE (0..80)),
		drt4xvalueITUChannelSetting   	INTEGER,
		drt4xstateflagITUChannelSetting    	INTEGER,
		    							         
        	drt4xlabelOpticalPowerSetting      	DisplayString (SIZE (0..80)),
		drt4xenumOpticalPowerSetting	    	DisplayString (SIZE (0..80)),
		drt4xvalueOpticalPowerSetting	    	INTEGER,
		drt4xstateflagOpticalPowerSetting  	INTEGER,
		    							         
        	drt4xlabelLaserControl      		DisplayString (SIZE (0..80)),
		drt4xenumLaserControl	    		DisplayString (SIZE (0..80)),
		drt4xvalueLaserControl   		INTEGER,
		drt4xstateflagLaserControl	  	INTEGER,
		    							         	    							         
		drt4xlabelFactoryDefaultReset	    	DisplayString (SIZE (0..80)),
		drt4xenumFactoryDefaultReset		DisplayString (SIZE (0..80)),
		drt4xvalueFactoryDefaultReset		INTEGER,
		drt4xstateflagFactoryDefaultReset 	INTEGER                             
	    }

		-- ****************  Status Parameters ************************************
	     Gx2drt4xStatusEntry    ::= SEQUENCE  
	     {
		gx2drt4xStatusTableIndex      	INTEGER,

		drt4xlabelBoot				DisplayString (SIZE (0..80)),
		drt4xvalueBoot				INTEGER,
		drt4xstateflagBoot			INTEGER,
		
		drt4xlabelFlash				DisplayString (SIZE (0..80)),
		drt4xvalueFlash				INTEGER,
		drt4xstateflagFlash			INTEGER,

		drt4xlabelFactoryDataCRC 		DisplayString (SIZE (0..80)),
		drt4xvalueFactoryDataCRC		INTEGER,
		drt4xstateflagFactoryDataCRC		INTEGER,

		drt4xlabelAlarmDataCrc			DisplayString (SIZE (0..80)),
		drt4xvalueAlarmDataCrc			INTEGER,
		drt4xstateflagAlarmDataCrc		INTEGER,

		drt4xlabelCalibrationDataCrc		DisplayString (SIZE (0..80)),
		drt4xvalueCalibrationDataCrc		INTEGER,
		drt4xstateflagCalibrationDataCrc	INTEGER,

		drt4xlabelHardwareStatus		DisplayString (SIZE (0..80)),
		drt4xvalueHardwareStatus		INTEGER,
		drt4xstateflagHardwareStatus		INTEGER
	     }


--   ***************************************************************************
--   ********************************** FACTORY ********************************
--   ***************************************************************************
       Gx2drt4xFactoryEntry    ::= SEQUENCE  
       {
		gx2drt4xFactoryTableIndex       	INTEGER,
		drt4xbootControlByte  			INTEGER,
		drt4xbootStatusByte   			INTEGER,
		drt4xbank1CRC    			      INTEGER,
		drt4xbank2CRC    			      INTEGER,
		drt4xprgEEPROMByte    			INTEGER,
		drt4xfactoryCRC    			INTEGER,
		drt4xcalculateCRC    			INTEGER,
		drt4xhourMeter    			INTEGER,
		drt4xflashPrgCntA    			INTEGER,
		drt4xflashPrgCntB    			INTEGER,
		drt4xflashBankARev    			DisplayString (SIZE (0..80)),
		drt4xflashBankBRev    			DisplayString (SIZE (0..80)),
		drt4xSubAgentRev				DisplayString (SIZE (0..80))
	}

--   ***************************************************************************
--   ********************************** ANALOG *********************************
--   ***************************************************************************
		gx2drt4xAnalogTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2drt4xAnalogEntry 1}
			   
--   ***************************************************************************	          
        	drt4xlabelRFAAttenuation           OBJECT-TYPE
			   SYNTAX           DisplayString (SIZE (0..80))
			   ACCESS           read-only
			   STATUS           optional
			   DESCRIPTION
			   "The value of this object provides the label of the
			    RF Channel A Attenuation Analog parameter."
			   ::= { gx2drt4xAnalogEntry 2}

		drt4xuomRFAAttenuation             OBJECT-TYPE
			   SYNTAX           DisplayString (SIZE (0..80))
			   ACCESS           read-only
			   STATUS           optional
			   DESCRIPTION
			   "The value of this object provides the Unit of Measure of the
			     RF Channel A Attenuation Analog parameter."
			   ::= { gx2drt4xAnalogEntry 3}

		drt4xmajorHighRFAAttenuation       OBJECT-TYPE
			   SYNTAX           Float 
			   ACCESS           read-only
			   STATUS           mandatory
			   DESCRIPTION
			   "The value of this object provides the Major High alarm value
			    of the  RF Channel A Attenuation Analog parameter. This parameter has not been used by the module 
			    and set as the invalid float value (0xFFFFFFFF)"
			   ::= { gx2drt4xAnalogEntry 4}

		drt4xmajorLowRFAAttenuation        OBJECT-TYPE
			   SYNTAX           Float 
			   ACCESS           read-only
			   STATUS           mandatory
			   DESCRIPTION
			   "The value of this object provides the Major Low alarm value
			    of the RF Channel A Attenuation  Analog parameter.
			   This parameter has not been used by the module 
                     and set as the invalid float value (0xFFFFFFFF) "
			   ::= { gx2drt4xAnalogEntry 5}

		drt4xminorHighRFAAttenuation       OBJECT-TYPE
			   SYNTAX           Float
			   ACCESS           read-only
			   STATUS           mandatory
			   DESCRIPTION
			   "The value of this object provides the Minor High alarm value
			    of the RF Channel A Attenuation  Analog parameter.
			   This value is a floating point number that is represented as an IEEE 32 bit number.
			    Set as the invalid float value (0xFFFFFFFF) "
			   ::= { gx2drt4xAnalogEntry 6}

		drt4xminorLowRFAAttenuation        OBJECT-TYPE
			   SYNTAX           Float 
			   ACCESS           read-only
			   STATUS           mandatory
			   DESCRIPTION
			   "The value of this object provides the Minor Low alarm value
			    of the RF Channel A Attenuation Analog parameter.
			   This value is a floating point number that is represented as an IEEE 32 bit number.
			   Set as the invalid float value (0xFFFFFFFF) "
			   ::= { gx2drt4xAnalogEntry 7}

		drt4xvalueRFAAttenuation  	  OBJECT-TYPE
			   SYNTAX           Float 
			   ACCESS           read-write
			   STATUS           mandatory
			   DESCRIPTION
			   "The value of this object provides the Current value
			    of the RF Channel A Attenuation Analog parameter.
			   This value is a floating point number that is represented as an IEEE 32 bit number."
			   ::= { gx2drt4xAnalogEntry 8}

		drt4xstateFlagRFAAttenuation       OBJECT-TYPE
			   SYNTAX           INTEGER
								{
								hidden(1),
								read-only(2),
								updateable(3)
								}
			   ACCESS           read-only
			   STATUS           mandatory
			   DESCRIPTION
			   "The value of this object provides the state
			    of the RF Channel A Attenuation Analog parameter. (0-Hidden	
			          1-Read-Only, 2-Updateable)."
			   ::= { gx2drt4xAnalogEntry 9}

		drt4xminValueRFAAttenuation        OBJECT-TYPE
			   SYNTAX           Float
			   ACCESS           read-only
			   STATUS           mandatory
			   DESCRIPTION
			   "The value of this object provides the minimum value
			    the RF Channel A Attenuation Analog parameter can achive.
			   This value is a floating point number that is represented as an IEEE 32 bit number."
			   ::= { gx2drt4xAnalogEntry 10}

		drt4xmaxValueRFAAttenuation        OBJECT-TYPE
			   SYNTAX           Float
			   ACCESS           read-only
			   STATUS           mandatory
			   DESCRIPTION
			   "The value of this object provides the maximum value
			    the RF Channel A Attenuation Analog parameter can achive.which is 31.0 
			   This value is a floating point number that is represented as an IEEE 32 bit number."
			   ::= { gx2drt4xAnalogEntry 11}

     		drt4xalarmStateRFAAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel A Attenuation Analog parameter."
			   ::= { gx2drt4xAnalogEntry 12}
			   
			   		         
       
--   ***************************************************************************	          
      	drt4xlabelRFBAttenuation           OBJECT-TYPE
			   SYNTAX           DisplayString (SIZE (0..80))
			   ACCESS           read-only
			   STATUS           optional
			   DESCRIPTION
			   "The value of this object provides the label of the
			    RF Channel B Attenuation Analog parameter."
			   ::= { gx2drt4xAnalogEntry 13}

		drt4xuomRFBAttenuation             OBJECT-TYPE
			   SYNTAX           DisplayString (SIZE (0..80))
			   ACCESS           read-only
			   STATUS           optional
			   DESCRIPTION
			   "The value of this object provides the Unit of Measure of the
			     RF Channel B Attenuation Analog parameter."
			   ::= { gx2drt4xAnalogEntry 14}

		drt4xmajorHighRFBAttenuation       OBJECT-TYPE
			   SYNTAX           Float 
			   ACCESS           read-only
			   STATUS           mandatory
			   DESCRIPTION
			   "The value of this object provides the Major High alarm value
			    of the  RF Channel B Attenuation Analog parameter.
			   This value is a floating point number that is represented as an IEEE 32 bit number.
			   and set as the invalid float value (0xFFFFFFFF)"
			   ::= { gx2drt4xAnalogEntry 15}

		drt4xmajorLowRFBAttenuation        OBJECT-TYPE
			   SYNTAX           Float 
			   ACCESS           read-only
			   STATUS           mandatory
			   DESCRIPTION
			   "The value of this object provides the Major Low alarm value
			    of the RF Channel B Attenuation  Analog parameter.
			   This value is a floating point number that is represented as an IEEE 32 bit number.
			   and set as the invalid float value (0xFFFFFFFF)"
			   ::= { gx2drt4xAnalogEntry 16}

		drt4xminorHighRFBAttenuation       OBJECT-TYPE
			   SYNTAX           Float
			   ACCESS           read-only
			   STATUS           mandatory
			   DESCRIPTION
			   "The value of this object provides the Minor High alarm value
			    of the RF Channel B Attenuation  Analog parameter.
			   This value is a floating point number that is represented as an IEEE 32 bit number.
			    and set as the invalid float value (0xFFFFFFFF)"
			   ::= { gx2drt4xAnalogEntry 17}

		drt4xminorLowRFBAttenuation        OBJECT-TYPE
			   SYNTAX           Float 
			   ACCESS           read-only
			   STATUS           mandatory
			   DESCRIPTION
			   "The value of this object provides the Minor Low alarm value
			    of the RF Channel B Attenuation Analog parameter.
			   This value is a floating point number that is represented as an IEEE 32 bit number.
			   and set as the invalid float value (0xFFFFFFFF)"
			   ::= { gx2drt4xAnalogEntry 18}

		drt4xvalueRFBAttenuation   	 OBJECT-TYPE
			   SYNTAX           Float 
			   ACCESS           read-write
			   STATUS           mandatory
			   DESCRIPTION
			   "The value of this object provides the Current value
			    of the RF Channel B Attenuation Analog parameter.                 
			   This value is a floating point number that is represented as an IEEE 32 bit number."
			   ::= { gx2drt4xAnalogEntry 19}

		drt4xstateFlagRFBAttenuation       OBJECT-TYPE
			   SYNTAX           INTEGER
								{
								hidden(1),
								read-only(2),
								updateable(3)
								}
			   ACCESS           read-only
			   STATUS           mandatory
			   DESCRIPTION
			   "The value of this object provides the state
			    of the RF Channel B Attenuation Analog parameter. (0-Hidden	
			          1-Read-Only, 2-Updateable)."
			   ::= { gx2drt4xAnalogEntry 20}

		drt4xminValueRFBAttenuation        OBJECT-TYPE
			   SYNTAX           Float
			   ACCESS           read-only
			   STATUS           mandatory
			   DESCRIPTION
			   "The value of this object provides the minimum value
			    the RF Channel B Attenuation Analog parameter can achive.
			   This value is a floating point number that is represented as an IEEE 32 bit number."
			   ::= { gx2drt4xAnalogEntry 21}

		drt4xmaxValueRFBAttenuation        OBJECT-TYPE
			   SYNTAX           Float
			   ACCESS           read-only
			   STATUS           mandatory
			   DESCRIPTION
			   "The value of this object provides the maximum value
			    the RF Channel B Attenuation Analog parameter can achive.which is 31.0 
			   This value is a floating point number that is represented as an IEEE 32 bit number."
			   ::= { gx2drt4xAnalogEntry 22}

        	drt4xalarmStateRFBAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel B Attenuation Analog parameter."
			   ::= { gx2drt4xAnalogEntry 23}
                 
                 
--   ***************************************************************************	          
		drt4xlabelRFCAttenuation           OBJECT-TYPE
			   SYNTAX           DisplayString (SIZE (0..80))
			   ACCESS           read-only
			   STATUS           optional
			   DESCRIPTION
			   "The value of this object provides the label of the
			    RF Channel C Attenuation Analog parameter."
			   ::= { gx2drt4xAnalogEntry 24}

		drt4xuomRFCAttenuation             OBJECT-TYPE
			   SYNTAX           DisplayString (SIZE (0..80))
			   ACCESS           read-only
			   STATUS           optional
			   DESCRIPTION
			   "The value of this object provides the Unit of Measure of the
			     RF Channel C Attenuation Analog parameter."
			   ::= { gx2drt4xAnalogEntry 25}

		drt4xmajorHighRFCAttenuation       OBJECT-TYPE
			   SYNTAX           Float 
			   ACCESS           read-only
			   STATUS           mandatory
			   DESCRIPTION
			   "The value of this object provides the Major High alarm value
			    of the  RF Channel C Attenuation Analog parameter.
			   This value is a floating point number that is represented as an IEEE 32 bit number.
			   and set as the invalid float value (0xFFFFFFFF)"
			   ::= { gx2drt4xAnalogEntry 26}

		drt4xmajorLowRFCAttenuation        OBJECT-TYPE
			   SYNTAX           Float 
			   ACCESS           read-only
			   STATUS           mandatory
			   DESCRIPTION
			   "The value of this object provides the Major Low alarm value
			    of the RF Channel C Attenuation  Analog parameter.
			   This value is a floating point number that is represented as an IEEE 32 bit number.
			   and set as the invalid float value (0xFFFFFFFF)"
			   ::= { gx2drt4xAnalogEntry 27}

		drt4xminorHighRFCAttenuation       OBJECT-TYPE
			   SYNTAX           Float
			   ACCESS           read-only
			   STATUS           mandatory
			   DESCRIPTION
			   "The value of this object provides the Minor High alarm value
			    of the RF Channel C Attenuation  Analog parameter.
			   This value is a floating point number that is represented as an IEEE 32 bit number.
			    and set as the invalid float value (0xFFFFFFFF)"
			   ::= { gx2drt4xAnalogEntry 28}

		drt4xminorLowRFCAttenuation        OBJECT-TYPE
			   SYNTAX           Float 
			   ACCESS           read-only
			   STATUS           mandatory
			   DESCRIPTION
			   "The value of this object provides the Minor Low alarm value
			    of the RF Channel C Attenuation Analog parameter.
			   This value is a floating point number that is represented as an IEEE 32 bit number.
			   and set as the invalid float value (0xFFFFFFFF)"
			   ::= { gx2drt4xAnalogEntry 29}

		drt4xvalueRFCAttenuation  	  OBJECT-TYPE
			   SYNTAX           Float 
			   ACCESS           read-write
			   STATUS           mandatory
			   DESCRIPTION
			   "The value of this object provides the Current value
			    of the RF Channel C Attenuation Analog parameter.
			   This value is a floating point number that is represented as an IEEE 32 bit number."
			   ::= { gx2drt4xAnalogEntry 30}

		drt4xstateFlagRFCAttenuation       OBJECT-TYPE
			   SYNTAX           INTEGER
								{
								hidden(1),
								read-only(2),
								updateable(3)
								}
			   ACCESS           read-only
			   STATUS           mandatory
			   DESCRIPTION
			   "The value of this object provides the state
			    of the RF Channel C Attenuation Analog parameter. (0-Hidden	
			          1-Read-Only, 2-Updateable)."
			   ::= { gx2drt4xAnalogEntry 31}

		drt4xminValueRFCAttenuation        OBJECT-TYPE
			   SYNTAX           Float
			   ACCESS           read-only
			   STATUS           mandatory
			   DESCRIPTION
			   "The value of this object provides the minimum value
			    the RF Channel C Attenuation Analog parameter can achive.
			   This value is a floating point number that is represented as an IEEE 32 bit number."
			   ::= { gx2drt4xAnalogEntry 32}

		drt4xmaxValueRFCAttenuation        OBJECT-TYPE
			   SYNTAX           Float
			   ACCESS           read-only
			   STATUS           mandatory
			   DESCRIPTION
			   "The value of this object provides the maximum value
			    the RF Channel C Attenuation Analog parameter can achive.which is 31.0 
			   This value is a floating point number that is represented as an IEEE 32 bit number."
			   ::= { gx2drt4xAnalogEntry 33}

        	drt4xalarmStateRFCAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel C Attenuation Analog parameter."
			   ::= { gx2drt4xAnalogEntry 34}


--   ***************************************************************************	          
		drt4xlabelRFDAttenuation           OBJECT-TYPE
			   SYNTAX           DisplayString (SIZE (0..80))
			   ACCESS           read-only
			   STATUS           optional
			   DESCRIPTION
			   "The value of this object provides the label of the
			    RF Channel D Attenuation Analog parameter."
			   ::= { gx2drt4xAnalogEntry 35}

		drt4xuomRFDAttenuation             OBJECT-TYPE
			   SYNTAX           DisplayString (SIZE (0..80))
			   ACCESS           read-only
			   STATUS           optional
			   DESCRIPTION
			   "The value of this object provides the Unit of Measure of the
			     RF Channel D Attenuation Analog parameter."
			   ::= { gx2drt4xAnalogEntry 36}

		drt4xmajorHighRFDAttenuation       OBJECT-TYPE
			   SYNTAX           Float 
			   ACCESS           read-only
			   STATUS           mandatory
			   DESCRIPTION
			   "The value of this object provides the Major High alarm value
			    of the  RF Channel D Attenuation Analog parameter.
			   This value is a floating point number that is represented as an IEEE 32 bit number.
			   and set as the invalid float value (0xFFFFFFFF)"
			   ::= { gx2drt4xAnalogEntry 37}

		drt4xmajorLowRFDAttenuation        OBJECT-TYPE
			   SYNTAX           Float 
			   ACCESS           read-only
			   STATUS           mandatory
			   DESCRIPTION
			   "The value of this object provides the Major Low alarm value
			    of the RF Channel D Attenuation  Analog parameter.
			   This value is a floating point number that is represented as an IEEE 32 bit number.
			   and set as the invalid float value (0xFFFFFFFF)"
			   ::= { gx2drt4xAnalogEntry 38}

		drt4xminorHighRFDAttenuation       OBJECT-TYPE
			   SYNTAX           Float
			   ACCESS           read-only
			   STATUS           mandatory
			   DESCRIPTION
			   "The value of this object provides the Minor High alarm value
			    of the RF Channel D Attenuation  Analog parameter.
			   This value is a floating point number that is represented as an IEEE 32 bit number.
			    and set as the invalid float value (0xFFFFFFFF)"
			   ::= { gx2drt4xAnalogEntry 39}

		drt4xminorLowRFDAttenuation        OBJECT-TYPE
			   SYNTAX           Float 
			   ACCESS           read-only
			   STATUS           mandatory
			   DESCRIPTION
			   "The value of this object provides the Minor Low alarm value
			    of the RF Channel D Attenuation Analog parameter.
			   This value is a floating point number that is represented as an IEEE 32 bit number.
			   and set as the invalid float value (0xFFFFFFFF)"
			   ::= { gx2drt4xAnalogEntry 40} 

		drt4xvalueRFDAttenuation   	 OBJECT-TYPE
			   SYNTAX           Float 
			   ACCESS           read-write
			   STATUS           mandatory
			   DESCRIPTION
			   "The value of this object provides the Current value
			    of the RF Channel D Attenuation Analog parameter.
			   This value is a floating point number that is represented as an IEEE 32 bit number."
			   ::= { gx2drt4xAnalogEntry 41}

		drt4xstateFlagRFDAttenuation       OBJECT-TYPE
			   SYNTAX           INTEGER
								{
								hidden(1),
								read-only(2),
								updateable(3)
								}
			   ACCESS           read-only
			   STATUS           mandatory
			   DESCRIPTION
			   "The value of this object provides the state
			    of the RF Channel D Attenuation Analog parameter. (0-Hidden	
			          1-Read-Only, 2-Updateable)."
			   ::= { gx2drt4xAnalogEntry 42}

		drt4xminValueRFDAttenuation        OBJECT-TYPE
			   SYNTAX           Float
			   ACCESS           read-only
			   STATUS           mandatory
			   DESCRIPTION
			   "The value of this object provides the minimum value
			    the RF Channel D Attenuation Analog parameter can achive.
			   This value is a floating point number that is represented as an IEEE 32 bit number."
			   ::= { gx2drt4xAnalogEntry 43}

		drt4xmaxValueRFDAttenuation        OBJECT-TYPE
			   SYNTAX           Float
			   ACCESS           read-only
			   STATUS           mandatory
			   DESCRIPTION
			   "The value of this object provides the maximum value
			    the RF Channel D Attenuation Analog parameter can achive.which is 31.0 
			   This value is a floating point number that is represented as an IEEE 32 bit number."
			   ::= { gx2drt4xAnalogEntry 44}

		drt4xalarmStateRFDAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel D Attenuation Analog parameter."
			   ::= { gx2drt4xAnalogEntry 45}

			   
--   ***************************************************************************	          
		drt4xlabelLaserPowerMonitor           OBJECT-TYPE
			   SYNTAX           DisplayString (SIZE (0..80))
			   ACCESS           read-only
			   STATUS           optional
			   DESCRIPTION
			   "The value of this object provides the label of the
			    trip point level Analog parameter."
			   ::= { gx2drt4xAnalogEntry 46}

		drt4xuomLaserPowerMonitor             OBJECT-TYPE
			   SYNTAX           DisplayString (SIZE (0..80))
			   ACCESS           read-only
			   STATUS           optional
			   DESCRIPTION
			   "The value of this object provides the Unit of Measure of the
			     trip point level Analog parameter."
			   ::= { gx2drt4xAnalogEntry 47}

		drt4xmajorHighLaserPowerMonitor       OBJECT-TYPE
			   SYNTAX           Float 
			   ACCESS           read-only
			   STATUS           mandatory
			   DESCRIPTION
			   "The value of this object provides the Major High alarm value
			    of the  trip point level Analog parameter.
			   This value is a floating point number that is represented as an IEEE 32 bit number.
			   and set as the invalid float value (0xFFFFFFFF)"
			   ::= { gx2drt4xAnalogEntry 48}

		drt4xmajorLowLaserPowerMonitor        OBJECT-TYPE
			   SYNTAX           Float 
			   ACCESS           read-only
			   STATUS           mandatory
			   DESCRIPTION
			   "The value of this object provides the Major Low alarm value
			    of the trip point level Analog parameter.
			   This value is a floating point number that is represented as an IEEE 32 bit number.
			   and set as the invalid float value (0xFFFFFFFF)"
			   ::= { gx2drt4xAnalogEntry 49}

		drt4xminorHighLaserPowerMonitor       OBJECT-TYPE
			   SYNTAX           Float
			   ACCESS           read-only
			   STATUS           mandatory
			   DESCRIPTION
			   "The value of this object provides the Minor High alarm value
			    of the trip point level Analog parameter.
			   This value is a floating point number that is represented as an IEEE 32 bit number.
			    and set as the invalid float value (0xFFFFFFFF)"
			   ::= { gx2drt4xAnalogEntry 50}

		drt4xminorLowLaserPowerMonitor        OBJECT-TYPE
			   SYNTAX           Float 
			   ACCESS           read-only
			   STATUS           mandatory
			   DESCRIPTION
			   "The value of this object provides the Minor Low alarm value
			    of the trip point level Analog parameter.
			   This value is a floating point number that is represented as an IEEE 32 bit number.
			   and set as the invalid float value (0xFFFFFFFF)"
			   ::= { gx2drt4xAnalogEntry 51}

		drt4xvalueLaserPowerMonitor    OBJECT-TYPE
			   SYNTAX           Float 
			   ACCESS           read-only
			   STATUS           mandatory
			   DESCRIPTION
			   "The value of this object provides the Current value
			    of the trip point level Analog parameter. The trip point level set the custumer preferred 
                      optical input level. When trip point mode is ALARM_SWITCH, when optical power level is lower than 
                      trip point level (Set by this parameter), trip point alarm will be generated and RF output 
                      impedance will be changed to high impedance as >8.2K. 
			   This trip point level value is a floating point number that is represented as an IEEE 32 bit number."
			   ::= { gx2drt4xAnalogEntry 52}

		drt4xstateFlagLaserPowerMonitor       OBJECT-TYPE
			   SYNTAX           INTEGER
								{
								hidden(1),
								read-only(2),
								updateable(3)
								}
			   ACCESS           read-only
			   STATUS           mandatory
			   DESCRIPTION
			   "The value of this object provides the state
			    of the trip point level Analog parameter. (0-Hidden	
			          1-Read-Only, 2-Updateable)."
			   ::= { gx2drt4xAnalogEntry 53}

		drt4xminValueLaserPowerMonitor        OBJECT-TYPE
			   SYNTAX           Float
			   ACCESS           read-only
			   STATUS           mandatory
			   DESCRIPTION
			   "The value of this object provides the minimum value
			    the trip point level Analog parameter can achive.
			    The minimum value is -19dBm 
			   This value is a floating point number that is represented as an IEEE 32 bit number."
			   ::= { gx2drt4xAnalogEntry 54}

		drt4xmaxValueLaserPowerMonitor        OBJECT-TYPE
			   SYNTAX           Float
			   ACCESS           read-only
			   STATUS           mandatory
			   DESCRIPTION
			   "The value of this object provides the maximum value
			    the trip point level Analog parameter can achive.which is -1dBm 
			   This value is a floating point number that is represented as an IEEE 32 bit number."
			   ::= { gx2drt4xAnalogEntry 55}

		drt4xalarmStateLaserPowerMonitor      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the trip point level Analog parameter."
			   ::= { gx2drt4xAnalogEntry 56}
		
	               
--   ***************************************************************************	          
	    	drt4xlabelLaserBiasCurrent           OBJECT-TYPE
			   SYNTAX           DisplayString (SIZE (0..80))
			   ACCESS           read-only
			   STATUS           optional
			   DESCRIPTION
			   "The value of this object provides the label of the
			    Optical Power Current Analog parameter."
			   ::= { gx2drt4xAnalogEntry 57}

		drt4xuomLaserBiasCurrent             OBJECT-TYPE
			   SYNTAX           DisplayString (SIZE (0..80))
			   ACCESS           read-only
			   STATUS           optional
			   DESCRIPTION
			   "The value of this object provides the Unit of Measure of the
			    Optical Power Current Analog parameter."
			   ::= { gx2drt4xAnalogEntry 58}

		drt4xmajorHighLaserBiasCurrent       OBJECT-TYPE
			   SYNTAX           Float 
			   ACCESS           read-only
			   STATUS           mandatory
			   DESCRIPTION
			   "The value of this object provides the Major High alarm value
			    of the Optical Power Current Analog parameter.
			   This value is a floating point number that is represented as an IEEE 32 bit number."
			   ::= { gx2drt4xAnalogEntry 59}


		drt4xmajorLowLaserBiasCurrent        OBJECT-TYPE
			   SYNTAX           Float 
			   ACCESS           read-only
			   STATUS           mandatory
			   DESCRIPTION
			   "The value of this object provides the Major Low alarm value
			    of the Optical Power Current Analog parameter.
			   This value is a floating point number that is represented as an IEEE 32 bit number."
			   ::= { gx2drt4xAnalogEntry 60}

		drt4xminorHighLaserBiasCurrent       OBJECT-TYPE
			   SYNTAX           Float
			   ACCESS           read-only
			   STATUS           mandatory
			   DESCRIPTION
			   "The value of this object provides the Minor High alarm value
			   of the Optical Power Current Analog parameter.
			   This value is a floating point number that is represented as an IEEE 32 bit number."
			   ::= { gx2drt4xAnalogEntry 61}

		drt4xminorLowLaserBiasCurrent        OBJECT-TYPE
			   SYNTAX           Float 
			   ACCESS           read-only
			   STATUS           mandatory
			   DESCRIPTION
			   "The value of this object provides the Minor Low alarm value
			    of the Optical Power Current Analog parameter.
			   This value is a floating point number that is represented as an IEEE 32 bit number."
			   ::= { gx2drt4xAnalogEntry 62}

		drt4xvalueLaserBiasCurrent  	  OBJECT-TYPE
			   SYNTAX           Float 
			   ACCESS           read-only
			   STATUS           mandatory
			   DESCRIPTION
			   "The value of this object provides the Current value
			    of the Optical Power Current Analog parameter.
			   This value is a floating point number that is represented as an IEEE 32 bit number."
			   ::= { gx2drt4xAnalogEntry 63}

		drt4xstateFlagLaserBiasCurrent       OBJECT-TYPE
			   SYNTAX           INTEGER
								{
								hidden(1),
								read-only(2),
								updateable(3)
								}
			   ACCESS           read-only
			   STATUS           mandatory
			   DESCRIPTION
			   "The value of this object provides the state
			    of the Optical Power Current Analog parameter. (0-Hidden	
			          1-Read-Only, 2-Updateable)."
			   ::= { gx2drt4xAnalogEntry 64}

		drt4xminValueLaserBiasCurrent        OBJECT-TYPE
			   SYNTAX           Float
			   ACCESS           read-only
			   STATUS           mandatory
			   DESCRIPTION
			   "The value of this object provides the minimum value
			    the Optical Power Current Analog parameter can achive.
			   This value is a floating point number that is represented as an IEEE 32 bit number."
			   ::= { gx2drt4xAnalogEntry 65}

		drt4xmaxValueLaserBiasCurrent        OBJECT-TYPE
			   SYNTAX           Float
			   ACCESS           read-only
			   STATUS           mandatory
			   DESCRIPTION
			   "The value of this object provides the maximum value
			    the Optical Power Current  Analog parameter can achive.
			   This value is a floating point number that is represented as an IEEE 32 bit number."
			   ::= { gx2drt4xAnalogEntry 66}

        drt4xalarmStateLaserBiasCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Current Analog parameter."
			   ::= { gx2drt4xAnalogEntry 67}


--   ***************************************************************************

		drt4xlabelLaserTECTemperature              OBJECT-TYPE
			   SYNTAX           DisplayString (SIZE (0..80))
			   ACCESS           read-only
			   STATUS           optional
			   DESCRIPTION
			   "The value of this object provides the label of the
			    Laser TEC Temperature Analog parameter."
			   ::= { gx2drt4xAnalogEntry 68}

		drt4xuomLaserTECTemperature                OBJECT-TYPE
			   SYNTAX           DisplayString (SIZE (0..80))
			   ACCESS           read-only
			   STATUS           optional
			   DESCRIPTION
			   "The value of this object provides the Unit of Measure of the
			    Laser TEC Temperature Analog parameter."
			   ::= { gx2drt4xAnalogEntry 69}

		drt4xmajorHighLaserTECTemperature          OBJECT-TYPE
			   SYNTAX           Float 
			   ACCESS           read-only
			   STATUS           mandatory
			   DESCRIPTION
			   "The value of this object provides the Major High alarm value
			    of the Laser TEC Temperature Analog parameter.
			   This value is a floating point number that is represented as an IEEE 32 bit number."
			   ::= { gx2drt4xAnalogEntry 70}


		drt4xmajorLowLaserTECTemperature           OBJECT-TYPE
			   SYNTAX           Float 
			   ACCESS           read-only
			   STATUS           mandatory
			   DESCRIPTION
			   "The value of this object provides the Major Low alarm value
			    of the Laser TEC Temperature Analog parameter.
			   This value is a floating point number that is represented as an IEEE 32 bit number."
			   ::= { gx2drt4xAnalogEntry 71}

		drt4xminorHighLaserTECTemperature          OBJECT-TYPE
			   SYNTAX           Float
			   ACCESS           read-only
			   STATUS           mandatory
			   DESCRIPTION
			   "The value of this object provides the Minor High alarm value
			    of the Laser TEC Temperature Analog parameter.
			   This value is a floating point number that is represented as an IEEE 32 bit number."
			   ::= { gx2drt4xAnalogEntry 72}

		drt4xminorLowLaserTECTemperature           OBJECT-TYPE
			   SYNTAX           Float 
			   ACCESS           read-only
			   STATUS           mandatory
			   DESCRIPTION
			   "The value of this object provides the Minor Low alarm value
			    of the Laser TEC Temperature Analog parameter.
			   This value is a floating point number that is represented as an IEEE 32 bit number."
			   ::= { gx2drt4xAnalogEntry 73}

		drt4xvalueLaserTECTemperature     	  OBJECT-TYPE
			   SYNTAX           Float 
			   ACCESS           read-only
			   STATUS           mandatory
			   DESCRIPTION
			   "The value of this object provides the Current value
			    of the Laser TEC Temperature Analog parameter.
			   This value is a floating point number that is represented as an IEEE 32 bit number."
			   ::= { gx2drt4xAnalogEntry 74}

		drt4xstateFlagLaserTECTemperature          OBJECT-TYPE
			   SYNTAX           INTEGER
								{
								hidden(1),
								read-only(2),
								updateable(3)
								}
			   ACCESS           read-only
			   STATUS           mandatory
			   DESCRIPTION
			   "The value of this object provides the state
			    of the Laser TEC Temperature Analog parameter. (0-Hidden	
			          1-Read-Only, 2-Updateable)."
			   ::= { gx2drt4xAnalogEntry 75}

		drt4xminValueLaserTECTemperature           OBJECT-TYPE
			   SYNTAX           Float
			   ACCESS           read-only
			   STATUS           mandatory
			   DESCRIPTION
			   "The value of this object provides the minimum value
			    the Laser TEC Temperature Analog parameter can achive.
			   This value is a floating point number that is represented as an IEEE 32 bit number."
			   ::= { gx2drt4xAnalogEntry 76}

		drt4xmaxValueLaserTECTemperature           OBJECT-TYPE
			   SYNTAX           Float
			   ACCESS           read-only
			   STATUS           mandatory
			   DESCRIPTION
			   "The value of this object provides the maximum value
			    the Laser TEC Temperature Analog parameter can achive.
			   This value is a floating point number that is represented as an IEEE 32 bit number."
			   ::= { gx2drt4xAnalogEntry 77}

		drt4xalarmStateLaserTECTemperature         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser TEC Temperature Analog parameter."
			   ::= { gx2drt4xAnalogEntry 78}
			     
			   

--   ***************************************************************************

		drt4xlabelLaserTECCurrent              OBJECT-TYPE
			   SYNTAX           DisplayString (SIZE (0..80))
			   ACCESS           read-only
			   STATUS           optional
			   DESCRIPTION
			   "The value of this object provides the label of the
			    Laser TEC Current Analog parameter."
			   ::= { gx2drt4xAnalogEntry 79}

		drt4xuomLaserTECCurrent                OBJECT-TYPE
			   SYNTAX           DisplayString (SIZE (0..80))
			   ACCESS           read-only
			   STATUS           optional
			   DESCRIPTION
			   "The value of this object provides the Unit of Measure of the
			    Laser TEC Current Analog parameter."
			   ::= { gx2drt4xAnalogEntry 80}

		drt4xmajorHighLaserTECCurrent          OBJECT-TYPE
			   SYNTAX           Float 
			   ACCESS           read-only
			   STATUS           mandatory
			   DESCRIPTION
			   "The value of this object provides the Major High alarm value
			    of the Laser TEC Current Analog parameter.
			   This value is a floating point number that is represented as an IEEE 32 bit number."
			   ::= { gx2drt4xAnalogEntry 81}


		drt4xmajorLowLaserTECCurrent           OBJECT-TYPE
			   SYNTAX           Float 
			   ACCESS           read-only
			   STATUS           mandatory
			   DESCRIPTION
			   "The value of this object provides the Major Low alarm value
			    of the Laser TEC Current Analog parameter.
			   This value is a floating point number that is represented as an IEEE 32 bit number."
			   ::= { gx2drt4xAnalogEntry 82}

		drt4xminorHighLaserTECCurrent          OBJECT-TYPE
			   SYNTAX           Float
			   ACCESS           read-only
			   STATUS           mandatory
			   DESCRIPTION
			   "The value of this object provides the Minor High alarm value
			    of the Laser TEC Current Analog parameter.
			   This value is a floating point number that is represented as an IEEE 32 bit number."
			   ::= { gx2drt4xAnalogEntry 83}

		drt4xminorLowLaserTECCurrent           OBJECT-TYPE
			   SYNTAX           Float 
			   ACCESS           read-only
			   STATUS           mandatory
			   DESCRIPTION
			   "The value of this object provides the Minor Low alarm value
			    of the Laser TEC Current Analog parameter.
			   This value is a floating point number that is represented as an IEEE 32 bit number."
			   ::= { gx2drt4xAnalogEntry 84}

		drt4xvalueLaserTECCurrent     	  OBJECT-TYPE
			   SYNTAX           Float 
			   ACCESS           read-only
			   STATUS           mandatory
			   DESCRIPTION
			   "The value of this object provides the Current value
			    of the Laser TEC Current Analog parameter.
			   This value is a floating point number that is represented as an IEEE 32 bit number."
			   ::= { gx2drt4xAnalogEntry 85}

		drt4xstateFlagLaserTECCurrent          OBJECT-TYPE
			   SYNTAX           INTEGER
								{
								hidden(1),
								read-only(2),
								updateable(3)
								}
			   ACCESS           read-only
			   STATUS           mandatory
			   DESCRIPTION
			   "The value of this object provides the state
			    of the Laser TEC Current Analog parameter. (0-Hidden	
			          1-Read-Only, 2-Updateable)."
			   ::= { gx2drt4xAnalogEntry 86}

		drt4xminValueLaserTECCurrent           OBJECT-TYPE
			   SYNTAX           Float
			   ACCESS           read-only
			   STATUS           mandatory
			   DESCRIPTION
			   "The value of this object provides the minimum value
			    the Laser TEC Current Analog parameter can achive.
			   This value is a floating point number that is represented as an IEEE 32 bit number."
			   ::= { gx2drt4xAnalogEntry 87}

		drt4xmaxValueLaserTECCurrent           OBJECT-TYPE
			   SYNTAX           Float
			   ACCESS           read-only
			   STATUS           mandatory
			   DESCRIPTION
			   "The value of this object provides the maximum value
			    the Laser TEC Current Analog parameter can achive.
			   This value is a floating point number that is represented as an IEEE 32 bit number."
			   ::= { gx2drt4xAnalogEntry 88}

		drt4xalarmStateLaserTECCurrent         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser TEC Current Analog parameter."
			   ::= { gx2drt4xAnalogEntry 89}
			     
			   


--   ***************************************************************************	          
    		drt4xlabel12VCurrent           OBJECT-TYPE
			   SYNTAX           DisplayString (SIZE (0..80))
			   ACCESS           read-only
			   STATUS           optional
			   DESCRIPTION
			   "The value of this object provides the label of the
			    12v power supply Current Analog parameter."
			   ::= { gx2drt4xAnalogEntry 90}

		drt4xuom12VCurrent             OBJECT-TYPE
			   SYNTAX           DisplayString (SIZE (0..80))
			   ACCESS           read-only
			   STATUS           optional
			   DESCRIPTION
			   "The value of this object provides the Unit of Measure of the
			    12v power supply Current Analog parameter."
			   ::= { gx2drt4xAnalogEntry 91}

		drt4xmajorHigh12VCurrent       OBJECT-TYPE
			   SYNTAX           Float 
			   ACCESS           read-only
			   STATUS           mandatory
			   DESCRIPTION
			   "The value of this object provides the Major High alarm value
			    of the 12v power supply Current Analog parameter.
			   This value is a floating point number that is represented as an IEEE 32 bit number."
			   ::= { gx2drt4xAnalogEntry 92}


		drt4xmajorLow12VCurrent        OBJECT-TYPE
			   SYNTAX           Float 
			   ACCESS           read-only
			   STATUS           mandatory
			   DESCRIPTION
			   "The value of this object provides the Major Low alarm value
			    of the 12v power supply Current Analog parameter.
			   This value is a floating point number that is represented as an IEEE 32 bit number."
			   ::= { gx2drt4xAnalogEntry 93}

		drt4xminorHigh12VCurrent       OBJECT-TYPE
			   SYNTAX           Float
			   ACCESS           read-only
			   STATUS           mandatory
			   DESCRIPTION
			   "The value of this object provides the Minor High alarm value
			    of the 12v power supply Current Analog parameter.
			   This value is a floating point number that is represented as an IEEE 32 bit number."
			   ::= { gx2drt4xAnalogEntry 94}

		drt4xminorLow12VCurrent        OBJECT-TYPE
			   SYNTAX           Float 
			   ACCESS           read-only
			   STATUS           mandatory
			   DESCRIPTION
			   "The value of this object provides the Minor Low alarm value
			    of the 12v power supply Current Analog parameter.
			   This value is a floating point number that is represented as an IEEE 32 bit number."
			   ::= { gx2drt4xAnalogEntry 95}

		drt4xvalue12VCurrent  	  OBJECT-TYPE
			   SYNTAX           Float 
			   ACCESS           read-only
			   STATUS           mandatory
			   DESCRIPTION
			   "The value of this object provides the Current value
			    of the 12v power supply Current parameter.
			   This value is a floating point number that is represented as an IEEE 32 bit number."
			   ::= { gx2drt4xAnalogEntry 96}

		drt4xstateFlag12VCurrent       OBJECT-TYPE
			   SYNTAX           INTEGER
								{
								hidden(1),
								read-only(2),
								updateable(3)
								}
			   ACCESS           read-only
			   STATUS           mandatory
			   DESCRIPTION
			   "The value of this object provides the state
			    of the 12v power supply Current Analog parameter. (0-Hidden	
			          1-Read-Only, 2-Updateable)."
			   ::= { gx2drt4xAnalogEntry 97}

		drt4xminValue12VCurrent        OBJECT-TYPE
			   SYNTAX           Float
			   ACCESS           read-only
			   STATUS           mandatory
			   DESCRIPTION
			   "The value of this object provides the minimum value
			    the 12v power supply Current Analog parameter can achive.
			   This value is a floating point number that is represented as an IEEE 32 bit number."
			   ::= { gx2drt4xAnalogEntry 98}

		drt4xmaxValue12VCurrent        OBJECT-TYPE
			   SYNTAX           Float
			   ACCESS           read-only
			   STATUS           mandatory
			   DESCRIPTION
			   "The value of this object provides the maximum value
			    the 12v power supply Current Analog parameter can achive.
			   This value is a floating point number that is represented as an IEEE 32 bit number."
			   ::= { gx2drt4xAnalogEntry 99}

        drt4xalarmState12VCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v power supply Current Analog parameter."
			   ::= { gx2drt4xAnalogEntry 100}
			   


--   ***************************************************************************
		drt4xlabelModTemp              OBJECT-TYPE
			   SYNTAX           DisplayString (SIZE (0..80))
			   ACCESS           read-only
			   STATUS           optional
			   DESCRIPTION
			   "The value of this object provides the label of the
			    Module Temperature Analog parameter."
			   ::= { gx2drt4xAnalogEntry 101}

		drt4xuomModTemp                OBJECT-TYPE
			   SYNTAX           DisplayString (SIZE (0..80))
			   ACCESS           read-only
			   STATUS           optional
			   DESCRIPTION
			   "The value of this object provides the Unit of Measure of the
			    Module Temperature Analog parameter."
			   ::= { gx2drt4xAnalogEntry 102}

		drt4xmajorHighModTemp          OBJECT-TYPE
			   SYNTAX           Float 
			   ACCESS           read-only
			   STATUS           mandatory
			   DESCRIPTION
			   "The value of this object provides the Major High alarm value
			    of the Module Temperature Analog parameter.
			   This value is a floating point number that is represented as an IEEE 32 bit number."
			   ::= { gx2drt4xAnalogEntry 103}


		drt4xmajorLowModTemp           OBJECT-TYPE
			   SYNTAX           Float 
			   ACCESS           read-only
			   STATUS           mandatory
			   DESCRIPTION
			   "The value of this object provides the Major Low alarm value
			    of the Module Temperature Analog parameter.
			   This value is a floating point number that is represented as an IEEE 32 bit number."
			   ::= { gx2drt4xAnalogEntry 104}

		drt4xminorHighModTemp          OBJECT-TYPE
			   SYNTAX           Float
			   ACCESS           read-only
			   STATUS           mandatory
			   DESCRIPTION
			   "The value of this object provides the Minor High alarm value
			    of the Module Temperature Analog parameter.
			   This value is a floating point number that is represented as an IEEE 32 bit number."
			   ::= { gx2drt4xAnalogEntry 105}

		drt4xminorLowModTemp           OBJECT-TYPE
			   SYNTAX           Float 
			   ACCESS           read-only
			   STATUS           mandatory
			   DESCRIPTION
			   "The value of this object provides the Minor Low alarm value
			    of the Module Temperature Analog parameter.
			   This value is a floating point number that is represented as an IEEE 32 bit number."
			   ::= { gx2drt4xAnalogEntry 106}

		drt4xvalueModTemp    	   OBJECT-TYPE
			   SYNTAX           Float 
			   ACCESS           read-only
			   STATUS           mandatory
			   DESCRIPTION
			   "The value of this object provides the Current value
			    of the Module Temperature Analog parameter.
			   This value is a floating point number that is represented as an IEEE 32 bit number."
			   ::= { gx2drt4xAnalogEntry 107}

		drt4xstateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2drt4xAnalogEntry 108}

		drt4xminValueModTemp           OBJECT-TYPE
			   SYNTAX           Float
			   ACCESS           read-only
			   STATUS           mandatory
			   DESCRIPTION
			   "The value of this object provides the minimum value
			    the Module Temperature Analog parameter can achive.
			   This value is a floating point number that is represented as an IEEE 32 bit number."
			   ::= { gx2drt4xAnalogEntry 109}

		drt4xmaxValueModTemp           OBJECT-TYPE
			   SYNTAX           Float
			   ACCESS           read-only
			   STATUS           mandatory
			   DESCRIPTION
			   "The value of this object provides the maximum value
			    the Module Temperature Analog parameter can achive.
			   This value is a floating point number that is represented as an IEEE 32 bit number."
			   ::= { gx2drt4xAnalogEntry 110}

		drt4xalarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2drt4xAnalogEntry 111}
			     
			   
--   ***************************************************************************
		drt4xlabelFanCurrent           OBJECT-TYPE
			   SYNTAX           DisplayString (SIZE (0..80))
			   ACCESS           read-only
			   STATUS           optional
			   DESCRIPTION
			   "The value of this object provides the label of the
			    Fan Current Analog parameter."
			   ::= { gx2drt4xAnalogEntry 112}

		drt4xuomFanCurrent             OBJECT-TYPE
			   SYNTAX           DisplayString (SIZE (0..80))
			   ACCESS           read-only
			   STATUS           optional
			   DESCRIPTION
			   "The value of this object provides the Unit of Measure of the
			    Fan Current Analog parameter."
			   ::= { gx2drt4xAnalogEntry 113}

		drt4xmajorHighFanCurrent       OBJECT-TYPE
			   SYNTAX           Float 
			   ACCESS           read-only
			   STATUS           mandatory
			   DESCRIPTION
			   "The value of this object provides the Major High alarm value
			    of the Fan Current Analog parameter.This value is a floating 
			    point number that is represented as an IEEE 32 bit number."
			   ::= { gx2drt4xAnalogEntry 114}


		drt4xmajorLowFanCurrent        OBJECT-TYPE
			   SYNTAX           Float 
			   ACCESS           read-only
			   STATUS           mandatory
			   DESCRIPTION
			   "The value of this object provides the Major Low alarm value
			    of the Fan Current Analog parameter.This value is a floating
			    point number that is represented as an IEEE 32 bit number."
			   ::= { gx2drt4xAnalogEntry 115}

		drt4xminorHighFanCurrent       OBJECT-TYPE
			   SYNTAX           Float
			   ACCESS           read-only
			   STATUS           mandatory
			   DESCRIPTION
			   "The value of this object provides the Minor High alarm value
			    of the Fan Current Analog parameter.This value is a floating 
			    point number that is represented as an IEEE 32 bit number."
			   ::= { gx2drt4xAnalogEntry 116}

		drt4xminorLowFanCurrent        OBJECT-TYPE
			   SYNTAX           Float 
			   ACCESS           read-only
			   STATUS           mandatory
			   DESCRIPTION
			   "The value of this object provides the Minor Low alarm value
			    of the Fan Current Analog parameter.This value is a floating 
			    point number that is represented as an IEEE 32 bit number."
			   ::= { gx2drt4xAnalogEntry 117}

		drt4xvalueFanCurrent    	OBJECT-TYPE
			   SYNTAX           Float 
			   ACCESS           read-only
			   STATUS           mandatory
			   DESCRIPTION
			   "The value of this object provides the Current value
			    of the Fan Current Analog parameter.This value is a floating 
			    point number that is represented as an IEEE 32 bit number."
			   ::= { gx2drt4xAnalogEntry 118}

		drt4xstateFlagFanCurrent       OBJECT-TYPE
			   SYNTAX           INTEGER
								{
								hidden(1),
								read-only(2),
								updateable(3)
								}
			   ACCESS           read-only
			   STATUS           mandatory
			   DESCRIPTION
			   "The value of this object provides the state
			    of the Fan Current Analog parameter. (0-Hidden	
			          1-Read-Only, 2-Updateable)."
			   ::= { gx2drt4xAnalogEntry 119}

		drt4xminValueFanCurrent        OBJECT-TYPE
			   SYNTAX           Float
			   ACCESS           read-only
			   STATUS           mandatory
			   DESCRIPTION
			   "The value of this object provides the minimum value
			    the Fan Current Analog parameter can achive. This value is a 
			    floating point number that is represented as an IEEE 32 bit number."
			   ::= { gx2drt4xAnalogEntry 120}

		drt4xmaxValueFanCurrent        OBJECT-TYPE
			   SYNTAX           Float
			   ACCESS           read-only
			   STATUS           mandatory
			   DESCRIPTION
			   "The value of this object provides the maximum value
			    the Fan Current Analog parameter can achive. This value is a floating
			    point number that is represented as an IEEE 32 bit number."
			   ::= { gx2drt4xAnalogEntry 121}

        drt4xalarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2drt4xAnalogEntry 122}  
			   
    			   
--   ***************************************************************************
--   ********************************** DIGITAL ********************************
--   ***************************************************************************
		gx2drt4xDigitalTableIndex              OBJECT-TYPE
			   SYNTAX           INTEGER (1..4294967295)
			   ACCESS           read-only
			   STATUS           mandatory
			   DESCRIPTION
			   "The value of this object identifies the network
			    element. This index is equal to the
			    hfcCommonTableIndex for the same element."
               ::= { gx2drt4xDigitalEntry 1}
--   ***************************************************************************
         	drt4xlabelBaseITUChannel	OBJECT-TYPE
			   SYNTAX       		DisplayString (SIZE (0..80))         
			   ACCESS           	read-only
			   STATUS           	optional
			   DESCRIPTION
			   "The value of this object provides the label of the
			    Base ITU Channel Digital parameter." 
			   ::= { gx2drt4xDigitalEntry 2}

		drt4xenumBaseITUChannel   	OBJECT-TYPE
			   SYNTAX       		DisplayString (SIZE (0..80))         
			   ACCESS           	read-only
			   STATUS           	optional
			   DESCRIPTION
			   "The value of this object represents the Enumeration values
			    possible for the Digital parameter. Each Enumerated values is
			    separated by a comma. "
			   ::= { gx2drt4xDigitalEntry 3}


		drt4xvalueBaseITUChannel         	OBJECT-TYPE
			   SYNTAX					INTEGER{
			   							ch20(1),
			   							ch24(2),
			   							ch28(3),
			   							ch32(4),
			   							ch36(5),
			   							ch40(6),
			   							ch44(7),
			   							ch48(8),
			   							ch52(9),
			   							ch56(10)
			   							}			   					    	
			   ACCESS           	read-only
			   STATUS           	mandatory
			   DESCRIPTION
			   "The value of this object is the value of the Base ITU Channel.
			   There are 10 possible value: 1-ch20, 2-ch24, 3-ch28, 4-ch32,
			   5-ch36, 6-ch40, 7-ch44, 8-ch48, 9-ch52, 10-ch56."
			   ::= { gx2drt4xDigitalEntry 4}

		drt4xstateflagBaseITUChannel     	OBJECT-TYPE
			   SYNTAX       		INTEGER
								{
								hidden(1),
								readOnly(2),
								updateable(3)
								}
			   ACCESS           	read-only
			   STATUS           	mandatory
			   DESCRIPTION
			   "The value of this object provides the state
			    of the the parameter. (0-Hidden 1-Read-Only, 2-Updateable)."
			   ::= { gx2drt4xDigitalEntry 5}
			   		  
                
--   ***************************************************************************
         	drt4xlabelITUChannelSetting   OBJECT-TYPE
			   SYNTAX       		DisplayString (SIZE (0..80))         
			   ACCESS           	read-write
			   STATUS           	optional
			   DESCRIPTION
			   "The value of this object provides the label of the
			    ITU Channel Setting Digital parameter." 
			   ::= { gx2drt4xDigitalEntry 6}

		drt4xenumITUChannelSetting   	OBJECT-TYPE
			   SYNTAX       		DisplayString (SIZE (0..80))         
			   ACCESS           	read-only
			   STATUS           	optional
			   DESCRIPTION
			   "The value of this object represents the Enumeration values
			    possible for the Digital parameter. Each Enumerated values is
			    separated by a comma. "
			   ::= { gx2drt4xDigitalEntry 7}


		drt4xvalueITUChannelSetting         	OBJECT-TYPE
			   SYNTAX					INTEGER{
			   							base(1),
			   							basePlus1(2),
			   							basePlus2(3),
			   							basePlus3(4)
			   							}			   					    	
			   ACCESS           	read-write
			   STATUS           	mandatory
			   DESCRIPTION
			   "The value of this object is the value of the ITU Channel Setting.
			   There are 4 possible value: 1-base (base ITU channel), 2-basePlus1
                     (base ITU Channel + 1), 3-basePlus2 (base ITU Channel + 2),
                     and 4-basePlus3 (base ITU Channel + 3)."
			   ::= { gx2drt4xDigitalEntry 8}

		drt4xstateflagITUChannelSetting     	OBJECT-TYPE
			   SYNTAX       		INTEGER
								{
								hidden(1),
								readOnly(2),
								updateable(3)
								}
			   ACCESS           	read-only
			   STATUS           	mandatory
			   DESCRIPTION
			   "The value of this object provides the state
			    of the the parameter. (0-Hidden 1-Read-Only, 2-Updateable)."
			   ::= { gx2drt4xDigitalEntry 9}
			   		  
 		   		   
--   ***************************************************************************
         	drt4xlabelOpticalPowerSetting          OBJECT-TYPE
			   SYNTAX       		DisplayString (SIZE (0..80))         
			   ACCESS           	read-only
			   STATUS           	optional
			   DESCRIPTION
			   "The value of this object provides the label of the
			    Optical Power Setting Digital parameter. This parameter
                      defines the operating power level of the DRT-4X" 
			   ::= { gx2drt4xDigitalEntry 10}

		drt4xenumOpticalPowerSetting               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2drt4xDigitalEntry 11}


		drt4xvalueOpticalPowerSetting         	OBJECT-TYPE
			   SYNTAX					INTEGER{
			   							low(1),
			   							high(2)
			   							}			   					    	
			   ACCESS           	read-write
			   STATUS           	mandatory
			   DESCRIPTION
			   "The value of this object is the setting of the Optical Power.
			   There are two possible value: 1-low, and 2-high."
			   ::= { gx2drt4xDigitalEntry 12}

		drt4xstateflagOpticalPowerSetting     	OBJECT-TYPE
			   SYNTAX       		INTEGER
								{
								hidden(1),
								readOnly(2),
								updateable(3)
								}
			   ACCESS           	read-only
			   STATUS           	mandatory
			   DESCRIPTION
			   "The value of this object provides the state
			    of the the parameter. (0-Hidden 1-Read-Only, 2-Updateable)."
			   ::= { gx2drt4xDigitalEntry 13}
			   		   		   

--   ***************************************************************************
         	drt4xlabelLaserControl          OBJECT-TYPE
			   SYNTAX       		DisplayString (SIZE (0..80))         
			   ACCESS           	read-only
			   STATUS           	optional
			   DESCRIPTION
			   "The value of this object provides the label of the
			    Laser Control Digital parameter.  The Laser Control allows 
                      the DRT-4X laser to be turned off or on."
			   ::= { gx2drt4xDigitalEntry 14}

		drt4xenumLaserControl               	OBJECT-TYPE
			   SYNTAX       		DisplayString (SIZE (0..80))         
			   ACCESS           	read-only
			   STATUS           	optional
			   DESCRIPTION
			   "The value of this object represents the Enumeration values
			    possible for the Digital parameter. Each Enumerated values is
			    separated by a comma. "
			   ::= { gx2drt4xDigitalEntry 15}


		drt4xvalueLaserControl         	OBJECT-TYPE
			   SYNTAX					INTEGER{
			   							off(1),
			   							on(2)
			   							}			   					    	
			   ACCESS           	read-write
			   STATUS           	mandatory
			   DESCRIPTION
			   "The value of this object represents the Laser Control.
			   There are two possible values: 1-off, and 2-on."
			   ::= { gx2drt4xDigitalEntry 16}

		drt4xstateflagLaserControl     	OBJECT-TYPE
			   SYNTAX       		INTEGER
								{
								hidden(1),
								readOnly(2),
								updateable(3)
								}
			   ACCESS           	read-only
			   STATUS           	mandatory
			   DESCRIPTION
			   "The value of this object provides the state
			    of the the parameter. (0-Hidden 1-Read-Only, 2-Updateable)."
			   ::= { gx2drt4xDigitalEntry 17}
			   		   		   
--   ***************************************************************************
         drt4xlabelFactoryDefaultReset           OBJECT-TYPE
			   SYNTAX       		DisplayString (SIZE (0..80))         
			   ACCESS           	read-only
			   STATUS           	optional
			   DESCRIPTION
			   "The value of this object provides the label of the
			    Factory Default Reset  Digital parameter."
			   ::= { gx2drt4xDigitalEntry 18}

		drt4xenumFactoryDefaultReset               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2drt4xDigitalEntry 19}


		drt4xvalueFactoryDefaultReset         	OBJECT-TYPE
			   SYNTAX       		INTEGER
					    		{
							off(1),
							on(2)
					    		}
			   ACCESS           	read-write
			   STATUS           	mandatory
			   DESCRIPTION
			   "The value of this object is the current value of the parameter."
			   ::= { gx2drt4xDigitalEntry 20}

		drt4xstateflagFactoryDefaultReset     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2drt4xDigitalEntry 21} 
			   
   
--   ***************************************************************************
--   ********************************** STATUS *********************************
--   ***************************************************************************
		gx2drt4xStatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2drt4xStatusEntry 1}

--   ***************************************************************************
		drt4xlabelBoot               	OBJECT-TYPE
			   SYNTAX       		DisplayString (SIZE (0..80))         
			   ACCESS           	read-only
			   STATUS           	optional
			   DESCRIPTION
			   "The value of this object provides the label of the
			    Boot Status  parameter."
			   ::= { gx2drt4xStatusEntry 2}

		drt4xvalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drt4xStatusEntry 3}

		drt4xstateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2drt4xStatusEntry  4}

--   ***************************************************************************
		drt4xlabelFlash               	OBJECT-TYPE
			   SYNTAX       		DisplayString (SIZE (0..80))         
			   ACCESS           	read-only
			   STATUS           	optional
			   DESCRIPTION
			   "The value of this object provides the label of the
			    Flash Status  parameter."
			   ::= { gx2drt4xStatusEntry 5}

		drt4xvalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drt4xStatusEntry 6}

		drt4xstateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2drt4xStatusEntry  7}


--   ***************************************************************************
		drt4xlabelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2drt4xStatusEntry 8}

		drt4xvalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drt4xStatusEntry 9}

		drt4xstateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2drt4xStatusEntry  10}


--   ***************************************************************************
		drt4xlabelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2drt4xStatusEntry 11}

		drt4xvalueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drt4xStatusEntry 12}

		drt4xstateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2drt4xStatusEntry  13}

--   ***************************************************************************
		drt4xlabelCalibrationDataCrc               	      OBJECT-TYPE
			   SYNTAX       		DisplayString (SIZE (0..80))         
			   ACCESS           	read-only
			   STATUS           	optional
			   DESCRIPTION
			   "The value of this object provides the label of the
			    Calibration Data CRC parameter."
			   ::= { gx2drt4xStatusEntry 14}

		drt4xvalueCalibrationDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drt4xStatusEntry 15}

		drt4xstateflagCalibrationDataCrc     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2drt4xStatusEntry  16}



--   ***************************************************************************
		drt4xlabelHardwareStatus              OBJECT-TYPE
			   SYNTAX       		DisplayString (SIZE (0..80))         
			   ACCESS           	read-only
			   STATUS           	optional
			   DESCRIPTION
			   "The value of this object provides the label of the
			   Module Hardware Status parameter."
			   ::= { gx2drt4xStatusEntry 17}

		drt4xvalueHardwareStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drt4xStatusEntry 18}

		drt4xstateflagHardwareStatus     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2drt4xStatusEntry  19}


-- ************ FACTORY DATA ****************
		gx2drt4xFactoryTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2drt4xFactoryEntry 1}

		drt4xbootControlByte          	OBJECT-TYPE
			   SYNTAX       		INTEGER
			   ACCESS           	read-only
			   STATUS           	mandatory
			   DESCRIPTION
			   "The value of this object indicates which bank the firmware
			    is currently being boot from."
			   ::= { gx2drt4xFactoryEntry 2}

		drt4xbootStatusByte          	OBJECT-TYPE
			   SYNTAX       		INTEGER
			   ACCESS           	read-only
			   STATUS           	mandatory
			   DESCRIPTION
			   "This object indicates the status of the last boot"
			   ::= { gx2drt4xFactoryEntry 3}

		drt4xbank1CRC          		OBJECT-TYPE
			   SYNTAX       		INTEGER
			   ACCESS           	read-only
			   STATUS           	mandatory
			   DESCRIPTION
			   "This object provides the CRC code of bank 0."
			   ::= { gx2drt4xFactoryEntry 4}

		drt4xbank2CRC          		OBJECT-TYPE
			   SYNTAX       		INTEGER
			   ACCESS           	read-only
			   STATUS           	mandatory
			   DESCRIPTION
			   "This object provides the CRC code of bank 1."
			   ::= { gx2drt4xFactoryEntry 5}

		drt4xprgEEPROMByte          		OBJECT-TYPE
			   SYNTAX       		INTEGER
			   ACCESS           	read-only
			   STATUS           	mandatory
			   DESCRIPTION
			   "This object indicates if the EEPROM has been programmed"
			   ::= { gx2drt4xFactoryEntry 6}

		drt4xfactoryCRC          		OBJECT-TYPE
			   SYNTAX       		INTEGER
			   ACCESS           	read-only
			   STATUS           	mandatory
			   DESCRIPTION
			   "This object provides the CRC code for the Factory data."
			   ::= { gx2drt4xFactoryEntry 7}

		drt4xcalculateCRC          		OBJECT-TYPE
			   SYNTAX       		INTEGER
					    		{
							factory(1),
							alarm(2)
					    		}
			   ACCESS           	read-only
			   STATUS           	mandatory
			   DESCRIPTION
			   "This object indicates which of the Emnums will have the CRC calculated."
			   ::= { gx2drt4xFactoryEntry 8}

		drt4xhourMeter          		OBJECT-TYPE
			   SYNTAX       		INTEGER
			   ACCESS           	read-only
			   STATUS           	mandatory
			   DESCRIPTION
			   "This object provides the hour meter reading of the module."
			   ::= { gx2drt4xFactoryEntry 9}

		drt4xflashPrgCntA          		OBJECT-TYPE
			   SYNTAX       		INTEGER
			   ACCESS           	read-only
			   STATUS           	mandatory
			   DESCRIPTION
			   "This object provides the number of times Bank 0 flash has been 
                      programmed."
			   ::= { gx2drt4xFactoryEntry 10}

		drt4xflashPrgCntB          		OBJECT-TYPE
			   SYNTAX       		INTEGER
			   ACCESS           	read-only
			   STATUS           	mandatory
			   DESCRIPTION
			   "This object provides the number of times Bank 1 flash has been 
                      programmed."
			   ::= { gx2drt4xFactoryEntry 11}

		drt4xflashBankARev          		OBJECT-TYPE
			   SYNTAX       		DisplayString (SIZE (0..80))
			   ACCESS           	read-only
			   STATUS           	mandatory
			   DESCRIPTION
			   "This object provides the revision of flash bank 0."
			   ::= { gx2drt4xFactoryEntry 12}

		drt4xflashBankBRev          		OBJECT-TYPE
			   SYNTAX       		DisplayString (SIZE (0..80))
			   ACCESS           	read-only
			   STATUS           	mandatory
			   DESCRIPTION
			   "This object provides the revision of flash bank 1."
			   ::= { gx2drt4xFactoryEntry 13}
                  
		drt4xSubAgentRev          		OBJECT-TYPE
			   SYNTAX       		DisplayString (SIZE (0..80))
			   ACCESS           	read-only
			   STATUS           	mandatory
			   DESCRIPTION
			   "This object provides the subagent revision of receiver module."
			   ::= { gx2drt4xFactoryEntry 14}

--   ***************************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
--   ***************************************************************************
--   ***************************************************************************

--   ***************************************************************************
--                              Digital Return Transmitter 4X Module traps
--   ***************************************************************************
   trapdrt4xConfigChangeInteger TRAP-TYPE
       ENTERPRISE gx2Drt4x
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapdrt4xConfigChangeDisplayString TRAP-TYPE
       ENTERPRISE gx2Drt4x
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2
        
            
    trapdrt4xModulePlus12CurrentAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Module +12V Supply Current goes out of range.
	 trapAdditionalInfoInteger variable contains current reading of 
	 the this parameter."
    ::= 3
  
    trapdrt4xModuleTempAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Internal Module Temperature goes out of range.
	 trapAdditionalInfoInteger variable contains current reading of 
	 the this parameter."
    ::= 4
  
    trapdrt4xFanCurrentAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Fan Current 
	 parameter goes out of range.
	 trapAdditionalInfoInteger variable contains current reading of 
	 the this parameter."
  ::= 5

  trapdrt4xFlashAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the detects an error during
	Flash memory operations."
  ::= 6
  
  trapdrt4xBankBootAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the detects an error while booting
	from bank 0 or bank 1."
  ::= 7

	trapdrt4xFactoryDataCRCAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 8



	trapdrt4xAlarmDataCRCAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 9

	trapdrt4xCalibrationDataCRCAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Calibration Data CRC is incorrect."
  ::= 10

	trapdrt4xHardwareErrorAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when hardware is abnormal."
  ::= 11

 	trapdrt4xOpticalPowerAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the optical power is out of range."  
  ::= 12

	trapdrt4xTECTemperatureAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the TEC Temperature is out of range."
  ::= 13

	trapdrt4xTECCurrentAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the TEC Current is out of range."
  ::= 14

	trapdrt4xLaserBiasCurrentAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Bias Current is out of range."
  ::= 15

 
	trapdrt4xResetFactoryDefaultAlarm TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Default Reset occurs."
  ::= 16

  
	trapdrt4xLaserOnOffInfo TRAP-TYPE
	ENTERPRISE gx2Drt4x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the When the Laser turns on/off."
  ::= 17
 
  END
