-- file automatically created


TELDAT-TRAP-VRRP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


vrrpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the VRRP event subsystem."
    REVISION "201401200930Z"
    DESCRIPTION "Initial implementation"
        ::= { telEventTraps 179 }


vrrpEventsGroup	OBJECT IDENTIFIER	::= { vrrpTrapsMIB 1 }

vrrpNotifications	OBJECT IDENTIFIER	::= { vrrpTrapsMIB 2 }
vrrpNotificationsPrefix	OBJECT IDENTIFIER	::= { vrrpNotifications 0 }

vrrpEventObjects1 OBJECT-IDENTITY
    STATUS current
    DESCRIPTION
        "Event VRRP.1
        Generic info."
    ::= { vrrpEventsGroup 1 }

vrrp1_generic_info OBJECT-TYPE
    SYNTAX DisplayString
    MAX-ACCESS accessible-for-notify
    STATUS current
    DESCRIPTION
        "Parameter 'generic_info' in event VRRP.1"
    ::= { vrrpEventObjects1 1 }

vrrpEventObjects2 OBJECT-IDENTITY
    STATUS current
    DESCRIPTION
        "Event VRRP.2
        Virtual router event descriptor."
    ::= { vrrpEventsGroup 2 }

vrrp2_interface OBJECT-TYPE
    SYNTAX DisplayString
    MAX-ACCESS accessible-for-notify
    STATUS current
    DESCRIPTION
        "Parameter 'interface' in event VRRP.2"
    ::= { vrrpEventObjects2 1 }

vrrp2_vrid OBJECT-TYPE
    SYNTAX Integer32
    MAX-ACCESS accessible-for-notify
    STATUS current
    DESCRIPTION
        "Parameter 'vrid' in event VRRP.2"
    ::= { vrrpEventObjects2 2 }

vrrp2_state OBJECT-TYPE
    SYNTAX DisplayString
    MAX-ACCESS accessible-for-notify
    STATUS current
    DESCRIPTION
        "Parameter 'state' in event VRRP.2"
    ::= { vrrpEventObjects2 3 }

vrrp2_event OBJECT-TYPE
    SYNTAX DisplayString
    MAX-ACCESS accessible-for-notify
    STATUS current
    DESCRIPTION
        "Parameter 'event' in event VRRP.2"
    ::= { vrrpEventObjects2 4 }

vrrpEventObjects3 OBJECT-IDENTITY
    STATUS current
    DESCRIPTION
        "Event VRRP.3
        A virtual router has changed its state."
    ::= { vrrpEventsGroup 3 }

vrrp3_interface OBJECT-TYPE
    SYNTAX DisplayString
    MAX-ACCESS accessible-for-notify
    STATUS current
    DESCRIPTION
        "Parameter 'interface' in event VRRP.3"
    ::= { vrrpEventObjects3 1 }

vrrp3_vrid OBJECT-TYPE
    SYNTAX Integer32
    MAX-ACCESS accessible-for-notify
    STATUS current
    DESCRIPTION
        "Parameter 'vrid' in event VRRP.3"
    ::= { vrrpEventObjects3 2 }

vrrp3_new_state OBJECT-TYPE
    SYNTAX DisplayString
    MAX-ACCESS accessible-for-notify
    STATUS current
    DESCRIPTION
        "Parameter 'new_state' in event VRRP.3"
    ::= { vrrpEventObjects3 3 }

vrrpEventObjects4 OBJECT-IDENTITY
    STATUS current
    DESCRIPTION
        "Event VRRP.4
        An error has ocurred while receiving a VRRP Advertisement."
    ::= { vrrpEventsGroup 4 }

vrrp4_error_message OBJECT-TYPE
    SYNTAX DisplayString
    MAX-ACCESS accessible-for-notify
    STATUS current
    DESCRIPTION
        "Parameter 'error_message' in event VRRP.4"
    ::= { vrrpEventObjects4 1 }

vrrpEventObjects5 OBJECT-IDENTITY
    STATUS current
    DESCRIPTION
        "Event VRRP.5
        An error associated to a virtual router has ocurred while receiving a
        VRRP Advertisement."
    ::= { vrrpEventsGroup 5 }

vrrp5_interface OBJECT-TYPE
    SYNTAX DisplayString
    MAX-ACCESS accessible-for-notify
    STATUS current
    DESCRIPTION
        "Parameter 'interface' in event VRRP.5"
    ::= { vrrpEventObjects5 1 }

vrrp5_vrid OBJECT-TYPE
    SYNTAX Integer32
    MAX-ACCESS accessible-for-notify
    STATUS current
    DESCRIPTION
        "Parameter 'vrid' in event VRRP.5"
    ::= { vrrpEventObjects5 2 }

vrrp5_error_message OBJECT-TYPE
    SYNTAX DisplayString
    MAX-ACCESS accessible-for-notify
    STATUS current
    DESCRIPTION
        "Parameter 'error_message' in event VRRP.5"
    ::= { vrrpEventObjects5 3 }

vrrpEventObjects6 OBJECT-IDENTITY
    STATUS current
    DESCRIPTION
        "Event VRRP.6
        A VRRP Advertisement has been sent."
    ::= { vrrpEventsGroup 6 }

vrrp6_interface OBJECT-TYPE
    SYNTAX DisplayString
    MAX-ACCESS accessible-for-notify
    STATUS current
    DESCRIPTION
        "Parameter 'interface' in event VRRP.6"
    ::= { vrrpEventObjects6 1 }

vrrp6_vrid OBJECT-TYPE
    SYNTAX Integer32
    MAX-ACCESS accessible-for-notify
    STATUS current
    DESCRIPTION
        "Parameter 'vrid' in event VRRP.6"
    ::= { vrrpEventObjects6 2 }

vrrp6_priority OBJECT-TYPE
    SYNTAX Integer32
    MAX-ACCESS accessible-for-notify
    STATUS current
    DESCRIPTION
        "Parameter 'priority' in event VRRP.6"
    ::= { vrrpEventObjects6 3 }

vrrp6_checksum OBJECT-TYPE
    SYNTAX Integer32
    MAX-ACCESS accessible-for-notify
    STATUS current
    DESCRIPTION
        "Parameter 'checksum' in event VRRP.6"
    ::= { vrrpEventObjects6 4 }

vrrpEventObjects7 OBJECT-IDENTITY
    STATUS current
    DESCRIPTION
        "Event VRRP.7
        A gratuitous ARP-request has been sent."
    ::= { vrrpEventsGroup 7 }

vrrp7_virtual_ip_address OBJECT-TYPE
    SYNTAX IpAddress
    MAX-ACCESS accessible-for-notify
    STATUS current
    DESCRIPTION
        "Parameter 'virtual_ip_address' in event VRRP.7"
    ::= { vrrpEventObjects7 1 }

vrrp7_virtual_mac_address OBJECT-TYPE
    SYNTAX Integer32
    MAX-ACCESS accessible-for-notify
    STATUS current
    DESCRIPTION
        "Parameter 'virtual_mac_address' in event VRRP.7"
    ::= { vrrpEventObjects7 2 }

vrrpEventObjects8 OBJECT-IDENTITY
    STATUS current
    DESCRIPTION
        "Event VRRP.8
        An internal error has ocurred."
    ::= { vrrpEventsGroup 8 }

vrrp8_error_message OBJECT-TYPE
    SYNTAX DisplayString
    MAX-ACCESS accessible-for-notify
    STATUS current
    DESCRIPTION
        "Parameter 'error_message' in event VRRP.8"
    ::= { vrrpEventObjects8 1 }

vrrpEventObjects9 OBJECT-IDENTITY
    STATUS current
    DESCRIPTION
        "Event VRRP.9
        Waiting for preempt delay timeout."
    ::= { vrrpEventsGroup 9 }

vrrp9_interface OBJECT-TYPE
    SYNTAX DisplayString
    MAX-ACCESS accessible-for-notify
    STATUS current
    DESCRIPTION
        "Parameter 'interface' in event VRRP.9"
    ::= { vrrpEventObjects9 1 }

vrrp9_vrid OBJECT-TYPE
    SYNTAX Integer32
    MAX-ACCESS accessible-for-notify
    STATUS current
    DESCRIPTION
        "Parameter 'vrid' in event VRRP.9"
    ::= { vrrpEventObjects9 2 }

vrrp9_state OBJECT-TYPE
    SYNTAX DisplayString
    MAX-ACCESS accessible-for-notify
    STATUS current
    DESCRIPTION
        "Parameter 'state' in event VRRP.9"
    ::= { vrrpEventObjects9 3 }

vrrp9_timeout OBJECT-TYPE
    SYNTAX Integer32
    MAX-ACCESS accessible-for-notify
    STATUS current
    DESCRIPTION
        "Parameter 'timeout' in event VRRP.9"
    ::= { vrrpEventObjects9 4 }

vrrp9_sec OBJECT-TYPE
    SYNTAX DisplayString
    MAX-ACCESS accessible-for-notify
    STATUS current
    DESCRIPTION
        "Parameter 'sec' in event VRRP.9"
    ::= { vrrpEventObjects9 5 }

vrrpEventObjects10 OBJECT-IDENTITY
    STATUS current
    DESCRIPTION
        "Event VRRP.10
        Changing priority due to tracking."
    ::= { vrrpEventsGroup 10 }

vrrp10_interface OBJECT-TYPE
    SYNTAX DisplayString
    MAX-ACCESS accessible-for-notify
    STATUS current
    DESCRIPTION
        "Parameter 'interface' in event VRRP.10"
    ::= { vrrpEventObjects10 1 }

vrrp10_vrid OBJECT-TYPE
    SYNTAX Integer32
    MAX-ACCESS accessible-for-notify
    STATUS current
    DESCRIPTION
        "Parameter 'vrid' in event VRRP.10"
    ::= { vrrpEventObjects10 2 }

vrrp10_oldPriority OBJECT-TYPE
    SYNTAX Integer32
    MAX-ACCESS accessible-for-notify
    STATUS current
    DESCRIPTION
        "Parameter 'oldPriority' in event VRRP.10"
    ::= { vrrpEventObjects10 3 }

vrrp10_newPriority OBJECT-TYPE
    SYNTAX Integer32
    MAX-ACCESS accessible-for-notify
    STATUS current
    DESCRIPTION
        "Parameter 'newPriority' in event VRRP.10"
    ::= { vrrpEventObjects10 4 }

vrrpEventObjects11 OBJECT-IDENTITY
    STATUS current
    DESCRIPTION
        "Event VRRP.11
        Changing delay state."
    ::= { vrrpEventsGroup 11 }

vrrp11_interface OBJECT-TYPE
    SYNTAX DisplayString
    MAX-ACCESS accessible-for-notify
    STATUS current
    DESCRIPTION
        "Parameter 'interface' in event VRRP.11"
    ::= { vrrpEventObjects11 1 }

vrrp11_vrid OBJECT-TYPE
    SYNTAX Integer32
    MAX-ACCESS accessible-for-notify
    STATUS current
    DESCRIPTION
        "Parameter 'vrid' in event VRRP.11"
    ::= { vrrpEventObjects11 2 }

vrrp11_state OBJECT-TYPE
    SYNTAX DisplayString
    MAX-ACCESS accessible-for-notify
    STATUS current
    DESCRIPTION
        "Parameter 'state' in event VRRP.11"
    ::= { vrrpEventObjects11 3 }

vrrp11_reason OBJECT-TYPE
    SYNTAX DisplayString
    MAX-ACCESS accessible-for-notify
    STATUS current
    DESCRIPTION
        "Parameter 'reason' in event VRRP.11"
    ::= { vrrpEventObjects11 4 }

vrrpEventObjects12 OBJECT-IDENTITY
    STATUS current
    DESCRIPTION
        "Event VRRP.12
        Changing preemption exception state."
    ::= { vrrpEventsGroup 12 }

vrrp12_interface OBJECT-TYPE
    SYNTAX DisplayString
    MAX-ACCESS accessible-for-notify
    STATUS current
    DESCRIPTION
        "Parameter 'interface' in event VRRP.12"
    ::= { vrrpEventObjects12 1 }

vrrp12_vrid OBJECT-TYPE
    SYNTAX Integer32
    MAX-ACCESS accessible-for-notify
    STATUS current
    DESCRIPTION
        "Parameter 'vrid' in event VRRP.12"
    ::= { vrrpEventObjects12 2 }

vrrp12_state OBJECT-TYPE
    SYNTAX DisplayString
    MAX-ACCESS accessible-for-notify
    STATUS current
    DESCRIPTION
        "Parameter 'state' in event VRRP.12"
    ::= { vrrpEventObjects12 3 }

vrrp12_reason OBJECT-TYPE
    SYNTAX DisplayString
    MAX-ACCESS accessible-for-notify
    STATUS current
    DESCRIPTION
        "Parameter 'reason' in event VRRP.12"
    ::= { vrrpEventObjects12 4 }

vrrpEventObjects13 OBJECT-IDENTITY
    STATUS current
    DESCRIPTION
        "Event VRRP.13
        An advertisement timeout has occurred too fast."
    ::= { vrrpEventsGroup 13 }

vrrp13_interface OBJECT-TYPE
    SYNTAX DisplayString
    MAX-ACCESS accessible-for-notify
    STATUS current
    DESCRIPTION
        "Parameter 'interface' in event VRRP.13"
    ::= { vrrpEventObjects13 1 }

vrrp13_vrid OBJECT-TYPE
    SYNTAX Integer32
    MAX-ACCESS accessible-for-notify
    STATUS current
    DESCRIPTION
        "Parameter 'vrid' in event VRRP.13"
    ::= { vrrpEventObjects13 2 }

vrrpEventObjects14 OBJECT-IDENTITY
    STATUS current
    DESCRIPTION
        "Event VRRP.14
        The curernt key is not valid."
    ::= { vrrpEventsGroup 14 }

vrrp14_interface OBJECT-TYPE
    SYNTAX DisplayString
    MAX-ACCESS accessible-for-notify
    STATUS current
    DESCRIPTION
        "Parameter 'interface' in event VRRP.14"
    ::= { vrrpEventObjects14 1 }

vrrp14_vrid OBJECT-TYPE
    SYNTAX Integer32
    MAX-ACCESS accessible-for-notify
    STATUS current
    DESCRIPTION
        "Parameter 'vrid' in event VRRP.14"
    ::= { vrrpEventObjects14 2 }

vrrp14_reason OBJECT-TYPE
    SYNTAX DisplayString
    MAX-ACCESS accessible-for-notify
    STATUS current
    DESCRIPTION
        "Parameter 'reason' in event VRRP.14"
    ::= { vrrpEventObjects14 3 }

vrrpEventObjects15 OBJECT-IDENTITY
    STATUS current
    DESCRIPTION
        "Event VRRP.15
        Information about the authentication."
    ::= { vrrpEventsGroup 15 }

vrrp15_interface OBJECT-TYPE
    SYNTAX DisplayString
    MAX-ACCESS accessible-for-notify
    STATUS current
    DESCRIPTION
        "Parameter 'interface' in event VRRP.15"
    ::= { vrrpEventObjects15 1 }

vrrp15_vrid OBJECT-TYPE
    SYNTAX Integer32
    MAX-ACCESS accessible-for-notify
    STATUS current
    DESCRIPTION
        "Parameter 'vrid' in event VRRP.15"
    ::= { vrrpEventObjects15 2 }

vrrp15_info OBJECT-TYPE
    SYNTAX DisplayString
    MAX-ACCESS accessible-for-notify
    STATUS current
    DESCRIPTION
        "Parameter 'info' in event VRRP.15"
    ::= { vrrpEventObjects15 3 }


vrrpNotification1 NOTIFICATION-TYPE
    OBJECTS { 
              vrrp1_generic_info 
            }
    STATUS current
    DESCRIPTION
        "Notification of Event VRRP.1

        Message: '$1'

        Parameters list:
              $1: vrrp1_generic_info

        Generic info."
    ::= { vrrpNotificationsPrefix 1 }

vrrpNotification2 NOTIFICATION-TYPE
    OBJECTS { 
              vrrp2_interface, 
              vrrp2_vrid,
              vrrp2_state,
              vrrp2_event 
            }
    STATUS current
    DESCRIPTION
        "Notification of Event VRRP.2

        Message: 'VR[$1, vrId $2] State $3, Event $4'

        Parameters list:
              $1: vrrp2_interface
              $2: vrrp2_vrid
              $3: vrrp2_state
              $4: vrrp2_event

        Virtual router event descriptor."
    ::= { vrrpNotificationsPrefix 2 }

vrrpNotification3 NOTIFICATION-TYPE
    OBJECTS { 
              vrrp3_interface, 
              vrrp3_vrid,
              vrrp3_new_state 
            }
    STATUS current
    DESCRIPTION
        "Notification of Event VRRP.3

        Message: 'VR[$1, vrId $2] changing state to $3'

        Parameters list:
              $1: vrrp3_interface
              $2: vrrp3_vrid
              $3: vrrp3_new_state

        A virtual router has changed its state."
    ::= { vrrpNotificationsPrefix 3 }

vrrpNotification4 NOTIFICATION-TYPE
    OBJECTS { 
              vrrp4_error_message 
            }
    STATUS current
    DESCRIPTION
        "Notification of Event VRRP.4

        Message: 'I ERROR, $1'

        Parameters list:
              $1: vrrp4_error_message

        An error has ocurred while receiving a VRRP Advertisement."
    ::= { vrrpNotificationsPrefix 4 }

vrrpNotification5 NOTIFICATION-TYPE
    OBJECTS { 
              vrrp5_interface, 
              vrrp5_vrid,
              vrrp5_error_message 
            }
    STATUS current
    DESCRIPTION
        "Notification of Event VRRP.5

        Message: 'VR[$1, vrId $2] I ERROR, $3'

        Parameters list:
              $1: vrrp5_interface
              $2: vrrp5_vrid
              $3: vrrp5_error_message

        An error associated to a virtual router has ocurred while receiving a
        VRRP Advertisement."
    ::= { vrrpNotificationsPrefix 5 }

vrrpNotification6 NOTIFICATION-TYPE
    OBJECTS { 
              vrrp6_interface, 
              vrrp6_vrid,
              vrrp6_priority,
              vrrp6_checksum 
            }
    STATUS current
    DESCRIPTION
        "Notification of Event VRRP.6

        Message: 'VR[$1, vrId $2] O Advertisement prio $3, cksum $4'

        Parameters list:
              $1: vrrp6_interface
              $2: vrrp6_vrid
              $3: vrrp6_priority
              $4: vrrp6_checksum

        A VRRP Advertisement has been sent."
    ::= { vrrpNotificationsPrefix 6 }

vrrpNotification7 NOTIFICATION-TYPE
    OBJECTS { 
              vrrp7_virtual_ip_address, 
              vrrp7_virtual_mac_address 
            }
    STATUS current
    DESCRIPTION
        "Notification of Event VRRP.7

        Message: 'O Gratuitous ARP-req $1/00005e0001$2'

        Parameters list:
              $1: vrrp7_virtual_ip_address
              $2: vrrp7_virtual_mac_address

        A gratuitous ARP-request has been sent."
    ::= { vrrpNotificationsPrefix 7 }

vrrpNotification8 NOTIFICATION-TYPE
    OBJECTS { 
              vrrp8_error_message 
            }
    STATUS current
    DESCRIPTION
        "Notification of Event VRRP.8

        Message: 'Internal ERROR, $1'

        Parameters list:
              $1: vrrp8_error_message

        An internal error has ocurred."
    ::= { vrrpNotificationsPrefix 8 }

vrrpNotification9 NOTIFICATION-TYPE
    OBJECTS { 
              vrrp9_interface, 
              vrrp9_vrid,
              vrrp9_state,
              vrrp9_timeout,
              vrrp9_sec 
            }
    STATUS current
    DESCRIPTION
        "Notification of Event VRRP.9

        Message: 'VR[$1, vrId $2] State $3, Waiting for preempt delay timeout ($4 $5)'

        Parameters list:
              $1: vrrp9_interface
              $2: vrrp9_vrid
              $3: vrrp9_state
              $4: vrrp9_timeout
              $5: vrrp9_sec

        Waiting for preempt delay timeout."
    ::= { vrrpNotificationsPrefix 9 }

vrrpNotification10 NOTIFICATION-TYPE
    OBJECTS { 
              vrrp10_interface, 
              vrrp10_vrid,
              vrrp10_oldPriority,
              vrrp10_newPriority 
            }
    STATUS current
    DESCRIPTION
        "Notification of Event VRRP.10

        Message: 'VR[$1, vrId $2] Track: Changing priority from $3 to $4'

        Parameters list:
              $1: vrrp10_interface
              $2: vrrp10_vrid
              $3: vrrp10_oldPriority
              $4: vrrp10_newPriority

        Changing priority due to tracking."
    ::= { vrrpNotificationsPrefix 10 }

vrrpNotification11 NOTIFICATION-TYPE
    OBJECTS { 
              vrrp11_interface, 
              vrrp11_vrid,
              vrrp11_state,
              vrrp11_reason 
            }
    STATUS current
    DESCRIPTION
        "Notification of Event VRRP.11

        Message: 'VR[$1, vrId $2] Delay is $3, reason: $4'

        Parameters list:
              $1: vrrp11_interface
              $2: vrrp11_vrid
              $3: vrrp11_state
              $4: vrrp11_reason

        Changing delay state."
    ::= { vrrpNotificationsPrefix 11 }

vrrpNotification12 NOTIFICATION-TYPE
    OBJECTS { 
              vrrp12_interface, 
              vrrp12_vrid,
              vrrp12_state,
              vrrp12_reason 
            }
    STATUS current
    DESCRIPTION
        "Notification of Event VRRP.12

        Message: 'VR[$1, vrId $2] Preemption exception is $3, reason: $4'

        Parameters list:
              $1: vrrp12_interface
              $2: vrrp12_vrid
              $3: vrrp12_state
              $4: vrrp12_reason

        Changing preemption exception state."
    ::= { vrrpNotificationsPrefix 12 }

vrrpNotification13 NOTIFICATION-TYPE
    OBJECTS { 
              vrrp13_interface, 
              vrrp13_vrid 
            }
    STATUS current
    DESCRIPTION
        "Notification of Event VRRP.13

        Message: 'VR[$1, vrId $2] Advertisement timeout too fast. It will be ignored'

        Parameters list:
              $1: vrrp13_interface
              $2: vrrp13_vrid

        An advertisement timeout has occurred too fast."
    ::= { vrrpNotificationsPrefix 13 }

vrrpNotification14 NOTIFICATION-TYPE
    OBJECTS { 
              vrrp14_interface, 
              vrrp14_vrid,
              vrrp14_reason 
            }
    STATUS current
    DESCRIPTION
        "Notification of Event VRRP.14

        Message: 'VR[$1, vrId $2] Invalid authentication key: $3'

        Parameters list:
              $1: vrrp14_interface
              $2: vrrp14_vrid
              $3: vrrp14_reason

        The curernt key is not valid."
    ::= { vrrpNotificationsPrefix 14 }

vrrpNotification15 NOTIFICATION-TYPE
    OBJECTS { 
              vrrp15_interface, 
              vrrp15_vrid,
              vrrp15_info 
            }
    STATUS current
    DESCRIPTION
        "Notification of Event VRRP.15

        Message: 'VR[$1, vrId $2] Authentication info: $3'

        Parameters list:
              $1: vrrp15_interface
              $2: vrrp15_vrid
              $3: vrrp15_info

        Information about the authentication."
    ::= { vrrpNotificationsPrefix 15 }


END
