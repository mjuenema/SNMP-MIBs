-- file automatically created


TELDAT-TRAP-ATM-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


atmTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ATM event subsystem."
    REVISION "201401200930Z"
    DESCRIPTION "Initial implementation"
        ::= { telEventTraps 136 }


atmEventsGroup	OBJECT IDENTIFIER	::= { atmTrapsMIB 1 }

atmNotifications	OBJECT IDENTIFIER	::= { atmTrapsMIB 2 }
atmNotificationsPrefix	OBJECT IDENTIFIER	::= { atmNotifications 0 }

atmEventObjects1 OBJECT-IDENTITY
    STATUS current
    DESCRIPTION
        "Event ATM.1
        An ATM cell has been received."
    ::= { atmEventsGroup 1 }

atm1_mnemonic OBJECT-TYPE
    SYNTAX DisplayString
    MAX-ACCESS accessible-for-notify
    STATUS current
    DESCRIPTION
        "Parameter 'mnemonic' in event ATM.1"
    ::= { atmEventObjects1 1 }

atm1_vpi OBJECT-TYPE
    SYNTAX Integer32
    MAX-ACCESS accessible-for-notify
    STATUS current
    DESCRIPTION
        "Parameter 'vpi' in event ATM.1"
    ::= { atmEventObjects1 2 }

atm1_vci OBJECT-TYPE
    SYNTAX Integer32
    MAX-ACCESS accessible-for-notify
    STATUS current
    DESCRIPTION
        "Parameter 'vci' in event ATM.1"
    ::= { atmEventObjects1 3 }

atm1_data_ptr OBJECT-TYPE
    SYNTAX Integer32
    MAX-ACCESS accessible-for-notify
    STATUS current
    DESCRIPTION
        "Parameter 'data_ptr' in event ATM.1"
    ::= { atmEventObjects1 4 }

atm1_buffer OBJECT-TYPE
    SYNTAX DisplayString
    MAX-ACCESS accessible-for-notify
    STATUS current
    DESCRIPTION
        "Parameter 'buffer' in event ATM.1"
    ::= { atmEventObjects1 5 }

atmEventObjects2 OBJECT-IDENTITY
    STATUS current
    DESCRIPTION
        "Event ATM.2
        An AAL5 CPCS frame has been received."
    ::= { atmEventsGroup 2 }

atm2_mnemonic OBJECT-TYPE
    SYNTAX DisplayString
    MAX-ACCESS accessible-for-notify
    STATUS current
    DESCRIPTION
        "Parameter 'mnemonic' in event ATM.2"
    ::= { atmEventObjects2 1 }

atm2_vpi OBJECT-TYPE
    SYNTAX Integer32
    MAX-ACCESS accessible-for-notify
    STATUS current
    DESCRIPTION
        "Parameter 'vpi' in event ATM.2"
    ::= { atmEventObjects2 2 }

atm2_vci OBJECT-TYPE
    SYNTAX Integer32
    MAX-ACCESS accessible-for-notify
    STATUS current
    DESCRIPTION
        "Parameter 'vci' in event ATM.2"
    ::= { atmEventObjects2 3 }

atm2_data_ptr OBJECT-TYPE
    SYNTAX Integer32
    MAX-ACCESS accessible-for-notify
    STATUS current
    DESCRIPTION
        "Parameter 'data_ptr' in event ATM.2"
    ::= { atmEventObjects2 4 }

atm2_len OBJECT-TYPE
    SYNTAX Integer32
    MAX-ACCESS accessible-for-notify
    STATUS current
    DESCRIPTION
        "Parameter 'len' in event ATM.2"
    ::= { atmEventObjects2 5 }

atm2_buffer OBJECT-TYPE
    SYNTAX DisplayString
    MAX-ACCESS accessible-for-notify
    STATUS current
    DESCRIPTION
        "Parameter 'buffer' in event ATM.2"
    ::= { atmEventObjects2 6 }

atmEventObjects3 OBJECT-IDENTITY
    STATUS current
    DESCRIPTION
        "Event ATM.3
        An ATM cell has been transmitted."
    ::= { atmEventsGroup 3 }

atm3_mnemonic OBJECT-TYPE
    SYNTAX DisplayString
    MAX-ACCESS accessible-for-notify
    STATUS current
    DESCRIPTION
        "Parameter 'mnemonic' in event ATM.3"
    ::= { atmEventObjects3 1 }

atm3_vpi OBJECT-TYPE
    SYNTAX Integer32
    MAX-ACCESS accessible-for-notify
    STATUS current
    DESCRIPTION
        "Parameter 'vpi' in event ATM.3"
    ::= { atmEventObjects3 2 }

atm3_vci OBJECT-TYPE
    SYNTAX Integer32
    MAX-ACCESS accessible-for-notify
    STATUS current
    DESCRIPTION
        "Parameter 'vci' in event ATM.3"
    ::= { atmEventObjects3 3 }

atm3_data_ptr OBJECT-TYPE
    SYNTAX Integer32
    MAX-ACCESS accessible-for-notify
    STATUS current
    DESCRIPTION
        "Parameter 'data_ptr' in event ATM.3"
    ::= { atmEventObjects3 4 }

atm3_buffer OBJECT-TYPE
    SYNTAX DisplayString
    MAX-ACCESS accessible-for-notify
    STATUS current
    DESCRIPTION
        "Parameter 'buffer' in event ATM.3"
    ::= { atmEventObjects3 5 }

atmEventObjects4 OBJECT-IDENTITY
    STATUS current
    DESCRIPTION
        "Event ATM.4
        An AAL5 CPCS frame has been transmitted."
    ::= { atmEventsGroup 4 }

atm4_mnemonic OBJECT-TYPE
    SYNTAX DisplayString
    MAX-ACCESS accessible-for-notify
    STATUS current
    DESCRIPTION
        "Parameter 'mnemonic' in event ATM.4"
    ::= { atmEventObjects4 1 }

atm4_vpi OBJECT-TYPE
    SYNTAX Integer32
    MAX-ACCESS accessible-for-notify
    STATUS current
    DESCRIPTION
        "Parameter 'vpi' in event ATM.4"
    ::= { atmEventObjects4 2 }

atm4_vci OBJECT-TYPE
    SYNTAX Integer32
    MAX-ACCESS accessible-for-notify
    STATUS current
    DESCRIPTION
        "Parameter 'vci' in event ATM.4"
    ::= { atmEventObjects4 3 }

atm4_data_ptr OBJECT-TYPE
    SYNTAX Integer32
    MAX-ACCESS accessible-for-notify
    STATUS current
    DESCRIPTION
        "Parameter 'data_ptr' in event ATM.4"
    ::= { atmEventObjects4 4 }

atm4_len OBJECT-TYPE
    SYNTAX Integer32
    MAX-ACCESS accessible-for-notify
    STATUS current
    DESCRIPTION
        "Parameter 'len' in event ATM.4"
    ::= { atmEventObjects4 5 }

atm4_buffer OBJECT-TYPE
    SYNTAX DisplayString
    MAX-ACCESS accessible-for-notify
    STATUS current
    DESCRIPTION
        "Parameter 'buffer' in event ATM.4"
    ::= { atmEventObjects4 6 }

atmEventObjects5 OBJECT-IDENTITY
    STATUS current
    DESCRIPTION
        "Event ATM.5
        Detailed info about cell reception."
    ::= { atmEventsGroup 5 }

atm5_mnemonic OBJECT-TYPE
    SYNTAX DisplayString
    MAX-ACCESS accessible-for-notify
    STATUS current
    DESCRIPTION
        "Parameter 'mnemonic' in event ATM.5"
    ::= { atmEventObjects5 1 }

atm5_vpi OBJECT-TYPE
    SYNTAX Integer32
    MAX-ACCESS accessible-for-notify
    STATUS current
    DESCRIPTION
        "Parameter 'vpi' in event ATM.5"
    ::= { atmEventObjects5 2 }

atm5_vci OBJECT-TYPE
    SYNTAX Integer32
    MAX-ACCESS accessible-for-notify
    STATUS current
    DESCRIPTION
        "Parameter 'vci' in event ATM.5"
    ::= { atmEventObjects5 3 }

atm5_data_ptr OBJECT-TYPE
    SYNTAX Integer32
    MAX-ACCESS accessible-for-notify
    STATUS current
    DESCRIPTION
        "Parameter 'data_ptr' in event ATM.5"
    ::= { atmEventObjects5 4 }

atm5_descr OBJECT-TYPE
    SYNTAX DisplayString
    MAX-ACCESS accessible-for-notify
    STATUS current
    DESCRIPTION
        "Parameter 'descr' in event ATM.5"
    ::= { atmEventObjects5 5 }

atmEventObjects6 OBJECT-IDENTITY
    STATUS current
    DESCRIPTION
        "Event ATM.6
        Detailed info about AAL5 CPCS frame reception."
    ::= { atmEventsGroup 6 }

atm6_mnemonic OBJECT-TYPE
    SYNTAX DisplayString
    MAX-ACCESS accessible-for-notify
    STATUS current
    DESCRIPTION
        "Parameter 'mnemonic' in event ATM.6"
    ::= { atmEventObjects6 1 }

atm6_vpi OBJECT-TYPE
    SYNTAX Integer32
    MAX-ACCESS accessible-for-notify
    STATUS current
    DESCRIPTION
        "Parameter 'vpi' in event ATM.6"
    ::= { atmEventObjects6 2 }

atm6_vci OBJECT-TYPE
    SYNTAX Integer32
    MAX-ACCESS accessible-for-notify
    STATUS current
    DESCRIPTION
        "Parameter 'vci' in event ATM.6"
    ::= { atmEventObjects6 3 }

atm6_data_ptr OBJECT-TYPE
    SYNTAX Integer32
    MAX-ACCESS accessible-for-notify
    STATUS current
    DESCRIPTION
        "Parameter 'data_ptr' in event ATM.6"
    ::= { atmEventObjects6 4 }

atm6_descr OBJECT-TYPE
    SYNTAX DisplayString
    MAX-ACCESS accessible-for-notify
    STATUS current
    DESCRIPTION
        "Parameter 'descr' in event ATM.6"
    ::= { atmEventObjects6 5 }

atmEventObjects7 OBJECT-IDENTITY
    STATUS current
    DESCRIPTION
        "Event ATM.7
        Detailed info about cell transmission."
    ::= { atmEventsGroup 7 }

atm7_mnemonic OBJECT-TYPE
    SYNTAX DisplayString
    MAX-ACCESS accessible-for-notify
    STATUS current
    DESCRIPTION
        "Parameter 'mnemonic' in event ATM.7"
    ::= { atmEventObjects7 1 }

atm7_vpi OBJECT-TYPE
    SYNTAX Integer32
    MAX-ACCESS accessible-for-notify
    STATUS current
    DESCRIPTION
        "Parameter 'vpi' in event ATM.7"
    ::= { atmEventObjects7 2 }

atm7_vci OBJECT-TYPE
    SYNTAX Integer32
    MAX-ACCESS accessible-for-notify
    STATUS current
    DESCRIPTION
        "Parameter 'vci' in event ATM.7"
    ::= { atmEventObjects7 3 }

atm7_data_ptr OBJECT-TYPE
    SYNTAX Integer32
    MAX-ACCESS accessible-for-notify
    STATUS current
    DESCRIPTION
        "Parameter 'data_ptr' in event ATM.7"
    ::= { atmEventObjects7 4 }

atm7_descr OBJECT-TYPE
    SYNTAX DisplayString
    MAX-ACCESS accessible-for-notify
    STATUS current
    DESCRIPTION
        "Parameter 'descr' in event ATM.7"
    ::= { atmEventObjects7 5 }

atmEventObjects8 OBJECT-IDENTITY
    STATUS current
    DESCRIPTION
        "Event ATM.8
        Detailed info about AAL5 CPCS frame transmission."
    ::= { atmEventsGroup 8 }

atm8_mnemonic OBJECT-TYPE
    SYNTAX DisplayString
    MAX-ACCESS accessible-for-notify
    STATUS current
    DESCRIPTION
        "Parameter 'mnemonic' in event ATM.8"
    ::= { atmEventObjects8 1 }

atm8_vpi OBJECT-TYPE
    SYNTAX Integer32
    MAX-ACCESS accessible-for-notify
    STATUS current
    DESCRIPTION
        "Parameter 'vpi' in event ATM.8"
    ::= { atmEventObjects8 2 }

atm8_vci OBJECT-TYPE
    SYNTAX Integer32
    MAX-ACCESS accessible-for-notify
    STATUS current
    DESCRIPTION
        "Parameter 'vci' in event ATM.8"
    ::= { atmEventObjects8 3 }

atm8_data_ptr OBJECT-TYPE
    SYNTAX Integer32
    MAX-ACCESS accessible-for-notify
    STATUS current
    DESCRIPTION
        "Parameter 'data_ptr' in event ATM.8"
    ::= { atmEventObjects8 4 }

atm8_descr OBJECT-TYPE
    SYNTAX DisplayString
    MAX-ACCESS accessible-for-notify
    STATUS current
    DESCRIPTION
        "Parameter 'descr' in event ATM.8"
    ::= { atmEventObjects8 5 }

atmEventObjects9 OBJECT-IDENTITY
    STATUS current
    DESCRIPTION
        "Event ATM.9
        A transmission request has been rejected."
    ::= { atmEventsGroup 9 }

atm9_mnemonic OBJECT-TYPE
    SYNTAX DisplayString
    MAX-ACCESS accessible-for-notify
    STATUS current
    DESCRIPTION
        "Parameter 'mnemonic' in event ATM.9"
    ::= { atmEventObjects9 1 }

atm9_vpi OBJECT-TYPE
    SYNTAX Integer32
    MAX-ACCESS accessible-for-notify
    STATUS current
    DESCRIPTION
        "Parameter 'vpi' in event ATM.9"
    ::= { atmEventObjects9 2 }

atm9_vci OBJECT-TYPE
    SYNTAX Integer32
    MAX-ACCESS accessible-for-notify
    STATUS current
    DESCRIPTION
        "Parameter 'vci' in event ATM.9"
    ::= { atmEventObjects9 3 }

atm9_data_ptr OBJECT-TYPE
    SYNTAX Integer32
    MAX-ACCESS accessible-for-notify
    STATUS current
    DESCRIPTION
        "Parameter 'data_ptr' in event ATM.9"
    ::= { atmEventObjects9 4 }

atm9_len OBJECT-TYPE
    SYNTAX Integer32
    MAX-ACCESS accessible-for-notify
    STATUS current
    DESCRIPTION
        "Parameter 'len' in event ATM.9"
    ::= { atmEventObjects9 5 }

atm9_descr OBJECT-TYPE
    SYNTAX DisplayString
    MAX-ACCESS accessible-for-notify
    STATUS current
    DESCRIPTION
        "Parameter 'descr' in event ATM.9"
    ::= { atmEventObjects9 6 }

atmEventObjects10 OBJECT-IDENTITY
    STATUS current
    DESCRIPTION
        "Event ATM.10
        Unexpected software behaviour."
    ::= { atmEventsGroup 10 }

atm10_mnemonic OBJECT-TYPE
    SYNTAX DisplayString
    MAX-ACCESS accessible-for-notify
    STATUS current
    DESCRIPTION
        "Parameter 'mnemonic' in event ATM.10"
    ::= { atmEventObjects10 1 }

atm10_soft_descr OBJECT-TYPE
    SYNTAX DisplayString
    MAX-ACCESS accessible-for-notify
    STATUS current
    DESCRIPTION
        "Parameter 'soft_descr' in event ATM.10"
    ::= { atmEventObjects10 2 }

atm10_event_descr OBJECT-TYPE
    SYNTAX DisplayString
    MAX-ACCESS accessible-for-notify
    STATUS current
    DESCRIPTION
        "Parameter 'event_descr' in event ATM.10"
    ::= { atmEventObjects10 3 }

atmEventObjects11 OBJECT-IDENTITY
    STATUS current
    DESCRIPTION
        "Event ATM.11
        The frame received has been detected as errored at subinterface level."
    ::= { atmEventsGroup 11 }

atm11_mnemonic OBJECT-TYPE
    SYNTAX DisplayString
    MAX-ACCESS accessible-for-notify
    STATUS current
    DESCRIPTION
        "Parameter 'mnemonic' in event ATM.11"
    ::= { atmEventObjects11 1 }

atm11_rsn_descr OBJECT-TYPE
    SYNTAX DisplayString
    MAX-ACCESS accessible-for-notify
    STATUS current
    DESCRIPTION
        "Parameter 'rsn_descr' in event ATM.11"
    ::= { atmEventObjects11 2 }

atmEventObjects12 OBJECT-IDENTITY
    STATUS current
    DESCRIPTION
        "Event ATM.12
        Event at ATM interface level: up, down."
    ::= { atmEventsGroup 12 }

atm12_mnemonic OBJECT-TYPE
    SYNTAX DisplayString
    MAX-ACCESS accessible-for-notify
    STATUS current
    DESCRIPTION
        "Parameter 'mnemonic' in event ATM.12"
    ::= { atmEventObjects12 1 }

atm12_event_descr OBJECT-TYPE
    SYNTAX DisplayString
    MAX-ACCESS accessible-for-notify
    STATUS current
    DESCRIPTION
        "Parameter 'event_descr' in event ATM.12"
    ::= { atmEventObjects12 2 }

atmEventObjects13 OBJECT-IDENTITY
    STATUS current
    DESCRIPTION
        "Event ATM.13
        Event at ATM VCC level."
    ::= { atmEventsGroup 13 }

atm13_mnemonic OBJECT-TYPE
    SYNTAX DisplayString
    MAX-ACCESS accessible-for-notify
    STATUS current
    DESCRIPTION
        "Parameter 'mnemonic' in event ATM.13"
    ::= { atmEventObjects13 1 }

atm13_vpi OBJECT-TYPE
    SYNTAX Integer32
    MAX-ACCESS accessible-for-notify
    STATUS current
    DESCRIPTION
        "Parameter 'vpi' in event ATM.13"
    ::= { atmEventObjects13 2 }

atm13_vci OBJECT-TYPE
    SYNTAX Integer32
    MAX-ACCESS accessible-for-notify
    STATUS current
    DESCRIPTION
        "Parameter 'vci' in event ATM.13"
    ::= { atmEventObjects13 3 }

atm13_event_descr OBJECT-TYPE
    SYNTAX DisplayString
    MAX-ACCESS accessible-for-notify
    STATUS current
    DESCRIPTION
        "Parameter 'event_descr' in event ATM.13"
    ::= { atmEventObjects13 4 }

atmEventObjects14 OBJECT-IDENTITY
    STATUS current
    DESCRIPTION
        "Event ATM.14
        An AAL5 SAR cell has been transmitted."
    ::= { atmEventsGroup 14 }

atm14_mnemonic OBJECT-TYPE
    SYNTAX DisplayString
    MAX-ACCESS accessible-for-notify
    STATUS current
    DESCRIPTION
        "Parameter 'mnemonic' in event ATM.14"
    ::= { atmEventObjects14 1 }

atm14_vpi OBJECT-TYPE
    SYNTAX Integer32
    MAX-ACCESS accessible-for-notify
    STATUS current
    DESCRIPTION
        "Parameter 'vpi' in event ATM.14"
    ::= { atmEventObjects14 2 }

atm14_vci OBJECT-TYPE
    SYNTAX Integer32
    MAX-ACCESS accessible-for-notify
    STATUS current
    DESCRIPTION
        "Parameter 'vci' in event ATM.14"
    ::= { atmEventObjects14 3 }

atm14_data_ptr OBJECT-TYPE
    SYNTAX Integer32
    MAX-ACCESS accessible-for-notify
    STATUS current
    DESCRIPTION
        "Parameter 'data_ptr' in event ATM.14"
    ::= { atmEventObjects14 4 }

atm14_details OBJECT-TYPE
    SYNTAX DisplayString
    MAX-ACCESS accessible-for-notify
    STATUS current
    DESCRIPTION
        "Parameter 'details' in event ATM.14"
    ::= { atmEventObjects14 5 }

atmEventObjects15 OBJECT-IDENTITY
    STATUS current
    DESCRIPTION
        "Event ATM.15
        Event related to the SAR unit"
    ::= { atmEventsGroup 15 }

atm15_mnemonic OBJECT-TYPE
    SYNTAX DisplayString
    MAX-ACCESS accessible-for-notify
    STATUS current
    DESCRIPTION
        "Parameter 'mnemonic' in event ATM.15"
    ::= { atmEventObjects15 1 }

atm15_event_descr OBJECT-TYPE
    SYNTAX DisplayString
    MAX-ACCESS accessible-for-notify
    STATUS current
    DESCRIPTION
        "Parameter 'event_descr' in event ATM.15"
    ::= { atmEventObjects15 2 }


atmNotification1 NOTIFICATION-TYPE
    OBJECTS { 
              atm1_mnemonic, 
              atm1_vpi,
              atm1_vci,
              atm1_data_ptr,
              atm1_buffer 
            }
    STATUS current
    DESCRIPTION
        "Notification of Event ATM.1

        Message: '$1 ATM cell received ($2..$3) data=$4: $5'

        Parameters list:
              $1: atm1_mnemonic
              $2: atm1_vpi
              $3: atm1_vci
              $4: atm1_data_ptr
              $5: atm1_buffer

        An ATM cell has been received."
    ::= { atmNotificationsPrefix 1 }

atmNotification2 NOTIFICATION-TYPE
    OBJECTS { 
              atm2_mnemonic, 
              atm2_vpi,
              atm2_vci,
              atm2_data_ptr,
              atm2_len,
              atm2_buffer 
            }
    STATUS current
    DESCRIPTION
        "Notification of Event ATM.2

        Message: '$1 AAL5 CPCS frame Received ($2..$3) data=$4 len=$5: $6'

        Parameters list:
              $1: atm2_mnemonic
              $2: atm2_vpi
              $3: atm2_vci
              $4: atm2_data_ptr
              $5: atm2_len
              $6: atm2_buffer

        An AAL5 CPCS frame has been received."
    ::= { atmNotificationsPrefix 2 }

atmNotification3 NOTIFICATION-TYPE
    OBJECTS { 
              atm3_mnemonic, 
              atm3_vpi,
              atm3_vci,
              atm3_data_ptr,
              atm3_buffer 
            }
    STATUS current
    DESCRIPTION
        "Notification of Event ATM.3

        Message: '$1 ATM cell transmission ($2..$3) data=$4: $5'

        Parameters list:
              $1: atm3_mnemonic
              $2: atm3_vpi
              $3: atm3_vci
              $4: atm3_data_ptr
              $5: atm3_buffer

        An ATM cell has been transmitted."
    ::= { atmNotificationsPrefix 3 }

atmNotification4 NOTIFICATION-TYPE
    OBJECTS { 
              atm4_mnemonic, 
              atm4_vpi,
              atm4_vci,
              atm4_data_ptr,
              atm4_len,
              atm4_buffer 
            }
    STATUS current
    DESCRIPTION
        "Notification of Event ATM.4

        Message: '$1 AAL5 CPCS frame transmission ($2..$3) data=$4 len=$5: $6'

        Parameters list:
              $1: atm4_mnemonic
              $2: atm4_vpi
              $3: atm4_vci
              $4: atm4_data_ptr
              $5: atm4_len
              $6: atm4_buffer

        An AAL5 CPCS frame has been transmitted."
    ::= { atmNotificationsPrefix 4 }

atmNotification5 NOTIFICATION-TYPE
    OBJECTS { 
              atm5_mnemonic, 
              atm5_vpi,
              atm5_vci,
              atm5_data_ptr,
              atm5_descr 
            }
    STATUS current
    DESCRIPTION
        "Notification of Event ATM.5

        Message: '$1 ATM cell received ($2..$3) data=$4 $5'

        Parameters list:
              $1: atm5_mnemonic
              $2: atm5_vpi
              $3: atm5_vci
              $4: atm5_data_ptr
              $5: atm5_descr

        Detailed info about cell reception."
    ::= { atmNotificationsPrefix 5 }

atmNotification6 NOTIFICATION-TYPE
    OBJECTS { 
              atm6_mnemonic, 
              atm6_vpi,
              atm6_vci,
              atm6_data_ptr,
              atm6_descr 
            }
    STATUS current
    DESCRIPTION
        "Notification of Event ATM.6

        Message: '$1 AAL5 CPCS frame received ($2..$3) data=$4 $5'

        Parameters list:
              $1: atm6_mnemonic
              $2: atm6_vpi
              $3: atm6_vci
              $4: atm6_data_ptr
              $5: atm6_descr

        Detailed info about AAL5 CPCS frame reception."
    ::= { atmNotificationsPrefix 6 }

atmNotification7 NOTIFICATION-TYPE
    OBJECTS { 
              atm7_mnemonic, 
              atm7_vpi,
              atm7_vci,
              atm7_data_ptr,
              atm7_descr 
            }
    STATUS current
    DESCRIPTION
        "Notification of Event ATM.7

        Message: '$1 ATM cell transmission ($2..$3) data=$4 $5'

        Parameters list:
              $1: atm7_mnemonic
              $2: atm7_vpi
              $3: atm7_vci
              $4: atm7_data_ptr
              $5: atm7_descr

        Detailed info about cell transmission."
    ::= { atmNotificationsPrefix 7 }

atmNotification8 NOTIFICATION-TYPE
    OBJECTS { 
              atm8_mnemonic, 
              atm8_vpi,
              atm8_vci,
              atm8_data_ptr,
              atm8_descr 
            }
    STATUS current
    DESCRIPTION
        "Notification of Event ATM.8

        Message: '$1 AAL5 CPCS frame transmission ($2..$3) data=$4 $5'

        Parameters list:
              $1: atm8_mnemonic
              $2: atm8_vpi
              $3: atm8_vci
              $4: atm8_data_ptr
              $5: atm8_descr

        Detailed info about AAL5 CPCS frame transmission."
    ::= { atmNotificationsPrefix 8 }

atmNotification9 NOTIFICATION-TYPE
    OBJECTS { 
              atm9_mnemonic, 
              atm9_vpi,
              atm9_vci,
              atm9_data_ptr,
              atm9_len,
              atm9_descr 
            }
    STATUS current
    DESCRIPTION
        "Notification of Event ATM.9

        Message: '$1 Transmission rejected ($2..$3) data=$4 len=$5 rsn=$6'

        Parameters list:
              $1: atm9_mnemonic
              $2: atm9_vpi
              $3: atm9_vci
              $4: atm9_data_ptr
              $5: atm9_len
              $6: atm9_descr

        A transmission request has been rejected."
    ::= { atmNotificationsPrefix 9 }

atmNotification10 NOTIFICATION-TYPE
    OBJECTS { 
              atm10_mnemonic, 
              atm10_soft_descr,
              atm10_event_descr 
            }
    STATUS current
    DESCRIPTION
        "Notification of Event ATM.10

        Message: '$1 Unexpected $2 software event $3'

        Parameters list:
              $1: atm10_mnemonic
              $2: atm10_soft_descr
              $3: atm10_event_descr

        Unexpected software behaviour."
    ::= { atmNotificationsPrefix 10 }

atmNotification11 NOTIFICATION-TYPE
    OBJECTS { 
              atm11_mnemonic, 
              atm11_rsn_descr 
            }
    STATUS current
    DESCRIPTION
        "Notification of Event ATM.11

        Message: '$1 reception with error Reason=$2'

        Parameters list:
              $1: atm11_mnemonic
              $2: atm11_rsn_descr

        The frame received has been detected as errored at subinterface level."
    ::= { atmNotificationsPrefix 11 }

atmNotification12 NOTIFICATION-TYPE
    OBJECTS { 
              atm12_mnemonic, 
              atm12_event_descr 
            }
    STATUS current
    DESCRIPTION
        "Notification of Event ATM.12

        Message: '$1 $2'

        Parameters list:
              $1: atm12_mnemonic
              $2: atm12_event_descr

        Event at ATM interface level: up, down."
    ::= { atmNotificationsPrefix 12 }

atmNotification13 NOTIFICATION-TYPE
    OBJECTS { 
              atm13_mnemonic, 
              atm13_vpi,
              atm13_vci,
              atm13_event_descr 
            }
    STATUS current
    DESCRIPTION
        "Notification of Event ATM.13

        Message: '$1 VPI=$2 VCI=$3 $4'

        Parameters list:
              $1: atm13_mnemonic
              $2: atm13_vpi
              $3: atm13_vci
              $4: atm13_event_descr

        Event at ATM VCC level."
    ::= { atmNotificationsPrefix 13 }

atmNotification14 NOTIFICATION-TYPE
    OBJECTS { 
              atm14_mnemonic, 
              atm14_vpi,
              atm14_vci,
              atm14_data_ptr,
              atm14_details 
            }
    STATUS current
    DESCRIPTION
        "Notification of Event ATM.14

        Message: '$1 AAL5 SAR cell transmission ($2..$3) data=$4 $5'

        Parameters list:
              $1: atm14_mnemonic
              $2: atm14_vpi
              $3: atm14_vci
              $4: atm14_data_ptr
              $5: atm14_details

        An AAL5 SAR cell has been transmitted."
    ::= { atmNotificationsPrefix 14 }

atmNotification15 NOTIFICATION-TYPE
    OBJECTS { 
              atm15_mnemonic, 
              atm15_event_descr 
            }
    STATUS current
    DESCRIPTION
        "Notification of Event ATM.15

        Message: '$1 $2'

        Parameters list:
              $1: atm15_mnemonic
              $2: atm15_event_descr

        Event related to the SAR unit"
    ::= { atmNotificationsPrefix 15 }


END
