-- =============================================================================
-- Copyright (C) 2009 by HUAWEI TECHNOLOGIES. All rights reserved.
--    
-- Description: The MIB is designed to get HRP information. 
-- Reference: Huawei Enterprise MIB
-- Version: 1.0
-- History: 
--          V1.0 The initial version created by Cao Jiancang 00005275. 
-- =============================================================================

HUAWEI-SECURITY-IPLINK-MIB DEFINITIONS ::= BEGIN
 
		IMPORTS
	   	IpAddress, Counter32, Gauge32, OBJECT-TYPE, MODULE-IDENTITY
			FROM SNMPv2-SMI 
		MODULE-COMPLIANCE, OBJECT-GROUP, NOTIFICATION-GROUP          
		            FROM SNMPv2-CONF            
    		enterprises			
		            FROM RFC1155-SMI;  
            		    
		hwIplink MODULE-IDENTITY 
                    LAST-UPDATED "201203191933Z"                -- March 19, 2012 at 19:33 GMT
		    ORGANIZATION 
				"Huawei Technologies co.,Ltd."
	            CONTACT-INFO 
				"
				R&D BeiJing, Huawei Technologies co.,Ltd.
				Huawei Bld.,NO.3 Xinxi Rd.,
				Shang-Di Information Industry Base,
				Hai-Dian District Beijing P.R. China
				Zip:100085
				Http://www.huawei.com
				E-mail:support@huawei.com
				"
                    DESCRIPTION 
                        "
                        V1.00
                        The HUAWEI-SECURITY-IPLINK-MIB contains objects to manage the firewall IPLINK module.
                        "
			::= { hwSecurity 45 }
			
--
-- Node definitions
--
                -- 1.3.6.1.4.1.2011
                huawei OBJECT IDENTIFIER ::= { enterprises 2011 }
        
                -- 1.3.6.1.4.1.2011.6
                huaweiUtility OBJECT IDENTIFIER ::= { huawei 6 }
        
                -- 1.3.6.1.4.1.2011.6.122
                hwSecurity OBJECT IDENTIFIER ::= { huaweiUtility 122 }
                
		hwIPLinkNotification OBJECT IDENTIFIER ::= { hwIplink 1 }   
		hwIPLinkTrapObjects OBJECT IDENTIFIER ::= { hwIPLinkNotification 1 }
		hwIPLinkTraps OBJECT IDENTIFIER ::= { hwIplink 2 }

-- ===============================================
-- TrapObject.
-- ===============================================
	
	-- 1.3.6.1.4.1.2011.6.122.45.1.1.1
	   hwIPLinkID  OBJECT-TYPE
		SYNTAX Gauge32 
		MAX-ACCESS accessible-for-notify
		STATUS current
		DESCRIPTION
	    		"The ID of the IP-link"
		::= { hwIPLinkTrapObjects 1 }  
		-- 1.3.6.1.4.1.2011.6.122.45.1.1.1
		
	-- 1.3.6.1.4.1.2011.6.122.45.1.1.2	
	   hwIPLinkStatus  OBJECT-TYPE
		SYNTAX OCTET STRING 
		MAX-ACCESS accessible-for-notify
		STATUS current
		DESCRIPTION
	    		"The status of the IP-link."
		::= { hwIPLinkTrapObjects 2 } 	
	        			
-- ===============================================
-- definition of traps.      
-- ===============================================                                
	   hwIPLinkUp NOTIFICATION-TYPE
		OBJECTS { hwIPLinkID,hwIPLinkStatus }
		STATUS     current
		DESCRIPTION
		    "The IP-link changes to up"
		::= { hwIPLinkTraps 1}
			
	   hwIPLinkDown NOTIFICATION-TYPE
		OBJECTS { hwIPLinkID,hwIPLinkStatus }
		STATUS     current
		DESCRIPTION
		    "The IP-link changes to down"
		::= { hwIPLinkTraps 2}  
                					
        END
