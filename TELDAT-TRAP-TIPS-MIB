-- file automatically created


TELDAT-TRAP-TIPS-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tipsTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TIPS event subsystem."
    REVISION "201401200930Z"
    DESCRIPTION "Initial implementation"
        ::= { telEventTraps 221 }


tipsEventsGroup	OBJECT IDENTIFIER	::= { tipsTrapsMIB 1 }

tipsNotifications	OBJECT IDENTIFIER	::= { tipsTrapsMIB 2 }
tipsNotificationsPrefix	OBJECT IDENTIFIER	::= { tipsNotifications 0 }

tipsEventObjects1 OBJECT-IDENTITY
    STATUS current
    DESCRIPTION
        "Event TIPS.1
        packet processed"
    ::= { tipsEventsGroup 1 }

tips1_source_ip OBJECT-TYPE
    SYNTAX IpAddress
    MAX-ACCESS accessible-for-notify
    STATUS current
    DESCRIPTION
        "Parameter 'source_ip' in event TIPS.1"
    ::= { tipsEventObjects1 1 }

tips1_destination_ip OBJECT-TYPE
    SYNTAX IpAddress
    MAX-ACCESS accessible-for-notify
    STATUS current
    DESCRIPTION
        "Parameter 'destination_ip' in event TIPS.1"
    ::= { tipsEventObjects1 2 }

tipsEventObjects2 OBJECT-IDENTITY
    STATUS current
    DESCRIPTION
        "Event TIPS.2
        tips alert has been generated"
    ::= { tipsEventsGroup 2 }

tips2_msg OBJECT-TYPE
    SYNTAX DisplayString
    MAX-ACCESS accessible-for-notify
    STATUS current
    DESCRIPTION
        "Parameter 'msg' in event TIPS.2"
    ::= { tipsEventObjects2 1 }

tipsEventObjects3 OBJECT-IDENTITY
    STATUS current
    DESCRIPTION
        "Event TIPS.3
        tips state changed"
    ::= { tipsEventsGroup 3 }

tips3_state OBJECT-TYPE
    SYNTAX DisplayString
    MAX-ACCESS accessible-for-notify
    STATUS current
    DESCRIPTION
        "Parameter 'state' in event TIPS.3"
    ::= { tipsEventObjects3 1 }

tipsEventObjects4 OBJECT-IDENTITY
    STATUS current
    DESCRIPTION
        "Event TIPS.4
        packet processed"
    ::= { tipsEventsGroup 4 }

tips4_source_ip OBJECT-TYPE
    SYNTAX IpAddress
    MAX-ACCESS accessible-for-notify
    STATUS current
    DESCRIPTION
        "Parameter 'source_ip' in event TIPS.4"
    ::= { tipsEventObjects4 1 }

tips4_destination_ip OBJECT-TYPE
    SYNTAX IpAddress
    MAX-ACCESS accessible-for-notify
    STATUS current
    DESCRIPTION
        "Parameter 'destination_ip' in event TIPS.4"
    ::= { tipsEventObjects4 2 }

tipsEventObjects5 OBJECT-IDENTITY
    STATUS current
    DESCRIPTION
        "Event TIPS.5
        TIPS IP Spoofing engine has too many pending address resolutions for the
        specified address on the specified interface."
    ::= { tipsEventsGroup 5 }

tips5_ip_src OBJECT-TYPE
    SYNTAX IpAddress
    MAX-ACCESS accessible-for-notify
    STATUS current
    DESCRIPTION
        "Parameter 'ip_src' in event TIPS.5"
    ::= { tipsEventObjects5 1 }

tips5_interface OBJECT-TYPE
    SYNTAX DisplayString
    MAX-ACCESS accessible-for-notify
    STATUS current
    DESCRIPTION
        "Parameter 'interface' in event TIPS.5"
    ::= { tipsEventObjects5 2 }

tipsEventObjects6 OBJECT-IDENTITY
    STATUS current
    DESCRIPTION
        "Event TIPS.6
        TIPS IP Spoofing engine has too many pending packets from the specified
        source IP addres on reception of a new packet with specified mac and ip
        addresses on the specified interface."
    ::= { tipsEventsGroup 6 }

tips6_mac_src OBJECT-TYPE
    SYNTAX DisplayString
    MAX-ACCESS accessible-for-notify
    STATUS current
    DESCRIPTION
        "Parameter 'mac_src' in event TIPS.6"
    ::= { tipsEventObjects6 1 }

tips6_mac_dst OBJECT-TYPE
    SYNTAX DisplayString
    MAX-ACCESS accessible-for-notify
    STATUS current
    DESCRIPTION
        "Parameter 'mac_dst' in event TIPS.6"
    ::= { tipsEventObjects6 2 }

tips6_ip_src OBJECT-TYPE
    SYNTAX IpAddress
    MAX-ACCESS accessible-for-notify
    STATUS current
    DESCRIPTION
        "Parameter 'ip_src' in event TIPS.6"
    ::= { tipsEventObjects6 3 }

tips6_ip_dst OBJECT-TYPE
    SYNTAX IpAddress
    MAX-ACCESS accessible-for-notify
    STATUS current
    DESCRIPTION
        "Parameter 'ip_dst' in event TIPS.6"
    ::= { tipsEventObjects6 4 }

tips6_interface OBJECT-TYPE
    SYNTAX DisplayString
    MAX-ACCESS accessible-for-notify
    STATUS current
    DESCRIPTION
        "Parameter 'interface' in event TIPS.6"
    ::= { tipsEventObjects6 5 }

tipsEventObjects7 OBJECT-IDENTITY
    STATUS current
    DESCRIPTION
        "Event TIPS.7
        TIPS IP Spoofing engine received the specified packet on the specified
        interface and enqueued it while resolving source address."
    ::= { tipsEventsGroup 7 }

tips7_mac_src OBJECT-TYPE
    SYNTAX DisplayString
    MAX-ACCESS accessible-for-notify
    STATUS current
    DESCRIPTION
        "Parameter 'mac_src' in event TIPS.7"
    ::= { tipsEventObjects7 1 }

tips7_mac_dst OBJECT-TYPE
    SYNTAX DisplayString
    MAX-ACCESS accessible-for-notify
    STATUS current
    DESCRIPTION
        "Parameter 'mac_dst' in event TIPS.7"
    ::= { tipsEventObjects7 2 }

tips7_ip_src OBJECT-TYPE
    SYNTAX IpAddress
    MAX-ACCESS accessible-for-notify
    STATUS current
    DESCRIPTION
        "Parameter 'ip_src' in event TIPS.7"
    ::= { tipsEventObjects7 3 }

tips7_ip_dst OBJECT-TYPE
    SYNTAX IpAddress
    MAX-ACCESS accessible-for-notify
    STATUS current
    DESCRIPTION
        "Parameter 'ip_dst' in event TIPS.7"
    ::= { tipsEventObjects7 4 }

tips7_interface OBJECT-TYPE
    SYNTAX DisplayString
    MAX-ACCESS accessible-for-notify
    STATUS current
    DESCRIPTION
        "Parameter 'interface' in event TIPS.7"
    ::= { tipsEventObjects7 5 }

tipsEventObjects8 OBJECT-IDENTITY
    STATUS current
    DESCRIPTION
        "Event TIPS.8
        TIPS IP Spoofing engine sends an arp request for the specified address
        on the specified interface."
    ::= { tipsEventsGroup 8 }

tips8_ip_address OBJECT-TYPE
    SYNTAX IpAddress
    MAX-ACCESS accessible-for-notify
    STATUS current
    DESCRIPTION
        "Parameter 'ip_address' in event TIPS.8"
    ::= { tipsEventObjects8 1 }

tips8_interface OBJECT-TYPE
    SYNTAX DisplayString
    MAX-ACCESS accessible-for-notify
    STATUS current
    DESCRIPTION
        "Parameter 'interface' in event TIPS.8"
    ::= { tipsEventObjects8 2 }

tipsEventObjects9 OBJECT-IDENTITY
    STATUS current
    DESCRIPTION
        "Event TIPS.9
        TIPS IP Spoofing engine sent arp requests for the specified ip address
        on the specified interface. These requests timed out."
    ::= { tipsEventsGroup 9 }

tips9_ip_address OBJECT-TYPE
    SYNTAX IpAddress
    MAX-ACCESS accessible-for-notify
    STATUS current
    DESCRIPTION
        "Parameter 'ip_address' in event TIPS.9"
    ::= { tipsEventObjects9 1 }

tips9_interface OBJECT-TYPE
    SYNTAX DisplayString
    MAX-ACCESS accessible-for-notify
    STATUS current
    DESCRIPTION
        "Parameter 'interface' in event TIPS.9"
    ::= { tipsEventObjects9 2 }

tipsEventObjects10 OBJECT-IDENTITY
    STATUS current
    DESCRIPTION
        "Event TIPS.10
        TIPS IP Spoofing engine dropped the specified packet as a result of the
        specified reason. Possible reasons follow. 'timeout' when address
        resolution times out. 'mismatch' when address resolution provides a
        different mac address. 'DoS' when new untrusted source address packets
        are received short after address resolution completed successfully."
    ::= { tipsEventsGroup 10 }

tips10_reason OBJECT-TYPE
    SYNTAX DisplayString
    MAX-ACCESS accessible-for-notify
    STATUS current
    DESCRIPTION
        "Parameter 'reason' in event TIPS.10"
    ::= { tipsEventObjects10 1 }

tips10_mac_src OBJECT-TYPE
    SYNTAX DisplayString
    MAX-ACCESS accessible-for-notify
    STATUS current
    DESCRIPTION
        "Parameter 'mac_src' in event TIPS.10"
    ::= { tipsEventObjects10 2 }

tips10_mac_dst OBJECT-TYPE
    SYNTAX DisplayString
    MAX-ACCESS accessible-for-notify
    STATUS current
    DESCRIPTION
        "Parameter 'mac_dst' in event TIPS.10"
    ::= { tipsEventObjects10 3 }

tips10_ip_src OBJECT-TYPE
    SYNTAX IpAddress
    MAX-ACCESS accessible-for-notify
    STATUS current
    DESCRIPTION
        "Parameter 'ip_src' in event TIPS.10"
    ::= { tipsEventObjects10 4 }

tips10_ip_dst OBJECT-TYPE
    SYNTAX IpAddress
    MAX-ACCESS accessible-for-notify
    STATUS current
    DESCRIPTION
        "Parameter 'ip_dst' in event TIPS.10"
    ::= { tipsEventObjects10 5 }

tips10_interface OBJECT-TYPE
    SYNTAX DisplayString
    MAX-ACCESS accessible-for-notify
    STATUS current
    DESCRIPTION
        "Parameter 'interface' in event TIPS.10"
    ::= { tipsEventObjects10 6 }

tipsEventObjects11 OBJECT-IDENTITY
    STATUS current
    DESCRIPTION
        "Event TIPS.11
        TIPS IP Spoofing engine received an arp response with the specified mac
        address for the specified ip address on the specified interface."
    ::= { tipsEventsGroup 11 }

tips11_mac_address OBJECT-TYPE
    SYNTAX DisplayString
    MAX-ACCESS accessible-for-notify
    STATUS current
    DESCRIPTION
        "Parameter 'mac_address' in event TIPS.11"
    ::= { tipsEventObjects11 1 }

tips11_ip_address OBJECT-TYPE
    SYNTAX IpAddress
    MAX-ACCESS accessible-for-notify
    STATUS current
    DESCRIPTION
        "Parameter 'ip_address' in event TIPS.11"
    ::= { tipsEventObjects11 2 }

tips11_interface OBJECT-TYPE
    SYNTAX DisplayString
    MAX-ACCESS accessible-for-notify
    STATUS current
    DESCRIPTION
        "Parameter 'interface' in event TIPS.11"
    ::= { tipsEventObjects11 3 }

tipsEventObjects12 OBJECT-IDENTITY
    STATUS current
    DESCRIPTION
        "Event TIPS.12
        TIPS IP Spoofing engine forwarded the specified packet."
    ::= { tipsEventsGroup 12 }

tips12_mac_src OBJECT-TYPE
    SYNTAX DisplayString
    MAX-ACCESS accessible-for-notify
    STATUS current
    DESCRIPTION
        "Parameter 'mac_src' in event TIPS.12"
    ::= { tipsEventObjects12 1 }

tips12_mac_dst OBJECT-TYPE
    SYNTAX DisplayString
    MAX-ACCESS accessible-for-notify
    STATUS current
    DESCRIPTION
        "Parameter 'mac_dst' in event TIPS.12"
    ::= { tipsEventObjects12 2 }

tips12_ip_src OBJECT-TYPE
    SYNTAX IpAddress
    MAX-ACCESS accessible-for-notify
    STATUS current
    DESCRIPTION
        "Parameter 'ip_src' in event TIPS.12"
    ::= { tipsEventObjects12 3 }

tips12_ip_dst OBJECT-TYPE
    SYNTAX IpAddress
    MAX-ACCESS accessible-for-notify
    STATUS current
    DESCRIPTION
        "Parameter 'ip_dst' in event TIPS.12"
    ::= { tipsEventObjects12 4 }

tips12_interface OBJECT-TYPE
    SYNTAX DisplayString
    MAX-ACCESS accessible-for-notify
    STATUS current
    DESCRIPTION
        "Parameter 'interface' in event TIPS.12"
    ::= { tipsEventObjects12 5 }

tipsEventObjects13 OBJECT-IDENTITY
    STATUS current
    DESCRIPTION
        "Event TIPS.13
        TIPS IP Spoofing engine ignored a malformed packet with the specified
        mac addresses on the specified interface."
    ::= { tipsEventsGroup 13 }

tips13_mac_src OBJECT-TYPE
    SYNTAX DisplayString
    MAX-ACCESS accessible-for-notify
    STATUS current
    DESCRIPTION
        "Parameter 'mac_src' in event TIPS.13"
    ::= { tipsEventObjects13 1 }

tips13_mac_dst OBJECT-TYPE
    SYNTAX DisplayString
    MAX-ACCESS accessible-for-notify
    STATUS current
    DESCRIPTION
        "Parameter 'mac_dst' in event TIPS.13"
    ::= { tipsEventObjects13 2 }

tips13_interface OBJECT-TYPE
    SYNTAX DisplayString
    MAX-ACCESS accessible-for-notify
    STATUS current
    DESCRIPTION
        "Parameter 'interface' in event TIPS.13"
    ::= { tipsEventObjects13 3 }

tipsEventObjects14 OBJECT-IDENTITY
    STATUS current
    DESCRIPTION
        "Event TIPS.14
        TIPS IP Spoofing engine would drop the specified packet as a result of the
        specified reason. Possible reasons follow. 'timeout' when address
        resolution times out. 'mismatch' when address resolution provides a
        different mac address. 'DoS' when new untrusted source address packets
        are received short after address resolution completed successfully."
    ::= { tipsEventsGroup 14 }

tips14_reason OBJECT-TYPE
    SYNTAX DisplayString
    MAX-ACCESS accessible-for-notify
    STATUS current
    DESCRIPTION
        "Parameter 'reason' in event TIPS.14"
    ::= { tipsEventObjects14 1 }

tips14_mac_src OBJECT-TYPE
    SYNTAX DisplayString
    MAX-ACCESS accessible-for-notify
    STATUS current
    DESCRIPTION
        "Parameter 'mac_src' in event TIPS.14"
    ::= { tipsEventObjects14 2 }

tips14_mac_dst OBJECT-TYPE
    SYNTAX DisplayString
    MAX-ACCESS accessible-for-notify
    STATUS current
    DESCRIPTION
        "Parameter 'mac_dst' in event TIPS.14"
    ::= { tipsEventObjects14 3 }

tips14_ip_src OBJECT-TYPE
    SYNTAX IpAddress
    MAX-ACCESS accessible-for-notify
    STATUS current
    DESCRIPTION
        "Parameter 'ip_src' in event TIPS.14"
    ::= { tipsEventObjects14 4 }

tips14_ip_dst OBJECT-TYPE
    SYNTAX IpAddress
    MAX-ACCESS accessible-for-notify
    STATUS current
    DESCRIPTION
        "Parameter 'ip_dst' in event TIPS.14"
    ::= { tipsEventObjects14 5 }

tips14_interface OBJECT-TYPE
    SYNTAX DisplayString
    MAX-ACCESS accessible-for-notify
    STATUS current
    DESCRIPTION
        "Parameter 'interface' in event TIPS.14"
    ::= { tipsEventObjects14 6 }

tipsEventObjects15 OBJECT-IDENTITY
    STATUS current
    DESCRIPTION
        "Event TIPS.15
        TIPS IP Spoofing engine would forward the specified packet."
    ::= { tipsEventsGroup 15 }

tips15_mac_src OBJECT-TYPE
    SYNTAX DisplayString
    MAX-ACCESS accessible-for-notify
    STATUS current
    DESCRIPTION
        "Parameter 'mac_src' in event TIPS.15"
    ::= { tipsEventObjects15 1 }

tips15_mac_dst OBJECT-TYPE
    SYNTAX DisplayString
    MAX-ACCESS accessible-for-notify
    STATUS current
    DESCRIPTION
        "Parameter 'mac_dst' in event TIPS.15"
    ::= { tipsEventObjects15 2 }

tips15_ip_src OBJECT-TYPE
    SYNTAX IpAddress
    MAX-ACCESS accessible-for-notify
    STATUS current
    DESCRIPTION
        "Parameter 'ip_src' in event TIPS.15"
    ::= { tipsEventObjects15 3 }

tips15_ip_dst OBJECT-TYPE
    SYNTAX IpAddress
    MAX-ACCESS accessible-for-notify
    STATUS current
    DESCRIPTION
        "Parameter 'ip_dst' in event TIPS.15"
    ::= { tipsEventObjects15 4 }

tips15_interface OBJECT-TYPE
    SYNTAX DisplayString
    MAX-ACCESS accessible-for-notify
    STATUS current
    DESCRIPTION
        "Parameter 'interface' in event TIPS.15"
    ::= { tipsEventObjects15 5 }


tipsNotification1 NOTIFICATION-TYPE
    OBJECTS { 
              tips1_source_ip, 
              tips1_destination_ip 
            }
    STATUS current
    DESCRIPTION
        "Notification of Event TIPS.1

        Message: 'IP packet beeing processed $1->$2'

        Parameters list:
              $1: tips1_source_ip
              $2: tips1_destination_ip

        packet processed"
    ::= { tipsNotificationsPrefix 1 }

tipsNotification2 NOTIFICATION-TYPE
    OBJECTS { 
              tips2_msg 
            }
    STATUS current
    DESCRIPTION
        "Notification of Event TIPS.2

        Message: 'TIPS alert: $1'

        Parameters list:
              $1: tips2_msg

        tips alert has been generated"
    ::= { tipsNotificationsPrefix 2 }

tipsNotification3 NOTIFICATION-TYPE
    OBJECTS { 
              tips3_state 
            }
    STATUS current
    DESCRIPTION
        "Notification of Event TIPS.3

        Message: 'TIPS state changed $1'

        Parameters list:
              $1: tips3_state

        tips state changed"
    ::= { tipsNotificationsPrefix 3 }

tipsNotification4 NOTIFICATION-TYPE
    OBJECTS { 
              tips4_source_ip, 
              tips4_destination_ip 
            }
    STATUS current
    DESCRIPTION
        "Notification of Event TIPS.4

        Message: 'IP packet discarded $1->$2'

        Parameters list:
              $1: tips4_source_ip
              $2: tips4_destination_ip

        packet processed"
    ::= { tipsNotificationsPrefix 4 }

tipsNotification5 NOTIFICATION-TYPE
    OBJECTS { 
              tips5_ip_src, 
              tips5_interface 
            }
    STATUS current
    DESCRIPTION
        "Notification of Event TIPS.5

        Message: 'Ip spoofing pending ip queue full for $1 on interface $2'

        Parameters list:
              $1: tips5_ip_src
              $2: tips5_interface

        TIPS IP Spoofing engine has too many pending address resolutions for the
        specified address on the specified interface."
    ::= { tipsNotificationsPrefix 5 }

tipsNotification6 NOTIFICATION-TYPE
    OBJECTS { 
              tips6_mac_src, 
              tips6_mac_dst,
              tips6_ip_src,
              tips6_ip_dst,
              tips6_interface 
            }
    STATUS current
    DESCRIPTION
        "Notification of Event TIPS.6

        Message: 'Ip spoofing pending ip packet queue full for mac $1->$2 ip $3->$4 on interface $5'

        Parameters list:
              $1: tips6_mac_src
              $2: tips6_mac_dst
              $3: tips6_ip_src
              $4: tips6_ip_dst
              $5: tips6_interface

        TIPS IP Spoofing engine has too many pending packets from the specified
        source IP addres on reception of a new packet with specified mac and ip
        addresses on the specified interface."
    ::= { tipsNotificationsPrefix 6 }

tipsNotification7 NOTIFICATION-TYPE
    OBJECTS { 
              tips7_mac_src, 
              tips7_mac_dst,
              tips7_ip_src,
              tips7_ip_dst,
              tips7_interface 
            }
    STATUS current
    DESCRIPTION
        "Notification of Event TIPS.7

        Message: 'Ip spoofing enqueued for resolution a packet $1->$2 ip $3->$4 on interface $5'

        Parameters list:
              $1: tips7_mac_src
              $2: tips7_mac_dst
              $3: tips7_ip_src
              $4: tips7_ip_dst
              $5: tips7_interface

        TIPS IP Spoofing engine received the specified packet on the specified
        interface and enqueued it while resolving source address."
    ::= { tipsNotificationsPrefix 7 }

tipsNotification8 NOTIFICATION-TYPE
    OBJECTS { 
              tips8_ip_address, 
              tips8_interface 
            }
    STATUS current
    DESCRIPTION
        "Notification of Event TIPS.8

        Message: 'Ip spoofing sends an arp request for $1 on interface $2'

        Parameters list:
              $1: tips8_ip_address
              $2: tips8_interface

        TIPS IP Spoofing engine sends an arp request for the specified address
        on the specified interface."
    ::= { tipsNotificationsPrefix 8 }

tipsNotification9 NOTIFICATION-TYPE
    OBJECTS { 
              tips9_ip_address, 
              tips9_interface 
            }
    STATUS current
    DESCRIPTION
        "Notification of Event TIPS.9

        Message: 'Ip spoofing arp request timed out for ip address $1 on interface $2'

        Parameters list:
              $1: tips9_ip_address
              $2: tips9_interface

        TIPS IP Spoofing engine sent arp requests for the specified ip address
        on the specified interface. These requests timed out."
    ::= { tipsNotificationsPrefix 9 }

tipsNotification10 NOTIFICATION-TYPE
    OBJECTS { 
              tips10_reason, 
              tips10_mac_src,
              tips10_mac_dst,
              tips10_ip_src,
              tips10_ip_dst,
              tips10_interface 
            }
    STATUS current
    DESCRIPTION
        "Notification of Event TIPS.10

        Message: 'Ip spoofing dropped by reason $1 packet $2->$3 ip $4->$5 on interface $6'

        Parameters list:
              $1: tips10_reason
              $2: tips10_mac_src
              $3: tips10_mac_dst
              $4: tips10_ip_src
              $5: tips10_ip_dst
              $6: tips10_interface

        TIPS IP Spoofing engine dropped the specified packet as a result of the
        specified reason. Possible reasons follow. 'timeout' when address
        resolution times out. 'mismatch' when address resolution provides a
        different mac address. 'DoS' when new untrusted source address packets
        are received short after address resolution completed successfully."
    ::= { tipsNotificationsPrefix 10 }

tipsNotification11 NOTIFICATION-TYPE
    OBJECTS { 
              tips11_mac_address, 
              tips11_ip_address,
              tips11_interface 
            }
    STATUS current
    DESCRIPTION
        "Notification of Event TIPS.11

        Message: 'Ip spoofing received an arp response of $1 for $2 on interface $3'

        Parameters list:
              $1: tips11_mac_address
              $2: tips11_ip_address
              $3: tips11_interface

        TIPS IP Spoofing engine received an arp response with the specified mac
        address for the specified ip address on the specified interface."
    ::= { tipsNotificationsPrefix 11 }

tipsNotification12 NOTIFICATION-TYPE
    OBJECTS { 
              tips12_mac_src, 
              tips12_mac_dst,
              tips12_ip_src,
              tips12_ip_dst,
              tips12_interface 
            }
    STATUS current
    DESCRIPTION
        "Notification of Event TIPS.12

        Message: 'Ip spoofing forward packet $1->$2 ip $3->$4 on interface $5'

        Parameters list:
              $1: tips12_mac_src
              $2: tips12_mac_dst
              $3: tips12_ip_src
              $4: tips12_ip_dst
              $5: tips12_interface

        TIPS IP Spoofing engine forwarded the specified packet."
    ::= { tipsNotificationsPrefix 12 }

tipsNotification13 NOTIFICATION-TYPE
    OBJECTS { 
              tips13_mac_src, 
              tips13_mac_dst,
              tips13_interface 
            }
    STATUS current
    DESCRIPTION
        "Notification of Event TIPS.13

        Message: 'Ip spoofing ignored a malformed packet $1->$2 on interface $3'

        Parameters list:
              $1: tips13_mac_src
              $2: tips13_mac_dst
              $3: tips13_interface

        TIPS IP Spoofing engine ignored a malformed packet with the specified
        mac addresses on the specified interface."
    ::= { tipsNotificationsPrefix 13 }

tipsNotification14 NOTIFICATION-TYPE
    OBJECTS { 
              tips14_reason, 
              tips14_mac_src,
              tips14_mac_dst,
              tips14_ip_src,
              tips14_ip_dst,
              tips14_interface 
            }
    STATUS current
    DESCRIPTION
        "Notification of Event TIPS.14

        Message: 'Ip spoofing would be dropped by reason $1 packet $2->$3 ip $4->$5 on interface $6'

        Parameters list:
              $1: tips14_reason
              $2: tips14_mac_src
              $3: tips14_mac_dst
              $4: tips14_ip_src
              $5: tips14_ip_dst
              $6: tips14_interface

        TIPS IP Spoofing engine would drop the specified packet as a result of the
        specified reason. Possible reasons follow. 'timeout' when address
        resolution times out. 'mismatch' when address resolution provides a
        different mac address. 'DoS' when new untrusted source address packets
        are received short after address resolution completed successfully."
    ::= { tipsNotificationsPrefix 14 }

tipsNotification15 NOTIFICATION-TYPE
    OBJECTS { 
              tips15_mac_src, 
              tips15_mac_dst,
              tips15_ip_src,
              tips15_ip_dst,
              tips15_interface 
            }
    STATUS current
    DESCRIPTION
        "Notification of Event TIPS.15

        Message: 'Ip spoofing would forward packet $1->$2 ip $3->$4 on interface $5'

        Parameters list:
              $1: tips15_mac_src
              $2: tips15_mac_dst
              $3: tips15_ip_src
              $4: tips15_ip_dst
              $5: tips15_interface

        TIPS IP Spoofing engine would forward the specified packet."
    ::= { tipsNotificationsPrefix 15 }


END
