IBM-SYSTEM-ASSETID-MIB DEFINITIONS ::= BEGIN

IMPORTS
   OBJECT-TYPE
      FROM RFC-1212

   TRAP-TYPE
      FROM RFC-1215

   ibmSystemAssetID,
   Boolean, Uint8, Sint8, Uint16, Sint16, Uint32,
   Sint32, Uint64, Sint64, Real32, Real64, String, Datetime
      FROM IBM-SYSTEM-MIB;

--
-- Primitive types
--
Boolean  ::= INTEGER (0..1)
Uint8    ::= INTEGER (0..255)
Sint8    ::= INTEGER (-128..127)
Uint16   ::= INTEGER (0..65535)
Sint16   ::= INTEGER (-32767..32766)
Uint32   ::= INTEGER (0..4294967295)
Sint32   ::= INTEGER (-2147483647..2147483646)
Uint64   ::= OCTET STRING
Sint64   ::= OCTET STRING
Real32   ::= INTEGER (-1..1)
Real64   ::= INTEGER (-1..1)
String   ::= OCTET STRING
Datetime ::= OCTET STRING


ibmSystemSerialNumberInformationTable OBJECT-TYPE
   SYNTAX         SEQUENCE OF IbmSystemSerialNumberInformationEntry
   ACCESS         not-accessible
   STATUS         mandatory
   DESCRIPTION    "The IBMPSG_SerialNumberInformation class contains model numbers for each of the major hardware components in an IBM PC."
   REFERENCE      "IBMPSG_SerialNumberInformation"
::= { ibmSystemAssetID 1 }

ibmSystemSerialNumberInformationEntry OBJECT-TYPE
   SYNTAX         IbmSystemSerialNumberInformationEntry
   ACCESS         not-accessible
   STATUS         mandatory
   DESCRIPTION    ""
   INDEX          { ibmSystemSerialNumberInformationKeyIndex }
::= { ibmSystemSerialNumberInformationTable 1 }

IbmSystemSerialNumberInformationEntry ::= SEQUENCE
{
   ibmSystemSerialNumberInformationKeyIndex String,
   ibmSystemSerialNumberInformationName String,
   ibmSystemSerialNumberInformationSerialNumber String,
   ibmSystemSerialNumberInformationManufacturer String,
   ibmSystemSerialNumberInformationModel String,
   ibmSystemSerialNumberInformationVersion String,
   ibmSystemSerialNumberInformationOtherIdentifyingInfo String
}

ibmSystemSerialNumberInformationKeyIndex OBJECT-TYPE
   SYNTAX         String
   ACCESS         read-write
   STATUS         mandatory
   DESCRIPTION    ""
   REFERENCE      "IBMPSG_SerialNumberInformation.KeyIndex"
::= { ibmSystemSerialNumberInformationEntry 1 }

ibmSystemSerialNumberInformationName OBJECT-TYPE
   SYNTAX         String
   ACCESS         read-write
   STATUS         mandatory
   DESCRIPTION    "Name of the Asset"
   REFERENCE      "IBMPSG_SerialNumberInformation.Name"
::= { ibmSystemSerialNumberInformationEntry 2 }

ibmSystemSerialNumberInformationSerialNumber OBJECT-TYPE
   SYNTAX         String
   ACCESS         read-write
   STATUS         mandatory
   DESCRIPTION    "Serial Number of the Asset"
   REFERENCE      "IBMPSG_SerialNumberInformation.SerialNumber"
::= { ibmSystemSerialNumberInformationEntry 3 }

ibmSystemSerialNumberInformationManufacturer OBJECT-TYPE
   SYNTAX         String
   ACCESS         read-write
   STATUS         mandatory
   DESCRIPTION    ""
   REFERENCE      "IBMPSG_SerialNumberInformation.Manufacturer"
::= { ibmSystemSerialNumberInformationEntry 4 }

ibmSystemSerialNumberInformationModel OBJECT-TYPE
   SYNTAX         String
   ACCESS         read-write
   STATUS         mandatory
   DESCRIPTION    ""
   REFERENCE      "IBMPSG_SerialNumberInformation.Model"
::= { ibmSystemSerialNumberInformationEntry 5 }

ibmSystemSerialNumberInformationVersion OBJECT-TYPE
   SYNTAX         String
   ACCESS         read-write
   STATUS         mandatory
   DESCRIPTION    ""
   REFERENCE      "IBMPSG_SerialNumberInformation.Version"
::= { ibmSystemSerialNumberInformationEntry 6 }

ibmSystemSerialNumberInformationOtherIdentifyingInfo OBJECT-TYPE
   SYNTAX         String
   ACCESS         read-write
   STATUS         mandatory
   DESCRIPTION    ""
   REFERENCE      "IBMPSG_SerialNumberInformation.OtherIdentifyingInfo"
::= { ibmSystemSerialNumberInformationEntry 7 }

ibmSystemComputerSystemTable OBJECT-TYPE
   SYNTAX         SEQUENCE OF IbmSystemComputerSystemEntry
   ACCESS         not-accessible
   STATUS         mandatory
   DESCRIPTION    "The ibmSystem_ComputerSystem class represents an IBM managed PC."
   REFERENCE      "IBMPSG_ComputerSystem"
::= { ibmSystemAssetID 2 }

ibmSystemComputerSystemEntry OBJECT-TYPE
   SYNTAX         IbmSystemComputerSystemEntry
   ACCESS         not-accessible
   STATUS         mandatory
   DESCRIPTION    ""
   INDEX          { ibmSystemComputerSystemKeyIndex }
::= { ibmSystemComputerSystemTable 1 }

IbmSystemComputerSystemEntry ::= SEQUENCE
{
   ibmSystemComputerSystemKeyIndex String,   
   ibmSystemComputerSystemName String,
   ibmSystemComputerSystemModel String,
   ibmSystemComputerSystemPrimaryOwnerContact String,
   ibmSystemComputerSystemStatus String
}

ibmSystemComputerSystemKeyIndex OBJECT-TYPE
   SYNTAX         String
   ACCESS         read-write
   STATUS         mandatory
   DESCRIPTION    ""
   REFERENCE      "IBMPSG_ComputerSystem.KeyIndex"
::= { ibmSystemComputerSystemEntry 1 }

ibmSystemComputerSystemName OBJECT-TYPE
   SYNTAX         String
   ACCESS         read-write
   STATUS         mandatory
   DESCRIPTION    ""
   REFERENCE      "IBMPSG_ComputerSystem.Name"
::= { ibmSystemComputerSystemEntry 2 }

ibmSystemComputerSystemModel OBJECT-TYPE
   SYNTAX         String
   ACCESS         read-write
   STATUS         mandatory
   DESCRIPTION    ""
   REFERENCE      "IBMPSG_ComputerSystem.Model"
::= { ibmSystemComputerSystemEntry 3 }

ibmSystemComputerSystemPrimaryOwnerContact OBJECT-TYPE
   SYNTAX         String
   ACCESS         read-write
   STATUS         mandatory
   DESCRIPTION    ""
   REFERENCE      "IBMPSG_ComputerSystem.PrimaryOwnerContact"
::= { ibmSystemComputerSystemEntry 4 }

ibmSystemComputerSystemStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "IBMPSG_ComputerSystem.Status"
::= { ibmSystemComputerSystemEntry 5 }

ibmSystemComputerSystemDetailsTable OBJECT-TYPE
   SYNTAX         SEQUENCE OF IbmSystemComputerSystemDetailsEntry
   ACCESS         not-accessible
   STATUS         mandatory
   DESCRIPTION    "The IBMPSG_ComputerSystemDetails class contains extended information about an IBM managed PC."
   REFERENCE      "IBMPSG_ComputerSystemDetails"
::= { ibmSystemAssetID 3 }

ibmSystemComputerSystemDetailsEntry OBJECT-TYPE
   SYNTAX         IbmSystemComputerSystemDetailsEntry
   ACCESS         not-accessible
   STATUS         mandatory
   DESCRIPTION    ""
   INDEX          { ibmSystemComputerSystemDetailsKeyIndex }
::= { ibmSystemComputerSystemDetailsTable 1 }

IbmSystemComputerSystemDetailsEntry ::= SEQUENCE
{
   ibmSystemComputerSystemDetailsKeyIndex String,   
   ibmSystemComputerSystemDetailsName String,
   ibmSystemComputerSystemDetailsSystemUUID String,
   ibmSystemComputerSystemDetailsAssetNumber String,
   ibmSystemComputerSystemDetailsAssetIdTag String,
   ibmSystemComputerSystemDetailsLastInventoried Datetime,
   ibmSystemComputerSystemDetailsPurchaseDate Datetime,
   ibmSystemComputerSystemDetailsModel String,
   ibmSystemComputerSystemDetailsProductName String,
   ibmSystemComputerSystemDetailsSerialNumber String,
   ibmSystemComputerSystemDetailsPersonalizedLabel1 String,
   ibmSystemComputerSystemDetailsPersonalizedData1 String,
   ibmSystemComputerSystemDetailsPersonalizedLabel2 String,
   ibmSystemComputerSystemDetailsPersonalizedData2 String,
   ibmSystemComputerSystemDetailsPersonalizedLabel3 String,
   ibmSystemComputerSystemDetailsPersonalizedData3 String,
   ibmSystemComputerSystemDetailsPersonalizedLabel4 String,
   ibmSystemComputerSystemDetailsPersonalizedData4 String,
   ibmSystemComputerSystemDetailsPersonalizedLabel5 String,
   ibmSystemComputerSystemDetailsPersonalizedData5 String,
   ibmSystemComputerSystemDetailsPrimaryOwnerName String,
   ibmSystemComputerSystemDetailsPrimaryOwnerPhone String,
   ibmSystemComputerSystemDetailsPrimaryOwnerDepartment String,
   ibmSystemComputerSystemDetailsPrimaryOwnerPosition String,
   ibmSystemComputerSystemDetailsSystemLocation String,
   ibmSystemComputerSystemDetailsAssetIDStringArea Uint32,
   ibmSystemComputerSystemDetailsLocalDateTime Datetime,
   ibmSystemComputerSystemDetailsLCCMProfile String,
   ibmSystemComputerSystemDetailsLCCMUpdateTime Datetime
}

ibmSystemComputerSystemDetailsKeyIndex OBJECT-TYPE
   SYNTAX         String
   ACCESS         read-write
   STATUS         mandatory
   DESCRIPTION    ""
   REFERENCE      "IBMPSG_ComputerSystemDetails.KeyIndex"
::= { ibmSystemComputerSystemDetailsEntry 1 }

ibmSystemComputerSystemDetailsName OBJECT-TYPE
   SYNTAX         String
   ACCESS         read-write
   STATUS         mandatory
   DESCRIPTION    ""
   REFERENCE      "IBMPSG_ComputerSystemDetails.Name"
::= { ibmSystemComputerSystemDetailsEntry 2 }

ibmSystemComputerSystemDetailsSystemUUID OBJECT-TYPE
   SYNTAX         String
   ACCESS         read-write
   STATUS         mandatory
   DESCRIPTION    "Universally unique system identifier as defined in the PC97 and the SMBIOS specifications."
   REFERENCE      "IBMPSG_ComputerSystemDetails.SystemUUID"
::= { ibmSystemComputerSystemDetailsEntry 3 }

ibmSystemComputerSystemDetailsAssetNumber OBJECT-TYPE
   SYNTAX         String
   ACCESS         read-write
   STATUS         mandatory
   DESCRIPTION    "A unique identifier assigned to this asset."
   REFERENCE      "IBMPSG_ComputerSystemDetails.AssetNumber"
::= { ibmSystemComputerSystemDetailsEntry 4 }

ibmSystemComputerSystemDetailsAssetIdTag OBJECT-TYPE
   SYNTAX         String
   ACCESS         read-write
   STATUS         mandatory
   DESCRIPTION    "A unique identifier transmitted when a system with AssetID enters an RF field."
   REFERENCE      "IBMPSG_ComputerSystemDetails.AssetIdTag"
::= { ibmSystemComputerSystemDetailsEntry 5 }

ibmSystemComputerSystemDetailsLastInventoried OBJECT-TYPE
   SYNTAX         Datetime
   ACCESS         read-write
   STATUS         mandatory
   DESCRIPTION    "Date when the system was last counted."
   REFERENCE      "IBMPSG_ComputerSystemDetails.LastInventoried"
::= { ibmSystemComputerSystemDetailsEntry 6 }

ibmSystemComputerSystemDetailsPurchaseDate OBJECT-TYPE
   SYNTAX         Datetime
   ACCESS         read-write
   STATUS         mandatory
   DESCRIPTION    "Date on which this asset was purchased."
   REFERENCE      "IBMPSG_ComputerSystemDetails.PurchaseDate"
::= { ibmSystemComputerSystemDetailsEntry 7 }

ibmSystemComputerSystemDetailsModel OBJECT-TYPE
   SYNTAX         String
   ACCESS         read-write
   STATUS         mandatory
   DESCRIPTION    "Model number of this system."
   REFERENCE      "IBMPSG_ComputerSystemDetails.Model"
::= { ibmSystemComputerSystemDetailsEntry 8 }

ibmSystemComputerSystemDetailsProductName OBJECT-TYPE
   SYNTAX         String
   ACCESS         read-write
   STATUS         mandatory
   DESCRIPTION    "Product Name of this system."
   REFERENCE      "IBMPSG_ComputerSystemDetails.ProductName"
::= { ibmSystemComputerSystemDetailsEntry 9 }

ibmSystemComputerSystemDetailsSerialNumber OBJECT-TYPE
   SYNTAX         String
   ACCESS         read-write
   STATUS         mandatory
   DESCRIPTION    "Serial number of this system."
   REFERENCE      "IBMPSG_ComputerSystemDetails.SerialNumber"
::= { ibmSystemComputerSystemDetailsEntry 10 }

ibmSystemComputerSystemDetailsPersonalizedLabel1 OBJECT-TYPE
   SYNTAX         String
   ACCESS         read-write
   STATUS         mandatory
   DESCRIPTION    "Used to personalize information about this computer system."
   REFERENCE      "IBMPSG_ComputerSystemDetails.PersonalizedLabel1"
::= { ibmSystemComputerSystemDetailsEntry 11 }

ibmSystemComputerSystemDetailsPersonalizedData1 OBJECT-TYPE
   SYNTAX         String
   ACCESS         read-write
   STATUS         mandatory
   DESCRIPTION    "Used to personalize information about this computer system."
   REFERENCE      "IBMPSG_ComputerSystemDetails.PersonalizedData1"
::= { ibmSystemComputerSystemDetailsEntry 12 }

ibmSystemComputerSystemDetailsPersonalizedLabel2 OBJECT-TYPE
   SYNTAX         String
   ACCESS         read-write
   STATUS         mandatory
   DESCRIPTION    "Used to personalize information about this computer system."
   REFERENCE      "IBMPSG_ComputerSystemDetails.PersonalizedLabel2"
::= { ibmSystemComputerSystemDetailsEntry 13 }

ibmSystemComputerSystemDetailsPersonalizedData2 OBJECT-TYPE
   SYNTAX         String
   ACCESS         read-write
   STATUS         mandatory
   DESCRIPTION    "Used to personalize information about this computer system."
   REFERENCE      "IBMPSG_ComputerSystemDetails.PersonalizedData2"
::= { ibmSystemComputerSystemDetailsEntry 14 }

ibmSystemComputerSystemDetailsPersonalizedLabel3 OBJECT-TYPE
   SYNTAX         String
   ACCESS         read-write
   STATUS         mandatory
   DESCRIPTION    "Used to personalize information about this computer system."
   REFERENCE      "IBMPSG_ComputerSystemDetails.PersonalizedLabel3"
::= { ibmSystemComputerSystemDetailsEntry 15 }

ibmSystemComputerSystemDetailsPersonalizedData3 OBJECT-TYPE
   SYNTAX         String
   ACCESS         read-write
   STATUS         mandatory
   DESCRIPTION    "Used to personalize information about this computer system."
   REFERENCE      "IBMPSG_ComputerSystemDetails.PersonalizedData3"
::= { ibmSystemComputerSystemDetailsEntry 16 }

ibmSystemComputerSystemDetailsPersonalizedLabel4 OBJECT-TYPE
   SYNTAX         String
   ACCESS         read-write
   STATUS         mandatory
   DESCRIPTION    "Used to personalize information about this computer system."
   REFERENCE      "IBMPSG_ComputerSystemDetails.PersonalizedLabel4"
::= { ibmSystemComputerSystemDetailsEntry 17 }

ibmSystemComputerSystemDetailsPersonalizedData4 OBJECT-TYPE
   SYNTAX         String
   ACCESS         read-write
   STATUS         mandatory
   DESCRIPTION    "Used to personalize information about this computer system."
   REFERENCE      "IBMPSG_ComputerSystemDetails.PersonalizedData4"
::= { ibmSystemComputerSystemDetailsEntry 18 }

ibmSystemComputerSystemDetailsPersonalizedLabel5 OBJECT-TYPE
   SYNTAX         String
   ACCESS         read-write
   STATUS         mandatory
   DESCRIPTION    "Used to personalize information about this computer system"
   REFERENCE      "IBMPSG_ComputerSystemDetails.PersonalizedLabel5"
::= { ibmSystemComputerSystemDetailsEntry 19 }

ibmSystemComputerSystemDetailsPersonalizedData5 OBJECT-TYPE
   SYNTAX         String
   ACCESS         read-write
   STATUS         mandatory
   DESCRIPTION    "Used to personalize information about this computer system"
   REFERENCE      "IBMPSG_ComputerSystemDetails.PersonalizedData5"
::= { ibmSystemComputerSystemDetailsEntry 20 }

ibmSystemComputerSystemDetailsPrimaryOwnerName OBJECT-TYPE
   SYNTAX         String
   ACCESS         read-write
   STATUS         mandatory
   DESCRIPTION    ""
   REFERENCE      "IBMPSG_ComputerSystemDetails.PrimaryOwnerName"
::= { ibmSystemComputerSystemDetailsEntry 21 }

ibmSystemComputerSystemDetailsPrimaryOwnerPhone OBJECT-TYPE
   SYNTAX         String
   ACCESS         read-write
   STATUS         mandatory
   DESCRIPTION    ""
   REFERENCE      "IBMPSG_ComputerSystemDetails.PrimaryOwnerPhone"
::= { ibmSystemComputerSystemDetailsEntry 22 }

ibmSystemComputerSystemDetailsPrimaryOwnerDepartment OBJECT-TYPE
   SYNTAX         String
   ACCESS         read-write
   STATUS         mandatory
   DESCRIPTION    ""
   REFERENCE      "IBMPSG_ComputerSystemDetails.PrimaryOwnerDepartment"
::= { ibmSystemComputerSystemDetailsEntry 23 }

ibmSystemComputerSystemDetailsPrimaryOwnerPosition OBJECT-TYPE
   SYNTAX         String
   ACCESS         read-write
   STATUS         mandatory
   DESCRIPTION    ""
   REFERENCE      "IBMPSG_ComputerSystemDetails.PrimaryOwnerPosition"
::= { ibmSystemComputerSystemDetailsEntry 24 }

ibmSystemComputerSystemDetailsSystemLocation OBJECT-TYPE
   SYNTAX         String
   ACCESS         read-write
   STATUS         mandatory
   DESCRIPTION    ""
   REFERENCE      "IBMPSG_ComputerSystemDetails.SystemLocation"
::= { ibmSystemComputerSystemDetailsEntry 25 }

ibmSystemComputerSystemDetailsAssetIDStringArea OBJECT-TYPE
   SYNTAX         Uint32
   ACCESS         read-write
   STATUS         mandatory
   DESCRIPTION    "The available String Area in bytes in the RF-ID EEPROM."
   REFERENCE      "IBMPSG_ComputerSystemDetails.AssetIDStringArea"
::= { ibmSystemComputerSystemDetailsEntry 26 }

ibmSystemComputerSystemDetailsLocalDateTime OBJECT-TYPE
   SYNTAX         Datetime
   ACCESS         read-write
   STATUS         mandatory
   DESCRIPTION    "Writable version of the OperatingSystem's notion of the local date and time of day."
   REFERENCE      "IBMPSG_ComputerSystemDetails.LocalDateTime"
::= { ibmSystemComputerSystemDetailsEntry 27 }

ibmSystemComputerSystemDetailsLCCMProfile OBJECT-TYPE
   SYNTAX         String
   ACCESS         read-write
   STATUS         mandatory
   DESCRIPTION    "LCCM Profile name describing the operating system image installed on this system"
   REFERENCE      "IBMPSG_ComputerSystemDetails.LCCMProfile"
::= { ibmSystemComputerSystemDetailsEntry 28 }

ibmSystemComputerSystemDetailsLCCMUpdateTime OBJECT-TYPE
   SYNTAX         Datetime
   ACCESS         read-write
   STATUS         mandatory
   DESCRIPTION    "Date that the hard drive image was last updated by LCCM"
   REFERENCE      "IBMPSG_ComputerSystemDetails.LCCMUpdateTime"
::= { ibmSystemComputerSystemDetailsEntry 29 }

ibmSystemLeaseTable OBJECT-TYPE
   SYNTAX         SEQUENCE OF IbmSystemLeaseEntry
   ACCESS         not-accessible
   STATUS         mandatory
   DESCRIPTION    "The ibmSystem_Lease class contains leasing information about the computer system."
   REFERENCE      "IBMPSG_Lease"
::= { ibmSystemAssetID 4 }

ibmSystemLeaseEntry OBJECT-TYPE
   SYNTAX         IbmSystemLeaseEntry
   ACCESS         not-accessible
   STATUS         mandatory
   DESCRIPTION    ""
   INDEX          { ibmSystemLeaseKeyIndex }
::= { ibmSystemLeaseTable 1 }

IbmSystemLeaseEntry ::= SEQUENCE
{
   ibmSystemLeaseKeyIndex String,   
   ibmSystemLeaseName String,
   ibmSystemLeaseLessor String,
   ibmSystemLeaseBuyout Uint32,
   ibmSystemLeaseLRF Uint8,
   ibmSystemLeaseLeaseStartDate Datetime,
   ibmSystemLeaseLeaseEndDate Datetime,
   ibmSystemLeaseFMV Uint32,
   ibmSystemLeaseLeaseTerm Uint8,
   ibmSystemLeaseLeasePayment String
}

ibmSystemLeaseKeyIndex OBJECT-TYPE
   SYNTAX         String
   ACCESS         read-write
   STATUS         mandatory
   DESCRIPTION    ""
   REFERENCE      "IBMPSG_Lease.KeyIndex"
::= { ibmSystemLeaseEntry 1 }

ibmSystemLeaseName OBJECT-TYPE
   SYNTAX         String
   ACCESS         read-write
   STATUS         mandatory
   DESCRIPTION    "The name of this lease."
   REFERENCE      "IBMPSG_Lease.Name"
::= { ibmSystemLeaseEntry 2 }

ibmSystemLeaseLessor OBJECT-TYPE
   SYNTAX         String
   ACCESS         read-write
   STATUS         mandatory
   DESCRIPTION    "The name of the owner of the leased property."
   REFERENCE      "IBMPSG_Lease.Lessor"
::= { ibmSystemLeaseEntry 3 }

ibmSystemLeaseBuyout OBJECT-TYPE
   SYNTAX         Uint32
   ACCESS         read-write
   STATUS         mandatory
   DESCRIPTION    "Amount of money required to purchase the leased property at the end of the lease term."
   REFERENCE      "IBMPSG_Lease.Buyout"
::= { ibmSystemLeaseEntry 4 }

ibmSystemLeaseLRF OBJECT-TYPE
   SYNTAX         Uint8
   ACCESS         read-write
   STATUS         mandatory
   DESCRIPTION    "Lease Rate Factor.  This is a percentage that when multiplied by the cost gives the periodic lease payment amount."
   REFERENCE      "IBMPSG_Lease.LRF"
::= { ibmSystemLeaseEntry 5 }

ibmSystemLeaseLeaseStartDate OBJECT-TYPE
   SYNTAX         Datetime
   ACCESS         read-write
   STATUS         mandatory
   DESCRIPTION    "Start date of the lease agreement."
   REFERENCE      "IBMPSG_Lease.LeaseStartDate"
::= { ibmSystemLeaseEntry 6 }

ibmSystemLeaseLeaseEndDate OBJECT-TYPE
   SYNTAX         Datetime
   ACCESS         read-write
   STATUS         mandatory
   DESCRIPTION    "Lease end date."
   REFERENCE      "IBMPSG_Lease.LeaseEndDate"
::= { ibmSystemLeaseEntry 7 }

ibmSystemLeaseFMV OBJECT-TYPE
   SYNTAX         Uint32
   ACCESS         read-write
   STATUS         mandatory
   DESCRIPTION    "Residual value / Fair Market Value (FMV) of system.  The price a willing buyer will pay a willing seller for leased property on an as is, where is basis with both under no compulsion to either buy or sell."
   REFERENCE      "IBMPSG_Lease.FMV"
::= { ibmSystemLeaseEntry 8 }

ibmSystemLeaseLeaseTerm OBJECT-TYPE
   SYNTAX         Uint8
   ACCESS         read-write
   STATUS         mandatory
   DESCRIPTION    "Length of the lease agreement in months."
   REFERENCE      "IBMPSG_Lease.LeaseTerm"
::= { ibmSystemLeaseEntry 9 }

ibmSystemLeaseLeasePayment OBJECT-TYPE
   SYNTAX         String
   ACCESS         read-write
   STATUS         mandatory
   DESCRIPTION    "Lease payment (rent)."
   REFERENCE      "IBMPSG_Lease.LeasePayment"
::= { ibmSystemLeaseEntry 10 }

ibmSystemWarrantyTable OBJECT-TYPE
   SYNTAX         SEQUENCE OF IbmSystemWarrantyEntry
   ACCESS         not-accessible
   STATUS         mandatory
   DESCRIPTION    "The ibmSystem_Warranty class contains warranty information about the Computer System."
   REFERENCE      "IBMPSG_Warranty"
::= { ibmSystemAssetID 5 }

ibmSystemWarrantyEntry OBJECT-TYPE
   SYNTAX         IbmSystemWarrantyEntry
   ACCESS         not-accessible
   STATUS         mandatory
   DESCRIPTION    ""
   INDEX          { ibmSystemWarrantyKeyIndex }
::= { ibmSystemWarrantyTable 1 }

IbmSystemWarrantyEntry ::= SEQUENCE
{
   ibmSystemWarrantyKeyIndex String,   
   ibmSystemWarrantyName String,
   ibmSystemWarrantyWarrantyDuration Uint8,
   ibmSystemWarrantyWarrantyDurationUnit Uint8,
   ibmSystemWarrantyWarrantyEndDate Datetime,
   ibmSystemWarrantyWarrantyCost String
}

ibmSystemWarrantyKeyIndex OBJECT-TYPE
   SYNTAX         String
   ACCESS         read-write
   STATUS         mandatory
   DESCRIPTION    ""
   REFERENCE      "IBMPSG_Warranty.KeyIndex"
::= { ibmSystemWarrantyEntry 1 }

ibmSystemWarrantyName OBJECT-TYPE
   SYNTAX         String
   ACCESS         read-write
   STATUS         mandatory
   DESCRIPTION    "The name of this warranty."
   REFERENCE      "IBMPSG_Warranty.Name"
::= { ibmSystemWarrantyEntry 2 }

ibmSystemWarrantyWarrantyDuration OBJECT-TYPE
   SYNTAX         Uint8
   ACCESS         read-write
   STATUS         mandatory
   DESCRIPTION    "Time period of warranty (start date to end date)."
   REFERENCE      "IBMPSG_Warranty.WarrantyDuration"
::= { ibmSystemWarrantyEntry 3 }

ibmSystemWarrantyWarrantyDurationUnit OBJECT-TYPE
   SYNTAX         Uint8
   ACCESS         read-write
   STATUS         mandatory
   DESCRIPTION    "The time unit for the warranty duration."
   REFERENCE      "IBMPSG_Warranty.WarrantyDurationUnit"
::= { ibmSystemWarrantyEntry 4 }

ibmSystemWarrantyWarrantyEndDate OBJECT-TYPE
   SYNTAX         Datetime
   ACCESS         read-write
   STATUS         mandatory
   DESCRIPTION    "Date on which the warranty expires."
   REFERENCE      "IBMPSG_Warranty.WarrantyEndDate"
::= { ibmSystemWarrantyEntry 5 }

ibmSystemWarrantyWarrantyCost OBJECT-TYPE
   SYNTAX         String
   ACCESS         read-write
   STATUS         mandatory
   DESCRIPTION    "Cost of the extended warranty"
   REFERENCE      "IBMPSG_Warranty.WarrantyCost"
::= { ibmSystemWarrantyEntry 6 }



ibmSystemFRUTable OBJECT-TYPE
   SYNTAX         SEQUENCE OF IbmSystemFRUEntry
   ACCESS         not-accessible
   STATUS         mandatory
   DESCRIPTION    "The IBMPSG_FRU class contains FRU information about the Computer System."
   REFERENCE      "IBMPSG_FRU"
::= { ibmSystemAssetID 6 }

ibmSystemFRUEntry OBJECT-TYPE
   SYNTAX         IbmSystemFRUEntry
   ACCESS         not-accessible
   STATUS         mandatory
   DESCRIPTION    ""
   INDEX          { ibmSystemFRUKeyIndex }
::= { ibmSystemFRUTable 1 }

IbmSystemFRUEntry ::= SEQUENCE
{
   ibmSystemFRUKeyIndex String,   
   ibmSystemFRUName String,
   ibmSystemFRUFRUNumber String,
   ibmSystemFRUIdentifyingNumber String,
   ibmSystemFRUVendor String,
   ibmSystemFRURevisionLevel String,
   ibmSystemFRUDescription String
}

ibmSystemFRUKeyIndex OBJECT-TYPE
   SYNTAX         String
   ACCESS         read-write
   STATUS         mandatory
   DESCRIPTION    ""
   REFERENCE      "IBMPSG_FRU.KeyIndex"
::= { ibmSystemFRUEntry 1 }

ibmSystemFRUName OBJECT-TYPE
   SYNTAX         String
   ACCESS         read-write
   STATUS         mandatory
   DESCRIPTION    "FRU name."
   REFERENCE      "IBMPSG_FRU.Name"
::= { ibmSystemFRUEntry 2 }

ibmSystemFRUFRUNumber OBJECT-TYPE
   SYNTAX         String
   ACCESS         read-write
   STATUS         mandatory
   DESCRIPTION    "FRU ordering information."
   REFERENCE      "IBMPSG_FRU.FRUNumber"
::= { ibmSystemFRUEntry 3 }

ibmSystemFRUIdentifyingNumber OBJECT-TYPE
   SYNTAX         String
   ACCESS         read-write
   STATUS         mandatory
   DESCRIPTION    "FRU identification such as a serial number on software or a die number on a hardware chip."
   REFERENCE      "IBMPSG_FRU.IdentifyingNumber"
::= { ibmSystemFRUEntry 4 }

ibmSystemFRUVendor OBJECT-TYPE
   SYNTAX         String
   ACCESS         read-write
   STATUS         mandatory
   DESCRIPTION    "The name of the FRU's supplier."
   REFERENCE      "IBMPSG_FRU.Vendor"
::= { ibmSystemFRUEntry 5 }

ibmSystemFRURevisionLevel OBJECT-TYPE
   SYNTAX         String
   ACCESS         read-write
   STATUS         mandatory
   DESCRIPTION    "The FRU's revision level."
   REFERENCE      "IBMPSG_FRU.RevisionLevel"
::= { ibmSystemFRUEntry 6 }

ibmSystemFRUDescription OBJECT-TYPE
   SYNTAX         String
   ACCESS         read-write
   STATUS         mandatory
   DESCRIPTION    "A textual description of the FRU."
   REFERENCE      "IBMPSG_FRU.Description"
::= { ibmSystemFRUEntry 7 }

END
