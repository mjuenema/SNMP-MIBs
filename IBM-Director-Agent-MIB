IBM-Director-Agent-MIB DEFINITIONS ::= BEGIN

IMPORTS
   MODULE-IDENTITY, OBJECT-TYPE, Integer32,
   Unsigned32                                 FROM SNMPv2-SMI
   TEXTUAL-CONVENTION, DisplayString          FROM SNMPv2-TC
   MODULE-COMPLIANCE, OBJECT-GROUP            FROM SNMPv2-CONF
   ibm                                        FROM IBM-REC-MIB;


directorAgentMIB MODULE-IDENTITY
   LAST-UPDATED "200307090000Z"
   ORGANIZATION "IBM Corp."
   CONTACT-INFO
      "IBM Corporation"
   DESCRIPTION
      "This module defines objects for the IBM Director Agent portion
       of the MIB tree."
   ::= { dmiMibs 2 }


ibmProd     OBJECT IDENTIFIER ::= { ibm 6 }

director    OBJECT IDENTIFIER ::= { ibmProd 159 }

dmiMibs     OBJECT IDENTIFIER ::= { director 200 }

dmtfGroups  OBJECT IDENTIFIER ::= { directorAgentMIB 1 }


DmiDate ::= TEXTUAL-CONVENTION
   STATUS      current
   DESCRIPTION
     "Represents a DMI date format."
   SYNTAX      OCTET STRING (SIZE (28))


componentidTable OBJECT-TYPE
   SYNTAX      SEQUENCE OF SComponentid
   MAX-ACCESS  not-accessible
   STATUS      current
   DESCRIPTION
      "This group defines attributes common to all components.  This
       group is required."
   ::= {dmtfGroups 1}

componentidEntry OBJECT-TYPE
   SYNTAX      SComponentid
   MAX-ACCESS  not-accessible
   STATUS      current
   DESCRIPTION
      "INDEX INTEGER value is DmiComponentIndex"
   INDEX       { a1Index }
   ::= {componentidTable 1}

SComponentid ::= SEQUENCE {
   a1Index                                         Unsigned32,
   a1Manufacturer                                  DisplayString,
   a1Product                                       DisplayString,
   a1Version                                       DisplayString,
   a1SerialNumber                                  DisplayString
}

a1Index OBJECT-TYPE
   SYNTAX      Unsigned32
   MAX-ACCESS  read-only
   STATUS      current
   DESCRIPTION
      "The index for this table."
   ::= {componentidEntry 5}

a1Manufacturer OBJECT-TYPE
   SYNTAX      DisplayString
   MAX-ACCESS  read-only
   STATUS      current
   DESCRIPTION
      "The name of the manufacturer that produces this component."
   ::= {componentidEntry 1}

a1Product OBJECT-TYPE
   SYNTAX      DisplayString
   MAX-ACCESS  read-only
   STATUS      current
   DESCRIPTION
      "The name of the component."
   ::= {componentidEntry 2}

a1Version OBJECT-TYPE
   SYNTAX      DisplayString
   MAX-ACCESS  read-only
   STATUS      current
   DESCRIPTION
      "The version for the component."
   ::= {componentidEntry 3}

a1SerialNumber OBJECT-TYPE
   SYNTAX      DisplayString
   MAX-ACCESS  read-only
   STATUS      current
   DESCRIPTION
      "The serial number for this instance of this component."
   ::= {componentidEntry 4}

directorAlertTable OBJECT-TYPE
   SYNTAX      SEQUENCE OF SDirectorAlert
   MAX-ACCESS  not-accessible
   STATUS      current
   DESCRIPTION
      "Director Alert data fields."
   ::= {dmtfGroups 2}

directorAlertEntry OBJECT-TYPE
   SYNTAX      SDirectorAlert
   MAX-ACCESS  not-accessible
   STATUS      current
   DESCRIPTION
      "INDEX INTEGER value is DmiComponentIndex"
   INDEX      { a2Index }
   ::= {directorAlertTable 1}

SDirectorAlert ::= SEQUENCE {
   a2Index                                         Unsigned32,
   a2AlertText                                     DisplayString,
   a2Severity                                      Integer32,
   a2AlertType                                     DisplayString,
   a2ApplicationId                                 DisplayString,
   a2ApplicationAlertType                          Integer32,
   a2AlertTimeAndDate                              DmiDate,
   a2AlertSender                                   DisplayString,
   a2AlertSystemName                               DisplayString
}

a2Index OBJECT-TYPE
   SYNTAX      Unsigned32
   MAX-ACCESS  read-only
   STATUS      current
   DESCRIPTION
      "The index for this table."
   ::= {directorAlertEntry 9}

a2AlertText OBJECT-TYPE
   SYNTAX      DisplayString
   MAX-ACCESS  read-only
   STATUS      current
   DESCRIPTION
      "Text associated with the Director Alert."
   ::= {directorAlertEntry 1}

a2Severity OBJECT-TYPE
   SYNTAX      Integer32
   MAX-ACCESS  read-only
   STATUS      current
   DESCRIPTION
      "Alert severity level (0 = highest, 7 = lowest)."
   ::= {directorAlertEntry 2}

a2AlertType OBJECT-TYPE
   SYNTAX      DisplayString
   MAX-ACCESS  read-only
   STATUS      current
   DESCRIPTION
      "Standard alert ID and type."
   ::= {directorAlertEntry 3}

a2ApplicationId OBJECT-TYPE
   SYNTAX      DisplayString
   MAX-ACCESS  read-only
   STATUS      current
   DESCRIPTION
      "Identity of the application which issued the alert."
   ::= {directorAlertEntry 4}

a2ApplicationAlertType OBJECT-TYPE
   SYNTAX      Integer32
   MAX-ACCESS  read-only
   STATUS      current
   DESCRIPTION
      "Application-specific alert ID."
   ::= {directorAlertEntry 5}

a2AlertTimeAndDate OBJECT-TYPE
   SYNTAX      DmiDate
   MAX-ACCESS  read-only
   STATUS      current
   DESCRIPTION
      "Time and date when alert was issued."
   ::= {directorAlertEntry 6}

a2AlertSender OBJECT-TYPE
   SYNTAX      DisplayString
   MAX-ACCESS  read-only
   STATUS      current
   DESCRIPTION
      "Network path to system which created alert, if not local system."
   ::= {directorAlertEntry 7}

a2AlertSystemName OBJECT-TYPE
   SYNTAX      DisplayString
   MAX-ACCESS  read-only
   STATUS      current
   DESCRIPTION
      "System name of system which created alert."
   ::= {directorAlertEntry 8}

directorMonitorAttributesTable OBJECT-TYPE
   SYNTAX      SEQUENCE OF SDirectorMonitorAttributes
   MAX-ACCESS  not-accessible
   STATUS      current
   DESCRIPTION
      "Current values of Director Monitor Attributes."
   ::= {dmtfGroups 3}

directorMonitorAttributesEntry OBJECT-TYPE
   SYNTAX      SDirectorMonitorAttributes
   MAX-ACCESS  not-accessible
   STATUS      current
   DESCRIPTION
      "INDEX INTEGER value is DmiComponentIndex"
   INDEX       {a3AttributeId}
   ::= {directorMonitorAttributesTable 1}

SDirectorMonitorAttributes ::= SEQUENCE {
   a3AttributeId                                   Unsigned32,
   a3AttributeName                                 DisplayString,
   a3CurrentValueInteger                           Integer32,
   a3CurrentValueThousandths                       Integer32,
   a3CurrentValueString                            DisplayString,
   a3ValueUnits                                    DisplayString,
   a3RecordingEnabled                              Integer32
}

a3AttributeId OBJECT-TYPE
   SYNTAX      Unsigned32
   MAX-ACCESS  read-only
   STATUS      current
   DESCRIPTION
      "Unique ID for monitored attribute."
   ::= {directorMonitorAttributesEntry 1}

a3AttributeName OBJECT-TYPE
   SYNTAX      DisplayString
   MAX-ACCESS  read-only
   STATUS      current
   DESCRIPTION
      "Textual name of the monitored attribute."
   ::= {directorMonitorAttributesEntry 2}

a3CurrentValueInteger OBJECT-TYPE
   SYNTAX      Integer32
   MAX-ACCESS  read-only
   STATUS      current
   DESCRIPTION
      "Integral portion of current value of attribute."
   ::= {directorMonitorAttributesEntry 3}

a3CurrentValueThousandths OBJECT-TYPE
   SYNTAX      Integer32
   MAX-ACCESS  read-only
   STATUS      current
   DESCRIPTION
      "Fraction portion of current value of attribute, in units of 1/1000th"
   ::= {directorMonitorAttributesEntry 4}

a3CurrentValueString OBJECT-TYPE
   SYNTAX      DisplayString
   MAX-ACCESS  read-only
   STATUS      current
   DESCRIPTION
      "Current value of attribute, as display string."
   ::= {directorMonitorAttributesEntry 5}

a3ValueUnits OBJECT-TYPE
   SYNTAX      DisplayString
   MAX-ACCESS  read-only
   STATUS      current
   DESCRIPTION
      "Textual label for value units."
   ::= {directorMonitorAttributesEntry 6}

a3RecordingEnabled OBJECT-TYPE
   SYNTAX      INTEGER {
                  false(0),
                  true(1)
               }
   MAX-ACCESS  read-only
   STATUS      current
   DESCRIPTION
      "Flag indicates if data recording is active."
   ::= {directorMonitorAttributesEntry 7}

directorAttributeGroupsTable OBJECT-TYPE
   SYNTAX      SEQUENCE OF SDirectorAttributeGroups
   MAX-ACCESS  not-accessible
   STATUS      current
   DESCRIPTION
      "Current values of Director Attribute Groups."
   ::= {dmtfGroups 4}

directorAttributeGroupsEntry OBJECT-TYPE
   SYNTAX      SDirectorAttributeGroups
   MAX-ACCESS  not-accessible
   STATUS      current
   DESCRIPTION
      "INDEX INTEGER value is DmiComponentIndex"
   INDEX      {a4AttributeGroupId, a4AttributeId}
   ::= {directorAttributeGroupsTable 1}

SDirectorAttributeGroups ::= SEQUENCE {
   a4AttributeGroupId                              Unsigned32,
   a4AttributeId                                   Unsigned32,
   a4AttributeGroupName                            DisplayString,
   a4AttributeName                                 DisplayString,
   a4CurrentValueTextual                           DisplayString,
   a4CurrentValueIndex                             Integer32
}

a4AttributeGroupId OBJECT-TYPE
   SYNTAX      Unsigned32
   MAX-ACCESS  read-only
   STATUS      current
   DESCRIPTION
      "Unique ID for attribute group."
   ::= {directorAttributeGroupsEntry 1}

a4AttributeId OBJECT-TYPE
   SYNTAX      Unsigned32
   MAX-ACCESS  read-only
   STATUS      current
   DESCRIPTION
      "Unique ID for attribute within attribute group."
   ::= {directorAttributeGroupsEntry 2}

a4AttributeGroupName OBJECT-TYPE
   SYNTAX      DisplayString
   MAX-ACCESS  read-only
   STATUS      current
   DESCRIPTION
      "Textual name of the attribute group."
   ::= {directorAttributeGroupsEntry 3}

a4AttributeName OBJECT-TYPE
   SYNTAX      DisplayString
   MAX-ACCESS  read-only
   STATUS      current
   DESCRIPTION
      "Textual name of the attribute within the attribute group."
   ::= {directorAttributeGroupsEntry 4}

a4CurrentValueTextual OBJECT-TYPE
   SYNTAX      DisplayString
   MAX-ACCESS  read-only
   STATUS      current
   DESCRIPTION
      "Current value of attribute, as text."
   ::= {directorAttributeGroupsEntry 5}

a4CurrentValueIndex OBJECT-TYPE
   SYNTAX      Integer32
   MAX-ACCESS  read-only
   STATUS      current
   DESCRIPTION
      "Index of current value of attribute. Index = -1 if attribute's value is not indexed."
   ::= {directorAttributeGroupsEntry 6}

directorAgentMIBConformance OBJECT IDENTIFIER ::= { directorAgentMIB 2 }

directorAgentMIBGroups      OBJECT IDENTIFIER ::= { directorAgentMIBConformance 1 }
directorAgentMIBCompliances OBJECT IDENTIFIER ::= { directorAgentMIBConformance 2 }

directorAgentMIBCompliance MODULE-COMPLIANCE
   STATUS  current
   DESCRIPTION
      "The compliance statement for this module."
   MODULE  -- this module
   MANDATORY-GROUPS { directorAgentMIBGroup }
   ::= { directorAgentMIBCompliances 1 }

directorAgentMIBGroup OBJECT-GROUP
   OBJECTS { a1Index, a1Manufacturer, a1Product, a1Version,
             a1SerialNumber, a2Index, a2AlertText, a2Severity,
             a2AlertType, a2ApplicationId, a2ApplicationAlertType, a2AlertTimeAndDate,
             a2AlertSender, a2AlertSystemName,
             a3AttributeId, a3AttributeName, a3CurrentValueInteger, a3CurrentValueThousandths,
             a3CurrentValueString, a3ValueUnits, a3RecordingEnabled,
             a4AttributeGroupId, a4AttributeId, a4AttributeGroupName,
             a4AttributeName, a4CurrentValueTextual, a4CurrentValueIndex }
   STATUS  current
   DESCRIPTION
      "The objects group for objects defined in this module."
   ::= { directorAgentMIBGroups 1 }

END
