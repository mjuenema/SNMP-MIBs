CBS-HARDWARE-MIB DEFINITIONS ::= BEGIN

IMPORTS
   MODULE-IDENTITY, OBJECT-TYPE, NOTIFICATION-TYPE,
   Integer32, Unsigned32, Gauge32           FROM SNMPv2-SMI
 
   TEXTUAL-CONVENTION,
   DisplayString, TruthValue                FROM SNMPv2-TC

   ProductID, KBytes                        FROM HOST-RESOURCES-MIB

   cbsMIBs, cbsMgmt, cbsTraps               FROM CROSSBEAM-SYSTEMS-MIB;


cbsHardwareMIB MODULE-IDENTITY
   LAST-UPDATED "200703230000Z"     -- 23 Mar 2007
   ORGANIZATION "Crossbeam Systems, Inc."
   CONTACT-INFO "Email:  mib-admin@crossbeamsys.com
                 Postal: 80 Central Street
                         Boxborough MA 01719"
   DESCRIPTION  "This MIB module defines the objects to identify
                 and monitor Crossbeam Systems hardware."

   REVISION     "200203150000Z"     -- 15 March 2002
   DESCRIPTION  "Initial Revision"

   REVISION     "200208210000Z"     -- 21 August 2002
   DESCRIPTION  "Added bootwait state to hardware module status."

   REVISION     "200305080000Z"     -- 8 May 2003
   DESCRIPTION  "Added separate objects for AC & DC power supply/feed."

   REVISION     "200307220000Z"     -- 22 July 2003
   DESCRIPTION  "Added Trap definitions for DBHA link up/down."

   REVISION     "200312150000Z"     -- 15 Dec 2003
   DESCRIPTION  "Added Trap definitions for CPU2's temp."

   REVISION     "200402200000Z"     -- 20 Feb 2004
   DESCRIPTION  "Added offline and maintenance module states."

   REVISION     "200402240000Z"     -- 24 Feb 2004
   DESCRIPTION  "Added Trap definitions for AFT usage high/normal."

   REVISION     "200407060000Z"     -- 6 July 2004
   DESCRIPTION  "Defined Textual Convention for ModuleState."

   REVISION     "200606160000Z"     -- 16 June 2006
   DESCRIPTION  "Added Trap definitions for individual AC power supply bays."

   REVISION     "200611200000Z"     -- 20 Nov 2006
   DESCRIPTION  "Added Trap definition for NPM diag failure."
   
   REVISION     "200703230000Z"     -- 23 Mar 2007
   DESCRIPTION  "Added Trap definition for NPM PRC link 13/14."   
::= { cbsMIBs 2 }


OperationalState ::= TEXTUAL-CONVENTION
    STATUS current
    DESCRIPTION
        "The operational state of a hardware subsystem."
    SYNTAX INTEGER {
              up(1),
              down(2),
              not-present(3)
           }


ExistentialState ::= TEXTUAL-CONVENTION
    STATUS current
    DESCRIPTION
        "Indicates the component exists."
    SYNTAX INTEGER {
              present(1),
              not-present(2)
           }
   
ModuleState ::= TEXTUAL-CONVENTION
    STATUS current
    DESCRIPTION
        "The operational state of a hardware module.
            unavailable  - No status is currently available for this
                           module.
            down         - The module is currently down.
            initializing - The module is loading.
            up           - The module is in an operational state.
            standby      - The module is operating in standby mode.
            bootwait     - The module is waiting for resources to become
                           available so it can load software.
            offline      - The module is operating in standby mode,
                           applicable for CPs only.
            maintenance  - The module is operating in maintenance mode."

    SYNTAX INTEGER {
                unavailable(1),
                down(2),
                initializing(3),
                up(4),
                standby(5),
                bootwait(6),
                offline(7),
                maintenance(8)
           }


cbsHardware       OBJECT IDENTIFIER ::= { cbsMgmt 1 }
cbsHwTraps        OBJECT IDENTIFIER ::= { cbsTraps 1 }

cbsHwSystem       OBJECT IDENTIFIER ::= { cbsHardware 1 }
cbsHwSystemStatus OBJECT IDENTIFIER ::= { cbsHardware 2 }



-- System Information

cbsHwSystemProductID OBJECT-TYPE
   SYNTAX     ProductID
   MAX-ACCESS read-only
   STATUS     current
   DESCRIPTION
      "The identifier for this system"
   ::= { cbsHwSystem 1 }

cbsHwSystemDescription OBJECT-TYPE
   SYNTAX     DisplayString
   MAX-ACCESS read-only
   STATUS     current
   DESCRIPTION
      "A textual description of the product."
   ::= { cbsHwSystem 2 }

cbsHwSystemSerialNumber OBJECT-TYPE
   SYNTAX     DisplayString
   MAX-ACCESS read-only
   STATUS     current
   DESCRIPTION
      "The serial number of the system."
   ::= { cbsHwSystem 3 }

cbsHwSystemBackplaneRevision OBJECT-TYPE
   SYNTAX     DisplayString
   MAX-ACCESS read-only
   STATUS     current
   DESCRIPTION
      "The Revision of the system backplane."
   ::= { cbsHwSystem 4 }



--  Hardware system status

cbsHwSystemRedundantPowerSupplyStatus OBJECT-TYPE
   SYNTAX     OperationalState
   MAX-ACCESS read-only
   STATUS     obsolete
   DESCRIPTION
      "Indicates that the redundant power supply is operational.
      
       This object is obsoleted in favor of separate objects for AC
       and DC power supply."
   ::= { cbsHwSystemStatus 1 }

cbsHwSystemRedundantPowerFeedStatus OBJECT-TYPE
   SYNTAX     OperationalState
   MAX-ACCESS read-only
   STATUS     obsolete
   DESCRIPTION
      "Indicates that both of the redundant backplane power feeds
       are operational.
      
       This object is obsoleted in favor of separate objects for AC
       and DC power feed."
   ::= { cbsHwSystemStatus 2 }

cbsHwSystemChassisTemp OBJECT-TYPE
   SYNTAX     Integer32 (-25..50)
   MAX-ACCESS read-only
   STATUS     current
   DESCRIPTION
      "The temperature of the chassis air flow as measured at the
       upper fan tray."
   ::= { cbsHwSystemStatus 3 }

cbsHwSystemUpperFanTray OBJECT-TYPE
   SYNTAX     ExistentialState
   MAX-ACCESS read-only
   STATUS     current
   DESCRIPTION
      "The upper fan tray is present in the system."
   ::= { cbsHwSystemStatus 4 }

cbsHwSystemLowerFanTray OBJECT-TYPE
   SYNTAX     ExistentialState
   MAX-ACCESS read-only
   STATUS     current
   DESCRIPTION
      "The lower fan tray is present in the system."
   ::= { cbsHwSystemStatus 5 }

cbsHwSystemAlarm OBJECT-TYPE
   SYNTAX     INTEGER
                { none(1),
                  minor(2),
                  major(3),
                  critical(4) }
   MAX-ACCESS read-only
   STATUS     current
   DESCRIPTION
      "Indicates the highest current alarm state of the system."
   ::= { cbsHwSystemStatus 6 }

cbsHwSystemPowerType OBJECT-TYPE
   SYNTAX     INTEGER
                { ac1(1),
                  dc1(2),
		  ac2(3),
		  ac3(4),
		  dc2(5),
		  dc3(6),
                  unknown(7) }
   MAX-ACCESS read-only
   STATUS     current
   DESCRIPTION
      "Indicates the power type of the system."
   ::= { cbsHwSystemStatus 7 }

cbsHwSystemRedundantACPowerSupplyStatus OBJECT-TYPE
   SYNTAX     OperationalState
   MAX-ACCESS read-only
   STATUS     current
   DESCRIPTION
      "Indicates that the redundant AC power supply is operational.
       Will return down (i.e. not-operational) for DC chassis."
   ::= { cbsHwSystemStatus 8 }

cbsHwSystemRedundantACPowerFeedStatus OBJECT-TYPE
   SYNTAX     OperationalState
   MAX-ACCESS read-only
   STATUS     current
   DESCRIPTION
      "Indicates that both of the redundant backplane AC power feeds
       are operational.
       Will return down (i.e. not-operational) for DC chassis."
   ::= { cbsHwSystemStatus 9 }

cbsHwSystemDCPowerFilterA OBJECT-TYPE
   SYNTAX     ExistentialState
   MAX-ACCESS read-only
   STATUS     current
   DESCRIPTION
      "Indicates if DC power filter A is present or not present.
       Will return not present for AC chassis."
   ::= { cbsHwSystemStatus 10 }

cbsHwSystemDCPowerFilterB OBJECT-TYPE
   SYNTAX     ExistentialState
   MAX-ACCESS read-only
   STATUS     current
   DESCRIPTION
      "Indicates if DC power filter B is present or not present.
       Will return not present for AC chassis."
   ::= { cbsHwSystemStatus 11 }

cbsHwSystemDCPowerFeedA OBJECT-TYPE
   SYNTAX     ExistentialState
   MAX-ACCESS read-only
   STATUS     current
   DESCRIPTION
      "Indicates if DC power feed A is present or not present.
       Will return not present for AC chassis."
   ::= { cbsHwSystemStatus 12 }

cbsHwSystemDCPowerFeedB OBJECT-TYPE
   SYNTAX     ExistentialState
   MAX-ACCESS read-only
   STATUS     current
   DESCRIPTION
      "Indicates if DC power feed B is present or not present.
       Will return not present for AC chassis."
   ::= { cbsHwSystemStatus 13 }

cbsHwSystemACPwrBay1Presence OBJECT-TYPE
   SYNTAX     ExistentialState
   MAX-ACCESS read-only
   STATUS     current
   DESCRIPTION
      "Indicates if the redundant AC power supply in Bay 1 is present.
       Will return not present for DC chassis."
   ::= { cbsHwSystemStatus 14 }

cbsHwSystemACPwrBay2Presence OBJECT-TYPE
   SYNTAX     ExistentialState
   MAX-ACCESS read-only
   STATUS     current
   DESCRIPTION
      "Indicates if the redundant AC power supply in Bay 2 is present.
       Will return not present for DC chassis."
   ::= { cbsHwSystemStatus 15 }

cbsHwSystemACPwrBay3Presence OBJECT-TYPE
   SYNTAX     ExistentialState
   MAX-ACCESS read-only
   STATUS     current
   DESCRIPTION
      "Indicates if the redundant AC power supply in Bay 3 is present.
       Will return not present for DC chassis."
   ::= { cbsHwSystemStatus 16 }

cbsHwSystemACPwrBay4Presence OBJECT-TYPE
   SYNTAX     ExistentialState
   MAX-ACCESS read-only
   STATUS     current
   DESCRIPTION
      "Indicates if the redundant AC power supply in Bay 4 is present.
       Will return not present for DC chassis."
   ::= { cbsHwSystemStatus 17 }

cbsHwSystemACPwrBay1Status OBJECT-TYPE
   SYNTAX     OperationalState
   MAX-ACCESS read-only
   STATUS     current
   DESCRIPTION
      "Indicates if the redundant AC power supply in Bay 1 is operational.
       Will return down (i.e. not-operational) for DC chassis."
   ::= { cbsHwSystemStatus 18 }

cbsHwSystemACPwrBay2Status OBJECT-TYPE
   SYNTAX     OperationalState
   MAX-ACCESS read-only
   STATUS     current
   DESCRIPTION
      "Indicates if the redundant AC power supply in Bay 2 is operational.
       Will return down (i.e. not-operational) for DC chassis."
   ::= { cbsHwSystemStatus 19 }

cbsHwSystemACPwrBay3Status OBJECT-TYPE
   SYNTAX     OperationalState
   MAX-ACCESS read-only
   STATUS     current
   DESCRIPTION
      "Indicates if the redundant AC power supply in Bay 3 is operational.
       Will return down (i.e. not-operational) for DC chassis."
   ::= { cbsHwSystemStatus 20 }

cbsHwSystemACPwrBay4Status OBJECT-TYPE
   SYNTAX     OperationalState
   MAX-ACCESS read-only
   STATUS     current
   DESCRIPTION
      "Indicates if the redundant AC power supply in Bay 4 is operational.
       Will return down (i.e. not-operational) for DC chassis."
   ::= { cbsHwSystemStatus 21 }


-- Fan status table

cbsFanStatusTable OBJECT-TYPE
   SYNTAX       SEQUENCE OF CbsFanStatusEntry
   MAX-ACCESS   not-accessible
   STATUS       current
   DESCRIPTION
      "This table contains information about the fan trays
       currently installed in the system."
   ::= { cbsHardware 3 }

cbsFanStatusEntry OBJECT-TYPE
   SYNTAX     CbsFanStatusEntry
   MAX-ACCESS not-accessible
   STATUS     current
   DESCRIPTION
      "An entry in the hardware module table."
   INDEX { cbsFanGroupIndex, cbsFanIndex }
   ::= { cbsFanStatusTable 1 }


CbsFanStatusEntry ::= SEQUENCE {
   cbsFanGroupIndex              INTEGER,
   cbsFanIndex                   INTEGER,
   cbsFanStatus                  OperationalState
}

cbsFanGroupIndex OBJECT-TYPE
   SYNTAX     INTEGER { lower(1),
                        upper(2) }
   MAX-ACCESS not-accessible
   STATUS     current
   DESCRIPTION
      "Index of the fan tray."
   ::= { cbsFanStatusEntry 1 }

cbsFanIndex OBJECT-TYPE
   SYNTAX     INTEGER (1..9)
   MAX-ACCESS not-accessible
   STATUS     current
   DESCRIPTION
      "The fan number in the fan tray."
   ::= { cbsFanStatusEntry 2 }

cbsFanStatus OBJECT-TYPE
   SYNTAX     OperationalState
   MAX-ACCESS read-only
   STATUS     current
   DESCRIPTION
      "Operational status of the fan."
   ::= { cbsFanStatusEntry 3 }


-- Table of processor modules

cbsHwModuleTable OBJECT-TYPE
   SYNTAX       SEQUENCE OF CbsHwModuleEntry
   MAX-ACCESS   not-accessible
   STATUS       current
   DESCRIPTION
      "This table contains information about the processor modules
       currently installed in the system."
   ::= { cbsHardware 4 }

cbsHwModuleEntry OBJECT-TYPE
   SYNTAX     CbsHwModuleEntry
   MAX-ACCESS not-accessible
   STATUS     current
   DESCRIPTION
      "An entry in the hardware module table."
   INDEX { cbsHwModuleID }
   ::= { cbsHwModuleTable 1 }

CbsHwModuleEntry ::= SEQUENCE {
   cbsHwModuleID                 Integer32,
   cbsHwModuleProductID          ProductID,
   cbsHwModuleDescription        DisplayString,
   cbsHwModuleBoardRevision      DisplayString,
   cbsHwModuleSerialNumber       DisplayString,
   cbsHwModuleBootStrapRev       DisplayString,
   cbsHwModuleBootloaderRev      DisplayString,
   cbsHwModuleDiagnosticsRev     DisplayString,
   cbsHwModuleSDRAMSize          KBytes,
   cbsHwModuleRDRAMSize          KBytes,
   cbsHwModuleDiskAPresent       TruthValue,
   cbsHwModuleDiskBPresent       TruthValue,
   cbsHwModuleDuartAPresent      TruthValue,
   cbsHwModuleDuartBPresent      TruthValue,
   cbsHwModuleAccelCard1Present  TruthValue,
   cbsHwModuleAccelCard2Present  TruthValue
}

cbsHwModuleID OBJECT-TYPE
   SYNTAX     Integer32 (1..14)
   MAX-ACCESS read-only
   STATUS     current
   DESCRIPTION
      "The product ID for the module."
   ::= { cbsHwModuleEntry 1 }

cbsHwModuleProductID OBJECT-TYPE
   SYNTAX     ProductID
   MAX-ACCESS read-only
   STATUS     current
   DESCRIPTION
      "The product ID for the module."
   ::= { cbsHwModuleEntry 2 }

cbsHwModuleDescription OBJECT-TYPE
   SYNTAX     DisplayString
   MAX-ACCESS read-only
   STATUS     current
   DESCRIPTION
      "A short description of the module."
   ::= { cbsHwModuleEntry 3 }

cbsHwModuleBoardRevision OBJECT-TYPE
   SYNTAX     DisplayString
   MAX-ACCESS read-only
   STATUS     current
   DESCRIPTION
      "The board revision level of the module."
   ::= { cbsHwModuleEntry 4 }

cbsHwModuleSerialNumber OBJECT-TYPE
   SYNTAX     DisplayString
   MAX-ACCESS read-only
   STATUS     current
   DESCRIPTION
      "The serial number of the module."
   ::= { cbsHwModuleEntry 5 }

cbsHwModuleBootStrapRev OBJECT-TYPE
   SYNTAX      DisplayString
   MAX-ACCESS  read-only
   STATUS      current
   DESCRIPTION
      "Revision of the boot strap software."
   ::= { cbsHwModuleEntry 6 }

cbsHwModuleBootloaderRev OBJECT-TYPE
   SYNTAX      DisplayString
   MAX-ACCESS  read-only
   STATUS      current
   DESCRIPTION
      "Revision of the boot loader software."
   ::= { cbsHwModuleEntry 7 }

cbsHwModuleDiagnosticsRev OBJECT-TYPE
   SYNTAX      DisplayString
   MAX-ACCESS  read-only
   STATUS      current
   DESCRIPTION 
      "Revision of the diagnostic software."     
   ::= { cbsHwModuleEntry 8 }

cbsHwModuleSDRAMSize OBJECT-TYPE
   SYNTAX      KBytes
   MAX-ACCESS  read-only
   STATUS      current
   DESCRIPTION
      "Total Static DRAM memory on the module in Kilobytes."
   ::= { cbsHwModuleEntry 9 }

cbsHwModuleRDRAMSize OBJECT-TYPE
   SYNTAX      KBytes
   MAX-ACCESS  read-only
   STATUS      current
   DESCRIPTION
      "Total RDRAM memory on the module in Kilobytes."
   ::= { cbsHwModuleEntry 10 }

cbsHwModuleDiskAPresent OBJECT-TYPE
   SYNTAX      TruthValue
   MAX-ACCESS  read-only
   STATUS      current
   DESCRIPTION
      "The first disk storage device is present."
   ::= { cbsHwModuleEntry 11 }

cbsHwModuleDiskBPresent OBJECT-TYPE
   SYNTAX      TruthValue
   MAX-ACCESS  read-only
   STATUS      current
   DESCRIPTION
      "The second disk storage device is present."
   ::= { cbsHwModuleEntry 12 }

cbsHwModuleDuartAPresent OBJECT-TYPE
   SYNTAX      TruthValue
   MAX-ACCESS  read-only
   STATUS      current
   DESCRIPTION
      "The first DUART device is present on the module."
   ::= { cbsHwModuleEntry 13 }

cbsHwModuleDuartBPresent OBJECT-TYPE
   SYNTAX      TruthValue
   MAX-ACCESS  read-only
   STATUS      current
   DESCRIPTION
      "The second DUART device is present on the module."
   ::= { cbsHwModuleEntry 14 }

cbsHwModuleAccelCard1Present OBJECT-TYPE
   SYNTAX      TruthValue
   MAX-ACCESS  read-only
   STATUS      current
   DESCRIPTION
      "The Accelerator Card 1 is present on the module."
   ::= { cbsHwModuleEntry 15 }

cbsHwModuleAccelCard2Present OBJECT-TYPE
   SYNTAX      TruthValue
   MAX-ACCESS  read-only
   STATUS      current
   DESCRIPTION
      "The Accelerator Card 2 is present on the module."
   ::= { cbsHwModuleEntry 16 }


cbsHwComponentRevTable OBJECT-TYPE
   SYNTAX       SEQUENCE OF CbsHwComponentRevEntry
   MAX-ACCESS   not-accessible
   STATUS       current
   DESCRIPTION
      "A table containing the revision level of programable
      hardware components."
   ::= { cbsHardware 5 }

cbsHwComponentRevEntry OBJECT-TYPE
   SYNTAX     CbsHwComponentRevEntry
   MAX-ACCESS not-accessible
   STATUS     current
   DESCRIPTION
      "An entry in the hardware component revision table."
   INDEX { cbsHwModuleID, cbsHwComponentIndex }
   ::= { cbsHwComponentRevTable 1 }


CbsHwComponentRevEntry ::= SEQUENCE {
   cbsHwComponentIndex            Unsigned32,
   cbsHwComponentDescription      DisplayString,
   cbsHwComponentRevision         OCTET STRING
}

cbsHwComponentIndex   OBJECT-TYPE
   SYNTAX     Unsigned32
   MAX-ACCESS not-accessible
   STATUS     current
   DESCRIPTION
      "Description of the programable component"
   ::= { cbsHwComponentRevEntry 1 }

cbsHwComponentDescription   OBJECT-TYPE
   SYNTAX     DisplayString
   MAX-ACCESS read-only
   STATUS     current
   DESCRIPTION
      "Description of the programable component"
   ::= { cbsHwComponentRevEntry 2 }

cbsHwComponentRevision OBJECT-TYPE
   SYNTAX     OCTET STRING
   MAX-ACCESS read-only
   STATUS     current
   DESCRIPTION
      "Revision level of the programable component"
   ::= { cbsHwComponentRevEntry 3 }


-- Table of processor module status info

cbsHwModuleStatusTable OBJECT-TYPE
   SYNTAX       SEQUENCE OF CbsHwModuleStatusEntry
   MAX-ACCESS   not-accessible
   STATUS       current
   DESCRIPTION
      "This table contains the status of processor modules
       currently installed in the system."
   ::= { cbsHardware 6 }

cbsHwModuleStatusEntry OBJECT-TYPE
   SYNTAX     CbsHwModuleStatusEntry
   MAX-ACCESS not-accessible
   STATUS     current
   DESCRIPTION
      "An entry in the hardware module status table."
   AUGMENTS { cbsHwModuleEntry }
   ::= { cbsHwModuleStatusTable 1 }

CbsHwModuleStatusEntry ::= SEQUENCE {
   cbsHwModuleStatus              ModuleState,
   cbsHwModuleCpuTemp             Integer32,
   cbsHwModuleFPGATemp            Integer32,
   cbsHwModuleInTemp              Integer32,
   cbsHwModuleInTempAlarm         TruthValue,
   cbsHwModuleExhaustTemp         Integer32,
   cbsHwModuleExhaustTempAlarm    TruthValue,
   cbsHwModuleCPUVoltage          Gauge32,
   cbsHwModule1-8Voltage          Gauge32,
   cbsHwModule3-3Voltage          Gauge32,
   cbsHwModule2-5Voltage          Gauge32,
   cbsHwModuleControlLinkA        OperationalState,
   cbsHwModuleControlLinkB        OperationalState,
   cbsHwModuleActiveLED           TruthValue,
   cbsHwModuleStandbyLED          TruthValue,
   cbsHwModuleFailedLED           TruthValue,
   cbsHwModuleCpu2Temp            Integer32,
   cbsHwModuleCPU2Voltage         Gauge32,
   cbsHwModuleFPGA1-8Voltage      Gauge32,
   cbsHwModule125Voltage          Gauge32
}


cbsHwModuleStatus   OBJECT-TYPE
   SYNTAX     ModuleState
   MAX-ACCESS read-only
   STATUS     current
   DESCRIPTION
      "The operational state of the module."
   ::= { cbsHwModuleStatusEntry 1 }

cbsHwModuleCpuTemp OBJECT-TYPE
   SYNTAX     Integer32 (-25..50)
   MAX-ACCESS read-only
   STATUS     current
   DESCRIPTION
      "The current CPU temperature in degrees centigrade."
   ::= { cbsHwModuleStatusEntry 2 }

cbsHwModuleFPGATemp OBJECT-TYPE
   SYNTAX     Integer32 (-25..75)
   MAX-ACCESS read-only
   STATUS     current
   DESCRIPTION
      "The current FPGA temperature in degrees centigrade.
       Not all modules support this variable. When module 
       does not support, a value of 0 will be reported."
   ::= { cbsHwModuleStatusEntry 3 }

cbsHwModuleInTemp OBJECT-TYPE
   SYNTAX     Integer32 (-25..75)
   MAX-ACCESS read-only
   STATUS     current
   DESCRIPTION
      "The current temperature at the sensor located at the bottom of
       the board in degrees centigrade."
   ::= { cbsHwModuleStatusEntry 4 }

cbsHwModuleInTempAlarm OBJECT-TYPE
   SYNTAX     TruthValue
   MAX-ACCESS read-only
   STATUS     current
   DESCRIPTION
      "Indicates a high temperature alarm for the bottom board sensor."
   ::= { cbsHwModuleStatusEntry 5 }

cbsHwModuleExhaustTemp OBJECT-TYPE
   SYNTAX     Integer32 (-25..75)
   MAX-ACCESS read-only
   STATUS     current
   DESCRIPTION
      "The current temperature at the sensor located at the top of
       the board in degrees centigrade."
   ::= { cbsHwModuleStatusEntry 6 }

cbsHwModuleExhaustTempAlarm OBJECT-TYPE
   SYNTAX     TruthValue
   MAX-ACCESS read-only
   STATUS     current
   DESCRIPTION
      "Indicates a high temperature alarm for the top board sensor."
   ::= { cbsHwModuleStatusEntry 7 }

cbsHwModuleCPUVoltage OBJECT-TYPE
   SYNTAX     Gauge32
   MAX-ACCESS read-only
   STATUS     current
   DESCRIPTION
     "The current voltage level of the processor supply. This
      number is in 1/100ths of a volt and the ideal value depends
      on the speed of the processor."
   ::= { cbsHwModuleStatusEntry 8 }

cbsHwModule1-8Voltage OBJECT-TYPE
   SYNTAX     Gauge32
   MAX-ACCESS read-only
   STATUS     current
   DESCRIPTION
      "The current voltage level of the 1.8 volt power supply. This
       number is in 1/100ths of a volt and the ideal value of
       1.8 volts will be read as 180."
   ::= { cbsHwModuleStatusEntry 9 }

cbsHwModule3-3Voltage OBJECT-TYPE
   SYNTAX     Gauge32
   MAX-ACCESS read-only
   STATUS     current
   DESCRIPTION
      "The current voltage level of the 3.3 volt power supply. This
       number is in 1/100ths of a volt and the ideal value of
       3.3 volts will be read as 330."
   ::= { cbsHwModuleStatusEntry 10 }

cbsHwModule2-5Voltage OBJECT-TYPE
   SYNTAX     Gauge32
   MAX-ACCESS read-only
   STATUS     current
   DESCRIPTION
      "The current voltage level of the 2.5 volt power supply. This
       number is in 1/100ths of a volt and the ideal value of
       2.5 volts will be read as 250."
   ::= { cbsHwModuleStatusEntry 11 }

cbsHwModuleControlLinkA OBJECT-TYPE
   SYNTAX     OperationalState
   MAX-ACCESS read-only
   STATUS     current
   DESCRIPTION
      "The operation state of control link A."
   ::= { cbsHwModuleStatusEntry 12 }

cbsHwModuleControlLinkB OBJECT-TYPE
   SYNTAX     OperationalState
   MAX-ACCESS read-only
   STATUS     current
   DESCRIPTION
      "The Operational state of control link B."
   ::= { cbsHwModuleStatusEntry 13 }


cbsHwModuleActiveLED OBJECT-TYPE
   SYNTAX     TruthValue
   MAX-ACCESS read-only
   STATUS     current
   DESCRIPTION
      "Indicates the board's active LED is on."
   ::= { cbsHwModuleStatusEntry 14 }

cbsHwModuleStandbyLED  OBJECT-TYPE
   SYNTAX     TruthValue
   MAX-ACCESS read-only
   STATUS     current
   DESCRIPTION
      "Indicates the board's standby LED is on."
   ::= { cbsHwModuleStatusEntry 15 }

cbsHwModuleFailedLED  OBJECT-TYPE
   SYNTAX     TruthValue
   MAX-ACCESS read-only
   STATUS     current
   DESCRIPTION
      "Indicates the board's failed LED is on."
   ::= { cbsHwModuleStatusEntry 16 }

cbsHwModuleCpu2Temp OBJECT-TYPE
   SYNTAX     Integer32 (-25..50)
   MAX-ACCESS read-only
   STATUS     current
   DESCRIPTION
      "For dual processor modules, 2nd CPU's current temperature in 
       degrees centigrade. For modules that don't support it,
       a special invalid value of 10000 will be returned."
   ::= { cbsHwModuleStatusEntry 17 }

cbsHwModuleCPU2Voltage OBJECT-TYPE
   SYNTAX     Gauge32
   MAX-ACCESS read-only
   STATUS     current
   DESCRIPTION
      "For dual processor modules, 2nd CPU's current voltage level.
       This number is in 1/100ths of a volt and the ideal value 
       depends on the speed of the processor. For modules that don't 
       support it, a special invalid value of 10000 will be returned."
   ::= { cbsHwModuleStatusEntry 18 }

cbsHwModuleFPGA1-8Voltage OBJECT-TYPE
   SYNTAX     Gauge32
   MAX-ACCESS read-only
   STATUS     current
   DESCRIPTION
      "FPGA's current voltage level of the 1.8 volt power supply. This
       number is in 1/100ths of a volt and the ideal value of
       1.8 volts will be read as 180. For modules that don't support it,
       a special invalid value of 10000 will be returned."
   ::= { cbsHwModuleStatusEntry 19 }

cbsHwModule125Voltage OBJECT-TYPE
   SYNTAX     Gauge32
   MAX-ACCESS read-only
   STATUS     current
   DESCRIPTION
      "Current voltage level of the 1.25 volt power supply. This
       number is in 1/100ths of a volt and the ideal value of
       1.25 volts will be read as 125. For modules that don't support it,
       a special invalid value of 10000 will be returned."
   ::= { cbsHwModuleStatusEntry 20 }


cbsHwSdpStatusTable OBJECT-TYPE
   SYNTAX       SEQUENCE OF CbsHwSdpStatusEntry
   MAX-ACCESS   not-accessible
   STATUS       current
   DESCRIPTION
      "Table containing status of the Switched Data Path backplane links."
   ::= { cbsHardware 7 }

cbsHwSdpStatusEntry OBJECT-TYPE
   SYNTAX     CbsHwSdpStatusEntry
   MAX-ACCESS not-accessible
   STATUS     current
   DESCRIPTION
      "An entry in the hardware SDP status table."
   INDEX { cbsHwSdpNpmSlot, cbsHwSdpRemoteSlot }
   ::= { cbsHwSdpStatusTable 1 }

CbsHwSdpStatusEntry ::= SEQUENCE {
   cbsHwSdpNpmSlot             Unsigned32,
   cbsHwSdpRemoteSlot          Unsigned32,
   cbsHwSdpNpmState            OperationalState,
   cbsHwSdpRemoteState         OperationalState
}


cbsHwSdpNpmSlot OBJECT-TYPE
   SYNTAX     Unsigned32 (1..2)
   MAX-ACCESS not-accessible
   STATUS     current
   DESCRIPTION
      "The slot number of the Network Processor Module end of the link"
   ::= { cbsHwSdpStatusEntry 1 }

cbsHwSdpRemoteSlot OBJECT-TYPE
   SYNTAX     Unsigned32 (1..14)
   MAX-ACCESS not-accessible
   STATUS     current
   DESCRIPTION
      "The slot number of the remote end of the link"
   ::= { cbsHwSdpStatusEntry 2 }

cbsHwSdpNpmState OBJECT-TYPE
   SYNTAX     OperationalState  
   MAX-ACCESS read-only
   STATUS     current
   DESCRIPTION
      "The operational state of the NPM side of the link."
   ::= { cbsHwSdpStatusEntry 3 }

cbsHwSdpRemoteState OBJECT-TYPE
   SYNTAX     OperationalState
   MAX-ACCESS read-only
   STATUS     current
   DESCRIPTION
      "The operational state of the remote end of the link."
   ::= { cbsHwSdpStatusEntry 4 }


--  The traps

cbsHwPowerSupplyFailed NOTIFICATION-TYPE
   STATUS  current
   DESCRIPTION
     "One of the redundant power supplies or DC filters has 
      failed or been removed."
   ::= { cbsHwTraps 1 }

cbsHwPowerSupplyRecovered NOTIFICATION-TYPE
   STATUS  current
   DESCRIPTION
     "A redundant power supply or DC filter that was previously 
      failed or missing has been replaced."
   ::= { cbsHwTraps 2 }

cbsHwPowerFeedFailed NOTIFICATION-TYPE
   STATUS  current
   DESCRIPTION
     "One of the redundant backplane power feed has failed."
   ::= { cbsHwTraps 3 }

cbsHwPowerFeedRecovered NOTIFICATION-TYPE
   STATUS  current
   DESCRIPTION
     "One of the redundant backplane power feed that previously not
      working has become operational."
   ::= { cbsHwTraps 4 }

cbsHwUpperFanTrayInserted NOTIFICATION-TYPE
   STATUS  current
   DESCRIPTION
     "A fan tray has been inserted into the system."
   ::= { cbsHwTraps 5 }

cbsHwUpperFanTrayRemoved NOTIFICATION-TYPE
   STATUS current
   DESCRIPTION
     "A fan tray has been removed from the system."
   ::= { cbsHwTraps 6 }

cbsHwLowerFanTrayInserted NOTIFICATION-TYPE
   STATUS  current
   DESCRIPTION
     "A fan tray has been inserted into the system."
   ::= { cbsHwTraps 7 }

cbsHwLowerFanTrayRemoved NOTIFICATION-TYPE
   STATUS current
   DESCRIPTION
     "A fan tray has been removed from the system."
   ::= { cbsHwTraps 8 }

cbsHwFanFailed NOTIFICATION-TYPE
   OBJECTS { cbsFanStatus }
   STATUS current
   DESCRIPTION
     "One of the system cooling fans has failed."
   ::= { cbsHwTraps 9 }

cbsHwFanRecovered NOTIFICATION-TYPE
   OBJECTS { cbsFanStatus }
   STATUS current
   DESCRIPTION
     "A Fan that was inoperative has recovered."
   ::= { cbsHwTraps 10 }

cbsHwSystemAlarmTrap NOTIFICATION-TYPE
   OBJECTS { cbsHwSystemAlarm }
   STATUS  current
   DESCRIPTION
      "Indicates that the alarm state of the system has changed."
   ::= { cbsHwTraps 11 }


cbsHwChassisTempExceeded NOTIFICATION-TYPE
   OBJECTS { cbsHwSystemChassisTemp }
   STATUS  current
   DESCRIPTION
     "Indicates the the chassis temperature, as measure at the exhaust fan
      has exceeded the maximum."
   ::= { cbsHwTraps 12 }

cbsHwChassisTempNormal NOTIFICATION-TYPE
   OBJECTS { cbsHwSystemChassisTemp }
   STATUS  current
   DESCRIPTION
     "Indicates the the chassis temperature, as measure at the exhaust fan
      has returned to normal."
   ::= { cbsHwTraps 13 }

cbsHwModuleStatusChanged NOTIFICATION-TYPE
   OBJECTS { cbsHwModuleStatus }
   STATUS  current
   DESCRIPTION
     "The status of a processor module has changed, the new status of
      the module that has changed is reported."
   ::= { cbsHwTraps 14 }

cbsHwModuleInserted NOTIFICATION-TYPE
   OBJECTS { cbsHwModuleID }
   STATUS  current
   DESCRIPTION
     "A processor module been inserted into the system, reports the slot
      number of the module that has been inserted."
   ::= { cbsHwTraps 15 }

cbsHwModuleRemoved NOTIFICATION-TYPE
   OBJECTS { cbsHwModuleID }
   STATUS  current
   DESCRIPTION
     "A processor module been removed into the system, reports the slot
      number of the module that has been removed."
   ::= { cbsHwTraps 16 }

cbsModuleTempExceeded NOTIFICATION-TYPE
   OBJECTS { cbsHwModuleCpuTemp }
   STATUS  current
   DESCRIPTION
     "Indicates that the module CPU temperature has execeeded the high limit."
   ::= { cbsHwTraps 17 }

cbsModuleTempNormal NOTIFICATION-TYPE
   OBJECTS { cbsHwModuleCpuTemp }
   STATUS  current
   DESCRIPTION
     "Indicates that the module CPU temperature has returned to the normal 
      operating range."
   ::= { cbsHwTraps 18 }

cbsDbhaLinkUp NOTIFICATION-TYPE
   OBJECTS { cbsHwModuleID }
   STATUS  current
   DESCRIPTION
     "The DBHA link on this CPM has come up."
   ::= { cbsHwTraps 19 }

cbsDbhaLinkDown NOTIFICATION-TYPE
   OBJECTS { cbsHwModuleID }
   STATUS  current
   DESCRIPTION
     "The DBHA link on this CPM has failed."
   ::= { cbsHwTraps 20 }

cbsModuleCpu2TempExceeded NOTIFICATION-TYPE
   OBJECTS { cbsHwModuleCpu2Temp }
   STATUS  current
   DESCRIPTION
     "Temperature has execeeded the high limit for module's 2nd CPU."
   ::= { cbsHwTraps 21 }

cbsModuleCpu2TempNormal NOTIFICATION-TYPE
   OBJECTS { cbsHwModuleCpu2Temp }
   STATUS  current
   DESCRIPTION
     "Temperature has returned to the normal operating range for module's 2nd CPU."
   ::= { cbsHwTraps 22 }

cbsAFTUsageHigh NOTIFICATION-TYPE
   OBJECTS { cbsHwModuleID }
   STATUS  current
   DESCRIPTION
     "The Active Flow Table's usage on this NPM module is excessive."
   ::= { cbsHwTraps 23 }

cbsAFTUsageNormal NOTIFICATION-TYPE
   OBJECTS { cbsHwModuleID }
   STATUS  current
   DESCRIPTION
     "The Active Flow Table's usage on this NPM, that was previously 
      excessive, has returned to normal level."
   ::= { cbsHwTraps 24 }

cbsHwSystemACPwrBay1Failed NOTIFICATION-TYPE
   STATUS  current
   DESCRIPTION
     "The redundant AC power supply in Bay 1 has failed or been removed."
   ::= { cbsHwTraps 25 }

cbsHwSystemACPwrBay1Recovered NOTIFICATION-TYPE
   STATUS  current
   DESCRIPTION
     "The redundant AC power supply in Bay 1 that was previously 
      failed or missing has been replaced."
   ::= { cbsHwTraps 26 }

cbsHwSystemACPwrBay2Failed NOTIFICATION-TYPE
   STATUS  current
   DESCRIPTION
     "The redundant AC power supply in Bay 2 has failed or been removed."
   ::= { cbsHwTraps 27 }

cbsHwSystemACPwrBay2Recovered NOTIFICATION-TYPE
   STATUS  current
   DESCRIPTION
     "The redundant AC power supply in Bay 2 that was previously 
      failed or missing has been replaced."
   ::= { cbsHwTraps 28 }

cbsHwSystemACPwrBay3Failed NOTIFICATION-TYPE
   STATUS  current
   DESCRIPTION
     "The redundant AC power supply in Bay 3 has failed or been removed."
   ::= { cbsHwTraps 29 }

cbsHwSystemACPwrBay3Recovered NOTIFICATION-TYPE
   STATUS  current
   DESCRIPTION
     "The redundant AC power supply in Bay 3 that was previously 
      failed or missing has been replaced."
   ::= { cbsHwTraps 30 }

cbsHwSystemACPwrBay4Failed NOTIFICATION-TYPE
   STATUS  current
   DESCRIPTION
     "The redundant AC power supply in Bay 4 has failed or been removed."
   ::= { cbsHwTraps 31 }

cbsHwSystemACPwrBay4Recovered NOTIFICATION-TYPE
   STATUS  current
   DESCRIPTION
     "The redundant AC power supply in Bay 4 that was previously 
      failed or missing has been replaced."
   ::= { cbsHwTraps 32 }

cbsNPMDiagFailure NOTIFICATION-TYPE
   OBJECTS { cbsHwModuleID }
   STATUS  current
   DESCRIPTION
     "The NPM failed Diags."
   ::= { cbsHwTraps 33 }
   
cbsNPMPrcLink13Down NOTIFICATION-TYPE
   OBJECTS { cbsHwModuleID }
   STATUS  current
   DESCRIPTION
     "The PRC link 13 on this NPM is down."
   ::= { cbsHwTraps 34 }

cbsNPMPrcLink13Up NOTIFICATION-TYPE
   OBJECTS { cbsHwModuleID }
   STATUS  current
   DESCRIPTION
     "The PRC link 13 on this NPM is up."
   ::= { cbsHwTraps 35 }

cbsNPMPrcLink14Down NOTIFICATION-TYPE
   OBJECTS { cbsHwModuleID }
   STATUS  current
   DESCRIPTION
     "The PRC link 14 on this NPM is down."
   ::= { cbsHwTraps 36 }

cbsNPMPrcLink14Up NOTIFICATION-TYPE
   OBJECTS { cbsHwModuleID }
   STATUS  current
   DESCRIPTION
     "The PRC link 14 on this NPM is up."
   ::= { cbsHwTraps 37 }
   
      
 -- Added for 8.1  Bug ....??? (FredM will fill in)  
   cbsHwInTempExceeded NOTIFICATION-TYPE
   OBJECTS { cbsHwModuleInTemp }
   STATUS  current
   DESCRIPTION
     "Indicates the the chassis temperature, as measure at the exhaust fan
      has exceeded the maximum."
   ::= { cbsHwTraps 38 }

   cbsHwInTempNormal NOTIFICATION-TYPE
   OBJECTS { cbsHwModuleInTemp }
   STATUS  current
   DESCRIPTION
     "Indicates the the chassis temperature, as measure at the exhaust fan
      is within the normal range."
   ::= { cbsHwTraps 39 }



   cbsHwExhaustTempExceeded NOTIFICATION-TYPE
   OBJECTS { cbsHwModuleExhaustTemp }
   STATUS  current
   DESCRIPTION
     "Indicates the the chassis temperature, as measure at the exhaust fan
      has exceeded the maximum."
   ::= { cbsHwTraps 40 }

   cbsHwExhaustTempNormal NOTIFICATION-TYPE
   OBJECTS { cbsHwModuleExhaustTemp }
   STATUS  current
   DESCRIPTION
     "Indicates the the chassis temperature, as measure at the exhaust fan
      is within the normal range."
   ::= { cbsHwTraps 41 }



   cbsHwFPGATempExceeded NOTIFICATION-TYPE
   OBJECTS { cbsHwModuleFPGATemp }
   STATUS  current
   DESCRIPTION
     "Indicates the the chassis temperature, as measure at the exhaust fan
      has exceeded the maximum."
   ::= { cbsHwTraps 42 }

   cbsHwFPGATempNormal NOTIFICATION-TYPE
   OBJECTS { cbsHwModuleFPGATemp }
   STATUS  current
   DESCRIPTION
     "Indicates the the chassis temperature, as measure at the exhaust fan
      is within the normal range."
   ::= { cbsHwTraps 43 }

   
END
