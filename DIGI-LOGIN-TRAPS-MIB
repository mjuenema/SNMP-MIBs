-- =====================================================================
-- == DIGI-LOGIN-TRAPS-MIB :                                          ==
-- ==  DIGI Login Traps Management Information Base                   ==
-- ==                                                                 ==
-- ==   Digi International Part Number: 40002339_C                    ==
-- ==                                                                 ==
-- == (c) Copyright 2001-2003 Digi International, Inc.                ==
-- =====================================================================

DIGI-LOGIN-TRAPS-MIB DEFINITIONS ::= BEGIN

IMPORTS digiLoginTraps FROM DIGI-SMI
TRAP-TYPE FROM RFC-1215
OBJECT-TYPE FROM RFC-1212;

--   digiLoginTraps MODULE-IDENTITY
--       LAST-UPDATED "0308120100Z"
--       ORGANIZATION "Digi International Inc."
--       CONTACT-INFO
--               "
--                Postal: Digi International Inc.
--                        11001 Bren Road East
--                        Minnetonka, MN 55343
--
--               "
--       DESCRIPTION
--               "Login Traps MIB"
--       ::= { digiFeatures 14 }

-- === + Textual Conventions + ===========================================

DisplayString ::= OCTET STRING

-- =======================================================================
-- =======================================================================
-- === + Variables + =====================================================
-- =======================================================================
-- =======================================================================

loginName OBJECT-TYPE
    SYNTAX DisplayString
    ACCESS read-write
    STATUS mandatory
    DESCRIPTION
	    "The name that identifies a user"
::= { digiLoginTraps 11 }

portIndex OBJECT-TYPE
    SYNTAX INTEGER
    ACCESS read-write
    STATUS mandatory
    DESCRIPTION
	    "Index of port which event occured on"
::= { digiLoginTraps 12 }

portDescription OBJECT-TYPE
    SYNTAX DisplayString
    ACCESS read-write
    STATUS mandatory
    DESCRIPTION
        "Description of port which event occured on"
::= { digiLoginTraps 13 }

-- =======================================================================
-- =======================================================================
-- === + Traps + =========================================================
-- =======================================================================
-- =======================================================================

loginSuccess TRAP-TYPE
    ENTERPRISE  digiLoginTraps
    VARIABLES { loginName }
    DESCRIPTION
		  "A loginSuccess trap signifies that a
		  user was successfully authenticated on the
		  Digi device."
::= 1

loginFailure TRAP-TYPE
    ENTERPRISE  digiLoginTraps
    VARIABLES { loginName }
    DESCRIPTION
		  "A loginFailure trap signifies that the
		  user was unsuccessful at a login attempt on
		  the Digi device."
::= 2

loginConnection TRAP-TYPE
    ENTERPRISE  digiLoginTraps
    VARIABLES { loginName, portIndex, portDescription }
    DESCRIPTION
        "A loginConnection trap signifies that a
        connection was attempted to the port indexed 
        by portIndex on the Digi device."
::= 3

END
