--MibName=caiUxsA2
--	------------------------------------------------------------------------
--
--	This material contains, and is a part of a computer software program
--	which is, proprietary and confidential information owned by:
--	               COMPUTER ASSOCIATES INTERNATIONAL, INC.
--	The program, including this material, may not be duplicated, disclosed
--	or reproduced in whole or in part for any purpose without the express
--	written authorisation of COMPUTER ASSOCIATES.  All authorised
--	reproductions must be marked with this legend.
--
--	        Copyright 2006 Computer Associates International, Inc.
--	                 The Software that Manages eBusiness
--
--	------------------------------------------------------------------------

--
--	------------------------------------------------------------------------
--	$Header: $
--	------------------------------------------------------------------------
--
--	Description
--		Definition file for caiUxsA2 MIB.
--
--	Development History
--
--		File generated by cagenagt
--
--	========================================================================
--
--	NOTE: This file was generated - Please do not edit!
--
--	This is the caiUxsA2 MIB for the Unicenter UNIX System Agent.
--
--	caiUxsA2 contains four major groups:
--
--	uxsA2ConfigGroup specifies the agent configuration
--	uxsA2StatusGroup contains status information on the monitored entities
--	uxsA2AvailableGroup specifies available entities for monitoring
--	uxsA2HistoryGroup records status trap history
--
--	caiUxsA2 monitors the following resources:
--
--	  OS Resource Parameters
--	  CPU
--	  Load Averages
--	  Real Memory
--	  Swaps
--	  Quotas
--	  Directories
--	  File Systems
--	  Files
--	  Disks
--	  Processes
--	  Print Queues
--	  Network Interfaces
--	  Shared Memory
--	  Semaphores
--	  Message Queues
--
--	caiUxsA2 provides a means to also monitor arbitrary UNIX System
--	resources through the concept of Programmable Watchers.
--
--	caiUxsA2 provides the following tables of available UNIX System
--	resources:
--
--	  Quotas
--	  File Systems
--	  Disks
--	  Processes
--	  Print Queues
--	  Shared Memory
--	  Semaphores
--	  Message Queues
--
--	caiUxsA2 records status traps in a history table.
--
--	========================================================================

CAIUXSA2-MIB DEFINITIONS ::= BEGIN

IMPORTS
	enterprises,
	IpAddress,
	Counter,
	Gauge         FROM RFC1155-SMI

	PhysAddress,
	DisplayString FROM RFC1213-MIB

	OBJECT-TYPE   FROM RFC-1212

	TRAP-TYPE     FROM RFC-1215;

-- FROM RFC1514-MIB
KBytes ::= INTEGER (0..2147483647)

cai       OBJECT IDENTIFIER ::= { enterprises 791 }
caiSysMgr OBJECT IDENTIFIER ::= { cai 2 }
tng       OBJECT IDENTIFIER ::= { caiSysMgr 10 }
agents    OBJECT IDENTIFIER ::= { tng 2 }

caiUxsA2 OBJECT IDENTIFIER ::= { agents 74 }

--
-- The Config Group
--

uxsA2ConfigGroup OBJECT IDENTIFIER ::= { caiUxsA2 1 }

uxsA2ConfigGeneralGroup OBJECT IDENTIFIER ::= { uxsA2ConfigGroup 1 }
uxsA2ConfigSysGroup OBJECT IDENTIFIER ::= { uxsA2ConfigGroup 2 }
uxsA2ConfigResParamGroup OBJECT IDENTIFIER ::= { uxsA2ConfigGroup 3 }
uxsA2ConfigCPUGroup OBJECT IDENTIFIER ::= { uxsA2ConfigGroup 4 }
uxsA2ConfigLoadGroup OBJECT IDENTIFIER ::= { uxsA2ConfigGroup 5 }
uxsA2ConfigMemGroup OBJECT IDENTIFIER ::= { uxsA2ConfigGroup 6 }
uxsA2ConfigSwapGroup OBJECT IDENTIFIER ::= { uxsA2ConfigGroup 7 }
uxsA2ConfigQuotaGroup OBJECT IDENTIFIER ::= { uxsA2ConfigGroup 8 }
uxsA2ConfigDirGroup OBJECT IDENTIFIER ::= { uxsA2ConfigGroup 9 }
uxsA2ConfigFSysGroup OBJECT IDENTIFIER ::= { uxsA2ConfigGroup 10 }
uxsA2ConfigFileGroup OBJECT IDENTIFIER ::= { uxsA2ConfigGroup 11 }
uxsA2ConfigDiskGroup OBJECT IDENTIFIER ::= { uxsA2ConfigGroup 12 }
uxsA2ConfigProcGroup OBJECT IDENTIFIER ::= { uxsA2ConfigGroup 13 }
uxsA2ConfigPrnGroup OBJECT IDENTIFIER ::= { uxsA2ConfigGroup 14 }
uxsA2ConfigNetGroup OBJECT IDENTIFIER ::= { uxsA2ConfigGroup 15 }
uxsA2ConfigSHMGroup OBJECT IDENTIFIER ::= { uxsA2ConfigGroup 16 }
uxsA2ConfigSEMGroup OBJECT IDENTIFIER ::= { uxsA2ConfigGroup 17 }
uxsA2ConfigMQGroup OBJECT IDENTIFIER ::= { uxsA2ConfigGroup 18 }
uxsA2ConfigHardwrGroup OBJECT IDENTIFIER ::= { uxsA2ConfigGroup 19 }
uxsA2ConfigProgrmGroup OBJECT IDENTIFIER ::= { uxsA2ConfigGroup 20 }

--
-- The Status Group
--

uxsA2StatusGroup OBJECT IDENTIFIER ::= { caiUxsA2 2 }

uxsA2StatusGeneralGroup OBJECT IDENTIFIER ::= { uxsA2StatusGroup 1 }
uxsA2StatusResParamGroup OBJECT IDENTIFIER ::= { uxsA2StatusGroup 3 }
uxsA2StatusCPUGroup OBJECT IDENTIFIER ::= { uxsA2StatusGroup 4 }
uxsA2StatusLoadGroup OBJECT IDENTIFIER ::= { uxsA2StatusGroup 5 }
uxsA2StatusMemGroup OBJECT IDENTIFIER ::= { uxsA2StatusGroup 6 }
uxsA2StatusSwapGroup OBJECT IDENTIFIER ::= { uxsA2StatusGroup 7 }
uxsA2StatusQuotaGroup OBJECT IDENTIFIER ::= { uxsA2StatusGroup 8 }
uxsA2StatusDirGroup OBJECT IDENTIFIER ::= { uxsA2StatusGroup 9 }
uxsA2StatusFSysGroup OBJECT IDENTIFIER ::= { uxsA2StatusGroup 10 }
uxsA2StatusFileGroup OBJECT IDENTIFIER ::= { uxsA2StatusGroup 11 }
uxsA2StatusDiskGroup OBJECT IDENTIFIER ::= { uxsA2StatusGroup 12 }
uxsA2StatusProcGroup OBJECT IDENTIFIER ::= { uxsA2StatusGroup 13 }
uxsA2StatusPrnGroup OBJECT IDENTIFIER ::= { uxsA2StatusGroup 14 }
uxsA2StatusNetGroup OBJECT IDENTIFIER ::= { uxsA2StatusGroup 15 }
uxsA2StatusSHMGroup OBJECT IDENTIFIER ::= { uxsA2StatusGroup 16 }
uxsA2StatusSEMGroup OBJECT IDENTIFIER ::= { uxsA2StatusGroup 17 }
uxsA2StatusMQGroup OBJECT IDENTIFIER ::= { uxsA2StatusGroup 18 }
uxsA2StatusHardwrGroup OBJECT IDENTIFIER ::= { uxsA2StatusGroup 19 }
uxsA2StatusProgrmGroup OBJECT IDENTIFIER ::= { uxsA2StatusGroup 20 }

--
-- The Available Group
--

uxsA2AvailableGroup OBJECT IDENTIFIER ::= { caiUxsA2 3 }

uxsA2AvailQuotaGroup OBJECT IDENTIFIER ::= { uxsA2AvailableGroup 8 }
uxsA2AvailFSysGroup OBJECT IDENTIFIER ::= { uxsA2AvailableGroup 10 }
uxsA2AvailDiskGroup OBJECT IDENTIFIER ::= { uxsA2AvailableGroup 12 }
uxsA2AvailProcGroup OBJECT IDENTIFIER ::= { uxsA2AvailableGroup 13 }
uxsA2AvailPrnGroup OBJECT IDENTIFIER ::= { uxsA2AvailableGroup 14 }
uxsA2AvailSHMGroup OBJECT IDENTIFIER ::= { uxsA2AvailableGroup 16 }
uxsA2AvailSEMGroup OBJECT IDENTIFIER ::= { uxsA2AvailableGroup 17 }
uxsA2AvailMQGroup OBJECT IDENTIFIER ::= { uxsA2AvailableGroup 18 }
uxsA2AvailHardwrGroup OBJECT IDENTIFIER ::= { uxsA2AvailableGroup 19 }
uxsA2AvailProgrmGroup OBJECT IDENTIFIER ::= { uxsA2AvailableGroup 20 }

--
-- The History Group
--

uxsA2HistoryGroup OBJECT IDENTIFIER ::= { caiUxsA2 4 }

--
-- The ConfigGeneral Group
--

uxsA2ConfigGeneralAgentVersion OBJECT-TYPE
	SYNTAX DisplayString
	ACCESS read-only
	STATUS mandatory
	DESCRIPTION "&<caiUxsA2.101>Currently installed version of the agent."
	::= { uxsA2ConfigGeneralGroup 1 }

uxsA2ConfigGeneralColdStartTime OBJECT-TYPE
	SYNTAX DisplayString
	ACCESS read-only
	STATUS mandatory
	DESCRIPTION "&<caiUxsA2.102>Date and time that the agent was last started."
	::= { uxsA2ConfigGeneralGroup 2 }

uxsA2ConfigGeneralWarmStartTime OBJECT-TYPE
	SYNTAX DisplayString
	ACCESS read-only
	STATUS mandatory
	DESCRIPTION "&<caiUxsA2.103>Date and time that the agent's configuration was last changed."
	::= { uxsA2ConfigGeneralGroup 3 }

uxsA2ConfigGeneralResParamPollTime OBJECT-TYPE
	SYNTAX DisplayString
	ACCESS read-only
	STATUS mandatory
	DESCRIPTION "&<caiUxsA2.104>Date and time that the agent last collected OS resource parameter information."
	::= { uxsA2ConfigGeneralGroup 4 }

uxsA2ConfigGeneralCPUPollTime OBJECT-TYPE
	SYNTAX DisplayString
	ACCESS read-only
	STATUS mandatory
	DESCRIPTION "&<caiUxsA2.105>Date and time that the agent last collected CPU information."
	::= { uxsA2ConfigGeneralGroup 5 }

uxsA2ConfigGeneralLoadPollTime OBJECT-TYPE
	SYNTAX DisplayString
	ACCESS read-only
	STATUS mandatory
	DESCRIPTION "&<caiUxsA2.106>Date and time that the agent last collected load average information."
	::= { uxsA2ConfigGeneralGroup 6 }

uxsA2ConfigGeneralMemPollTime OBJECT-TYPE
	SYNTAX DisplayString
	ACCESS read-only
	STATUS mandatory
	DESCRIPTION "&<caiUxsA2.107>Date and time that the agent last collected real memory information."
	::= { uxsA2ConfigGeneralGroup 7 }

uxsA2ConfigGeneralSwapPollTime OBJECT-TYPE
	SYNTAX DisplayString
	ACCESS read-only
	STATUS mandatory
	DESCRIPTION "&<caiUxsA2.108>Date and time that the agent last collected swap information."
	::= { uxsA2ConfigGeneralGroup 8 }

uxsA2ConfigGeneralQuotaPollTime OBJECT-TYPE
	SYNTAX DisplayString
	ACCESS read-only
	STATUS mandatory
	DESCRIPTION "&<caiUxsA2.109>Date and time that the agent last collected quota information."
	::= { uxsA2ConfigGeneralGroup 9 }

uxsA2ConfigGeneralDirPollTime OBJECT-TYPE
	SYNTAX DisplayString
	ACCESS read-only
	STATUS mandatory
	DESCRIPTION "&<caiUxsA2.110>Date and time that the agent last collected directory information."
	::= { uxsA2ConfigGeneralGroup 10 }

uxsA2ConfigGeneralFSysPollTime OBJECT-TYPE
	SYNTAX DisplayString
	ACCESS read-only
	STATUS mandatory
	DESCRIPTION "&<caiUxsA2.111>Date and time that the agent last collected file system information."
	::= { uxsA2ConfigGeneralGroup 11 }

uxsA2ConfigGeneralFilePollTime OBJECT-TYPE
	SYNTAX DisplayString
	ACCESS read-only
	STATUS mandatory
	DESCRIPTION "&<caiUxsA2.112>Date and time that the agent last collected file information."
	::= { uxsA2ConfigGeneralGroup 12 }

uxsA2ConfigGeneralDiskPollTime OBJECT-TYPE
	SYNTAX DisplayString
	ACCESS read-only
	STATUS mandatory
	DESCRIPTION "&<caiUxsA2.113>Date and time that the agent last collected disk information."
	::= { uxsA2ConfigGeneralGroup 13 }

uxsA2ConfigGeneralProcPollTime OBJECT-TYPE
	SYNTAX DisplayString
	ACCESS read-only
	STATUS mandatory
	DESCRIPTION "&<caiUxsA2.114>Date and time that the agent last collected process information."
	::= { uxsA2ConfigGeneralGroup 14 }

uxsA2ConfigGeneralPrnPollTime OBJECT-TYPE
	SYNTAX DisplayString
	ACCESS read-only
	STATUS mandatory
	DESCRIPTION "&<caiUxsA2.115>Date and time that the agent last collected print queue information."
	::= { uxsA2ConfigGeneralGroup 15 }

uxsA2ConfigGeneralNetPollTime OBJECT-TYPE
	SYNTAX DisplayString
	ACCESS read-only
	STATUS mandatory
	DESCRIPTION "&<caiUxsA2.116>Date and time that the agent last collected network interface information."
	::= { uxsA2ConfigGeneralGroup 16 }

uxsA2ConfigGeneralSHMPollTime OBJECT-TYPE
	SYNTAX DisplayString
	ACCESS read-only
	STATUS mandatory
	DESCRIPTION "&<caiUxsA2.117>Date and time that the agent last collected shared memory information."
	::= { uxsA2ConfigGeneralGroup 17 }

uxsA2ConfigGeneralSEMPollTime OBJECT-TYPE
	SYNTAX DisplayString
	ACCESS read-only
	STATUS mandatory
	DESCRIPTION "&<caiUxsA2.118>Date and time that the agent last collected semaphore information."
	::= { uxsA2ConfigGeneralGroup 18 }

uxsA2ConfigGeneralMQPollTime OBJECT-TYPE
	SYNTAX DisplayString
	ACCESS read-only
	STATUS mandatory
	DESCRIPTION "&<caiUxsA2.119>Date and time that the agent last collected message queue information."
	::= { uxsA2ConfigGeneralGroup 19 }

uxsA2ConfigGeneralHardwrPollTime OBJECT-TYPE
	SYNTAX DisplayString
	ACCESS read-only
	STATUS mandatory
	DESCRIPTION "&<caiUxsA2.120>Date and time that the agent last collected hardware resource information."
	::= { uxsA2ConfigGeneralGroup 20 }

uxsA2ConfigGeneralProgrmPollTime OBJECT-TYPE
	SYNTAX DisplayString
	ACCESS read-only
	STATUS mandatory
	DESCRIPTION "&<caiUxsA2.121>Date and time that the agent last collected programmable resource information."
	::= { uxsA2ConfigGeneralGroup 21 }

--
-- The ConfigSys Group
--

uxsA2ConfigSysNodeName OBJECT-TYPE
	SYNTAX DisplayString
	ACCESS read-only
	STATUS mandatory
	DESCRIPTION "&<caiUxsA2.122>The name of the UNIX node (uname -n)."
	::= { uxsA2ConfigSysGroup 1 }

uxsA2ConfigSysOSName OBJECT-TYPE
	SYNTAX DisplayString
	ACCESS read-only
	STATUS mandatory
	DESCRIPTION "&<caiUxsA2.123>The name of the operating system (uname -s) installed on the machine."
	::= { uxsA2ConfigSysGroup 2 }

uxsA2ConfigSysOSRelease OBJECT-TYPE
	SYNTAX DisplayString
	ACCESS read-only
	STATUS mandatory
	DESCRIPTION "&<caiUxsA2.124>The release level of the operating system (uname -r) installed on the machine."
	::= { uxsA2ConfigSysGroup 3 }

uxsA2ConfigSysOSVersion OBJECT-TYPE
	SYNTAX DisplayString
	ACCESS read-only
	STATUS mandatory
	DESCRIPTION "&<caiUxsA2.125>The version of the operating system (uname -v) installed on the machine."
	::= { uxsA2ConfigSysGroup 4 }

uxsA2ConfigSysHardware OBJECT-TYPE
	SYNTAX DisplayString
	ACCESS read-only
	STATUS mandatory
	DESCRIPTION "&<caiUxsA2.126>Shows hardware information according to the uname -m command (uname -p for SunOS and AIX)."
	::= { uxsA2ConfigSysGroup 5 }

uxsA2ConfigSysProcessorWidth OBJECT-TYPE
	SYNTAX DisplayString
	ACCESS read-only
	STATUS mandatory
	DESCRIPTION "&<caiUxsA2.127>The processor width / kernel mode of the UNIX OS."
	::= { uxsA2ConfigSysGroup 6 }

uxsA2ConfigSysBootDate OBJECT-TYPE
	SYNTAX DisplayString
	ACCESS read-only
	STATUS mandatory
	DESCRIPTION "&<caiUxsA2.128>The date and time the machine was booted."
	::= { uxsA2ConfigSysGroup 7 }

uxsA2ConfigSysRunLevel OBJECT-TYPE
	SYNTAX DisplayString
	ACCESS read-only
	STATUS mandatory
	DESCRIPTION "&<caiUxsA2.129>The run level of the machine at the time the agent started."
	::= { uxsA2ConfigSysGroup 8 }

uxsA2ConfigSysClusterName OBJECT-TYPE
	SYNTAX DisplayString
	ACCESS read-only
	STATUS mandatory
	DESCRIPTION "&<caiUxsA2.130>The name of the cluster. For an unclustered host this is set to '-'."
	::= { uxsA2ConfigSysGroup 9 }

uxsA2ConfigSysOsParCount OBJECT-TYPE
	SYNTAX INTEGER
	ACCESS read-only
	STATUS mandatory
	DESCRIPTION "&<caiUxsA2.131>Number of entries in the operating system information configuration table."
	::= { uxsA2ConfigSysGroup 10 }

--uxsA2ConfigSysOsParTable OBJECT-TYPE
--	SYNTAX SEQUENCE OF UxsA2ConfigSysOsParEntry
--	ACCESS not-accessible
--	STATUS mandatory
--	DESCRIPTION "&<caiUxsA2.132>The operating system information configuration table containing details of the UNIX System configuration."
--	::= { uxsA2ConfigSysGroup 11 }

--uxsA2ConfigSysOsParEntry OBJECT-TYPE
--	SYNTAX UxsA2ConfigSysOsParEntry
--	ACCESS not-accessible
--	STATUS mandatory
--	DESCRIPTION "&<caiUxsA2.133>Entry in the operating system information configuration table."
--	::= { uxsA2ConfigSysOsParTable 1 }

--UxsA2ConfigSysOsParEntry ::= SEQUENCE {
--	uxsA2ConfigSysOsParName DisplayString,
--	uxsA2ConfigSysOsParValue DisplayString,
--	uxsA2ConfigSysOsParDescription DisplayString
--}

--uxsA2ConfigSysOsParName OBJECT-TYPE
--	SYNTAX DisplayString
--	ACCESS read-only
--	STATUS mandatory
--	DESCRIPTION "&<caiUxsA2.134>The name of the configuration parameter."
--	::= { uxsA2ConfigSysOsParEntry 1 }

--uxsA2ConfigSysOsParValue OBJECT-TYPE
--	SYNTAX DisplayString
--	ACCESS read-only
--	STATUS mandatory
--	DESCRIPTION "&<caiUxsA2.135>The current value of the configuration parameter."
--	::= { uxsA2ConfigSysOsParEntry 2 }

--uxsA2ConfigSysOsParDescription OBJECT-TYPE
--	SYNTAX DisplayString
--	ACCESS read-only
--	STATUS mandatory
--	DESCRIPTION "&<caiUxsA2.136>The description of the configuration parameter."
--	::= { uxsA2ConfigSysOsParEntry 3 }

--
-- The ConfigResParam Group
--

uxsA2ConfigResParamPollInterval OBJECT-TYPE
	SYNTAX INTEGER
	ACCESS read-write
	STATUS mandatory
	DESCRIPTION "&<caiUxsA2.137>Time, in seconds, between collections of OS resource parameter information. Valid range: 30 seconds or greater."
	DEFVAL { 120 }
	::= { uxsA2ConfigResParamGroup 1 }

uxsA2ConfigResParamPollMethod OBJECT-TYPE
	SYNTAX INTEGER {
		disabled(1),
		poll-interval-only(2)
	}
	ACCESS read-write
	STATUS mandatory
	DESCRIPTION "&<caiUxsA2.138>Specifies how and when the agent collects OS resource parameter information. If set to 1 (disabled), the agent does not retrieve the OS resource parameter information (neither by polling nor by get request) and sets all statuses to passive or ok. If set to 2 (poll-interval-only), the agent only retrieves the information by polling, but not by get request."
	DEFVAL { 2 }
	::= { uxsA2ConfigResParamGroup 2 }

uxsA2ConfigResParamUtilLag OBJECT-TYPE
	SYNTAX INTEGER
	ACCESS read-write
	STATUS mandatory
	DESCRIPTION "&<caiUxsA2.139>Default lag setting for the resource utilization monitoring of the OS resource parameter watcher to add. Specifies the number of consecutive threshold breaches on which the resource utilization state changes. This value must be greater than 0."
	DEFVAL { 3 }
	::= { uxsA2ConfigResParamGroup 3 }

uxsA2ConfigResParamUtilWarnMin OBJECT-TYPE
	SYNTAX DisplayString
	ACCESS read-write
	STATUS mandatory
	DESCRIPTION "&<caiUxsA2.140>Default warning minimum threshold for the resource utilization monitoring of the OS resource parameter watcher to add. This value represents a declining threshold and must be equal to or greater than 0.0, equal to or greater than the critical minimum threshold, but cannot be greater than the warning maximum threshold. A value of -1 disables the evaluation of this threshold. The threshold can be specified as either an absolute value (n) or a percentage (n%). The value of uxsA2StatusResParamUtilTotal will be the reference value for n% notations."
	DEFVAL { "-1" }
	::= { uxsA2ConfigResParamGroup 4 }

uxsA2ConfigResParamUtilWarnMax OBJECT-TYPE
	SYNTAX DisplayString
	ACCESS read-write
	STATUS mandatory
	DESCRIPTION "&<caiUxsA2.141>Default warning maximum threshold for the resource utilization monitoring of the OS resource parameter watcher to add. This value represents a rising threshold and must be equal to or greater than 0.0, equal to or greater than the warning minimum threshold, but cannot be greater than the critical maximum threshold. A value of -1 disables the evaluation of this threshold. The threshold can be specified as either an absolute value (n) or a percentage (n%). The value of uxsA2StatusResParamUtilTotal will be the reference value for n% notations."
	DEFVAL { "85.0%" }
	::= { uxsA2ConfigResParamGroup 5 }

uxsA2ConfigResParamUtilCritMin OBJECT-TYPE
	SYNTAX DisplayString
	ACCESS read-write
	STATUS mandatory
	DESCRIPTION "&<caiUxsA2.142>Default critical minimum threshold for the resource utilization monitoring of the OS resource parameter watcher to add. This value represents a declining threshold and must be equal to or greater than 0.0, but cannot be greater than the warning minimum threshold. A value of -1 disables the evaluation of this threshold. The threshold can be specified as either an absolute value (n) or a percentage (n%). The value of uxsA2StatusResParamUtilTotal will be the reference value for n% notations."
	DEFVAL { "-1" }
	::= { uxsA2ConfigResParamGroup 6 }

uxsA2ConfigResParamUtilCritMax OBJECT-TYPE
	SYNTAX DisplayString
	ACCESS read-write
	STATUS mandatory
	DESCRIPTION "&<caiUxsA2.143>Default critical maximum threshold for the resource utilization monitoring of the OS resource parameter watcher to add. This value represents a rising threshold and must be equal to or greater than 0.0, but cannot be less than the warning maximum threshold. A value of -1 disables the evaluation of this threshold. The threshold can be specified as either an absolute value (n) or a percentage (n%). The value of uxsA2StatusResParamUtilTotal will be the reference value for n% notations."
	DEFVAL { "95.0%" }
	::= { uxsA2ConfigResParamGroup 7 }

uxsA2ConfigResParamUtilMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.144>Default monitor level for the resource utilization monitoring of the OS resource parameter watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { uxsA2ConfigResParamGroup 8 }

--
-- The ConfigCPU Group
--

uxsA2ConfigCPUPollInterval OBJECT-TYPE
	SYNTAX INTEGER
	ACCESS read-write
	STATUS mandatory
	DESCRIPTION "&<caiUxsA2.145>Time, in seconds, between collections of CPU information. Valid range: 30 seconds or greater."
	DEFVAL { 60 }
	::= { uxsA2ConfigCPUGroup 1 }

uxsA2ConfigCPUPollMethod OBJECT-TYPE
	SYNTAX INTEGER {
		disabled(1),
		poll-interval-only(2),
		poll-interval-and-query(3),
		query-only(4)
	}
	ACCESS read-write
	STATUS mandatory
	DESCRIPTION "&<caiUxsA2.146>Specifies how and when the agent collects CPU information. If set to 1 (disabled), the agent does not retrieve the CPU information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigCPUGroup 2 }

uxsA2ConfigCPULoadLag OBJECT-TYPE
	SYNTAX INTEGER
	ACCESS read-write
	STATUS mandatory
	DESCRIPTION "&<caiUxsA2.147>Default lag setting for the CPU utilization monitoring of the CPU watcher to add. Specifies the number of consecutive threshold breaches on which the CPU utilization state changes. This value must be greater than 0."
	DEFVAL { 10 }
	::= { uxsA2ConfigCPUGroup 3 }

uxsA2ConfigCPULoadWarn OBJECT-TYPE
	SYNTAX INTEGER
	ACCESS read-write
	STATUS mandatory
	DESCRIPTION "&<caiUxsA2.148>Default warning threshold, in percent, for the CPU utilization monitoring of the CPU watcher to add. This value represents a rising threshold and must be greater than 0, less than or equal to 100, but cannot be greater than the critical threshold."
	DEFVAL { 70 }
	::= { uxsA2ConfigCPUGroup 4 }

uxsA2ConfigCPULoadCrit OBJECT-TYPE
	SYNTAX INTEGER
	ACCESS read-write
	STATUS mandatory
	DESCRIPTION "&<caiUxsA2.149>Default critical threshold, in percent, for the CPU utilization monitoring of the CPU watcher to add. This value represents a rising threshold and must be greater than 0, less than or equal to 100, but cannot be less than the warning threshold."
	DEFVAL { 90 }
	::= { uxsA2ConfigCPUGroup 5 }

uxsA2ConfigCPULoadMonitor OBJECT-TYPE
	SYNTAX INTEGER {
		do-not-monitor(1),
		warning-only(2),
		critical-only(3),
		both(4)
	}
	ACCESS read-write
	STATUS mandatory
	DESCRIPTION "&<caiUxsA2.150>Default monitor level for the CPU utilization monitoring of the CPU watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { uxsA2ConfigCPUGroup 6 }

uxsA2ConfigCPULossAction OBJECT-TYPE
	SYNTAX INTEGER {
		remove(1),
		up(2),
		down-warning(3),
		down-critical(4)
	}
	ACCESS read-write
	STATUS mandatory
	DESCRIPTION "&<caiUxsA2.151>Default loss action for the CPU watcher to add. Specifies the action to take if the monitored CPU is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { uxsA2ConfigCPUGroup 7 }

--
-- The ConfigLoad Group
--

uxsA2ConfigLoadPollInterval OBJECT-TYPE
	SYNTAX INTEGER
	ACCESS read-write
	STATUS mandatory
	DESCRIPTION "&<caiUxsA2.152>Time, in seconds, between collections of load average information. Valid range: 30 seconds or greater."
	DEFVAL { 60 }
	::= { uxsA2ConfigLoadGroup 1 }

uxsA2ConfigLoadPollMethod OBJECT-TYPE
	SYNTAX INTEGER {
		disabled(1),
		poll-interval-only(2),
		poll-interval-and-query(3),
		query-only(4)
	}
	ACCESS read-write
	STATUS mandatory
	DESCRIPTION "&<caiUxsA2.153>Specifies how and when the agent collects load average information. If set to 1 (disabled), the agent does not retrieve the load average information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigLoadGroup 2 }

--
-- The ConfigMem Group
--

uxsA2ConfigMemPollInterval OBJECT-TYPE
	SYNTAX INTEGER
	ACCESS read-write
	STATUS mandatory
	DESCRIPTION "&<caiUxsA2.154>Time, in seconds, between collections of real memory information. Valid range: 30 seconds or greater."
	DEFVAL { 60 }
	::= { uxsA2ConfigMemGroup 1 }

uxsA2ConfigMemPollMethod OBJECT-TYPE
	SYNTAX INTEGER {
		disabled(1),
		poll-interval-only(2),
		poll-interval-and-query(3),
		query-only(4)
	}
	ACCESS read-write
	STATUS mandatory
	DESCRIPTION "&<caiUxsA2.155>Specifies how and when the agent collects real memory information. If set to 1 (disabled), the agent does not retrieve the real memory information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigMemGroup 2 }

--
-- The ConfigSwap Group
--

uxsA2ConfigSwapPollInterval OBJECT-TYPE
	SYNTAX INTEGER
	ACCESS read-write
	STATUS mandatory
	DESCRIPTION "&<caiUxsA2.156>Time, in seconds, between collections of swap information. Valid range: 30 seconds or greater."
	DEFVAL { 60 }
	::= { uxsA2ConfigSwapGroup 1 }

uxsA2ConfigSwapPollMethod OBJECT-TYPE
	SYNTAX INTEGER {
		disabled(1),
		poll-interval-only(2),
		poll-interval-and-query(3),
		query-only(4)
	}
	ACCESS read-write
	STATUS mandatory
	DESCRIPTION "&<caiUxsA2.157>Specifies how and when the agent collects swap information. If set to 1 (disabled), the agent does not retrieve the swap information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigSwapGroup 2 }

uxsA2ConfigSwapSpaceLag OBJECT-TYPE
	SYNTAX INTEGER
	ACCESS read-write
	STATUS mandatory
	DESCRIPTION "&<caiUxsA2.158>Default lag setting for the swap space utilization monitoring of the swap watcher to add. Specifies the number of consecutive threshold breaches on which the swap space utilization state changes. This value must be greater than 0."
	DEFVAL { 3 }
	::= { uxsA2ConfigSwapGroup 3 }

uxsA2ConfigSwapSpaceWarn OBJECT-TYPE
	SYNTAX DisplayString
	ACCESS read-write
	STATUS mandatory
	DESCRIPTION "&<caiUxsA2.159>Default warning threshold, in kilobytes, for the swap space utilization monitoring of the swap watcher to add. The active warning threshold is derived from this value and represents a rising threshold. The derived value must be greater than 0.0, less than or equal to the total value (maximum capacity) of the monitored resource as specified in uxsA2StatusSwapSpaceTotal, but cannot be greater than the active critical threshold. These constraints will be maintained by the agent during all configuration actions. The threshold can be specified as either an absolute value (n) or a percentage (n%). It can also be specified as the absolute value left free (nF). The value of uxsA2StatusSwapSpaceTotal will be the reference value for n% and nF notations."
	DEFVAL { "85.0%" }
	::= { uxsA2ConfigSwapGroup 4 }

uxsA2ConfigSwapSpaceCrit OBJECT-TYPE
	SYNTAX DisplayString
	ACCESS read-write
	STATUS mandatory
	DESCRIPTION "&<caiUxsA2.160>Default critical threshold, in kilobytes, for the swap space utilization monitoring of the swap watcher to add. The active critical threshold is derived from this value and represents a rising threshold. The derived value must be greater than 0.0, less than or equal to the total value (maximum capacity) of the monitored resource as specified in uxsA2StatusSwapSpaceTotal, but cannot be less than the active warning threshold. These constraints will be maintained by the agent during all configuration actions. The threshold can be specified as either an absolute value (n) or a percentage (n%). It can also be specified as the absolute value left free (nF). The value of uxsA2StatusSwapSpaceTotal will be the reference value for n% and nF notations."
	DEFVAL { "95.0%" }
	::= { uxsA2ConfigSwapGroup 5 }

uxsA2ConfigSwapSpaceMonitor OBJECT-TYPE
	SYNTAX INTEGER {
		do-not-monitor(1),
		warning-only(2),
		critical-only(3),
		both(4)
	}
	ACCESS read-write
	STATUS mandatory
	DESCRIPTION "&<caiUxsA2.161>Default monitor level for the swap space utilization monitoring of the swap watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { uxsA2ConfigSwapGroup 6 }

uxsA2ConfigSwapLossAction OBJECT-TYPE
	SYNTAX INTEGER {
		remove(1),
		up(2),
		down-warning(3),
		down-critical(4)
	}
	ACCESS read-write
	STATUS mandatory
	DESCRIPTION "&<caiUxsA2.162>Default loss action for the swap watcher to add. Specifies the action to take if the monitored swap is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { uxsA2ConfigSwapGroup 7 }

--
-- The ConfigQuota Group
--

uxsA2ConfigQuotaPollInterval OBJECT-TYPE
	SYNTAX INTEGER
	ACCESS read-write
	STATUS mandatory
	DESCRIPTION "&<caiUxsA2.163>Time, in seconds, between collections of quota information. Valid range: 30 seconds or greater."
	DEFVAL { 120 }
	::= { uxsA2ConfigQuotaGroup 1 }

uxsA2ConfigQuotaPollMethod OBJECT-TYPE
	SYNTAX INTEGER {
		disabled(1),
		poll-interval-only(2),
		poll-interval-and-query(3),
		query-only(4)
	}
	ACCESS read-write
	STATUS mandatory
	DESCRIPTION "&<caiUxsA2.164>Specifies how and when the agent collects quota information. If set to 1 (disabled), the agent does not retrieve the quota information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigQuotaGroup 2 }

uxsA2ConfigQuotaAutoPollInterval OBJECT-TYPE
	SYNTAX INTEGER
	ACCESS read-write
	STATUS mandatory
	DESCRIPTION "&<caiUxsA2.165>Time, in minutes, between the processing of the quota auto watchers. Valid range: -1 (suspended), 30 minutes or greater."
	DEFVAL { 60 }
	::= { uxsA2ConfigQuotaGroup 3 }

uxsA2ConfigQuotaFSys OBJECT-TYPE
	SYNTAX DisplayString
	ACCESS read-write
	STATUS mandatory
	DESCRIPTION "&<caiUxsA2.166>Specifies the name of the file system for which quotas are enabled. When adding an auto watcher, the name can constitute an extended regular expression pattern."
	::= { uxsA2ConfigQuotaGroup 4 }

uxsA2ConfigQuotaUser OBJECT-TYPE
	SYNTAX DisplayString
	ACCESS read-write
	STATUS mandatory
	DESCRIPTION "&<caiUxsA2.167>Specifies the name of the user for which quota information exists on the corresponding file system. When adding an auto watcher, the name can constitute an extended regular expression pattern."
	::= { uxsA2ConfigQuotaGroup 5 }

uxsA2ConfigQuotaDescription OBJECT-TYPE
	SYNTAX DisplayString
	ACCESS read-write
	STATUS mandatory
	DESCRIPTION "&<caiUxsA2.168>Default description for the quota watcher to add."
	::= { uxsA2ConfigQuotaGroup 6 }

uxsA2ConfigQuotaAggLag OBJECT-TYPE
	SYNTAX INTEGER
	ACCESS read-write
	STATUS mandatory
	DESCRIPTION "&<caiUxsA2.169>Default aggregate lag setting for the quota watcher to add. Specifies the consecutive number of times at which any status is not in the ok state, before the aggregate status changes. This value must be greater than 0."
	DEFVAL { 3 }
	::= { uxsA2ConfigQuotaGroup 7 }

uxsA2ConfigQuotaSpaceWarn OBJECT-TYPE
	SYNTAX DisplayString
	ACCESS read-write
	STATUS mandatory
	DESCRIPTION "&<caiUxsA2.170>Default warning threshold, in kilobytes, for the space utilization monitoring of the quota watcher to add. The active warning threshold is derived from this value and represents a rising threshold. The derived value must be greater than 0.0, less than or equal to the total value (maximum capacity) of the monitored resource as specified in uxsA2StatusQuotaSpaceTotal, but cannot be greater than the active critical threshold. These constraints will be maintained by the agent during all configuration actions. The threshold can be specified as either an absolute value (n) or a percentage (n%). It can also be specified as the absolute value left free (nF). The value of uxsA2StatusQuotaSpaceTotal will be the reference value for n% and nF notations."
	DEFVAL { "85.0%" }
	::= { uxsA2ConfigQuotaGroup 8 }

uxsA2ConfigQuotaSpaceCrit OBJECT-TYPE
	SYNTAX DisplayString
	ACCESS read-write
	STATUS mandatory
	DESCRIPTION "&<caiUxsA2.171>Default critical threshold, in kilobytes, for the space utilization monitoring of the quota watcher to add. The active critical threshold is derived from this value and represents a rising threshold. The derived value must be greater than 0.0, less than or equal to the total value (maximum capacity) of the monitored resource as specified in uxsA2StatusQuotaSpaceTotal, but cannot be less than the active warning threshold. These constraints will be maintained by the agent during all configuration actions. The threshold can be specified as either an absolute value (n) or a percentage (n%). It can also be specified as the absolute value left free (nF). The value of uxsA2StatusQuotaSpaceTotal will be the reference value for n% and nF notations."
	DEFVAL { "95.0%" }
	::= { uxsA2ConfigQuotaGroup 9 }

uxsA2ConfigQuotaSpaceMonitor OBJECT-TYPE
	SYNTAX INTEGER {
		do-not-monitor(1),
		warning-only(2),
		critical-only(3),
		both(4)
	}
	ACCESS read-write
	STATUS mandatory
	DESCRIPTION "&<caiUxsA2.172>Default monitor level for the space utilization monitoring of the quota watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigQuotaGroup 10 }

uxsA2ConfigQuotaInodesWarn OBJECT-TYPE
	SYNTAX DisplayString
	ACCESS read-write
	STATUS mandatory
	DESCRIPTION "&<caiUxsA2.173>Default warning threshold for the inodes utilization monitoring of the quota watcher to add. The active warning threshold is derived from this value and represents a rising threshold. The derived value must be greater than 0.0, less than or equal to the total value (maximum capacity) of the monitored resource as specified in uxsA2StatusQuotaInodesTotal, but cannot be greater than the active critical threshold. These constraints will be maintained by the agent during all configuration actions. The threshold can be specified as either an absolute value (n) or a percentage (n%). It can also be specified as the absolute value left free (nF). The value of uxsA2StatusQuotaInodesTotal will be the reference value for n% and nF notations."
	DEFVAL { "85.0%" }
	::= { uxsA2ConfigQuotaGroup 11 }

uxsA2ConfigQuotaInodesCrit OBJECT-TYPE
	SYNTAX DisplayString
	ACCESS read-write
	STATUS mandatory
	DESCRIPTION "&<caiUxsA2.174>Default critical threshold for the inodes utilization monitoring of the quota watcher to add. The active critical threshold is derived from this value and represents a rising threshold. The derived value must be greater than 0.0, less than or equal to the total value (maximum capacity) of the monitored resource as specified in uxsA2StatusQuotaInodesTotal, but cannot be less than the active warning threshold. These constraints will be maintained by the agent during all configuration actions. The threshold can be specified as either an absolute value (n) or a percentage (n%). It can also be specified as the absolute value left free (nF). The value of uxsA2StatusQuotaInodesTotal will be the reference value for n% and nF notations."
	DEFVAL { "95.0%" }
	::= { uxsA2ConfigQuotaGroup 12 }

uxsA2ConfigQuotaInodesMonitor OBJECT-TYPE
	SYNTAX INTEGER {
		do-not-monitor(1),
		warning-only(2),
		critical-only(3),
		both(4)
	}
	ACCESS read-write
	STATUS mandatory
	DESCRIPTION "&<caiUxsA2.175>Default monitor level for the inodes utilization monitoring of the quota watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigQuotaGroup 13 }

uxsA2ConfigQuotaExpiredSpaceMonitor OBJECT-TYPE
	SYNTAX INTEGER {
		do-not-monitor(1),
		down-warning(2),
		down-critical(3)
	}
	ACCESS read-write
	STATUS mandatory
	DESCRIPTION "&<caiUxsA2.176>Default monitor level for the expired space monitoring of the quota watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { uxsA2ConfigQuotaGroup 14 }

uxsA2ConfigQuotaExpiredInodesMonitor OBJECT-TYPE
	SYNTAX INTEGER {
		do-not-monitor(1),
		down-warning(2),
		down-critical(3)
	}
	ACCESS read-write
	STATUS mandatory
	DESCRIPTION "&<caiUxsA2.177>Default monitor level for the expired inodes monitoring of the quota watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { uxsA2ConfigQuotaGroup 15 }

uxsA2ConfigQuotaLossAction OBJECT-TYPE
	SYNTAX INTEGER {
		remove(1),
		up(2),
		down-warning(3),
		down-critical(4)
	}
	ACCESS read-write
	STATUS mandatory
	DESCRIPTION "&<caiUxsA2.178>Default loss action for the quota watcher to add. Specifies the action to take if the monitored quota is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { uxsA2ConfigQuotaGroup 16 }

uxsA2ConfigQuotaAutoTableWatcherName OBJECT-TYPE
	SYNTAX DisplayString
	ACCESS read-write
	STATUS mandatory
	DESCRIPTION "&<caiUxsA2.179>Name of the quota auto watcher to add or remove."
	::= { uxsA2ConfigQuotaGroup 17 }

uxsA2ConfigQuotaAutoTableWatcherMatchType OBJECT-TYPE
	SYNTAX INTEGER {
		positive(1),
		negative(2)
	}
	ACCESS read-write
	STATUS mandatory
	DESCRIPTION "&<caiUxsA2.180>Default search algorithm for the quota auto watcher to add. The filter is the logical AND of all attributes used to identify or otherwise narrow down resources. If set to 1 (positive), the agent searches for quota resources that match the filter. If set to 2 (negative), the agent searches for quota resources that do not match the filter."
	DEFVAL { 1 }
	::= { uxsA2ConfigQuotaGroup 18 }

uxsA2ConfigQuotaAutoTableWatcherLimit OBJECT-TYPE
	SYNTAX INTEGER
	ACCESS read-write
	STATUS mandatory
	DESCRIPTION "&<caiUxsA2.181>Default minimum number of matches that causes a lock of the quota auto watcher to add."
	DEFVAL { 100 }
	::= { uxsA2ConfigQuotaGroup 19 }

uxsA2ConfigQuotaButton OBJECT-TYPE
	SYNTAX INTEGER {
		none(1),
		add(2),
		remove(3),
		add-auto(4),
		remove-auto(5)
	}
	ACCESS read-write
	STATUS mandatory
	DESCRIPTION "&<caiUxsA2.182>This attribute is used to add or remove the quota watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { uxsA2ConfigQuotaGroup 20 }

uxsA2ConfigQuotaAutoCount OBJECT-TYPE
	SYNTAX INTEGER
	ACCESS read-only
	STATUS mandatory
	DESCRIPTION "&<caiUxsA2.183>Number of auto watchers in the quota auto configuration table."
	::= { uxsA2ConfigQuotaGroup 21 }

uxsA2ConfigQuotaAutoLocked OBJECT-TYPE
	SYNTAX INTEGER
	ACCESS read-only
	STATUS mandatory
	DESCRIPTION "&<caiUxsA2.184>Number of auto watchers in the quota auto configuration table which are currently locked."
	::= { uxsA2ConfigQuotaGroup 22 }

uxsA2ConfigQuotaAutoTable OBJECT-TYPE
	SYNTAX SEQUENCE OF UxsA2ConfigQuotaAutoEntry
	ACCESS not-accessible
	STATUS mandatory
	DESCRIPTION "&<caiUxsA2.185>Configuration table containing a list of quota auto watchers."
	::= { uxsA2ConfigQuotaGroup 23 }

uxsA2ConfigQuotaAutoEntry OBJECT-TYPE
	SYNTAX UxsA2ConfigQuotaAutoEntry
	ACCESS not-accessible
	STATUS mandatory
	DESCRIPTION "&<caiUxsA2.186>Entry in the quota auto watcher configuration table."
	INDEX {
		uxsA2ConfigQuotaAutoWatcherName
	}
	::= { uxsA2ConfigQuotaAutoTable 1 }

UxsA2ConfigQuotaAutoEntry ::= SEQUENCE {
	uxsA2ConfigQuotaAutoWatcherName DisplayString,
	uxsA2ConfigQuotaAutoFSys DisplayString,
	uxsA2ConfigQuotaAutoUser DisplayString,
	uxsA2ConfigQuotaAutoDescription DisplayString,
	uxsA2ConfigQuotaAutoWatcherMatchType INTEGER,
	uxsA2ConfigQuotaAutoWatcherLimit INTEGER,
	uxsA2ConfigQuotaAutoWatcherLastMatched INTEGER,
	uxsA2ConfigQuotaAutoAggLag INTEGER,
	uxsA2ConfigQuotaAutoSpaceWarn DisplayString,
	uxsA2ConfigQuotaAutoSpaceCrit DisplayString,
	uxsA2ConfigQuotaAutoSpaceMonitor INTEGER,
	uxsA2ConfigQuotaAutoInodesWarn DisplayString,
	uxsA2ConfigQuotaAutoInodesCrit DisplayString,
	uxsA2ConfigQuotaAutoInodesMonitor INTEGER,
	uxsA2ConfigQuotaAutoExpiredSpaceMonitor INTEGER,
	uxsA2ConfigQuotaAutoExpiredInodesMonitor INTEGER,
	uxsA2ConfigQuotaAutoLossAction INTEGER,
	uxsA2ConfigQuotaAutoButton INTEGER
}

uxsA2ConfigQuotaAutoWatcherName OBJECT-TYPE
	SYNTAX DisplayString
	ACCESS read-only
	STATUS mandatory
	DESCRIPTION "&<caiUxsA2.187>Name of the quota auto watcher."
	::= { uxsA2ConfigQuotaAutoEntry 1 }

uxsA2ConfigQuotaAutoFSys OBJECT-TYPE
	SYNTAX DisplayString
	ACCESS read-write
	STATUS mandatory
	DESCRIPTION "&<caiUxsA2.188>Specifies the name of the file system for which quotas are enabled. The name can constitute an extended regular expression pattern."
	::= { uxsA2ConfigQuotaAutoEntry 2 }

uxsA2ConfigQuotaAutoUser OBJECT-TYPE
	SYNTAX DisplayString
	ACCESS read-write
	STATUS mandatory
	DESCRIPTION "&<caiUxsA2.189>Specifies the name of the user for which quota information exists on the corresponding file system. The name can constitute an extended regular expression pattern."
	::= { uxsA2ConfigQuotaAutoEntry 3 }

uxsA2ConfigQuotaAutoDescription OBJECT-TYPE
	SYNTAX DisplayString
	ACCESS read-write
	STATUS mandatory
	DESCRIPTION "&<caiUxsA2.190>Current description for the quota auto watcher."
	::= { uxsA2ConfigQuotaAutoEntry 4 }

uxsA2ConfigQuotaAutoWatcherMatchType OBJECT-TYPE
	SYNTAX INTEGER {
		positive(1),
		negative(2)
	}
	ACCESS read-write
	STATUS mandatory
	DESCRIPTION "&<caiUxsA2.191>Current search algorithm for the quota auto watcher. The filter is the logical AND of all attributes used to identify or otherwise narrow down resources. If set to 1 (positive), the agent searches for quota resources that match the filter. If set to 2 (negative), the agent searches for quota resources that do not match the filter."
	DEFVAL { 0 }
	::= { uxsA2ConfigQuotaAutoEntry 5 }

uxsA2ConfigQuotaAutoWatcherLimit OBJECT-TYPE
	SYNTAX INTEGER
	ACCESS read-write
	STATUS mandatory
	DESCRIPTION "&<caiUxsA2.192>Current minimum number of matches that causes the quota auto watcher to be locked."
	::= { uxsA2ConfigQuotaAutoEntry 6 }

uxsA2ConfigQuotaAutoWatcherLastMatched OBJECT-TYPE
	SYNTAX INTEGER
	ACCESS read-only
	STATUS mandatory
	DESCRIPTION "&<caiUxsA2.193>Number of matches for the last quota auto discovery run."
	::= { uxsA2ConfigQuotaAutoEntry 7 }

uxsA2ConfigQuotaAutoAggLag OBJECT-TYPE
	SYNTAX INTEGER
	ACCESS read-write
	STATUS mandatory
	DESCRIPTION "&<caiUxsA2.194>Current lag setting for the quota auto watcher. Specifies the consecutive number of times at which any status is not in the ok state, before the aggregate status changes. This value must be greater than 0."
	::= { uxsA2ConfigQuotaAutoEntry 8 }

uxsA2ConfigQuotaAutoSpaceWarn OBJECT-TYPE
	SYNTAX DisplayString
	ACCESS read-write
	STATUS mandatory
	DESCRIPTION "&<caiUxsA2.195>Default warning threshold, in kilobytes, for the space utilization monitoring of any quota watcher created by the auto watcher. The active warning threshold is derived from this value and represents a rising threshold. The derived value must be greater than 0.0, less than or equal to the total value (maximum capacity) of the monitored resource as specified in uxsA2StatusQuotaSpaceTotal, but cannot be greater than the active critical threshold. These constraints will be maintained by the agent during all configuration actions. The threshold can be specified as either an absolute value (n) or a percentage (n%). It can also be specified as the absolute value left free (nF). The value of uxsA2StatusQuotaSpaceTotal will be the reference value for n% and nF notations."
	::= { uxsA2ConfigQuotaAutoEntry 9 }

uxsA2ConfigQuotaAutoSpaceCrit OBJECT-TYPE
	SYNTAX DisplayString
	ACCESS read-write
	STATUS mandatory
	DESCRIPTION "&<caiUxsA2.196>Default critical threshold, in kilobytes, for the space utilization monitoring of any quota watcher created by the auto watcher. The active critical threshold is derived from this value and represents a rising threshold. The derived value must be greater than 0.0, less than or equal to the total value (maximum capacity) of the monitored resource as specified in uxsA2StatusQuotaSpaceTotal, but cannot be less than the active warning threshold. These constraints will be maintained by the agent during all configuration actions. The threshold can be specified as either an absolute value (n) or a percentage (n%). It can also be specified as the absolute value left free (nF). The value of uxsA2StatusQuotaSpaceTotal will be the reference value for n% and nF notations."
	::= { uxsA2ConfigQuotaAutoEntry 10 }

uxsA2ConfigQuotaAutoSpaceMonitor OBJECT-TYPE
	SYNTAX INTEGER {
		do-not-monitor(1),
		warning-only(2),
		critical-only(3),
		both(4)
	}
	ACCESS read-write
	STATUS mandatory
	DESCRIPTION "&<caiUxsA2.197>Default monitor level for the space utilization monitoring of any quota watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2ConfigQuotaAutoEntry 11 }

uxsA2ConfigQuotaAutoInodesWarn OBJECT-TYPE
	SYNTAX DisplayString
	ACCESS read-write
	STATUS mandatory
	DESCRIPTION "&<caiUxsA2.198>Default warning threshold for the inodes utilization monitoring of any quota watcher created by the auto watcher. The active warning threshold is derived from this value and represents a rising threshold. The derived value must be greater than 0.0, less than or equal to the total value (maximum capacity) of the monitored resource as specified in uxsA2StatusQuotaInodesTotal, but cannot be greater than the active critical threshold. These constraints will be maintained by the agent during all configuration actions. The threshold can be specified as either an absolute value (n) or a percentage (n%). It can also be specified as the absolute value left free (nF). The value of uxsA2StatusQuotaInodesTotal will be the reference value for n% and nF notations."
	::= { uxsA2ConfigQuotaAutoEntry 12 }

uxsA2ConfigQuotaAutoInodesCrit OBJECT-TYPE
	SYNTAX DisplayString
	ACCESS read-write
	STATUS mandatory
	DESCRIPTION "&<caiUxsA2.199>Default critical threshold for the inodes utilization monitoring of any quota watcher created by the auto watcher. The active critical threshold is derived from this value and represents a rising threshold. The derived value must be greater than 0.0, less than or equal to the total value (maximum capacity) of the monitored resource as specified in uxsA2StatusQuotaInodesTotal, but cannot be less than the active warning threshold. These constraints will be maintained by the agent during all configuration actions. The threshold can be specified as either an absolute value (n) or a percentage (n%). It can also be specified as the absolute value left free (nF). The value of uxsA2StatusQuotaInodesTotal will be the reference value for n% and nF notations."
	::= { uxsA2ConfigQuotaAutoEntry 13 }

uxsA2ConfigQuotaAutoInodesMonitor OBJECT-TYPE
	SYNTAX INTEGER {
		do-not-monitor(1),
		warning-only(2),
		critical-only(3),
		both(4)
	}
	ACCESS read-write
	STATUS mandatory
	DESCRIPTION "&<caiUxsA2.200>Default monitor level for the inodes utilization monitoring of any quota watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2ConfigQuotaAutoEntry 14 }

uxsA2ConfigQuotaAutoExpiredSpaceMonitor OBJECT-TYPE
	SYNTAX INTEGER {
		do-not-monitor(1),
		down-warning(2),
		down-critical(3)
	}
	ACCESS read-write
	STATUS mandatory
	DESCRIPTION "&<caiUxsA2.201>Default monitor level for the expired space monitoring of any quota watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2ConfigQuotaAutoEntry 15 }

uxsA2ConfigQuotaAutoExpiredInodesMonitor OBJECT-TYPE
	SYNTAX INTEGER {
		do-not-monitor(1),
		down-warning(2),
		down-critical(3)
	}
	ACCESS read-write
	STATUS mandatory
	DESCRIPTION "&<caiUxsA2.202>Default monitor level for the expired inodes monitoring of any quota watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2ConfigQuotaAutoEntry 16 }

uxsA2ConfigQuotaAutoLossAction OBJECT-TYPE
	SYNTAX INTEGER {
		remove(1),
		up(2),
		down-warning(3),
		down-critical(4)
	}
	ACCESS read-write
	STATUS mandatory
	DESCRIPTION "&<caiUxsA2.203>Default loss action for any quota watcher created by the auto watcher. Specifies the action to take if the monitored quota is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2ConfigQuotaAutoEntry 17 }

uxsA2ConfigQuotaAutoButton OBJECT-TYPE
	SYNTAX INTEGER {
		active(1),
		remove(2),
		locked(3)
	}
	ACCESS read-write
	STATUS mandatory
	DESCRIPTION "&<caiUxsA2.204>This attribute is used to enable/disable or remove the quota auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { uxsA2ConfigQuotaAutoEntry 18 }

--
-- The ConfigDir Group
--

uxsA2ConfigDirPollInterval OBJECT-TYPE
	SYNTAX INTEGER
	ACCESS read-write
	STATUS mandatory
	DESCRIPTION "&<caiUxsA2.205>Time, in seconds, between collections of directory information. Valid range: 30 seconds or greater."
	DEFVAL { 120 }
	::= { uxsA2ConfigDirGroup 1 }

uxsA2ConfigDirPollMethod OBJECT-TYPE
	SYNTAX INTEGER {
		disabled(1),
		poll-interval-only(2),
		poll-interval-and-query(3),
		query-only(4)
	}
	ACCESS read-write
	STATUS mandatory
	DESCRIPTION "&<caiUxsA2.206>Specifies how and when the agent collects directory information. If set to 1 (disabled), the agent does not retrieve the directory information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigDirGroup 2 }

uxsA2ConfigDirWatcherName OBJECT-TYPE
	SYNTAX DisplayString
	ACCESS read-write
	STATUS mandatory
	DESCRIPTION "&<caiUxsA2.207>Name of the directory watcher."
	::= { uxsA2ConfigDirGroup 3 }

uxsA2ConfigDirName OBJECT-TYPE
	SYNTAX DisplayString
	ACCESS read-write
	STATUS mandatory
	DESCRIPTION "&<caiUxsA2.208>Name of the directory for which to add or remove a watcher. This must be a fully qualified name that may contain environment variables."
	::= { uxsA2ConfigDirGroup 4 }

uxsA2ConfigDirRecursivePolicy OBJECT-TYPE
	SYNTAX INTEGER {
		no(1),
		yes(2)
	}
	ACCESS read-write
	STATUS mandatory
	DESCRIPTION "&<caiUxsA2.209>Recursiveness of the directory watcher. If set to 1 (no) only entries in the given directory are monitored. If set to 2 (yes) additionally all subentries (subdirectories and their files) are monitored."
	DEFVAL { 1 }
	::= { uxsA2ConfigDirGroup 5 }

uxsA2ConfigDirDescription OBJECT-TYPE
	SYNTAX DisplayString
	ACCESS read-write
	STATUS mandatory
	DESCRIPTION "&<caiUxsA2.210>Default description for the directory watcher to add."
	::= { uxsA2ConfigDirGroup 6 }

uxsA2ConfigDirAggLag OBJECT-TYPE
	SYNTAX INTEGER
	ACCESS read-write
	STATUS mandatory
	DESCRIPTION "&<caiUxsA2.211>Default aggregate lag setting for the directory watcher to add. Specifies the consecutive number of times at which any status is not in the ok state, before the aggregate status changes. This value must be greater than 0."
	DEFVAL { 2 }
	::= { uxsA2ConfigDirGroup 7 }

uxsA2ConfigDirSizeWarnMin OBJECT-TYPE
	SYNTAX DisplayString
	ACCESS read-write
	STATUS mandatory
	DESCRIPTION "&<caiUxsA2.212>Default warning minimum threshold, in kilobytes, for the size utilization monitoring of the directory watcher to add. This value represents a declining threshold and must be equal to or greater than 0.0, equal to or greater than the critical minimum threshold, but cannot be greater than the warning maximum threshold. A value of -1 disables the evaluation of this threshold. The threshold can be specified as either an absolute value (n) or a percentage (n%). The value of uxsA2StatusDirSizeTotal will be the reference value for n% notations."
	DEFVAL { "-1" }
	::= { uxsA2ConfigDirGroup 8 }

uxsA2ConfigDirSizeWarnMax OBJECT-TYPE
	SYNTAX DisplayString
	ACCESS read-write
	STATUS mandatory
	DESCRIPTION "&<caiUxsA2.213>Default warning maximum threshold, in kilobytes, for the size utilization monitoring of the directory watcher to add. This value represents a rising threshold and must be equal to or greater than 0.0, equal to or greater than the warning minimum threshold, but cannot be greater than the critical maximum threshold. A value of -1 disables the evaluation of this threshold. The threshold can be specified as either an absolute value (n) or a percentage (n%). The value of uxsA2StatusDirSizeTotal will be the reference value for n% notations."
	DEFVAL { "150.0%" }
	::= { uxsA2ConfigDirGroup 9 }

uxsA2ConfigDirSizeCritMin OBJECT-TYPE
	SYNTAX DisplayString
	ACCESS read-write
	STATUS mandatory
	DESCRIPTION "&<caiUxsA2.214>Default critical minimum threshold, in kilobytes, for the size utilization monitoring of the directory watcher to add. This value represents a declining threshold and must be equal to or greater than 0.0, but cannot be greater than the warning minimum threshold. A value of -1 disables the evaluation of this threshold. The threshold can be specified as either an absolute value (n) or a percentage (n%). The value of uxsA2StatusDirSizeTotal will be the reference value for n% notations."
	DEFVAL { "-1" }
	::= { uxsA2ConfigDirGroup 10 }

uxsA2ConfigDirSizeCritMax OBJECT-TYPE
	SYNTAX DisplayString
	ACCESS read-write
	STATUS mandatory
	DESCRIPTION "&<caiUxsA2.215>Default critical maximum threshold, in kilobytes, for the size utilization monitoring of the directory watcher to add. This value represents a rising threshold and must be equal to or greater than 0.0, but cannot be less than the warning maximum threshold. A value of -1 disables the evaluation of this threshold. The threshold can be specified as either an absolute value (n) or a percentage (n%). The value of uxsA2StatusDirSizeTotal will be the reference value for n% notations."
	DEFVAL { "200.0%" }
	::= { uxsA2ConfigDirGroup 11 }

uxsA2ConfigDirSizeMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.216>Default monitor level for the size utilization monitoring of the directory watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { uxsA2ConfigDirGroup 12 }

uxsA2ConfigDirSizeDWarn OBJECT-TYPE
	SYNTAX DisplayString
	ACCESS read-write
	STATUS mandatory
	DESCRIPTION "&<caiUxsA2.217>Default warning threshold, in kilobytes, for the delta size utilization monitoring of the directory watcher to add. The active warning threshold is derived from this value and represents a rising threshold. The derived value must be greater than 0.0, but cannot be greater than the active critical threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusDirSizeTotal will be the reference value for n% notations."
	DEFVAL { "20.0%+" }
	::= { uxsA2ConfigDirGroup 13 }

uxsA2ConfigDirSizeDCrit OBJECT-TYPE
	SYNTAX DisplayString
	ACCESS read-write
	STATUS mandatory
	DESCRIPTION "&<caiUxsA2.218>Default critical threshold, in kilobytes, for the delta size utilization monitoring of the directory watcher to add. The active critical threshold is derived from this value and represents a rising threshold. The derived value must be greater than 0.0, but cannot be less than the active warning threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusDirSizeTotal will be the reference value for n% notations."
	DEFVAL { "40.0%+" }
	::= { uxsA2ConfigDirGroup 14 }

uxsA2ConfigDirSizeDMonitor OBJECT-TYPE
	SYNTAX INTEGER {
		do-not-monitor(1),
		warning-only(2),
		critical-only(3),
		both(4)
	}
	ACCESS read-write
	STATUS mandatory
	DESCRIPTION "&<caiUxsA2.219>Default monitor level for the delta size utilization monitoring of the directory watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigDirGroup 15 }

uxsA2ConfigDirEntriesMin OBJECT-TYPE
	SYNTAX DisplayString
	ACCESS read-write
	STATUS mandatory
	DESCRIPTION "&<caiUxsA2.220>Default minimum threshold for the number of file and/or directory entries monitoring of the directory watcher to add. This value represents a declining threshold and must be equal to or greater than 0.0, but cannot be greater than the maximum threshold. A value of -1 disables the evaluation of this threshold."
	DEFVAL { "-1" }
	::= { uxsA2ConfigDirGroup 16 }

uxsA2ConfigDirEntriesMax OBJECT-TYPE
	SYNTAX DisplayString
	ACCESS read-write
	STATUS mandatory
	DESCRIPTION "&<caiUxsA2.221>Default maximum threshold for the number of file and/or directory entries monitoring of the directory watcher to add. This value represents a rising threshold and must be equal to or greater than 0.0, but cannot be less than the minimum threshold. A value of -1 disables the evaluation of this threshold."
	DEFVAL { "100.0" }
	::= { uxsA2ConfigDirGroup 17 }

uxsA2ConfigDirEntriesMonitor OBJECT-TYPE
	SYNTAX INTEGER {
		do-not-monitor(1),
		down-warning(2),
		down-critical(3)
	}
	ACCESS read-write
	STATUS mandatory
	DESCRIPTION "&<caiUxsA2.222>Default monitor level for the number of file and/or directory entries monitoring of the directory watcher to add. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { uxsA2ConfigDirGroup 18 }

uxsA2ConfigDirModInterval OBJECT-TYPE
	SYNTAX DisplayString
	ACCESS read-write
	STATUS mandatory
	DESCRIPTION "&<caiUxsA2.223>The period in seconds to be considered for calculating status and value of the modification metric. For a value of zero the period is identical to the current poll interval."
	DEFVAL { "0" }
	::= { uxsA2ConfigDirGroup 19 }

uxsA2ConfigDirMod OBJECT-TYPE
	SYNTAX INTEGER {
		should-not-be-modified(1),
		should-not-be-changed(2),
		should-not-be-changed-only(3),
		should-not-be-accessed(4),
		should-be-modified(5),
		should-be-changed(6),
		should-be-changed-only(7),
		should-be-accessed(8)
	}
	ACCESS read-write
	STATUS mandatory
	DESCRIPTION "&<caiUxsA2.224>Default monitor condition for the modification monitoring of the directory watcher to add. As a reference for modification the user can choose between modification time, change time, change time only (change time is modified and modification time is not), and access time. All times can be monitored for being modified (should-be-modified, should-be-changed, should-be-changed-only, should-be-accessed) or for being unmodified (should-not-be-modified, should-not-be-changed, should-not-be-changed-only, should-not-be-accessed). At each poll the latest timestamp of the chosen policy for the directory in question will be compared with the reference timestamp. If the resulting monitor status is 'up' the reference time is set automatically to the most recent value of access time, change time, or modification time. If the monitor status is 'down' the metric may be reset manually by setting the monitor condition to reset-time-reference. Status calculation depends on the kind of monitoring (modified or unmodified) and the value of DirModInterval'. If monitoring is for being modified the status is down if the file was not modified for more seconds than the value of 'DirModInterval'. Status is reset to up if there are modifications within 'DirModInterval'. If monitoring is for being unmodified the status is down if the file was modified more often than every 'DirModInterval' seconds. If 'DirModInterval' is zero any modification sets the status down. Note that status evaluation only takes place when the agent polls. Thus the end of the modification interval will be detected on the subsequent poll."
	DEFVAL { 1 }
	::= { uxsA2ConfigDirGroup 20 }

uxsA2ConfigDirModMonitor OBJECT-TYPE
	SYNTAX INTEGER {
		do-not-monitor(1),
		down-warning(2),
		down-critical(3)
	}
	ACCESS read-write
	STATUS mandatory
	DESCRIPTION "&<caiUxsA2.225>Default monitor level for the modification monitoring of the directory watcher to add. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { uxsA2ConfigDirGroup 21 }

uxsA2ConfigDirExist OBJECT-TYPE
	SYNTAX INTEGER {
		should-exist(1),
		should-not-exist(2)
	}
	ACCESS read-write
	STATUS mandatory
	DESCRIPTION "&<caiUxsA2.226>Default monitor condition for the existence monitoring of the directory watcher to add. Specifies how the agent should evaluate the presence or absence of the monitored resource in order to determine whether the resource is in good condition. If set to 1 (should-exist), the resource is expected to be existent. If set to 2 (should-not-exist), the resource is expected to be nonexistent."
	DEFVAL { 1 }
	::= { uxsA2ConfigDirGroup 22 }

uxsA2ConfigDirExistMonitor OBJECT-TYPE
	SYNTAX INTEGER {
		do-not-monitor(1),
		down-warning(2),
		down-critical(3)
	}
	ACCESS read-write
	STATUS mandatory
	DESCRIPTION "&<caiUxsA2.227>Default monitor level for the existence monitoring of the directory watcher to add. If set to 1 (do-not-monitor), the agent does not evaluate the actual state of the resource and sets the status to ok. If set to 2 (down-warning), the agent uses a warning severity if the resource is in bad condition. If set to 3 (down-critical), the agent uses a critical severity if the resource is in bad condition."
	DEFVAL { 3 }
	::= { uxsA2ConfigDirGroup 23 }

uxsA2ConfigDirButton OBJECT-TYPE
	SYNTAX INTEGER {
		none(1),
		add(2),
		remove(3)
	}
	ACCESS read-write
	STATUS mandatory
	DESCRIPTION "&<caiUxsA2.228>This attribute is used to add or remove the directory watcher specified by the current setting of the watcher name attribute(s) in this group. If set to 2 (add), the agent adds the specified watcher to the status table using the current values of the remaining attributes as defaults. If set to 3 (remove), the agent removes the specified watcher from the status table. This attribute cannot be set to 1 (none)."
	DEFVAL { 1 }
	::= { uxsA2ConfigDirGroup 24 }

--
-- The ConfigFSys Group
--

uxsA2ConfigFSysPollInterval OBJECT-TYPE
	SYNTAX INTEGER
	ACCESS read-write
	STATUS mandatory
	DESCRIPTION "&<caiUxsA2.229>Time, in seconds, between collections of file system information. Valid range: 30 seconds or greater."
	DEFVAL { 300 }
	::= { uxsA2ConfigFSysGroup 1 }

uxsA2ConfigFSysPollMethod OBJECT-TYPE
	SYNTAX INTEGER {
		disabled(1),
		poll-interval-only(2),
		poll-interval-and-query(3),
		query-only(4)
	}
	ACCESS read-write
	STATUS mandatory
	DESCRIPTION "&<caiUxsA2.230>Specifies how and when the agent collects file system information. If set to 1 (disabled), the agent does not retrieve the file system information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigFSysGroup 2 }

uxsA2ConfigFSysAutoPollInterval OBJECT-TYPE
	SYNTAX INTEGER
	ACCESS read-write
	STATUS mandatory
	DESCRIPTION "&<caiUxsA2.231>Time, in minutes, between the processing of the file system auto watchers. Valid range: -1 (suspended), 30 minutes or greater."
	DEFVAL { 60 }
	::= { uxsA2ConfigFSysGroup 3 }

uxsA2ConfigFSysName OBJECT-TYPE
	SYNTAX DisplayString
	ACCESS read-write
	STATUS mandatory
	DESCRIPTION "&<caiUxsA2.232>Name of the file system for which to add or remove a watcher. When adding an auto watcher, the name can constitute an extended regular expression pattern."
	::= { uxsA2ConfigFSysGroup 4 }

uxsA2ConfigFSysRelatedTo OBJECT-TYPE
	SYNTAX DisplayString
	ACCESS read-write
	STATUS mandatory
	DESCRIPTION "&<caiUxsA2.233>The name of the device from which the file system is mounted. When adding an auto watcher, the name can constitute an extended regular expression pattern."
	DEFVAL { ".*" }
	::= { uxsA2ConfigFSysGroup 5 }

uxsA2ConfigFSysType OBJECT-TYPE
	SYNTAX DisplayString
	ACCESS read-write
	STATUS mandatory
	DESCRIPTION "&<caiUxsA2.234>The type of the mounted file system. The value is platform dependent."
	DEFVAL { ".*" }
	::= { uxsA2ConfigFSysGroup 6 }

uxsA2ConfigFSysClusterType OBJECT-TYPE
	SYNTAX INTEGER {
		not-clustered(1),
		clustered-active(2),
		clustered-passive(3),
		any(4)
	}
	ACCESS read-write
	STATUS mandatory
	DESCRIPTION "&<caiUxsA2.235>Cluster type of the file system to be searched for during an auto discovery run. This attribute is only used when adding an auto watcher. If set to 1 (not-clustered), the search is restricted to not-clustered resources only. If set to 2 (clustered-active), the search is restricted to clustered-active resources only. If set to 3 (clustered-passive), the search is restricted to clustered-passive resources only. If set to 4 (any), the cluster type does not affect the search."
	DEFVAL { 4 }
	::= { uxsA2ConfigFSysGroup 7 }

uxsA2ConfigFSysDescription OBJECT-TYPE
	SYNTAX DisplayString
	ACCESS read-write
	STATUS mandatory
	DESCRIPTION "&<caiUxsA2.236>Default description for the file system watcher to add."
	::= { uxsA2ConfigFSysGroup 8 }

uxsA2ConfigFSysAggLag OBJECT-TYPE
	SYNTAX INTEGER
	ACCESS read-write
	STATUS mandatory
	DESCRIPTION "&<caiUxsA2.237>Default aggregate lag setting for the file system watcher to add. Specifies the consecutive number of times at which any status is not in the ok state, before the aggregate status changes. This value must be greater than 0."
	DEFVAL { 3 }
	::= { uxsA2ConfigFSysGroup 9 }

uxsA2ConfigFSysTotalPolicy OBJECT-TYPE
	SYNTAX INTEGER {
		unprivileged-user(1),
		privileged-user(2)
	}
	ACCESS read-write
	STATUS mandatory
	DESCRIPTION "&<caiUxsA2.238>If set to privileged-user the Total Value of the file system includes the superuser reserve. For unprivileged-user the reserve is not included."
	DEFVAL { 1 }
	::= { uxsA2ConfigFSysGroup 10 }

uxsA2ConfigFSysSpaceWarn OBJECT-TYPE
	SYNTAX DisplayString
	ACCESS read-write
	STATUS mandatory
	DESCRIPTION "&<caiUxsA2.239>Default warning threshold, in megabytes, for the space utilization monitoring of the file system watcher to add. The active warning threshold is derived from this value and represents a rising threshold. The derived value must be greater than 0.0, less than or equal to the total value (maximum capacity) of the monitored resource as specified in uxsA2StatusFSysSpaceTotal, but cannot be greater than the active critical threshold. These constraints will be maintained by the agent during all configuration actions. The threshold can be specified as either an absolute value (n) or a percentage (n%). It can also be specified as the absolute value left free (nF). The value of uxsA2StatusFSysSpaceTotal will be the reference value for n% and nF notations."
	DEFVAL { "85.0%" }
	::= { uxsA2ConfigFSysGroup 11 }

uxsA2ConfigFSysSpaceCrit OBJECT-TYPE
	SYNTAX DisplayString
	ACCESS read-write
	STATUS mandatory
	DESCRIPTION "&<caiUxsA2.240>Default critical threshold, in megabytes, for the space utilization monitoring of the file system watcher to add. The active critical threshold is derived from this value and represents a rising threshold. The derived value must be greater than 0.0, less than or equal to the total value (maximum capacity) of the monitored resource as specified in uxsA2StatusFSysSpaceTotal, but cannot be less than the active warning threshold. These constraints will be maintained by the agent during all configuration actions. The threshold can be specified as either an absolute value (n) or a percentage (n%). It can also be specified as the absolute value left free (nF). The value of uxsA2StatusFSysSpaceTotal will be the reference value for n% and nF notations."
	DEFVAL { "95.0%" }
	::= { uxsA2ConfigFSysGroup 12 }

uxsA2ConfigFSysSpaceMonitor OBJECT-TYPE
	SYNTAX INTEGER {
		do-not-monitor(1),
		warning-only(2),
		critical-only(3),
		both(4)
	}
	ACCESS read-write
	STATUS mandatory
	DESCRIPTION "&<caiUxsA2.241>Default monitor level for the space utilization monitoring of the file system watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigFSysGroup 13 }

uxsA2ConfigFSysSpaceDWarn OBJECT-TYPE
	SYNTAX DisplayString
	ACCESS read-write
	STATUS mandatory
	DESCRIPTION "&<caiUxsA2.242>Default warning threshold, in kilobytes, for the delta space utilization monitoring of the file system watcher to add. The active warning threshold is derived from this value and represents a rising threshold. The derived value must be greater than 0.0, less than or equal to the total value (maximum capacity) of the monitored resource as specified in uxsA2StatusFSysSpaceTotal, but cannot be greater than the active critical threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusFSysSpaceTotal will be the reference value for n% notations."
	DEFVAL { "3.0%+" }
	::= { uxsA2ConfigFSysGroup 14 }

uxsA2ConfigFSysSpaceDCrit OBJECT-TYPE
	SYNTAX DisplayString
	ACCESS read-write
	STATUS mandatory
	DESCRIPTION "&<caiUxsA2.243>Default critical threshold, in kilobytes, for the delta space utilization monitoring of the file system watcher to add. The active critical threshold is derived from this value and represents a rising threshold. The derived value must be greater than 0.0, less than or equal to the total value (maximum capacity) of the monitored resource as specified in uxsA2StatusFSysSpaceTotal, but cannot be less than the active warning threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusFSysSpaceTotal will be the reference value for n% notations."
	DEFVAL { "5.0%+" }
	::= { uxsA2ConfigFSysGroup 15 }

uxsA2ConfigFSysSpaceDMonitor OBJECT-TYPE
	SYNTAX INTEGER {
		do-not-monitor(1),
		warning-only(2),
		critical-only(3),
		both(4)
	}
	ACCESS read-write
	STATUS mandatory
	DESCRIPTION "&<caiUxsA2.244>Default monitor level for the delta space utilization monitoring of the file system watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigFSysGroup 16 }

uxsA2ConfigFSysInodesWarn OBJECT-TYPE
	SYNTAX DisplayString
	ACCESS read-write
	STATUS mandatory
	DESCRIPTION "&<caiUxsA2.245>Default warning threshold for the inodes used monitoring of the file system watcher to add. The active warning threshold is derived from this value and represents a rising threshold. The derived value must be greater than 0.0, less than or equal to the total value (maximum capacity) of the monitored resource as specified in uxsA2StatusFSysInodesTotal, but cannot be greater than the active critical threshold. These constraints will be maintained by the agent during all configuration actions. The threshold can be specified as either an absolute value (n) or a percentage (n%). It can also be specified as the absolute value left free (nF). The value of uxsA2StatusFSysInodesTotal will be the reference value for n% and nF notations."
	DEFVAL { "85.0%" }
	::= { uxsA2ConfigFSysGroup 17 }

uxsA2ConfigFSysInodesCrit OBJECT-TYPE
	SYNTAX DisplayString
	ACCESS read-write
	STATUS mandatory
	DESCRIPTION "&<caiUxsA2.246>Default critical threshold for the inodes used monitoring of the file system watcher to add. The active critical threshold is derived from this value and represents a rising threshold. The derived value must be greater than 0.0, less than or equal to the total value (maximum capacity) of the monitored resource as specified in uxsA2StatusFSysInodesTotal, but cannot be less than the active warning threshold. These constraints will be maintained by the agent during all configuration actions. The threshold can be specified as either an absolute value (n) or a percentage (n%). It can also be specified as the absolute value left free (nF). The value of uxsA2StatusFSysInodesTotal will be the reference value for n% and nF notations."
	DEFVAL { "95.0%" }
	::= { uxsA2ConfigFSysGroup 18 }

uxsA2ConfigFSysInodesMonitor OBJECT-TYPE
	SYNTAX INTEGER {
		do-not-monitor(1),
		warning-only(2),
		critical-only(3),
		both(4)
	}
	ACCESS read-write
	STATUS mandatory
	DESCRIPTION "&<caiUxsA2.247>Default monitor level for the inodes used monitoring of the file system watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigFSysGroup 19 }

uxsA2ConfigFSysInodesDWarn OBJECT-TYPE
	SYNTAX DisplayString
	ACCESS read-write
	STATUS mandatory
	DESCRIPTION "&<caiUxsA2.248>Default warning threshold for the delta inodes used monitoring of the file system watcher to add. The active warning threshold is derived from this value and represents a rising threshold. The derived value must be greater than 0.0, less than or equal to the total value (maximum capacity) of the monitored resource as specified in uxsA2StatusFSysInodesTotal, but cannot be greater than the active critical threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusFSysInodesTotal will be the reference value for n% notations."
	DEFVAL { "3.0%+" }
	::= { uxsA2ConfigFSysGroup 20 }

uxsA2ConfigFSysInodesDCrit OBJECT-TYPE
	SYNTAX DisplayString
	ACCESS read-write
	STATUS mandatory
	DESCRIPTION "&<caiUxsA2.249>Default critical threshold for the delta inodes used monitoring of the file system watcher to add. The active critical threshold is derived from this value and represents a rising threshold. The derived value must be greater than 0.0, less than or equal to the total value (maximum capacity) of the monitored resource as specified in uxsA2StatusFSysInodesTotal, but cannot be less than the active warning threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusFSysInodesTotal will be the reference value for n% notations."
	DEFVAL { "5.0%+" }
	::= { uxsA2ConfigFSysGroup 21 }

uxsA2ConfigFSysInodesDMonitor OBJECT-TYPE
	SYNTAX INTEGER {
		do-not-monitor(1),
		warning-only(2),
		critical-only(3),
		both(4)
	}
	ACCESS read-write
	STATUS mandatory
	DESCRIPTION "&<caiUxsA2.250>Default monitor level for the delta inodes used monitoring of the file system watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigFSysGroup 22 }

uxsA2ConfigFSysMount OBJECT-TYPE
	SYNTAX INTEGER {
		should-be-mounted(1),
		should-not-be-mounted(2)
	}
	ACCESS read-write
	STATUS mandatory
	DESCRIPTION "&<caiUxsA2.251>Default monitor condition for the mount status monitoring of the file system watcher to add."
	DEFVAL { 1 }
	::= { uxsA2ConfigFSysGroup 23 }

uxsA2ConfigFSysMountMonitor OBJECT-TYPE
	SYNTAX INTEGER {
		do-not-monitor(1),
		down-warning(2),
		down-critical(3)
	}
	ACCESS read-write
	STATUS mandatory
	DESCRIPTION "&<caiUxsA2.252>Default monitor level for the mount status monitoring of the file system watcher to add. If set to 1 (do-not-monitor), the agent does not evaluate the actual state of the resource and sets the status to ok. If set to 2 (down-warning), the agent uses a warning severity if the resource is in bad condition. If set to 3 (down-critical), the agent uses a critical severity if the resource is in bad condition."
	DEFVAL { 3 }
	::= { uxsA2ConfigFSysGroup 24 }

uxsA2ConfigFSysLossAction OBJECT-TYPE
	SYNTAX INTEGER {
		remove(1),
		up(2),
		down-warning(3),
		down-critical(4)
	}
	ACCESS read-write
	STATUS mandatory
	DESCRIPTION "&<caiUxsA2.253>Default loss action for the file system watcher to add. Specifies the action to take if the monitored file system is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { uxsA2ConfigFSysGroup 25 }

uxsA2ConfigFSysAutoTableWatcherName OBJECT-TYPE
	SYNTAX DisplayString
	ACCESS read-write
	STATUS mandatory
	DESCRIPTION "&<caiUxsA2.254>Name of the file system auto watcher to add or remove."
	::= { uxsA2ConfigFSysGroup 26 }

uxsA2ConfigFSysAutoTableWatcherMatchType OBJECT-TYPE
	SYNTAX INTEGER {
		positive(1),
		negative(2)
	}
	ACCESS read-write
	STATUS mandatory
	DESCRIPTION "&<caiUxsA2.255>Default search algorithm for the file system auto watcher to add. The filter is the logical AND of all attributes used to identify or otherwise narrow down resources. If set to 1 (positive), the agent searches for file system resources that match the filter. If set to 2 (negative), the agent searches for file system resources that do not match the filter."
	DEFVAL { 1 }
	::= { uxsA2ConfigFSysGroup 27 }

uxsA2ConfigFSysAutoTableWatcherLimit OBJECT-TYPE
	SYNTAX INTEGER
	ACCESS read-write
	STATUS mandatory
	DESCRIPTION "&<caiUxsA2.256>Default minimum number of matches that causes a lock of the file system auto watcher to add."
	DEFVAL { 100 }
	::= { uxsA2ConfigFSysGroup 28 }

uxsA2ConfigFSysButton OBJECT-TYPE
	SYNTAX INTEGER {
		none(1),
		add(2),
		remove(3),
		add-auto(4),
		remove-auto(5)
	}
	ACCESS read-write
	STATUS mandatory
	DESCRIPTION "&<caiUxsA2.257>This attribute is used to add or remove the file system watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { uxsA2ConfigFSysGroup 29 }

uxsA2ConfigFSysAutoCount OBJECT-TYPE
	SYNTAX INTEGER
	ACCESS read-only
	STATUS mandatory
	DESCRIPTION "&<caiUxsA2.258>Number of auto watchers in the file system auto configuration table."
	::= { uxsA2ConfigFSysGroup 30 }

uxsA2ConfigFSysAutoLocked OBJECT-TYPE
	SYNTAX INTEGER
	ACCESS read-only
	STATUS mandatory
	DESCRIPTION "&<caiUxsA2.259>Number of auto watchers in the file system auto configuration table which are currently locked."
	::= { uxsA2ConfigFSysGroup 31 }

uxsA2ConfigFSysAutoTable OBJECT-TYPE
	SYNTAX SEQUENCE OF UxsA2ConfigFSysAutoEntry
	ACCESS not-accessible
	STATUS mandatory
	DESCRIPTION "&<caiUxsA2.260>Configuration table containing a list of file system auto watchers."
	::= { uxsA2ConfigFSysGroup 32 }

uxsA2ConfigFSysAutoEntry OBJECT-TYPE
	SYNTAX UxsA2ConfigFSysAutoEntry
	ACCESS not-accessible
	STATUS mandatory
	DESCRIPTION "&<caiUxsA2.261>Entry in the file system auto watcher configuration table."
	INDEX {
		uxsA2ConfigFSysAutoWatcherName
	}
	::= { uxsA2ConfigFSysAutoTable 1 }

UxsA2ConfigFSysAutoEntry ::= SEQUENCE {
	uxsA2ConfigFSysAutoWatcherName DisplayString,
	uxsA2ConfigFSysAutoName DisplayString,
	uxsA2ConfigFSysAutoRelatedTo DisplayString,
	uxsA2ConfigFSysAutoType DisplayString,
	uxsA2ConfigFSysAutoClusterType INTEGER,
	uxsA2ConfigFSysAutoDescription DisplayString,
	uxsA2ConfigFSysAutoWatcherMatchType INTEGER,
	uxsA2ConfigFSysAutoWatcherLimit INTEGER,
	uxsA2ConfigFSysAutoWatcherLastMatched INTEGER,
	uxsA2ConfigFSysAutoAggLag INTEGER,
	uxsA2ConfigFSysAutoTotalPolicy INTEGER,
	uxsA2ConfigFSysAutoSpaceWarn DisplayString,
	uxsA2ConfigFSysAutoSpaceCrit DisplayString,
	uxsA2ConfigFSysAutoSpaceMonitor INTEGER,
	uxsA2ConfigFSysAutoSpaceDWarn DisplayString,
	uxsA2ConfigFSysAutoSpaceDCrit DisplayString,
	uxsA2ConfigFSysAutoSpaceDMonitor INTEGER,
	uxsA2ConfigFSysAutoInodesWarn DisplayString,
	uxsA2ConfigFSysAutoInodesCrit DisplayString,
	uxsA2ConfigFSysAutoInodesMonitor INTEGER,
	uxsA2ConfigFSysAutoInodesDWarn DisplayString,
	uxsA2ConfigFSysAutoInodesDCrit DisplayString,
	uxsA2ConfigFSysAutoInodesDMonitor INTEGER,
	uxsA2ConfigFSysAutoMount INTEGER,
	uxsA2ConfigFSysAutoMountMonitor INTEGER,
	uxsA2ConfigFSysAutoLossAction INTEGER,
	uxsA2ConfigFSysAutoButton INTEGER
}

uxsA2ConfigFSysAutoWatcherName OBJECT-TYPE
	SYNTAX DisplayString
	ACCESS read-only
	STATUS mandatory
	DESCRIPTION "&<caiUxsA2.262>Name of the file system auto watcher."
	::= { uxsA2ConfigFSysAutoEntry 1 }

uxsA2ConfigFSysAutoName OBJECT-TYPE
	SYNTAX DisplayString
	ACCESS read-write
	STATUS mandatory
	DESCRIPTION "&<caiUxsA2.263>Name of the file system to be searched for during an auto discovery run. The name can constitute an extended regular expression pattern."
	::= { uxsA2ConfigFSysAutoEntry 2 }

uxsA2ConfigFSysAutoRelatedTo OBJECT-TYPE
	SYNTAX DisplayString
	ACCESS read-write
	STATUS mandatory
	DESCRIPTION "&<caiUxsA2.264>The device from which the file system is mounted. The name can constitute an extended regular expression pattern."
	::= { uxsA2ConfigFSysAutoEntry 3 }

uxsA2ConfigFSysAutoType OBJECT-TYPE
	SYNTAX DisplayString
	ACCESS read-write
	STATUS mandatory
	DESCRIPTION "&<caiUxsA2.265>The type of the mounted file system. The value is platform dependent."
	::= { uxsA2ConfigFSysAutoEntry 4 }

uxsA2ConfigFSysAutoClusterType OBJECT-TYPE
	SYNTAX INTEGER {
		not-clustered(1),
		clustered-active(2),
		clustered-passive(3),
		any(4)
	}
	ACCESS read-write
	STATUS mandatory
	DESCRIPTION "&<caiUxsA2.266>Cluster type of the file system to be searched for during an auto discovery run. If set to 1 (not-clustered), the search is restricted to not-clustered resources only. If set to 2 (clustered-active), the search is restricted to clustered-active resources only. If set to 3 (clustered-passive), the search is restricted to clustered-passive resources only. If set to 4 (any), the cluster type does not affect the search."
	DEFVAL { 0 }
	::= { uxsA2ConfigFSysAutoEntry 5 }

uxsA2ConfigFSysAutoDescription OBJECT-TYPE
	SYNTAX DisplayString
	ACCESS read-write
	STATUS mandatory
	DESCRIPTION "&<caiUxsA2.267>Current description for the file system auto watcher."
	::= { uxsA2ConfigFSysAutoEntry 6 }

uxsA2ConfigFSysAutoWatcherMatchType OBJECT-TYPE
	SYNTAX INTEGER {
		positive(1),
		negative(2)
	}
	ACCESS read-write
	STATUS mandatory
	DESCRIPTION "&<caiUxsA2.268>Current search algorithm for the file system auto watcher. The filter is the logical AND of all attributes used to identify or otherwise narrow down resources. If set to 1 (positive), the agent searches for file system resources that match the filter. If set to 2 (negative), the agent searches for file system resources that do not match the filter."
	DEFVAL { 0 }
	::= { uxsA2ConfigFSysAutoEntry 7 }

uxsA2ConfigFSysAutoWatcherLimit OBJECT-TYPE
	SYNTAX INTEGER
	ACCESS read-write
	STATUS mandatory
	DESCRIPTION "&<caiUxsA2.269>Current minimum number of matches that causes the file system auto watcher to be locked."
	::= { uxsA2ConfigFSysAutoEntry 8 }

uxsA2ConfigFSysAutoWatcherLastMatched OBJECT-TYPE
	SYNTAX INTEGER
	ACCESS read-only
	STATUS mandatory
	DESCRIPTION "&<caiUxsA2.270>Number of matches for the last file system auto discovery run."
	::= { uxsA2ConfigFSysAutoEntry 9 }

uxsA2ConfigFSysAutoAggLag OBJECT-TYPE
	SYNTAX INTEGER
	ACCESS read-write
	STATUS mandatory
	DESCRIPTION "&<caiUxsA2.271>Current lag setting for the file system auto watcher. Specifies the consecutive number of times at which any status is not in the ok state, before the aggregate status changes. This value must be greater than 0."
	::= { uxsA2ConfigFSysAutoEntry 10 }

uxsA2ConfigFSysAutoTotalPolicy OBJECT-TYPE
	SYNTAX INTEGER {
		unprivileged-user(1),
		privileged-user(2)
	}
	ACCESS read-write
	STATUS mandatory
	DESCRIPTION "&<caiUxsA2.272>If set to privileged-user the Total Value of the file system includes the superuser reserve. For unprivileged-user the reserve is not included."
	DEFVAL { 0 }
	::= { uxsA2ConfigFSysAutoEntry 11 }

uxsA2ConfigFSysAutoSpaceWarn OBJECT-TYPE
	SYNTAX DisplayString
	ACCESS read-write
	STATUS mandatory
	DESCRIPTION "&<caiUxsA2.273>Default warning threshold, in megabytes, for the space utilization monitoring of any file system watcher created by the auto watcher. The active warning threshold is derived from this value and represents a rising threshold. The derived value must be greater than 0.0, less than or equal to the total value (maximum capacity) of the monitored resource as specified in uxsA2StatusFSysSpaceTotal, but cannot be greater than the active critical threshold. These constraints will be maintained by the agent during all configuration actions. The threshold can be specified as either an absolute value (n) or a percentage (n%). It can also be specified as the absolute value left free (nF). The value of uxsA2StatusFSysSpaceTotal will be the reference value for n% and nF notations."
	::= { uxsA2ConfigFSysAutoEntry 12 }

uxsA2ConfigFSysAutoSpaceCrit OBJECT-TYPE
	SYNTAX DisplayString
	ACCESS read-write
	STATUS mandatory
	DESCRIPTION "&<caiUxsA2.274>Default critical threshold, in megabytes, for the space utilization monitoring of any file system watcher created by the auto watcher. The active critical threshold is derived from this value and represents a rising threshold. The derived value must be greater than 0.0, less than or equal to the total value (maximum capacity) of the monitored resource as specified in uxsA2StatusFSysSpaceTotal, but cannot be less than the active warning threshold. These constraints will be maintained by the agent during all configuration actions. The threshold can be specified as either an absolute value (n) or a percentage (n%). It can also be specified as the absolute value left free (nF). The value of uxsA2StatusFSysSpaceTotal will be the reference value for n% and nF notations."
	::= { uxsA2ConfigFSysAutoEntry 13 }

uxsA2ConfigFSysAutoSpaceMonitor OBJECT-TYPE
	SYNTAX INTEGER {
		do-not-monitor(1),
		warning-only(2),
		critical-only(3),
		both(4)
	}
	ACCESS read-write
	STATUS mandatory
	DESCRIPTION "&<caiUxsA2.275>Default monitor level for the space utilization monitoring of any file system watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2ConfigFSysAutoEntry 14 }

uxsA2ConfigFSysAutoSpaceDWarn OBJECT-TYPE
	SYNTAX DisplayString
	ACCESS read-write
	STATUS mandatory
	DESCRIPTION "&<caiUxsA2.276>Default warning threshold, in kilobytes, for the delta space utilization monitoring of any file system watcher created by the auto watcher. The active warning threshold is derived from this value and represents a rising threshold. The derived value must be greater than 0.0, less than or equal to the total value (maximum capacity) of the monitored resource as specified in uxsA2StatusFSysSpaceTotal, but cannot be greater than the active critical threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusFSysSpaceTotal will be the reference value for n% notations."
	::= { uxsA2ConfigFSysAutoEntry 15 }

uxsA2ConfigFSysAutoSpaceDCrit OBJECT-TYPE
	SYNTAX DisplayString
	ACCESS read-write
	STATUS mandatory
	DESCRIPTION "&<caiUxsA2.277>Default critical threshold, in kilobytes, for the delta space utilization monitoring of any file system watcher created by the auto watcher. The active critical threshold is derived from this value and represents a rising threshold. The derived value must be greater than 0.0, less than or equal to the total value (maximum capacity) of the monitored resource as specified in uxsA2StatusFSysSpaceTotal, but cannot be less than the active warning threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusFSysSpaceTotal will be the reference value for n% notations."
	::= { uxsA2ConfigFSysAutoEntry 16 }

uxsA2ConfigFSysAutoSpaceDMonitor OBJECT-TYPE
	SYNTAX INTEGER {
		do-not-monitor(1),
		warning-only(2),
		critical-only(3),
		both(4)
	}
	ACCESS read-write
	STATUS mandatory
	DESCRIPTION "&<caiUxsA2.278>Default monitor level for the delta space utilization monitoring of any file system watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2ConfigFSysAutoEntry 17 }

uxsA2ConfigFSysAutoInodesWarn OBJECT-TYPE
	SYNTAX DisplayString
	ACCESS read-write
	STATUS mandatory
	DESCRIPTION "&<caiUxsA2.279>Default warning threshold for the inodes used monitoring of any file system watcher created by the auto watcher. The active warning threshold is derived from this value and represents a rising threshold. The derived value must be greater than 0.0, less than or equal to the total value (maximum capacity) of the monitored resource as specified in uxsA2StatusFSysInodesTotal, but cannot be greater than the active critical threshold. These constraints will be maintained by the agent during all configuration actions. The threshold can be specified as either an absolute value (n) or a percentage (n%). It can also be specified as the absolute value left free (nF). The value of uxsA2StatusFSysInodesTotal will be the reference value for n% and nF notations."
	::= { uxsA2ConfigFSysAutoEntry 18 }

uxsA2ConfigFSysAutoInodesCrit OBJECT-TYPE
	SYNTAX DisplayString
	ACCESS read-write
	STATUS mandatory
	DESCRIPTION "&<caiUxsA2.280>Default critical threshold for the inodes used monitoring of any file system watcher created by the auto watcher. The active critical threshold is derived from this value and represents a rising threshold. The derived value must be greater than 0.0, less than or equal to the total value (maximum capacity) of the monitored resource as specified in uxsA2StatusFSysInodesTotal, but cannot be less than the active warning threshold. These constraints will be maintained by the agent during all configuration actions. The threshold can be specified as either an absolute value (n) or a percentage (n%). It can also be specified as the absolute value left free (nF). The value of uxsA2StatusFSysInodesTotal will be the reference value for n% and nF notations."
	::= { uxsA2ConfigFSysAutoEntry 19 }

uxsA2ConfigFSysAutoInodesMonitor OBJECT-TYPE
	SYNTAX INTEGER {
		do-not-monitor(1),
		warning-only(2),
		critical-only(3),
		both(4)
	}
	ACCESS read-write
	STATUS mandatory
	DESCRIPTION "&<caiUxsA2.281>Default monitor level for the inodes used monitoring of any file system watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2ConfigFSysAutoEntry 20 }

uxsA2ConfigFSysAutoInodesDWarn OBJECT-TYPE
	SYNTAX DisplayString
	ACCESS read-write
	STATUS mandatory
	DESCRIPTION "&<caiUxsA2.282>Default warning threshold for the delta inodes used monitoring of any file system watcher created by the auto watcher. The active warning threshold is derived from this value and represents a rising threshold. The derived value must be greater than 0.0, less than or equal to the total value (maximum capacity) of the monitored resource as specified in uxsA2StatusFSysInodesTotal, but cannot be greater than the active critical threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusFSysInodesTotal will be the reference value for n% notations."
	::= { uxsA2ConfigFSysAutoEntry 21 }

uxsA2ConfigFSysAutoInodesDCrit OBJECT-TYPE
	SYNTAX DisplayString
	ACCESS read-write
	STATUS mandatory
	DESCRIPTION "&<caiUxsA2.283>Default critical threshold for the delta inodes used monitoring of any file system watcher created by the auto watcher. The active critical threshold is derived from this value and represents a rising threshold. The derived value must be greater than 0.0, less than or equal to the total value (maximum capacity) of the monitored resource as specified in uxsA2StatusFSysInodesTotal, but cannot be less than the active warning threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusFSysInodesTotal will be the reference value for n% notations."
	::= { uxsA2ConfigFSysAutoEntry 22 }

uxsA2ConfigFSysAutoInodesDMonitor OBJECT-TYPE
	SYNTAX INTEGER {
		do-not-monitor(1),
		warning-only(2),
		critical-only(3),
		both(4)
	}
	ACCESS read-write
	STATUS mandatory
	DESCRIPTION "&<caiUxsA2.284>Default monitor level for the delta inodes used monitoring of any file system watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2ConfigFSysAutoEntry 23 }

uxsA2ConfigFSysAutoMount OBJECT-TYPE
	SYNTAX INTEGER {
		should-be-mounted(1),
		should-not-be-mounted(2)
	}
	ACCESS read-write
	STATUS mandatory
	DESCRIPTION "&<caiUxsA2.285>Default monitor condition for the mount status monitoring of any file system watcher created by the auto watcher."
	DEFVAL { 0 }
	::= { uxsA2ConfigFSysAutoEntry 24 }

uxsA2ConfigFSysAutoMountMonitor OBJECT-TYPE
	SYNTAX INTEGER {
		do-not-monitor(1),
		down-warning(2),
		down-critical(3)
	}
	ACCESS read-write
	STATUS mandatory
	DESCRIPTION "&<caiUxsA2.286>Default monitor level for the mount status monitoring of any file system watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2ConfigFSysAutoEntry 25 }

uxsA2ConfigFSysAutoLossAction OBJECT-TYPE
	SYNTAX INTEGER {
		remove(1),
		up(2),
		down-warning(3),
		down-critical(4)
	}
	ACCESS read-write
	STATUS mandatory
	DESCRIPTION "&<caiUxsA2.287>Default loss action for any file system watcher created by the auto watcher. Specifies the action to take if the monitored file system is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2ConfigFSysAutoEntry 26 }

uxsA2ConfigFSysAutoButton OBJECT-TYPE
	SYNTAX INTEGER {
		active(1),
		remove(2),
		locked(3)
	}
	ACCESS read-write
	STATUS mandatory
	DESCRIPTION "&<caiUxsA2.288>This attribute is used to enable/disable or remove the file system auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { uxsA2ConfigFSysAutoEntry 27 }

--
-- The ConfigFile Group
--

uxsA2ConfigFilePollInterval OBJECT-TYPE
	SYNTAX INTEGER
	ACCESS read-write
	STATUS mandatory
	DESCRIPTION "&<caiUxsA2.289>Time, in seconds, between collections of file information. Valid range: 30 seconds or greater."
	DEFVAL { 120 }
	::= { uxsA2ConfigFileGroup 1 }

uxsA2ConfigFilePollMethod OBJECT-TYPE
	SYNTAX INTEGER {
		disabled(1),
		poll-interval-only(2),
		poll-interval-and-query(3),
		query-only(4)
	}
	ACCESS read-write
	STATUS mandatory
	DESCRIPTION "&<caiUxsA2.290>Specifies how and when the agent collects file information. If set to 1 (disabled), the agent does not retrieve the file information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigFileGroup 2 }

uxsA2ConfigFileWatcherName OBJECT-TYPE
	SYNTAX DisplayString
	ACCESS read-write
	STATUS mandatory
	DESCRIPTION "&<caiUxsA2.291>The user-defined name which uniquely identifies the file watcher."
	::= { uxsA2ConfigFileGroup 3 }

uxsA2ConfigFileName OBJECT-TYPE
	SYNTAX DisplayString
	ACCESS read-write
	STATUS mandatory
	DESCRIPTION "&<caiUxsA2.292>Name of the file for which to add or remove a watcher. This name may contain environment variables. The attribute is used as a filter element for one-to-many monitoring (one watcher monitors several resources simultaneously). The file name (not the path) can be a regular expression."
	::= { uxsA2ConfigFileGroup 4 }

uxsA2ConfigFileEvalPolicy OBJECT-TYPE
	SYNTAX INTEGER {
		individual(1),
		min(2),
		max(3),
		sum(4),
		avg(5)
	}
	ACCESS read-write
	STATUS mandatory
	DESCRIPTION "&<caiUxsA2.293>Default evaluation policy for the file watcher. Defines how metric values will be calculated and 'culprits' be determined if two or more file resources fall into the monitoring scope of a one-to-many watcher. If set to 1 (individual), metric values will be set to the worst values (lowest and/or highest) of all file instances; if the value of a metric violates the threshold condition, the respective 'culprits' list will contain all instances individually violating the most severe threshold. If set to 2 (min), metric values will be set to the lowest (minimum) values of all file instances; if the value of a metric violates the threshold condition, the respective 'culprits' list will contain all instances having the same minimum value. If set to 3 (max), metric values will be set to the highest (maximum) values of all file instances; if the value of a metric violates the threshold condition, the respective 'culprits' list will contain all instances having the same maximum value. If set to 4 (sum), metric values will be set to the cumulative values (sum) of all file instances; if the value of a metric violates the threshold condition, the respective 'culprits' list will contain all instances. If set to 5 (avg), metric values will be set to the average values of all file instances; if the value of a metric violates the threshold condition, the respective 'culprits' list will contain all instances individually violating the most severe threshold."
	DEFVAL { 1 }
	::= { uxsA2ConfigFileGroup 5 }

uxsA2ConfigFileDescription OBJECT-TYPE
	SYNTAX DisplayString
	ACCESS read-write
	STATUS mandatory
	DESCRIPTION "&<caiUxsA2.294>Default description for the file watcher to add."
	::= { uxsA2ConfigFileGroup 6 }

uxsA2ConfigFileAggLag OBJECT-TYPE
	SYNTAX INTEGER
	ACCESS read-write
	STATUS mandatory
	DESCRIPTION "&<caiUxsA2.295>Default aggregate lag setting for the file watcher to add. Specifies the consecutive number of times at which any status is not in the ok state, before the aggregate status changes. This value must be greater than 0."
	DEFVAL { 2 }
	::= { uxsA2ConfigFileGroup 7 }

uxsA2ConfigFileInstMin OBJECT-TYPE
	SYNTAX DisplayString
	ACCESS read-write
	STATUS mandatory
	DESCRIPTION "&<caiUxsA2.296>Default minimum threshold for the instance count monitoring of the file watcher to add. This value represents a declining threshold and must be equal to or greater than 0.0, but cannot be greater than the maximum threshold. A value of -1 disables the evaluation of this threshold."
	DEFVAL { "1.0" }
	::= { uxsA2ConfigFileGroup 8 }

uxsA2ConfigFileInstMax OBJECT-TYPE
	SYNTAX DisplayString
	ACCESS read-write
	STATUS mandatory
	DESCRIPTION "&<caiUxsA2.297>Default maximum threshold for the instance count monitoring of the file watcher to add. This value represents a rising threshold and must be equal to or greater than 0.0, but cannot be less than the minimum threshold. A value of -1 disables the evaluation of this threshold."
	DEFVAL { "-1" }
	::= { uxsA2ConfigFileGroup 9 }

uxsA2ConfigFileInstMonitor OBJECT-TYPE
	SYNTAX INTEGER {
		do-not-monitor(1),
		down-warning(2),
		down-critical(3)
	}
	ACCESS read-write
	STATUS mandatory
	DESCRIPTION "&<caiUxsA2.298>Default monitor level for the instance count monitoring of the file watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { uxsA2ConfigFileGroup 10 }

uxsA2ConfigFileSizeWarnMin OBJECT-TYPE
	SYNTAX DisplayString
	ACCESS read-write
	STATUS mandatory
	DESCRIPTION "&<caiUxsA2.299>Default warning minimum threshold, in kilobytes, for the size utilization monitoring of the file watcher to add. This value represents a declining threshold and must be equal to or greater than 0.0, equal to or greater than the critical minimum threshold, but cannot be greater than the warning maximum threshold. A value of -1 disables the evaluation of this threshold. The threshold can be specified as either an absolute value (n) or a percentage (n%). The value of uxsA2StatusFileSizeTotal will be the reference value for n% notations."
	DEFVAL { "-1" }
	::= { uxsA2ConfigFileGroup 11 }

uxsA2ConfigFileSizeWarnMax OBJECT-TYPE
	SYNTAX DisplayString
	ACCESS read-write
	STATUS mandatory
	DESCRIPTION "&<caiUxsA2.300>Default warning maximum threshold, in kilobytes, for the size utilization monitoring of the file watcher to add. This value represents a rising threshold and must be equal to or greater than 0.0, equal to or greater than the warning minimum threshold, but cannot be greater than the critical maximum threshold. A value of -1 disables the evaluation of this threshold. The threshold can be specified as either an absolute value (n) or a percentage (n%). The value of uxsA2StatusFileSizeTotal will be the reference value for n% notations."
	DEFVAL { "150.0%" }
	::= { uxsA2ConfigFileGroup 12 }

uxsA2ConfigFileSizeCritMin OBJECT-TYPE
	SYNTAX DisplayString
	ACCESS read-write
	STATUS mandatory
	DESCRIPTION "&<caiUxsA2.301>Default critical minimum threshold, in kilobytes, for the size utilization monitoring of the file watcher to add. This value represents a declining threshold and must be equal to or greater than 0.0, but cannot be greater than the warning minimum threshold. A value of -1 disables the evaluation of this threshold. The threshold can be specified as either an absolute value (n) or a percentage (n%). The value of uxsA2StatusFileSizeTotal will be the reference value for n% notations."
	DEFVAL { "-1" }
	::= { uxsA2ConfigFileGroup 13 }

uxsA2ConfigFileSizeCritMax OBJECT-TYPE
	SYNTAX DisplayString
	ACCESS read-write
	STATUS mandatory
	DESCRIPTION "&<caiUxsA2.302>Default critical maximum threshold, in kilobytes, for the size utilization monitoring of the file watcher to add. This value represents a rising threshold and must be equal to or greater than 0.0, but cannot be less than the warning maximum threshold. A value of -1 disables the evaluation of this threshold. The threshold can be specified as either an absolute value (n) or a percentage (n%). The value of uxsA2StatusFileSizeTotal will be the reference value for n% notations."
	DEFVAL { "200.0%" }
	::= { uxsA2ConfigFileGroup 14 }

uxsA2ConfigFileSizeMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.303>Default monitor level for the size utilization monitoring of the file watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { uxsA2ConfigFileGroup 15 }

uxsA2ConfigFileSizeDWarn OBJECT-TYPE
	SYNTAX DisplayString
	ACCESS read-write
	STATUS mandatory
	DESCRIPTION "&<caiUxsA2.304>Default warning threshold, in kilobytes, for the delta size utilization monitoring of the file watcher to add. The active warning threshold is derived from this value and represents a rising threshold. The derived value must be greater than 0.0, but cannot be greater than the active critical threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusFileSizeTotal will be the reference value for n% notations."
	DEFVAL { "20.0%+" }
	::= { uxsA2ConfigFileGroup 16 }

uxsA2ConfigFileSizeDCrit OBJECT-TYPE
	SYNTAX DisplayString
	ACCESS read-write
	STATUS mandatory
	DESCRIPTION "&<caiUxsA2.305>Default critical threshold, in kilobytes, for the delta size utilization monitoring of the file watcher to add. The active critical threshold is derived from this value and represents a rising threshold. The derived value must be greater than 0.0, but cannot be less than the active warning threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of uxsA2StatusFileSizeTotal will be the reference value for n% notations."
	DEFVAL { "40.0%+" }
	::= { uxsA2ConfigFileGroup 17 }

uxsA2ConfigFileSizeDMonitor OBJECT-TYPE
	SYNTAX INTEGER {
		do-not-monitor(1),
		warning-only(2),
		critical-only(3),
		both(4)
	}
	ACCESS read-write
	STATUS mandatory
	DESCRIPTION "&<caiUxsA2.306>Default monitor level for the delta size utilization monitoring of the file watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigFileGroup 18 }

uxsA2ConfigFileModInterval OBJECT-TYPE
	SYNTAX DisplayString
	ACCESS read-write
	STATUS mandatory
	DESCRIPTION "&<caiUxsA2.307>The period in seconds to be considered for calculating status and value of the modification metric. For a value of zero the period is identical to the current poll interval."
	DEFVAL { "0" }
	::= { uxsA2ConfigFileGroup 19 }

uxsA2ConfigFileMod OBJECT-TYPE
	SYNTAX INTEGER {
		should-not-be-modified(1),
		should-not-be-changed(2),
		should-not-be-changed-only(3),
		should-not-be-accessed(4),
		should-be-modified(5),
		should-be-changed(6),
		should-be-changed-only(7),
		should-be-accessed(8)
	}
	ACCESS read-write
	STATUS mandatory
	DESCRIPTION "&<caiUxsA2.308>Default monitor condition for the modification monitoring of the file watcher to add. As basis for the comparison the user can choose between modification time, change time, change time only (change time is modified and modification time is not) and access time. The timestamps can be monitored for being modified (should-be-modified, should-be-changed, should-be-changed-only, should-be-accessed) or for being unmodified (should-not-be-modified, should-not-be-changed, should-not-be-changed-only, should-not-be-accessed). At each poll the current timestamp of the file will be compared with the reference timestamp according to the chosen policy. For one-to-many watchers the latest timestamp of all files is considered. If monitoring is for being modified the status is down if the file was not modified for more seconds than the value of 'FileModInterval'. If monitoring is for being unmodified the status is down if the file was modified more often than every 'FileModInterval' seconds. If 'FileModInterval' is zero any modification sets the status down. If the monitor status is 'down' and the monitoring condition is met at the next poll the status of the watcher will revert to up (automatic repair). However, the metric may be reset manually at any time by setting the monitor condition to reset-time-reference. Afterwards the previous policy setting is restored. Note: if the policy is set to should-not-xxx and 'FileModInterval' is 0, no automatic repair takes place. This behaviour is for compatibility with the old UNIX System Agent (caiUxOs). Note that status evaluation only takes place when the agent polls. Thus the end of the modification interval will be detected on the subsequent poll or query."
	DEFVAL { 1 }
	::= { uxsA2ConfigFileGroup 20 }

uxsA2ConfigFileModMonitor OBJECT-TYPE
	SYNTAX INTEGER {
		do-not-monitor(1),
		down-warning(2),
		down-critical(3)
	}
	ACCESS read-write
	STATUS mandatory
	DESCRIPTION "&<caiUxsA2.309>Default monitor level for the modification monitoring of the file watcher to add. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { uxsA2ConfigFileGroup 21 }

uxsA2ConfigFileButton OBJECT-TYPE
	SYNTAX INTEGER {
		none(1),
		add(2),
		remove(3)
	}
	ACCESS read-write
	STATUS mandatory
	DESCRIPTION "&<caiUxsA2.310>This attribute is used to add or remove the file watcher specified by the current setting of the watcher name attribute(s) in this group. If set to 2 (add), the agent adds the specified watcher to the status table using the current values of the remaining attributes as defaults. If set to 3 (remove), the agent removes the specified watcher from the status table. This attribute cannot be set to 1 (none)."
	DEFVAL { 1 }
	::= { uxsA2ConfigFileGroup 22 }

--
-- The ConfigDisk Group
--

uxsA2ConfigDiskPollInterval OBJECT-TYPE
	SYNTAX INTEGER
	ACCESS read-write
	STATUS mandatory
	DESCRIPTION "&<caiUxsA2.311>Time, in seconds, between collections of disk information. Valid range: 30 seconds or greater."
	DEFVAL { 120 }
	::= { uxsA2ConfigDiskGroup 1 }

uxsA2ConfigDiskPollMethod OBJECT-TYPE
	SYNTAX INTEGER {
		disabled(1),
		poll-interval-only(2),
		poll-interval-and-query(3),
		query-only(4)
	}
	ACCESS read-write
	STATUS mandatory
	DESCRIPTION "&<caiUxsA2.312>Specifies how and when the agent collects disk information. If set to 1 (disabled), the agent does not retrieve the disk information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigDiskGroup 2 }

uxsA2ConfigDiskAutoPollInterval OBJECT-TYPE
	SYNTAX INTEGER
	ACCESS read-write
	STATUS mandatory
	DESCRIPTION "&<caiUxsA2.313>Time, in minutes, between the processing of the disk auto watchers. Valid range: -1 (suspended), 30 minutes or greater."
	DEFVAL { 60 }
	::= { uxsA2ConfigDiskGroup 3 }

uxsA2ConfigDiskName OBJECT-TYPE
	SYNTAX DisplayString
	ACCESS read-write
	STATUS mandatory
	DESCRIPTION "&<caiUxsA2.314>Name of the disk for which to add or remove a watcher. When adding an auto watcher, the name can constitute an extended regular expression pattern."
	::= { uxsA2ConfigDiskGroup 4 }

uxsA2ConfigDiskDescriptiveName OBJECT-TYPE
	SYNTAX DisplayString
	ACCESS read-write
	STATUS mandatory
	DESCRIPTION "&<caiUxsA2.315>An arbitrary descriptive string. When adding an auto watcher, the string can constitute an extended regular expression pattern."
	DEFVAL { ".*" }
	::= { uxsA2ConfigDiskGroup 5 }

uxsA2ConfigDiskClusterType OBJECT-TYPE
	SYNTAX INTEGER {
		not-clustered(1),
		clustered-active(2),
		clustered-passive(3),
		any(4)
	}
	ACCESS read-write
	STATUS mandatory
	DESCRIPTION "&<caiUxsA2.316>Cluster type of the disk to be searched for during an auto discovery run. This attribute is only used when adding an auto watcher. If set to 1 (not-clustered), the search is restricted to not-clustered resources only. If set to 2 (clustered-active), the search is restricted to clustered-active resources only. If set to 3 (clustered-passive), the search is restricted to clustered-passive resources only. If set to 4 (any), the cluster type does not affect the search."
	DEFVAL { 4 }
	::= { uxsA2ConfigDiskGroup 6 }

uxsA2ConfigDiskDescription OBJECT-TYPE
	SYNTAX DisplayString
	ACCESS read-write
	STATUS mandatory
	DESCRIPTION "&<caiUxsA2.317>Default description for the disk watcher to add."
	::= { uxsA2ConfigDiskGroup 7 }

uxsA2ConfigDiskAggLag OBJECT-TYPE
	SYNTAX INTEGER
	ACCESS read-write
	STATUS mandatory
	DESCRIPTION "&<caiUxsA2.318>Default aggregate lag setting for the disk watcher to add. Specifies the consecutive number of times at which any status is not in the ok state, before the aggregate status changes. This value must be greater than 0."
	DEFVAL { 5 }
	::= { uxsA2ConfigDiskGroup 8 }

uxsA2ConfigDiskTputWarnMin OBJECT-TYPE
	SYNTAX DisplayString
	ACCESS read-write
	STATUS mandatory
	DESCRIPTION "&<caiUxsA2.319>Default warning minimum threshold, in kilobytes/s, for the disk throughput monitoring of the disk watcher to add. This value represents a declining threshold and must be equal to or greater than 0.0, equal to or greater than the critical minimum threshold, but cannot be greater than the warning maximum threshold. A value of -1 disables the evaluation of this threshold."
	DEFVAL { "-1" }
	::= { uxsA2ConfigDiskGroup 9 }

uxsA2ConfigDiskTputWarnMax OBJECT-TYPE
	SYNTAX DisplayString
	ACCESS read-write
	STATUS mandatory
	DESCRIPTION "&<caiUxsA2.320>Default warning maximum threshold, in kilobytes/s, for the disk throughput monitoring of the disk watcher to add. This value represents a rising threshold and must be equal to or greater than 0.0, equal to or greater than the warning minimum threshold, but cannot be greater than the critical maximum threshold. A value of -1 disables the evaluation of this threshold."
	DEFVAL { "3000.0" }
	::= { uxsA2ConfigDiskGroup 10 }

uxsA2ConfigDiskTputCritMin OBJECT-TYPE
	SYNTAX DisplayString
	ACCESS read-write
	STATUS mandatory
	DESCRIPTION "&<caiUxsA2.321>Default critical minimum threshold, in kilobytes/s, for the disk throughput monitoring of the disk watcher to add. This value represents a declining threshold and must be equal to or greater than 0.0, but cannot be greater than the warning minimum threshold. A value of -1 disables the evaluation of this threshold."
	DEFVAL { "-1" }
	::= { uxsA2ConfigDiskGroup 11 }

uxsA2ConfigDiskTputCritMax OBJECT-TYPE
	SYNTAX DisplayString
	ACCESS read-write
	STATUS mandatory
	DESCRIPTION "&<caiUxsA2.322>Default critical maximum threshold, in kilobytes/s, for the disk throughput monitoring of the disk watcher to add. This value represents a rising threshold and must be equal to or greater than 0.0, but cannot be less than the warning maximum threshold. A value of -1 disables the evaluation of this threshold."
	DEFVAL { "6000.0" }
	::= { uxsA2ConfigDiskGroup 12 }

uxsA2ConfigDiskTputMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.323>Default monitor level for the disk throughput monitoring of the disk watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { uxsA2ConfigDiskGroup 13 }

uxsA2ConfigDiskLossAction OBJECT-TYPE
	SYNTAX INTEGER {
		remove(1),
		up(2),
		down-warning(3),
		down-critical(4)
	}
	ACCESS read-write
	STATUS mandatory
	DESCRIPTION "&<caiUxsA2.324>Default loss action for the disk watcher to add. Specifies the action to take if the monitored disk is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { uxsA2ConfigDiskGroup 14 }

uxsA2ConfigDiskAutoTableWatcherName OBJECT-TYPE
	SYNTAX DisplayString
	ACCESS read-write
	STATUS mandatory
	DESCRIPTION "&<caiUxsA2.325>Name of the disk auto watcher to add or remove."
	::= { uxsA2ConfigDiskGroup 15 }

uxsA2ConfigDiskAutoTableWatcherMatchType OBJECT-TYPE
	SYNTAX INTEGER {
		positive(1),
		negative(2)
	}
	ACCESS read-write
	STATUS mandatory
	DESCRIPTION "&<caiUxsA2.326>Default search algorithm for the disk auto watcher to add. The filter is the logical AND of all attributes used to identify or otherwise narrow down resources. If set to 1 (positive), the agent searches for disk resources that match the filter. If set to 2 (negative), the agent searches for disk resources that do not match the filter."
	DEFVAL { 1 }
	::= { uxsA2ConfigDiskGroup 16 }

uxsA2ConfigDiskAutoTableWatcherLimit OBJECT-TYPE
	SYNTAX INTEGER
	ACCESS read-write
	STATUS mandatory
	DESCRIPTION "&<caiUxsA2.327>Default minimum number of matches that causes a lock of the disk auto watcher to add."
	DEFVAL { 100 }
	::= { uxsA2ConfigDiskGroup 17 }

uxsA2ConfigDiskButton OBJECT-TYPE
	SYNTAX INTEGER {
		none(1),
		add(2),
		remove(3),
		add-auto(4),
		remove-auto(5)
	}
	ACCESS read-write
	STATUS mandatory
	DESCRIPTION "&<caiUxsA2.328>This attribute is used to add or remove the disk watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { uxsA2ConfigDiskGroup 18 }

uxsA2ConfigDiskAutoCount OBJECT-TYPE
	SYNTAX INTEGER
	ACCESS read-only
	STATUS mandatory
	DESCRIPTION "&<caiUxsA2.329>Number of auto watchers in the disk auto configuration table."
	::= { uxsA2ConfigDiskGroup 19 }

uxsA2ConfigDiskAutoLocked OBJECT-TYPE
	SYNTAX INTEGER
	ACCESS read-only
	STATUS mandatory
	DESCRIPTION "&<caiUxsA2.330>Number of auto watchers in the disk auto configuration table which are currently locked."
	::= { uxsA2ConfigDiskGroup 20 }

uxsA2ConfigDiskAutoTable OBJECT-TYPE
	SYNTAX SEQUENCE OF UxsA2ConfigDiskAutoEntry
	ACCESS not-accessible
	STATUS mandatory
	DESCRIPTION "&<caiUxsA2.331>Configuration table containing a list of disk auto watchers."
	::= { uxsA2ConfigDiskGroup 21 }

uxsA2ConfigDiskAutoEntry OBJECT-TYPE
	SYNTAX UxsA2ConfigDiskAutoEntry
	ACCESS not-accessible
	STATUS mandatory
	DESCRIPTION "&<caiUxsA2.332>Entry in the disk auto watcher configuration table."
	INDEX {
		uxsA2ConfigDiskAutoWatcherName
	}
	::= { uxsA2ConfigDiskAutoTable 1 }

UxsA2ConfigDiskAutoEntry ::= SEQUENCE {
	uxsA2ConfigDiskAutoWatcherName DisplayString,
	uxsA2ConfigDiskAutoName DisplayString,
	uxsA2ConfigDiskAutoDescriptiveName DisplayString,
	uxsA2ConfigDiskAutoClusterType INTEGER,
	uxsA2ConfigDiskAutoDescription DisplayString,
	uxsA2ConfigDiskAutoWatcherMatchType INTEGER,
	uxsA2ConfigDiskAutoWatcherLimit INTEGER,
	uxsA2ConfigDiskAutoWatcherLastMatched INTEGER,
	uxsA2ConfigDiskAutoAggLag INTEGER,
	uxsA2ConfigDiskAutoTputWarnMin DisplayString,
	uxsA2ConfigDiskAutoTputWarnMax DisplayString,
	uxsA2ConfigDiskAutoTputCritMin DisplayString,
	uxsA2ConfigDiskAutoTputCritMax DisplayString,
	uxsA2ConfigDiskAutoTputMonitor INTEGER,
	uxsA2ConfigDiskAutoLossAction INTEGER,
	uxsA2ConfigDiskAutoButton INTEGER
}

uxsA2ConfigDiskAutoWatcherName OBJECT-TYPE
	SYNTAX DisplayString
	ACCESS read-only
	STATUS mandatory
	DESCRIPTION "&<caiUxsA2.333>Name of the disk auto watcher."
	::= { uxsA2ConfigDiskAutoEntry 1 }

uxsA2ConfigDiskAutoName OBJECT-TYPE
	SYNTAX DisplayString
	ACCESS read-write
	STATUS mandatory
	DESCRIPTION "&<caiUxsA2.334>Name of the disk to be searched for during an auto discovery run. The name can constitute an extended regular expression pattern."
	::= { uxsA2ConfigDiskAutoEntry 2 }

uxsA2ConfigDiskAutoDescriptiveName OBJECT-TYPE
	SYNTAX DisplayString
	ACCESS read-write
	STATUS mandatory
	DESCRIPTION "&<caiUxsA2.335>An arbitrary descriptive string. The name can constitute an extended regular expression pattern."
	::= { uxsA2ConfigDiskAutoEntry 3 }

uxsA2ConfigDiskAutoClusterType OBJECT-TYPE
	SYNTAX INTEGER {
		not-clustered(1),
		clustered-active(2),
		clustered-passive(3),
		any(4)
	}
	ACCESS read-write
	STATUS mandatory
	DESCRIPTION "&<caiUxsA2.336>Cluster type of the disk to be searched for during an auto discovery run. If set to 1 (not-clustered), the search is restricted to not-clustered resources only. If set to 2 (clustered-active), the search is restricted to clustered-active resources only. If set to 3 (clustered-passive), the search is restricted to clustered-passive resources only. If set to 4 (any), the cluster type does not affect the search."
	DEFVAL { 0 }
	::= { uxsA2ConfigDiskAutoEntry 4 }

uxsA2ConfigDiskAutoDescription OBJECT-TYPE
	SYNTAX DisplayString
	ACCESS read-write
	STATUS mandatory
	DESCRIPTION "&<caiUxsA2.337>Current description for the disk auto watcher."
	::= { uxsA2ConfigDiskAutoEntry 5 }

uxsA2ConfigDiskAutoWatcherMatchType OBJECT-TYPE
	SYNTAX INTEGER {
		positive(1),
		negative(2)
	}
	ACCESS read-write
	STATUS mandatory
	DESCRIPTION "&<caiUxsA2.338>Current search algorithm for the disk auto watcher. The filter is the logical AND of all attributes used to identify or otherwise narrow down resources. If set to 1 (positive), the agent searches for disk resources that match the filter. If set to 2 (negative), the agent searches for disk resources that do not match the filter."
	DEFVAL { 0 }
	::= { uxsA2ConfigDiskAutoEntry 6 }

uxsA2ConfigDiskAutoWatcherLimit OBJECT-TYPE
	SYNTAX INTEGER
	ACCESS read-write
	STATUS mandatory
	DESCRIPTION "&<caiUxsA2.339>Current minimum number of matches that causes the disk auto watcher to be locked."
	::= { uxsA2ConfigDiskAutoEntry 7 }

uxsA2ConfigDiskAutoWatcherLastMatched OBJECT-TYPE
	SYNTAX INTEGER
	ACCESS read-only
	STATUS mandatory
	DESCRIPTION "&<caiUxsA2.340>Number of matches for the last disk auto discovery run."
	::= { uxsA2ConfigDiskAutoEntry 8 }

uxsA2ConfigDiskAutoAggLag OBJECT-TYPE
	SYNTAX INTEGER
	ACCESS read-write
	STATUS mandatory
	DESCRIPTION "&<caiUxsA2.341>Current lag setting for the disk auto watcher. Specifies the consecutive number of times at which any status is not in the ok state, before the aggregate status changes. This value must be greater than 0."
	::= { uxsA2ConfigDiskAutoEntry 9 }

uxsA2ConfigDiskAutoTputWarnMin OBJECT-TYPE
	SYNTAX DisplayString
	ACCESS read-write
	STATUS mandatory
	DESCRIPTION "&<caiUxsA2.342>Default warning minimum threshold, in kilobytes/s, for the disk throughput monitoring of any disk watcher created by the auto watcher. This value represents a declining threshold and must be equal to or greater than 0.0, equal to or greater than the critical minimum threshold, but cannot be greater than the warning maximum threshold. A value of -1 disables the evaluation of this threshold."
	DEFVAL { "-2" }
	::= { uxsA2ConfigDiskAutoEntry 10 }

uxsA2ConfigDiskAutoTputWarnMax OBJECT-TYPE
	SYNTAX DisplayString
	ACCESS read-write
	STATUS mandatory
	DESCRIPTION "&<caiUxsA2.343>Default warning maximum threshold, in kilobytes/s, for the disk throughput monitoring of any disk watcher created by the auto watcher. This value represents a rising threshold and must be equal to or greater than 0.0, equal to or greater than the warning minimum threshold, but cannot be greater than the critical maximum threshold. A value of -1 disables the evaluation of this threshold."
	DEFVAL { "-2" }
	::= { uxsA2ConfigDiskAutoEntry 11 }

uxsA2ConfigDiskAutoTputCritMin OBJECT-TYPE
	SYNTAX DisplayString
	ACCESS read-write
	STATUS mandatory
	DESCRIPTION "&<caiUxsA2.344>Default critical minimum threshold, in kilobytes/s, for the disk throughput monitoring of any disk watcher created by the auto watcher. This value represents a declining threshold and must be equal to or greater than 0.0, but cannot be greater than the warning minimum threshold. A value of -1 disables the evaluation of this threshold."
	DEFVAL { "-2" }
	::= { uxsA2ConfigDiskAutoEntry 12 }

uxsA2ConfigDiskAutoTputCritMax OBJECT-TYPE
	SYNTAX DisplayString
	ACCESS read-write
	STATUS mandatory
	DESCRIPTION "&<caiUxsA2.345>Default critical maximum threshold, in kilobytes/s, for the disk throughput monitoring of any disk watcher created by the auto watcher. This value represents a rising threshold and must be equal to or greater than 0.0, but cannot be less than the warning maximum threshold. A value of -1 disables the evaluation of this threshold."
	DEFVAL { "-2" }
	::= { uxsA2ConfigDiskAutoEntry 13 }

uxsA2ConfigDiskAutoTputMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.346>Default monitor level for the disk throughput monitoring of any disk watcher created by the auto watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2ConfigDiskAutoEntry 14 }

uxsA2ConfigDiskAutoLossAction OBJECT-TYPE
	SYNTAX INTEGER {
		remove(1),
		up(2),
		down-warning(3),
		down-critical(4)
	}
	ACCESS read-write
	STATUS mandatory
	DESCRIPTION "&<caiUxsA2.347>Default loss action for any disk watcher created by the auto watcher. Specifies the action to take if the monitored disk is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2ConfigDiskAutoEntry 15 }

uxsA2ConfigDiskAutoButton OBJECT-TYPE
	SYNTAX INTEGER {
		active(1),
		remove(2),
		locked(3)
	}
	ACCESS read-write
	STATUS mandatory
	DESCRIPTION "&<caiUxsA2.348>This attribute is used to enable/disable or remove the disk auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { uxsA2ConfigDiskAutoEntry 16 }

--
-- The ConfigProc Group
--

uxsA2ConfigProcPollInterval OBJECT-TYPE
	SYNTAX INTEGER
	ACCESS read-write
	STATUS mandatory
	DESCRIPTION "&<caiUxsA2.349>Time, in seconds, between collections of process information. Valid range: 30 seconds or greater."
	DEFVAL { 120 }
	::= { uxsA2ConfigProcGroup 1 }

uxsA2ConfigProcPollMethod OBJECT-TYPE
	SYNTAX INTEGER {
		disabled(1),
		poll-interval-only(2),
		poll-interval-and-query(3),
		query-only(4)
	}
	ACCESS read-write
	STATUS mandatory
	DESCRIPTION "&<caiUxsA2.350>Specifies how and when the agent collects process information. If set to 1 (disabled), the agent does not retrieve the process information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigProcGroup 2 }

uxsA2ConfigProcWatcherName OBJECT-TYPE
	SYNTAX DisplayString
	ACCESS read-write
	STATUS mandatory
	DESCRIPTION "&<caiUxsA2.351>The default name of the process watcher. Because every process watcher must have assigned a unique watcher name this should normally be empty."
	::= { uxsA2ConfigProcGroup 3 }

uxsA2ConfigProcMatchType OBJECT-TYPE
	SYNTAX INTEGER {
		positive-regular-expression(1),
		negative-regular-expression(2),
		positive-compare(3),
		negative-compare(4)
	}
	ACCESS read-write
	STATUS mandatory
	DESCRIPTION "&<caiUxsA2.352>Default search algorithm for the process watcher. The filter is the logical AND of all attributes used to identify or otherwise narrow down resources. If the value of one of these attributes includes 'wildcards', then the watcher will basically behave like a one-to-many watcher, i.e. it may monitor two or more resources simultaneously. If set to 1 (positive-regular-expression), the agent searches for process resources that match the filter. Each of the filter attributes can denote an extended regular expression. If set to 2 (negative-regular-expression), the agent searches for process resources that do not match the filter. Each of the filter attributes can denote an extended regular expression. If set to 3 (positive-compare), the agent searches for process resources that match the filter. Each of the filter attributes specifies a substring to match from the beginning. If set to 4 (negative-compare), the agent searches for process resources that do not match the filter. Each of the filter attributes specifies a substring to match from the beginning."
	DEFVAL { 1 }
	::= { uxsA2ConfigProcGroup 4 }

uxsA2ConfigProcName OBJECT-TYPE
	SYNTAX DisplayString
	ACCESS read-write
	STATUS mandatory
	DESCRIPTION "&<caiUxsA2.353>The default filter condition for matching the names of the processes. Matches as specified in match type."
	DEFVAL { ".*" }
	::= { uxsA2ConfigProcGroup 5 }

uxsA2ConfigProcPath OBJECT-TYPE
	SYNTAX DisplayString
	ACCESS read-write
	STATUS mandatory
	DESCRIPTION "&<caiUxsA2.354>The default filter condition for matching the pathes of the processes. Matches as specified in match type."
	DEFVAL { ".*" }
	::= { uxsA2ConfigProcGroup 6 }

uxsA2ConfigProcArgs OBJECT-TYPE
	SYNTAX DisplayString
	ACCESS read-write
	STATUS mandatory
	DESCRIPTION "&<caiUxsA2.355>The default filter condition for matching the arguments of the processes. Matches as specified in match type."
	DEFVAL { ".*" }
	::= { uxsA2ConfigProcGroup 7 }

uxsA2ConfigProcUser OBJECT-TYPE
	SYNTAX DisplayString
	ACCESS read-write
	STATUS mandatory
	DESCRIPTION "&<caiUxsA2.356>The default filter condition for matching the owners of the processes. Matches as specified in match type. On Solaris 10 machines the name of the zone the process belongs to can be added to the attribute: <user>@<zone>. User and zone are evaluated as separate regular expressions. When no zone is specified the expression matches processes in the current zone only (<user>@<current>)."
	DEFVAL { ".*" }
	::= { uxsA2ConfigProcGroup 8 }

uxsA2ConfigProcEvalPolicy OBJECT-TYPE
	SYNTAX INTEGER {
		individual(1),
		min(2),
		max(3),
		sum(4),
		avg(5)
	}
	ACCESS read-write
	STATUS mandatory
	DESCRIPTION "&<caiUxsA2.357>Default evaluation policy for the process watcher. Defines how metric values will be calculated and 'culprits' be determined if two or more process resources fall into the monitoring scope of a one-to-many watcher. If set to 1 (individual), metric values will be set to the worst values (lowest and/or highest) of all process instances; if the value of a metric violates the threshold condition, the respective 'culprits' list will contain all instances individually violating the most severe threshold. If set to 2 (min), metric values will be set to the lowest (minimum) values of all process instances; if the value of a metric violates the threshold condition, the respective 'culprits' list will contain all instances having the same minimum value. If set to 3 (max), metric values will be set to the highest (maximum) values of all process instances; if the value of a metric violates the threshold condition, the respective 'culprits' list will contain all instances having the same maximum value. If set to 4 (sum), metric values will be set to the cumulative values (sum) of all process instances; if the value of a metric violates the threshold condition, the respective 'culprits' list will contain all instances. If set to 5 (avg), metric values will be set to the average values of all process instances; if the value of a metric violates the threshold condition, the respective 'culprits' list will contain all instances individually violating the most severe threshold."
	DEFVAL { 1 }
	::= { uxsA2ConfigProcGroup 9 }

uxsA2ConfigProcClusterResourceGroup OBJECT-TYPE
	SYNTAX DisplayString
	ACCESS read-write
	STATUS mandatory
	DESCRIPTION "&<caiUxsA2.358>Name of the cluster resource group of the process. For an unclustered process it is set to '-'."
	DEFVAL { "-" }
	::= { uxsA2ConfigProcGroup 10 }

uxsA2ConfigProcDescription OBJECT-TYPE
	SYNTAX DisplayString
	ACCESS read-write
	STATUS mandatory
	DESCRIPTION "&<caiUxsA2.359>Default description for the process watcher to add."
	::= { uxsA2ConfigProcGroup 11 }

uxsA2ConfigProcAggLag OBJECT-TYPE
	SYNTAX INTEGER
	ACCESS read-write
	STATUS mandatory
	DESCRIPTION "&<caiUxsA2.360>Default aggregate lag setting for the process watcher to add. Specifies the consecutive number of times at which any status is not in the ok state, before the aggregate status changes. This value must be greater than 0."
	DEFVAL { 3 }
	::= { uxsA2ConfigProcGroup 12 }

uxsA2ConfigProcInstMin OBJECT-TYPE
	SYNTAX INTEGER
	ACCESS read-write
	STATUS mandatory
	DESCRIPTION "&<caiUxsA2.361>Default minimum threshold for the instance count monitoring of the process watcher to add. This value represents a declining threshold and must be equal to or greater than 0, but cannot be greater than the maximum threshold. A value of -1 disables the evaluation of this threshold."
	DEFVAL { 1 }
	::= { uxsA2ConfigProcGroup 13 }

uxsA2ConfigProcInstMax OBJECT-TYPE
	SYNTAX INTEGER
	ACCESS read-write
	STATUS mandatory
	DESCRIPTION "&<caiUxsA2.362>Default maximum threshold for the instance count monitoring of the process watcher to add. This value represents a rising threshold and must be equal to or greater than 0, but cannot be less than the minimum threshold. A value of -1 disables the evaluation of this threshold."
	DEFVAL { -1 }
	::= { uxsA2ConfigProcGroup 14 }

uxsA2ConfigProcInstMonitor OBJECT-TYPE
	SYNTAX INTEGER {
		do-not-monitor(1),
		down-warning(2),
		down-critical(3)
	}
	ACCESS read-write
	STATUS mandatory
	DESCRIPTION "&<caiUxsA2.363>Default monitor level for the instance count monitoring of the process watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { uxsA2ConfigProcGroup 15 }

uxsA2ConfigProcChildMin OBJECT-TYPE
	SYNTAX INTEGER
	ACCESS read-write
	STATUS mandatory
	DESCRIPTION "&<caiUxsA2.364>Default minimum threshold for the number of children monitoring of the process watcher to add. This value represents a declining threshold and must be equal to or greater than 0, but cannot be greater than the maximum threshold. A value of -1 disables the evaluation of this threshold."
	DEFVAL { -1 }
	::= { uxsA2ConfigProcGroup 16 }

uxsA2ConfigProcChildMax OBJECT-TYPE
	SYNTAX INTEGER
	ACCESS read-write
	STATUS mandatory
	DESCRIPTION "&<caiUxsA2.365>Default maximum threshold for the number of children monitoring of the process watcher to add. This value represents a rising threshold and must be equal to or greater than 0, but cannot be less than the minimum threshold. A value of -1 disables the evaluation of this threshold."
	DEFVAL { -1 }
	::= { uxsA2ConfigProcGroup 17 }

uxsA2ConfigProcChildMonitor OBJECT-TYPE
	SYNTAX INTEGER {
		do-not-monitor(1),
		down-warning(2),
		down-critical(3)
	}
	ACCESS read-write
	STATUS mandatory
	DESCRIPTION "&<caiUxsA2.366>Default monitor level for the number of children monitoring of the process watcher to add. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { uxsA2ConfigProcGroup 18 }

uxsA2ConfigProcThreadMin OBJECT-TYPE
	SYNTAX INTEGER
	ACCESS read-write
	STATUS mandatory
	DESCRIPTION "&<caiUxsA2.367>Default minimum threshold for the number of threads monitoring of the process watcher to add. This value represents a declining threshold and must be equal to or greater than 0, but cannot be greater than the maximum threshold. A value of -1 disables the evaluation of this threshold."
	DEFVAL { -1 }
	::= { uxsA2ConfigProcGroup 19 }

uxsA2ConfigProcThreadMax OBJECT-TYPE
	SYNTAX INTEGER
	ACCESS read-write
	STATUS mandatory
	DESCRIPTION "&<caiUxsA2.368>Default maximum threshold for the number of threads monitoring of the process watcher to add. This value represents a rising threshold and must be equal to or greater than 0, but cannot be less than the minimum threshold. A value of -1 disables the evaluation of this threshold."
	DEFVAL { -1 }
	::= { uxsA2ConfigProcGroup 20 }

uxsA2ConfigProcThreadMonitor OBJECT-TYPE
	SYNTAX INTEGER {
		do-not-monitor(1),
		down-warning(2),
		down-critical(3)
	}
	ACCESS read-write
	STATUS mandatory
	DESCRIPTION "&<caiUxsA2.369>Default monitor level for the number of threads monitoring of the process watcher to add. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { uxsA2ConfigProcGroup 21 }

uxsA2ConfigProcSizeMin OBJECT-TYPE
	SYNTAX INTEGER
	ACCESS read-write
	STATUS mandatory
	DESCRIPTION "&<caiUxsA2.370>Default minimum threshold, in kilobytes, for the size monitoring of the process watcher to add. This value represents a declining threshold and must be equal to or greater than 0, but cannot be greater than the maximum threshold. A value of -1 disables the evaluation of this threshold."
	DEFVAL { -1 }
	::= { uxsA2ConfigProcGroup 22 }

uxsA2ConfigProcSizeMax OBJECT-TYPE
	SYNTAX INTEGER
	ACCESS read-write
	STATUS mandatory
	DESCRIPTION "&<caiUxsA2.371>Default maximum threshold, in kilobytes, for the size monitoring of the process watcher to add. This value represents a rising threshold and must be equal to or greater than 0, but cannot be less than the minimum threshold. A value of -1 disables the evaluation of this threshold."
	DEFVAL { 150000 }
	::= { uxsA2ConfigProcGroup 23 }

uxsA2ConfigProcSizeMonitor OBJECT-TYPE
	SYNTAX INTEGER {
		do-not-monitor(1),
		down-warning(2),
		down-critical(3)
	}
	ACCESS read-write
	STATUS mandatory
	DESCRIPTION "&<caiUxsA2.372>Default monitor level for the size monitoring of the process watcher to add. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { uxsA2ConfigProcGroup 24 }

uxsA2ConfigProcCpuUtilWarnMin OBJECT-TYPE
	SYNTAX DisplayString
	ACCESS read-write
	STATUS mandatory
	DESCRIPTION "&<caiUxsA2.373>Default warning minimum threshold, in seconds, for the per poll CPU usage monitoring of the process watcher to add. This value represents a declining threshold and must be equal to or greater than 0.0, less than or equal to the total value (maximum capacity) of the monitored resource as specified in uxsA2StatusProcCpuUtilInterval, equal to or greater than the critical minimum threshold, but cannot be greater than the warning maximum threshold. A value of -1 disables the evaluation of this threshold. The threshold can be specified as either an absolute value (n) or a percentage (n%). The value of uxsA2StatusProcCpuUtilInterval will be the reference value for n% notations."
	DEFVAL { "-1" }
	::= { uxsA2ConfigProcGroup 25 }

uxsA2ConfigProcCpuUtilWarnMax OBJECT-TYPE
	SYNTAX DisplayString
	ACCESS read-write
	STATUS mandatory
	DESCRIPTION "&<caiUxsA2.374>Default warning maximum threshold, in seconds, for the per poll CPU usage monitoring of the process watcher to add. This value represents a rising threshold and must be equal to or greater than 0.0, less than or equal to the total value (maximum capacity) of the monitored resource as specified in uxsA2StatusProcCpuUtilInterval, equal to or greater than the warning minimum threshold, but cannot be greater than the critical maximum threshold. A value of -1 disables the evaluation of this threshold. The threshold can be specified as either an absolute value (n) or a percentage (n%). The value of uxsA2StatusProcCpuUtilInterval will be the reference value for n% notations."
	DEFVAL { "40.0%" }
	::= { uxsA2ConfigProcGroup 26 }

uxsA2ConfigProcCpuUtilCritMin OBJECT-TYPE
	SYNTAX DisplayString
	ACCESS read-write
	STATUS mandatory
	DESCRIPTION "&<caiUxsA2.375>Default critical minimum threshold, in seconds, for the per poll CPU usage monitoring of the process watcher to add. This value represents a declining threshold and must be equal to or greater than 0.0, less than or equal to the total value (maximum capacity) of the monitored resource as specified in uxsA2StatusProcCpuUtilInterval, but cannot be greater than the warning minimum threshold. A value of -1 disables the evaluation of this threshold. The threshold can be specified as either an absolute value (n) or a percentage (n%). The value of uxsA2StatusProcCpuUtilInterval will be the reference value for n% notations."
	DEFVAL { "-1" }
	::= { uxsA2ConfigProcGroup 27 }

uxsA2ConfigProcCpuUtilCritMax OBJECT-TYPE
	SYNTAX DisplayString
	ACCESS read-write
	STATUS mandatory
	DESCRIPTION "&<caiUxsA2.376>Default critical maximum threshold, in seconds, for the per poll CPU usage monitoring of the process watcher to add. This value represents a rising threshold and must be equal to or greater than 0.0, less than or equal to the total value (maximum capacity) of the monitored resource as specified in uxsA2StatusProcCpuUtilInterval, but cannot be less than the warning maximum threshold. A value of -1 disables the evaluation of this threshold. The threshold can be specified as either an absolute value (n) or a percentage (n%). The value of uxsA2StatusProcCpuUtilInterval will be the reference value for n% notations."
	DEFVAL { "70.0%" }
	::= { uxsA2ConfigProcGroup 28 }

uxsA2ConfigProcCpuUtilMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.377>Default monitor level for the per poll CPU usage monitoring of the process watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 1 }
	::= { uxsA2ConfigProcGroup 29 }

uxsA2ConfigProcCpuUtilLongtermInterval OBJECT-TYPE
	SYNTAX DisplayString
	ACCESS read-write
	STATUS mandatory
	DESCRIPTION "&<caiUxsA2.378>Default time, in seconds, defining the total value to use as base for the calculation of the cpu value. This means, the cpu usage of a process, in seconds, refers to this interval. Valid range: Greater 0 or '-1'. If set to '-1', the cpu value is calculated as the cpu usage, in seconds, used up to now since the start of the agent or the creation of the watcher. If this interval is set to a value greater than the current poll interval and this time is not elapsed for the first time, the CPU value is extrapolated. If this interval is set to a value smaller than the current poll interval, the CPU value is calculated as the appropriate fraction of the value for the last poll interval. If this interval is set to a value greater than the current poll interval and this time is already elapsed, the CPU value is calculated as the sliding sum, i.e. the sum of the value for the current poll interval and the value calculated at the last poll, weighted according to it's fraction of this interval. If the interval is set to '-1', any overloading (%) used for the thresholds will be ignored."
	DEFVAL { "1800" }
	::= { uxsA2ConfigProcGroup 30 }

uxsA2ConfigProcCpuUtilLongtermWarnMin OBJECT-TYPE
	SYNTAX DisplayString
	ACCESS read-write
	STATUS mandatory
	DESCRIPTION "&<caiUxsA2.379>Default warning minimum threshold, in seconds, for the long-term CPU usage monitoring of the process watcher to add. This value represents a declining threshold and must be equal to or greater than 0.0, less than or equal to the total value (maximum capacity) of the monitored resource as specified in uxsA2StatusProcCpuUtilLongtermInterval, equal to or greater than the critical minimum threshold, but cannot be greater than the warning maximum threshold. A value of -1 disables the evaluation of this threshold. The threshold can be specified as either an absolute value (n) or a percentage (n%). The value of uxsA2StatusProcCpuUtilLongtermInterval will be the reference value for n% notations."
	DEFVAL { "-1" }
	::= { uxsA2ConfigProcGroup 31 }

uxsA2ConfigProcCpuUtilLongtermWarnMax OBJECT-TYPE
	SYNTAX DisplayString
	ACCESS read-write
	STATUS mandatory
	DESCRIPTION "&<caiUxsA2.380>Default warning maximum threshold, in seconds, for the long-term CPU usage monitoring of the process watcher to add. This value represents a rising threshold and must be equal to or greater than 0.0, less than or equal to the total value (maximum capacity) of the monitored resource as specified in uxsA2StatusProcCpuUtilLongtermInterval, equal to or greater than the warning minimum threshold, but cannot be greater than the critical maximum threshold. A value of -1 disables the evaluation of this threshold. The threshold can be specified as either an absolute value (n) or a percentage (n%). The value of uxsA2StatusProcCpuUtilLongtermInterval will be the reference value for n% notations."
	DEFVAL { "20.0%" }
	::= { uxsA2ConfigProcGroup 32 }

uxsA2ConfigProcCpuUtilLongtermCritMin OBJECT-TYPE
	SYNTAX DisplayString
	ACCESS read-write
	STATUS mandatory
	DESCRIPTION "&<caiUxsA2.381>Default critical minimum threshold, in seconds, for the long-term CPU usage monitoring of the process watcher to add. This value represents a declining threshold and must be equal to or greater than 0.0, less than or equal to the total value (maximum capacity) of the monitored resource as specified in uxsA2StatusProcCpuUtilLongtermInterval, but cannot be greater than the warning minimum threshold. A value of -1 disables the evaluation of this threshold. The threshold can be specified as either an absolute value (n) or a percentage (n%). The value of uxsA2StatusProcCpuUtilLongtermInterval will be the reference value for n% notations."
	DEFVAL { "-1" }
	::= { uxsA2ConfigProcGroup 33 }

uxsA2ConfigProcCpuUtilLongtermCritMax OBJECT-TYPE
	SYNTAX DisplayString
	ACCESS read-write
	STATUS mandatory
	DESCRIPTION "&<caiUxsA2.382>Default critical maximum threshold, in seconds, for the long-term CPU usage monitoring of the process watcher to add. This value represents a rising threshold and must be equal to or greater than 0.0, less than or equal to the total value (maximum capacity) of the monitored resource as specified in uxsA2StatusProcCpuUtilLongtermInterval, but cannot be less than the warning maximum threshold. A value of -1 disables the evaluation of this threshold. The threshold can be specified as either an absolute value (n) or a percentage (n%). The value of uxsA2StatusProcCpuUtilLongtermInterval will be the reference value for n% notations."
	DEFVAL { "50.0%" }
	::= { uxsA2ConfigProcGroup 34 }

uxsA2ConfigProcCpuUtilLongtermMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.383>Default monitor level for the long-term CPU usage monitoring of the process watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { uxsA2ConfigProcGroup 35 }

uxsA2ConfigProcRestart OBJECT-TYPE
	SYNTAX INTEGER {
		should-be-restarted(1),
		should-not-be-restarted(2)
	}
	ACCESS read-write
	STATUS mandatory
	DESCRIPTION "&<caiUxsA2.384>Default monitor condition for the restart policy monitoring of the process watcher to add."
	DEFVAL { 2 }
	::= { uxsA2ConfigProcGroup 36 }

uxsA2ConfigProcRestartMonitor OBJECT-TYPE
	SYNTAX INTEGER {
		do-not-monitor(1),
		down-warning(2),
		down-critical(3)
	}
	ACCESS read-write
	STATUS mandatory
	DESCRIPTION "&<caiUxsA2.385>Default monitor level for the restart policy monitoring of the process watcher to add. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { uxsA2ConfigProcGroup 37 }

uxsA2ConfigProcButton OBJECT-TYPE
	SYNTAX INTEGER {
		none(1),
		add(2),
		remove(3)
	}
	ACCESS read-write
	STATUS mandatory
	DESCRIPTION "&<caiUxsA2.386>This attribute is used to add or remove the process watcher specified by the current setting of the watcher name attribute(s) in this group. If set to 2 (add), the agent adds the specified watcher to the status table using the current values of the remaining attributes as defaults. If set to 3 (remove), the agent removes the specified watcher from the status table. This attribute cannot be set to 1 (none)."
	DEFVAL { 1 }
	::= { uxsA2ConfigProcGroup 38 }

--
-- The ConfigPrn Group
--

uxsA2ConfigPrnPollInterval OBJECT-TYPE
	SYNTAX INTEGER
	ACCESS read-write
	STATUS mandatory
	DESCRIPTION "&<caiUxsA2.387>Time, in seconds, between collections of print queue information. Valid range: 30 seconds or greater."
	DEFVAL { 120 }
	::= { uxsA2ConfigPrnGroup 1 }

uxsA2ConfigPrnPollMethod OBJECT-TYPE
	SYNTAX INTEGER {
		disabled(1),
		poll-interval-only(2),
		poll-interval-and-query(3),
		query-only(4)
	}
	ACCESS read-write
	STATUS mandatory
	DESCRIPTION "&<caiUxsA2.388>Specifies how and when the agent collects print queue information. If set to 1 (disabled), the agent does not retrieve the print queue information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigPrnGroup 2 }

uxsA2ConfigPrnAutoPollInterval OBJECT-TYPE
	SYNTAX INTEGER
	ACCESS read-write
	STATUS mandatory
	DESCRIPTION "&<caiUxsA2.389>Time, in minutes, between the processing of the print queue auto watchers. Valid range: -1 (suspended), 30 minutes or greater."
	DEFVAL { 60 }
	::= { uxsA2ConfigPrnGroup 3 }

uxsA2ConfigPrnName OBJECT-TYPE
	SYNTAX DisplayString
	ACCESS read-write
	STATUS mandatory
	DESCRIPTION "&<caiUxsA2.390>Name of the print queue for which to add or remove a watcher. When adding an auto watcher, the name can constitute an extended regular expression pattern."
	::= { uxsA2ConfigPrnGroup 4 }

uxsA2ConfigPrnDescription OBJECT-TYPE
	SYNTAX DisplayString
	ACCESS read-write
	STATUS mandatory
	DESCRIPTION "&<caiUxsA2.391>Default description for the print queue watcher to add."
	::= { uxsA2ConfigPrnGroup 5 }

uxsA2ConfigPrnAggLag OBJECT-TYPE
	SYNTAX INTEGER
	ACCESS read-write
	STATUS mandatory
	DESCRIPTION "&<caiUxsA2.392>Default aggregate lag setting for the print queue watcher to add. Specifies the consecutive number of times at which any status is not in the ok state, before the aggregate status changes. This value must be greater than 0."
	DEFVAL { 3 }
	::= { uxsA2ConfigPrnGroup 6 }

uxsA2ConfigPrnQueueUtilWarn OBJECT-TYPE
	SYNTAX INTEGER
	ACCESS read-write
	STATUS mandatory
	DESCRIPTION "&<caiUxsA2.393>Default warning threshold for the print queue utilization monitoring of the print queue watcher to add. This value represents a rising threshold and must be greater than 0, but cannot be greater than the critical threshold."
	DEFVAL { 100 }
	::= { uxsA2ConfigPrnGroup 7 }

uxsA2ConfigPrnQueueUtilCrit OBJECT-TYPE
	SYNTAX INTEGER
	ACCESS read-write
	STATUS mandatory
	DESCRIPTION "&<caiUxsA2.394>Default critical threshold for the print queue utilization monitoring of the print queue watcher to add. This value represents a rising threshold and must be greater than 0, but cannot be less than the warning threshold."
	DEFVAL { 200 }
	::= { uxsA2ConfigPrnGroup 8 }

uxsA2ConfigPrnQueueUtilMonitor OBJECT-TYPE
	SYNTAX INTEGER {
		do-not-monitor(1),
		warning-only(2),
		critical-only(3),
		both(4)
	}
	ACCESS read-write
	STATUS mandatory
	DESCRIPTION "&<caiUxsA2.395>Default monitor level for the print queue utilization monitoring of the print queue watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigPrnGroup 9 }

uxsA2ConfigPrnPrinterMonitor OBJECT-TYPE
	SYNTAX INTEGER {
		do-not-monitor(1),
		down-warning(2),
		down-critical(3)
	}
	ACCESS read-write
	STATUS mandatory
	DESCRIPTION "&<caiUxsA2.396>Default monitor level for the printer status monitoring of the print queue watcher to add. If set to 1 (do-not-monitor), the agent does not evaluate the actual state of the resource and sets the status to ok. If set to 2 (down-warning), the agent uses a warning severity if the resource is in bad condition. If set to 3 (down-critical), the agent uses a critical severity if the resource is in bad condition."
	DEFVAL { 3 }
	::= { uxsA2ConfigPrnGroup 10 }

uxsA2ConfigPrnLossAction OBJECT-TYPE
	SYNTAX INTEGER {
		remove(1),
		up(2),
		down-warning(3),
		down-critical(4)
	}
	ACCESS read-write
	STATUS mandatory
	DESCRIPTION "&<caiUxsA2.397>Default loss action for the print queue watcher to add. Specifies the action to take if the monitored print queue is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { uxsA2ConfigPrnGroup 11 }

uxsA2ConfigPrnAutoTableWatcherName OBJECT-TYPE
	SYNTAX DisplayString
	ACCESS read-write
	STATUS mandatory
	DESCRIPTION "&<caiUxsA2.398>Name of the print queue auto watcher to add or remove."
	::= { uxsA2ConfigPrnGroup 12 }

uxsA2ConfigPrnAutoTableWatcherMatchType OBJECT-TYPE
	SYNTAX INTEGER {
		positive(1),
		negative(2)
	}
	ACCESS read-write
	STATUS mandatory
	DESCRIPTION "&<caiUxsA2.399>Default search algorithm for the print queue auto watcher to add. The filter is the logical AND of all attributes used to identify or otherwise narrow down resources. If set to 1 (positive), the agent searches for print queue resources that match the filter. If set to 2 (negative), the agent searches for print queue resources that do not match the filter."
	DEFVAL { 1 }
	::= { uxsA2ConfigPrnGroup 13 }

uxsA2ConfigPrnAutoTableWatcherLimit OBJECT-TYPE
	SYNTAX INTEGER
	ACCESS read-write
	STATUS mandatory
	DESCRIPTION "&<caiUxsA2.400>Default minimum number of matches that causes a lock of the print queue auto watcher to add."
	DEFVAL { 100 }
	::= { uxsA2ConfigPrnGroup 14 }

uxsA2ConfigPrnButton OBJECT-TYPE
	SYNTAX INTEGER {
		none(1),
		add(2),
		remove(3),
		add-auto(4),
		remove-auto(5)
	}
	ACCESS read-write
	STATUS mandatory
	DESCRIPTION "&<caiUxsA2.401>This attribute is used to add or remove the print queue watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { uxsA2ConfigPrnGroup 15 }

uxsA2ConfigPrnAutoCount OBJECT-TYPE
	SYNTAX INTEGER
	ACCESS read-only
	STATUS mandatory
	DESCRIPTION "&<caiUxsA2.402>Number of auto watchers in the print queue auto configuration table."
	::= { uxsA2ConfigPrnGroup 16 }

uxsA2ConfigPrnAutoLocked OBJECT-TYPE
	SYNTAX INTEGER
	ACCESS read-only
	STATUS mandatory
	DESCRIPTION "&<caiUxsA2.403>Number of auto watchers in the print queue auto configuration table which are currently locked."
	::= { uxsA2ConfigPrnGroup 17 }

uxsA2ConfigPrnAutoTable OBJECT-TYPE
	SYNTAX SEQUENCE OF UxsA2ConfigPrnAutoEntry
	ACCESS not-accessible
	STATUS mandatory
	DESCRIPTION "&<caiUxsA2.404>Configuration table containing a list of print queue auto watchers."
	::= { uxsA2ConfigPrnGroup 18 }

uxsA2ConfigPrnAutoEntry OBJECT-TYPE
	SYNTAX UxsA2ConfigPrnAutoEntry
	ACCESS not-accessible
	STATUS mandatory
	DESCRIPTION "&<caiUxsA2.405>Entry in the print queue auto watcher configuration table."
	INDEX {
		uxsA2ConfigPrnAutoWatcherName
	}
	::= { uxsA2ConfigPrnAutoTable 1 }

UxsA2ConfigPrnAutoEntry ::= SEQUENCE {
	uxsA2ConfigPrnAutoWatcherName DisplayString,
	uxsA2ConfigPrnAutoName DisplayString,
	uxsA2ConfigPrnAutoDescription DisplayString,
	uxsA2ConfigPrnAutoWatcherMatchType INTEGER,
	uxsA2ConfigPrnAutoWatcherLimit INTEGER,
	uxsA2ConfigPrnAutoWatcherLastMatched INTEGER,
	uxsA2ConfigPrnAutoAggLag INTEGER,
	uxsA2ConfigPrnAutoQueueUtilWarn INTEGER,
	uxsA2ConfigPrnAutoQueueUtilCrit INTEGER,
	uxsA2ConfigPrnAutoQueueUtilMonitor INTEGER,
	uxsA2ConfigPrnAutoPrinterMonitor INTEGER,
	uxsA2ConfigPrnAutoLossAction INTEGER,
	uxsA2ConfigPrnAutoButton INTEGER
}

uxsA2ConfigPrnAutoWatcherName OBJECT-TYPE
	SYNTAX DisplayString
	ACCESS read-only
	STATUS mandatory
	DESCRIPTION "&<caiUxsA2.406>Name of the print queue auto watcher."
	::= { uxsA2ConfigPrnAutoEntry 1 }

uxsA2ConfigPrnAutoName OBJECT-TYPE
	SYNTAX DisplayString
	ACCESS read-write
	STATUS mandatory
	DESCRIPTION "&<caiUxsA2.407>Name of the print queue to be searched for during an auto discovery run. The name can constitute an extended regular expression pattern."
	::= { uxsA2ConfigPrnAutoEntry 2 }

uxsA2ConfigPrnAutoDescription OBJECT-TYPE
	SYNTAX DisplayString
	ACCESS read-write
	STATUS mandatory
	DESCRIPTION "&<caiUxsA2.408>Current description for the print queue auto watcher."
	::= { uxsA2ConfigPrnAutoEntry 3 }

uxsA2ConfigPrnAutoWatcherMatchType OBJECT-TYPE
	SYNTAX INTEGER {
		positive(1),
		negative(2)
	}
	ACCESS read-write
	STATUS mandatory
	DESCRIPTION "&<caiUxsA2.409>Current search algorithm for the print queue auto watcher. The filter is the logical AND of all attributes used to identify or otherwise narrow down resources. If set to 1 (positive), the agent searches for print queue resources that match the filter. If set to 2 (negative), the agent searches for print queue resources that do not match the filter."
	DEFVAL { 0 }
	::= { uxsA2ConfigPrnAutoEntry 4 }

uxsA2ConfigPrnAutoWatcherLimit OBJECT-TYPE
	SYNTAX INTEGER
	ACCESS read-write
	STATUS mandatory
	DESCRIPTION "&<caiUxsA2.410>Current minimum number of matches that causes the print queue auto watcher to be locked."
	::= { uxsA2ConfigPrnAutoEntry 5 }

uxsA2ConfigPrnAutoWatcherLastMatched OBJECT-TYPE
	SYNTAX INTEGER
	ACCESS read-only
	STATUS mandatory
	DESCRIPTION "&<caiUxsA2.411>Number of matches for the last print queue auto discovery run."
	::= { uxsA2ConfigPrnAutoEntry 6 }

uxsA2ConfigPrnAutoAggLag OBJECT-TYPE
	SYNTAX INTEGER
	ACCESS read-write
	STATUS mandatory
	DESCRIPTION "&<caiUxsA2.412>Current lag setting for the print queue auto watcher. Specifies the consecutive number of times at which any status is not in the ok state, before the aggregate status changes. This value must be greater than 0."
	::= { uxsA2ConfigPrnAutoEntry 7 }

uxsA2ConfigPrnAutoQueueUtilWarn OBJECT-TYPE
	SYNTAX INTEGER
	ACCESS read-write
	STATUS mandatory
	DESCRIPTION "&<caiUxsA2.413>Default warning threshold for the print queue utilization monitoring of any print queue watcher created by the auto watcher. This value represents a rising threshold and must be greater than 0, but cannot be greater than the critical threshold."
	::= { uxsA2ConfigPrnAutoEntry 8 }

uxsA2ConfigPrnAutoQueueUtilCrit OBJECT-TYPE
	SYNTAX INTEGER
	ACCESS read-write
	STATUS mandatory
	DESCRIPTION "&<caiUxsA2.414>Default critical threshold for the print queue utilization monitoring of any print queue watcher created by the auto watcher. This value represents a rising threshold and must be greater than 0, but cannot be less than the warning threshold."
	::= { uxsA2ConfigPrnAutoEntry 9 }

uxsA2ConfigPrnAutoQueueUtilMonitor OBJECT-TYPE
	SYNTAX INTEGER {
		do-not-monitor(1),
		warning-only(2),
		critical-only(3),
		both(4)
	}
	ACCESS read-write
	STATUS mandatory
	DESCRIPTION "&<caiUxsA2.415>Default monitor level for the print queue utilization monitoring of any print queue watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2ConfigPrnAutoEntry 10 }

uxsA2ConfigPrnAutoPrinterMonitor OBJECT-TYPE
	SYNTAX INTEGER {
		do-not-monitor(1),
		down-warning(2),
		down-critical(3)
	}
	ACCESS read-write
	STATUS mandatory
	DESCRIPTION "&<caiUxsA2.416>Default monitor level for the printer status monitoring of any print queue watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2ConfigPrnAutoEntry 11 }

uxsA2ConfigPrnAutoLossAction OBJECT-TYPE
	SYNTAX INTEGER {
		remove(1),
		up(2),
		down-warning(3),
		down-critical(4)
	}
	ACCESS read-write
	STATUS mandatory
	DESCRIPTION "&<caiUxsA2.417>Default loss action for any print queue watcher created by the auto watcher. Specifies the action to take if the monitored print queue is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2ConfigPrnAutoEntry 12 }

uxsA2ConfigPrnAutoButton OBJECT-TYPE
	SYNTAX INTEGER {
		active(1),
		remove(2),
		locked(3)
	}
	ACCESS read-write
	STATUS mandatory
	DESCRIPTION "&<caiUxsA2.418>This attribute is used to enable/disable or remove the print queue auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { uxsA2ConfigPrnAutoEntry 13 }

--
-- The ConfigNet Group
--

uxsA2ConfigNetPollInterval OBJECT-TYPE
	SYNTAX INTEGER
	ACCESS read-write
	STATUS mandatory
	DESCRIPTION "&<caiUxsA2.419>Time, in seconds, between collections of network interface information. Valid range: 30 seconds or greater."
	DEFVAL { 60 }
	::= { uxsA2ConfigNetGroup 1 }

uxsA2ConfigNetPollMethod OBJECT-TYPE
	SYNTAX INTEGER {
		disabled(1),
		poll-interval-only(2),
		poll-interval-and-query(3),
		query-only(4)
	}
	ACCESS read-write
	STATUS mandatory
	DESCRIPTION "&<caiUxsA2.420>Specifies how and when the agent collects network interface information. If set to 1 (disabled), the agent does not retrieve the network interface information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigNetGroup 2 }

uxsA2ConfigNetAggLag OBJECT-TYPE
	SYNTAX INTEGER
	ACCESS read-write
	STATUS mandatory
	DESCRIPTION "&<caiUxsA2.421>Default aggregate lag setting for the network interface watcher to add. Specifies the consecutive number of times at which any status is not in the ok state, before the aggregate status changes. This value must be greater than 0."
	DEFVAL { 10 }
	::= { uxsA2ConfigNetGroup 3 }

uxsA2ConfigNetInPktWarn OBJECT-TYPE
	SYNTAX INTEGER
	ACCESS read-write
	STATUS mandatory
	DESCRIPTION "&<caiUxsA2.422>Default warning threshold, in pkts/s, for the input packets monitoring of the network interface watcher to add. This value represents a rising threshold and must be greater than 0, but cannot be greater than the critical threshold."
	DEFVAL { 8000 }
	::= { uxsA2ConfigNetGroup 4 }

uxsA2ConfigNetInPktCrit OBJECT-TYPE
	SYNTAX INTEGER
	ACCESS read-write
	STATUS mandatory
	DESCRIPTION "&<caiUxsA2.423>Default critical threshold, in pkts/s, for the input packets monitoring of the network interface watcher to add. This value represents a rising threshold and must be greater than 0, but cannot be less than the warning threshold."
	DEFVAL { 15000 }
	::= { uxsA2ConfigNetGroup 5 }

uxsA2ConfigNetInPktMonitor OBJECT-TYPE
	SYNTAX INTEGER {
		do-not-monitor(1),
		warning-only(2),
		critical-only(3),
		both(4)
	}
	ACCESS read-write
	STATUS mandatory
	DESCRIPTION "&<caiUxsA2.424>Default monitor level for the input packets monitoring of the network interface watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigNetGroup 6 }

uxsA2ConfigNetRecBytesWarnMin OBJECT-TYPE
	SYNTAX DisplayString
	ACCESS read-write
	STATUS mandatory
	DESCRIPTION "&<caiUxsA2.425>Default warning minimum threshold, in bytes/s, for the received bytes monitoring of the network interface watcher to add. This value represents a declining threshold and must be equal to or greater than 0.0, equal to or greater than the critical minimum threshold, but cannot be greater than the warning maximum threshold. A value of -1 disables the evaluation of this threshold."
	DEFVAL { "-1" }
	::= { uxsA2ConfigNetGroup 7 }

uxsA2ConfigNetRecBytesWarnMax OBJECT-TYPE
	SYNTAX DisplayString
	ACCESS read-write
	STATUS mandatory
	DESCRIPTION "&<caiUxsA2.426>Default warning maximum threshold, in bytes/s, for the received bytes monitoring of the network interface watcher to add. This value represents a rising threshold and must be equal to or greater than 0.0, equal to or greater than the warning minimum threshold, but cannot be greater than the critical maximum threshold. A value of -1 disables the evaluation of this threshold."
	DEFVAL { "2000000.0" }
	::= { uxsA2ConfigNetGroup 8 }

uxsA2ConfigNetRecBytesCritMin OBJECT-TYPE
	SYNTAX DisplayString
	ACCESS read-write
	STATUS mandatory
	DESCRIPTION "&<caiUxsA2.427>Default critical minimum threshold, in bytes/s, for the received bytes monitoring of the network interface watcher to add. This value represents a declining threshold and must be equal to or greater than 0.0, but cannot be greater than the warning minimum threshold. A value of -1 disables the evaluation of this threshold."
	DEFVAL { "-1" }
	::= { uxsA2ConfigNetGroup 9 }

uxsA2ConfigNetRecBytesCritMax OBJECT-TYPE
	SYNTAX DisplayString
	ACCESS read-write
	STATUS mandatory
	DESCRIPTION "&<caiUxsA2.428>Default critical maximum threshold, in bytes/s, for the received bytes monitoring of the network interface watcher to add. This value represents a rising threshold and must be equal to or greater than 0.0, but cannot be less than the warning maximum threshold. A value of -1 disables the evaluation of this threshold."
	DEFVAL { "4000000.0" }
	::= { uxsA2ConfigNetGroup 10 }

uxsA2ConfigNetRecBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.429>Default monitor level for the received bytes monitoring of the network interface watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { uxsA2ConfigNetGroup 11 }

uxsA2ConfigNetInErrWarn OBJECT-TYPE
	SYNTAX INTEGER
	ACCESS read-write
	STATUS mandatory
	DESCRIPTION "&<caiUxsA2.430>Default warning threshold, in number/poll, for the input errors monitoring of the network interface watcher to add. This value represents a rising threshold and must be greater than 0, but cannot be greater than the critical threshold."
	DEFVAL { 5 }
	::= { uxsA2ConfigNetGroup 12 }

uxsA2ConfigNetInErrCrit OBJECT-TYPE
	SYNTAX INTEGER
	ACCESS read-write
	STATUS mandatory
	DESCRIPTION "&<caiUxsA2.431>Default critical threshold, in number/poll, for the input errors monitoring of the network interface watcher to add. This value represents a rising threshold and must be greater than 0, but cannot be less than the warning threshold."
	DEFVAL { 10 }
	::= { uxsA2ConfigNetGroup 13 }

uxsA2ConfigNetInErrMonitor OBJECT-TYPE
	SYNTAX INTEGER {
		do-not-monitor(1),
		warning-only(2),
		critical-only(3),
		both(4)
	}
	ACCESS read-write
	STATUS mandatory
	DESCRIPTION "&<caiUxsA2.432>Default monitor level for the input errors monitoring of the network interface watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigNetGroup 14 }

uxsA2ConfigNetOutPktWarn OBJECT-TYPE
	SYNTAX INTEGER
	ACCESS read-write
	STATUS mandatory
	DESCRIPTION "&<caiUxsA2.433>Default warning threshold, in pkts/s, for the output packets monitoring of the network interface watcher to add. This value represents a rising threshold and must be greater than 0, but cannot be greater than the critical threshold."
	DEFVAL { 25000 }
	::= { uxsA2ConfigNetGroup 15 }

uxsA2ConfigNetOutPktCrit OBJECT-TYPE
	SYNTAX INTEGER
	ACCESS read-write
	STATUS mandatory
	DESCRIPTION "&<caiUxsA2.434>Default critical threshold, in pkts/s, for the output packets monitoring of the network interface watcher to add. This value represents a rising threshold and must be greater than 0, but cannot be less than the warning threshold."
	DEFVAL { 50000 }
	::= { uxsA2ConfigNetGroup 16 }

uxsA2ConfigNetOutPktMonitor OBJECT-TYPE
	SYNTAX INTEGER {
		do-not-monitor(1),
		warning-only(2),
		critical-only(3),
		both(4)
	}
	ACCESS read-write
	STATUS mandatory
	DESCRIPTION "&<caiUxsA2.435>Default monitor level for the output packets monitoring of the network interface watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigNetGroup 17 }

uxsA2ConfigNetSentBytesWarnMin OBJECT-TYPE
	SYNTAX DisplayString
	ACCESS read-write
	STATUS mandatory
	DESCRIPTION "&<caiUxsA2.436>Default warning minimum threshold, in bytes/s, for the sent bytes monitoring of the network interface watcher to add. This value represents a declining threshold and must be equal to or greater than 0.0, equal to or greater than the critical minimum threshold, but cannot be greater than the warning maximum threshold. A value of -1 disables the evaluation of this threshold."
	DEFVAL { "-1" }
	::= { uxsA2ConfigNetGroup 18 }

uxsA2ConfigNetSentBytesWarnMax OBJECT-TYPE
	SYNTAX DisplayString
	ACCESS read-write
	STATUS mandatory
	DESCRIPTION "&<caiUxsA2.437>Default warning maximum threshold, in bytes/s, for the sent bytes monitoring of the network interface watcher to add. This value represents a rising threshold and must be equal to or greater than 0.0, equal to or greater than the warning minimum threshold, but cannot be greater than the critical maximum threshold. A value of -1 disables the evaluation of this threshold."
	DEFVAL { "6000000.0" }
	::= { uxsA2ConfigNetGroup 19 }

uxsA2ConfigNetSentBytesCritMin OBJECT-TYPE
	SYNTAX DisplayString
	ACCESS read-write
	STATUS mandatory
	DESCRIPTION "&<caiUxsA2.438>Default critical minimum threshold, in bytes/s, for the sent bytes monitoring of the network interface watcher to add. This value represents a declining threshold and must be equal to or greater than 0.0, but cannot be greater than the warning minimum threshold. A value of -1 disables the evaluation of this threshold."
	DEFVAL { "-1" }
	::= { uxsA2ConfigNetGroup 20 }

uxsA2ConfigNetSentBytesCritMax OBJECT-TYPE
	SYNTAX DisplayString
	ACCESS read-write
	STATUS mandatory
	DESCRIPTION "&<caiUxsA2.439>Default critical maximum threshold, in bytes/s, for the sent bytes monitoring of the network interface watcher to add. This value represents a rising threshold and must be equal to or greater than 0.0, but cannot be less than the warning maximum threshold. A value of -1 disables the evaluation of this threshold."
	DEFVAL { "12000000.0" }
	::= { uxsA2ConfigNetGroup 21 }

uxsA2ConfigNetSentBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.440>Default monitor level for the sent bytes monitoring of the network interface watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { uxsA2ConfigNetGroup 22 }

uxsA2ConfigNetOutErrWarn OBJECT-TYPE
	SYNTAX INTEGER
	ACCESS read-write
	STATUS mandatory
	DESCRIPTION "&<caiUxsA2.441>Default warning threshold, in number/poll, for the output errors monitoring of the network interface watcher to add. This value represents a rising threshold and must be greater than 0, but cannot be greater than the critical threshold."
	DEFVAL { 5 }
	::= { uxsA2ConfigNetGroup 23 }

uxsA2ConfigNetOutErrCrit OBJECT-TYPE
	SYNTAX INTEGER
	ACCESS read-write
	STATUS mandatory
	DESCRIPTION "&<caiUxsA2.442>Default critical threshold, in number/poll, for the output errors monitoring of the network interface watcher to add. This value represents a rising threshold and must be greater than 0, but cannot be less than the warning threshold."
	DEFVAL { 10 }
	::= { uxsA2ConfigNetGroup 24 }

uxsA2ConfigNetOutErrMonitor OBJECT-TYPE
	SYNTAX INTEGER {
		do-not-monitor(1),
		warning-only(2),
		critical-only(3),
		both(4)
	}
	ACCESS read-write
	STATUS mandatory
	DESCRIPTION "&<caiUxsA2.443>Default monitor level for the output errors monitoring of the network interface watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigNetGroup 25 }

uxsA2ConfigNetCollWarn OBJECT-TYPE
	SYNTAX INTEGER
	ACCESS read-write
	STATUS mandatory
	DESCRIPTION "&<caiUxsA2.444>Default warning threshold, in number/poll, for the collisions monitoring of the network interface watcher to add. This value represents a rising threshold and must be greater than 0, but cannot be greater than the critical threshold."
	DEFVAL { 5 }
	::= { uxsA2ConfigNetGroup 26 }

uxsA2ConfigNetCollCrit OBJECT-TYPE
	SYNTAX INTEGER
	ACCESS read-write
	STATUS mandatory
	DESCRIPTION "&<caiUxsA2.445>Default critical threshold, in number/poll, for the collisions monitoring of the network interface watcher to add. This value represents a rising threshold and must be greater than 0, but cannot be less than the warning threshold."
	DEFVAL { 10 }
	::= { uxsA2ConfigNetGroup 27 }

uxsA2ConfigNetCollMonitor OBJECT-TYPE
	SYNTAX INTEGER {
		do-not-monitor(1),
		warning-only(2),
		critical-only(3),
		both(4)
	}
	ACCESS read-write
	STATUS mandatory
	DESCRIPTION "&<caiUxsA2.446>Default monitor level for the collisions monitoring of the network interface watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigNetGroup 28 }

uxsA2ConfigNetInterfaceMonitor OBJECT-TYPE
	SYNTAX INTEGER {
		do-not-monitor(1),
		down-warning(2),
		down-critical(3)
	}
	ACCESS read-write
	STATUS mandatory
	DESCRIPTION "&<caiUxsA2.447>Default monitor level for the interface status monitoring of the network interface watcher to add. If set to 1 (do-not-monitor), the agent does not evaluate the actual state of the resource and sets the status to ok. If set to 2 (down-warning), the agent uses a warning severity if the resource is in bad condition. If set to 3 (down-critical), the agent uses a critical severity if the resource is in bad condition."
	DEFVAL { 3 }
	::= { uxsA2ConfigNetGroup 29 }

uxsA2ConfigNetLossAction OBJECT-TYPE
	SYNTAX INTEGER {
		remove(1),
		up(2),
		down-warning(3),
		down-critical(4)
	}
	ACCESS read-write
	STATUS mandatory
	DESCRIPTION "&<caiUxsA2.448>Default loss action for the network interface watcher to add. Specifies the action to take if the monitored network interface is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 1 }
	::= { uxsA2ConfigNetGroup 30 }

--
-- The ConfigSHM Group
--

uxsA2ConfigSHMPollInterval OBJECT-TYPE
	SYNTAX INTEGER
	ACCESS read-write
	STATUS mandatory
	DESCRIPTION "&<caiUxsA2.449>Time, in seconds, between collections of shared memory information. Valid range: 30 seconds or greater."
	DEFVAL { 120 }
	::= { uxsA2ConfigSHMGroup 1 }

uxsA2ConfigSHMPollMethod OBJECT-TYPE
	SYNTAX INTEGER {
		disabled(1),
		poll-interval-only(2),
		poll-interval-and-query(3),
		query-only(4)
	}
	ACCESS read-write
	STATUS mandatory
	DESCRIPTION "&<caiUxsA2.450>Specifies how and when the agent collects shared memory information. If set to 1 (disabled), the agent does not retrieve the shared memory information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigSHMGroup 2 }

uxsA2ConfigSHMAutoPollInterval OBJECT-TYPE
	SYNTAX INTEGER
	ACCESS read-write
	STATUS mandatory
	DESCRIPTION "&<caiUxsA2.451>Time, in minutes, between the processing of the shared memory auto watchers. Valid range: -1 (suspended), 30 minutes or greater."
	DEFVAL { 60 }
	::= { uxsA2ConfigSHMGroup 3 }

uxsA2ConfigSHMId OBJECT-TYPE
	SYNTAX DisplayString
	ACCESS read-write
	STATUS mandatory
	DESCRIPTION "&<caiUxsA2.452>Name of the shared memory identifier. The number of used and totally available shared memory identifiers is monitored in the OS Resource Parameters group. When adding an auto watcher, the name can constitute an extended regular expression pattern."
	::= { uxsA2ConfigSHMGroup 4 }

uxsA2ConfigSHMKey OBJECT-TYPE
	SYNTAX DisplayString
	ACCESS read-write
	STATUS mandatory
	DESCRIPTION "&<caiUxsA2.453>Key of the shared memory. When adding an auto watcher, the key can constitute an extended regular expression pattern."
	DEFVAL { ".*" }
	::= { uxsA2ConfigSHMGroup 5 }

uxsA2ConfigSHMMode OBJECT-TYPE
	SYNTAX DisplayString
	ACCESS read-write
	STATUS mandatory
	DESCRIPTION "&<caiUxsA2.454>Access mode and flags of the shared memory. When adding an auto watcher, the mode can constitute an extended regular expression pattern."
	DEFVAL { ".*" }
	::= { uxsA2ConfigSHMGroup 6 }

uxsA2ConfigSHMOwner OBJECT-TYPE
	SYNTAX DisplayString
	ACCESS read-write
	STATUS mandatory
	DESCRIPTION "&<caiUxsA2.455>User name of the owner of the shared memory. When adding an auto watcher, the name can constitute an extended regular expression pattern. On Solaris 10 machines the name of the zone the resource belongs to can be added to the attribute: <owner>@<zone>. Owner and zone are evaluated as separate regular expressions. When no zone is specified the expression matches resources in the current zone only (<owner>@<currentzone>)."
	DEFVAL { ".*" }
	::= { uxsA2ConfigSHMGroup 7 }

uxsA2ConfigSHMGrp OBJECT-TYPE
	SYNTAX DisplayString
	ACCESS read-write
	STATUS mandatory
	DESCRIPTION "&<caiUxsA2.456>Group name of the owner of the shared memory. When adding an auto watcher, the name can constitute an extended regular expression pattern."
	DEFVAL { ".*" }
	::= { uxsA2ConfigSHMGroup 8 }

uxsA2ConfigSHMDescription OBJECT-TYPE
	SYNTAX DisplayString
	ACCESS read-write
	STATUS mandatory
	DESCRIPTION "&<caiUxsA2.457>Default description for the shared memory watcher to add."
	::= { uxsA2ConfigSHMGroup 9 }

uxsA2ConfigSHMAggLag OBJECT-TYPE
	SYNTAX INTEGER
	ACCESS read-write
	STATUS mandatory
	DESCRIPTION "&<caiUxsA2.458>Default aggregate lag setting for the shared memory watcher to add. Specifies the consecutive number of times at which any status is not in the ok state, before the aggregate status changes. This value must be greater than 0."
	DEFVAL { 3 }
	::= { uxsA2ConfigSHMGroup 10 }

uxsA2ConfigSHMNAttachMin OBJECT-TYPE
	SYNTAX INTEGER
	ACCESS read-write
	STATUS mandatory
	DESCRIPTION "&<caiUxsA2.459>Default minimum threshold for the number of processes attached monitoring of the shared memory watcher to add. This value represents a declining threshold and must be equal to or greater than 0, but cannot be greater than the maximum threshold. A value of -1 disables the evaluation of this threshold."
	DEFVAL { -1 }
	::= { uxsA2ConfigSHMGroup 11 }

uxsA2ConfigSHMNAttachMax OBJECT-TYPE
	SYNTAX INTEGER
	ACCESS read-write
	STATUS mandatory
	DESCRIPTION "&<caiUxsA2.460>Default maximum threshold for the number of processes attached monitoring of the shared memory watcher to add. This value represents a rising threshold and must be equal to or greater than 0, but cannot be less than the minimum threshold. A value of -1 disables the evaluation of this threshold."
	DEFVAL { 40 }
	::= { uxsA2ConfigSHMGroup 12 }

uxsA2ConfigSHMNAttachMonitor OBJECT-TYPE
	SYNTAX INTEGER {
		do-not-monitor(1),
		down-warning(2),
		down-critical(3)
	}
	ACCESS read-write
	STATUS mandatory
	DESCRIPTION "&<caiUxsA2.461>Default monitor level for the number of processes attached monitoring of the shared memory watcher to add. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { uxsA2ConfigSHMGroup 13 }

uxsA2ConfigSHMSegSzWarn OBJECT-TYPE
	SYNTAX DisplayString
	ACCESS read-write
	STATUS mandatory
	DESCRIPTION "&<caiUxsA2.462>Default warning threshold, in megabytes, for the size of associated shared memory segment monitoring of the shared memory watcher to add. The active warning threshold is derived from this value and represents a rising threshold. The derived value must be greater than 0.0, less than or equal to the total value (maximum capacity) of the monitored resource as specified in uxsA2StatusSHMSegSzTotal, but cannot be greater than the active critical threshold. These constraints will be maintained by the agent during all configuration actions. The threshold can be specified as either an absolute value (n) or a percentage (n%). It can also be specified as the absolute value left free (nF). The value of uxsA2StatusSHMSegSzTotal will be the reference value for n% and nF notations."
	DEFVAL { "80.0%" }
	::= { uxsA2ConfigSHMGroup 14 }

uxsA2ConfigSHMSegSzCrit OBJECT-TYPE
	SYNTAX DisplayString
	ACCESS read-write
	STATUS mandatory
	DESCRIPTION "&<caiUxsA2.463>Default critical threshold, in megabytes, for the size of associated shared memory segment monitoring of the shared memory watcher to add. The active critical threshold is derived from this value and represents a rising threshold. The derived value must be greater than 0.0, less than or equal to the total value (maximum capacity) of the monitored resource as specified in uxsA2StatusSHMSegSzTotal, but cannot be less than the active warning threshold. These constraints will be maintained by the agent during all configuration actions. The threshold can be specified as either an absolute value (n) or a percentage (n%). It can also be specified as the absolute value left free (nF). The value of uxsA2StatusSHMSegSzTotal will be the reference value for n% and nF notations."
	DEFVAL { "90.0%" }
	::= { uxsA2ConfigSHMGroup 15 }

uxsA2ConfigSHMSegSzMonitor OBJECT-TYPE
	SYNTAX INTEGER {
		do-not-monitor(1),
		warning-only(2),
		critical-only(3),
		both(4)
	}
	ACCESS read-write
	STATUS mandatory
	DESCRIPTION "&<caiUxsA2.464>Default monitor level for the size of associated shared memory segment monitoring of the shared memory watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigSHMGroup 16 }

uxsA2ConfigSHMLossAction OBJECT-TYPE
	SYNTAX INTEGER {
		remove(1),
		up(2),
		down-warning(3),
		down-critical(4)
	}
	ACCESS read-write
	STATUS mandatory
	DESCRIPTION "&<caiUxsA2.465>Default loss action for the shared memory watcher to add. Specifies the action to take if the monitored shared memory is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 1 }
	::= { uxsA2ConfigSHMGroup 17 }

uxsA2ConfigSHMAutoTableWatcherName OBJECT-TYPE
	SYNTAX DisplayString
	ACCESS read-write
	STATUS mandatory
	DESCRIPTION "&<caiUxsA2.466>Name of the shared memory auto watcher to add or remove."
	::= { uxsA2ConfigSHMGroup 18 }

uxsA2ConfigSHMAutoTableWatcherMatchType OBJECT-TYPE
	SYNTAX INTEGER {
		positive(1),
		negative(2)
	}
	ACCESS read-write
	STATUS mandatory
	DESCRIPTION "&<caiUxsA2.467>Default search algorithm for the shared memory auto watcher to add. The filter is the logical AND of all attributes used to identify or otherwise narrow down resources. If set to 1 (positive), the agent searches for shared memory resources that match the filter. If set to 2 (negative), the agent searches for shared memory resources that do not match the filter."
	DEFVAL { 1 }
	::= { uxsA2ConfigSHMGroup 19 }

uxsA2ConfigSHMAutoTableWatcherLimit OBJECT-TYPE
	SYNTAX INTEGER
	ACCESS read-write
	STATUS mandatory
	DESCRIPTION "&<caiUxsA2.468>Default minimum number of matches that causes a lock of the shared memory auto watcher to add."
	DEFVAL { 100 }
	::= { uxsA2ConfigSHMGroup 20 }

uxsA2ConfigSHMButton OBJECT-TYPE
	SYNTAX INTEGER {
		none(1),
		add(2),
		remove(3),
		add-auto(4),
		remove-auto(5)
	}
	ACCESS read-write
	STATUS mandatory
	DESCRIPTION "&<caiUxsA2.469>This attribute is used to add or remove the shared memory watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { uxsA2ConfigSHMGroup 21 }

uxsA2ConfigSHMAutoCount OBJECT-TYPE
	SYNTAX INTEGER
	ACCESS read-only
	STATUS mandatory
	DESCRIPTION "&<caiUxsA2.470>Number of auto watchers in the shared memory auto configuration table."
	::= { uxsA2ConfigSHMGroup 22 }

uxsA2ConfigSHMAutoLocked OBJECT-TYPE
	SYNTAX INTEGER
	ACCESS read-only
	STATUS mandatory
	DESCRIPTION "&<caiUxsA2.471>Number of auto watchers in the shared memory auto configuration table which are currently locked."
	::= { uxsA2ConfigSHMGroup 23 }

uxsA2ConfigSHMAutoTable OBJECT-TYPE
	SYNTAX SEQUENCE OF UxsA2ConfigSHMAutoEntry
	ACCESS not-accessible
	STATUS mandatory
	DESCRIPTION "&<caiUxsA2.472>Configuration table containing a list of shared memory auto watchers."
	::= { uxsA2ConfigSHMGroup 24 }

uxsA2ConfigSHMAutoEntry OBJECT-TYPE
	SYNTAX UxsA2ConfigSHMAutoEntry
	ACCESS not-accessible
	STATUS mandatory
	DESCRIPTION "&<caiUxsA2.473>Entry in the shared memory auto watcher configuration table."
	INDEX {
		uxsA2ConfigSHMAutoWatcherName
	}
	::= { uxsA2ConfigSHMAutoTable 1 }

UxsA2ConfigSHMAutoEntry ::= SEQUENCE {
	uxsA2ConfigSHMAutoWatcherName DisplayString,
	uxsA2ConfigSHMAutoId DisplayString,
	uxsA2ConfigSHMAutoKey DisplayString,
	uxsA2ConfigSHMAutoMode DisplayString,
	uxsA2ConfigSHMAutoOwner DisplayString,
	uxsA2ConfigSHMAutoGrp DisplayString,
	uxsA2ConfigSHMAutoDescription DisplayString,
	uxsA2ConfigSHMAutoWatcherMatchType INTEGER,
	uxsA2ConfigSHMAutoWatcherLimit INTEGER,
	uxsA2ConfigSHMAutoWatcherLastMatched INTEGER,
	uxsA2ConfigSHMAutoAggLag INTEGER,
	uxsA2ConfigSHMAutoNAttachMin INTEGER,
	uxsA2ConfigSHMAutoNAttachMax INTEGER,
	uxsA2ConfigSHMAutoNAttachMonitor INTEGER,
	uxsA2ConfigSHMAutoSegSzWarn DisplayString,
	uxsA2ConfigSHMAutoSegSzCrit DisplayString,
	uxsA2ConfigSHMAutoSegSzMonitor INTEGER,
	uxsA2ConfigSHMAutoLossAction INTEGER,
	uxsA2ConfigSHMAutoButton INTEGER
}

uxsA2ConfigSHMAutoWatcherName OBJECT-TYPE
	SYNTAX DisplayString
	ACCESS read-only
	STATUS mandatory
	DESCRIPTION "&<caiUxsA2.474>Name of the shared memory auto watcher."
	::= { uxsA2ConfigSHMAutoEntry 1 }

uxsA2ConfigSHMAutoId OBJECT-TYPE
	SYNTAX DisplayString
	ACCESS read-write
	STATUS mandatory
	DESCRIPTION "&<caiUxsA2.475>Name of the shared memory identifier to be searched for during an auto discovery run. The name can constitute an extended regular expression pattern."
	::= { uxsA2ConfigSHMAutoEntry 2 }

uxsA2ConfigSHMAutoKey OBJECT-TYPE
	SYNTAX DisplayString
	ACCESS read-write
	STATUS mandatory
	DESCRIPTION "&<caiUxsA2.476>Key of the shared memory to be searched for during an auto discovery run. The name can constitute an extended regular expression pattern."
	::= { uxsA2ConfigSHMAutoEntry 3 }

uxsA2ConfigSHMAutoMode OBJECT-TYPE
	SYNTAX DisplayString
	ACCESS read-write
	STATUS mandatory
	DESCRIPTION "&<caiUxsA2.477>Access mode and flags of the shared memory to be searched for during an auto discovery run. The name can constitute an extended regular expression pattern."
	::= { uxsA2ConfigSHMAutoEntry 4 }

uxsA2ConfigSHMAutoOwner OBJECT-TYPE
	SYNTAX DisplayString
	ACCESS read-write
	STATUS mandatory
	DESCRIPTION "&<caiUxsA2.478>User name of the owner of the shared memory to be searched for during an auto discovery run. The name can constitute an extended regular expression pattern. On Solaris 10 machines the name of the zone the resource belongs to can be added to the attribute: <owner>@<zone>. Owner and zone are evaluated as separate regular expressions. When no zone is specified the expression matches resources in the current zone only (<owner>@<currentzone>)."
	::= { uxsA2ConfigSHMAutoEntry 5 }

uxsA2ConfigSHMAutoGrp OBJECT-TYPE
	SYNTAX DisplayString
	ACCESS read-write
	STATUS mandatory
	DESCRIPTION "&<caiUxsA2.479>Group name of the owner of the shared memory to be searched for during an auto discovery run. The name can constitute an extended regular expression pattern."
	::= { uxsA2ConfigSHMAutoEntry 6 }

uxsA2ConfigSHMAutoDescription OBJECT-TYPE
	SYNTAX DisplayString
	ACCESS read-write
	STATUS mandatory
	DESCRIPTION "&<caiUxsA2.480>Current description for the shared memory auto watcher."
	::= { uxsA2ConfigSHMAutoEntry 7 }

uxsA2ConfigSHMAutoWatcherMatchType OBJECT-TYPE
	SYNTAX INTEGER {
		positive(1),
		negative(2)
	}
	ACCESS read-write
	STATUS mandatory
	DESCRIPTION "&<caiUxsA2.481>Current search algorithm for the shared memory auto watcher. The filter is the logical AND of all attributes used to identify or otherwise narrow down resources. If set to 1 (positive), the agent searches for shared memory resources that match the filter. If set to 2 (negative), the agent searches for shared memory resources that do not match the filter."
	DEFVAL { 0 }
	::= { uxsA2ConfigSHMAutoEntry 8 }

uxsA2ConfigSHMAutoWatcherLimit OBJECT-TYPE
	SYNTAX INTEGER
	ACCESS read-write
	STATUS mandatory
	DESCRIPTION "&<caiUxsA2.482>Current minimum number of matches that causes the shared memory auto watcher to be locked."
	::= { uxsA2ConfigSHMAutoEntry 9 }

uxsA2ConfigSHMAutoWatcherLastMatched OBJECT-TYPE
	SYNTAX INTEGER
	ACCESS read-only
	STATUS mandatory
	DESCRIPTION "&<caiUxsA2.483>Number of matches for the last shared memory auto discovery run."
	::= { uxsA2ConfigSHMAutoEntry 10 }

uxsA2ConfigSHMAutoAggLag OBJECT-TYPE
	SYNTAX INTEGER
	ACCESS read-write
	STATUS mandatory
	DESCRIPTION "&<caiUxsA2.484>Current lag setting for the shared memory auto watcher. Specifies the consecutive number of times at which any status is not in the ok state, before the aggregate status changes. This value must be greater than 0."
	::= { uxsA2ConfigSHMAutoEntry 11 }

uxsA2ConfigSHMAutoNAttachMin OBJECT-TYPE
	SYNTAX INTEGER
	ACCESS read-write
	STATUS mandatory
	DESCRIPTION "&<caiUxsA2.485>Default minimum threshold for the number of processes attached monitoring of any shared memory watcher created by the auto watcher. This value represents a declining threshold and must be equal to or greater than 0, but cannot be greater than the maximum threshold. A value of -1 disables the evaluation of this threshold."
	DEFVAL { -2 }
	::= { uxsA2ConfigSHMAutoEntry 12 }

uxsA2ConfigSHMAutoNAttachMax OBJECT-TYPE
	SYNTAX INTEGER
	ACCESS read-write
	STATUS mandatory
	DESCRIPTION "&<caiUxsA2.486>Default maximum threshold for the number of processes attached monitoring of any shared memory watcher created by the auto watcher. This value represents a rising threshold and must be equal to or greater than 0, but cannot be less than the minimum threshold. A value of -1 disables the evaluation of this threshold."
	DEFVAL { -2 }
	::= { uxsA2ConfigSHMAutoEntry 13 }

uxsA2ConfigSHMAutoNAttachMonitor OBJECT-TYPE
	SYNTAX INTEGER {
		do-not-monitor(1),
		down-warning(2),
		down-critical(3)
	}
	ACCESS read-write
	STATUS mandatory
	DESCRIPTION "&<caiUxsA2.487>Default monitor level for the number of processes attached monitoring of any shared memory watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2ConfigSHMAutoEntry 14 }

uxsA2ConfigSHMAutoSegSzWarn OBJECT-TYPE
	SYNTAX DisplayString
	ACCESS read-write
	STATUS mandatory
	DESCRIPTION "&<caiUxsA2.488>Default warning threshold, in megabytes, for the size of associated shared memory segment monitoring of any shared memory watcher created by the auto watcher. The active warning threshold is derived from this value and represents a rising threshold. The derived value must be greater than 0.0, less than or equal to the total value (maximum capacity) of the monitored resource as specified in uxsA2StatusSHMSegSzTotal, but cannot be greater than the active critical threshold. These constraints will be maintained by the agent during all configuration actions. The threshold can be specified as either an absolute value (n) or a percentage (n%). It can also be specified as the absolute value left free (nF). The value of uxsA2StatusSHMSegSzTotal will be the reference value for n% and nF notations."
	::= { uxsA2ConfigSHMAutoEntry 15 }

uxsA2ConfigSHMAutoSegSzCrit OBJECT-TYPE
	SYNTAX DisplayString
	ACCESS read-write
	STATUS mandatory
	DESCRIPTION "&<caiUxsA2.489>Default critical threshold, in megabytes, for the size of associated shared memory segment monitoring of any shared memory watcher created by the auto watcher. The active critical threshold is derived from this value and represents a rising threshold. The derived value must be greater than 0.0, less than or equal to the total value (maximum capacity) of the monitored resource as specified in uxsA2StatusSHMSegSzTotal, but cannot be less than the active warning threshold. These constraints will be maintained by the agent during all configuration actions. The threshold can be specified as either an absolute value (n) or a percentage (n%). It can also be specified as the absolute value left free (nF). The value of uxsA2StatusSHMSegSzTotal will be the reference value for n% and nF notations."
	::= { uxsA2ConfigSHMAutoEntry 16 }

uxsA2ConfigSHMAutoSegSzMonitor OBJECT-TYPE
	SYNTAX INTEGER {
		do-not-monitor(1),
		warning-only(2),
		critical-only(3),
		both(4)
	}
	ACCESS read-write
	STATUS mandatory
	DESCRIPTION "&<caiUxsA2.490>Default monitor level for the size of associated shared memory segment monitoring of any shared memory watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2ConfigSHMAutoEntry 17 }

uxsA2ConfigSHMAutoLossAction OBJECT-TYPE
	SYNTAX INTEGER {
		remove(1),
		up(2),
		down-warning(3),
		down-critical(4)
	}
	ACCESS read-write
	STATUS mandatory
	DESCRIPTION "&<caiUxsA2.491>Default loss action for any shared memory watcher created by the auto watcher. Specifies the action to take if the monitored shared memory is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2ConfigSHMAutoEntry 18 }

uxsA2ConfigSHMAutoButton OBJECT-TYPE
	SYNTAX INTEGER {
		active(1),
		remove(2),
		locked(3)
	}
	ACCESS read-write
	STATUS mandatory
	DESCRIPTION "&<caiUxsA2.492>This attribute is used to enable/disable or remove the shared memory auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { uxsA2ConfigSHMAutoEntry 19 }

--
-- The ConfigSEM Group
--

uxsA2ConfigSEMPollInterval OBJECT-TYPE
	SYNTAX INTEGER
	ACCESS read-write
	STATUS mandatory
	DESCRIPTION "&<caiUxsA2.493>Time, in seconds, between collections of semaphore information. Valid range: 30 seconds or greater."
	DEFVAL { 120 }
	::= { uxsA2ConfigSEMGroup 1 }

uxsA2ConfigSEMPollMethod OBJECT-TYPE
	SYNTAX INTEGER {
		disabled(1),
		poll-interval-only(2),
		poll-interval-and-query(3),
		query-only(4)
	}
	ACCESS read-write
	STATUS mandatory
	DESCRIPTION "&<caiUxsA2.494>Specifies how and when the agent collects semaphore information. If set to 1 (disabled), the agent does not retrieve the semaphore information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigSEMGroup 2 }

uxsA2ConfigSEMAutoPollInterval OBJECT-TYPE
	SYNTAX INTEGER
	ACCESS read-write
	STATUS mandatory
	DESCRIPTION "&<caiUxsA2.495>Time, in minutes, between the processing of the semaphore auto watchers. Valid range: -1 (suspended), 30 minutes or greater."
	DEFVAL { 60 }
	::= { uxsA2ConfigSEMGroup 3 }

uxsA2ConfigSEMId OBJECT-TYPE
	SYNTAX DisplayString
	ACCESS read-write
	STATUS mandatory
	DESCRIPTION "&<caiUxsA2.496>Name of the semaphore identifier. The number of used and totally available semaphore identifiers is monitored in the OS Resource Parameters group. When adding an auto watcher, the name can constitute an extended regular expression pattern."
	::= { uxsA2ConfigSEMGroup 4 }

uxsA2ConfigSEMKey OBJECT-TYPE
	SYNTAX DisplayString
	ACCESS read-write
	STATUS mandatory
	DESCRIPTION "&<caiUxsA2.497>Key of the semaphore. When adding an auto watcher, the key can constitute an extended regular expression pattern."
	DEFVAL { ".*" }
	::= { uxsA2ConfigSEMGroup 5 }

uxsA2ConfigSEMMode OBJECT-TYPE
	SYNTAX DisplayString
	ACCESS read-write
	STATUS mandatory
	DESCRIPTION "&<caiUxsA2.498>Access mode and flags of the semaphore. When adding an auto watcher, the mode can constitute an extended regular expression pattern."
	DEFVAL { ".*" }
	::= { uxsA2ConfigSEMGroup 6 }

uxsA2ConfigSEMOwner OBJECT-TYPE
	SYNTAX DisplayString
	ACCESS read-write
	STATUS mandatory
	DESCRIPTION "&<caiUxsA2.499>User name of the owner of the semaphore. When adding an auto watcher, the name can constitute an extended regular expression pattern. On Solaris 10 machines the name of the zone the resource belongs to can be added to the attribute: <owner>@<zone>. Owner and zone are evaluated as separate regular expressions. When no zone is specified the expression matches resources in the current zone only (<owner>@<currentzone>)."
	DEFVAL { ".*" }
	::= { uxsA2ConfigSEMGroup 7 }

uxsA2ConfigSEMGrp OBJECT-TYPE
	SYNTAX DisplayString
	ACCESS read-write
	STATUS mandatory
	DESCRIPTION "&<caiUxsA2.500>Group name of the owner of the semaphore. When adding an auto watcher, the name can constitute an extended regular expression pattern."
	DEFVAL { ".*" }
	::= { uxsA2ConfigSEMGroup 8 }

uxsA2ConfigSEMDescription OBJECT-TYPE
	SYNTAX DisplayString
	ACCESS read-write
	STATUS mandatory
	DESCRIPTION "&<caiUxsA2.501>Default description for the semaphore watcher to add."
	::= { uxsA2ConfigSEMGroup 9 }

uxsA2ConfigSEMAggLag OBJECT-TYPE
	SYNTAX INTEGER
	ACCESS read-write
	STATUS mandatory
	DESCRIPTION "&<caiUxsA2.502>Default aggregate lag setting for the semaphore watcher to add. Specifies the consecutive number of times at which any status is not in the ok state, before the aggregate status changes. This value must be greater than 0."
	DEFVAL { 3 }
	::= { uxsA2ConfigSEMGroup 10 }

uxsA2ConfigSEMNSemsWarn OBJECT-TYPE
	SYNTAX INTEGER
	ACCESS read-write
	STATUS mandatory
	DESCRIPTION "&<caiUxsA2.503>Default warning threshold for the number of semaphores in the set monitoring of the semaphore watcher to add. This value represents a rising threshold and must be greater than 0, but cannot be greater than the critical threshold."
	DEFVAL { 20 }
	::= { uxsA2ConfigSEMGroup 11 }

uxsA2ConfigSEMNSemsCrit OBJECT-TYPE
	SYNTAX INTEGER
	ACCESS read-write
	STATUS mandatory
	DESCRIPTION "&<caiUxsA2.504>Default critical threshold for the number of semaphores in the set monitoring of the semaphore watcher to add. This value represents a rising threshold and must be greater than 0, but cannot be less than the warning threshold."
	DEFVAL { 40 }
	::= { uxsA2ConfigSEMGroup 12 }

uxsA2ConfigSEMNSemsMonitor OBJECT-TYPE
	SYNTAX INTEGER {
		do-not-monitor(1),
		warning-only(2),
		critical-only(3),
		both(4)
	}
	ACCESS read-write
	STATUS mandatory
	DESCRIPTION "&<caiUxsA2.505>Default monitor level for the number of semaphores in the set monitoring of the semaphore watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { uxsA2ConfigSEMGroup 13 }

uxsA2ConfigSEMLossAction OBJECT-TYPE
	SYNTAX INTEGER {
		remove(1),
		up(2),
		down-warning(3),
		down-critical(4)
	}
	ACCESS read-write
	STATUS mandatory
	DESCRIPTION "&<caiUxsA2.506>Default loss action for the semaphore watcher to add. Specifies the action to take if the monitored semaphore is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 1 }
	::= { uxsA2ConfigSEMGroup 14 }

uxsA2ConfigSEMAutoTableWatcherName OBJECT-TYPE
	SYNTAX DisplayString
	ACCESS read-write
	STATUS mandatory
	DESCRIPTION "&<caiUxsA2.507>Name of the semaphore auto watcher to add or remove."
	::= { uxsA2ConfigSEMGroup 15 }

uxsA2ConfigSEMAutoTableWatcherMatchType OBJECT-TYPE
	SYNTAX INTEGER {
		positive(1),
		negative(2)
	}
	ACCESS read-write
	STATUS mandatory
	DESCRIPTION "&<caiUxsA2.508>Default search algorithm for the semaphore auto watcher to add. The filter is the logical AND of all attributes used to identify or otherwise narrow down resources. If set to 1 (positive), the agent searches for semaphore resources that match the filter. If set to 2 (negative), the agent searches for semaphore resources that do not match the filter."
	DEFVAL { 1 }
	::= { uxsA2ConfigSEMGroup 16 }

uxsA2ConfigSEMAutoTableWatcherLimit OBJECT-TYPE
	SYNTAX INTEGER
	ACCESS read-write
	STATUS mandatory
	DESCRIPTION "&<caiUxsA2.509>Default minimum number of matches that causes a lock of the semaphore auto watcher to add."
	DEFVAL { 100 }
	::= { uxsA2ConfigSEMGroup 17 }

uxsA2ConfigSEMButton OBJECT-TYPE
	SYNTAX INTEGER {
		none(1),
		add(2),
		remove(3),
		add-auto(4),
		remove-auto(5)
	}
	ACCESS read-write
	STATUS mandatory
	DESCRIPTION "&<caiUxsA2.510>This attribute is used to add or remove the semaphore watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { uxsA2ConfigSEMGroup 18 }

uxsA2ConfigSEMAutoCount OBJECT-TYPE
	SYNTAX INTEGER
	ACCESS read-only
	STATUS mandatory
	DESCRIPTION "&<caiUxsA2.511>Number of auto watchers in the semaphore auto configuration table."
	::= { uxsA2ConfigSEMGroup 19 }

uxsA2ConfigSEMAutoLocked OBJECT-TYPE
	SYNTAX INTEGER
	ACCESS read-only
	STATUS mandatory
	DESCRIPTION "&<caiUxsA2.512>Number of auto watchers in the semaphore auto configuration table which are currently locked."
	::= { uxsA2ConfigSEMGroup 20 }

uxsA2ConfigSEMAutoTable OBJECT-TYPE
	SYNTAX SEQUENCE OF UxsA2ConfigSEMAutoEntry
	ACCESS not-accessible
	STATUS mandatory
	DESCRIPTION "&<caiUxsA2.513>Configuration table containing a list of semaphore auto watchers."
	::= { uxsA2ConfigSEMGroup 21 }

uxsA2ConfigSEMAutoEntry OBJECT-TYPE
	SYNTAX UxsA2ConfigSEMAutoEntry
	ACCESS not-accessible
	STATUS mandatory
	DESCRIPTION "&<caiUxsA2.514>Entry in the semaphore auto watcher configuration table."
	INDEX {
		uxsA2ConfigSEMAutoWatcherName
	}
	::= { uxsA2ConfigSEMAutoTable 1 }

UxsA2ConfigSEMAutoEntry ::= SEQUENCE {
	uxsA2ConfigSEMAutoWatcherName DisplayString,
	uxsA2ConfigSEMAutoId DisplayString,
	uxsA2ConfigSEMAutoKey DisplayString,
	uxsA2ConfigSEMAutoMode DisplayString,
	uxsA2ConfigSEMAutoOwner DisplayString,
	uxsA2ConfigSEMAutoGrp DisplayString,
	uxsA2ConfigSEMAutoDescription DisplayString,
	uxsA2ConfigSEMAutoWatcherMatchType INTEGER,
	uxsA2ConfigSEMAutoWatcherLimit INTEGER,
	uxsA2ConfigSEMAutoWatcherLastMatched INTEGER,
	uxsA2ConfigSEMAutoAggLag INTEGER,
	uxsA2ConfigSEMAutoNSemsWarn INTEGER,
	uxsA2ConfigSEMAutoNSemsCrit INTEGER,
	uxsA2ConfigSEMAutoNSemsMonitor INTEGER,
	uxsA2ConfigSEMAutoLossAction INTEGER,
	uxsA2ConfigSEMAutoButton INTEGER
}

uxsA2ConfigSEMAutoWatcherName OBJECT-TYPE
	SYNTAX DisplayString
	ACCESS read-only
	STATUS mandatory
	DESCRIPTION "&<caiUxsA2.515>Name of the semaphore auto watcher."
	::= { uxsA2ConfigSEMAutoEntry 1 }

uxsA2ConfigSEMAutoId OBJECT-TYPE
	SYNTAX DisplayString
	ACCESS read-write
	STATUS mandatory
	DESCRIPTION "&<caiUxsA2.516>Name of the semaphore identifier to be searched for during an auto discovery run. The name can constitute an extended regular expression pattern."
	::= { uxsA2ConfigSEMAutoEntry 2 }

uxsA2ConfigSEMAutoKey OBJECT-TYPE
	SYNTAX DisplayString
	ACCESS read-write
	STATUS mandatory
	DESCRIPTION "&<caiUxsA2.517>Key of the semaphore to be searched for during an auto discovery run. The name can constitute an extended regular expression pattern."
	::= { uxsA2ConfigSEMAutoEntry 3 }

uxsA2ConfigSEMAutoMode OBJECT-TYPE
	SYNTAX DisplayString
	ACCESS read-write
	STATUS mandatory
	DESCRIPTION "&<caiUxsA2.518>Access mode and flags of the semaphore to be searched for during an auto discovery run. The name can constitute an extended regular expression pattern."
	::= { uxsA2ConfigSEMAutoEntry 4 }

uxsA2ConfigSEMAutoOwner OBJECT-TYPE
	SYNTAX DisplayString
	ACCESS read-write
	STATUS mandatory
	DESCRIPTION "&<caiUxsA2.519>User name of the owner of the semaphore to be searched for during an auto discovery run. The name can constitute an extended regular expression pattern. On Solaris 10 machines the name of the zone the resource belongs to can be added to the attribute: <owner>@<zone>. Owner and zone are evaluated as separate regular expressions. When no zone is specified the expression matches resources in the current zone only (<owner>@<currentzone>)."
	::= { uxsA2ConfigSEMAutoEntry 5 }

uxsA2ConfigSEMAutoGrp OBJECT-TYPE
	SYNTAX DisplayString
	ACCESS read-write
	STATUS mandatory
	DESCRIPTION "&<caiUxsA2.520>Group name of the owner of the semaphore to be searched for during an auto discovery run. The name can constitute an extended regular expression pattern."
	::= { uxsA2ConfigSEMAutoEntry 6 }

uxsA2ConfigSEMAutoDescription OBJECT-TYPE
	SYNTAX DisplayString
	ACCESS read-write
	STATUS mandatory
	DESCRIPTION "&<caiUxsA2.521>Current description for the semaphore auto watcher."
	::= { uxsA2ConfigSEMAutoEntry 7 }

uxsA2ConfigSEMAutoWatcherMatchType OBJECT-TYPE
	SYNTAX INTEGER {
		positive(1),
		negative(2)
	}
	ACCESS read-write
	STATUS mandatory
	DESCRIPTION "&<caiUxsA2.522>Current search algorithm for the semaphore auto watcher. The filter is the logical AND of all attributes used to identify or otherwise narrow down resources. If set to 1 (positive), the agent searches for semaphore resources that match the filter. If set to 2 (negative), the agent searches for semaphore resources that do not match the filter."
	DEFVAL { 0 }
	::= { uxsA2ConfigSEMAutoEntry 8 }

uxsA2ConfigSEMAutoWatcherLimit OBJECT-TYPE
	SYNTAX INTEGER
	ACCESS read-write
	STATUS mandatory
	DESCRIPTION "&<caiUxsA2.523>Current minimum number of matches that causes the semaphore auto watcher to be locked."
	::= { uxsA2ConfigSEMAutoEntry 9 }

uxsA2ConfigSEMAutoWatcherLastMatched OBJECT-TYPE
	SYNTAX INTEGER
	ACCESS read-only
	STATUS mandatory
	DESCRIPTION "&<caiUxsA2.524>Number of matches for the last semaphore auto discovery run."
	::= { uxsA2ConfigSEMAutoEntry 10 }

uxsA2ConfigSEMAutoAggLag OBJECT-TYPE
	SYNTAX INTEGER
	ACCESS read-write
	STATUS mandatory
	DESCRIPTION "&<caiUxsA2.525>Current lag setting for the semaphore auto watcher. Specifies the consecutive number of times at which any status is not in the ok state, before the aggregate status changes. This value must be greater than 0."
	::= { uxsA2ConfigSEMAutoEntry 11 }

uxsA2ConfigSEMAutoNSemsWarn OBJECT-TYPE
	SYNTAX INTEGER
	ACCESS read-write
	STATUS mandatory
	DESCRIPTION "&<caiUxsA2.526>Default warning threshold for the number of semaphores in the set monitoring of any semaphore watcher created by the auto watcher. This value represents a rising threshold and must be greater than 0, but cannot be greater than the critical threshold."
	::= { uxsA2ConfigSEMAutoEntry 12 }

uxsA2ConfigSEMAutoNSemsCrit OBJECT-TYPE
	SYNTAX INTEGER
	ACCESS read-write
	STATUS mandatory
	DESCRIPTION "&<caiUxsA2.527>Default critical threshold for the number of semaphores in the set monitoring of any semaphore watcher created by the auto watcher. This value represents a rising threshold and must be greater than 0, but cannot be less than the warning threshold."
	::= { uxsA2ConfigSEMAutoEntry 13 }

uxsA2ConfigSEMAutoNSemsMonitor OBJECT-TYPE
	SYNTAX INTEGER {
		do-not-monitor(1),
		warning-only(2),
		critical-only(3),
		both(4)
	}
	ACCESS read-write
	STATUS mandatory
	DESCRIPTION "&<caiUxsA2.528>Default monitor level for the number of semaphores in the set monitoring of any semaphore watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2ConfigSEMAutoEntry 14 }

uxsA2ConfigSEMAutoLossAction OBJECT-TYPE
	SYNTAX INTEGER {
		remove(1),
		up(2),
		down-warning(3),
		down-critical(4)
	}
	ACCESS read-write
	STATUS mandatory
	DESCRIPTION "&<caiUxsA2.529>Default loss action for any semaphore watcher created by the auto watcher. Specifies the action to take if the monitored semaphore is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2ConfigSEMAutoEntry 15 }

uxsA2ConfigSEMAutoButton OBJECT-TYPE
	SYNTAX INTEGER {
		active(1),
		remove(2),
		locked(3)
	}
	ACCESS read-write
	STATUS mandatory
	DESCRIPTION "&<caiUxsA2.530>This attribute is used to enable/disable or remove the semaphore auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { uxsA2ConfigSEMAutoEntry 16 }

--
-- The ConfigMQ Group
--

uxsA2ConfigMQPollInterval OBJECT-TYPE
	SYNTAX INTEGER
	ACCESS read-write
	STATUS mandatory
	DESCRIPTION "&<caiUxsA2.531>Time, in seconds, between collections of message queue information. Valid range: 30 seconds or greater."
	DEFVAL { 120 }
	::= { uxsA2ConfigMQGroup 1 }

uxsA2ConfigMQPollMethod OBJECT-TYPE
	SYNTAX INTEGER {
		disabled(1),
		poll-interval-only(2),
		poll-interval-and-query(3),
		query-only(4)
	}
	ACCESS read-write
	STATUS mandatory
	DESCRIPTION "&<caiUxsA2.532>Specifies how and when the agent collects message queue information. If set to 1 (disabled), the agent does not retrieve the message queue information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigMQGroup 2 }

uxsA2ConfigMQAutoPollInterval OBJECT-TYPE
	SYNTAX INTEGER
	ACCESS read-write
	STATUS mandatory
	DESCRIPTION "&<caiUxsA2.533>Time, in minutes, between the processing of the message queue auto watchers. Valid range: -1 (suspended), 30 minutes or greater."
	DEFVAL { 60 }
	::= { uxsA2ConfigMQGroup 3 }

uxsA2ConfigMQId OBJECT-TYPE
	SYNTAX DisplayString
	ACCESS read-write
	STATUS mandatory
	DESCRIPTION "&<caiUxsA2.534>Name of the message queue identifier. The number of used and totally available message queue identifiers is monitored in the OS Resource Parameters group. When adding an auto watcher, the name can constitute an extended regular expression pattern."
	::= { uxsA2ConfigMQGroup 4 }

uxsA2ConfigMQKey OBJECT-TYPE
	SYNTAX DisplayString
	ACCESS read-write
	STATUS mandatory
	DESCRIPTION "&<caiUxsA2.535>Key of the message queue. When adding an auto watcher, the key can constitute an extended regular expression pattern."
	DEFVAL { ".*" }
	::= { uxsA2ConfigMQGroup 5 }

uxsA2ConfigMQMode OBJECT-TYPE
	SYNTAX DisplayString
	ACCESS read-write
	STATUS mandatory
	DESCRIPTION "&<caiUxsA2.536>Access mode and flags of the message queue. When adding an auto watcher, the mode can constitute an extended regular expression pattern."
	DEFVAL { ".*" }
	::= { uxsA2ConfigMQGroup 6 }

uxsA2ConfigMQOwner OBJECT-TYPE
	SYNTAX DisplayString
	ACCESS read-write
	STATUS mandatory
	DESCRIPTION "&<caiUxsA2.537>User name of the owner of the message queue. When adding an auto watcher, the name can constitute an extended regular expression pattern. On Solaris 10 machines the name of the zone the resource belongs to can be added to the attribute: <owner>@<zone>. Owner and zone are evaluated as separate regular expressions. When no zone is specified the expression matches resources in the current zone only (<owner>@<currentzone>)."
	DEFVAL { ".*" }
	::= { uxsA2ConfigMQGroup 7 }

uxsA2ConfigMQGrp OBJECT-TYPE
	SYNTAX DisplayString
	ACCESS read-write
	STATUS mandatory
	DESCRIPTION "&<caiUxsA2.538>Group name of the owner of the message queue. When adding an auto watcher, the name can constitute an extended regular expression pattern."
	DEFVAL { ".*" }
	::= { uxsA2ConfigMQGroup 8 }

uxsA2ConfigMQDescription OBJECT-TYPE
	SYNTAX DisplayString
	ACCESS read-write
	STATUS mandatory
	DESCRIPTION "&<caiUxsA2.539>Default description for the message queue watcher to add."
	::= { uxsA2ConfigMQGroup 9 }

uxsA2ConfigMQAggLag OBJECT-TYPE
	SYNTAX INTEGER
	ACCESS read-write
	STATUS mandatory
	DESCRIPTION "&<caiUxsA2.540>Default aggregate lag setting for the message queue watcher to add. Specifies the consecutive number of times at which any status is not in the ok state, before the aggregate status changes. This value must be greater than 0."
	DEFVAL { 3 }
	::= { uxsA2ConfigMQGroup 10 }

uxsA2ConfigMQCBytesWarn OBJECT-TYPE
	SYNTAX DisplayString
	ACCESS read-write
	STATUS mandatory
	DESCRIPTION "&<caiUxsA2.541>Default warning threshold, in bytes, for the number of bytes in messages currently outstanding monitoring of the message queue watcher to add. The active warning threshold is derived from this value and represents a rising threshold. The derived value must be greater than 0.0, less than or equal to the total value (maximum capacity) of the monitored resource as specified in uxsA2StatusMQCBytesTotal, but cannot be greater than the active critical threshold. These constraints will be maintained by the agent during all configuration actions. The threshold can be specified as either an absolute value (n) or a percentage (n%). It can also be specified as the absolute value left free (nF). The value of uxsA2StatusMQCBytesTotal will be the reference value for n% and nF notations."
	DEFVAL { "80.0%" }
	::= { uxsA2ConfigMQGroup 11 }

uxsA2ConfigMQCBytesCrit OBJECT-TYPE
	SYNTAX DisplayString
	ACCESS read-write
	STATUS mandatory
	DESCRIPTION "&<caiUxsA2.542>Default critical threshold, in bytes, for the number of bytes in messages currently outstanding monitoring of the message queue watcher to add. The active critical threshold is derived from this value and represents a rising threshold. The derived value must be greater than 0.0, less than or equal to the total value (maximum capacity) of the monitored resource as specified in uxsA2StatusMQCBytesTotal, but cannot be less than the active warning threshold. These constraints will be maintained by the agent during all configuration actions. The threshold can be specified as either an absolute value (n) or a percentage (n%). It can also be specified as the absolute value left free (nF). The value of uxsA2StatusMQCBytesTotal will be the reference value for n% and nF notations."
	DEFVAL { "90.0%" }
	::= { uxsA2ConfigMQGroup 12 }

uxsA2ConfigMQCBytesMonitor OBJECT-TYPE
	SYNTAX INTEGER {
		do-not-monitor(1),
		warning-only(2),
		critical-only(3),
		both(4)
	}
	ACCESS read-write
	STATUS mandatory
	DESCRIPTION "&<caiUxsA2.543>Default monitor level for the number of bytes in messages currently outstanding monitoring of the message queue watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2ConfigMQGroup 13 }

uxsA2ConfigMQQNumWarn OBJECT-TYPE
	SYNTAX INTEGER
	ACCESS read-write
	STATUS mandatory
	DESCRIPTION "&<caiUxsA2.544>Default warning threshold for the number of messages currently outstanding monitoring of the message queue watcher to add. This value represents a rising threshold and must be greater than 0, but cannot be greater than the critical threshold."
	DEFVAL { 20 }
	::= { uxsA2ConfigMQGroup 14 }

uxsA2ConfigMQQNumCrit OBJECT-TYPE
	SYNTAX INTEGER
	ACCESS read-write
	STATUS mandatory
	DESCRIPTION "&<caiUxsA2.545>Default critical threshold for the number of messages currently outstanding monitoring of the message queue watcher to add. This value represents a rising threshold and must be greater than 0, but cannot be less than the warning threshold."
	DEFVAL { 40 }
	::= { uxsA2ConfigMQGroup 15 }

uxsA2ConfigMQQNumMonitor OBJECT-TYPE
	SYNTAX INTEGER {
		do-not-monitor(1),
		warning-only(2),
		critical-only(3),
		both(4)
	}
	ACCESS read-write
	STATUS mandatory
	DESCRIPTION "&<caiUxsA2.546>Default monitor level for the number of messages currently outstanding monitoring of the message queue watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { uxsA2ConfigMQGroup 16 }

uxsA2ConfigMQLossAction OBJECT-TYPE
	SYNTAX INTEGER {
		remove(1),
		up(2),
		down-warning(3),
		down-critical(4)
	}
	ACCESS read-write
	STATUS mandatory
	DESCRIPTION "&<caiUxsA2.547>Default loss action for the message queue watcher to add. Specifies the action to take if the monitored message queue is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 1 }
	::= { uxsA2ConfigMQGroup 17 }

uxsA2ConfigMQAutoTableWatcherName OBJECT-TYPE
	SYNTAX DisplayString
	ACCESS read-write
	STATUS mandatory
	DESCRIPTION "&<caiUxsA2.548>Name of the message queue auto watcher to add or remove."
	::= { uxsA2ConfigMQGroup 18 }

uxsA2ConfigMQAutoTableWatcherMatchType OBJECT-TYPE
	SYNTAX INTEGER {
		positive(1),
		negative(2)
	}
	ACCESS read-write
	STATUS mandatory
	DESCRIPTION "&<caiUxsA2.549>Default search algorithm for the message queue auto watcher to add. The filter is the logical AND of all attributes used to identify or otherwise narrow down resources. If set to 1 (positive), the agent searches for message queue resources that match the filter. If set to 2 (negative), the agent searches for message queue resources that do not match the filter."
	DEFVAL { 1 }
	::= { uxsA2ConfigMQGroup 19 }

uxsA2ConfigMQAutoTableWatcherLimit OBJECT-TYPE
	SYNTAX INTEGER
	ACCESS read-write
	STATUS mandatory
	DESCRIPTION "&<caiUxsA2.550>Default minimum number of matches that causes a lock of the message queue auto watcher to add."
	DEFVAL { 100 }
	::= { uxsA2ConfigMQGroup 20 }

uxsA2ConfigMQButton OBJECT-TYPE
	SYNTAX INTEGER {
		none(1),
		add(2),
		remove(3),
		add-auto(4),
		remove-auto(5)
	}
	ACCESS read-write
	STATUS mandatory
	DESCRIPTION "&<caiUxsA2.551>This attribute is used to add or remove the message queue watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { uxsA2ConfigMQGroup 21 }

uxsA2ConfigMQAutoCount OBJECT-TYPE
	SYNTAX INTEGER
	ACCESS read-only
	STATUS mandatory
	DESCRIPTION "&<caiUxsA2.552>Number of auto watchers in the message queue auto configuration table."
	::= { uxsA2ConfigMQGroup 22 }

uxsA2ConfigMQAutoLocked OBJECT-TYPE
	SYNTAX INTEGER
	ACCESS read-only
	STATUS mandatory
	DESCRIPTION "&<caiUxsA2.553>Number of auto watchers in the message queue auto configuration table which are currently locked."
	::= { uxsA2ConfigMQGroup 23 }

uxsA2ConfigMQAutoTable OBJECT-TYPE
	SYNTAX SEQUENCE OF UxsA2ConfigMQAutoEntry
	ACCESS not-accessible
	STATUS mandatory
	DESCRIPTION "&<caiUxsA2.554>Configuration table containing a list of message queue auto watchers."
	::= { uxsA2ConfigMQGroup 24 }

uxsA2ConfigMQAutoEntry OBJECT-TYPE
	SYNTAX UxsA2ConfigMQAutoEntry
	ACCESS not-accessible
	STATUS mandatory
	DESCRIPTION "&<caiUxsA2.555>Entry in the message queue auto watcher configuration table."
	INDEX {
		uxsA2ConfigMQAutoWatcherName
	}
	::= { uxsA2ConfigMQAutoTable 1 }

UxsA2ConfigMQAutoEntry ::= SEQUENCE {
	uxsA2ConfigMQAutoWatcherName DisplayString,
	uxsA2ConfigMQAutoId DisplayString,
	uxsA2ConfigMQAutoKey DisplayString,
	uxsA2ConfigMQAutoMode DisplayString,
	uxsA2ConfigMQAutoOwner DisplayString,
	uxsA2ConfigMQAutoGrp DisplayString,
	uxsA2ConfigMQAutoDescription DisplayString,
	uxsA2ConfigMQAutoWatcherMatchType INTEGER,
	uxsA2ConfigMQAutoWatcherLimit INTEGER,
	uxsA2ConfigMQAutoWatcherLastMatched INTEGER,
	uxsA2ConfigMQAutoAggLag INTEGER,
	uxsA2ConfigMQAutoCBytesWarn DisplayString,
	uxsA2ConfigMQAutoCBytesCrit DisplayString,
	uxsA2ConfigMQAutoCBytesMonitor INTEGER,
	uxsA2ConfigMQAutoQNumWarn INTEGER,
	uxsA2ConfigMQAutoQNumCrit INTEGER,
	uxsA2ConfigMQAutoQNumMonitor INTEGER,
	uxsA2ConfigMQAutoLossAction INTEGER,
	uxsA2ConfigMQAutoButton INTEGER
}

uxsA2ConfigMQAutoWatcherName OBJECT-TYPE
	SYNTAX DisplayString
	ACCESS read-only
	STATUS mandatory
	DESCRIPTION "&<caiUxsA2.556>Name of the message queue auto watcher."
	::= { uxsA2ConfigMQAutoEntry 1 }

uxsA2ConfigMQAutoId OBJECT-TYPE
	SYNTAX DisplayString
	ACCESS read-write
	STATUS mandatory
	DESCRIPTION "&<caiUxsA2.557>Name of the message queue identifier to be searched for during an auto discovery run. The name can constitute an extended regular expression pattern."
	::= { uxsA2ConfigMQAutoEntry 2 }

uxsA2ConfigMQAutoKey OBJECT-TYPE
	SYNTAX DisplayString
	ACCESS read-write
	STATUS mandatory
	DESCRIPTION "&<caiUxsA2.558>Key of the message queue to be searched for during an auto discovery run. The name can constitute an extended regular expression pattern."
	::= { uxsA2ConfigMQAutoEntry 3 }

uxsA2ConfigMQAutoMode OBJECT-TYPE
	SYNTAX DisplayString
	ACCESS read-write
	STATUS mandatory
	DESCRIPTION "&<caiUxsA2.559>Access mode and flags of the message queue to be searched for during an auto discovery run. The name can constitute an extended regular expression pattern."
	::= { uxsA2ConfigMQAutoEntry 4 }

uxsA2ConfigMQAutoOwner OBJECT-TYPE
	SYNTAX DisplayString
	ACCESS read-write
	STATUS mandatory
	DESCRIPTION "&<caiUxsA2.560>User name of the owner of the message queue to be searched for during an auto discovery run. The name can constitute an extended regular expression pattern. On Solaris 10 machines the name of the zone the resource belongs to can be added to the attribute: <owner>@<zone>. Owner and zone are evaluated as separate regular expressions. When no zone is specified the expression matches resources in the current zone only (<owner>@<currentzone>)."
	::= { uxsA2ConfigMQAutoEntry 5 }

uxsA2ConfigMQAutoGrp OBJECT-TYPE
	SYNTAX DisplayString
	ACCESS read-write
	STATUS mandatory
	DESCRIPTION "&<caiUxsA2.561>Group name of the owner of the message queue to be searched for during an auto discovery run. The name can constitute an extended regular expression pattern."
	::= { uxsA2ConfigMQAutoEntry 6 }

uxsA2ConfigMQAutoDescription OBJECT-TYPE
	SYNTAX DisplayString
	ACCESS read-write
	STATUS mandatory
	DESCRIPTION "&<caiUxsA2.562>Current description for the message queue auto watcher."
	::= { uxsA2ConfigMQAutoEntry 7 }

uxsA2ConfigMQAutoWatcherMatchType OBJECT-TYPE
	SYNTAX INTEGER {
		positive(1),
		negative(2)
	}
	ACCESS read-write
	STATUS mandatory
	DESCRIPTION "&<caiUxsA2.563>Current search algorithm for the message queue auto watcher. The filter is the logical AND of all attributes used to identify or otherwise narrow down resources. If set to 1 (positive), the agent searches for message queue resources that match the filter. If set to 2 (negative), the agent searches for message queue resources that do not match the filter."
	DEFVAL { 0 }
	::= { uxsA2ConfigMQAutoEntry 8 }

uxsA2ConfigMQAutoWatcherLimit OBJECT-TYPE
	SYNTAX INTEGER
	ACCESS read-write
	STATUS mandatory
	DESCRIPTION "&<caiUxsA2.564>Current minimum number of matches that causes the message queue auto watcher to be locked."
	::= { uxsA2ConfigMQAutoEntry 9 }

uxsA2ConfigMQAutoWatcherLastMatched OBJECT-TYPE
	SYNTAX INTEGER
	ACCESS read-only
	STATUS mandatory
	DESCRIPTION "&<caiUxsA2.565>Number of matches for the last message queue auto discovery run."
	::= { uxsA2ConfigMQAutoEntry 10 }

uxsA2ConfigMQAutoAggLag OBJECT-TYPE
	SYNTAX INTEGER
	ACCESS read-write
	STATUS mandatory
	DESCRIPTION "&<caiUxsA2.566>Current lag setting for the message queue auto watcher. Specifies the consecutive number of times at which any status is not in the ok state, before the aggregate status changes. This value must be greater than 0."
	::= { uxsA2ConfigMQAutoEntry 11 }

uxsA2ConfigMQAutoCBytesWarn OBJECT-TYPE
	SYNTAX DisplayString
	ACCESS read-write
	STATUS mandatory
	DESCRIPTION "&<caiUxsA2.567>Default warning threshold, in bytes, for the number of bytes in messages currently outstanding monitoring of any message queue watcher created by the auto watcher. The active warning threshold is derived from this value and represents a rising threshold. The derived value must be greater than 0.0, less than or equal to the total value (maximum capacity) of the monitored resource as specified in uxsA2StatusMQCBytesTotal, but cannot be greater than the active critical threshold. These constraints will be maintained by the agent during all configuration actions. The threshold can be specified as either an absolute value (n) or a percentage (n%). It can also be specified as the absolute value left free (nF). The value of uxsA2StatusMQCBytesTotal will be the reference value for n% and nF notations."
	::= { uxsA2ConfigMQAutoEntry 12 }

uxsA2ConfigMQAutoCBytesCrit OBJECT-TYPE
	SYNTAX DisplayString
	ACCESS read-write
	STATUS mandatory
	DESCRIPTION "&<caiUxsA2.568>Default critical threshold, in bytes, for the number of bytes in messages currently outstanding monitoring of any message queue watcher created by the auto watcher. The active critical threshold is derived from this value and represents a rising threshold. The derived value must be greater than 0.0, less than or equal to the total value (maximum capacity) of the monitored resource as specified in uxsA2StatusMQCBytesTotal, but cannot be less than the active warning threshold. These constraints will be maintained by the agent during all configuration actions. The threshold can be specified as either an absolute value (n) or a percentage (n%). It can also be specified as the absolute value left free (nF). The value of uxsA2StatusMQCBytesTotal will be the reference value for n% and nF notations."
	::= { uxsA2ConfigMQAutoEntry 13 }

uxsA2ConfigMQAutoCBytesMonitor OBJECT-TYPE
	SYNTAX INTEGER {
		do-not-monitor(1),
		warning-only(2),
		critical-only(3),
		both(4)
	}
	ACCESS read-write
	STATUS mandatory
	DESCRIPTION "&<caiUxsA2.569>Default monitor level for the number of bytes in messages currently outstanding monitoring of any message queue watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2ConfigMQAutoEntry 14 }

uxsA2ConfigMQAutoQNumWarn OBJECT-TYPE
	SYNTAX INTEGER
	ACCESS read-write
	STATUS mandatory
	DESCRIPTION "&<caiUxsA2.570>Default warning threshold for the number of messages currently outstanding monitoring of any message queue watcher created by the auto watcher. This value represents a rising threshold and must be greater than 0, but cannot be greater than the critical threshold."
	::= { uxsA2ConfigMQAutoEntry 15 }

uxsA2ConfigMQAutoQNumCrit OBJECT-TYPE
	SYNTAX INTEGER
	ACCESS read-write
	STATUS mandatory
	DESCRIPTION "&<caiUxsA2.571>Default critical threshold for the number of messages currently outstanding monitoring of any message queue watcher created by the auto watcher. This value represents a rising threshold and must be greater than 0, but cannot be less than the warning threshold."
	::= { uxsA2ConfigMQAutoEntry 16 }

uxsA2ConfigMQAutoQNumMonitor OBJECT-TYPE
	SYNTAX INTEGER {
		do-not-monitor(1),
		warning-only(2),
		critical-only(3),
		both(4)
	}
	ACCESS read-write
	STATUS mandatory
	DESCRIPTION "&<caiUxsA2.572>Default monitor level for the number of messages currently outstanding monitoring of any message queue watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2ConfigMQAutoEntry 17 }

uxsA2ConfigMQAutoLossAction OBJECT-TYPE
	SYNTAX INTEGER {
		remove(1),
		up(2),
		down-warning(3),
		down-critical(4)
	}
	ACCESS read-write
	STATUS mandatory
	DESCRIPTION "&<caiUxsA2.573>Default loss action for any message queue watcher created by the auto watcher. Specifies the action to take if the monitored message queue is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2ConfigMQAutoEntry 18 }

uxsA2ConfigMQAutoButton OBJECT-TYPE
	SYNTAX INTEGER {
		active(1),
		remove(2),
		locked(3)
	}
	ACCESS read-write
	STATUS mandatory
	DESCRIPTION "&<caiUxsA2.574>This attribute is used to enable/disable or remove the message queue auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { uxsA2ConfigMQAutoEntry 19 }

--
-- The ConfigHardwr Group
--

uxsA2ConfigHardwrPollInterval OBJECT-TYPE
	SYNTAX INTEGER
	ACCESS read-write
	STATUS mandatory
	DESCRIPTION "&<caiUxsA2.575>Time, in seconds, between collections of hardware resource information. Valid range: 30 seconds or greater."
	DEFVAL { 300 }
	::= { uxsA2ConfigHardwrGroup 1 }

uxsA2ConfigHardwrPollMethod OBJECT-TYPE
	SYNTAX INTEGER {
		disabled(1),
		poll-interval-only(2),
		poll-interval-and-query(3),
		query-only(4)
	}
	ACCESS read-write
	STATUS mandatory
	DESCRIPTION "&<caiUxsA2.576>Specifies how and when the agent collects hardware resource information. If set to 1 (disabled), the agent does not retrieve the hardware resource information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigHardwrGroup 2 }

uxsA2ConfigHardwrAutoPollInterval OBJECT-TYPE
	SYNTAX INTEGER
	ACCESS read-write
	STATUS mandatory
	DESCRIPTION "&<caiUxsA2.577>Time, in minutes, between the processing of the hardware resource auto watchers. Valid range: -1 (suspended), 30 minutes or greater."
	DEFVAL { 60 }
	::= { uxsA2ConfigHardwrGroup 3 }

uxsA2ConfigHardwrResName OBJECT-TYPE
	SYNTAX DisplayString
	ACCESS read-write
	STATUS mandatory
	DESCRIPTION "&<caiUxsA2.578>The name of the resource. This is the first index used by the agent in the different MIB tables for this resource (e.g. PowerSupply)."
	::= { uxsA2ConfigHardwrGroup 4 }

uxsA2ConfigHardwrResSubName OBJECT-TYPE
	SYNTAX DisplayString
	ACCESS read-write
	STATUS mandatory
	DESCRIPTION "&<caiUxsA2.579>The subname of the resource. This is the second index used by the agent in the different MIB tables for this resource (e.g. Voltage)."
	::= { uxsA2ConfigHardwrGroup 5 }

uxsA2ConfigHardwrInstName OBJECT-TYPE
	SYNTAX DisplayString
	ACCESS read-write
	STATUS mandatory
	DESCRIPTION "&<caiUxsA2.580>If a resource supports instances, this must be the name of an instance. The instance name is the third index used by the agent in the different MIB tables for this resource. If a resource does not support instances, <none> should be used as third index."
	::= { uxsA2ConfigHardwrGroup 6 }

uxsA2ConfigHardwrDescription OBJECT-TYPE
	SYNTAX DisplayString
	ACCESS read-write
	STATUS mandatory
	DESCRIPTION "&<caiUxsA2.581>Default description for the hardware resource watcher to add."
	::= { uxsA2ConfigHardwrGroup 7 }

uxsA2ConfigHardwrErrorMsgPattern OBJECT-TYPE
	SYNTAX DisplayString
	ACCESS read-write
	STATUS mandatory
	DESCRIPTION "&<caiUxsA2.582>An extended regular expression. If the error message matches this pattern, the error message status changes according to the error message monitor policy."
	DEFVAL { ".*" }
	::= { uxsA2ConfigHardwrGroup 8 }

uxsA2ConfigHardwrErrorMsgMonitor OBJECT-TYPE
	SYNTAX INTEGER {
		do-not-monitor(1),
		down-warning(2),
		down-critical(3)
	}
	ACCESS read-write
	STATUS mandatory
	DESCRIPTION "&<caiUxsA2.583>Default monitor level for the error message monitoring of the hardware resource watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { uxsA2ConfigHardwrGroup 9 }

uxsA2ConfigHardwrResultLag OBJECT-TYPE
	SYNTAX INTEGER
	ACCESS read-write
	STATUS mandatory
	DESCRIPTION "&<caiUxsA2.584>Default lag setting for the result monitoring of the hardware resource watcher to add. Specifies the number of consecutive threshold breaches on which the result state changes. This value must be greater than 0."
	DEFVAL { 1 }
	::= { uxsA2ConfigHardwrGroup 10 }

uxsA2ConfigHardwrResultWarnMin OBJECT-TYPE
	SYNTAX DisplayString
	ACCESS read-write
	STATUS mandatory
	DESCRIPTION "&<caiUxsA2.585>Default warning minimum threshold for the result monitoring of the hardware resource watcher to add. This value represents a declining threshold and must be equal to or greater than 0.0, equal to or greater than the critical minimum threshold, but cannot be greater than the warning maximum threshold. A value of -1 disables the evaluation of this threshold."
	DEFVAL { "-1" }
	::= { uxsA2ConfigHardwrGroup 11 }

uxsA2ConfigHardwrResultWarnMax OBJECT-TYPE
	SYNTAX DisplayString
	ACCESS read-write
	STATUS mandatory
	DESCRIPTION "&<caiUxsA2.586>Default warning maximum threshold for the result monitoring of the hardware resource watcher to add. This value represents a rising threshold and must be equal to or greater than 0.0, equal to or greater than the warning minimum threshold, but cannot be greater than the critical maximum threshold. A value of -1 disables the evaluation of this threshold."
	DEFVAL { "1.0" }
	::= { uxsA2ConfigHardwrGroup 12 }

uxsA2ConfigHardwrResultCritMin OBJECT-TYPE
	SYNTAX DisplayString
	ACCESS read-write
	STATUS mandatory
	DESCRIPTION "&<caiUxsA2.587>Default critical minimum threshold for the result monitoring of the hardware resource watcher to add. This value represents a declining threshold and must be equal to or greater than 0.0, but cannot be greater than the warning minimum threshold. A value of -1 disables the evaluation of this threshold."
	DEFVAL { "-1" }
	::= { uxsA2ConfigHardwrGroup 13 }

uxsA2ConfigHardwrResultCritMax OBJECT-TYPE
	SYNTAX DisplayString
	ACCESS read-write
	STATUS mandatory
	DESCRIPTION "&<caiUxsA2.588>Default critical maximum threshold for the result monitoring of the hardware resource watcher to add. This value represents a rising threshold and must be equal to or greater than 0.0, but cannot be less than the warning maximum threshold. A value of -1 disables the evaluation of this threshold."
	DEFVAL { "2.0" }
	::= { uxsA2ConfigHardwrGroup 14 }

uxsA2ConfigHardwrResultMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.589>Default monitor level for the result monitoring of the hardware resource watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { uxsA2ConfigHardwrGroup 15 }

uxsA2ConfigHardwrLossAction OBJECT-TYPE
	SYNTAX INTEGER {
		remove(1),
		up(2),
		down-warning(3),
		down-critical(4)
	}
	ACCESS read-write
	STATUS mandatory
	DESCRIPTION "&<caiUxsA2.590>Default loss action for the hardware resource watcher to add. Specifies the action to take if the monitored hardware resource is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { uxsA2ConfigHardwrGroup 16 }

uxsA2ConfigHardwrAutoTableWatcherName OBJECT-TYPE
	SYNTAX DisplayString
	ACCESS read-write
	STATUS mandatory
	DESCRIPTION "&<caiUxsA2.591>Name of the hardware resource auto watcher to add or remove."
	::= { uxsA2ConfigHardwrGroup 17 }

uxsA2ConfigHardwrAutoTableWatcherMatchType OBJECT-TYPE
	SYNTAX INTEGER {
		positive(1),
		negative(2)
	}
	ACCESS read-write
	STATUS mandatory
	DESCRIPTION "&<caiUxsA2.592>Default search algorithm for the hardware auto watcher to add. The filter is the logical AND of all attributes used to identify or otherwise narrow down resources. If set to 1 (positive), the agent searches for hardware resources that match the filter. If set to 2 (negative), the agent searches for hardware resources that do not match the filter."
	DEFVAL { 1 }
	::= { uxsA2ConfigHardwrGroup 18 }

uxsA2ConfigHardwrAutoTableWatcherLimit OBJECT-TYPE
	SYNTAX INTEGER
	ACCESS read-write
	STATUS mandatory
	DESCRIPTION "&<caiUxsA2.593>Default minimum number of matches that causes a lock of the hardware resource auto watcher to add."
	DEFVAL { 200 }
	::= { uxsA2ConfigHardwrGroup 19 }

uxsA2ConfigHardwrButton OBJECT-TYPE
	SYNTAX INTEGER {
		none(1),
		add(2),
		remove(3),
		add-auto(4),
		remove-auto(5)
	}
	ACCESS read-write
	STATUS mandatory
	DESCRIPTION "&<caiUxsA2.594>This attribute is used to add or remove the hardware resource watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { uxsA2ConfigHardwrGroup 20 }

uxsA2ConfigHardwrAutoCount OBJECT-TYPE
	SYNTAX INTEGER
	ACCESS read-only
	STATUS mandatory
	DESCRIPTION "&<caiUxsA2.595>Number of auto watchers in the hardware resource auto configuration table."
	::= { uxsA2ConfigHardwrGroup 21 }

uxsA2ConfigHardwrAutoLocked OBJECT-TYPE
	SYNTAX INTEGER
	ACCESS read-only
	STATUS mandatory
	DESCRIPTION "&<caiUxsA2.596>Number of auto watchers in the hardware resource auto configuration table which are currently locked."
	::= { uxsA2ConfigHardwrGroup 22 }

uxsA2ConfigHardwrAutoTable OBJECT-TYPE
	SYNTAX SEQUENCE OF UxsA2ConfigHardwrAutoEntry
	ACCESS not-accessible
	STATUS mandatory
	DESCRIPTION "&<caiUxsA2.597>Configuration table containing a list of hardware resource auto watchers."
	::= { uxsA2ConfigHardwrGroup 23 }

uxsA2ConfigHardwrAutoEntry OBJECT-TYPE
	SYNTAX UxsA2ConfigHardwrAutoEntry
	ACCESS not-accessible
	STATUS mandatory
	DESCRIPTION "&<caiUxsA2.598>Entry in the hardware resource auto watcher configuration table."
	INDEX {
		uxsA2ConfigHardwrAutoWatcherName
	}
	::= { uxsA2ConfigHardwrAutoTable 1 }

UxsA2ConfigHardwrAutoEntry ::= SEQUENCE {
	uxsA2ConfigHardwrAutoWatcherName DisplayString,
	uxsA2ConfigHardwrAutoResName DisplayString,
	uxsA2ConfigHardwrAutoResSubName DisplayString,
	uxsA2ConfigHardwrAutoInstName DisplayString,
	uxsA2ConfigHardwrAutoDescription DisplayString,
	uxsA2ConfigHardwrAutoWatcherMatchType INTEGER,
	uxsA2ConfigHardwrAutoWatcherLimit INTEGER,
	uxsA2ConfigHardwrAutoWatcherLastMatched INTEGER,
	uxsA2ConfigHardwrAutoErrorMsgPattern DisplayString,
	uxsA2ConfigHardwrAutoErrorMsgMonitor INTEGER,
	uxsA2ConfigHardwrAutoResultLag INTEGER,
	uxsA2ConfigHardwrAutoResultWarnMin DisplayString,
	uxsA2ConfigHardwrAutoResultWarnMax DisplayString,
	uxsA2ConfigHardwrAutoResultCritMin DisplayString,
	uxsA2ConfigHardwrAutoResultCritMax DisplayString,
	uxsA2ConfigHardwrAutoResultMonitor INTEGER,
	uxsA2ConfigHardwrAutoLossAction INTEGER,
	uxsA2ConfigHardwrAutoButton INTEGER
}

uxsA2ConfigHardwrAutoWatcherName OBJECT-TYPE
	SYNTAX DisplayString
	ACCESS read-only
	STATUS mandatory
	DESCRIPTION "&<caiUxsA2.599>Name of the hardware resource auto watcher."
	::= { uxsA2ConfigHardwrAutoEntry 1 }

uxsA2ConfigHardwrAutoResName OBJECT-TYPE
	SYNTAX DisplayString
	ACCESS read-write
	STATUS mandatory
	DESCRIPTION "&<caiUxsA2.600>An extended regular expression used to filter the resource names in oder to determine the set of status watchers being created for this resource."
	::= { uxsA2ConfigHardwrAutoEntry 2 }

uxsA2ConfigHardwrAutoResSubName OBJECT-TYPE
	SYNTAX DisplayString
	ACCESS read-write
	STATUS mandatory
	DESCRIPTION "&<caiUxsA2.601>An extended regular expression used to filter the resource subnames in oder to determine the set of status watchers being created for this resource."
	::= { uxsA2ConfigHardwrAutoEntry 3 }

uxsA2ConfigHardwrAutoInstName OBJECT-TYPE
	SYNTAX DisplayString
	ACCESS read-write
	STATUS mandatory
	DESCRIPTION "&<caiUxsA2.602>An extended regular expression used to filter the instance names in oder to determine the set of status watchers being created for this resource."
	::= { uxsA2ConfigHardwrAutoEntry 4 }

uxsA2ConfigHardwrAutoDescription OBJECT-TYPE
	SYNTAX DisplayString
	ACCESS read-write
	STATUS mandatory
	DESCRIPTION "&<caiUxsA2.603>Current description for the hardware resource auto watcher."
	::= { uxsA2ConfigHardwrAutoEntry 5 }

uxsA2ConfigHardwrAutoWatcherMatchType OBJECT-TYPE
	SYNTAX INTEGER {
		positive(1),
		negative(2)
	}
	ACCESS read-write
	STATUS mandatory
	DESCRIPTION "&<caiUxsA2.604>Current search algorithm for the hardware auto watcher. The filter is the logical AND of all attributes used to identify or otherwise narrow down resources. If set to 1 (positive), the agent searches for hardware resources that match the filter. If set to 2 (negative), the agent searches for hardware resources that do not match the filter."
	DEFVAL { 0 }
	::= { uxsA2ConfigHardwrAutoEntry 6 }

uxsA2ConfigHardwrAutoWatcherLimit OBJECT-TYPE
	SYNTAX INTEGER
	ACCESS read-write
	STATUS mandatory
	DESCRIPTION "&<caiUxsA2.605>Current minimum number of matches that causes the hardware resource auto watcher to be locked."
	::= { uxsA2ConfigHardwrAutoEntry 7 }

uxsA2ConfigHardwrAutoWatcherLastMatched OBJECT-TYPE
	SYNTAX INTEGER
	ACCESS read-only
	STATUS mandatory
	DESCRIPTION "&<caiUxsA2.606>Number of matches for the last hardware resource auto discovery run."
	::= { uxsA2ConfigHardwrAutoEntry 8 }

uxsA2ConfigHardwrAutoErrorMsgPattern OBJECT-TYPE
	SYNTAX DisplayString
	ACCESS read-write
	STATUS mandatory
	DESCRIPTION "&<caiUxsA2.607>An extended regular expression. If the error message matches this pattern, the error message status changes according to the error message monitor policy."
	::= { uxsA2ConfigHardwrAutoEntry 9 }

uxsA2ConfigHardwrAutoErrorMsgMonitor OBJECT-TYPE
	SYNTAX INTEGER {
		do-not-monitor(1),
		down-warning(2),
		down-critical(3)
	}
	ACCESS read-write
	STATUS mandatory
	DESCRIPTION "&<caiUxsA2.608>Default monitor level for the error message monitoring of any hardware resource watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2ConfigHardwrAutoEntry 10 }

uxsA2ConfigHardwrAutoResultLag OBJECT-TYPE
	SYNTAX INTEGER
	ACCESS read-write
	STATUS mandatory
	DESCRIPTION "&<caiUxsA2.609>Default lag setting for the result monitoring of any hardware resource watcher created by the auto watcher. Specifies the number of consecutive threshold breaches on which the result state changes. This value must be greater than 0."
	::= { uxsA2ConfigHardwrAutoEntry 11 }

uxsA2ConfigHardwrAutoResultWarnMin OBJECT-TYPE
	SYNTAX DisplayString
	ACCESS read-write
	STATUS mandatory
	DESCRIPTION "&<caiUxsA2.610>Default warning minimum threshold for the result monitoring of any hardware resource watcher created by the auto watcher. This value represents a declining threshold and must be equal to or greater than 0.0, equal to or greater than the critical minimum threshold, but cannot be greater than the warning maximum threshold. A value of -1 disables the evaluation of this threshold."
	DEFVAL { "-2" }
	::= { uxsA2ConfigHardwrAutoEntry 12 }

uxsA2ConfigHardwrAutoResultWarnMax OBJECT-TYPE
	SYNTAX DisplayString
	ACCESS read-write
	STATUS mandatory
	DESCRIPTION "&<caiUxsA2.611>Default warning maximum threshold for the result monitoring of any hardware resource watcher created by the auto watcher. This value represents a rising threshold and must be equal to or greater than 0.0, equal to or greater than the warning minimum threshold, but cannot be greater than the critical maximum threshold. A value of -1 disables the evaluation of this threshold."
	DEFVAL { "-2" }
	::= { uxsA2ConfigHardwrAutoEntry 13 }

uxsA2ConfigHardwrAutoResultCritMin OBJECT-TYPE
	SYNTAX DisplayString
	ACCESS read-write
	STATUS mandatory
	DESCRIPTION "&<caiUxsA2.612>Default critical minimum threshold for the result monitoring of any hardware resource watcher created by the auto watcher. This value represents a declining threshold and must be equal to or greater than 0.0, but cannot be greater than the warning minimum threshold. A value of -1 disables the evaluation of this threshold."
	DEFVAL { "-2" }
	::= { uxsA2ConfigHardwrAutoEntry 14 }

uxsA2ConfigHardwrAutoResultCritMax OBJECT-TYPE
	SYNTAX DisplayString
	ACCESS read-write
	STATUS mandatory
	DESCRIPTION "&<caiUxsA2.613>Default critical maximum threshold for the result monitoring of any hardware resource watcher created by the auto watcher. This value represents a rising threshold and must be equal to or greater than 0.0, but cannot be less than the warning maximum threshold. A value of -1 disables the evaluation of this threshold."
	DEFVAL { "-2" }
	::= { uxsA2ConfigHardwrAutoEntry 15 }

uxsA2ConfigHardwrAutoResultMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.614>Default monitor level for the result monitoring of any hardware resource watcher created by the auto watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2ConfigHardwrAutoEntry 16 }

uxsA2ConfigHardwrAutoLossAction OBJECT-TYPE
	SYNTAX INTEGER {
		remove(1),
		up(2),
		down-warning(3),
		down-critical(4)
	}
	ACCESS read-write
	STATUS mandatory
	DESCRIPTION "&<caiUxsA2.615>Default loss action for any hardware resource watcher created by the auto watcher. Specifies the action to take if the monitored hardware resource is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2ConfigHardwrAutoEntry 17 }

uxsA2ConfigHardwrAutoButton OBJECT-TYPE
	SYNTAX INTEGER {
		active(1),
		remove(2),
		locked(3)
	}
	ACCESS read-write
	STATUS mandatory
	DESCRIPTION "&<caiUxsA2.616>This attribute is used to enable/disable or remove the hardware resource auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { uxsA2ConfigHardwrAutoEntry 18 }

--
-- The ConfigProgrm Group
--

uxsA2ConfigProgrmPollInterval OBJECT-TYPE
	SYNTAX INTEGER
	ACCESS read-write
	STATUS mandatory
	DESCRIPTION "&<caiUxsA2.617>Time, in seconds, between collections of programmable resource information. Valid range: 30 seconds or greater."
	DEFVAL { 300 }
	::= { uxsA2ConfigProgrmGroup 1 }

uxsA2ConfigProgrmPollMethod OBJECT-TYPE
	SYNTAX INTEGER {
		disabled(1),
		poll-interval-only(2),
		poll-interval-and-query(3),
		query-only(4)
	}
	ACCESS read-write
	STATUS mandatory
	DESCRIPTION "&<caiUxsA2.618>Specifies how and when the agent collects programmable resource information. If set to 1 (disabled), the agent does not retrieve the programmable resource information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { uxsA2ConfigProgrmGroup 2 }

uxsA2ConfigProgrmAutoPollInterval OBJECT-TYPE
	SYNTAX INTEGER
	ACCESS read-write
	STATUS mandatory
	DESCRIPTION "&<caiUxsA2.619>Time, in minutes, between the processing of the programmable resource auto watchers. Valid range: -1 (suspended), 30 minutes or greater."
	DEFVAL { 60 }
	::= { uxsA2ConfigProgrmGroup 3 }

uxsA2ConfigProgrmResName OBJECT-TYPE
	SYNTAX DisplayString
	ACCESS read-write
	STATUS mandatory
	DESCRIPTION "&<caiUxsA2.620>The name of the resource. This is the first index used by the agent in the different MIB tables for this resource (e.g. PowerSupply)."
	::= { uxsA2ConfigProgrmGroup 4 }

uxsA2ConfigProgrmResSubName OBJECT-TYPE
	SYNTAX DisplayString
	ACCESS read-write
	STATUS mandatory
	DESCRIPTION "&<caiUxsA2.621>The subname of the resource. This is the second index used by the agent in the different MIB tables for this resource (e.g. Voltage)."
	::= { uxsA2ConfigProgrmGroup 5 }

uxsA2ConfigProgrmInstName OBJECT-TYPE
	SYNTAX DisplayString
	ACCESS read-write
	STATUS mandatory
	DESCRIPTION "&<caiUxsA2.622>If a resource supports instances, this must be the name of an instance. The instance name is the third index used by the agent in the different MIB tables for this resource. If a resource does not support instances, <none> should be used as third index."
	::= { uxsA2ConfigProgrmGroup 6 }

uxsA2ConfigProgrmDescription OBJECT-TYPE
	SYNTAX DisplayString
	ACCESS read-write
	STATUS mandatory
	DESCRIPTION "&<caiUxsA2.623>Default description for the programmable resource watcher to add."
	::= { uxsA2ConfigProgrmGroup 7 }

uxsA2ConfigProgrmErrorMsgPattern OBJECT-TYPE
	SYNTAX DisplayString
	ACCESS read-write
	STATUS mandatory
	DESCRIPTION "&<caiUxsA2.624>An extended regular expression. If the error message matches this pattern, the error message status changes according to the error message monitor policy."
	DEFVAL { ".*" }
	::= { uxsA2ConfigProgrmGroup 8 }

uxsA2ConfigProgrmErrorMsgMonitor OBJECT-TYPE
	SYNTAX INTEGER {
		do-not-monitor(1),
		down-warning(2),
		down-critical(3)
	}
	ACCESS read-write
	STATUS mandatory
	DESCRIPTION "&<caiUxsA2.625>Default monitor level for the error message monitoring of the programmable resource watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { uxsA2ConfigProgrmGroup 9 }

uxsA2ConfigProgrmResultLag OBJECT-TYPE
	SYNTAX INTEGER
	ACCESS read-write
	STATUS mandatory
	DESCRIPTION "&<caiUxsA2.626>Default lag setting for the result monitoring of the programmable resource watcher to add. Specifies the number of consecutive threshold breaches on which the result state changes. This value must be greater than 0."
	DEFVAL { 1 }
	::= { uxsA2ConfigProgrmGroup 10 }

uxsA2ConfigProgrmResultWarnMin OBJECT-TYPE
	SYNTAX DisplayString
	ACCESS read-write
	STATUS mandatory
	DESCRIPTION "&<caiUxsA2.627>Default warning minimum threshold for the result monitoring of the programmable resource watcher to add. This value represents a declining threshold and must be equal to or greater than 0.0, equal to or greater than the critical minimum threshold, but cannot be greater than the warning maximum threshold. A value of -1 disables the evaluation of this threshold."
	DEFVAL { "-1" }
	::= { uxsA2ConfigProgrmGroup 11 }

uxsA2ConfigProgrmResultWarnMax OBJECT-TYPE
	SYNTAX DisplayString
	ACCESS read-write
	STATUS mandatory
	DESCRIPTION "&<caiUxsA2.628>Default warning maximum threshold for the result monitoring of the programmable resource watcher to add. This value represents a rising threshold and must be equal to or greater than 0.0, equal to or greater than the warning minimum threshold, but cannot be greater than the critical maximum threshold. A value of -1 disables the evaluation of this threshold."
	DEFVAL { "1.0" }
	::= { uxsA2ConfigProgrmGroup 12 }

uxsA2ConfigProgrmResultCritMin OBJECT-TYPE
	SYNTAX DisplayString
	ACCESS read-write
	STATUS mandatory
	DESCRIPTION "&<caiUxsA2.629>Default critical minimum threshold for the result monitoring of the programmable resource watcher to add. This value represents a declining threshold and must be equal to or greater than 0.0, but cannot be greater than the warning minimum threshold. A value of -1 disables the evaluation of this threshold."
	DEFVAL { "-1" }
	::= { uxsA2ConfigProgrmGroup 13 }

uxsA2ConfigProgrmResultCritMax OBJECT-TYPE
	SYNTAX DisplayString
	ACCESS read-write
	STATUS mandatory
	DESCRIPTION "&<caiUxsA2.630>Default critical maximum threshold for the result monitoring of the programmable resource watcher to add. This value represents a rising threshold and must be equal to or greater than 0.0, but cannot be less than the warning maximum threshold. A value of -1 disables the evaluation of this threshold."
	DEFVAL { "2.0" }
	::= { uxsA2ConfigProgrmGroup 14 }

uxsA2ConfigProgrmResultMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.631>Default monitor level for the result monitoring of the programmable resource watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { uxsA2ConfigProgrmGroup 15 }

uxsA2ConfigProgrmLossAction OBJECT-TYPE
	SYNTAX INTEGER {
		remove(1),
		up(2),
		down-warning(3),
		down-critical(4)
	}
	ACCESS read-write
	STATUS mandatory
	DESCRIPTION "&<caiUxsA2.632>Default loss action for the programmable resource watcher to add. Specifies the action to take if the monitored programmable resource is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { uxsA2ConfigProgrmGroup 16 }

uxsA2ConfigProgrmAutoTableWatcherName OBJECT-TYPE
	SYNTAX DisplayString
	ACCESS read-write
	STATUS mandatory
	DESCRIPTION "&<caiUxsA2.633>Name of the programmable resource auto watcher to add or remove."
	::= { uxsA2ConfigProgrmGroup 17 }

uxsA2ConfigProgrmAutoTableWatcherMatchType OBJECT-TYPE
	SYNTAX INTEGER {
		positive(1),
		negative(2)
	}
	ACCESS read-write
	STATUS mandatory
	DESCRIPTION "&<caiUxsA2.634>Default search algorithm for the programmable auto watcher to add. The filter is the logical AND of all attributes used to identify or otherwise narrow down resources. If set to 1 (positive), the agent searches for programmable resources that match the filter. If set to 2 (negative), the agent searches for programmable resources that do not match the filter."
	DEFVAL { 1 }
	::= { uxsA2ConfigProgrmGroup 18 }

uxsA2ConfigProgrmAutoTableWatcherLimit OBJECT-TYPE
	SYNTAX INTEGER
	ACCESS read-write
	STATUS mandatory
	DESCRIPTION "&<caiUxsA2.635>Default minimum number of matches that causes a lock of the programmable resource auto watcher to add."
	DEFVAL { 200 }
	::= { uxsA2ConfigProgrmGroup 19 }

uxsA2ConfigProgrmButton OBJECT-TYPE
	SYNTAX INTEGER {
		none(1),
		add(2),
		remove(3),
		add-auto(4),
		remove-auto(5)
	}
	ACCESS read-write
	STATUS mandatory
	DESCRIPTION "&<caiUxsA2.636>This attribute is used to add or remove the programmable resource watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { uxsA2ConfigProgrmGroup 20 }

uxsA2ConfigProgrmAutoCount OBJECT-TYPE
	SYNTAX INTEGER
	ACCESS read-only
	STATUS mandatory
	DESCRIPTION "&<caiUxsA2.637>Number of auto watchers in the programmable resource auto configuration table."
	::= { uxsA2ConfigProgrmGroup 21 }

uxsA2ConfigProgrmAutoLocked OBJECT-TYPE
	SYNTAX INTEGER
	ACCESS read-only
	STATUS mandatory
	DESCRIPTION "&<caiUxsA2.638>Number of auto watchers in the programmable resource auto configuration table which are currently locked."
	::= { uxsA2ConfigProgrmGroup 22 }

uxsA2ConfigProgrmAutoTable OBJECT-TYPE
	SYNTAX SEQUENCE OF UxsA2ConfigProgrmAutoEntry
	ACCESS not-accessible
	STATUS mandatory
	DESCRIPTION "&<caiUxsA2.639>Configuration table containing a list of programmable resource auto watchers."
	::= { uxsA2ConfigProgrmGroup 23 }

uxsA2ConfigProgrmAutoEntry OBJECT-TYPE
	SYNTAX UxsA2ConfigProgrmAutoEntry
	ACCESS not-accessible
	STATUS mandatory
	DESCRIPTION "&<caiUxsA2.640>Entry in the programmable resource auto watcher configuration table."
	INDEX {
		uxsA2ConfigProgrmAutoWatcherName
	}
	::= { uxsA2ConfigProgrmAutoTable 1 }

UxsA2ConfigProgrmAutoEntry ::= SEQUENCE {
	uxsA2ConfigProgrmAutoWatcherName DisplayString,
	uxsA2ConfigProgrmAutoResName DisplayString,
	uxsA2ConfigProgrmAutoResSubName DisplayString,
	uxsA2ConfigProgrmAutoInstName DisplayString,
	uxsA2ConfigProgrmAutoDescription DisplayString,
	uxsA2ConfigProgrmAutoWatcherMatchType INTEGER,
	uxsA2ConfigProgrmAutoWatcherLimit INTEGER,
	uxsA2ConfigProgrmAutoWatcherLastMatched INTEGER,
	uxsA2ConfigProgrmAutoErrorMsgPattern DisplayString,
	uxsA2ConfigProgrmAutoErrorMsgMonitor INTEGER,
	uxsA2ConfigProgrmAutoResultLag INTEGER,
	uxsA2ConfigProgrmAutoResultWarnMin DisplayString,
	uxsA2ConfigProgrmAutoResultWarnMax DisplayString,
	uxsA2ConfigProgrmAutoResultCritMin DisplayString,
	uxsA2ConfigProgrmAutoResultCritMax DisplayString,
	uxsA2ConfigProgrmAutoResultMonitor INTEGER,
	uxsA2ConfigProgrmAutoLossAction INTEGER,
	uxsA2ConfigProgrmAutoButton INTEGER
}

uxsA2ConfigProgrmAutoWatcherName OBJECT-TYPE
	SYNTAX DisplayString
	ACCESS read-only
	STATUS mandatory
	DESCRIPTION "&<caiUxsA2.641>Name of the programmable resource auto watcher."
	::= { uxsA2ConfigProgrmAutoEntry 1 }

uxsA2ConfigProgrmAutoResName OBJECT-TYPE
	SYNTAX DisplayString
	ACCESS read-write
	STATUS mandatory
	DESCRIPTION "&<caiUxsA2.642>An extended regular expression used to filter the resource names in oder to determine the set of status watchers being created for this resource."
	::= { uxsA2ConfigProgrmAutoEntry 2 }

uxsA2ConfigProgrmAutoResSubName OBJECT-TYPE
	SYNTAX DisplayString
	ACCESS read-write
	STATUS mandatory
	DESCRIPTION "&<caiUxsA2.643>An extended regular expression used to filter the resource subnames in oder to determine the set of status watchers being created for this resource."
	::= { uxsA2ConfigProgrmAutoEntry 3 }

uxsA2ConfigProgrmAutoInstName OBJECT-TYPE
	SYNTAX DisplayString
	ACCESS read-write
	STATUS mandatory
	DESCRIPTION "&<caiUxsA2.644>An extended regular expression used to filter the instance names in oder to determine the set of status watchers being created for this resource."
	::= { uxsA2ConfigProgrmAutoEntry 4 }

uxsA2ConfigProgrmAutoDescription OBJECT-TYPE
	SYNTAX DisplayString
	ACCESS read-write
	STATUS mandatory
	DESCRIPTION "&<caiUxsA2.645>Current description for the programmable resource auto watcher."
	::= { uxsA2ConfigProgrmAutoEntry 5 }

uxsA2ConfigProgrmAutoWatcherMatchType OBJECT-TYPE
	SYNTAX INTEGER {
		positive(1),
		negative(2)
	}
	ACCESS read-write
	STATUS mandatory
	DESCRIPTION "&<caiUxsA2.646>Current search algorithm for the programmable auto watcher. The filter is the logical AND of all attributes used to identify or otherwise narrow down resources. If set to 1 (positive), the agent searches for programmable resources that match the filter. If set to 2 (negative), the agent searches for programmable resources that do not match the filter."
	DEFVAL { 0 }
	::= { uxsA2ConfigProgrmAutoEntry 6 }

uxsA2ConfigProgrmAutoWatcherLimit OBJECT-TYPE
	SYNTAX INTEGER
	ACCESS read-write
	STATUS mandatory
	DESCRIPTION "&<caiUxsA2.647>Current minimum number of matches that causes the programmable resource auto watcher to be locked."
	::= { uxsA2ConfigProgrmAutoEntry 7 }

uxsA2ConfigProgrmAutoWatcherLastMatched OBJECT-TYPE
	SYNTAX INTEGER
	ACCESS read-only
	STATUS mandatory
	DESCRIPTION "&<caiUxsA2.648>Number of matches for the last programmable resource auto discovery run."
	::= { uxsA2ConfigProgrmAutoEntry 8 }

uxsA2ConfigProgrmAutoErrorMsgPattern OBJECT-TYPE
	SYNTAX DisplayString
	ACCESS read-write
	STATUS mandatory
	DESCRIPTION "&<caiUxsA2.649>An extended regular expression. If the error message matches this pattern, the error message status changes according to the error message monitor policy."
	::= { uxsA2ConfigProgrmAutoEntry 9 }

uxsA2ConfigProgrmAutoErrorMsgMonitor OBJECT-TYPE
	SYNTAX INTEGER {
		do-not-monitor(1),
		down-warning(2),
		down-critical(3)
	}
	ACCESS read-write
	STATUS mandatory
	DESCRIPTION "&<caiUxsA2.650>Default monitor level for the error message monitoring of any programmable resource watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2ConfigProgrmAutoEntry 10 }

uxsA2ConfigProgrmAutoResultLag OBJECT-TYPE
	SYNTAX INTEGER
	ACCESS read-write
	STATUS mandatory
	DESCRIPTION "&<caiUxsA2.651>Default lag setting for the result monitoring of any programmable resource watcher created by the auto watcher. Specifies the number of consecutive threshold breaches on which the result state changes. This value must be greater than 0."
	::= { uxsA2ConfigProgrmAutoEntry 11 }

uxsA2ConfigProgrmAutoResultWarnMin OBJECT-TYPE
	SYNTAX DisplayString
	ACCESS read-write
	STATUS mandatory
	DESCRIPTION "&<caiUxsA2.652>Default warning minimum threshold for the result monitoring of any programmable resource watcher created by the auto watcher. This value represents a declining threshold and must be equal to or greater than 0.0, equal to or greater than the critical minimum threshold, but cannot be greater than the warning maximum threshold. A value of -1 disables the evaluation of this threshold."
	DEFVAL { "-2" }
	::= { uxsA2ConfigProgrmAutoEntry 12 }

uxsA2ConfigProgrmAutoResultWarnMax OBJECT-TYPE
	SYNTAX DisplayString
	ACCESS read-write
	STATUS mandatory
	DESCRIPTION "&<caiUxsA2.653>Default warning maximum threshold for the result monitoring of any programmable resource watcher created by the auto watcher. This value represents a rising threshold and must be equal to or greater than 0.0, equal to or greater than the warning minimum threshold, but cannot be greater than the critical maximum threshold. A value of -1 disables the evaluation of this threshold."
	DEFVAL { "-2" }
	::= { uxsA2ConfigProgrmAutoEntry 13 }

uxsA2ConfigProgrmAutoResultCritMin OBJECT-TYPE
	SYNTAX DisplayString
	ACCESS read-write
	STATUS mandatory
	DESCRIPTION "&<caiUxsA2.654>Default critical minimum threshold for the result monitoring of any programmable resource watcher created by the auto watcher. This value represents a declining threshold and must be equal to or greater than 0.0, but cannot be greater than the warning minimum threshold. A value of -1 disables the evaluation of this threshold."
	DEFVAL { "-2" }
	::= { uxsA2ConfigProgrmAutoEntry 14 }

uxsA2ConfigProgrmAutoResultCritMax OBJECT-TYPE
	SYNTAX DisplayString
	ACCESS read-write
	STATUS mandatory
	DESCRIPTION "&<caiUxsA2.655>Default critical maximum threshold for the result monitoring of any programmable resource watcher created by the auto watcher. This value represents a rising threshold and must be equal to or greater than 0.0, but cannot be less than the warning maximum threshold. A value of -1 disables the evaluation of this threshold."
	DEFVAL { "-2" }
	::= { uxsA2ConfigProgrmAutoEntry 15 }

uxsA2ConfigProgrmAutoResultMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.656>Default monitor level for the result monitoring of any programmable resource watcher created by the auto watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2ConfigProgrmAutoEntry 16 }

uxsA2ConfigProgrmAutoLossAction OBJECT-TYPE
	SYNTAX INTEGER {
		remove(1),
		up(2),
		down-warning(3),
		down-critical(4)
	}
	ACCESS read-write
	STATUS mandatory
	DESCRIPTION "&<caiUxsA2.657>Default loss action for any programmable resource watcher created by the auto watcher. Specifies the action to take if the monitored programmable resource is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2ConfigProgrmAutoEntry 17 }

uxsA2ConfigProgrmAutoButton OBJECT-TYPE
	SYNTAX INTEGER {
		active(1),
		remove(2),
		locked(3)
	}
	ACCESS read-write
	STATUS mandatory
	DESCRIPTION "&<caiUxsA2.658>This attribute is used to enable/disable or remove the programmable resource auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { uxsA2ConfigProgrmAutoEntry 18 }

--
-- The StatusGeneral Group
--

uxsA2StatusGeneralTotalCount OBJECT-TYPE
	SYNTAX INTEGER
	ACCESS read-only
	STATUS mandatory
	DESCRIPTION "&<caiUxsA2.659>Total number of resources that the agent is configured to monitor."
	::= { uxsA2StatusGeneralGroup 1 }

uxsA2StatusGeneralTotalWarn OBJECT-TYPE
	SYNTAX INTEGER
	ACCESS read-only
	STATUS mandatory
	DESCRIPTION "&<caiUxsA2.660>Total number of resources that the agent is configured to monitor that are in a warning state."
	::= { uxsA2StatusGeneralGroup 2 }

uxsA2StatusGeneralTotalCrit OBJECT-TYPE
	SYNTAX INTEGER
	ACCESS read-only
	STATUS mandatory
	DESCRIPTION "&<caiUxsA2.661>Total number of resources that the agent is configured to monitor that are in a critical state."
	::= { uxsA2StatusGeneralGroup 3 }

uxsA2StatusGeneralResParamCount OBJECT-TYPE
	SYNTAX INTEGER
	ACCESS read-only
	STATUS mandatory
	DESCRIPTION "&<caiUxsA2.662>Total number of OS resource parameter resources that the agent is configured to monitor."
	::= { uxsA2StatusGeneralGroup 4 }

uxsA2StatusGeneralResParamWarn OBJECT-TYPE
	SYNTAX INTEGER
	ACCESS read-only
	STATUS mandatory
	DESCRIPTION "&<caiUxsA2.663>Total number of OS resource parameter resources that the agent is configured to monitor that are in a warning state."
	::= { uxsA2StatusGeneralGroup 5 }

uxsA2StatusGeneralResParamCrit OBJECT-TYPE
	SYNTAX INTEGER
	ACCESS read-only
	STATUS mandatory
	DESCRIPTION "&<caiUxsA2.664>Total number of OS resource parameter resources that the agent is configured to monitor that are in a critical state."
	::= { uxsA2StatusGeneralGroup 6 }

uxsA2StatusGeneralCPUCount OBJECT-TYPE
	SYNTAX INTEGER
	ACCESS read-only
	STATUS mandatory
	DESCRIPTION "&<caiUxsA2.665>Total number of CPU resources that the agent is configured to monitor."
	::= { uxsA2StatusGeneralGroup 7 }

uxsA2StatusGeneralCPUWarn OBJECT-TYPE
	SYNTAX INTEGER
	ACCESS read-only
	STATUS mandatory
	DESCRIPTION "&<caiUxsA2.666>Total number of CPU resources that the agent is configured to monitor that are in a warning state."
	::= { uxsA2StatusGeneralGroup 8 }

uxsA2StatusGeneralCPUCrit OBJECT-TYPE
	SYNTAX INTEGER
	ACCESS read-only
	STATUS mandatory
	DESCRIPTION "&<caiUxsA2.667>Total number of CPU resources that the agent is configured to monitor that are in a critical state."
	::= { uxsA2StatusGeneralGroup 9 }

uxsA2StatusGeneralLoadCount OBJECT-TYPE
	SYNTAX INTEGER
	ACCESS read-only
	STATUS mandatory
	DESCRIPTION "&<caiUxsA2.668>Total number of load average resources that the agent is configured to monitor."
	::= { uxsA2StatusGeneralGroup 10 }

uxsA2StatusGeneralLoadWarn OBJECT-TYPE
	SYNTAX INTEGER
	ACCESS read-only
	STATUS mandatory
	DESCRIPTION "&<caiUxsA2.669>Total number of load average resources that the agent is configured to monitor that are in a warning state."
	::= { uxsA2StatusGeneralGroup 11 }

uxsA2StatusGeneralLoadCrit OBJECT-TYPE
	SYNTAX INTEGER
	ACCESS read-only
	STATUS mandatory
	DESCRIPTION "&<caiUxsA2.670>Total number of load average resources that the agent is configured to monitor that are in a critical state."
	::= { uxsA2StatusGeneralGroup 12 }

uxsA2StatusGeneralMemCount OBJECT-TYPE
	SYNTAX INTEGER
	ACCESS read-only
	STATUS mandatory
	DESCRIPTION "&<caiUxsA2.671>Total number of real memory resources that the agent is configured to monitor."
	::= { uxsA2StatusGeneralGroup 13 }

uxsA2StatusGeneralMemWarn OBJECT-TYPE
	SYNTAX INTEGER
	ACCESS read-only
	STATUS mandatory
	DESCRIPTION "&<caiUxsA2.672>Total number of real memory resources that the agent is configured to monitor that are in a warning state."
	::= { uxsA2StatusGeneralGroup 14 }

uxsA2StatusGeneralMemCrit OBJECT-TYPE
	SYNTAX INTEGER
	ACCESS read-only
	STATUS mandatory
	DESCRIPTION "&<caiUxsA2.673>Total number of real memory resources that the agent is configured to monitor that are in a critical state."
	::= { uxsA2StatusGeneralGroup 15 }

uxsA2StatusGeneralSwapCount OBJECT-TYPE
	SYNTAX INTEGER
	ACCESS read-only
	STATUS mandatory
	DESCRIPTION "&<caiUxsA2.674>Total number of swap resources that the agent is configured to monitor."
	::= { uxsA2StatusGeneralGroup 16 }

uxsA2StatusGeneralSwapWarn OBJECT-TYPE
	SYNTAX INTEGER
	ACCESS read-only
	STATUS mandatory
	DESCRIPTION "&<caiUxsA2.675>Total number of swap resources that the agent is configured to monitor that are in a warning state."
	::= { uxsA2StatusGeneralGroup 17 }

uxsA2StatusGeneralSwapCrit OBJECT-TYPE
	SYNTAX INTEGER
	ACCESS read-only
	STATUS mandatory
	DESCRIPTION "&<caiUxsA2.676>Total number of swap resources that the agent is configured to monitor that are in a critical state."
	::= { uxsA2StatusGeneralGroup 18 }

uxsA2StatusGeneralQuotaCount OBJECT-TYPE
	SYNTAX INTEGER
	ACCESS read-only
	STATUS mandatory
	DESCRIPTION "&<caiUxsA2.677>Total number of quota resources that the agent is configured to monitor."
	::= { uxsA2StatusGeneralGroup 19 }

uxsA2StatusGeneralQuotaWarn OBJECT-TYPE
	SYNTAX INTEGER
	ACCESS read-only
	STATUS mandatory
	DESCRIPTION "&<caiUxsA2.678>Total number of quota resources that the agent is configured to monitor that are in a warning state."
	::= { uxsA2StatusGeneralGroup 20 }

uxsA2StatusGeneralQuotaCrit OBJECT-TYPE
	SYNTAX INTEGER
	ACCESS read-only
	STATUS mandatory
	DESCRIPTION "&<caiUxsA2.679>Total number of quota resources that the agent is configured to monitor that are in a critical state."
	::= { uxsA2StatusGeneralGroup 21 }

uxsA2StatusGeneralDirCount OBJECT-TYPE
	SYNTAX INTEGER
	ACCESS read-only
	STATUS mandatory
	DESCRIPTION "&<caiUxsA2.680>Total number of directory resources that the agent is configured to monitor."
	::= { uxsA2StatusGeneralGroup 22 }

uxsA2StatusGeneralDirWarn OBJECT-TYPE
	SYNTAX INTEGER
	ACCESS read-only
	STATUS mandatory
	DESCRIPTION "&<caiUxsA2.681>Total number of directory resources that the agent is configured to monitor that are in a warning state."
	::= { uxsA2StatusGeneralGroup 23 }

uxsA2StatusGeneralDirCrit OBJECT-TYPE
	SYNTAX INTEGER
	ACCESS read-only
	STATUS mandatory
	DESCRIPTION "&<caiUxsA2.682>Total number of directory resources that the agent is configured to monitor that are in a critical state."
	::= { uxsA2StatusGeneralGroup 24 }

uxsA2StatusGeneralFSysCount OBJECT-TYPE
	SYNTAX INTEGER
	ACCESS read-only
	STATUS mandatory
	DESCRIPTION "&<caiUxsA2.683>Total number of file system resources that the agent is configured to monitor."
	::= { uxsA2StatusGeneralGroup 25 }

uxsA2StatusGeneralFSysWarn OBJECT-TYPE
	SYNTAX INTEGER
	ACCESS read-only
	STATUS mandatory
	DESCRIPTION "&<caiUxsA2.684>Total number of file system resources that the agent is configured to monitor that are in a warning state."
	::= { uxsA2StatusGeneralGroup 26 }

uxsA2StatusGeneralFSysCrit OBJECT-TYPE
	SYNTAX INTEGER
	ACCESS read-only
	STATUS mandatory
	DESCRIPTION "&<caiUxsA2.685>Total number of file system resources that the agent is configured to monitor that are in a critical state."
	::= { uxsA2StatusGeneralGroup 27 }

uxsA2StatusGeneralFileCount OBJECT-TYPE
	SYNTAX INTEGER
	ACCESS read-only
	STATUS mandatory
	DESCRIPTION "&<caiUxsA2.686>Total number of file resources that the agent is configured to monitor."
	::= { uxsA2StatusGeneralGroup 28 }

uxsA2StatusGeneralFileWarn OBJECT-TYPE
	SYNTAX INTEGER
	ACCESS read-only
	STATUS mandatory
	DESCRIPTION "&<caiUxsA2.687>Total number of file resources that the agent is configured to monitor that are in a warning state."
	::= { uxsA2StatusGeneralGroup 29 }

uxsA2StatusGeneralFileCrit OBJECT-TYPE
	SYNTAX INTEGER
	ACCESS read-only
	STATUS mandatory
	DESCRIPTION "&<caiUxsA2.688>Total number of file resources that the agent is configured to monitor that are in a critical state."
	::= { uxsA2StatusGeneralGroup 30 }

uxsA2StatusGeneralDiskCount OBJECT-TYPE
	SYNTAX INTEGER
	ACCESS read-only
	STATUS mandatory
	DESCRIPTION "&<caiUxsA2.689>Total number of disk resources that the agent is configured to monitor."
	::= { uxsA2StatusGeneralGroup 31 }

uxsA2StatusGeneralDiskWarn OBJECT-TYPE
	SYNTAX INTEGER
	ACCESS read-only
	STATUS mandatory
	DESCRIPTION "&<caiUxsA2.690>Total number of disk resources that the agent is configured to monitor that are in a warning state."
	::= { uxsA2StatusGeneralGroup 32 }

uxsA2StatusGeneralDiskCrit OBJECT-TYPE
	SYNTAX INTEGER
	ACCESS read-only
	STATUS mandatory
	DESCRIPTION "&<caiUxsA2.691>Total number of disk resources that the agent is configured to monitor that are in a critical state."
	::= { uxsA2StatusGeneralGroup 33 }

uxsA2StatusGeneralProcCount OBJECT-TYPE
	SYNTAX INTEGER
	ACCESS read-only
	STATUS mandatory
	DESCRIPTION "&<caiUxsA2.692>Total number of process resources that the agent is configured to monitor."
	::= { uxsA2StatusGeneralGroup 34 }

uxsA2StatusGeneralProcWarn OBJECT-TYPE
	SYNTAX INTEGER
	ACCESS read-only
	STATUS mandatory
	DESCRIPTION "&<caiUxsA2.693>Total number of process resources that the agent is configured to monitor that are in a warning state."
	::= { uxsA2StatusGeneralGroup 35 }

uxsA2StatusGeneralProcCrit OBJECT-TYPE
	SYNTAX INTEGER
	ACCESS read-only
	STATUS mandatory
	DESCRIPTION "&<caiUxsA2.694>Total number of process resources that the agent is configured to monitor that are in a critical state."
	::= { uxsA2StatusGeneralGroup 36 }

uxsA2StatusGeneralPrnCount OBJECT-TYPE
	SYNTAX INTEGER
	ACCESS read-only
	STATUS mandatory
	DESCRIPTION "&<caiUxsA2.695>Total number of print queue resources that the agent is configured to monitor."
	::= { uxsA2StatusGeneralGroup 37 }

uxsA2StatusGeneralPrnWarn OBJECT-TYPE
	SYNTAX INTEGER
	ACCESS read-only
	STATUS mandatory
	DESCRIPTION "&<caiUxsA2.696>Total number of print queue resources that the agent is configured to monitor that are in a warning state."
	::= { uxsA2StatusGeneralGroup 38 }

uxsA2StatusGeneralPrnCrit OBJECT-TYPE
	SYNTAX INTEGER
	ACCESS read-only
	STATUS mandatory
	DESCRIPTION "&<caiUxsA2.697>Total number of print queue resources that the agent is configured to monitor that are in a critical state."
	::= { uxsA2StatusGeneralGroup 39 }

uxsA2StatusGeneralNetCount OBJECT-TYPE
	SYNTAX INTEGER
	ACCESS read-only
	STATUS mandatory
	DESCRIPTION "&<caiUxsA2.698>Total number of network interface resources that the agent is configured to monitor."
	::= { uxsA2StatusGeneralGroup 40 }

uxsA2StatusGeneralNetWarn OBJECT-TYPE
	SYNTAX INTEGER
	ACCESS read-only
	STATUS mandatory
	DESCRIPTION "&<caiUxsA2.699>Total number of network interface resources that the agent is configured to monitor that are in a warning state."
	::= { uxsA2StatusGeneralGroup 41 }

uxsA2StatusGeneralNetCrit OBJECT-TYPE
	SYNTAX INTEGER
	ACCESS read-only
	STATUS mandatory
	DESCRIPTION "&<caiUxsA2.700>Total number of network interface resources that the agent is configured to monitor that are in a critical state."
	::= { uxsA2StatusGeneralGroup 42 }

uxsA2StatusGeneralSHMCount OBJECT-TYPE
	SYNTAX INTEGER
	ACCESS read-only
	STATUS mandatory
	DESCRIPTION "&<caiUxsA2.701>Total number of shared memory resources that the agent is configured to monitor."
	::= { uxsA2StatusGeneralGroup 43 }

uxsA2StatusGeneralSHMWarn OBJECT-TYPE
	SYNTAX INTEGER
	ACCESS read-only
	STATUS mandatory
	DESCRIPTION "&<caiUxsA2.702>Total number of shared memory resources that the agent is configured to monitor that are in a warning state."
	::= { uxsA2StatusGeneralGroup 44 }

uxsA2StatusGeneralSHMCrit OBJECT-TYPE
	SYNTAX INTEGER
	ACCESS read-only
	STATUS mandatory
	DESCRIPTION "&<caiUxsA2.703>Total number of shared memory resources that the agent is configured to monitor that are in a critical state."
	::= { uxsA2StatusGeneralGroup 45 }

uxsA2StatusGeneralSEMCount OBJECT-TYPE
	SYNTAX INTEGER
	ACCESS read-only
	STATUS mandatory
	DESCRIPTION "&<caiUxsA2.704>Total number of semaphore resources that the agent is configured to monitor."
	::= { uxsA2StatusGeneralGroup 46 }

uxsA2StatusGeneralSEMWarn OBJECT-TYPE
	SYNTAX INTEGER
	ACCESS read-only
	STATUS mandatory
	DESCRIPTION "&<caiUxsA2.705>Total number of semaphore resources that the agent is configured to monitor that are in a warning state."
	::= { uxsA2StatusGeneralGroup 47 }

uxsA2StatusGeneralSEMCrit OBJECT-TYPE
	SYNTAX INTEGER
	ACCESS read-only
	STATUS mandatory
	DESCRIPTION "&<caiUxsA2.706>Total number of semaphore resources that the agent is configured to monitor that are in a critical state."
	::= { uxsA2StatusGeneralGroup 48 }

uxsA2StatusGeneralMQCount OBJECT-TYPE
	SYNTAX INTEGER
	ACCESS read-only
	STATUS mandatory
	DESCRIPTION "&<caiUxsA2.707>Total number of message queue resources that the agent is configured to monitor."
	::= { uxsA2StatusGeneralGroup 49 }

uxsA2StatusGeneralMQWarn OBJECT-TYPE
	SYNTAX INTEGER
	ACCESS read-only
	STATUS mandatory
	DESCRIPTION "&<caiUxsA2.708>Total number of message queue resources that the agent is configured to monitor that are in a warning state."
	::= { uxsA2StatusGeneralGroup 50 }

uxsA2StatusGeneralMQCrit OBJECT-TYPE
	SYNTAX INTEGER
	ACCESS read-only
	STATUS mandatory
	DESCRIPTION "&<caiUxsA2.709>Total number of message queue resources that the agent is configured to monitor that are in a critical state."
	::= { uxsA2StatusGeneralGroup 51 }

uxsA2StatusGeneralHardwrCount OBJECT-TYPE
	SYNTAX INTEGER
	ACCESS read-only
	STATUS mandatory
	DESCRIPTION "&<caiUxsA2.710>Total number of hardware resources that the agent is configured to monitor."
	::= { uxsA2StatusGeneralGroup 52 }

uxsA2StatusGeneralHardwrWarn OBJECT-TYPE
	SYNTAX INTEGER
	ACCESS read-only
	STATUS mandatory
	DESCRIPTION "&<caiUxsA2.711>Total number of hardware resources that the agent is configured to monitor that are in a warning state."
	::= { uxsA2StatusGeneralGroup 53 }

uxsA2StatusGeneralHardwrCrit OBJECT-TYPE
	SYNTAX INTEGER
	ACCESS read-only
	STATUS mandatory
	DESCRIPTION "&<caiUxsA2.712>Total number of hardware resources that the agent is configured to monitor that are in a critical state."
	::= { uxsA2StatusGeneralGroup 54 }

uxsA2StatusGeneralProgrmCount OBJECT-TYPE
	SYNTAX INTEGER
	ACCESS read-only
	STATUS mandatory
	DESCRIPTION "&<caiUxsA2.713>Total number of programmable resources that the agent is configured to monitor."
	::= { uxsA2StatusGeneralGroup 55 }

uxsA2StatusGeneralProgrmWarn OBJECT-TYPE
	SYNTAX INTEGER
	ACCESS read-only
	STATUS mandatory
	DESCRIPTION "&<caiUxsA2.714>Total number of programmable resources that the agent is configured to monitor that are in a warning state."
	::= { uxsA2StatusGeneralGroup 56 }

uxsA2StatusGeneralProgrmCrit OBJECT-TYPE
	SYNTAX INTEGER
	ACCESS read-only
	STATUS mandatory
	DESCRIPTION "&<caiUxsA2.715>Total number of programmable resources that the agent is configured to monitor that are in a critical state."
	::= { uxsA2StatusGeneralGroup 57 }

--
-- The StatusResParam Group
--

uxsA2StatusResParamCount OBJECT-TYPE
	SYNTAX INTEGER
	ACCESS read-only
	STATUS mandatory
	DESCRIPTION "&<caiUxsA2.716>Number of entries in the OS resource parameter status table."
	::= { uxsA2StatusResParamGroup 1 }

uxsA2StatusResParamTable OBJECT-TYPE
	SYNTAX SEQUENCE OF UxsA2StatusResParamEntry
	ACCESS not-accessible
	STATUS mandatory
	DESCRIPTION "&<caiUxsA2.717>The OS resource parameter status table containing details about the currently configured OS resource parameter watchers."
	::= { uxsA2StatusResParamGroup 2 }

uxsA2StatusResParamEntry OBJECT-TYPE
	SYNTAX UxsA2StatusResParamEntry
	ACCESS not-accessible
	STATUS mandatory
	DESCRIPTION "&<caiUxsA2.718>Entry in the OS resource parameter status table."
	INDEX {
		uxsA2StatusResParamName
	}
	::= { uxsA2StatusResParamTable 1 }

UxsA2StatusResParamEntry ::= SEQUENCE {
	uxsA2StatusResParamName DisplayString,
	uxsA2StatusResParamAggStatus INTEGER,
	uxsA2StatusResParamDescription DisplayString,
	uxsA2StatusResParamUtilTotal DisplayString,
	uxsA2StatusResParamUtilValue DisplayString,
	uxsA2StatusResParamUtilLagValue INTEGER,
	uxsA2StatusResParamUtilLag INTEGER,
	uxsA2StatusResParamUtilWarnMin DisplayString,
	uxsA2StatusResParamUtilWarnMax DisplayString,
	uxsA2StatusResParamUtilCritMin DisplayString,
	uxsA2StatusResParamUtilCritMax DisplayString,
	uxsA2StatusResParamUtilMonitor INTEGER,
	uxsA2StatusResParamUtilStatus INTEGER,
	uxsA2StatusResParamCallBackRef DisplayString
}

uxsA2StatusResParamName OBJECT-TYPE
	SYNTAX DisplayString
	ACCESS read-only
	STATUS mandatory
	DESCRIPTION "&<caiUxsA2.719>Name of the OS resource parameter."
	::= { uxsA2StatusResParamEntry 1 }

uxsA2StatusResParamAggStatus OBJECT-TYPE
	SYNTAX INTEGER {
		unknown(1),
		ok(2),
		warning(3),
		critical(4),
		passive(5)
	}
	ACCESS read-only
	STATUS mandatory
	DESCRIPTION "&<caiUxsA2.720>Current aggregate status of the OS resource parameter watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { uxsA2StatusResParamEntry 2 }

uxsA2StatusResParamDescription OBJECT-TYPE
	SYNTAX DisplayString
	ACCESS read-only
	STATUS mandatory
	DESCRIPTION "&<caiUxsA2.721>Current description for the OS resource parameter watcher."
	::= { uxsA2StatusResParamEntry 3 }

uxsA2StatusResParamUtilTotal OBJECT-TYPE
	SYNTAX DisplayString
	ACCESS read-only
	STATUS mandatory
	DESCRIPTION "&<caiUxsA2.722>The total i.e. maximum value for the resource utilization monitoring of the OS resource parameter watcher."
	DEFVAL { "0" }
	::= { uxsA2StatusResParamEntry 4 }

uxsA2StatusResParamUtilValue OBJECT-TYPE
	SYNTAX DisplayString
	ACCESS read-only
	STATUS mandatory
	DESCRIPTION "&<caiUxsA2.723>Current value for the resource utilization monitoring of the OS resource parameter watcher."
	DEFVAL { "0" }
	::= { uxsA2StatusResParamEntry 5 }

uxsA2StatusResParamUtilLagValue OBJECT-TYPE
	SYNTAX INTEGER
	ACCESS read-only
	STATUS mandatory
	DESCRIPTION "&<caiUxsA2.724>Current number of consecutive threshold breaches for the resource utilization monitoring of the OS resource parameter watcher. The resource utilization state changes from ok as soon as the lag value reaches the configured value. The state reverts back to ok if a threshold is no longer breached."
	::= { uxsA2StatusResParamEntry 6 }

uxsA2StatusResParamUtilLag OBJECT-TYPE
	SYNTAX INTEGER
	ACCESS read-write
	STATUS mandatory
	DESCRIPTION "&<caiUxsA2.725>Current lag setting for the resource utilization monitoring of the OS resource parameter watcher. Specifies the number of consecutive threshold breaches on which the resource utilization state changes. This value must be greater than 0."
	::= { uxsA2StatusResParamEntry 7 }

uxsA2StatusResParamUtilWarnMin OBJECT-TYPE
	SYNTAX DisplayString
	ACCESS read-write
	STATUS mandatory
	DESCRIPTION "&<caiUxsA2.726>Current warning minimum threshold for the resource utilization monitoring of the OS resource parameter watcher. This value represents a declining threshold and must be equal to or greater than 0.0, equal to or greater than the critical minimum threshold, but cannot be greater than the warning maximum threshold. A value of -1 disables the evaluation of this threshold. The threshold can be specified as either an absolute value (n) or a percentage (n%). The value of uxsA2StatusResParamUtilTotal will be the reference value for n% notations."
	DEFVAL { "-2" }
	::= { uxsA2StatusResParamEntry 8 }

uxsA2StatusResParamUtilWarnMax OBJECT-TYPE
	SYNTAX DisplayString
	ACCESS read-write
	STATUS mandatory
	DESCRIPTION "&<caiUxsA2.727>Current warning maximum threshold for the resource utilization monitoring of the OS resource parameter watcher. This value represents a rising threshold and must be equal to or greater than 0.0, equal to or greater than the warning minimum threshold, but cannot be greater than the critical maximum threshold. A value of -1 disables the evaluation of this threshold. The threshold can be specified as either an absolute value (n) or a percentage (n%). The value of uxsA2StatusResParamUtilTotal will be the reference value for n% notations."
	DEFVAL { "-2" }
	::= { uxsA2StatusResParamEntry 9 }

uxsA2StatusResParamUtilCritMin OBJECT-TYPE
	SYNTAX DisplayString
	ACCESS read-write
	STATUS mandatory
	DESCRIPTION "&<caiUxsA2.728>Current critical minimum threshold for the resource utilization monitoring of the OS resource parameter watcher. This value represents a declining threshold and must be equal to or greater than 0.0, but cannot be greater than the warning minimum threshold. A value of -1 disables the evaluation of this threshold. The threshold can be specified as either an absolute value (n) or a percentage (n%). The value of uxsA2StatusResParamUtilTotal will be the reference value for n% notations."
	DEFVAL { "-2" }
	::= { uxsA2StatusResParamEntry 10 }

uxsA2StatusResParamUtilCritMax OBJECT-TYPE
	SYNTAX DisplayString
	ACCESS read-write
	STATUS mandatory
	DESCRIPTION "&<caiUxsA2.729>Current critical maximum threshold for the resource utilization monitoring of the OS resource parameter watcher. This value represents a rising threshold and must be equal to or greater than 0.0, but cannot be less than the warning maximum threshold. A value of -1 disables the evaluation of this threshold. The threshold can be specified as either an absolute value (n) or a percentage (n%). The value of uxsA2StatusResParamUtilTotal will be the reference value for n% notations."
	DEFVAL { "-2" }
	::= { uxsA2StatusResParamEntry 11 }

uxsA2StatusResParamUtilMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.730>Current monitor level for the resource utilization monitoring of the OS resource parameter watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2StatusResParamEntry 12 }

uxsA2StatusResParamUtilStatus OBJECT-TYPE
	SYNTAX INTEGER {
		unknown(1),
		up(2),
		down-warning(3),
		down-critical(4)
	}
	ACCESS read-only
	STATUS mandatory
	DESCRIPTION "&<caiUxsA2.731>Current status for the resource utilization monitoring of the OS resource parameter watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusResParamEntry 13 }

uxsA2StatusResParamCallBackRef OBJECT-TYPE
	SYNTAX DisplayString
	ACCESS read-only
	STATUS mandatory
	DESCRIPTION "&<caiUxsA2.732>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusResParamEntry 14 }

--
-- The StatusCPU Group
--

uxsA2StatusCPUTotalWaitIO OBJECT-TYPE
	SYNTAX INTEGER
	ACCESS read-only
	STATUS mandatory
	DESCRIPTION "&<caiUxsA2.733>The average time all CPUs have spent waiting for I/O as percentage value. Linux 2.4: not available, Linux 2.6: iowait, Solaris: wait, HP-UX: wait + swait, AIX: wait."
	::= { uxsA2StatusCPUGroup 1 }

uxsA2StatusCPUTotalSystem OBJECT-TYPE
	SYNTAX INTEGER
	ACCESS read-only
	STATUS mandatory
	DESCRIPTION "&<caiUxsA2.734>The average time of all CPUs which has been consumed by system processes as percentage value. Linux 2.4: system, Linux 2.6: system + irq + softirq, Solaris: kernel, HP-UX: sys + ssys + intr, AIX: kernel."
	::= { uxsA2StatusCPUGroup 2 }

uxsA2StatusCPUTotalUser OBJECT-TYPE
	SYNTAX INTEGER
	ACCESS read-only
	STATUS mandatory
	DESCRIPTION "&<caiUxsA2.735>The average time of all CPUs which has been consumed by user processes as percentage value. Linux: user + nice, Solaris: user, HP-UX: user + nice, AIX: user."
	::= { uxsA2StatusCPUGroup 3 }

uxsA2StatusCPUTotalIdle OBJECT-TYPE
	SYNTAX INTEGER
	ACCESS read-only
	STATUS mandatory
	DESCRIPTION "&<caiUxsA2.736>The average time all CPUs have spent in Idle state as percentage value. Linux: idle, Solaris: idle, HP-UX: idle + block, AIX: idle."
	::= { uxsA2StatusCPUGroup 4 }

uxsA2StatusCPUTotalLoadValue OBJECT-TYPE
	SYNTAX INTEGER
	ACCESS read-only
	STATUS mandatory
	DESCRIPTION "&<caiUxsA2.737>Current value, in percent, for the total CPU utilization monitoring of the CPU watcher."
	::= { uxsA2StatusCPUGroup 5 }

uxsA2StatusCPUTotalLoadLagValue OBJECT-TYPE
	SYNTAX INTEGER
	ACCESS read-only
	STATUS mandatory
	DESCRIPTION "&<caiUxsA2.738>Current number of consecutive threshold breaches for the total CPU utilization monitoring of the CPU watcher. The total CPU utilization state changes from ok as soon as the lag value reaches the configured value. The state reverts back to ok if a threshold is no longer breached."
	::= { uxsA2StatusCPUGroup 6 }

uxsA2StatusCPUTotalLoadLag OBJECT-TYPE
	SYNTAX INTEGER
	ACCESS read-write
	STATUS mandatory
	DESCRIPTION "&<caiUxsA2.739>Current lag setting for the total CPU utilization monitoring of the CPU watcher. Specifies the number of consecutive threshold breaches on which the total CPU utilization state changes. This value must be greater than 0."
	DEFVAL { 10 }
	::= { uxsA2StatusCPUGroup 7 }

uxsA2StatusCPUTotalLoadWarn OBJECT-TYPE
	SYNTAX INTEGER
	ACCESS read-write
	STATUS mandatory
	DESCRIPTION "&<caiUxsA2.740>Current warning threshold, in percent, for the total CPU utilization monitoring of the CPU watcher. This value represents a rising threshold and must be greater than 0, less than or equal to 100, but cannot be greater than the critical threshold."
	DEFVAL { 70 }
	::= { uxsA2StatusCPUGroup 8 }

uxsA2StatusCPUTotalLoadCrit OBJECT-TYPE
	SYNTAX INTEGER
	ACCESS read-write
	STATUS mandatory
	DESCRIPTION "&<caiUxsA2.741>Current critical threshold, in percent, for the total CPU utilization monitoring of the CPU watcher. This value represents a rising threshold and must be greater than 0, less than or equal to 100, but cannot be less than the warning threshold."
	DEFVAL { 90 }
	::= { uxsA2StatusCPUGroup 9 }

uxsA2StatusCPUTotalLoadMonitor OBJECT-TYPE
	SYNTAX INTEGER {
		do-not-monitor(1),
		warning-only(2),
		critical-only(3),
		both(4)
	}
	ACCESS read-write
	STATUS mandatory
	DESCRIPTION "&<caiUxsA2.742>Current monitor level for the total CPU utilization monitoring of the CPU watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2StatusCPUGroup 10 }

uxsA2StatusCPUTotalLoadStatus OBJECT-TYPE
	SYNTAX INTEGER {
		unknown(1),
		ok(2),
		warning(3),
		critical(4),
		passive(5)
	}
	ACCESS read-only
	STATUS mandatory
	DESCRIPTION "&<caiUxsA2.743>Current status for the total CPU utilization monitoring of the CPU watcher: 1 (unknown) - An error occurred during data collection, 2 (ok) - The resource is operating within the defined limits or status evaluation is turned off, 3 (warning) - The resource has breached the warning threshold, 4 (critical) - The resource has breached the critical threshold, 5 (passive) - The polling is disabled for the resource and hence no data collection occurs."
	::= { uxsA2StatusCPUGroup 11 }

uxsA2StatusCPUTotalCallBackRef OBJECT-TYPE
	SYNTAX DisplayString
	ACCESS read-only
	STATUS mandatory
	DESCRIPTION "&<caiUxsA2.744>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusCPUGroup 12 }

uxsA2StatusCPUCount OBJECT-TYPE
	SYNTAX INTEGER
	ACCESS read-only
	STATUS mandatory
	DESCRIPTION "&<caiUxsA2.745>Number of entries in the CPU status table."
	::= { uxsA2StatusCPUGroup 13 }

uxsA2StatusCPUTable OBJECT-TYPE
	SYNTAX SEQUENCE OF UxsA2StatusCPUEntry
	ACCESS not-accessible
	STATUS mandatory
	DESCRIPTION "&<caiUxsA2.746>The CPU status table containing details about the currently configured CPU watchers."
	::= { uxsA2StatusCPUGroup 14 }

uxsA2StatusCPUEntry OBJECT-TYPE
	SYNTAX UxsA2StatusCPUEntry
	ACCESS not-accessible
	STATUS mandatory
	DESCRIPTION "&<caiUxsA2.747>Entry in the CPU status table."
	INDEX {
		uxsA2StatusCPUName
	}
	::= { uxsA2StatusCPUTable 1 }

UxsA2StatusCPUEntry ::= SEQUENCE {
	uxsA2StatusCPUName DisplayString,
	uxsA2StatusCPUAggStatus INTEGER,
	uxsA2StatusCPUWaitIO INTEGER,
	uxsA2StatusCPUSystem INTEGER,
	uxsA2StatusCPUUser INTEGER,
	uxsA2StatusCPUIdle INTEGER,
	uxsA2StatusCPULoadValue INTEGER,
	uxsA2StatusCPULoadLagValue INTEGER,
	uxsA2StatusCPULoadLag INTEGER,
	uxsA2StatusCPULoadWarn INTEGER,
	uxsA2StatusCPULoadCrit INTEGER,
	uxsA2StatusCPULoadMonitor INTEGER,
	uxsA2StatusCPULoadStatus INTEGER,
	uxsA2StatusCPULossAction INTEGER,
	uxsA2StatusCPULossStatus INTEGER,
	uxsA2StatusCPUCallBackRef DisplayString
}

uxsA2StatusCPUName OBJECT-TYPE
	SYNTAX DisplayString
	ACCESS read-only
	STATUS mandatory
	DESCRIPTION "&<caiUxsA2.748>Name of the CPU."
	::= { uxsA2StatusCPUEntry 1 }

uxsA2StatusCPUAggStatus OBJECT-TYPE
	SYNTAX INTEGER {
		unknown(1),
		ok(2),
		warning(3),
		critical(4),
		passive(5)
	}
	ACCESS read-only
	STATUS mandatory
	DESCRIPTION "&<caiUxsA2.749>Current aggregate status of the CPU watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { uxsA2StatusCPUEntry 2 }

uxsA2StatusCPUWaitIO OBJECT-TYPE
	SYNTAX INTEGER
	ACCESS read-only
	STATUS mandatory
	DESCRIPTION "&<caiUxsA2.750>The time the CPU has spent waiting for I/O as percentage value. Linux 2.4: not available, Linux 2.6: iowait, Solaris: wait, HP-UX: wait + swait, AIX: wait."
	::= { uxsA2StatusCPUEntry 3 }

uxsA2StatusCPUSystem OBJECT-TYPE
	SYNTAX INTEGER
	ACCESS read-only
	STATUS mandatory
	DESCRIPTION "&<caiUxsA2.751>The CPU time which has been consumed by system processes as percentage value. Linux 2.4: system, Linux 2.6: system + irq + softirq, Solaris: kernel, HP-UX: sys + ssys + intr, AIX: kernel."
	::= { uxsA2StatusCPUEntry 4 }

uxsA2StatusCPUUser OBJECT-TYPE
	SYNTAX INTEGER
	ACCESS read-only
	STATUS mandatory
	DESCRIPTION "&<caiUxsA2.752>The CPU time which has been consumed by user processes as percentage value. Linux: user + nice, Solaris: user, HP-UX: user + nice, AIX: user."
	::= { uxsA2StatusCPUEntry 5 }

uxsA2StatusCPUIdle OBJECT-TYPE
	SYNTAX INTEGER
	ACCESS read-only
	STATUS mandatory
	DESCRIPTION "&<caiUxsA2.753>The time the CPU has spent in Idle state as percentage value. Linux: idle, Solaris: idle, HP-UX: idle + block, AIX: idle."
	::= { uxsA2StatusCPUEntry 6 }

uxsA2StatusCPULoadValue OBJECT-TYPE
	SYNTAX INTEGER
	ACCESS read-only
	STATUS mandatory
	DESCRIPTION "&<caiUxsA2.754>Current value, in percent, for the CPU utilization monitoring of the CPU watcher."
	::= { uxsA2StatusCPUEntry 7 }

uxsA2StatusCPULoadLagValue OBJECT-TYPE
	SYNTAX INTEGER
	ACCESS read-only
	STATUS mandatory
	DESCRIPTION "&<caiUxsA2.755>Current number of consecutive threshold breaches for the CPU utilization monitoring of the CPU watcher. The CPU utilization state changes from ok as soon as the lag value reaches the configured value. The state reverts back to ok if a threshold is no longer breached."
	::= { uxsA2StatusCPUEntry 8 }

uxsA2StatusCPULoadLag OBJECT-TYPE
	SYNTAX INTEGER
	ACCESS read-write
	STATUS mandatory
	DESCRIPTION "&<caiUxsA2.756>Current lag setting for the CPU utilization monitoring of the CPU watcher. Specifies the number of consecutive threshold breaches on which the CPU utilization state changes. This value must be greater than 0."
	::= { uxsA2StatusCPUEntry 9 }

uxsA2StatusCPULoadWarn OBJECT-TYPE
	SYNTAX INTEGER
	ACCESS read-write
	STATUS mandatory
	DESCRIPTION "&<caiUxsA2.757>Current warning threshold, in percent, for the CPU utilization monitoring of the CPU watcher. This value represents a rising threshold and must be greater than 0, less than or equal to 100, but cannot be greater than the critical threshold."
	::= { uxsA2StatusCPUEntry 10 }

uxsA2StatusCPULoadCrit OBJECT-TYPE
	SYNTAX INTEGER
	ACCESS read-write
	STATUS mandatory
	DESCRIPTION "&<caiUxsA2.758>Current critical threshold, in percent, for the CPU utilization monitoring of the CPU watcher. This value represents a rising threshold and must be greater than 0, less than or equal to 100, but cannot be less than the warning threshold."
	::= { uxsA2StatusCPUEntry 11 }

uxsA2StatusCPULoadMonitor OBJECT-TYPE
	SYNTAX INTEGER {
		do-not-monitor(1),
		warning-only(2),
		critical-only(3),
		both(4)
	}
	ACCESS read-write
	STATUS mandatory
	DESCRIPTION "&<caiUxsA2.759>Current monitor level for the CPU utilization monitoring of the CPU watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusCPUEntry 12 }

uxsA2StatusCPULoadStatus OBJECT-TYPE
	SYNTAX INTEGER {
		unknown(1),
		ok(2),
		warning(3),
		critical(4)
	}
	ACCESS read-only
	STATUS mandatory
	DESCRIPTION "&<caiUxsA2.760>Current status for the CPU utilization monitoring of the CPU watcher: 1 (unknown) - An error occurred during data collection, 2 (ok) - The resource is operating within the defined limits or status evaluation is turned off and/or polling is disabled, 3 (warning) - The resource has breached the warning threshold, 4 (critical) - The resource has breached the critical threshold."
	::= { uxsA2StatusCPUEntry 13 }

uxsA2StatusCPULossAction OBJECT-TYPE
	SYNTAX INTEGER {
		remove(1),
		up(2),
		down-warning(3),
		down-critical(4)
	}
	ACCESS read-write
	STATUS mandatory
	DESCRIPTION "&<caiUxsA2.761>Current loss action for the CPU watcher. Specifies the action to take if the monitored CPU is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusCPUEntry 14 }

uxsA2StatusCPULossStatus OBJECT-TYPE
	SYNTAX INTEGER {
		unknown(1),
		up(2),
		down-warning(3),
		down-critical(4)
	}
	ACCESS read-only
	STATUS mandatory
	DESCRIPTION "&<caiUxsA2.762>Current loss status of the CPU watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusCPUEntry 15 }

uxsA2StatusCPUCallBackRef OBJECT-TYPE
	SYNTAX DisplayString
	ACCESS read-only
	STATUS mandatory
	DESCRIPTION "&<caiUxsA2.763>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusCPUEntry 16 }

--
-- The StatusLoad Group
--

uxsA2StatusLoad1MinValue OBJECT-TYPE
	SYNTAX DisplayString
	ACCESS read-only
	STATUS mandatory
	DESCRIPTION "&<caiUxsA2.764>Current value, in jobs, for the 1 minute load average monitoring of the load average watcher."
	DEFVAL { "0" }
	::= { uxsA2StatusLoadGroup 1 }

uxsA2StatusLoad1MinWarn OBJECT-TYPE
	SYNTAX DisplayString
	ACCESS read-write
	STATUS mandatory
	DESCRIPTION "&<caiUxsA2.765>Current warning threshold, in jobs, for the 1 minute load average monitoring of the load average watcher. This value represents a rising threshold and must be greater than 0.0, but cannot be greater than the critical threshold."
	DEFVAL { "10.0" }
	::= { uxsA2StatusLoadGroup 2 }

uxsA2StatusLoad1MinCrit OBJECT-TYPE
	SYNTAX DisplayString
	ACCESS read-write
	STATUS mandatory
	DESCRIPTION "&<caiUxsA2.766>Current critical threshold, in jobs, for the 1 minute load average monitoring of the load average watcher. This value represents a rising threshold and must be greater than 0.0, but cannot be less than the warning threshold."
	DEFVAL { "15.0" }
	::= { uxsA2StatusLoadGroup 3 }

uxsA2StatusLoad1MinMonitor OBJECT-TYPE
	SYNTAX INTEGER {
		do-not-monitor(1),
		warning-only(2),
		critical-only(3),
		both(4)
	}
	ACCESS read-write
	STATUS mandatory
	DESCRIPTION "&<caiUxsA2.767>Current monitor level for the 1 minute load average monitoring of the load average watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2StatusLoadGroup 4 }

uxsA2StatusLoad1MinStatus OBJECT-TYPE
	SYNTAX INTEGER {
		unknown(1),
		ok(2),
		warning(3),
		critical(4),
		passive(5)
	}
	ACCESS read-only
	STATUS mandatory
	DESCRIPTION "&<caiUxsA2.768>Current status for the 1 minute load average monitoring of the load average watcher: 1 (unknown) - An error occurred during data collection, 2 (ok) - The resource is operating within the defined limits or status evaluation is turned off, 3 (warning) - The resource has breached the warning threshold, 4 (critical) - The resource has breached the critical threshold, 5 (passive) - The polling is disabled for the resource and hence no data collection occurs."
	::= { uxsA2StatusLoadGroup 5 }

uxsA2StatusLoad5MinValue OBJECT-TYPE
	SYNTAX DisplayString
	ACCESS read-only
	STATUS mandatory
	DESCRIPTION "&<caiUxsA2.769>Current value, in jobs, for the 5 minute load average monitoring of the load average watcher."
	DEFVAL { "0" }
	::= { uxsA2StatusLoadGroup 6 }

uxsA2StatusLoad5MinWarn OBJECT-TYPE
	SYNTAX DisplayString
	ACCESS read-write
	STATUS mandatory
	DESCRIPTION "&<caiUxsA2.770>Current warning threshold, in jobs, for the 5 minute load average monitoring of the load average watcher. This value represents a rising threshold and must be greater than 0.0, but cannot be greater than the critical threshold."
	DEFVAL { "7.0" }
	::= { uxsA2StatusLoadGroup 7 }

uxsA2StatusLoad5MinCrit OBJECT-TYPE
	SYNTAX DisplayString
	ACCESS read-write
	STATUS mandatory
	DESCRIPTION "&<caiUxsA2.771>Current critical threshold, in jobs, for the 5 minute load average monitoring of the load average watcher. This value represents a rising threshold and must be greater than 0.0, but cannot be less than the warning threshold."
	DEFVAL { "10.0" }
	::= { uxsA2StatusLoadGroup 8 }

uxsA2StatusLoad5MinMonitor OBJECT-TYPE
	SYNTAX INTEGER {
		do-not-monitor(1),
		warning-only(2),
		critical-only(3),
		both(4)
	}
	ACCESS read-write
	STATUS mandatory
	DESCRIPTION "&<caiUxsA2.772>Current monitor level for the 5 minute load average monitoring of the load average watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2StatusLoadGroup 9 }

uxsA2StatusLoad5MinStatus OBJECT-TYPE
	SYNTAX INTEGER {
		unknown(1),
		ok(2),
		warning(3),
		critical(4),
		passive(5)
	}
	ACCESS read-only
	STATUS mandatory
	DESCRIPTION "&<caiUxsA2.773>Current status for the 5 minute load average monitoring of the load average watcher: 1 (unknown) - An error occurred during data collection, 2 (ok) - The resource is operating within the defined limits or status evaluation is turned off, 3 (warning) - The resource has breached the warning threshold, 4 (critical) - The resource has breached the critical threshold, 5 (passive) - The polling is disabled for the resource and hence no data collection occurs."
	::= { uxsA2StatusLoadGroup 10 }

uxsA2StatusLoad15MinValue OBJECT-TYPE
	SYNTAX DisplayString
	ACCESS read-only
	STATUS mandatory
	DESCRIPTION "&<caiUxsA2.774>Current value, in jobs, for the 15 minute load average monitoring of the load average watcher."
	DEFVAL { "0" }
	::= { uxsA2StatusLoadGroup 11 }

uxsA2StatusLoad15MinWarn OBJECT-TYPE
	SYNTAX DisplayString
	ACCESS read-write
	STATUS mandatory
	DESCRIPTION "&<caiUxsA2.775>Current warning threshold, in jobs, for the 15 minute load average monitoring of the load average watcher. This value represents a rising threshold and must be greater than 0.0, but cannot be greater than the critical threshold."
	DEFVAL { "4.0" }
	::= { uxsA2StatusLoadGroup 12 }

uxsA2StatusLoad15MinCrit OBJECT-TYPE
	SYNTAX DisplayString
	ACCESS read-write
	STATUS mandatory
	DESCRIPTION "&<caiUxsA2.776>Current critical threshold, in jobs, for the 15 minute load average monitoring of the load average watcher. This value represents a rising threshold and must be greater than 0.0, but cannot be less than the warning threshold."
	DEFVAL { "6.0" }
	::= { uxsA2StatusLoadGroup 13 }

uxsA2StatusLoad15MinMonitor OBJECT-TYPE
	SYNTAX INTEGER {
		do-not-monitor(1),
		warning-only(2),
		critical-only(3),
		both(4)
	}
	ACCESS read-write
	STATUS mandatory
	DESCRIPTION "&<caiUxsA2.777>Current monitor level for the 15 minute load average monitoring of the load average watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2StatusLoadGroup 14 }

uxsA2StatusLoad15MinStatus OBJECT-TYPE
	SYNTAX INTEGER {
		unknown(1),
		ok(2),
		warning(3),
		critical(4),
		passive(5)
	}
	ACCESS read-only
	STATUS mandatory
	DESCRIPTION "&<caiUxsA2.778>Current status for the 15 minute load average monitoring of the load average watcher: 1 (unknown) - An error occurred during data collection, 2 (ok) - The resource is operating within the defined limits or status evaluation is turned off, 3 (warning) - The resource has breached the warning threshold, 4 (critical) - The resource has breached the critical threshold, 5 (passive) - The polling is disabled for the resource and hence no data collection occurs."
	::= { uxsA2StatusLoadGroup 15 }

uxsA2StatusLoadCallBackRef OBJECT-TYPE
	SYNTAX DisplayString
	ACCESS read-only
	STATUS mandatory
	DESCRIPTION "&<caiUxsA2.779>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusLoadGroup 16 }

--
-- The StatusMem Group
--

uxsA2StatusMemScanRateValue OBJECT-TYPE
	SYNTAX INTEGER
	ACCESS read-only
	STATUS mandatory
	DESCRIPTION "&<caiUxsA2.780>The current value, in scans/second, for the scan rate monitoring of the real memory watcher. Scan rate is an integer value and should be zero and fluctuate only occasionally for a short period (platform-dependent). This metric is not available and set to 0 on Linux."
	::= { uxsA2StatusMemGroup 1 }

uxsA2StatusMemScanRateLagValue OBJECT-TYPE
	SYNTAX INTEGER
	ACCESS read-only
	STATUS mandatory
	DESCRIPTION "&<caiUxsA2.781>Current number of consecutive threshold breaches for the scan rate monitoring of the real memory watcher. The scan rate state changes from ok as soon as the lag value reaches the configured value. The state reverts back to ok if a threshold is no longer breached."
	::= { uxsA2StatusMemGroup 2 }

uxsA2StatusMemScanRateLag OBJECT-TYPE
	SYNTAX INTEGER
	ACCESS read-write
	STATUS mandatory
	DESCRIPTION "&<caiUxsA2.782>Current lag setting for the scan rate monitoring of the real memory watcher. Specifies the number of consecutive threshold breaches on which the scan rate state changes. This value must be greater than 0."
	DEFVAL { 3 }
	::= { uxsA2StatusMemGroup 3 }

uxsA2StatusMemScanRateWarn OBJECT-TYPE
	SYNTAX INTEGER
	ACCESS read-write
	STATUS mandatory
	DESCRIPTION "&<caiUxsA2.783>Current warning threshold, in scans/s, for the scan rate monitoring of the real memory watcher. This value represents a rising threshold and must be greater than 0, but cannot be greater than the critical threshold."
	DEFVAL { 4 }
	::= { uxsA2StatusMemGroup 4 }

uxsA2StatusMemScanRateCrit OBJECT-TYPE
	SYNTAX INTEGER
	ACCESS read-write
	STATUS mandatory
	DESCRIPTION "&<caiUxsA2.784>Current critical threshold, in scans/s, for the scan rate monitoring of the real memory watcher. This value represents a rising threshold and must be greater than 0, but cannot be less than the warning threshold."
	DEFVAL { 7 }
	::= { uxsA2StatusMemGroup 5 }

uxsA2StatusMemScanRateMonitor OBJECT-TYPE
	SYNTAX INTEGER {
		do-not-monitor(1),
		warning-only(2),
		critical-only(3),
		both(4)
	}
	ACCESS read-write
	STATUS mandatory
	DESCRIPTION "&<caiUxsA2.785>Current monitor level for the scan rate monitoring of the real memory watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2StatusMemGroup 6 }

uxsA2StatusMemScanRateStatus OBJECT-TYPE
	SYNTAX INTEGER {
		unknown(1),
		ok(2),
		warning(3),
		critical(4),
		passive(5)
	}
	ACCESS read-only
	STATUS mandatory
	DESCRIPTION "&<caiUxsA2.786>Current status for the scan rate monitoring of the real memory watcher: 1 (unknown) - An error occurred during data collection, 2 (ok) - The resource is operating within the defined limits or status evaluation is turned off, 3 (warning) - The resource has breached the warning threshold, 4 (critical) - The resource has breached the critical threshold, 5 (passive) - The polling is disabled for the resource and hence no data collection occurs."
	::= { uxsA2StatusMemGroup 7 }

uxsA2StatusMemPageOutsValue OBJECT-TYPE
	SYNTAX INTEGER
	ACCESS read-only
	STATUS mandatory
	DESCRIPTION "&<caiUxsA2.787>Current value, in page outs/s, for the page outs monitoring of the real memory watcher."
	::= { uxsA2StatusMemGroup 8 }

uxsA2StatusMemPageOutsLagValue OBJECT-TYPE
	SYNTAX INTEGER
	ACCESS read-only
	STATUS mandatory
	DESCRIPTION "&<caiUxsA2.788>Current number of consecutive threshold breaches for the page outs monitoring of the real memory watcher. The page outs state changes from ok as soon as the lag value reaches the configured value. The state reverts back to ok if a threshold is no longer breached."
	::= { uxsA2StatusMemGroup 9 }

uxsA2StatusMemPageOutsLag OBJECT-TYPE
	SYNTAX INTEGER
	ACCESS read-write
	STATUS mandatory
	DESCRIPTION "&<caiUxsA2.789>Current lag setting for the page outs monitoring of the real memory watcher. Specifies the number of consecutive threshold breaches on which the page outs state changes. This value must be greater than 0."
	DEFVAL { 10 }
	::= { uxsA2StatusMemGroup 10 }

uxsA2StatusMemPageOutsWarn OBJECT-TYPE
	SYNTAX INTEGER
	ACCESS read-write
	STATUS mandatory
	DESCRIPTION "&<caiUxsA2.790>Current warning threshold, in page outs/s, for the page outs monitoring of the real memory watcher. This value represents a rising threshold and must be greater than 0, but cannot be greater than the critical threshold."
	DEFVAL { 50 }
	::= { uxsA2StatusMemGroup 11 }

uxsA2StatusMemPageOutsCrit OBJECT-TYPE
	SYNTAX INTEGER
	ACCESS read-write
	STATUS mandatory
	DESCRIPTION "&<caiUxsA2.791>Current critical threshold, in page outs/s, for the page outs monitoring of the real memory watcher. This value represents a rising threshold and must be greater than 0, but cannot be less than the warning threshold."
	DEFVAL { 100 }
	::= { uxsA2StatusMemGroup 12 }

uxsA2StatusMemPageOutsMonitor OBJECT-TYPE
	SYNTAX INTEGER {
		do-not-monitor(1),
		warning-only(2),
		critical-only(3),
		both(4)
	}
	ACCESS read-write
	STATUS mandatory
	DESCRIPTION "&<caiUxsA2.792>Current monitor level for the page outs monitoring of the real memory watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2StatusMemGroup 13 }

uxsA2StatusMemPageOutsStatus OBJECT-TYPE
	SYNTAX INTEGER {
		unknown(1),
		ok(2),
		warning(3),
		critical(4),
		passive(5)
	}
	ACCESS read-only
	STATUS mandatory
	DESCRIPTION "&<caiUxsA2.793>Current status for the page outs monitoring of the real memory watcher: 1 (unknown) - An error occurred during data collection, 2 (ok) - The resource is operating within the defined limits or status evaluation is turned off, 3 (warning) - The resource has breached the warning threshold, 4 (critical) - The resource has breached the critical threshold, 5 (passive) - The polling is disabled for the resource and hence no data collection occurs."
	::= { uxsA2StatusMemGroup 14 }

uxsA2StatusMemUtilNonLinear OBJECT-TYPE
	SYNTAX DisplayString
	ACCESS read-write
	STATUS mandatory
	DESCRIPTION "&<caiUxsA2.794>Parameter for non linear memory utilization calculation (a value betweeen 0.0 and 50.0). Depending on this parameter the memory utilization curve will be calculated more stretched in the upper range. The value 0.0 will calculate the linear curve."
	DEFVAL { "0.0" }
	::= { uxsA2StatusMemGroup 15 }

uxsA2StatusMemUtilTotal OBJECT-TYPE
	SYNTAX DisplayString
	ACCESS read-only
	STATUS mandatory
	DESCRIPTION "&<caiUxsA2.795>Absolute size of real memory in kilobytes."
	DEFVAL { "0" }
	::= { uxsA2StatusMemGroup 16 }

uxsA2StatusMemUtilValue OBJECT-TYPE
	SYNTAX DisplayString
	ACCESS read-only
	STATUS mandatory
	DESCRIPTION "&<caiUxsA2.796>Current value, in kilobytes, for the real memory utilization monitoring of the real memory watcher."
	DEFVAL { "0" }
	::= { uxsA2StatusMemGroup 17 }

uxsA2StatusMemUtilLagValue OBJECT-TYPE
	SYNTAX INTEGER
	ACCESS read-only
	STATUS mandatory
	DESCRIPTION "&<caiUxsA2.797>Current number of consecutive threshold breaches for the real memory utilization monitoring of the real memory watcher. The real memory utilization state changes from ok as soon as the lag value reaches the configured value. The state reverts back to ok if a threshold is no longer breached."
	::= { uxsA2StatusMemGroup 18 }

uxsA2StatusMemUtilLag OBJECT-TYPE
	SYNTAX INTEGER
	ACCESS read-write
	STATUS mandatory
	DESCRIPTION "&<caiUxsA2.798>Current lag setting for the real memory utilization monitoring of the real memory watcher. Specifies the number of consecutive threshold breaches on which the real memory utilization state changes. This value must be greater than 0."
	DEFVAL { 10 }
	::= { uxsA2StatusMemGroup 19 }

uxsA2StatusMemUtilWarnValue OBJECT-TYPE
	SYNTAX DisplayString
	ACCESS read-only
	STATUS mandatory
	DESCRIPTION "&<caiUxsA2.799>Active warning threshold, in kilobytes, as derived from the configured value for the real memory utilization monitoring of the real memory watcher. This value represents a rising threshold and must be greater than 0.0, less than or equal to the total value (maximum capacity) of the monitored resource as specified in uxsA2StatusMemUtilTotal, but cannot be greater than the active critical threshold. These constraints will be maintained by the agent during all configuration actions."
	::= { uxsA2StatusMemGroup 20 }

uxsA2StatusMemUtilCritValue OBJECT-TYPE
	SYNTAX DisplayString
	ACCESS read-only
	STATUS mandatory
	DESCRIPTION "&<caiUxsA2.800>Active critical threshold, in kilobytes, as derived from the configured value for the real memory utilization monitoring of the real memory watcher. This value represents a rising threshold and must be greater than 0.0, less than or equal to the total value (maximum capacity) of the monitored resource as specified in uxsA2StatusMemUtilTotal, but cannot be less than the active warning threshold. These constraints will be maintained by the agent during all configuration actions."
	::= { uxsA2StatusMemGroup 21 }

uxsA2StatusMemUtilWarn OBJECT-TYPE
	SYNTAX DisplayString
	ACCESS read-write
	STATUS mandatory
	DESCRIPTION "&<caiUxsA2.801>Configured warning threshold from which the active warning threshold is derived for the real memory utilization monitoring of the real memory watcher. The threshold can be specified as either an absolute value (n) or a percentage (n%). It can also be specified as the absolute value left free (nF). The value of uxsA2StatusMemUtilTotal will be the reference value for n% and nF notations."
	DEFVAL { "96.0%" }
	::= { uxsA2StatusMemGroup 22 }

uxsA2StatusMemUtilCrit OBJECT-TYPE
	SYNTAX DisplayString
	ACCESS read-write
	STATUS mandatory
	DESCRIPTION "&<caiUxsA2.802>Configured critical threshold from which the active critical threshold is derived for the real memory utilization monitoring of the real memory watcher. The threshold can be specified as either an absolute value (n) or a percentage (n%). It can also be specified as the absolute value left free (nF). The value of uxsA2StatusMemUtilTotal will be the reference value for n% and nF notations."
	DEFVAL { "99.0%" }
	::= { uxsA2StatusMemGroup 23 }

uxsA2StatusMemUtilMonitor OBJECT-TYPE
	SYNTAX INTEGER {
		do-not-monitor(1),
		warning-only(2),
		critical-only(3),
		both(4)
	}
	ACCESS read-write
	STATUS mandatory
	DESCRIPTION "&<caiUxsA2.803>Current monitor level for the real memory utilization monitoring of the real memory watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { uxsA2StatusMemGroup 24 }

uxsA2StatusMemUtilStatus OBJECT-TYPE
	SYNTAX INTEGER {
		unknown(1),
		ok(2),
		warning(3),
		critical(4),
		passive(5)
	}
	ACCESS read-only
	STATUS mandatory
	DESCRIPTION "&<caiUxsA2.804>Current status for the real memory utilization monitoring of the real memory watcher: 1 (unknown) - An error occurred during data collection, 2 (ok) - The resource is operating within the defined limits or status evaluation is turned off, 3 (warning) - The resource has breached the warning threshold, 4 (critical) - The resource has breached the critical threshold, 5 (passive) - The polling is disabled for the resource and hence no data collection occurs."
	::= { uxsA2StatusMemGroup 25 }

uxsA2StatusMemRef OBJECT-TYPE
	SYNTAX DisplayString
	ACCESS read-only
	STATUS mandatory
	DESCRIPTION "&<caiUxsA2.805>The delta of total memory size. This will be only different from zero if memory was added or removed dynamically."
	DEFVAL { "0" }
	::= { uxsA2StatusMemGroup 26 }

uxsA2StatusMemSizeValue OBJECT-TYPE
	SYNTAX INTEGER {
		not-changed(1),
		not-decreased(2),
		not-increased(3),
		changed(4),
		decreased(5),
		increased(6)
	}
	ACCESS read-only
	STATUS mandatory
	DESCRIPTION "&<caiUxsA2.806>The current value of the modification monitoring of the real memory watcher."
	::= { uxsA2StatusMemGroup 27 }

uxsA2StatusMemSize OBJECT-TYPE
	SYNTAX INTEGER {
		should-not-change(1),
		should-not-decrease(2),
		should-not-increase(3),
		reset-size(4)
	}
	ACCESS read-write
	STATUS mandatory
	DESCRIPTION "&<caiUxsA2.807>Current monitor condition for the dynamic memory reconfiguration monitoring of the real memory watcher."
	DEFVAL { 1 }
	::= { uxsA2StatusMemGroup 28 }

uxsA2StatusMemSizeMonitor OBJECT-TYPE
	SYNTAX INTEGER {
		do-not-monitor(1),
		down-warning(2),
		down-critical(3)
	}
	ACCESS read-write
	STATUS mandatory
	DESCRIPTION "&<caiUxsA2.808>Current monitor level for the dynamic memory reconfiguration monitoring of the real memory watcher. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { uxsA2StatusMemGroup 29 }

uxsA2StatusMemSizeStatus OBJECT-TYPE
	SYNTAX INTEGER {
		unknown(1),
		up(2),
		down-warning(3),
		down-critical(4),
		passive(5)
	}
	ACCESS read-only
	STATUS mandatory
	DESCRIPTION "&<caiUxsA2.809>Current status for the dynamic memory reconfiguration monitoring of the real memory watcher: 1 (unknown) - An error occurred during data collection, 2 (up) - The resource is in good condition or status evaluation is turned off, 3 (down-warning) - The resource is in bad condition and has been given a warning severity, 4 (down-critical) - The resource is in bad condition and has been given a critical severity, 5 (passive) - The polling is disabled for the resource and hence no data collection occurs."
	::= { uxsA2StatusMemGroup 30 }

uxsA2StatusMemCallBackRef OBJECT-TYPE
	SYNTAX DisplayString
	ACCESS read-only
	STATUS mandatory
	DESCRIPTION "&<caiUxsA2.810>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusMemGroup 31 }

--
-- The StatusSwap Group
--

uxsA2StatusSwapTotalSpaceTotal OBJECT-TYPE
	SYNTAX DisplayString
	ACCESS read-only
	STATUS mandatory
	DESCRIPTION "&<caiUxsA2.811>Total configured swap space on the machine (in kilobytes). On Solaris/HP-UX this may differ from the sum of all swap devices because of additional in-memory swap."
	DEFVAL { "0" }
	::= { uxsA2StatusSwapGroup 1 }

uxsA2StatusSwapTotalSpaceValue OBJECT-TYPE
	SYNTAX DisplayString
	ACCESS read-only
	STATUS mandatory
	DESCRIPTION "&<caiUxsA2.812>Current value, in kilobytes, for the total swap space utilization monitoring of the swap watcher."
	DEFVAL { "0" }
	::= { uxsA2StatusSwapGroup 2 }

uxsA2StatusSwapTotalSpaceLagValue OBJECT-TYPE
	SYNTAX INTEGER
	ACCESS read-only
	STATUS mandatory
	DESCRIPTION "&<caiUxsA2.813>Current number of consecutive threshold breaches for the total swap space utilization monitoring of the swap watcher. The total swap space utilization state changes from ok as soon as the lag value reaches the configured value. The state reverts back to ok if a threshold is no longer breached."
	::= { uxsA2StatusSwapGroup 3 }

uxsA2StatusSwapTotalSpaceLag OBJECT-TYPE
	SYNTAX INTEGER
	ACCESS read-write
	STATUS mandatory
	DESCRIPTION "&<caiUxsA2.814>Current lag setting for the total swap space utilization monitoring of the swap watcher. Specifies the number of consecutive threshold breaches on which the total swap space utilization state changes. This value must be greater than 0."
	DEFVAL { 3 }
	::= { uxsA2StatusSwapGroup 4 }

uxsA2StatusSwapTotalSpaceWarnValue OBJECT-TYPE
	SYNTAX DisplayString
	ACCESS read-only
	STATUS mandatory
	DESCRIPTION "&<caiUxsA2.815>Active warning threshold, in kilobytes, as derived from the configured value for the total swap space utilization monitoring of the swap watcher. This value represents a rising threshold and must be greater than 0.0, less than or equal to the total value (maximum capacity) of the monitored resource as specified in uxsA2StatusSwapTotalSpaceTotal, but cannot be greater than the active critical threshold. These constraints will be maintained by the agent during all configuration actions."
	::= { uxsA2StatusSwapGroup 5 }

uxsA2StatusSwapTotalSpaceCritValue OBJECT-TYPE
	SYNTAX DisplayString
	ACCESS read-only
	STATUS mandatory
	DESCRIPTION "&<caiUxsA2.816>Active critical threshold, in kilobytes, as derived from the configured value for the total swap space utilization monitoring of the swap watcher. This value represents a rising threshold and must be greater than 0.0, less than or equal to the total value (maximum capacity) of the monitored resource as specified in uxsA2StatusSwapTotalSpaceTotal, but cannot be less than the active warning threshold. These constraints will be maintained by the agent during all configuration actions."
	::= { uxsA2StatusSwapGroup 6 }

uxsA2StatusSwapTotalSpaceWarn OBJECT-TYPE
	SYNTAX DisplayString
	ACCESS read-write
	STATUS mandatory
	DESCRIPTION "&<caiUxsA2.817>Configured warning threshold from which the active warning threshold is derived for the total swap space utilization monitoring of the swap watcher. The threshold can be specified as either an absolute value (n) or a percentage (n%). It can also be specified as the absolute value left free (nF). The value of uxsA2StatusSwapTotalSpaceTotal will be the reference value for n% and nF notations."
	DEFVAL { "85.0%" }
	::= { uxsA2StatusSwapGroup 7 }

uxsA2StatusSwapTotalSpaceCrit OBJECT-TYPE
	SYNTAX DisplayString
	ACCESS read-write
	STATUS mandatory
	DESCRIPTION "&<caiUxsA2.818>Configured critical threshold from which the active critical threshold is derived for the total swap space utilization monitoring of the swap watcher. The threshold can be specified as either an absolute value (n) or a percentage (n%). It can also be specified as the absolute value left free (nF). The value of uxsA2StatusSwapTotalSpaceTotal will be the reference value for n% and nF notations."
	DEFVAL { "95.0%" }
	::= { uxsA2StatusSwapGroup 8 }

uxsA2StatusSwapTotalSpaceMonitor OBJECT-TYPE
	SYNTAX INTEGER {
		do-not-monitor(1),
		warning-only(2),
		critical-only(3),
		both(4)
	}
	ACCESS read-write
	STATUS mandatory
	DESCRIPTION "&<caiUxsA2.819>Current monitor level for the total swap space utilization monitoring of the swap watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { uxsA2StatusSwapGroup 9 }

uxsA2StatusSwapTotalSpaceStatus OBJECT-TYPE
	SYNTAX INTEGER {
		unknown(1),
		ok(2),
		warning(3),
		critical(4),
		passive(5)
	}
	ACCESS read-only
	STATUS mandatory
	DESCRIPTION "&<caiUxsA2.820>Current status for the total swap space utilization monitoring of the swap watcher: 1 (unknown) - An error occurred during data collection, 2 (ok) - The resource is operating within the defined limits or status evaluation is turned off, 3 (warning) - The resource has breached the warning threshold, 4 (critical) - The resource has breached the critical threshold, 5 (passive) - The polling is disabled for the resource and hence no data collection occurs."
	::= { uxsA2StatusSwapGroup 10 }

uxsA2StatusSwapTotalCallBackRef OBJECT-TYPE
	SYNTAX DisplayString
	ACCESS read-only
	STATUS mandatory
	DESCRIPTION "&<caiUxsA2.821>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusSwapGroup 11 }

uxsA2StatusSwapCount OBJECT-TYPE
	SYNTAX INTEGER
	ACCESS read-only
	STATUS mandatory
	DESCRIPTION "&<caiUxsA2.822>Number of entries in the swap status table."
	::= { uxsA2StatusSwapGroup 12 }

uxsA2StatusSwapTable OBJECT-TYPE
	SYNTAX SEQUENCE OF UxsA2StatusSwapEntry
	ACCESS not-accessible
	STATUS mandatory
	DESCRIPTION "&<caiUxsA2.823>The swap status table containing details about the currently configured swap watchers."
	::= { uxsA2StatusSwapGroup 13 }

uxsA2StatusSwapEntry OBJECT-TYPE
	SYNTAX UxsA2StatusSwapEntry
	ACCESS not-accessible
	STATUS mandatory
	DESCRIPTION "&<caiUxsA2.824>Entry in the swap status table."
	INDEX {
		uxsA2StatusSwapName
	}
	::= { uxsA2StatusSwapTable 1 }

UxsA2StatusSwapEntry ::= SEQUENCE {
	uxsA2StatusSwapName DisplayString,
	uxsA2StatusSwapAggStatus INTEGER,
	uxsA2StatusSwapSpaceTotal DisplayString,
	uxsA2StatusSwapSpaceValue DisplayString,
	uxsA2StatusSwapSpaceLagValue INTEGER,
	uxsA2StatusSwapSpaceLag INTEGER,
	uxsA2StatusSwapSpaceWarnValue DisplayString,
	uxsA2StatusSwapSpaceCritValue DisplayString,
	uxsA2StatusSwapSpaceWarn DisplayString,
	uxsA2StatusSwapSpaceCrit DisplayString,
	uxsA2StatusSwapSpaceMonitor INTEGER,
	uxsA2StatusSwapSpaceStatus INTEGER,
	uxsA2StatusSwapLossAction INTEGER,
	uxsA2StatusSwapLossStatus INTEGER,
	uxsA2StatusSwapCallBackRef DisplayString
}

uxsA2StatusSwapName OBJECT-TYPE
	SYNTAX DisplayString
	ACCESS read-only
	STATUS mandatory
	DESCRIPTION "&<caiUxsA2.825>Name of the swap."
	::= { uxsA2StatusSwapEntry 1 }

uxsA2StatusSwapAggStatus OBJECT-TYPE
	SYNTAX INTEGER {
		unknown(1),
		ok(2),
		warning(3),
		critical(4),
		passive(5)
	}
	ACCESS read-only
	STATUS mandatory
	DESCRIPTION "&<caiUxsA2.826>Current aggregate status of the swap watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { uxsA2StatusSwapEntry 2 }

uxsA2StatusSwapSpaceTotal OBJECT-TYPE
	SYNTAX DisplayString
	ACCESS read-only
	STATUS mandatory
	DESCRIPTION "&<caiUxsA2.827>Total size of the swap device (in kilobytes)."
	DEFVAL { "0" }
	::= { uxsA2StatusSwapEntry 3 }

uxsA2StatusSwapSpaceValue OBJECT-TYPE
	SYNTAX DisplayString
	ACCESS read-only
	STATUS mandatory
	DESCRIPTION "&<caiUxsA2.828>Current value, in kilobytes, for the swap space utilization monitoring of the swap watcher."
	DEFVAL { "0" }
	::= { uxsA2StatusSwapEntry 4 }

uxsA2StatusSwapSpaceLagValue OBJECT-TYPE
	SYNTAX INTEGER
	ACCESS read-only
	STATUS mandatory
	DESCRIPTION "&<caiUxsA2.829>Current number of consecutive threshold breaches for the swap space utilization monitoring of the swap watcher. The swap space utilization state changes from ok as soon as the lag value reaches the configured value. The state reverts back to ok if a threshold is no longer breached."
	::= { uxsA2StatusSwapEntry 5 }

uxsA2StatusSwapSpaceLag OBJECT-TYPE
	SYNTAX INTEGER
	ACCESS read-write
	STATUS mandatory
	DESCRIPTION "&<caiUxsA2.830>Current lag setting for the swap space utilization monitoring of the swap watcher. Specifies the number of consecutive threshold breaches on which the swap space utilization state changes. This value must be greater than 0."
	::= { uxsA2StatusSwapEntry 6 }

uxsA2StatusSwapSpaceWarnValue OBJECT-TYPE
	SYNTAX DisplayString
	ACCESS read-only
	STATUS mandatory
	DESCRIPTION "&<caiUxsA2.831>Active warning threshold, in kilobytes, as derived from the configured value for the swap space utilization monitoring of the swap watcher. This value represents a rising threshold and must be greater than 0.0, less than or equal to the total value (maximum capacity) of the monitored resource as specified in uxsA2StatusSwapSpaceTotal, but cannot be greater than the active critical threshold. These constraints will be maintained by the agent during all configuration actions."
	::= { uxsA2StatusSwapEntry 7 }

uxsA2StatusSwapSpaceCritValue OBJECT-TYPE
	SYNTAX DisplayString
	ACCESS read-only
	STATUS mandatory
	DESCRIPTION "&<caiUxsA2.832>Active critical threshold, in kilobytes, as derived from the configured value for the swap space utilization monitoring of the swap watcher. This value represents a rising threshold and must be greater than 0.0, less than or equal to the total value (maximum capacity) of the monitored resource as specified in uxsA2StatusSwapSpaceTotal, but cannot be less than the active warning threshold. These constraints will be maintained by the agent during all configuration actions."
	::= { uxsA2StatusSwapEntry 8 }

uxsA2StatusSwapSpaceWarn OBJECT-TYPE
	SYNTAX DisplayString
	ACCESS read-write
	STATUS mandatory
	DESCRIPTION "&<caiUxsA2.833>Configured warning threshold from which the active warning threshold is derived for the swap space utilization monitoring of the swap watcher. The threshold can be specified as either an absolute value (n) or a percentage (n%). It can also be specified as the absolute value left free (nF). The value of uxsA2StatusSwapSpaceTotal will be the reference value for n% and nF notations."
	::= { uxsA2StatusSwapEntry 9 }

uxsA2StatusSwapSpaceCrit OBJECT-TYPE
	SYNTAX DisplayString
	ACCESS read-write
	STATUS mandatory
	DESCRIPTION "&<caiUxsA2.834>Configured critical threshold from which the active critical threshold is derived for the swap space utilization monitoring of the swap watcher. The threshold can be specified as either an absolute value (n) or a percentage (n%). It can also be specified as the absolute value left free (nF). The value of uxsA2StatusSwapSpaceTotal will be the reference value for n% and nF notations."
	::= { uxsA2StatusSwapEntry 10 }

uxsA2StatusSwapSpaceMonitor OBJECT-TYPE
	SYNTAX INTEGER {
		do-not-monitor(1),
		warning-only(2),
		critical-only(3),
		both(4)
	}
	ACCESS read-write
	STATUS mandatory
	DESCRIPTION "&<caiUxsA2.835>Current monitor level for the swap space utilization monitoring of the swap watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusSwapEntry 11 }

uxsA2StatusSwapSpaceStatus OBJECT-TYPE
	SYNTAX INTEGER {
		unknown(1),
		ok(2),
		warning(3),
		critical(4)
	}
	ACCESS read-only
	STATUS mandatory
	DESCRIPTION "&<caiUxsA2.836>Current status for the swap space utilization monitoring of the swap watcher: 1 (unknown) - An error occurred during data collection, 2 (ok) - The resource is operating within the defined limits or status evaluation is turned off and/or polling is disabled, 3 (warning) - The resource has breached the warning threshold, 4 (critical) - The resource has breached the critical threshold."
	::= { uxsA2StatusSwapEntry 12 }

uxsA2StatusSwapLossAction OBJECT-TYPE
	SYNTAX INTEGER {
		remove(1),
		up(2),
		down-warning(3),
		down-critical(4)
	}
	ACCESS read-write
	STATUS mandatory
	DESCRIPTION "&<caiUxsA2.837>Current loss action for the swap watcher. Specifies the action to take if the monitored swap is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusSwapEntry 13 }

uxsA2StatusSwapLossStatus OBJECT-TYPE
	SYNTAX INTEGER {
		unknown(1),
		up(2),
		down-warning(3),
		down-critical(4)
	}
	ACCESS read-only
	STATUS mandatory
	DESCRIPTION "&<caiUxsA2.838>Current loss status of the swap watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusSwapEntry 14 }

uxsA2StatusSwapCallBackRef OBJECT-TYPE
	SYNTAX DisplayString
	ACCESS read-only
	STATUS mandatory
	DESCRIPTION "&<caiUxsA2.839>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusSwapEntry 15 }

--
-- The StatusQuota Group
--

uxsA2StatusQuotaCount OBJECT-TYPE
	SYNTAX INTEGER
	ACCESS read-only
	STATUS mandatory
	DESCRIPTION "&<caiUxsA2.840>Number of entries in the quota status table."
	::= { uxsA2StatusQuotaGroup 1 }

uxsA2StatusQuotaTable OBJECT-TYPE
	SYNTAX SEQUENCE OF UxsA2StatusQuotaEntry
	ACCESS not-accessible
	STATUS mandatory
	DESCRIPTION "&<caiUxsA2.841>The quota status table containing details about the currently configured quota watchers."
	::= { uxsA2StatusQuotaGroup 2 }

uxsA2StatusQuotaEntry OBJECT-TYPE
	SYNTAX UxsA2StatusQuotaEntry
	ACCESS not-accessible
	STATUS mandatory
	DESCRIPTION "&<caiUxsA2.842>Entry in the quota status table."
	INDEX {
		uxsA2StatusQuotaFSys,
		uxsA2StatusQuotaUser
	}
	::= { uxsA2StatusQuotaTable 1 }

UxsA2StatusQuotaEntry ::= SEQUENCE {
	uxsA2StatusQuotaFSys DisplayString,
	uxsA2StatusQuotaUser DisplayString,
	uxsA2StatusQuotaDescription DisplayString,
	uxsA2StatusQuotaAutoWatcherName DisplayString,
	uxsA2StatusQuotaAggLagValue INTEGER,
	uxsA2StatusQuotaAggLag INTEGER,
	uxsA2StatusQuotaAggStatus INTEGER,
	uxsA2StatusQuotaSpaceTotal DisplayString,
	uxsA2StatusQuotaSpaceSoftLimit DisplayString,
	uxsA2StatusQuotaSpaceValue DisplayString,
	uxsA2StatusQuotaSpaceWarnValue DisplayString,
	uxsA2StatusQuotaSpaceCritValue DisplayString,
	uxsA2StatusQuotaSpaceWarn DisplayString,
	uxsA2StatusQuotaSpaceCrit DisplayString,
	uxsA2StatusQuotaSpaceMonitor INTEGER,
	uxsA2StatusQuotaSpaceStatus INTEGER,
	uxsA2StatusQuotaInodesTotal DisplayString,
	uxsA2StatusQuotaInodesSoftLimit DisplayString,
	uxsA2StatusQuotaInodesValue DisplayString,
	uxsA2StatusQuotaInodesWarnValue DisplayString,
	uxsA2StatusQuotaInodesCritValue DisplayString,
	uxsA2StatusQuotaInodesWarn DisplayString,
	uxsA2StatusQuotaInodesCrit DisplayString,
	uxsA2StatusQuotaInodesMonitor INTEGER,
	uxsA2StatusQuotaInodesStatus INTEGER,
	uxsA2StatusQuotaExpiredSpaceValue INTEGER,
	uxsA2StatusQuotaExpiredSpaceMonitor INTEGER,
	uxsA2StatusQuotaExpiredSpaceStatus INTEGER,
	uxsA2StatusQuotaExpiredInodesValue INTEGER,
	uxsA2StatusQuotaExpiredInodesMonitor INTEGER,
	uxsA2StatusQuotaExpiredInodesStatus INTEGER,
	uxsA2StatusQuotaLossAction INTEGER,
	uxsA2StatusQuotaLossStatus INTEGER,
	uxsA2StatusQuotaCallBackRef DisplayString,
	uxsA2StatusQuotaButton INTEGER
}

uxsA2StatusQuotaFSys OBJECT-TYPE
	SYNTAX DisplayString
	ACCESS read-only
	STATUS mandatory
	DESCRIPTION "&<caiUxsA2.843>Name of the file system for which quotas are enabled."
	::= { uxsA2StatusQuotaEntry 1 }

uxsA2StatusQuotaUser OBJECT-TYPE
	SYNTAX DisplayString
	ACCESS read-only
	STATUS mandatory
	DESCRIPTION "&<caiUxsA2.844>Name of the user for which quota information exists on the corresponding file system."
	::= { uxsA2StatusQuotaEntry 2 }

uxsA2StatusQuotaDescription OBJECT-TYPE
	SYNTAX DisplayString
	ACCESS read-write
	STATUS mandatory
	DESCRIPTION "&<caiUxsA2.845>Current description for the quota watcher."
	::= { uxsA2StatusQuotaEntry 3 }

uxsA2StatusQuotaAutoWatcherName OBJECT-TYPE
	SYNTAX DisplayString
	ACCESS read-only
	STATUS mandatory
	DESCRIPTION "&<caiUxsA2.846>Name of the quota auto watcher which automatically created this watcher. This attribute is left blank if the watcher was added manually."
	::= { uxsA2StatusQuotaEntry 4 }

uxsA2StatusQuotaAggLagValue OBJECT-TYPE
	SYNTAX INTEGER
	ACCESS read-only
	STATUS mandatory
	DESCRIPTION "&<caiUxsA2.847>Current aggregate lag value of the quota watcher. Indicates the consecutive number of times at which any status was not in the ok state. The aggregate status changes from ok as soon as the aggregate lag value reaches the configured value."
	::= { uxsA2StatusQuotaEntry 5 }

uxsA2StatusQuotaAggLag OBJECT-TYPE
	SYNTAX INTEGER
	ACCESS read-write
	STATUS mandatory
	DESCRIPTION "&<caiUxsA2.848>Current aggregate lag setting for the quota watcher. Specifies the consecutive number of times at which any status is not in the ok state, before the aggregate status changes. This value must be greater than 0."
	::= { uxsA2StatusQuotaEntry 6 }

uxsA2StatusQuotaAggStatus OBJECT-TYPE
	SYNTAX INTEGER {
		unknown(1),
		ok(2),
		warning(3),
		critical(4),
		passive(5)
	}
	ACCESS read-only
	STATUS mandatory
	DESCRIPTION "&<caiUxsA2.849>Current aggregate status of the quota watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { uxsA2StatusQuotaEntry 7 }

uxsA2StatusQuotaSpaceTotal OBJECT-TYPE
	SYNTAX DisplayString
	ACCESS read-only
	STATUS mandatory
	DESCRIPTION "&<caiUxsA2.850>The current total value, in kilobytes, for the space utilization monitoring of the quota watcher."
	DEFVAL { "0" }
	::= { uxsA2StatusQuotaEntry 8 }

uxsA2StatusQuotaSpaceSoftLimit OBJECT-TYPE
	SYNTAX DisplayString
	ACCESS read-only
	STATUS mandatory
	DESCRIPTION "&<caiUxsA2.851>Software limit, in kilobytes, for the space utilization monitoring of the quota watcher."
	DEFVAL { "0" }
	::= { uxsA2StatusQuotaEntry 9 }

uxsA2StatusQuotaSpaceValue OBJECT-TYPE
	SYNTAX DisplayString
	ACCESS read-only
	STATUS mandatory
	DESCRIPTION "&<caiUxsA2.852>Current value, in kilobytes, for the space utilization monitoring of the quota watcher."
	DEFVAL { "0" }
	::= { uxsA2StatusQuotaEntry 10 }

uxsA2StatusQuotaSpaceWarnValue OBJECT-TYPE
	SYNTAX DisplayString
	ACCESS read-only
	STATUS mandatory
	DESCRIPTION "&<caiUxsA2.853>Active warning threshold, in kilobytes, as derived from the configured value for the space utilization monitoring of the quota watcher. This value represents a rising threshold and must be greater than 0.0, less than or equal to the total value (maximum capacity) of the monitored resource as specified in uxsA2StatusQuotaSpaceTotal, but cannot be greater than the active critical threshold. These constraints will be maintained by the agent during all configuration actions."
	::= { uxsA2StatusQuotaEntry 11 }

uxsA2StatusQuotaSpaceCritValue OBJECT-TYPE
	SYNTAX DisplayString
	ACCESS read-only
	STATUS mandatory
	DESCRIPTION "&<caiUxsA2.854>Active critical threshold, in kilobytes, as derived from the configured value for the space utilization monitoring of the quota watcher. This value represents a rising threshold and must be greater than 0.0, less than or equal to the total value (maximum capacity) of the monitored resource as specified in uxsA2StatusQuotaSpaceTotal, but cannot be less than the active warning threshold. These constraints will be maintained by the agent during all configuration actions."
	::= { uxsA2StatusQuotaEntry 12 }

uxsA2StatusQuotaSpaceWarn OBJECT-TYPE
	SYNTAX DisplayString
	ACCESS read-write
	STATUS mandatory
	DESCRIPTION "&<caiUxsA2.855>Configured warning threshold from which the active warning threshold is derived for the space utilization monitoring of the quota watcher. The threshold can be specified as either an absolute value (n) or a percentage (n%). It can also be specified as the absolute value left free (nF). The value of uxsA2StatusQuotaSpaceTotal will be the reference value for n% and nF notations."
	::= { uxsA2StatusQuotaEntry 13 }

uxsA2StatusQuotaSpaceCrit OBJECT-TYPE
	SYNTAX DisplayString
	ACCESS read-write
	STATUS mandatory
	DESCRIPTION "&<caiUxsA2.856>Configured critical threshold from which the active critical threshold is derived for the space utilization monitoring of the quota watcher. The threshold can be specified as either an absolute value (n) or a percentage (n%). It can also be specified as the absolute value left free (nF). The value of uxsA2StatusQuotaSpaceTotal will be the reference value for n% and nF notations."
	::= { uxsA2StatusQuotaEntry 14 }

uxsA2StatusQuotaSpaceMonitor OBJECT-TYPE
	SYNTAX INTEGER {
		do-not-monitor(1),
		warning-only(2),
		critical-only(3),
		both(4)
	}
	ACCESS read-write
	STATUS mandatory
	DESCRIPTION "&<caiUxsA2.857>Current monitor level for the space utilization monitoring of the quota watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusQuotaEntry 15 }

uxsA2StatusQuotaSpaceStatus OBJECT-TYPE
	SYNTAX INTEGER {
		unknown(1),
		ok(2),
		warning(3),
		critical(4)
	}
	ACCESS read-only
	STATUS mandatory
	DESCRIPTION "&<caiUxsA2.858>Current status for the space utilization monitoring of the quota watcher: 1 (unknown) - An error occurred during data collection, 2 (ok) - The resource is operating within the defined limits or status evaluation is turned off and/or polling is disabled, 3 (warning) - The resource has breached the warning threshold, 4 (critical) - The resource has breached the critical threshold."
	::= { uxsA2StatusQuotaEntry 16 }

uxsA2StatusQuotaInodesTotal OBJECT-TYPE
	SYNTAX DisplayString
	ACCESS read-only
	STATUS mandatory
	DESCRIPTION "&<caiUxsA2.859>The current total value for the inodes utilization monitoring of the quota watcher."
	DEFVAL { "0" }
	::= { uxsA2StatusQuotaEntry 17 }

uxsA2StatusQuotaInodesSoftLimit OBJECT-TYPE
	SYNTAX DisplayString
	ACCESS read-only
	STATUS mandatory
	DESCRIPTION "&<caiUxsA2.860>Software limit for the inodes utilization monitoring of the quota watcher."
	DEFVAL { "0" }
	::= { uxsA2StatusQuotaEntry 18 }

uxsA2StatusQuotaInodesValue OBJECT-TYPE
	SYNTAX DisplayString
	ACCESS read-only
	STATUS mandatory
	DESCRIPTION "&<caiUxsA2.861>Current value for the inodes utilization monitoring of the quota watcher."
	DEFVAL { "0" }
	::= { uxsA2StatusQuotaEntry 19 }

uxsA2StatusQuotaInodesWarnValue OBJECT-TYPE
	SYNTAX DisplayString
	ACCESS read-only
	STATUS mandatory
	DESCRIPTION "&<caiUxsA2.862>Active warning threshold as derived from the configured value for the inodes utilization monitoring of the quota watcher. This value represents a rising threshold and must be greater than 0.0, less than or equal to the total value (maximum capacity) of the monitored resource as specified in uxsA2StatusQuotaInodesTotal, but cannot be greater than the active critical threshold. These constraints will be maintained by the agent during all configuration actions."
	::= { uxsA2StatusQuotaEntry 20 }

uxsA2StatusQuotaInodesCritValue OBJECT-TYPE
	SYNTAX DisplayString
	ACCESS read-only
	STATUS mandatory
	DESCRIPTION "&<caiUxsA2.863>Active critical threshold as derived from the configured value for the inodes utilization monitoring of the quota watcher. This value represents a rising threshold and must be greater than 0.0, less than or equal to the total value (maximum capacity) of the monitored resource as specified in uxsA2StatusQuotaInodesTotal, but cannot be less than the active warning threshold. These constraints will be maintained by the agent during all configuration actions."
	::= { uxsA2StatusQuotaEntry 21 }

uxsA2StatusQuotaInodesWarn OBJECT-TYPE
	SYNTAX DisplayString
	ACCESS read-write
	STATUS mandatory
	DESCRIPTION "&<caiUxsA2.864>Configured warning threshold from which the active warning threshold is derived for the inodes utilization monitoring of the quota watcher. The threshold can be specified as either an absolute value (n) or a percentage (n%). It can also be specified as the absolute value left free (nF). The value of uxsA2StatusQuotaInodesTotal will be the reference value for n% and nF notations."
	::= { uxsA2StatusQuotaEntry 22 }

uxsA2StatusQuotaInodesCrit OBJECT-TYPE
	SYNTAX DisplayString
	ACCESS read-write
	STATUS mandatory
	DESCRIPTION "&<caiUxsA2.865>Configured critical threshold from which the active critical threshold is derived for the inodes utilization monitoring of the quota watcher. The threshold can be specified as either an absolute value (n) or a percentage (n%). It can also be specified as the absolute value left free (nF). The value of uxsA2StatusQuotaInodesTotal will be the reference value for n% and nF notations."
	::= { uxsA2StatusQuotaEntry 23 }

uxsA2StatusQuotaInodesMonitor OBJECT-TYPE
	SYNTAX INTEGER {
		do-not-monitor(1),
		warning-only(2),
		critical-only(3),
		both(4)
	}
	ACCESS read-write
	STATUS mandatory
	DESCRIPTION "&<caiUxsA2.866>Current monitor level for the inodes utilization monitoring of the quota watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusQuotaEntry 24 }

uxsA2StatusQuotaInodesStatus OBJECT-TYPE
	SYNTAX INTEGER {
		unknown(1),
		ok(2),
		warning(3),
		critical(4)
	}
	ACCESS read-only
	STATUS mandatory
	DESCRIPTION "&<caiUxsA2.867>Current status for the inodes utilization monitoring of the quota watcher: 1 (unknown) - An error occurred during data collection, 2 (ok) - The resource is operating within the defined limits or status evaluation is turned off and/or polling is disabled, 3 (warning) - The resource has breached the warning threshold, 4 (critical) - The resource has breached the critical threshold."
	::= { uxsA2StatusQuotaEntry 25 }

uxsA2StatusQuotaExpiredSpaceValue OBJECT-TYPE
	SYNTAX INTEGER {
		not-expired(1),
		expired(2)
	}
	ACCESS read-only
	STATUS mandatory
	DESCRIPTION "&<caiUxsA2.868>The current expired space value for the expired space monitoring of the quota watcher."
	::= { uxsA2StatusQuotaEntry 26 }

uxsA2StatusQuotaExpiredSpaceMonitor OBJECT-TYPE
	SYNTAX INTEGER {
		do-not-monitor(1),
		down-warning(2),
		down-critical(3)
	}
	ACCESS read-write
	STATUS mandatory
	DESCRIPTION "&<caiUxsA2.869>Current monitor level for the expired space monitoring of the quota watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusQuotaEntry 27 }

uxsA2StatusQuotaExpiredSpaceStatus OBJECT-TYPE
	SYNTAX INTEGER {
		unknown(1),
		up(2),
		down-warning(3),
		down-critical(4)
	}
	ACCESS read-only
	STATUS mandatory
	DESCRIPTION "&<caiUxsA2.870>Current status for the expired space monitoring of the quota watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusQuotaEntry 28 }

uxsA2StatusQuotaExpiredInodesValue OBJECT-TYPE
	SYNTAX INTEGER {
		not-expired(1),
		expired(2)
	}
	ACCESS read-only
	STATUS mandatory
	DESCRIPTION "&<caiUxsA2.871>The current expired inodes value for the inodes utilization monitoring of the quota watcher."
	::= { uxsA2StatusQuotaEntry 29 }

uxsA2StatusQuotaExpiredInodesMonitor OBJECT-TYPE
	SYNTAX INTEGER {
		do-not-monitor(1),
		down-warning(2),
		down-critical(3)
	}
	ACCESS read-write
	STATUS mandatory
	DESCRIPTION "&<caiUxsA2.872>Current monitor level for the expired inodes monitoring of the quota watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusQuotaEntry 30 }

uxsA2StatusQuotaExpiredInodesStatus OBJECT-TYPE
	SYNTAX INTEGER {
		unknown(1),
		up(2),
		down-warning(3),
		down-critical(4)
	}
	ACCESS read-only
	STATUS mandatory
	DESCRIPTION "&<caiUxsA2.873>Current status for the expired inodes monitoring of the quota watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusQuotaEntry 31 }

uxsA2StatusQuotaLossAction OBJECT-TYPE
	SYNTAX INTEGER {
		remove(1),
		up(2),
		down-warning(3),
		down-critical(4)
	}
	ACCESS read-write
	STATUS mandatory
	DESCRIPTION "&<caiUxsA2.874>Current loss action for the quota watcher. Specifies the action to take if the monitored quota is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusQuotaEntry 32 }

uxsA2StatusQuotaLossStatus OBJECT-TYPE
	SYNTAX INTEGER {
		unknown(1),
		up(2),
		down-warning(3),
		down-critical(4)
	}
	ACCESS read-only
	STATUS mandatory
	DESCRIPTION "&<caiUxsA2.875>Current loss status of the quota watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusQuotaEntry 33 }

uxsA2StatusQuotaCallBackRef OBJECT-TYPE
	SYNTAX DisplayString
	ACCESS read-only
	STATUS mandatory
	DESCRIPTION "&<caiUxsA2.876>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusQuotaEntry 34 }

uxsA2StatusQuotaButton OBJECT-TYPE
	SYNTAX INTEGER {
		none(1),
		remove(2)
	}
	ACCESS read-write
	STATUS mandatory
	DESCRIPTION "&<caiUxsA2.877>This attribute is used to remove the quota watcher. If set to 2 (remove), the agent removes the watcher from the table. This attribute cannot be set to 1 (none)."
	DEFVAL { 1 }
	::= { uxsA2StatusQuotaEntry 35 }

--
-- The StatusDir Group
--

uxsA2StatusDirCount OBJECT-TYPE
	SYNTAX INTEGER
	ACCESS read-only
	STATUS mandatory
	DESCRIPTION "&<caiUxsA2.878>Number of entries in the directory status table."
	::= { uxsA2StatusDirGroup 1 }

uxsA2StatusDirTable OBJECT-TYPE
	SYNTAX SEQUENCE OF UxsA2StatusDirEntry
	ACCESS not-accessible
	STATUS mandatory
	DESCRIPTION "&<caiUxsA2.879>The directory status table containing details about the currently configured directory watchers."
	::= { uxsA2StatusDirGroup 2 }

uxsA2StatusDirEntry OBJECT-TYPE
	SYNTAX UxsA2StatusDirEntry
	ACCESS not-accessible
	STATUS mandatory
	DESCRIPTION "&<caiUxsA2.880>Entry in the directory status table."
	INDEX {
		uxsA2StatusDirWatcherName
	}
	::= { uxsA2StatusDirTable 1 }

UxsA2StatusDirEntry ::= SEQUENCE {
	uxsA2StatusDirWatcherName DisplayString,
	uxsA2StatusDirName DisplayString,
	uxsA2StatusDirRecursivePolicy INTEGER,
	uxsA2StatusDirDescription DisplayString,
	uxsA2StatusDirAggLagValue INTEGER,
	uxsA2StatusDirAggLag INTEGER,
	uxsA2StatusDirAggStatus INTEGER,
	uxsA2StatusDirSizeTotal DisplayString,
	uxsA2StatusDirSizeValue DisplayString,
	uxsA2StatusDirSizeWarnMin DisplayString,
	uxsA2StatusDirSizeWarnMax DisplayString,
	uxsA2StatusDirSizeCritMin DisplayString,
	uxsA2StatusDirSizeCritMax DisplayString,
	uxsA2StatusDirSizeMonitor INTEGER,
	uxsA2StatusDirSizeStatus INTEGER,
	uxsA2StatusDirSizeDValue DisplayString,
	uxsA2StatusDirSizeDWarnValue DisplayString,
	uxsA2StatusDirSizeDCritValue DisplayString,
	uxsA2StatusDirSizeDWarn DisplayString,
	uxsA2StatusDirSizeDCrit DisplayString,
	uxsA2StatusDirSizeDMonitor INTEGER,
	uxsA2StatusDirSizeDStatus INTEGER,
	uxsA2StatusDirEntriesValue DisplayString,
	uxsA2StatusDirEntriesMin DisplayString,
	uxsA2StatusDirEntriesMax DisplayString,
	uxsA2StatusDirEntriesMonitor INTEGER,
	uxsA2StatusDirEntriesStatus INTEGER,
	uxsA2StatusDirModTime DisplayString,
	uxsA2StatusDirChangeTime DisplayString,
	uxsA2StatusDirAccessTime DisplayString,
	uxsA2StatusDirTimeRef DisplayString,
	uxsA2StatusDirModInterval DisplayString,
	uxsA2StatusDirModValue INTEGER,
	uxsA2StatusDirMod INTEGER,
	uxsA2StatusDirModMonitor INTEGER,
	uxsA2StatusDirModStatus INTEGER,
	uxsA2StatusDirExist INTEGER,
	uxsA2StatusDirExistMonitor INTEGER,
	uxsA2StatusDirExistStatus INTEGER,
	uxsA2StatusDirCallBackRef DisplayString,
	uxsA2StatusDirButton INTEGER
}

uxsA2StatusDirWatcherName OBJECT-TYPE
	SYNTAX DisplayString
	ACCESS read-only
	STATUS mandatory
	DESCRIPTION "&<caiUxsA2.881>Name of the directory watcher."
	::= { uxsA2StatusDirEntry 1 }

uxsA2StatusDirName OBJECT-TYPE
	SYNTAX DisplayString
	ACCESS read-write
	STATUS mandatory
	DESCRIPTION "&<caiUxsA2.882>Name of the directory. This must be a fully qualified name that may contain environment variables."
	::= { uxsA2StatusDirEntry 2 }

uxsA2StatusDirRecursivePolicy OBJECT-TYPE
	SYNTAX INTEGER {
		no(1),
		yes(2)
	}
	ACCESS read-write
	STATUS mandatory
	DESCRIPTION "&<caiUxsA2.883>Recursiveness of the directory watcher. If set to 1 (no) only entries in the given directory are monitored. If set to 2 (yes) additionally all subentries (subdirectories and their files) are monitored."
	DEFVAL { 0 }
	::= { uxsA2StatusDirEntry 3 }

uxsA2StatusDirDescription OBJECT-TYPE
	SYNTAX DisplayString
	ACCESS read-write
	STATUS mandatory
	DESCRIPTION "&<caiUxsA2.884>Current description for the directory watcher."
	::= { uxsA2StatusDirEntry 4 }

uxsA2StatusDirAggLagValue OBJECT-TYPE
	SYNTAX INTEGER
	ACCESS read-only
	STATUS mandatory
	DESCRIPTION "&<caiUxsA2.885>Current aggregate lag value of the directory watcher. Indicates the consecutive number of times at which any status was not in the ok state. The aggregate status changes from ok as soon as the aggregate lag value reaches the configured value."
	::= { uxsA2StatusDirEntry 5 }

uxsA2StatusDirAggLag OBJECT-TYPE
	SYNTAX INTEGER
	ACCESS read-write
	STATUS mandatory
	DESCRIPTION "&<caiUxsA2.886>Current aggregate lag setting for the directory watcher. Specifies the consecutive number of times at which any status is not in the ok state, before the aggregate status changes. This value must be greater than 0."
	::= { uxsA2StatusDirEntry 6 }

uxsA2StatusDirAggStatus OBJECT-TYPE
	SYNTAX INTEGER {
		unknown(1),
		ok(2),
		warning(3),
		critical(4),
		passive(5)
	}
	ACCESS read-only
	STATUS mandatory
	DESCRIPTION "&<caiUxsA2.887>Current aggregate status of the directory watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { uxsA2StatusDirEntry 7 }

uxsA2StatusDirSizeTotal OBJECT-TYPE
	SYNTAX DisplayString
	ACCESS read-only
	STATUS mandatory
	DESCRIPTION "&<caiUxsA2.888>Total value in kilobytes for the size utilization monitoring of the directory watcher. The total is used as a reference (100%) for percentage values. When the directory watcher is created the total value is set to the actual size of the directory watcher."
	DEFVAL { "0" }
	::= { uxsA2StatusDirEntry 8 }

uxsA2StatusDirSizeValue OBJECT-TYPE
	SYNTAX DisplayString
	ACCESS read-only
	STATUS mandatory
	DESCRIPTION "&<caiUxsA2.889>Current value, in kilobytes, for the size utilization monitoring of the directory watcher."
	DEFVAL { "0" }
	::= { uxsA2StatusDirEntry 9 }

uxsA2StatusDirSizeWarnMin OBJECT-TYPE
	SYNTAX DisplayString
	ACCESS read-write
	STATUS mandatory
	DESCRIPTION "&<caiUxsA2.890>Current warning minimum threshold, in kilobytes, for the size utilization monitoring of the directory watcher. This value represents a declining threshold and must be equal to or greater than 0.0, equal to or greater than the critical minimum threshold, but cannot be greater than the warning maximum threshold. A value of -1 disables the evaluation of this threshold. The threshold can be specified as either an absolute value (n) or a percentage (n%). The value of uxsA2StatusDirSizeTotal will be the reference value for n% notations."
	DEFVAL { "-2" }
	::= { uxsA2StatusDirEntry 10 }

uxsA2StatusDirSizeWarnMax OBJECT-TYPE
	SYNTAX DisplayString
	ACCESS read-write
	STATUS mandatory
	DESCRIPTION "&<caiUxsA2.891>Current warning maximum threshold, in kilobytes, for the size utilization monitoring of the directory watcher. This value represents a rising threshold and must be equal to or greater than 0.0, equal to or greater than the warning minimum threshold, but cannot be greater than the critical maximum threshold. A value of -1 disables the evaluation of this threshold. The threshold can be specified as either an absolute value (n) or a percentage (n%). The value of uxsA2StatusDirSizeTotal will be the reference value for n% notations."
	DEFVAL { "-2" }
	::= { uxsA2StatusDirEntry 11 }

uxsA2StatusDirSizeCritMin OBJECT-TYPE
	SYNTAX DisplayString
	ACCESS read-write
	STATUS mandatory
	DESCRIPTION "&<caiUxsA2.892>Current critical minimum threshold, in kilobytes, for the size utilization monitoring of the directory watcher. This value represents a declining threshold and must be equal to or greater than 0.0, but cannot be greater than the warning minimum threshold. A value of -1 disables the evaluation of this threshold. The threshold can be specified as either an absolute value (n) or a percentage (n%). The value of uxsA2StatusDirSizeTotal will be the reference value for n% notations."
	DEFVAL { "-2" }
	::= { uxsA2StatusDirEntry 12 }

uxsA2StatusDirSizeCritMax OBJECT-TYPE
	SYNTAX DisplayString
	ACCESS read-write
	STATUS mandatory
	DESCRIPTION "&<caiUxsA2.893>Current critical maximum threshold, in kilobytes, for the size utilization monitoring of the directory watcher. This value represents a rising threshold and must be equal to or greater than 0.0, but cannot be less than the warning maximum threshold. A value of -1 disables the evaluation of this threshold. The threshold can be specified as either an absolute value (n) or a percentage (n%). The value of uxsA2StatusDirSizeTotal will be the reference value for n% notations."
	DEFVAL { "-2" }
	::= { uxsA2StatusDirEntry 13 }

uxsA2StatusDirSizeMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.894>Current monitor level for the size utilization monitoring of the directory watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2StatusDirEntry 14 }

uxsA2StatusDirSizeStatus OBJECT-TYPE
	SYNTAX INTEGER {
		unknown(1),
		up(2),
		down-warning(3),
		down-critical(4)
	}
	ACCESS read-only
	STATUS mandatory
	DESCRIPTION "&<caiUxsA2.895>Current status for the size utilization monitoring of the directory watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusDirEntry 15 }

uxsA2StatusDirSizeDValue OBJECT-TYPE
	SYNTAX DisplayString
	ACCESS read-only
	STATUS mandatory
	DESCRIPTION "&<caiUxsA2.896>Current value, in kilobytes, for the delta size utilization monitoring of the directory watcher."
	DEFVAL { "0" }
	::= { uxsA2StatusDirEntry 16 }

uxsA2StatusDirSizeDWarnValue OBJECT-TYPE
	SYNTAX DisplayString
	ACCESS read-only
	STATUS mandatory
	DESCRIPTION "&<caiUxsA2.897>Active warning threshold, in kilobytes, as derived from the configured value for the delta size utilization monitoring of the directory watcher. This value represents a rising threshold and must be greater than 0.0, but cannot be greater than the active critical threshold. These constraints will be maintained by the agent during all configuration actions."
	::= { uxsA2StatusDirEntry 17 }

uxsA2StatusDirSizeDCritValue OBJECT-TYPE
	SYNTAX DisplayString
	ACCESS read-only
	STATUS mandatory
	DESCRIPTION "&<caiUxsA2.898>Active critical threshold, in kilobytes, as derived from the configured value for the delta size utilization monitoring of the directory watcher. This value represents a rising threshold and must be greater than 0.0, but cannot be less than the active warning threshold. These constraints will be maintained by the agent during all configuration actions."
	::= { uxsA2StatusDirEntry 18 }

uxsA2StatusDirSizeDWarn OBJECT-TYPE
	SYNTAX DisplayString
	ACCESS read-write
	STATUS mandatory
	DESCRIPTION "&<caiUxsA2.899>Configured warning threshold from which the active warning threshold is derived for the delta size utilization monitoring of the directory watcher. The threshold can be specified as either an absolute value or a percentage and can denote a growth, shrinkage or change in either direction: Absolute shrinkage (n-), absolute growth (n+), absolute change in either direction (n), percentage shrinkage (n%-), percentage growth (n%+), or percentage change in either direction (n%). The value of uxsA2StatusDirSizeTotal will be the reference value for n% notations."
	::= { uxsA2StatusDirEntry 19 }

uxsA2StatusDirSizeDCrit OBJECT-TYPE
	SYNTAX DisplayString
	ACCESS read-write
	STATUS mandatory
	DESCRIPTION "&<caiUxsA2.900>Configured critical threshold from which the active critical threshold is derived for the delta size utilization monitoring of the directory watcher. The threshold can be specified as either an absolute value or a percentage and can denote a growth, shrinkage or change in either direction: Absolute shrinkage (n-), absolute growth (n+), absolute change in either direction (n), percentage shrinkage (n%-), percentage growth (n%+), or percentage change in either direction (n%). The value of uxsA2StatusDirSizeTotal will be the reference value for n% notations."
	::= { uxsA2StatusDirEntry 20 }

uxsA2StatusDirSizeDMonitor OBJECT-TYPE
	SYNTAX INTEGER {
		do-not-monitor(1),
		warning-only(2),
		critical-only(3),
		both(4)
	}
	ACCESS read-write
	STATUS mandatory
	DESCRIPTION "&<caiUxsA2.901>Current monitor level for the delta size utilization monitoring of the directory watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusDirEntry 21 }

uxsA2StatusDirSizeDStatus OBJECT-TYPE
	SYNTAX INTEGER {
		unknown(1),
		ok(2),
		warning(3),
		critical(4)
	}
	ACCESS read-only
	STATUS mandatory
	DESCRIPTION "&<caiUxsA2.902>Current status for the delta size utilization monitoring of the directory watcher: 1 (unknown) - An error occurred during data collection, 2 (ok) - The resource is operating within the defined limits or status evaluation is turned off and/or polling is disabled, 3 (warning) - The resource has breached the warning threshold, 4 (critical) - The resource has breached the critical threshold."
	::= { uxsA2StatusDirEntry 22 }

uxsA2StatusDirEntriesValue OBJECT-TYPE
	SYNTAX DisplayString
	ACCESS read-only
	STATUS mandatory
	DESCRIPTION "&<caiUxsA2.903>Current value for the number of file and/or directory entries monitoring of the directory watcher."
	DEFVAL { "0" }
	::= { uxsA2StatusDirEntry 23 }

uxsA2StatusDirEntriesMin OBJECT-TYPE
	SYNTAX DisplayString
	ACCESS read-write
	STATUS mandatory
	DESCRIPTION "&<caiUxsA2.904>Current minimum threshold for the number of file and/or directory entries monitoring of the directory watcher. This value represents a declining threshold and must be equal to or greater than 0.0, but cannot be greater than the maximum threshold. A value of -1 disables the evaluation of this threshold."
	DEFVAL { "-2" }
	::= { uxsA2StatusDirEntry 24 }

uxsA2StatusDirEntriesMax OBJECT-TYPE
	SYNTAX DisplayString
	ACCESS read-write
	STATUS mandatory
	DESCRIPTION "&<caiUxsA2.905>Current maximum threshold for the number of file and/or directory entries monitoring of the directory watcher. This value represents a rising threshold and must be equal to or greater than 0.0, but cannot be less than the minimum threshold. A value of -1 disables the evaluation of this threshold."
	DEFVAL { "-2" }
	::= { uxsA2StatusDirEntry 25 }

uxsA2StatusDirEntriesMonitor OBJECT-TYPE
	SYNTAX INTEGER {
		do-not-monitor(1),
		down-warning(2),
		down-critical(3)
	}
	ACCESS read-write
	STATUS mandatory
	DESCRIPTION "&<caiUxsA2.906>Current monitor level for the number of file and/or directory entries monitoring of the directory watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusDirEntry 26 }

uxsA2StatusDirEntriesStatus OBJECT-TYPE
	SYNTAX INTEGER {
		unknown(1),
		up(2),
		down-warning(3),
		down-critical(4)
	}
	ACCESS read-only
	STATUS mandatory
	DESCRIPTION "&<caiUxsA2.907>Current status for the number of file and/or directory entries monitoring of the directory watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusDirEntry 27 }

uxsA2StatusDirModTime OBJECT-TYPE
	SYNTAX DisplayString
	ACCESS read-only
	STATUS mandatory
	DESCRIPTION "&<caiUxsA2.908>Time of last data modfication for the monitored directory and its entries. Time format is YYYY-mm-dd HH:MM:SS, denoting year, including the century, month number [1,12], day of month [1,31], hour (24-hour clock) [0,23], minute [00,59]; seconds [00,61(to allow for leap seconds)]. Modification time is typically changed by the following functions: write, creat."
	::= { uxsA2StatusDirEntry 28 }

uxsA2StatusDirChangeTime OBJECT-TYPE
	SYNTAX DisplayString
	ACCESS read-only
	STATUS mandatory
	DESCRIPTION "&<caiUxsA2.909>Time of last file status change for the monitored directory and its entries. Time format is YYYY-mm-dd HH:MM:SS, denoting year, including the century, month number [1,12], day of month [1,31], hour (24-hour clock) [0,23], minute [00,59]; seconds [00,61(to allow for leap seconds)]. Change time is typically changed by the following functions: chmod, chown, write, creat."
	::= { uxsA2StatusDirEntry 29 }

uxsA2StatusDirAccessTime OBJECT-TYPE
	SYNTAX DisplayString
	ACCESS read-only
	STATUS mandatory
	DESCRIPTION "&<caiUxsA2.910>Time of last data access for the monitored directory and its entries. Time format is YYYY-mm-dd HH:MM:SS, denoting year, including the century, month number [1,12], day of month [1,31], hour (24-hour clock) [0,23], minute [00,59]; seconds [00,61(to allow for leap seconds)]. Access time is typically changed by the following functions: read, creat."
	::= { uxsA2StatusDirEntry 30 }

uxsA2StatusDirTimeRef OBJECT-TYPE
	SYNTAX DisplayString
	ACCESS read-only
	STATUS mandatory
	DESCRIPTION "&<caiUxsA2.911>Reference Time for modification metric. It is reset automatically to the most recent value of access time, change time, and modification time if the status is up. Otherwise reference time may be reset manually. Time format is YYYY-mm-dd HH:MM:SS, denoting year, including the century, month number [1,12], day of month [1,31], hour (24-hour clock) [0,23], minute [00,59]; seconds [00,61(to allow for leap seconds)]."
	::= { uxsA2StatusDirEntry 31 }

uxsA2StatusDirModInterval OBJECT-TYPE
	SYNTAX DisplayString
	ACCESS read-write
	STATUS mandatory
	DESCRIPTION "&<caiUxsA2.912>The period in seconds to be considered for calculating status and value of the modification metric. For a value of zero the period is identical to the current poll interval."
	::= { uxsA2StatusDirEntry 32 }

uxsA2StatusDirModValue OBJECT-TYPE
	SYNTAX INTEGER {
		not-modified(1),
		not-changed(2),
		not-changed-only(3),
		not-accessed(4),
		modified(5),
		changed(6),
		changed-only(7),
		accessed(8)
	}
	ACCESS read-only
	STATUS mandatory
	DESCRIPTION "&<caiUxsA2.913>The current value of the modification monitoring of the directory watcher."
	::= { uxsA2StatusDirEntry 33 }

uxsA2StatusDirMod OBJECT-TYPE
	SYNTAX INTEGER {
		should-not-be-modified(1),
		should-not-be-changed(2),
		should-not-be-changed-only(3),
		should-not-be-accessed(4),
		should-be-modified(5),
		should-be-changed(6),
		should-be-changed-only(7),
		should-be-accessed(8),
		reset-time-reference(9)
	}
	ACCESS read-write
	STATUS mandatory
	DESCRIPTION "&<caiUxsA2.914>Current monitor condition for the modification monitoring of the directory watcher. As a reference for modification the user can choose between modification time, change time, change time only (change time is modified and modification time is not), and access time. All times can be monitored for being modified (should-be-modified, should-be-changed, should-be-changed-only, should-be-accessed) or for being unmodified (should-not-be-modified, should-not-be-changed, should-not-be-changed-only, should-not-be-accessed). At each poll the latest timestamp of the chosen policy for the directory in question will be compared with the reference timestamp. If the resulting monitor status is 'up' the reference time is set automatically to the most recent value of access time, change time, or modification time. If the monitor status is 'down' the metric may be reset manually by setting the monitor condition to reset-time-reference. Status calculation depends on the kind of monitoring (modified or unmodified) and the value of 'DirModInterval'. If monitoring is for being modified the status is down if the file was not modified for more seconds than the value of 'DirModInterval'. Status is reset to up if there are modifications within 'DirModInterval'. If monitoring is for being unmodified the status is down if the file was modified more often than every 'DirModInterval' seconds. If 'DirModInterval' is zero any modification sets the status down. Note that status evaluation only takes place when the agent polls. Thus the end of the modification interval will be detected on the subsequent poll."
	DEFVAL { 0 }
	::= { uxsA2StatusDirEntry 34 }

uxsA2StatusDirModMonitor OBJECT-TYPE
	SYNTAX INTEGER {
		do-not-monitor(1),
		down-warning(2),
		down-critical(3)
	}
	ACCESS read-write
	STATUS mandatory
	DESCRIPTION "&<caiUxsA2.915>Current monitor level for the modification monitoring of the directory watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusDirEntry 35 }

uxsA2StatusDirModStatus OBJECT-TYPE
	SYNTAX INTEGER {
		unknown(1),
		up(2),
		down-warning(3),
		down-critical(4)
	}
	ACCESS read-only
	STATUS mandatory
	DESCRIPTION "&<caiUxsA2.916>Current status for the modification monitoring of the directory watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusDirEntry 36 }

uxsA2StatusDirExist OBJECT-TYPE
	SYNTAX INTEGER {
		should-exist(1),
		should-not-exist(2)
	}
	ACCESS read-write
	STATUS mandatory
	DESCRIPTION "&<caiUxsA2.917>Current monitor condition for the existence monitoring of the directory watcher. Specifies how the agent should evaluate the presence or absence of the monitored resource in order to determine whether the resource is in good condition. If set to 1 (should-exist), the resource is expected to be existent. If set to 2 (should-not-exist), the resource is expected to be nonexistent."
	DEFVAL { 0 }
	::= { uxsA2StatusDirEntry 37 }

uxsA2StatusDirExistMonitor OBJECT-TYPE
	SYNTAX INTEGER {
		do-not-monitor(1),
		down-warning(2),
		down-critical(3)
	}
	ACCESS read-write
	STATUS mandatory
	DESCRIPTION "&<caiUxsA2.918>Current monitor level for the existence monitoring of the directory watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusDirEntry 38 }

uxsA2StatusDirExistStatus OBJECT-TYPE
	SYNTAX INTEGER {
		unknown(1),
		up(2),
		down-warning(3),
		down-critical(4)
	}
	ACCESS read-only
	STATUS mandatory
	DESCRIPTION "&<caiUxsA2.919>Current status for the existence monitoring of the directory watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusDirEntry 39 }

uxsA2StatusDirCallBackRef OBJECT-TYPE
	SYNTAX DisplayString
	ACCESS read-only
	STATUS mandatory
	DESCRIPTION "&<caiUxsA2.920>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusDirEntry 40 }

uxsA2StatusDirButton OBJECT-TYPE
	SYNTAX INTEGER {
		none(1),
		remove(2)
	}
	ACCESS read-write
	STATUS mandatory
	DESCRIPTION "&<caiUxsA2.921>This attribute is used to remove the directory watcher. If set to 2 (remove), the agent removes the watcher from the table. This attribute cannot be set to 1 (none)."
	DEFVAL { 1 }
	::= { uxsA2StatusDirEntry 41 }

--
-- The StatusFSys Group
--

uxsA2StatusFSysCount OBJECT-TYPE
	SYNTAX INTEGER
	ACCESS read-only
	STATUS mandatory
	DESCRIPTION "&<caiUxsA2.922>Number of entries in the file system status table."
	::= { uxsA2StatusFSysGroup 1 }

uxsA2StatusFSysTable OBJECT-TYPE
	SYNTAX SEQUENCE OF UxsA2StatusFSysEntry
	ACCESS not-accessible
	STATUS mandatory
	DESCRIPTION "&<caiUxsA2.923>The file system status table containing details about the currently configured file system watchers."
	::= { uxsA2StatusFSysGroup 2 }

uxsA2StatusFSysEntry OBJECT-TYPE
	SYNTAX UxsA2StatusFSysEntry
	ACCESS not-accessible
	STATUS mandatory
	DESCRIPTION "&<caiUxsA2.924>Entry in the file system status table."
	INDEX {
		uxsA2StatusFSysName
	}
	::= { uxsA2StatusFSysTable 1 }

UxsA2StatusFSysEntry ::= SEQUENCE {
	uxsA2StatusFSysName DisplayString,
	uxsA2StatusFSysDescription DisplayString,
	uxsA2StatusFSysAutoWatcherName DisplayString,
	uxsA2StatusFSysAggLagValue INTEGER,
	uxsA2StatusFSysAggLag INTEGER,
	uxsA2StatusFSysAggStatus INTEGER,
	uxsA2StatusFSysRelatedTo DisplayString,
	uxsA2StatusFSysType DisplayString,
	uxsA2StatusFSysClusterType INTEGER,
	uxsA2StatusFSysSpaceTotal DisplayString,
	uxsA2StatusFSysTotalPolicy INTEGER,
	uxsA2StatusFSysSpaceValue DisplayString,
	uxsA2StatusFSysSpaceWarnValue DisplayString,
	uxsA2StatusFSysSpaceCritValue DisplayString,
	uxsA2StatusFSysSpaceWarn DisplayString,
	uxsA2StatusFSysSpaceCrit DisplayString,
	uxsA2StatusFSysSpaceMonitor INTEGER,
	uxsA2StatusFSysSpaceStatus INTEGER,
	uxsA2StatusFSysSpaceDValue DisplayString,
	uxsA2StatusFSysSpaceDWarnValue DisplayString,
	uxsA2StatusFSysSpaceDCritValue DisplayString,
	uxsA2StatusFSysSpaceDWarn DisplayString,
	uxsA2StatusFSysSpaceDCrit DisplayString,
	uxsA2StatusFSysSpaceDMonitor INTEGER,
	uxsA2StatusFSysSpaceDStatus INTEGER,
	uxsA2StatusFSysInodesTotal DisplayString,
	uxsA2StatusFSysInodesValue DisplayString,
	uxsA2StatusFSysInodesWarnValue DisplayString,
	uxsA2StatusFSysInodesCritValue DisplayString,
	uxsA2StatusFSysInodesWarn DisplayString,
	uxsA2StatusFSysInodesCrit DisplayString,
	uxsA2StatusFSysInodesMonitor INTEGER,
	uxsA2StatusFSysInodesStatus INTEGER,
	uxsA2StatusFSysInodesDValue DisplayString,
	uxsA2StatusFSysInodesDWarnValue DisplayString,
	uxsA2StatusFSysInodesDCritValue DisplayString,
	uxsA2StatusFSysInodesDWarn DisplayString,
	uxsA2StatusFSysInodesDCrit DisplayString,
	uxsA2StatusFSysInodesDMonitor INTEGER,
	uxsA2StatusFSysInodesDStatus INTEGER,
	uxsA2StatusFSysMountValue INTEGER,
	uxsA2StatusFSysMount INTEGER,
	uxsA2StatusFSysMountMonitor INTEGER,
	uxsA2StatusFSysMountStatus INTEGER,
	uxsA2StatusFSysLossAction INTEGER,
	uxsA2StatusFSysLossStatus INTEGER,
	uxsA2StatusFSysCallBackRef DisplayString,
	uxsA2StatusFSysButton INTEGER
}

uxsA2StatusFSysName OBJECT-TYPE
	SYNTAX DisplayString
	ACCESS read-only
	STATUS mandatory
	DESCRIPTION "&<caiUxsA2.925>The file system mount point."
	::= { uxsA2StatusFSysEntry 1 }

uxsA2StatusFSysDescription OBJECT-TYPE
	SYNTAX DisplayString
	ACCESS read-write
	STATUS mandatory
	DESCRIPTION "&<caiUxsA2.926>Current description for the file system watcher."
	::= { uxsA2StatusFSysEntry 2 }

uxsA2StatusFSysAutoWatcherName OBJECT-TYPE
	SYNTAX DisplayString
	ACCESS read-only
	STATUS mandatory
	DESCRIPTION "&<caiUxsA2.927>Name of the file system auto watcher which automatically created this watcher. This attribute is left blank if the watcher was added manually."
	::= { uxsA2StatusFSysEntry 3 }

uxsA2StatusFSysAggLagValue OBJECT-TYPE
	SYNTAX INTEGER
	ACCESS read-only
	STATUS mandatory
	DESCRIPTION "&<caiUxsA2.928>Current aggregate lag value of the file system watcher. Indicates the consecutive number of times at which any status was not in the ok state. The aggregate status changes from ok as soon as the aggregate lag value reaches the configured value."
	::= { uxsA2StatusFSysEntry 4 }

uxsA2StatusFSysAggLag OBJECT-TYPE
	SYNTAX INTEGER
	ACCESS read-write
	STATUS mandatory
	DESCRIPTION "&<caiUxsA2.929>Current aggregate lag setting for the file system watcher. Specifies the consecutive number of times at which any status is not in the ok state, before the aggregate status changes. This value must be greater than 0."
	::= { uxsA2StatusFSysEntry 5 }

uxsA2StatusFSysAggStatus OBJECT-TYPE
	SYNTAX INTEGER {
		unknown(1),
		ok(2),
		warning(3),
		critical(4),
		passive(5)
	}
	ACCESS read-only
	STATUS mandatory
	DESCRIPTION "&<caiUxsA2.930>Current aggregate status of the file system watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { uxsA2StatusFSysEntry 6 }

uxsA2StatusFSysRelatedTo OBJECT-TYPE
	SYNTAX DisplayString
	ACCESS read-only
	STATUS mandatory
	DESCRIPTION "&<caiUxsA2.931>The device from which the file system is mounted."
	::= { uxsA2StatusFSysEntry 7 }

uxsA2StatusFSysType OBJECT-TYPE
	SYNTAX DisplayString
	ACCESS read-only
	STATUS mandatory
	DESCRIPTION "&<caiUxsA2.932>The type of the mounted file system. The value is platform dependent."
	::= { uxsA2StatusFSysEntry 8 }

uxsA2StatusFSysClusterType OBJECT-TYPE
	SYNTAX INTEGER {
		not-clustered(1),
		clustered-active(2),
		clustered-passive(3)
	}
	ACCESS read-only
	STATUS mandatory
	DESCRIPTION "&<caiUxsA2.933>Cluster type of the file system: 1 (not-clustered) - Resource is not clustered, 2 (clustered-active) - Local cluster node has resource ownership, 3 (clustered-passive) - Another node in the cluster has resource ownership; the agent on the local node does not actively monitor the resource until ownership is transferred back."
	::= { uxsA2StatusFSysEntry 9 }

uxsA2StatusFSysSpaceTotal OBJECT-TYPE
	SYNTAX DisplayString
	ACCESS read-only
	STATUS mandatory
	DESCRIPTION "&<caiUxsA2.934>The total amount of space on the file system in megabytes."
	DEFVAL { "0" }
	::= { uxsA2StatusFSysEntry 10 }

uxsA2StatusFSysTotalPolicy OBJECT-TYPE
	SYNTAX INTEGER {
		unprivileged-user(1),
		privileged-user(2)
	}
	ACCESS read-write
	STATUS mandatory
	DESCRIPTION "&<caiUxsA2.935>If set to privileged-user the Total Value of the file system includes the superuser reserve. For unprivileged-user the reserve is not included."
	DEFVAL { 0 }
	::= { uxsA2StatusFSysEntry 11 }

uxsA2StatusFSysSpaceValue OBJECT-TYPE
	SYNTAX DisplayString
	ACCESS read-only
	STATUS mandatory
	DESCRIPTION "&<caiUxsA2.936>Current value, in megabytes, for the space utilization monitoring of the file system watcher."
	DEFVAL { "0" }
	::= { uxsA2StatusFSysEntry 12 }

uxsA2StatusFSysSpaceWarnValue OBJECT-TYPE
	SYNTAX DisplayString
	ACCESS read-only
	STATUS mandatory
	DESCRIPTION "&<caiUxsA2.937>Active warning threshold, in megabytes, as derived from the configured value for the space utilization monitoring of the file system watcher. This value represents a rising threshold and must be greater than 0.0, less than or equal to the total value (maximum capacity) of the monitored resource as specified in uxsA2StatusFSysSpaceTotal, but cannot be greater than the active critical threshold. These constraints will be maintained by the agent during all configuration actions."
	::= { uxsA2StatusFSysEntry 13 }

uxsA2StatusFSysSpaceCritValue OBJECT-TYPE
	SYNTAX DisplayString
	ACCESS read-only
	STATUS mandatory
	DESCRIPTION "&<caiUxsA2.938>Active critical threshold, in megabytes, as derived from the configured value for the space utilization monitoring of the file system watcher. This value represents a rising threshold and must be greater than 0.0, less than or equal to the total value (maximum capacity) of the monitored resource as specified in uxsA2StatusFSysSpaceTotal, but cannot be less than the active warning threshold. These constraints will be maintained by the agent during all configuration actions."
	::= { uxsA2StatusFSysEntry 14 }

uxsA2StatusFSysSpaceWarn OBJECT-TYPE
	SYNTAX DisplayString
	ACCESS read-write
	STATUS mandatory
	DESCRIPTION "&<caiUxsA2.939>Configured warning threshold from which the active warning threshold is derived for the space utilization monitoring of the file system watcher. The threshold can be specified as either an absolute value (n) or a percentage (n%). It can also be specified as the absolute value left free (nF). The value of uxsA2StatusFSysSpaceTotal will be the reference value for n% and nF notations."
	::= { uxsA2StatusFSysEntry 15 }

uxsA2StatusFSysSpaceCrit OBJECT-TYPE
	SYNTAX DisplayString
	ACCESS read-write
	STATUS mandatory
	DESCRIPTION "&<caiUxsA2.940>Configured critical threshold from which the active critical threshold is derived for the space utilization monitoring of the file system watcher. The threshold can be specified as either an absolute value (n) or a percentage (n%). It can also be specified as the absolute value left free (nF). The value of uxsA2StatusFSysSpaceTotal will be the reference value for n% and nF notations."
	::= { uxsA2StatusFSysEntry 16 }

uxsA2StatusFSysSpaceMonitor OBJECT-TYPE
	SYNTAX INTEGER {
		do-not-monitor(1),
		warning-only(2),
		critical-only(3),
		both(4)
	}
	ACCESS read-write
	STATUS mandatory
	DESCRIPTION "&<caiUxsA2.941>Current monitor level for the space utilization monitoring of the file system watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusFSysEntry 17 }

uxsA2StatusFSysSpaceStatus OBJECT-TYPE
	SYNTAX INTEGER {
		unknown(1),
		ok(2),
		warning(3),
		critical(4)
	}
	ACCESS read-only
	STATUS mandatory
	DESCRIPTION "&<caiUxsA2.942>Current status for the space utilization monitoring of the file system watcher: 1 (unknown) - An error occurred during data collection, 2 (ok) - The resource is operating within the defined limits or status evaluation is turned off and/or polling is disabled, 3 (warning) - The resource has breached the warning threshold, 4 (critical) - The resource has breached the critical threshold."
	::= { uxsA2StatusFSysEntry 18 }

uxsA2StatusFSysSpaceDValue OBJECT-TYPE
	SYNTAX DisplayString
	ACCESS read-only
	STATUS mandatory
	DESCRIPTION "&<caiUxsA2.943>Current value, in kilobytes, for the delta space utilization monitoring of the file system watcher."
	DEFVAL { "0" }
	::= { uxsA2StatusFSysEntry 19 }

uxsA2StatusFSysSpaceDWarnValue OBJECT-TYPE
	SYNTAX DisplayString
	ACCESS read-only
	STATUS mandatory
	DESCRIPTION "&<caiUxsA2.944>Active warning threshold, in kilobytes, as derived from the configured value for the delta space utilization monitoring of the file system watcher. This value represents a rising threshold and must be greater than 0.0, less than or equal to the total value (maximum capacity) of the monitored resource as specified in uxsA2StatusFSysSpaceTotal, but cannot be greater than the active critical threshold. These constraints will be maintained by the agent during all configuration actions."
	::= { uxsA2StatusFSysEntry 20 }

uxsA2StatusFSysSpaceDCritValue OBJECT-TYPE
	SYNTAX DisplayString
	ACCESS read-only
	STATUS mandatory
	DESCRIPTION "&<caiUxsA2.945>Active critical threshold, in kilobytes, as derived from the configured value for the delta space utilization monitoring of the file system watcher. This value represents a rising threshold and must be greater than 0.0, less than or equal to the total value (maximum capacity) of the monitored resource as specified in uxsA2StatusFSysSpaceTotal, but cannot be less than the active warning threshold. These constraints will be maintained by the agent during all configuration actions."
	::= { uxsA2StatusFSysEntry 21 }

uxsA2StatusFSysSpaceDWarn OBJECT-TYPE
	SYNTAX DisplayString
	ACCESS read-write
	STATUS mandatory
	DESCRIPTION "&<caiUxsA2.946>Configured warning threshold from which the active warning threshold is derived for the delta space utilization monitoring of the file system watcher. The threshold can be specified as either an absolute value or a percentage and can denote a growth, shrinkage or change in either direction: Absolute shrinkage (n-), absolute growth (n+), absolute change in either direction (n), percentage shrinkage (n%-), percentage growth (n%+), or percentage change in either direction (n%). The value of uxsA2StatusFSysSpaceTotal will be the reference value for n% notations."
	::= { uxsA2StatusFSysEntry 22 }

uxsA2StatusFSysSpaceDCrit OBJECT-TYPE
	SYNTAX DisplayString
	ACCESS read-write
	STATUS mandatory
	DESCRIPTION "&<caiUxsA2.947>Configured critical threshold from which the active critical threshold is derived for the delta space utilization monitoring of the file system watcher. The threshold can be specified as either an absolute value or a percentage and can denote a growth, shrinkage or change in either direction: Absolute shrinkage (n-), absolute growth (n+), absolute change in either direction (n), percentage shrinkage (n%-), percentage growth (n%+), or percentage change in either direction (n%). The value of uxsA2StatusFSysSpaceTotal will be the reference value for n% notations."
	::= { uxsA2StatusFSysEntry 23 }

uxsA2StatusFSysSpaceDMonitor OBJECT-TYPE
	SYNTAX INTEGER {
		do-not-monitor(1),
		warning-only(2),
		critical-only(3),
		both(4)
	}
	ACCESS read-write
	STATUS mandatory
	DESCRIPTION "&<caiUxsA2.948>Current monitor level for the delta space utilization monitoring of the file system watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusFSysEntry 24 }

uxsA2StatusFSysSpaceDStatus OBJECT-TYPE
	SYNTAX INTEGER {
		unknown(1),
		ok(2),
		warning(3),
		critical(4)
	}
	ACCESS read-only
	STATUS mandatory
	DESCRIPTION "&<caiUxsA2.949>Current status for the delta space utilization monitoring of the file system watcher: 1 (unknown) - An error occurred during data collection, 2 (ok) - The resource is operating within the defined limits or status evaluation is turned off and/or polling is disabled, 3 (warning) - The resource has breached the warning threshold, 4 (critical) - The resource has breached the critical threshold."
	::= { uxsA2StatusFSysEntry 25 }

uxsA2StatusFSysInodesTotal OBJECT-TYPE
	SYNTAX DisplayString
	ACCESS read-only
	STATUS mandatory
	DESCRIPTION "&<caiUxsA2.950>The amount of inodes configured on the file system. For certain file system types the value is meaningless and therefore set to 0."
	DEFVAL { "0" }
	::= { uxsA2StatusFSysEntry 26 }

uxsA2StatusFSysInodesValue OBJECT-TYPE
	SYNTAX DisplayString
	ACCESS read-only
	STATUS mandatory
	DESCRIPTION "&<caiUxsA2.951>Current value for the inodes used monitoring of the file system watcher."
	DEFVAL { "0" }
	::= { uxsA2StatusFSysEntry 27 }

uxsA2StatusFSysInodesWarnValue OBJECT-TYPE
	SYNTAX DisplayString
	ACCESS read-only
	STATUS mandatory
	DESCRIPTION "&<caiUxsA2.952>Active warning threshold as derived from the configured value for the inodes used monitoring of the file system watcher. This value represents a rising threshold and must be greater than 0.0, less than or equal to the total value (maximum capacity) of the monitored resource as specified in uxsA2StatusFSysInodesTotal, but cannot be greater than the active critical threshold. These constraints will be maintained by the agent during all configuration actions."
	::= { uxsA2StatusFSysEntry 28 }

uxsA2StatusFSysInodesCritValue OBJECT-TYPE
	SYNTAX DisplayString
	ACCESS read-only
	STATUS mandatory
	DESCRIPTION "&<caiUxsA2.953>Active critical threshold as derived from the configured value for the inodes used monitoring of the file system watcher. This value represents a rising threshold and must be greater than 0.0, less than or equal to the total value (maximum capacity) of the monitored resource as specified in uxsA2StatusFSysInodesTotal, but cannot be less than the active warning threshold. These constraints will be maintained by the agent during all configuration actions."
	::= { uxsA2StatusFSysEntry 29 }

uxsA2StatusFSysInodesWarn OBJECT-TYPE
	SYNTAX DisplayString
	ACCESS read-write
	STATUS mandatory
	DESCRIPTION "&<caiUxsA2.954>Configured warning threshold from which the active warning threshold is derived for the inodes used monitoring of the file system watcher. The threshold can be specified as either an absolute value (n) or a percentage (n%). It can also be specified as the absolute value left free (nF). The value of uxsA2StatusFSysInodesTotal will be the reference value for n% and nF notations."
	::= { uxsA2StatusFSysEntry 30 }

uxsA2StatusFSysInodesCrit OBJECT-TYPE
	SYNTAX DisplayString
	ACCESS read-write
	STATUS mandatory
	DESCRIPTION "&<caiUxsA2.955>Configured critical threshold from which the active critical threshold is derived for the inodes used monitoring of the file system watcher. The threshold can be specified as either an absolute value (n) or a percentage (n%). It can also be specified as the absolute value left free (nF). The value of uxsA2StatusFSysInodesTotal will be the reference value for n% and nF notations."
	::= { uxsA2StatusFSysEntry 31 }

uxsA2StatusFSysInodesMonitor OBJECT-TYPE
	SYNTAX INTEGER {
		do-not-monitor(1),
		warning-only(2),
		critical-only(3),
		both(4)
	}
	ACCESS read-write
	STATUS mandatory
	DESCRIPTION "&<caiUxsA2.956>Current monitor level for the inodes used monitoring of the file system watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusFSysEntry 32 }

uxsA2StatusFSysInodesStatus OBJECT-TYPE
	SYNTAX INTEGER {
		unknown(1),
		ok(2),
		warning(3),
		critical(4)
	}
	ACCESS read-only
	STATUS mandatory
	DESCRIPTION "&<caiUxsA2.957>Current status for the inodes used monitoring of the file system watcher: 1 (unknown) - An error occurred during data collection, 2 (ok) - The resource is operating within the defined limits or status evaluation is turned off and/or polling is disabled, 3 (warning) - The resource has breached the warning threshold, 4 (critical) - The resource has breached the critical threshold."
	::= { uxsA2StatusFSysEntry 33 }

uxsA2StatusFSysInodesDValue OBJECT-TYPE
	SYNTAX DisplayString
	ACCESS read-only
	STATUS mandatory
	DESCRIPTION "&<caiUxsA2.958>Current value for the delta inodes used monitoring of the file system watcher."
	DEFVAL { "0" }
	::= { uxsA2StatusFSysEntry 34 }

uxsA2StatusFSysInodesDWarnValue OBJECT-TYPE
	SYNTAX DisplayString
	ACCESS read-only
	STATUS mandatory
	DESCRIPTION "&<caiUxsA2.959>Active warning threshold as derived from the configured value for the delta inodes used monitoring of the file system watcher. This value represents a rising threshold and must be greater than 0.0, less than or equal to the total value (maximum capacity) of the monitored resource as specified in uxsA2StatusFSysInodesTotal, but cannot be greater than the active critical threshold. These constraints will be maintained by the agent during all configuration actions."
	::= { uxsA2StatusFSysEntry 35 }

uxsA2StatusFSysInodesDCritValue OBJECT-TYPE
	SYNTAX DisplayString
	ACCESS read-only
	STATUS mandatory
	DESCRIPTION "&<caiUxsA2.960>Active critical threshold as derived from the configured value for the delta inodes used monitoring of the file system watcher. This value represents a rising threshold and must be greater than 0.0, less than or equal to the total value (maximum capacity) of the monitored resource as specified in uxsA2StatusFSysInodesTotal, but cannot be less than the active warning threshold. These constraints will be maintained by the agent during all configuration actions."
	::= { uxsA2StatusFSysEntry 36 }

uxsA2StatusFSysInodesDWarn OBJECT-TYPE
	SYNTAX DisplayString
	ACCESS read-write
	STATUS mandatory
	DESCRIPTION "&<caiUxsA2.961>Configured warning threshold from which the active warning threshold is derived for the delta inodes used monitoring of the file system watcher. The threshold can be specified as either an absolute value or a percentage and can denote a growth, shrinkage or change in either direction: Absolute shrinkage (n-), absolute growth (n+), absolute change in either direction (n), percentage shrinkage (n%-), percentage growth (n%+), or percentage change in either direction (n%). The value of uxsA2StatusFSysInodesTotal will be the reference value for n% notations."
	::= { uxsA2StatusFSysEntry 37 }

uxsA2StatusFSysInodesDCrit OBJECT-TYPE
	SYNTAX DisplayString
	ACCESS read-write
	STATUS mandatory
	DESCRIPTION "&<caiUxsA2.962>Configured critical threshold from which the active critical threshold is derived for the delta inodes used monitoring of the file system watcher. The threshold can be specified as either an absolute value or a percentage and can denote a growth, shrinkage or change in either direction: Absolute shrinkage (n-), absolute growth (n+), absolute change in either direction (n), percentage shrinkage (n%-), percentage growth (n%+), or percentage change in either direction (n%). The value of uxsA2StatusFSysInodesTotal will be the reference value for n% notations."
	::= { uxsA2StatusFSysEntry 38 }

uxsA2StatusFSysInodesDMonitor OBJECT-TYPE
	SYNTAX INTEGER {
		do-not-monitor(1),
		warning-only(2),
		critical-only(3),
		both(4)
	}
	ACCESS read-write
	STATUS mandatory
	DESCRIPTION "&<caiUxsA2.963>Current monitor level for the delta inodes used monitoring of the file system watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusFSysEntry 39 }

uxsA2StatusFSysInodesDStatus OBJECT-TYPE
	SYNTAX INTEGER {
		unknown(1),
		ok(2),
		warning(3),
		critical(4)
	}
	ACCESS read-only
	STATUS mandatory
	DESCRIPTION "&<caiUxsA2.964>Current status for the delta inodes used monitoring of the file system watcher: 1 (unknown) - An error occurred during data collection, 2 (ok) - The resource is operating within the defined limits or status evaluation is turned off and/or polling is disabled, 3 (warning) - The resource has breached the warning threshold, 4 (critical) - The resource has breached the critical threshold."
	::= { uxsA2StatusFSysEntry 40 }

uxsA2StatusFSysMountValue OBJECT-TYPE
	SYNTAX INTEGER {
		mounted(1),
		not-mounted(2)
	}
	ACCESS read-only
	STATUS mandatory
	DESCRIPTION "&<caiUxsA2.965>Denotes if the file system is currently mounted or not mounted."
	::= { uxsA2StatusFSysEntry 41 }

uxsA2StatusFSysMount OBJECT-TYPE
	SYNTAX INTEGER {
		should-be-mounted(1),
		should-not-be-mounted(2)
	}
	ACCESS read-write
	STATUS mandatory
	DESCRIPTION "&<caiUxsA2.966>Current monitor condition for the mount status monitoring of the file system watcher."
	DEFVAL { 0 }
	::= { uxsA2StatusFSysEntry 42 }

uxsA2StatusFSysMountMonitor OBJECT-TYPE
	SYNTAX INTEGER {
		do-not-monitor(1),
		down-warning(2),
		down-critical(3)
	}
	ACCESS read-write
	STATUS mandatory
	DESCRIPTION "&<caiUxsA2.967>Current monitor level for the mount status monitoring of the file system watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusFSysEntry 43 }

uxsA2StatusFSysMountStatus OBJECT-TYPE
	SYNTAX INTEGER {
		unknown(1),
		up(2),
		down-warning(3),
		down-critical(4)
	}
	ACCESS read-only
	STATUS mandatory
	DESCRIPTION "&<caiUxsA2.968>Current status for the mount status monitoring of the file system watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusFSysEntry 44 }

uxsA2StatusFSysLossAction OBJECT-TYPE
	SYNTAX INTEGER {
		remove(1),
		up(2),
		down-warning(3),
		down-critical(4)
	}
	ACCESS read-write
	STATUS mandatory
	DESCRIPTION "&<caiUxsA2.969>Current loss action for the file system watcher. Specifies the action to take if the monitored file system is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusFSysEntry 45 }

uxsA2StatusFSysLossStatus OBJECT-TYPE
	SYNTAX INTEGER {
		unknown(1),
		up(2),
		down-warning(3),
		down-critical(4)
	}
	ACCESS read-only
	STATUS mandatory
	DESCRIPTION "&<caiUxsA2.970>Current loss status of the file system watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusFSysEntry 46 }

uxsA2StatusFSysCallBackRef OBJECT-TYPE
	SYNTAX DisplayString
	ACCESS read-only
	STATUS mandatory
	DESCRIPTION "&<caiUxsA2.971>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusFSysEntry 47 }

uxsA2StatusFSysButton OBJECT-TYPE
	SYNTAX INTEGER {
		none(1),
		remove(2)
	}
	ACCESS read-write
	STATUS mandatory
	DESCRIPTION "&<caiUxsA2.972>This attribute is used to remove the file system watcher. If set to 2 (remove), the agent removes the watcher from the table. This attribute cannot be set to 1 (none)."
	DEFVAL { 1 }
	::= { uxsA2StatusFSysEntry 48 }

--
-- The StatusFile Group
--

uxsA2StatusFileCount OBJECT-TYPE
	SYNTAX INTEGER
	ACCESS read-only
	STATUS mandatory
	DESCRIPTION "&<caiUxsA2.973>Number of entries in the file status table."
	::= { uxsA2StatusFileGroup 1 }

uxsA2StatusFileTable OBJECT-TYPE
	SYNTAX SEQUENCE OF UxsA2StatusFileEntry
	ACCESS not-accessible
	STATUS mandatory
	DESCRIPTION "&<caiUxsA2.974>The file status table containing details about the currently configured file watchers."
	::= { uxsA2StatusFileGroup 2 }

uxsA2StatusFileEntry OBJECT-TYPE
	SYNTAX UxsA2StatusFileEntry
	ACCESS not-accessible
	STATUS mandatory
	DESCRIPTION "&<caiUxsA2.975>Entry in the file status table."
	INDEX {
		uxsA2StatusFileWatcherName
	}
	::= { uxsA2StatusFileTable 1 }

UxsA2StatusFileEntry ::= SEQUENCE {
	uxsA2StatusFileWatcherName DisplayString,
	uxsA2StatusFileName DisplayString,
	uxsA2StatusFileEvalPolicy INTEGER,
	uxsA2StatusFileDescription DisplayString,
	uxsA2StatusFileAggLagValue INTEGER,
	uxsA2StatusFileAggLag INTEGER,
	uxsA2StatusFileAggStatus INTEGER,
	uxsA2StatusFileInstValue DisplayString,
	uxsA2StatusFileInstMin DisplayString,
	uxsA2StatusFileInstMax DisplayString,
	uxsA2StatusFileInstMonitor INTEGER,
	uxsA2StatusFileInstStatus INTEGER,
	uxsA2StatusFileInstIds DisplayString,
	uxsA2StatusFileSizeTotal DisplayString,
	uxsA2StatusFileSizeMinValue DisplayString,
	uxsA2StatusFileSizeMaxValue DisplayString,
	uxsA2StatusFileSizeWarnMin DisplayString,
	uxsA2StatusFileSizeWarnMax DisplayString,
	uxsA2StatusFileSizeCritMin DisplayString,
	uxsA2StatusFileSizeCritMax DisplayString,
	uxsA2StatusFileSizeMonitor INTEGER,
	uxsA2StatusFileSizeStatus INTEGER,
	uxsA2StatusFileSizeIds DisplayString,
	uxsA2StatusFileSizeDValue DisplayString,
	uxsA2StatusFileSizeDWarnValue DisplayString,
	uxsA2StatusFileSizeDCritValue DisplayString,
	uxsA2StatusFileSizeDWarn DisplayString,
	uxsA2StatusFileSizeDCrit DisplayString,
	uxsA2StatusFileSizeDMonitor INTEGER,
	uxsA2StatusFileSizeDStatus INTEGER,
	uxsA2StatusFileSizeDIds DisplayString,
	uxsA2StatusFileModTime DisplayString,
	uxsA2StatusFileChangeTime DisplayString,
	uxsA2StatusFileAccessTime DisplayString,
	uxsA2StatusFileTimeRef DisplayString,
	uxsA2StatusFileModInterval DisplayString,
	uxsA2StatusFileModValue INTEGER,
	uxsA2StatusFileMod INTEGER,
	uxsA2StatusFileModMonitor INTEGER,
	uxsA2StatusFileModStatus INTEGER,
	uxsA2StatusFileCallBackRef DisplayString,
	uxsA2StatusFileButton INTEGER
}

uxsA2StatusFileWatcherName OBJECT-TYPE
	SYNTAX DisplayString
	ACCESS read-only
	STATUS mandatory
	DESCRIPTION "&<caiUxsA2.976>The user-defined name which uniquely identifies the file watcher."
	::= { uxsA2StatusFileEntry 1 }

uxsA2StatusFileName OBJECT-TYPE
	SYNTAX DisplayString
	ACCESS read-write
	STATUS mandatory
	DESCRIPTION "&<caiUxsA2.977>Name of the file. This name may contain environment variables. The attribute is used as a filter element for one-to-many monitoring (one watcher monitors several resources simultaneously). The file name (not the path) can be a regular expression."
	::= { uxsA2StatusFileEntry 2 }

uxsA2StatusFileEvalPolicy OBJECT-TYPE
	SYNTAX INTEGER {
		individual(1),
		min(2),
		max(3),
		sum(4),
		avg(5)
	}
	ACCESS read-write
	STATUS mandatory
	DESCRIPTION "&<caiUxsA2.978>Current evaluation policy for the file watcher. Defines how metric values will be calculated and 'culprits' be determined if two or more file resources fall into the monitoring scope of a one-to-many watcher. If set to 1 (individual), metric values will be set to the worst values (lowest and/or highest) of all file instances; if the value of a metric violates the threshold condition, the respective 'culprits' list will contain all instances individually violating the most severe threshold. If set to 2 (min), metric values will be set to the lowest (minimum) values of all file instances; if the value of a metric violates the threshold condition, the respective 'culprits' list will contain all instances having the same minimum value. If set to 3 (max), metric values will be set to the highest (maximum) values of all file instances; if the value of a metric violates the threshold condition, the respective 'culprits' list will contain all instances having the same maximum value. If set to 4 (sum), metric values will be set to the cumulative values (sum) of all file instances; if the value of a metric violates the threshold condition, the respective 'culprits' list will contain all instances. If set to 5 (avg), metric values will be set to the average values of all file instances; if the value of a metric violates the threshold condition, the respective 'culprits' list will contain all instances individually violating the most severe threshold."
	DEFVAL { 0 }
	::= { uxsA2StatusFileEntry 3 }

uxsA2StatusFileDescription OBJECT-TYPE
	SYNTAX DisplayString
	ACCESS read-write
	STATUS mandatory
	DESCRIPTION "&<caiUxsA2.979>Current description for the file watcher."
	::= { uxsA2StatusFileEntry 4 }

uxsA2StatusFileAggLagValue OBJECT-TYPE
	SYNTAX INTEGER
	ACCESS read-only
	STATUS mandatory
	DESCRIPTION "&<caiUxsA2.980>Current aggregate lag value of the file watcher. Indicates the consecutive number of times at which any status was not in the ok state. The aggregate status changes from ok as soon as the aggregate lag value reaches the configured value."
	::= { uxsA2StatusFileEntry 5 }

uxsA2StatusFileAggLag OBJECT-TYPE
	SYNTAX INTEGER
	ACCESS read-write
	STATUS mandatory
	DESCRIPTION "&<caiUxsA2.981>Current aggregate lag setting for the file watcher. Specifies the consecutive number of times at which any status is not in the ok state, before the aggregate status changes. This value must be greater than 0."
	::= { uxsA2StatusFileEntry 6 }

uxsA2StatusFileAggStatus OBJECT-TYPE
	SYNTAX INTEGER {
		unknown(1),
		ok(2),
		warning(3),
		critical(4),
		passive(5)
	}
	ACCESS read-only
	STATUS mandatory
	DESCRIPTION "&<caiUxsA2.982>Current aggregate status of the file watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { uxsA2StatusFileEntry 7 }

uxsA2StatusFileInstValue OBJECT-TYPE
	SYNTAX DisplayString
	ACCESS read-only
	STATUS mandatory
	DESCRIPTION "&<caiUxsA2.983>Current value for the instance count monitoring of the file watcher."
	DEFVAL { "0" }
	::= { uxsA2StatusFileEntry 8 }

uxsA2StatusFileInstMin OBJECT-TYPE
	SYNTAX DisplayString
	ACCESS read-write
	STATUS mandatory
	DESCRIPTION "&<caiUxsA2.984>Current minimum threshold for the instance count monitoring of the file watcher. This value represents a declining threshold and must be equal to or greater than 0.0, but cannot be greater than the maximum threshold. A value of -1 disables the evaluation of this threshold."
	DEFVAL { "-2" }
	::= { uxsA2StatusFileEntry 9 }

uxsA2StatusFileInstMax OBJECT-TYPE
	SYNTAX DisplayString
	ACCESS read-write
	STATUS mandatory
	DESCRIPTION "&<caiUxsA2.985>Current maximum threshold for the instance count monitoring of the file watcher. This value represents a rising threshold and must be equal to or greater than 0.0, but cannot be less than the minimum threshold. A value of -1 disables the evaluation of this threshold."
	DEFVAL { "-2" }
	::= { uxsA2StatusFileEntry 10 }

uxsA2StatusFileInstMonitor OBJECT-TYPE
	SYNTAX INTEGER {
		do-not-monitor(1),
		down-warning(2),
		down-critical(3)
	}
	ACCESS read-write
	STATUS mandatory
	DESCRIPTION "&<caiUxsA2.986>Current monitor level for the instance count monitoring of the file watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusFileEntry 11 }

uxsA2StatusFileInstStatus OBJECT-TYPE
	SYNTAX INTEGER {
		unknown(1),
		up(2),
		down-warning(3),
		down-critical(4)
	}
	ACCESS read-only
	STATUS mandatory
	DESCRIPTION "&<caiUxsA2.987>Current status for the instance count monitoring of the file watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusFileEntry 12 }

uxsA2StatusFileInstIds OBJECT-TYPE
	SYNTAX DisplayString
	ACCESS read-only
	STATUS mandatory
	DESCRIPTION "&<caiUxsA2.988>The names of all files monitored by the watcher are displayed here if the 'number of files' metric is in a warning or critical state. The entries are sorted in alphabetical order."
	::= { uxsA2StatusFileEntry 13 }

uxsA2StatusFileSizeTotal OBJECT-TYPE
	SYNTAX DisplayString
	ACCESS read-only
	STATUS mandatory
	DESCRIPTION "&<caiUxsA2.989>The total size (in kilobytes) of the file(s) being monitored at the time the watcher is created. This value may depend on the current evaluation policy (see there for a more detailed description). The total size is reset to the current size if the file name or the evaluation policy are changed."
	DEFVAL { "0" }
	::= { uxsA2StatusFileEntry 14 }

uxsA2StatusFileSizeMinValue OBJECT-TYPE
	SYNTAX DisplayString
	ACCESS read-only
	STATUS mandatory
	DESCRIPTION "&<caiUxsA2.990>The current minimum size (in kilobytes) of the file(s) being monitored. This value may depend on the evaluation policy (see there for a more detailed description)."
	DEFVAL { "0" }
	::= { uxsA2StatusFileEntry 15 }

uxsA2StatusFileSizeMaxValue OBJECT-TYPE
	SYNTAX DisplayString
	ACCESS read-only
	STATUS mandatory
	DESCRIPTION "&<caiUxsA2.991>The current maximum size (in kilobytes) of the file(s) being monitored. This value may depend on the evaluation policy (see there for a more detailed description)."
	DEFVAL { "0" }
	::= { uxsA2StatusFileEntry 16 }

uxsA2StatusFileSizeWarnMin OBJECT-TYPE
	SYNTAX DisplayString
	ACCESS read-write
	STATUS mandatory
	DESCRIPTION "&<caiUxsA2.992>Current warning minimum threshold, in kilobytes, for the size utilization monitoring of the file watcher. This value represents a declining threshold and must be equal to or greater than 0.0, equal to or greater than the critical minimum threshold, but cannot be greater than the warning maximum threshold. A value of -1 disables the evaluation of this threshold. The threshold can be specified as either an absolute value (n) or a percentage (n%). The value of uxsA2StatusFileSizeTotal will be the reference value for n% notations."
	DEFVAL { "-2" }
	::= { uxsA2StatusFileEntry 17 }

uxsA2StatusFileSizeWarnMax OBJECT-TYPE
	SYNTAX DisplayString
	ACCESS read-write
	STATUS mandatory
	DESCRIPTION "&<caiUxsA2.993>Current warning maximum threshold, in kilobytes, for the size utilization monitoring of the file watcher. This value represents a rising threshold and must be equal to or greater than 0.0, equal to or greater than the warning minimum threshold, but cannot be greater than the critical maximum threshold. A value of -1 disables the evaluation of this threshold. The threshold can be specified as either an absolute value (n) or a percentage (n%). The value of uxsA2StatusFileSizeTotal will be the reference value for n% notations."
	DEFVAL { "-2" }
	::= { uxsA2StatusFileEntry 18 }

uxsA2StatusFileSizeCritMin OBJECT-TYPE
	SYNTAX DisplayString
	ACCESS read-write
	STATUS mandatory
	DESCRIPTION "&<caiUxsA2.994>Current critical minimum threshold, in kilobytes, for the size utilization monitoring of the file watcher. This value represents a declining threshold and must be equal to or greater than 0.0, but cannot be greater than the warning minimum threshold. A value of -1 disables the evaluation of this threshold. The threshold can be specified as either an absolute value (n) or a percentage (n%). The value of uxsA2StatusFileSizeTotal will be the reference value for n% notations."
	DEFVAL { "-2" }
	::= { uxsA2StatusFileEntry 19 }

uxsA2StatusFileSizeCritMax OBJECT-TYPE
	SYNTAX DisplayString
	ACCESS read-write
	STATUS mandatory
	DESCRIPTION "&<caiUxsA2.995>Current critical maximum threshold, in kilobytes, for the size utilization monitoring of the file watcher. This value represents a rising threshold and must be equal to or greater than 0.0, but cannot be less than the warning maximum threshold. A value of -1 disables the evaluation of this threshold. The threshold can be specified as either an absolute value (n) or a percentage (n%). The value of uxsA2StatusFileSizeTotal will be the reference value for n% notations."
	DEFVAL { "-2" }
	::= { uxsA2StatusFileEntry 20 }

uxsA2StatusFileSizeMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.996>Current monitor level for the size utilization monitoring of the file watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2StatusFileEntry 21 }

uxsA2StatusFileSizeStatus OBJECT-TYPE
	SYNTAX INTEGER {
		unknown(1),
		up(2),
		down-warning(3),
		down-critical(4)
	}
	ACCESS read-only
	STATUS mandatory
	DESCRIPTION "&<caiUxsA2.997>Current status for the size utilization monitoring of the file watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusFileEntry 22 }

uxsA2StatusFileSizeIds OBJECT-TYPE
	SYNTAX DisplayString
	ACCESS read-only
	STATUS mandatory
	DESCRIPTION "&<caiUxsA2.998>The names and size values of the files causing a warning or critical state of the size metric. The entries in this culprit list depend on the evaluation policy. They are sorted by size in ascending order if a minimum threshold is broken and in descending order if a maximum threshold or both limits are broken. individual : Those individual instances breaching the thresholds are displayed in the culprit list. min : The instance(s) showing the minimum value is/are displayed in the culprit list. max : The instance(s) showing the maximum value is/are displayed in the culprit list. sum : All instances are displayed in the culprit list. avg : Those individual instances breaching the thresholds are displayed in the culprit list."
	::= { uxsA2StatusFileEntry 23 }

uxsA2StatusFileSizeDValue OBJECT-TYPE
	SYNTAX DisplayString
	ACCESS read-only
	STATUS mandatory
	DESCRIPTION "&<caiUxsA2.999>Current value, in kilobytes, for the delta size utilization monitoring of the file watcher."
	DEFVAL { "0" }
	::= { uxsA2StatusFileEntry 24 }

uxsA2StatusFileSizeDWarnValue OBJECT-TYPE
	SYNTAX DisplayString
	ACCESS read-only
	STATUS mandatory
	DESCRIPTION "&<caiUxsA2.1000>Active warning threshold, in kilobytes, as derived from the configured value for the delta size utilization monitoring of the file watcher. This value represents a rising threshold and must be greater than 0.0, but cannot be greater than the active critical threshold. These constraints will be maintained by the agent during all configuration actions."
	::= { uxsA2StatusFileEntry 25 }

uxsA2StatusFileSizeDCritValue OBJECT-TYPE
	SYNTAX DisplayString
	ACCESS read-only
	STATUS mandatory
	DESCRIPTION "&<caiUxsA2.1001>Active critical threshold, in kilobytes, as derived from the configured value for the delta size utilization monitoring of the file watcher. This value represents a rising threshold and must be greater than 0.0, but cannot be less than the active warning threshold. These constraints will be maintained by the agent during all configuration actions."
	::= { uxsA2StatusFileEntry 26 }

uxsA2StatusFileSizeDWarn OBJECT-TYPE
	SYNTAX DisplayString
	ACCESS read-write
	STATUS mandatory
	DESCRIPTION "&<caiUxsA2.1002>Configured warning threshold from which the active warning threshold is derived for the delta size utilization monitoring of the file watcher. The threshold can be specified as either an absolute value or a percentage and can denote a growth, shrinkage or change in either direction: Absolute shrinkage (n-), absolute growth (n+), absolute change in either direction (n), percentage shrinkage (n%-), percentage growth (n%+), or percentage change in either direction (n%). The value of uxsA2StatusFileSizeTotal will be the reference value for n% notations."
	::= { uxsA2StatusFileEntry 27 }

uxsA2StatusFileSizeDCrit OBJECT-TYPE
	SYNTAX DisplayString
	ACCESS read-write
	STATUS mandatory
	DESCRIPTION "&<caiUxsA2.1003>Configured critical threshold from which the active critical threshold is derived for the delta size utilization monitoring of the file watcher. The threshold can be specified as either an absolute value or a percentage and can denote a growth, shrinkage or change in either direction: Absolute shrinkage (n-), absolute growth (n+), absolute change in either direction (n), percentage shrinkage (n%-), percentage growth (n%+), or percentage change in either direction (n%). The value of uxsA2StatusFileSizeTotal will be the reference value for n% notations."
	::= { uxsA2StatusFileEntry 28 }

uxsA2StatusFileSizeDMonitor OBJECT-TYPE
	SYNTAX INTEGER {
		do-not-monitor(1),
		warning-only(2),
		critical-only(3),
		both(4)
	}
	ACCESS read-write
	STATUS mandatory
	DESCRIPTION "&<caiUxsA2.1004>Current monitor level for the delta size utilization monitoring of the file watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusFileEntry 29 }

uxsA2StatusFileSizeDStatus OBJECT-TYPE
	SYNTAX INTEGER {
		unknown(1),
		ok(2),
		warning(3),
		critical(4)
	}
	ACCESS read-only
	STATUS mandatory
	DESCRIPTION "&<caiUxsA2.1005>Current status for the delta size utilization monitoring of the file watcher: 1 (unknown) - An error occurred during data collection, 2 (ok) - The resource is operating within the defined limits or status evaluation is turned off and/or polling is disabled, 3 (warning) - The resource has breached the warning threshold, 4 (critical) - The resource has breached the critical threshold."
	::= { uxsA2StatusFileEntry 30 }

uxsA2StatusFileSizeDIds OBJECT-TYPE
	SYNTAX DisplayString
	ACCESS read-only
	STATUS mandatory
	DESCRIPTION "&<caiUxsA2.1006>The names and size delta values of the files causing a warning or critical state of the size delta metric. The entries in this culprit list depend on the evaluation policy. They are sorted by size delta in ascending order if shrinkage is monitored, in descending order if growth is monitored and in descending order of absolute values if any change is monitored. individual : Those individual instances breaching the thresholds are displayed in the culprit list. min : The instance(s) showing the minimum value is/are displayed in the culprit list. max : The instance(s) showing the maximum value is/are displayed in the culprit list. sum : All instances are displayed in the culprit list. avg : Those individual instances breaching the thresholds are displayed in the culprit list."
	::= { uxsA2StatusFileEntry 31 }

uxsA2StatusFileModTime OBJECT-TYPE
	SYNTAX DisplayString
	ACCESS read-only
	STATUS mandatory
	DESCRIPTION "&<caiUxsA2.1007>The modification time of the file. For one-to-many watchers, the maximum of all instances. The time format is YYYY-MM-DD HH:MM:SS."
	::= { uxsA2StatusFileEntry 32 }

uxsA2StatusFileChangeTime OBJECT-TYPE
	SYNTAX DisplayString
	ACCESS read-only
	STATUS mandatory
	DESCRIPTION "&<caiUxsA2.1008>The change time of the file. For one-to-many watchers, the maximum of all instances. The time format is YYYY-MM-DD HH:MM:SS."
	::= { uxsA2StatusFileEntry 33 }

uxsA2StatusFileAccessTime OBJECT-TYPE
	SYNTAX DisplayString
	ACCESS read-only
	STATUS mandatory
	DESCRIPTION "&<caiUxsA2.1009>The access time of the file. For one-to-many watchers, the maximum of all instances. The time format is YYYY-MM-DD HH:MM:SS."
	::= { uxsA2StatusFileEntry 34 }

uxsA2StatusFileTimeRef OBJECT-TYPE
	SYNTAX DisplayString
	ACCESS read-only
	STATUS mandatory
	DESCRIPTION "&<caiUxsA2.1010>The time reference used to calculate the status of the modification metric. The time format is YYYY-MM-DD HH:MM:SS. The time reference is reset: - if name or evaluation policy change. - manually by the user choosing the respective option of modification policy. - if the monitored time stamp has changed and the status is 'up' (condition is satisfied). At the same time a new modification interval is set up."
	::= { uxsA2StatusFileEntry 35 }

uxsA2StatusFileModInterval OBJECT-TYPE
	SYNTAX DisplayString
	ACCESS read-write
	STATUS mandatory
	DESCRIPTION "&<caiUxsA2.1011>The period in seconds to be considered for calculating status and value of the modification metric. For a value of zero the period is identical to the current poll interval."
	::= { uxsA2StatusFileEntry 36 }

uxsA2StatusFileModValue OBJECT-TYPE
	SYNTAX INTEGER {
		not-modified(1),
		not-changed(2),
		not-changed-only(3),
		not-accessed(4),
		modified(5),
		changed(6),
		changed-only(7),
		accessed(8)
	}
	ACCESS read-only
	STATUS mandatory
	DESCRIPTION "&<caiUxsA2.1012>The status of the modification metric. Possible values: If monitoring modification time: modified or not-modified. If monitoring change time: changed or not-changed. If monitoring change time only : changed-only or not-changed-only. If monitoring access time: accessed or not-accessed."
	::= { uxsA2StatusFileEntry 37 }

uxsA2StatusFileMod OBJECT-TYPE
	SYNTAX INTEGER {
		should-not-be-modified(1),
		should-not-be-changed(2),
		should-not-be-changed-only(3),
		should-not-be-accessed(4),
		should-be-modified(5),
		should-be-changed(6),
		should-be-changed-only(7),
		should-be-accessed(8),
		reset-time-reference(9)
	}
	ACCESS read-write
	STATUS mandatory
	DESCRIPTION "&<caiUxsA2.1013>Current monitor condition for the modification monitoring of the file watcher. As basis for the comparison the user can choose between modification time, change time, change time only (change time is modified and modification time is not) and access time. The timestamps can be monitored for being modified (should-be-modified, should-be-changed, should-be-changed-only, should-be-accessed) or for being unmodified (should-not-be-modified, should-not-be-changed, should-not-be-changed-only, should-not-be-accessed). At each poll the current timestamp of the file will be compared with the reference timestamp according to the chosen policy. For one-to-many watchers the latest timestamp of all files is considered. If monitoring is for being modified the status is down if the file was not modified for more seconds than the value of 'FileModInterval'. If monitoring is for being unmodified the status is down if the file was modified more often than every 'FileModInterval' seconds. If 'FileModInterval' is zero any modification sets the status down. If the monitor status is 'down' and the monitoring condition is met at the next poll the status of the watcher will revert to up (automatic repair). However, the metric may be reset manually at any time by setting the monitor condition to reset-time-reference. Afterwards the previous policy setting is restored. Note: if the policy is set to should-not-xxx and 'FileModInterval' is 0, no automatic repair takes place. This behaviour is for compatibility with the old UNIX System Agent (caiUxOs). Note that status evaluation only takes place when the agent polls. Thus the end of the modification interval will be detected on the subsequent poll or query."
	DEFVAL { 0 }
	::= { uxsA2StatusFileEntry 38 }

uxsA2StatusFileModMonitor OBJECT-TYPE
	SYNTAX INTEGER {
		do-not-monitor(1),
		down-warning(2),
		down-critical(3)
	}
	ACCESS read-write
	STATUS mandatory
	DESCRIPTION "&<caiUxsA2.1014>Current monitor level for the modification monitoring of the file watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusFileEntry 39 }

uxsA2StatusFileModStatus OBJECT-TYPE
	SYNTAX INTEGER {
		unknown(1),
		up(2),
		down-warning(3),
		down-critical(4)
	}
	ACCESS read-only
	STATUS mandatory
	DESCRIPTION "&<caiUxsA2.1015>Current status for the modification monitoring of the file watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusFileEntry 40 }

uxsA2StatusFileCallBackRef OBJECT-TYPE
	SYNTAX DisplayString
	ACCESS read-only
	STATUS mandatory
	DESCRIPTION "&<caiUxsA2.1016>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusFileEntry 41 }

uxsA2StatusFileButton OBJECT-TYPE
	SYNTAX INTEGER {
		none(1),
		remove(2)
	}
	ACCESS read-write
	STATUS mandatory
	DESCRIPTION "&<caiUxsA2.1017>This attribute is used to remove the file watcher. If set to 2 (remove), the agent removes the watcher from the table. This attribute cannot be set to 1 (none)."
	DEFVAL { 1 }
	::= { uxsA2StatusFileEntry 42 }

--
-- The StatusDisk Group
--

uxsA2StatusDiskCount OBJECT-TYPE
	SYNTAX INTEGER
	ACCESS read-only
	STATUS mandatory
	DESCRIPTION "&<caiUxsA2.1018>Number of entries in the disk status table."
	::= { uxsA2StatusDiskGroup 1 }

uxsA2StatusDiskTable OBJECT-TYPE
	SYNTAX SEQUENCE OF UxsA2StatusDiskEntry
	ACCESS not-accessible
	STATUS mandatory
	DESCRIPTION "&<caiUxsA2.1019>The disk status table containing details about the currently configured disk watchers."
	::= { uxsA2StatusDiskGroup 2 }

uxsA2StatusDiskEntry OBJECT-TYPE
	SYNTAX UxsA2StatusDiskEntry
	ACCESS not-accessible
	STATUS mandatory
	DESCRIPTION "&<caiUxsA2.1020>Entry in the disk status table."
	INDEX {
		uxsA2StatusDiskName
	}
	::= { uxsA2StatusDiskTable 1 }

UxsA2StatusDiskEntry ::= SEQUENCE {
	uxsA2StatusDiskName DisplayString,
	uxsA2StatusDiskDescription DisplayString,
	uxsA2StatusDiskAutoWatcherName DisplayString,
	uxsA2StatusDiskAggLagValue INTEGER,
	uxsA2StatusDiskAggLag INTEGER,
	uxsA2StatusDiskAggStatus INTEGER,
	uxsA2StatusDiskDescriptiveName DisplayString,
	uxsA2StatusDiskClusterType INTEGER,
	uxsA2StatusDiskTputValue DisplayString,
	uxsA2StatusDiskTputWarnMin DisplayString,
	uxsA2StatusDiskTputWarnMax DisplayString,
	uxsA2StatusDiskTputCritMin DisplayString,
	uxsA2StatusDiskTputCritMax DisplayString,
	uxsA2StatusDiskTputMonitor INTEGER,
	uxsA2StatusDiskTputStatus INTEGER,
	uxsA2StatusDiskLossAction INTEGER,
	uxsA2StatusDiskLossStatus INTEGER,
	uxsA2StatusDiskCallBackRef DisplayString,
	uxsA2StatusDiskButton INTEGER
}

uxsA2StatusDiskName OBJECT-TYPE
	SYNTAX DisplayString
	ACCESS read-only
	STATUS mandatory
	DESCRIPTION "&<caiUxsA2.1021>Name of the disk."
	::= { uxsA2StatusDiskEntry 1 }

uxsA2StatusDiskDescription OBJECT-TYPE
	SYNTAX DisplayString
	ACCESS read-write
	STATUS mandatory
	DESCRIPTION "&<caiUxsA2.1022>Current description for the disk watcher."
	::= { uxsA2StatusDiskEntry 2 }

uxsA2StatusDiskAutoWatcherName OBJECT-TYPE
	SYNTAX DisplayString
	ACCESS read-only
	STATUS mandatory
	DESCRIPTION "&<caiUxsA2.1023>Name of the disk auto watcher which automatically created this watcher. This attribute is left blank if the watcher was added manually."
	::= { uxsA2StatusDiskEntry 3 }

uxsA2StatusDiskAggLagValue OBJECT-TYPE
	SYNTAX INTEGER
	ACCESS read-only
	STATUS mandatory
	DESCRIPTION "&<caiUxsA2.1024>Current aggregate lag value of the disk watcher. Indicates the consecutive number of times at which any status was not in the ok state. The aggregate status changes from ok as soon as the aggregate lag value reaches the configured value."
	::= { uxsA2StatusDiskEntry 4 }

uxsA2StatusDiskAggLag OBJECT-TYPE
	SYNTAX INTEGER
	ACCESS read-write
	STATUS mandatory
	DESCRIPTION "&<caiUxsA2.1025>Current aggregate lag setting for the disk watcher. Specifies the consecutive number of times at which any status is not in the ok state, before the aggregate status changes. This value must be greater than 0."
	::= { uxsA2StatusDiskEntry 5 }

uxsA2StatusDiskAggStatus OBJECT-TYPE
	SYNTAX INTEGER {
		unknown(1),
		ok(2),
		warning(3),
		critical(4),
		passive(5)
	}
	ACCESS read-only
	STATUS mandatory
	DESCRIPTION "&<caiUxsA2.1026>Current aggregate status of the disk watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { uxsA2StatusDiskEntry 6 }

uxsA2StatusDiskDescriptiveName OBJECT-TYPE
	SYNTAX DisplayString
	ACCESS read-only
	STATUS mandatory
	DESCRIPTION "&<caiUxsA2.1027>An arbitrary descriptive string."
	::= { uxsA2StatusDiskEntry 7 }

uxsA2StatusDiskClusterType OBJECT-TYPE
	SYNTAX INTEGER {
		not-clustered(1),
		clustered-active(2),
		clustered-passive(3)
	}
	ACCESS read-only
	STATUS mandatory
	DESCRIPTION "&<caiUxsA2.1028>Cluster type of the disk: 1 (not-clustered) - Resource is not clustered, 2 (clustered-active) - Local cluster node has resource ownership, 3 (clustered-passive) - Another node in the cluster has resource ownership; the agent on the local node does not actively monitor the resource until ownership is transferred back."
	::= { uxsA2StatusDiskEntry 8 }

uxsA2StatusDiskTputValue OBJECT-TYPE
	SYNTAX DisplayString
	ACCESS read-only
	STATUS mandatory
	DESCRIPTION "&<caiUxsA2.1029>Current value, in kilobytes/s, for the disk throughput monitoring of the disk watcher."
	DEFVAL { "0" }
	::= { uxsA2StatusDiskEntry 9 }

uxsA2StatusDiskTputWarnMin OBJECT-TYPE
	SYNTAX DisplayString
	ACCESS read-write
	STATUS mandatory
	DESCRIPTION "&<caiUxsA2.1030>Current warning minimum threshold, in kilobytes/s, for the disk throughput monitoring of the disk watcher. This value represents a declining threshold and must be equal to or greater than 0.0, equal to or greater than the critical minimum threshold, but cannot be greater than the warning maximum threshold. A value of -1 disables the evaluation of this threshold."
	DEFVAL { "-2" }
	::= { uxsA2StatusDiskEntry 10 }

uxsA2StatusDiskTputWarnMax OBJECT-TYPE
	SYNTAX DisplayString
	ACCESS read-write
	STATUS mandatory
	DESCRIPTION "&<caiUxsA2.1031>Current warning maximum threshold, in kilobytes/s, for the disk throughput monitoring of the disk watcher. This value represents a rising threshold and must be equal to or greater than 0.0, equal to or greater than the warning minimum threshold, but cannot be greater than the critical maximum threshold. A value of -1 disables the evaluation of this threshold."
	DEFVAL { "-2" }
	::= { uxsA2StatusDiskEntry 11 }

uxsA2StatusDiskTputCritMin OBJECT-TYPE
	SYNTAX DisplayString
	ACCESS read-write
	STATUS mandatory
	DESCRIPTION "&<caiUxsA2.1032>Current critical minimum threshold, in kilobytes/s, for the disk throughput monitoring of the disk watcher. This value represents a declining threshold and must be equal to or greater than 0.0, but cannot be greater than the warning minimum threshold. A value of -1 disables the evaluation of this threshold."
	DEFVAL { "-2" }
	::= { uxsA2StatusDiskEntry 12 }

uxsA2StatusDiskTputCritMax OBJECT-TYPE
	SYNTAX DisplayString
	ACCESS read-write
	STATUS mandatory
	DESCRIPTION "&<caiUxsA2.1033>Current critical maximum threshold, in kilobytes/s, for the disk throughput monitoring of the disk watcher. This value represents a rising threshold and must be equal to or greater than 0.0, but cannot be less than the warning maximum threshold. A value of -1 disables the evaluation of this threshold."
	DEFVAL { "-2" }
	::= { uxsA2StatusDiskEntry 13 }

uxsA2StatusDiskTputMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.1034>Current monitor level for the disk throughput monitoring of the disk watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2StatusDiskEntry 14 }

uxsA2StatusDiskTputStatus OBJECT-TYPE
	SYNTAX INTEGER {
		unknown(1),
		up(2),
		down-warning(3),
		down-critical(4)
	}
	ACCESS read-only
	STATUS mandatory
	DESCRIPTION "&<caiUxsA2.1035>Current status for the disk throughput monitoring of the disk watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusDiskEntry 15 }

uxsA2StatusDiskLossAction OBJECT-TYPE
	SYNTAX INTEGER {
		remove(1),
		up(2),
		down-warning(3),
		down-critical(4)
	}
	ACCESS read-write
	STATUS mandatory
	DESCRIPTION "&<caiUxsA2.1036>Current loss action for the disk watcher. Specifies the action to take if the monitored disk is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusDiskEntry 16 }

uxsA2StatusDiskLossStatus OBJECT-TYPE
	SYNTAX INTEGER {
		unknown(1),
		up(2),
		down-warning(3),
		down-critical(4)
	}
	ACCESS read-only
	STATUS mandatory
	DESCRIPTION "&<caiUxsA2.1037>Current loss status of the disk watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusDiskEntry 17 }

uxsA2StatusDiskCallBackRef OBJECT-TYPE
	SYNTAX DisplayString
	ACCESS read-only
	STATUS mandatory
	DESCRIPTION "&<caiUxsA2.1038>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusDiskEntry 18 }

uxsA2StatusDiskButton OBJECT-TYPE
	SYNTAX INTEGER {
		none(1),
		remove(2)
	}
	ACCESS read-write
	STATUS mandatory
	DESCRIPTION "&<caiUxsA2.1039>This attribute is used to remove the disk watcher. If set to 2 (remove), the agent removes the watcher from the table. This attribute cannot be set to 1 (none)."
	DEFVAL { 1 }
	::= { uxsA2StatusDiskEntry 19 }

--
-- The StatusProc Group
--

uxsA2StatusProcCount OBJECT-TYPE
	SYNTAX INTEGER
	ACCESS read-only
	STATUS mandatory
	DESCRIPTION "&<caiUxsA2.1040>Number of entries in the process status table."
	::= { uxsA2StatusProcGroup 1 }

uxsA2StatusProcTable OBJECT-TYPE
	SYNTAX SEQUENCE OF UxsA2StatusProcEntry
	ACCESS not-accessible
	STATUS mandatory
	DESCRIPTION "&<caiUxsA2.1041>The process status table containing details about the currently configured process watchers."
	::= { uxsA2StatusProcGroup 2 }

uxsA2StatusProcEntry OBJECT-TYPE
	SYNTAX UxsA2StatusProcEntry
	ACCESS not-accessible
	STATUS mandatory
	DESCRIPTION "&<caiUxsA2.1042>Entry in the process status table."
	INDEX {
		uxsA2StatusProcWatcherName
	}
	::= { uxsA2StatusProcTable 1 }

UxsA2StatusProcEntry ::= SEQUENCE {
	uxsA2StatusProcWatcherName DisplayString,
	uxsA2StatusProcMatchType INTEGER,
	uxsA2StatusProcName DisplayString,
	uxsA2StatusProcPath DisplayString,
	uxsA2StatusProcArgs DisplayString,
	uxsA2StatusProcUser DisplayString,
	uxsA2StatusProcEvalPolicy INTEGER,
	uxsA2StatusProcClusterResourceGroup DisplayString,
	uxsA2StatusProcDescription DisplayString,
	uxsA2StatusProcAggLagValue INTEGER,
	uxsA2StatusProcAggLag INTEGER,
	uxsA2StatusProcAggStatus INTEGER,
	uxsA2StatusProcClusterType INTEGER,
	uxsA2StatusProcInstValue INTEGER,
	uxsA2StatusProcInstMin INTEGER,
	uxsA2StatusProcInstMax INTEGER,
	uxsA2StatusProcInstMonitor INTEGER,
	uxsA2StatusProcInstStatus INTEGER,
	uxsA2StatusProcInstIds DisplayString,
	uxsA2StatusProcChildMinValue INTEGER,
	uxsA2StatusProcChildMaxValue INTEGER,
	uxsA2StatusProcChildMin INTEGER,
	uxsA2StatusProcChildMax INTEGER,
	uxsA2StatusProcChildMonitor INTEGER,
	uxsA2StatusProcChildStatus INTEGER,
	uxsA2StatusProcChildIds DisplayString,
	uxsA2StatusProcThreadMinValue INTEGER,
	uxsA2StatusProcThreadMaxValue INTEGER,
	uxsA2StatusProcThreadMin INTEGER,
	uxsA2StatusProcThreadMax INTEGER,
	uxsA2StatusProcThreadMonitor INTEGER,
	uxsA2StatusProcThreadStatus INTEGER,
	uxsA2StatusProcThreadIds DisplayString,
	uxsA2StatusProcSizeMinValue INTEGER,
	uxsA2StatusProcSizeMaxValue INTEGER,
	uxsA2StatusProcSizeMin INTEGER,
	uxsA2StatusProcSizeMax INTEGER,
	uxsA2StatusProcSizeMonitor INTEGER,
	uxsA2StatusProcSizeStatus INTEGER,
	uxsA2StatusProcSizeIds DisplayString,
	uxsA2StatusProcCpuUtilInterval DisplayString,
	uxsA2StatusProcCpuUtilMinValue DisplayString,
	uxsA2StatusProcCpuUtilMaxValue DisplayString,
	uxsA2StatusProcCpuUtilWarnMin DisplayString,
	uxsA2StatusProcCpuUtilWarnMax DisplayString,
	uxsA2StatusProcCpuUtilCritMin DisplayString,
	uxsA2StatusProcCpuUtilCritMax DisplayString,
	uxsA2StatusProcCpuUtilMonitor INTEGER,
	uxsA2StatusProcCpuUtilStatus INTEGER,
	uxsA2StatusProcCpuUtilIds DisplayString,
	uxsA2StatusProcCpuUtilLongtermInterval DisplayString,
	uxsA2StatusProcCpuUtilLongtermMinValue DisplayString,
	uxsA2StatusProcCpuUtilLongtermMaxValue DisplayString,
	uxsA2StatusProcCpuUtilLongtermWarnMin DisplayString,
	uxsA2StatusProcCpuUtilLongtermWarnMax DisplayString,
	uxsA2StatusProcCpuUtilLongtermCritMin DisplayString,
	uxsA2StatusProcCpuUtilLongtermCritMax DisplayString,
	uxsA2StatusProcCpuUtilLongtermMonitor INTEGER,
	uxsA2StatusProcCpuUtilLongtermStatus INTEGER,
	uxsA2StatusProcCpuUtilLongtermIds DisplayString,
	uxsA2StatusProcRestartValue INTEGER,
	uxsA2StatusProcRestart INTEGER,
	uxsA2StatusProcRestartMonitor INTEGER,
	uxsA2StatusProcRestartStatus INTEGER,
	uxsA2StatusProcCallBackRef DisplayString,
	uxsA2StatusProcButton INTEGER
}

uxsA2StatusProcWatcherName OBJECT-TYPE
	SYNTAX DisplayString
	ACCESS read-only
	STATUS mandatory
	DESCRIPTION "&<caiUxsA2.1043>Name of the process watcher."
	::= { uxsA2StatusProcEntry 1 }

uxsA2StatusProcMatchType OBJECT-TYPE
	SYNTAX INTEGER {
		positive-regular-expression(1),
		negative-regular-expression(2),
		positive-compare(3),
		negative-compare(4)
	}
	ACCESS read-write
	STATUS mandatory
	DESCRIPTION "&<caiUxsA2.1044>Current search algorithm for the process watcher. The filter is the logical AND of all attributes used to identify or otherwise narrow down resources. If the value of one of these attributes includes 'wildcards', then the watcher will basically behave like a one-to-many watcher, i.e. it may monitor two or more resources simultaneously. If set to 1 (positive-regular-expression), the agent searches for process resources that match the filter. Each of the filter attributes can denote an extended regular expression. If set to 2 (negative-regular-expression), the agent searches for process resources that do not match the filter. Each of the filter attributes can denote an extended regular expression. If set to 3 (positive-compare), the agent searches for process resources that match the filter. Each of the filter attributes specifies a substring to match from the beginning. If set to 4 (negative-compare), the agent searches for process resources that do not match the filter. Each of the filter attributes specifies a substring to match from the beginning."
	DEFVAL { 0 }
	::= { uxsA2StatusProcEntry 2 }

uxsA2StatusProcName OBJECT-TYPE
	SYNTAX DisplayString
	ACCESS read-write
	STATUS mandatory
	DESCRIPTION "&<caiUxsA2.1045>The filter condition for process names to match for this process watcher. Matches as specified in match type."
	::= { uxsA2StatusProcEntry 3 }

uxsA2StatusProcPath OBJECT-TYPE
	SYNTAX DisplayString
	ACCESS read-write
	STATUS mandatory
	DESCRIPTION "&<caiUxsA2.1046>The filter condition for process pathes to match for this process watcher. Matches as specified in match type."
	::= { uxsA2StatusProcEntry 4 }

uxsA2StatusProcArgs OBJECT-TYPE
	SYNTAX DisplayString
	ACCESS read-write
	STATUS mandatory
	DESCRIPTION "&<caiUxsA2.1047>The filter condition for process arguments to match for this process watcher. Matches as specified in match type."
	::= { uxsA2StatusProcEntry 5 }

uxsA2StatusProcUser OBJECT-TYPE
	SYNTAX DisplayString
	ACCESS read-write
	STATUS mandatory
	DESCRIPTION "&<caiUxsA2.1048>The filter condition for process owners to match for this process watcher. Matches as specified in match type. On Solaris 10 machines the name of the zone the process belongs to can be added to the attribute: <user>@<zone>. User and zone are evaluated as separate regular expressions. When no zone is specified the expression matches processes in the current zone only (<user>@<current>)."
	::= { uxsA2StatusProcEntry 6 }

uxsA2StatusProcEvalPolicy OBJECT-TYPE
	SYNTAX INTEGER {
		individual(1),
		min(2),
		max(3),
		sum(4),
		avg(5)
	}
	ACCESS read-write
	STATUS mandatory
	DESCRIPTION "&<caiUxsA2.1049>Current evaluation policy for the process watcher. Defines how metric values will be calculated and 'culprits' be determined if two or more process resources fall into the monitoring scope of a one-to-many watcher. If set to 1 (individual), metric values will be set to the worst values (lowest and/or highest) of all process instances; if the value of a metric violates the threshold condition, the respective 'culprits' list will contain all instances individually violating the most severe threshold. If set to 2 (min), metric values will be set to the lowest (minimum) values of all process instances; if the value of a metric violates the threshold condition, the respective 'culprits' list will contain all instances having the same minimum value. If set to 3 (max), metric values will be set to the highest (maximum) values of all process instances; if the value of a metric violates the threshold condition, the respective 'culprits' list will contain all instances having the same maximum value. If set to 4 (sum), metric values will be set to the cumulative values (sum) of all process instances; if the value of a metric violates the threshold condition, the respective 'culprits' list will contain all instances. If set to 5 (avg), metric values will be set to the average values of all process instances; if the value of a metric violates the threshold condition, the respective 'culprits' list will contain all instances individually violating the most severe threshold."
	DEFVAL { 0 }
	::= { uxsA2StatusProcEntry 7 }

uxsA2StatusProcClusterResourceGroup OBJECT-TYPE
	SYNTAX DisplayString
	ACCESS read-write
	STATUS mandatory
	DESCRIPTION "&<caiUxsA2.1050>Name of the cluster resource group of the process. For an unclustered process it is set to '-'."
	::= { uxsA2StatusProcEntry 8 }

uxsA2StatusProcDescription OBJECT-TYPE
	SYNTAX DisplayString
	ACCESS read-write
	STATUS mandatory
	DESCRIPTION "&<caiUxsA2.1051>Current description for the process watcher."
	::= { uxsA2StatusProcEntry 9 }

uxsA2StatusProcAggLagValue OBJECT-TYPE
	SYNTAX INTEGER
	ACCESS read-only
	STATUS mandatory
	DESCRIPTION "&<caiUxsA2.1052>Current aggregate lag value of the process watcher. Indicates the consecutive number of times at which any status was not in the ok state. The aggregate status changes from ok as soon as the aggregate lag value reaches the configured value."
	::= { uxsA2StatusProcEntry 10 }

uxsA2StatusProcAggLag OBJECT-TYPE
	SYNTAX INTEGER
	ACCESS read-write
	STATUS mandatory
	DESCRIPTION "&<caiUxsA2.1053>Current aggregate lag setting for the process watcher. Specifies the consecutive number of times at which any status is not in the ok state, before the aggregate status changes. This value must be greater than 0."
	::= { uxsA2StatusProcEntry 11 }

uxsA2StatusProcAggStatus OBJECT-TYPE
	SYNTAX INTEGER {
		unknown(1),
		ok(2),
		warning(3),
		critical(4),
		passive(5)
	}
	ACCESS read-only
	STATUS mandatory
	DESCRIPTION "&<caiUxsA2.1054>Current aggregate status of the process watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { uxsA2StatusProcEntry 12 }

uxsA2StatusProcClusterType OBJECT-TYPE
	SYNTAX INTEGER {
		not-clustered(1),
		clustered-active(2),
		clustered-passive(3),
		clustered-mixed(4)
	}
	ACCESS read-only
	STATUS mandatory
	DESCRIPTION "&<caiUxsA2.1055>Cluster type of the process: 1 (not-clustered) - Resource is not clustered, 2 (clustered-active) - Local cluster node has resource ownership, 3 (clustered-passive) - Another node in the cluster has resource ownership; the agent on the local node does not actively monitor the resource until ownership is transferred back, 4 (clustered-mixed) - The resource instances monitored by the watcher have different cluster types."
	::= { uxsA2StatusProcEntry 13 }

uxsA2StatusProcInstValue OBJECT-TYPE
	SYNTAX INTEGER
	ACCESS read-only
	STATUS mandatory
	DESCRIPTION "&<caiUxsA2.1056>The current value for the instance count monitoring of the process watcher."
	::= { uxsA2StatusProcEntry 14 }

uxsA2StatusProcInstMin OBJECT-TYPE
	SYNTAX INTEGER
	ACCESS read-write
	STATUS mandatory
	DESCRIPTION "&<caiUxsA2.1057>Current minimum threshold for the instance count monitoring of the process watcher. This value represents a declining threshold and must be equal to or greater than 0, but cannot be greater than the maximum threshold. A value of -1 disables the evaluation of this threshold."
	DEFVAL { -2 }
	::= { uxsA2StatusProcEntry 15 }

uxsA2StatusProcInstMax OBJECT-TYPE
	SYNTAX INTEGER
	ACCESS read-write
	STATUS mandatory
	DESCRIPTION "&<caiUxsA2.1058>Current maximum threshold for the instance count monitoring of the process watcher. This value represents a rising threshold and must be equal to or greater than 0, but cannot be less than the minimum threshold. A value of -1 disables the evaluation of this threshold."
	DEFVAL { -2 }
	::= { uxsA2StatusProcEntry 16 }

uxsA2StatusProcInstMonitor OBJECT-TYPE
	SYNTAX INTEGER {
		do-not-monitor(1),
		down-warning(2),
		down-critical(3)
	}
	ACCESS read-write
	STATUS mandatory
	DESCRIPTION "&<caiUxsA2.1059>Current monitor level for the instance count monitoring of the process watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusProcEntry 17 }

uxsA2StatusProcInstStatus OBJECT-TYPE
	SYNTAX INTEGER {
		unknown(1),
		up(2),
		down-warning(3),
		down-critical(4)
	}
	ACCESS read-only
	STATUS mandatory
	DESCRIPTION "&<caiUxsA2.1060>Current status for the instance count monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusProcEntry 18 }

uxsA2StatusProcInstIds OBJECT-TYPE
	SYNTAX DisplayString
	ACCESS read-only
	STATUS mandatory
	DESCRIPTION "&<caiUxsA2.1061>List of PIDs. This list is given if the number of instances is below/above the defined minimum/maximum threshold. This list is sorted in ascending order."
	::= { uxsA2StatusProcEntry 19 }

uxsA2StatusProcChildMinValue OBJECT-TYPE
	SYNTAX INTEGER
	ACCESS read-only
	STATUS mandatory
	DESCRIPTION "&<caiUxsA2.1062>The number of children of that process(es) which have currently the lowest number of children of all processes monitored by the process watcher."
	::= { uxsA2StatusProcEntry 20 }

uxsA2StatusProcChildMaxValue OBJECT-TYPE
	SYNTAX INTEGER
	ACCESS read-only
	STATUS mandatory
	DESCRIPTION "&<caiUxsA2.1063>The number of children of that process(es) which have currently the highest number of children of all processes monitored by the process watcher."
	::= { uxsA2StatusProcEntry 21 }

uxsA2StatusProcChildMin OBJECT-TYPE
	SYNTAX INTEGER
	ACCESS read-write
	STATUS mandatory
	DESCRIPTION "&<caiUxsA2.1064>Current minimum threshold for the number of children monitoring of the process watcher. This value represents a declining threshold and must be equal to or greater than 0, but cannot be greater than the maximum threshold. A value of -1 disables the evaluation of this threshold."
	DEFVAL { -2 }
	::= { uxsA2StatusProcEntry 22 }

uxsA2StatusProcChildMax OBJECT-TYPE
	SYNTAX INTEGER
	ACCESS read-write
	STATUS mandatory
	DESCRIPTION "&<caiUxsA2.1065>Current maximum threshold for the number of children monitoring of the process watcher. This value represents a rising threshold and must be equal to or greater than 0, but cannot be less than the minimum threshold. A value of -1 disables the evaluation of this threshold."
	DEFVAL { -2 }
	::= { uxsA2StatusProcEntry 23 }

uxsA2StatusProcChildMonitor OBJECT-TYPE
	SYNTAX INTEGER {
		do-not-monitor(1),
		down-warning(2),
		down-critical(3)
	}
	ACCESS read-write
	STATUS mandatory
	DESCRIPTION "&<caiUxsA2.1066>Current monitor level for the number of children monitoring of the process watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusProcEntry 24 }

uxsA2StatusProcChildStatus OBJECT-TYPE
	SYNTAX INTEGER {
		unknown(1),
		up(2),
		down-warning(3),
		down-critical(4)
	}
	ACCESS read-only
	STATUS mandatory
	DESCRIPTION "&<caiUxsA2.1067>Current status for the number of children monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusProcEntry 25 }

uxsA2StatusProcChildIds OBJECT-TYPE
	SYNTAX DisplayString
	ACCESS read-only
	STATUS mandatory
	DESCRIPTION "&<caiUxsA2.1068>List of tuples PID:number. This list is given if the number of instances is below/above the defined minimum/maximum threshold. The sort order and length of this list is depending on Evaluation Policy."
	::= { uxsA2StatusProcEntry 26 }

uxsA2StatusProcThreadMinValue OBJECT-TYPE
	SYNTAX INTEGER
	ACCESS read-only
	STATUS mandatory
	DESCRIPTION "&<caiUxsA2.1069>The number of threads of that process(es) which have currently the lowest number of threads of all processes monitored by the process watcher."
	::= { uxsA2StatusProcEntry 27 }

uxsA2StatusProcThreadMaxValue OBJECT-TYPE
	SYNTAX INTEGER
	ACCESS read-only
	STATUS mandatory
	DESCRIPTION "&<caiUxsA2.1070>The number of threads of that process(es) which have currently the highest number of threads of all processes monitored by the process watcher."
	::= { uxsA2StatusProcEntry 28 }

uxsA2StatusProcThreadMin OBJECT-TYPE
	SYNTAX INTEGER
	ACCESS read-write
	STATUS mandatory
	DESCRIPTION "&<caiUxsA2.1071>Current minimum threshold for the number of threads monitoring of the process watcher. This value represents a declining threshold and must be equal to or greater than 0, but cannot be greater than the maximum threshold. A value of -1 disables the evaluation of this threshold."
	DEFVAL { -2 }
	::= { uxsA2StatusProcEntry 29 }

uxsA2StatusProcThreadMax OBJECT-TYPE
	SYNTAX INTEGER
	ACCESS read-write
	STATUS mandatory
	DESCRIPTION "&<caiUxsA2.1072>Current maximum threshold for the number of threads monitoring of the process watcher. This value represents a rising threshold and must be equal to or greater than 0, but cannot be less than the minimum threshold. A value of -1 disables the evaluation of this threshold."
	DEFVAL { -2 }
	::= { uxsA2StatusProcEntry 30 }

uxsA2StatusProcThreadMonitor OBJECT-TYPE
	SYNTAX INTEGER {
		do-not-monitor(1),
		down-warning(2),
		down-critical(3)
	}
	ACCESS read-write
	STATUS mandatory
	DESCRIPTION "&<caiUxsA2.1073>Current monitor level for the number of threads monitoring of the process watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusProcEntry 31 }

uxsA2StatusProcThreadStatus OBJECT-TYPE
	SYNTAX INTEGER {
		unknown(1),
		up(2),
		down-warning(3),
		down-critical(4)
	}
	ACCESS read-only
	STATUS mandatory
	DESCRIPTION "&<caiUxsA2.1074>Current status for the number of threads monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusProcEntry 32 }

uxsA2StatusProcThreadIds OBJECT-TYPE
	SYNTAX DisplayString
	ACCESS read-only
	STATUS mandatory
	DESCRIPTION "&<caiUxsA2.1075>List of tuples PID:number. This list is given if the number of instances is below/above the defined minimum/maximum threshold. The sort order and length of this list is depending on Evaluation Policy."
	::= { uxsA2StatusProcEntry 33 }

uxsA2StatusProcSizeMinValue OBJECT-TYPE
	SYNTAX INTEGER
	ACCESS read-only
	STATUS mandatory
	DESCRIPTION "&<caiUxsA2.1076>The size of that process(es) in Kilobytes which have currently the smallest size of all processes monitored by the process watcher."
	::= { uxsA2StatusProcEntry 34 }

uxsA2StatusProcSizeMaxValue OBJECT-TYPE
	SYNTAX INTEGER
	ACCESS read-only
	STATUS mandatory
	DESCRIPTION "&<caiUxsA2.1077>The size of that process(es) in Kilobytes which have currently the largest size of all processes monitored by the process watcher."
	::= { uxsA2StatusProcEntry 35 }

uxsA2StatusProcSizeMin OBJECT-TYPE
	SYNTAX INTEGER
	ACCESS read-write
	STATUS mandatory
	DESCRIPTION "&<caiUxsA2.1078>Current minimum threshold, in kilobytes, for the size monitoring of the process watcher. This value represents a declining threshold and must be equal to or greater than 0, but cannot be greater than the maximum threshold. A value of -1 disables the evaluation of this threshold."
	DEFVAL { -2 }
	::= { uxsA2StatusProcEntry 36 }

uxsA2StatusProcSizeMax OBJECT-TYPE
	SYNTAX INTEGER
	ACCESS read-write
	STATUS mandatory
	DESCRIPTION "&<caiUxsA2.1079>Current maximum threshold, in kilobytes, for the size monitoring of the process watcher. This value represents a rising threshold and must be equal to or greater than 0, but cannot be less than the minimum threshold. A value of -1 disables the evaluation of this threshold."
	DEFVAL { -2 }
	::= { uxsA2StatusProcEntry 37 }

uxsA2StatusProcSizeMonitor OBJECT-TYPE
	SYNTAX INTEGER {
		do-not-monitor(1),
		down-warning(2),
		down-critical(3)
	}
	ACCESS read-write
	STATUS mandatory
	DESCRIPTION "&<caiUxsA2.1080>Current monitor level for the size monitoring of the process watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusProcEntry 38 }

uxsA2StatusProcSizeStatus OBJECT-TYPE
	SYNTAX INTEGER {
		unknown(1),
		up(2),
		down-warning(3),
		down-critical(4)
	}
	ACCESS read-only
	STATUS mandatory
	DESCRIPTION "&<caiUxsA2.1081>Current status for the size monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusProcEntry 39 }

uxsA2StatusProcSizeIds OBJECT-TYPE
	SYNTAX DisplayString
	ACCESS read-only
	STATUS mandatory
	DESCRIPTION "&<caiUxsA2.1082>List of tuples PID:value of processes whose size is above/below the defined minimum/maximum threshold. The sort order and length of this list is depending on Evaluation Policy."
	::= { uxsA2StatusProcEntry 40 }

uxsA2StatusProcCpuUtilInterval OBJECT-TYPE
	SYNTAX DisplayString
	ACCESS read-only
	STATUS mandatory
	DESCRIPTION "&<caiUxsA2.1083>The value of the current poll interval in seconds."
	::= { uxsA2StatusProcEntry 41 }

uxsA2StatusProcCpuUtilMinValue OBJECT-TYPE
	SYNTAX DisplayString
	ACCESS read-only
	STATUS mandatory
	DESCRIPTION "&<caiUxsA2.1084>The CPU Utilization of that process(es) in Seconds per poll interval which have currently the lowest amount of CPU Utilization of all processes monitored by the process watcher."
	DEFVAL { "0" }
	::= { uxsA2StatusProcEntry 42 }

uxsA2StatusProcCpuUtilMaxValue OBJECT-TYPE
	SYNTAX DisplayString
	ACCESS read-only
	STATUS mandatory
	DESCRIPTION "&<caiUxsA2.1085>The CPU Utilization of that process(es) in Seconds per poll interval which have currently the highest amount of CPU Utilization of all processes monitored by the process watcher."
	DEFVAL { "0" }
	::= { uxsA2StatusProcEntry 43 }

uxsA2StatusProcCpuUtilWarnMin OBJECT-TYPE
	SYNTAX DisplayString
	ACCESS read-write
	STATUS mandatory
	DESCRIPTION "&<caiUxsA2.1086>Current warning minimum threshold, in seconds, for the per poll CPU usage monitoring of the process watcher. This value represents a declining threshold and must be equal to or greater than 0.0, less than or equal to the total value (maximum capacity) of the monitored resource as specified in uxsA2StatusProcCpuUtilInterval, equal to or greater than the critical minimum threshold, but cannot be greater than the warning maximum threshold. A value of -1 disables the evaluation of this threshold. The threshold can be specified as either an absolute value (n) or a percentage (n%). The value of uxsA2StatusProcCpuUtilInterval will be the reference value for n% notations."
	DEFVAL { "-2" }
	::= { uxsA2StatusProcEntry 44 }

uxsA2StatusProcCpuUtilWarnMax OBJECT-TYPE
	SYNTAX DisplayString
	ACCESS read-write
	STATUS mandatory
	DESCRIPTION "&<caiUxsA2.1087>Current warning maximum threshold, in seconds, for the per poll CPU usage monitoring of the process watcher. This value represents a rising threshold and must be equal to or greater than 0.0, less than or equal to the total value (maximum capacity) of the monitored resource as specified in uxsA2StatusProcCpuUtilInterval, equal to or greater than the warning minimum threshold, but cannot be greater than the critical maximum threshold. A value of -1 disables the evaluation of this threshold. The threshold can be specified as either an absolute value (n) or a percentage (n%). The value of uxsA2StatusProcCpuUtilInterval will be the reference value for n% notations."
	DEFVAL { "-2" }
	::= { uxsA2StatusProcEntry 45 }

uxsA2StatusProcCpuUtilCritMin OBJECT-TYPE
	SYNTAX DisplayString
	ACCESS read-write
	STATUS mandatory
	DESCRIPTION "&<caiUxsA2.1088>Current critical minimum threshold, in seconds, for the per poll CPU usage monitoring of the process watcher. This value represents a declining threshold and must be equal to or greater than 0.0, less than or equal to the total value (maximum capacity) of the monitored resource as specified in uxsA2StatusProcCpuUtilInterval, but cannot be greater than the warning minimum threshold. A value of -1 disables the evaluation of this threshold. The threshold can be specified as either an absolute value (n) or a percentage (n%). The value of uxsA2StatusProcCpuUtilInterval will be the reference value for n% notations."
	DEFVAL { "-2" }
	::= { uxsA2StatusProcEntry 46 }

uxsA2StatusProcCpuUtilCritMax OBJECT-TYPE
	SYNTAX DisplayString
	ACCESS read-write
	STATUS mandatory
	DESCRIPTION "&<caiUxsA2.1089>Current critical maximum threshold, in seconds, for the per poll CPU usage monitoring of the process watcher. This value represents a rising threshold and must be equal to or greater than 0.0, less than or equal to the total value (maximum capacity) of the monitored resource as specified in uxsA2StatusProcCpuUtilInterval, but cannot be less than the warning maximum threshold. A value of -1 disables the evaluation of this threshold. The threshold can be specified as either an absolute value (n) or a percentage (n%). The value of uxsA2StatusProcCpuUtilInterval will be the reference value for n% notations."
	DEFVAL { "-2" }
	::= { uxsA2StatusProcEntry 47 }

uxsA2StatusProcCpuUtilMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.1090>Current monitor level for the per poll CPU usage monitoring of the process watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2StatusProcEntry 48 }

uxsA2StatusProcCpuUtilStatus OBJECT-TYPE
	SYNTAX INTEGER {
		unknown(1),
		up(2),
		down-warning(3),
		down-critical(4)
	}
	ACCESS read-only
	STATUS mandatory
	DESCRIPTION "&<caiUxsA2.1091>Current status for the per poll CPU usage monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusProcEntry 49 }

uxsA2StatusProcCpuUtilIds OBJECT-TYPE
	SYNTAX DisplayString
	ACCESS read-only
	STATUS mandatory
	DESCRIPTION "&<caiUxsA2.1092>List of tuples PID:value whose amount of CPU Utilization per poll interval is below/above the defined minimum/maximum threshold. The sort order and length of this list is depending on Evaluation Policy."
	::= { uxsA2StatusProcEntry 50 }

uxsA2StatusProcCpuUtilLongtermInterval OBJECT-TYPE
	SYNTAX DisplayString
	ACCESS read-write
	STATUS mandatory
	DESCRIPTION "&<caiUxsA2.1093>Time, in seconds, defining the total value to use as base for the calculation of the cpu value. This means, the cpu usage of a process, in seconds, refers to this interval. Valid range: Greater 0 or '-1'. If set to '-1', the cpu value is calculated as the cpu usage, in seconds, used up to now since the start of the agent or the creation of the watcher. If this interval is set to a value greater than the current poll interval and this time is not elapsed for the first time, the CPU value is extrapolated. If this interval is set to a value smaller than the current poll interval, the CPU value is calculated as the appropriate fraction of the value for the last poll interval. If this interval is set to a value greater than the current poll interval and this time is already elapsed, the CPU value is calculated as the sliding sum, i.e. the sum of the value for the current poll interval and the value calculated at the last poll, weighted according to it's fraction of this interval. If the interval is set to '-1', any overloading (%) used for the thresholds will be ignored."
	::= { uxsA2StatusProcEntry 51 }

uxsA2StatusProcCpuUtilLongtermMinValue OBJECT-TYPE
	SYNTAX DisplayString
	ACCESS read-only
	STATUS mandatory
	DESCRIPTION "&<caiUxsA2.1094>The longterm CPU Utilization of that process(es) in Seconds per longterm interval which have currently the lowest amount of Longterm CPU Utilization of all processes monitored by the process watcher."
	DEFVAL { "0" }
	::= { uxsA2StatusProcEntry 52 }

uxsA2StatusProcCpuUtilLongtermMaxValue OBJECT-TYPE
	SYNTAX DisplayString
	ACCESS read-only
	STATUS mandatory
	DESCRIPTION "&<caiUxsA2.1095>The longterm CPU Utilization of that process(es) in Seconds per longterm interval which have currently the highest amount of Longterm CPU Utilization of all processes monitored by the process watcher."
	DEFVAL { "0" }
	::= { uxsA2StatusProcEntry 53 }

uxsA2StatusProcCpuUtilLongtermWarnMin OBJECT-TYPE
	SYNTAX DisplayString
	ACCESS read-write
	STATUS mandatory
	DESCRIPTION "&<caiUxsA2.1096>Current warning minimum threshold, in seconds, for the long-term CPU usage monitoring of the process watcher. This value represents a declining threshold and must be equal to or greater than 0.0, less than or equal to the total value (maximum capacity) of the monitored resource as specified in uxsA2StatusProcCpuUtilLongtermInterval, equal to or greater than the critical minimum threshold, but cannot be greater than the warning maximum threshold. A value of -1 disables the evaluation of this threshold. The threshold can be specified as either an absolute value (n) or a percentage (n%). The value of uxsA2StatusProcCpuUtilLongtermInterval will be the reference value for n% notations."
	DEFVAL { "-2" }
	::= { uxsA2StatusProcEntry 54 }

uxsA2StatusProcCpuUtilLongtermWarnMax OBJECT-TYPE
	SYNTAX DisplayString
	ACCESS read-write
	STATUS mandatory
	DESCRIPTION "&<caiUxsA2.1097>Current warning maximum threshold, in seconds, for the long-term CPU usage monitoring of the process watcher. This value represents a rising threshold and must be equal to or greater than 0.0, less than or equal to the total value (maximum capacity) of the monitored resource as specified in uxsA2StatusProcCpuUtilLongtermInterval, equal to or greater than the warning minimum threshold, but cannot be greater than the critical maximum threshold. A value of -1 disables the evaluation of this threshold. The threshold can be specified as either an absolute value (n) or a percentage (n%). The value of uxsA2StatusProcCpuUtilLongtermInterval will be the reference value for n% notations."
	DEFVAL { "-2" }
	::= { uxsA2StatusProcEntry 55 }

uxsA2StatusProcCpuUtilLongtermCritMin OBJECT-TYPE
	SYNTAX DisplayString
	ACCESS read-write
	STATUS mandatory
	DESCRIPTION "&<caiUxsA2.1098>Current critical minimum threshold, in seconds, for the long-term CPU usage monitoring of the process watcher. This value represents a declining threshold and must be equal to or greater than 0.0, less than or equal to the total value (maximum capacity) of the monitored resource as specified in uxsA2StatusProcCpuUtilLongtermInterval, but cannot be greater than the warning minimum threshold. A value of -1 disables the evaluation of this threshold. The threshold can be specified as either an absolute value (n) or a percentage (n%). The value of uxsA2StatusProcCpuUtilLongtermInterval will be the reference value for n% notations."
	DEFVAL { "-2" }
	::= { uxsA2StatusProcEntry 56 }

uxsA2StatusProcCpuUtilLongtermCritMax OBJECT-TYPE
	SYNTAX DisplayString
	ACCESS read-write
	STATUS mandatory
	DESCRIPTION "&<caiUxsA2.1099>Current critical maximum threshold, in seconds, for the long-term CPU usage monitoring of the process watcher. This value represents a rising threshold and must be equal to or greater than 0.0, less than or equal to the total value (maximum capacity) of the monitored resource as specified in uxsA2StatusProcCpuUtilLongtermInterval, but cannot be less than the warning maximum threshold. A value of -1 disables the evaluation of this threshold. The threshold can be specified as either an absolute value (n) or a percentage (n%). The value of uxsA2StatusProcCpuUtilLongtermInterval will be the reference value for n% notations."
	DEFVAL { "-2" }
	::= { uxsA2StatusProcEntry 57 }

uxsA2StatusProcCpuUtilLongtermMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.1100>Current monitor level for the long-term CPU usage monitoring of the process watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2StatusProcEntry 58 }

uxsA2StatusProcCpuUtilLongtermStatus OBJECT-TYPE
	SYNTAX INTEGER {
		unknown(1),
		up(2),
		down-warning(3),
		down-critical(4)
	}
	ACCESS read-only
	STATUS mandatory
	DESCRIPTION "&<caiUxsA2.1101>Current status for the long-term CPU usage monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusProcEntry 59 }

uxsA2StatusProcCpuUtilLongtermIds OBJECT-TYPE
	SYNTAX DisplayString
	ACCESS read-only
	STATUS mandatory
	DESCRIPTION "&<caiUxsA2.1102>List of tuples PID:value whose amount of CPU Utilization per longterm interval is below/above the defined minimum/maximum threshold. The sort order and length of this list is depending on Evaluation Policy."
	::= { uxsA2StatusProcEntry 60 }

uxsA2StatusProcRestartValue OBJECT-TYPE
	SYNTAX INTEGER {
		not-restarted(1),
		restarted(2),
		not-applicable(3)
	}
	ACCESS read-only
	STATUS mandatory
	DESCRIPTION "&<caiUxsA2.1103>The current value of the modification monitoring of the process watcher (not-restarted(1), restarted(2), not-applicable(3)). Always not-applicable if the process watcher is a 1:m watcher."
	::= { uxsA2StatusProcEntry 61 }

uxsA2StatusProcRestart OBJECT-TYPE
	SYNTAX INTEGER {
		should-be-restarted(1),
		should-not-be-restarted(2),
		reset(3)
	}
	ACCESS read-write
	STATUS mandatory
	DESCRIPTION "&<caiUxsA2.1104>The current monitor condition for the restart policy monitoring of the process watcher."
	DEFVAL { 0 }
	::= { uxsA2StatusProcEntry 62 }

uxsA2StatusProcRestartMonitor OBJECT-TYPE
	SYNTAX INTEGER {
		do-not-monitor(1),
		down-warning(2),
		down-critical(3)
	}
	ACCESS read-write
	STATUS mandatory
	DESCRIPTION "&<caiUxsA2.1105>Current monitor level for the restart policy monitoring of the process watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusProcEntry 63 }

uxsA2StatusProcRestartStatus OBJECT-TYPE
	SYNTAX INTEGER {
		unknown(1),
		up(2),
		down-warning(3),
		down-critical(4)
	}
	ACCESS read-only
	STATUS mandatory
	DESCRIPTION "&<caiUxsA2.1106>Current status for the restart policy monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusProcEntry 64 }

uxsA2StatusProcCallBackRef OBJECT-TYPE
	SYNTAX DisplayString
	ACCESS read-only
	STATUS mandatory
	DESCRIPTION "&<caiUxsA2.1107>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusProcEntry 65 }

uxsA2StatusProcButton OBJECT-TYPE
	SYNTAX INTEGER {
		none(1),
		remove(2)
	}
	ACCESS read-write
	STATUS mandatory
	DESCRIPTION "&<caiUxsA2.1108>This attribute is used to remove the process watcher. If set to 2 (remove), the agent removes the watcher from the table. This attribute cannot be set to 1 (none)."
	DEFVAL { 1 }
	::= { uxsA2StatusProcEntry 66 }

--
-- The StatusPrn Group
--

uxsA2StatusPrnCount OBJECT-TYPE
	SYNTAX INTEGER
	ACCESS read-only
	STATUS mandatory
	DESCRIPTION "&<caiUxsA2.1109>Number of entries in the print queue status table."
	::= { uxsA2StatusPrnGroup 1 }

uxsA2StatusPrnTable OBJECT-TYPE
	SYNTAX SEQUENCE OF UxsA2StatusPrnEntry
	ACCESS not-accessible
	STATUS mandatory
	DESCRIPTION "&<caiUxsA2.1110>The print queue status table containing details about the currently configured print queue watchers."
	::= { uxsA2StatusPrnGroup 2 }

uxsA2StatusPrnEntry OBJECT-TYPE
	SYNTAX UxsA2StatusPrnEntry
	ACCESS not-accessible
	STATUS mandatory
	DESCRIPTION "&<caiUxsA2.1111>Entry in the print queue status table."
	INDEX {
		uxsA2StatusPrnName
	}
	::= { uxsA2StatusPrnTable 1 }

UxsA2StatusPrnEntry ::= SEQUENCE {
	uxsA2StatusPrnName DisplayString,
	uxsA2StatusPrnDescription DisplayString,
	uxsA2StatusPrnAutoWatcherName DisplayString,
	uxsA2StatusPrnAggLagValue INTEGER,
	uxsA2StatusPrnAggLag INTEGER,
	uxsA2StatusPrnAggStatus INTEGER,
	uxsA2StatusPrnQueueUtilValue INTEGER,
	uxsA2StatusPrnQueueUtilWarn INTEGER,
	uxsA2StatusPrnQueueUtilCrit INTEGER,
	uxsA2StatusPrnQueueUtilMonitor INTEGER,
	uxsA2StatusPrnQueueUtilStatus INTEGER,
	uxsA2StatusPrnReason DisplayString,
	uxsA2StatusPrnPrinterValue INTEGER,
	uxsA2StatusPrnPrinterMonitor INTEGER,
	uxsA2StatusPrnPrinterStatus INTEGER,
	uxsA2StatusPrnLossAction INTEGER,
	uxsA2StatusPrnLossStatus INTEGER,
	uxsA2StatusPrnCallBackRef DisplayString,
	uxsA2StatusPrnButton INTEGER
}

uxsA2StatusPrnName OBJECT-TYPE
	SYNTAX DisplayString
	ACCESS read-only
	STATUS mandatory
	DESCRIPTION "&<caiUxsA2.1112>Name of the print queue."
	::= { uxsA2StatusPrnEntry 1 }

uxsA2StatusPrnDescription OBJECT-TYPE
	SYNTAX DisplayString
	ACCESS read-write
	STATUS mandatory
	DESCRIPTION "&<caiUxsA2.1113>Current description for the print queue watcher."
	::= { uxsA2StatusPrnEntry 2 }

uxsA2StatusPrnAutoWatcherName OBJECT-TYPE
	SYNTAX DisplayString
	ACCESS read-only
	STATUS mandatory
	DESCRIPTION "&<caiUxsA2.1114>Name of the print queue auto watcher which automatically created this watcher. This attribute is left blank if the watcher was added manually."
	::= { uxsA2StatusPrnEntry 3 }

uxsA2StatusPrnAggLagValue OBJECT-TYPE
	SYNTAX INTEGER
	ACCESS read-only
	STATUS mandatory
	DESCRIPTION "&<caiUxsA2.1115>Current aggregate lag value of the print queue watcher. Indicates the consecutive number of times at which any status was not in the ok state. The aggregate status changes from ok as soon as the aggregate lag value reaches the configured value."
	::= { uxsA2StatusPrnEntry 4 }

uxsA2StatusPrnAggLag OBJECT-TYPE
	SYNTAX INTEGER
	ACCESS read-write
	STATUS mandatory
	DESCRIPTION "&<caiUxsA2.1116>Current aggregate lag setting for the print queue watcher. Specifies the consecutive number of times at which any status is not in the ok state, before the aggregate status changes. This value must be greater than 0."
	::= { uxsA2StatusPrnEntry 5 }

uxsA2StatusPrnAggStatus OBJECT-TYPE
	SYNTAX INTEGER {
		unknown(1),
		ok(2),
		warning(3),
		critical(4),
		passive(5)
	}
	ACCESS read-only
	STATUS mandatory
	DESCRIPTION "&<caiUxsA2.1117>Current aggregate status of the print queue watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { uxsA2StatusPrnEntry 6 }

uxsA2StatusPrnQueueUtilValue OBJECT-TYPE
	SYNTAX INTEGER
	ACCESS read-only
	STATUS mandatory
	DESCRIPTION "&<caiUxsA2.1118>Current value for the print queue utilization monitoring of the print queue watcher."
	::= { uxsA2StatusPrnEntry 7 }

uxsA2StatusPrnQueueUtilWarn OBJECT-TYPE
	SYNTAX INTEGER
	ACCESS read-write
	STATUS mandatory
	DESCRIPTION "&<caiUxsA2.1119>Current warning threshold for the print queue utilization monitoring of the print queue watcher. This value represents a rising threshold and must be greater than 0, but cannot be greater than the critical threshold."
	::= { uxsA2StatusPrnEntry 8 }

uxsA2StatusPrnQueueUtilCrit OBJECT-TYPE
	SYNTAX INTEGER
	ACCESS read-write
	STATUS mandatory
	DESCRIPTION "&<caiUxsA2.1120>Current critical threshold for the print queue utilization monitoring of the print queue watcher. This value represents a rising threshold and must be greater than 0, but cannot be less than the warning threshold."
	::= { uxsA2StatusPrnEntry 9 }

uxsA2StatusPrnQueueUtilMonitor OBJECT-TYPE
	SYNTAX INTEGER {
		do-not-monitor(1),
		warning-only(2),
		critical-only(3),
		both(4)
	}
	ACCESS read-write
	STATUS mandatory
	DESCRIPTION "&<caiUxsA2.1121>Current monitor level for the print queue utilization monitoring of the print queue watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusPrnEntry 10 }

uxsA2StatusPrnQueueUtilStatus OBJECT-TYPE
	SYNTAX INTEGER {
		unknown(1),
		ok(2),
		warning(3),
		critical(4)
	}
	ACCESS read-only
	STATUS mandatory
	DESCRIPTION "&<caiUxsA2.1122>Current status for the print queue utilization monitoring of the print queue watcher: 1 (unknown) - An error occurred during data collection, 2 (ok) - The resource is operating within the defined limits or status evaluation is turned off and/or polling is disabled, 3 (warning) - The resource has breached the warning threshold, 4 (critical) - The resource has breached the critical threshold."
	::= { uxsA2StatusPrnEntry 11 }

uxsA2StatusPrnReason OBJECT-TYPE
	SYNTAX DisplayString
	ACCESS read-only
	STATUS mandatory
	DESCRIPTION "&<caiUxsA2.1123>If the printer status is offline the reason for the problem is displayed. This field may be empty if no reason is available."
	::= { uxsA2StatusPrnEntry 12 }

uxsA2StatusPrnPrinterValue OBJECT-TYPE
	SYNTAX INTEGER {
		online(1),
		offline(2)
	}
	ACCESS read-only
	STATUS mandatory
	DESCRIPTION "&<caiUxsA2.1124>The current status of the printer. Possible values are online and offline (an error occured)."
	::= { uxsA2StatusPrnEntry 13 }

uxsA2StatusPrnPrinterMonitor OBJECT-TYPE
	SYNTAX INTEGER {
		do-not-monitor(1),
		down-warning(2),
		down-critical(3)
	}
	ACCESS read-write
	STATUS mandatory
	DESCRIPTION "&<caiUxsA2.1125>Current monitor level for the printer status monitoring of the print queue watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusPrnEntry 14 }

uxsA2StatusPrnPrinterStatus OBJECT-TYPE
	SYNTAX INTEGER {
		unknown(1),
		up(2),
		down-warning(3),
		down-critical(4)
	}
	ACCESS read-only
	STATUS mandatory
	DESCRIPTION "&<caiUxsA2.1126>Current status for the printer status monitoring of the print queue watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusPrnEntry 15 }

uxsA2StatusPrnLossAction OBJECT-TYPE
	SYNTAX INTEGER {
		remove(1),
		up(2),
		down-warning(3),
		down-critical(4)
	}
	ACCESS read-write
	STATUS mandatory
	DESCRIPTION "&<caiUxsA2.1127>Current loss action for the print queue watcher. Specifies the action to take if the monitored print queue is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusPrnEntry 16 }

uxsA2StatusPrnLossStatus OBJECT-TYPE
	SYNTAX INTEGER {
		unknown(1),
		up(2),
		down-warning(3),
		down-critical(4)
	}
	ACCESS read-only
	STATUS mandatory
	DESCRIPTION "&<caiUxsA2.1128>Current loss status of the print queue watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusPrnEntry 17 }

uxsA2StatusPrnCallBackRef OBJECT-TYPE
	SYNTAX DisplayString
	ACCESS read-only
	STATUS mandatory
	DESCRIPTION "&<caiUxsA2.1129>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusPrnEntry 18 }

uxsA2StatusPrnButton OBJECT-TYPE
	SYNTAX INTEGER {
		none(1),
		remove(2)
	}
	ACCESS read-write
	STATUS mandatory
	DESCRIPTION "&<caiUxsA2.1130>This attribute is used to remove the print queue watcher. If set to 2 (remove), the agent removes the watcher from the table. This attribute cannot be set to 1 (none)."
	DEFVAL { 1 }
	::= { uxsA2StatusPrnEntry 19 }

--
-- The StatusNet Group
--

uxsA2StatusNetTotalAggLagValue OBJECT-TYPE
	SYNTAX INTEGER
	ACCESS read-only
	STATUS mandatory
	DESCRIPTION "&<caiUxsA2.1131>Current aggregate lag value of the network interface watcher. Indicates the consecutive number of times at which any status was not in the ok state. The aggregate status changes from ok as soon as the aggregate lag value reaches the configured value."
	::= { uxsA2StatusNetGroup 1 }

uxsA2StatusNetTotalAggLag OBJECT-TYPE
	SYNTAX INTEGER
	ACCESS read-write
	STATUS mandatory
	DESCRIPTION "&<caiUxsA2.1132>Current aggregate lag setting for the network interface watcher. Specifies the consecutive number of times at which any status is not in the ok state, before the aggregate status changes. This value must be greater than 0."
	DEFVAL { 10 }
	::= { uxsA2StatusNetGroup 2 }

uxsA2StatusNetTotalAggStatus OBJECT-TYPE
	SYNTAX INTEGER {
		unknown(1),
		ok(2),
		warning(3),
		critical(4),
		passive(5)
	}
	ACCESS read-only
	STATUS mandatory
	DESCRIPTION "&<caiUxsA2.1133>Current aggregate status of the network interface watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { uxsA2StatusNetGroup 3 }

uxsA2StatusNetTotalInPktValue OBJECT-TYPE
	SYNTAX INTEGER
	ACCESS read-only
	STATUS mandatory
	DESCRIPTION "&<caiUxsA2.1134>Current value, in pkts/s, for the total input packets monitoring of the network interface watcher."
	::= { uxsA2StatusNetGroup 4 }

uxsA2StatusNetTotalInPktWarn OBJECT-TYPE
	SYNTAX INTEGER
	ACCESS read-write
	STATUS mandatory
	DESCRIPTION "&<caiUxsA2.1135>Current warning threshold, in pkts/s, for the total input packets monitoring of the network interface watcher. This value represents a rising threshold and must be greater than 0, but cannot be greater than the critical threshold."
	DEFVAL { 8000 }
	::= { uxsA2StatusNetGroup 5 }

uxsA2StatusNetTotalInPktCrit OBJECT-TYPE
	SYNTAX INTEGER
	ACCESS read-write
	STATUS mandatory
	DESCRIPTION "&<caiUxsA2.1136>Current critical threshold, in pkts/s, for the total input packets monitoring of the network interface watcher. This value represents a rising threshold and must be greater than 0, but cannot be less than the warning threshold."
	DEFVAL { 15000 }
	::= { uxsA2StatusNetGroup 6 }

uxsA2StatusNetTotalInPktMonitor OBJECT-TYPE
	SYNTAX INTEGER {
		do-not-monitor(1),
		warning-only(2),
		critical-only(3),
		both(4)
	}
	ACCESS read-write
	STATUS mandatory
	DESCRIPTION "&<caiUxsA2.1137>Current monitor level for the total input packets monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { uxsA2StatusNetGroup 7 }

uxsA2StatusNetTotalInPktStatus OBJECT-TYPE
	SYNTAX INTEGER {
		unknown(1),
		ok(2),
		warning(3),
		critical(4)
	}
	ACCESS read-only
	STATUS mandatory
	DESCRIPTION "&<caiUxsA2.1138>Current status for the total input packets monitoring of the network interface watcher: 1 (unknown) - An error occurred during data collection, 2 (ok) - The resource is operating within the defined limits or status evaluation is turned off and/or polling is disabled, 3 (warning) - The resource has breached the warning threshold, 4 (critical) - The resource has breached the critical threshold."
	::= { uxsA2StatusNetGroup 8 }

uxsA2StatusNetTotalRecBytesValue OBJECT-TYPE
	SYNTAX DisplayString
	ACCESS read-only
	STATUS mandatory
	DESCRIPTION "&<caiUxsA2.1139>Current value, in bytes/s, for the total received bytes monitoring of the network interface watcher."
	DEFVAL { "0" }
	::= { uxsA2StatusNetGroup 9 }

uxsA2StatusNetTotalRecBytesWarnMin OBJECT-TYPE
	SYNTAX DisplayString
	ACCESS read-write
	STATUS mandatory
	DESCRIPTION "&<caiUxsA2.1140>Current warning minimum threshold, in bytes/s, for the total received bytes monitoring of the network interface watcher. This value represents a declining threshold and must be equal to or greater than 0.0, equal to or greater than the critical minimum threshold, but cannot be greater than the warning maximum threshold. A value of -1 disables the evaluation of this threshold."
	DEFVAL { "-1" }
	::= { uxsA2StatusNetGroup 10 }

uxsA2StatusNetTotalRecBytesWarnMax OBJECT-TYPE
	SYNTAX DisplayString
	ACCESS read-write
	STATUS mandatory
	DESCRIPTION "&<caiUxsA2.1141>Current warning maximum threshold, in bytes/s, for the total received bytes monitoring of the network interface watcher. This value represents a rising threshold and must be equal to or greater than 0.0, equal to or greater than the warning minimum threshold, but cannot be greater than the critical maximum threshold. A value of -1 disables the evaluation of this threshold."
	DEFVAL { "2000000.0" }
	::= { uxsA2StatusNetGroup 11 }

uxsA2StatusNetTotalRecBytesCritMin OBJECT-TYPE
	SYNTAX DisplayString
	ACCESS read-write
	STATUS mandatory
	DESCRIPTION "&<caiUxsA2.1142>Current critical minimum threshold, in bytes/s, for the total received bytes monitoring of the network interface watcher. This value represents a declining threshold and must be equal to or greater than 0.0, but cannot be greater than the warning minimum threshold. A value of -1 disables the evaluation of this threshold."
	DEFVAL { "-1" }
	::= { uxsA2StatusNetGroup 12 }

uxsA2StatusNetTotalRecBytesCritMax OBJECT-TYPE
	SYNTAX DisplayString
	ACCESS read-write
	STATUS mandatory
	DESCRIPTION "&<caiUxsA2.1143>Current critical maximum threshold, in bytes/s, for the total received bytes monitoring of the network interface watcher. This value represents a rising threshold and must be equal to or greater than 0.0, but cannot be less than the warning maximum threshold. A value of -1 disables the evaluation of this threshold."
	DEFVAL { "4000000.0" }
	::= { uxsA2StatusNetGroup 13 }

uxsA2StatusNetTotalRecBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.1144>Current monitor level for the total received bytes monitoring of the network interface watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 1 }
	::= { uxsA2StatusNetGroup 14 }

uxsA2StatusNetTotalRecBytesStatus OBJECT-TYPE
	SYNTAX INTEGER {
		unknown(1),
		up(2),
		down-warning(3),
		down-critical(4)
	}
	ACCESS read-only
	STATUS mandatory
	DESCRIPTION "&<caiUxsA2.1145>Current status for the total received bytes monitoring of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusNetGroup 15 }

uxsA2StatusNetTotalInErrValue OBJECT-TYPE
	SYNTAX INTEGER
	ACCESS read-only
	STATUS mandatory
	DESCRIPTION "&<caiUxsA2.1146>Current value, in number/poll, for the total input errors monitoring of the network interface watcher."
	::= { uxsA2StatusNetGroup 16 }

uxsA2StatusNetTotalInErrWarn OBJECT-TYPE
	SYNTAX INTEGER
	ACCESS read-write
	STATUS mandatory
	DESCRIPTION "&<caiUxsA2.1147>Current warning threshold, in number/poll, for the total input errors monitoring of the network interface watcher. This value represents a rising threshold and must be greater than 0, but cannot be greater than the critical threshold."
	DEFVAL { 5 }
	::= { uxsA2StatusNetGroup 17 }

uxsA2StatusNetTotalInErrCrit OBJECT-TYPE
	SYNTAX INTEGER
	ACCESS read-write
	STATUS mandatory
	DESCRIPTION "&<caiUxsA2.1148>Current critical threshold, in number/poll, for the total input errors monitoring of the network interface watcher. This value represents a rising threshold and must be greater than 0, but cannot be less than the warning threshold."
	DEFVAL { 10 }
	::= { uxsA2StatusNetGroup 18 }

uxsA2StatusNetTotalInErrMonitor OBJECT-TYPE
	SYNTAX INTEGER {
		do-not-monitor(1),
		warning-only(2),
		critical-only(3),
		both(4)
	}
	ACCESS read-write
	STATUS mandatory
	DESCRIPTION "&<caiUxsA2.1149>Current monitor level for the total input errors monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { uxsA2StatusNetGroup 19 }

uxsA2StatusNetTotalInErrStatus OBJECT-TYPE
	SYNTAX INTEGER {
		unknown(1),
		ok(2),
		warning(3),
		critical(4)
	}
	ACCESS read-only
	STATUS mandatory
	DESCRIPTION "&<caiUxsA2.1150>Current status for the total input errors monitoring of the network interface watcher: 1 (unknown) - An error occurred during data collection, 2 (ok) - The resource is operating within the defined limits or status evaluation is turned off and/or polling is disabled, 3 (warning) - The resource has breached the warning threshold, 4 (critical) - The resource has breached the critical threshold."
	::= { uxsA2StatusNetGroup 20 }

uxsA2StatusNetTotalOutPktValue OBJECT-TYPE
	SYNTAX INTEGER
	ACCESS read-only
	STATUS mandatory
	DESCRIPTION "&<caiUxsA2.1151>Current value, in pkts/s, for the total output packets monitoring of the network interface watcher."
	::= { uxsA2StatusNetGroup 21 }

uxsA2StatusNetTotalOutPktWarn OBJECT-TYPE
	SYNTAX INTEGER
	ACCESS read-write
	STATUS mandatory
	DESCRIPTION "&<caiUxsA2.1152>Current warning threshold, in pkts/s, for the total output packets monitoring of the network interface watcher. This value represents a rising threshold and must be greater than 0, but cannot be greater than the critical threshold."
	DEFVAL { 25000 }
	::= { uxsA2StatusNetGroup 22 }

uxsA2StatusNetTotalOutPktCrit OBJECT-TYPE
	SYNTAX INTEGER
	ACCESS read-write
	STATUS mandatory
	DESCRIPTION "&<caiUxsA2.1153>Current critical threshold, in pkts/s, for the total output packets monitoring of the network interface watcher. This value represents a rising threshold and must be greater than 0, but cannot be less than the warning threshold."
	DEFVAL { 50000 }
	::= { uxsA2StatusNetGroup 23 }

uxsA2StatusNetTotalOutPktMonitor OBJECT-TYPE
	SYNTAX INTEGER {
		do-not-monitor(1),
		warning-only(2),
		critical-only(3),
		both(4)
	}
	ACCESS read-write
	STATUS mandatory
	DESCRIPTION "&<caiUxsA2.1154>Current monitor level for the total output packets monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { uxsA2StatusNetGroup 24 }

uxsA2StatusNetTotalOutPktStatus OBJECT-TYPE
	SYNTAX INTEGER {
		unknown(1),
		ok(2),
		warning(3),
		critical(4)
	}
	ACCESS read-only
	STATUS mandatory
	DESCRIPTION "&<caiUxsA2.1155>Current status for the total output packets monitoring of the network interface watcher: 1 (unknown) - An error occurred during data collection, 2 (ok) - The resource is operating within the defined limits or status evaluation is turned off and/or polling is disabled, 3 (warning) - The resource has breached the warning threshold, 4 (critical) - The resource has breached the critical threshold."
	::= { uxsA2StatusNetGroup 25 }

uxsA2StatusNetTotalSentBytesValue OBJECT-TYPE
	SYNTAX DisplayString
	ACCESS read-only
	STATUS mandatory
	DESCRIPTION "&<caiUxsA2.1156>Current value, in bytes/s, for the total sent bytes monitoring of the network interface watcher."
	DEFVAL { "0" }
	::= { uxsA2StatusNetGroup 26 }

uxsA2StatusNetTotalSentBytesWarnMin OBJECT-TYPE
	SYNTAX DisplayString
	ACCESS read-write
	STATUS mandatory
	DESCRIPTION "&<caiUxsA2.1157>Current warning minimum threshold, in bytes/s, for the total sent bytes monitoring of the network interface watcher. This value represents a declining threshold and must be equal to or greater than 0.0, equal to or greater than the critical minimum threshold, but cannot be greater than the warning maximum threshold. A value of -1 disables the evaluation of this threshold."
	DEFVAL { "-1" }
	::= { uxsA2StatusNetGroup 27 }

uxsA2StatusNetTotalSentBytesWarnMax OBJECT-TYPE
	SYNTAX DisplayString
	ACCESS read-write
	STATUS mandatory
	DESCRIPTION "&<caiUxsA2.1158>Current warning maximum threshold, in bytes/s, for the total sent bytes monitoring of the network interface watcher. This value represents a rising threshold and must be equal to or greater than 0.0, equal to or greater than the warning minimum threshold, but cannot be greater than the critical maximum threshold. A value of -1 disables the evaluation of this threshold."
	DEFVAL { "6000000.0" }
	::= { uxsA2StatusNetGroup 28 }

uxsA2StatusNetTotalSentBytesCritMin OBJECT-TYPE
	SYNTAX DisplayString
	ACCESS read-write
	STATUS mandatory
	DESCRIPTION "&<caiUxsA2.1159>Current critical minimum threshold, in bytes/s, for the total sent bytes monitoring of the network interface watcher. This value represents a declining threshold and must be equal to or greater than 0.0, but cannot be greater than the warning minimum threshold. A value of -1 disables the evaluation of this threshold."
	DEFVAL { "-1" }
	::= { uxsA2StatusNetGroup 29 }

uxsA2StatusNetTotalSentBytesCritMax OBJECT-TYPE
	SYNTAX DisplayString
	ACCESS read-write
	STATUS mandatory
	DESCRIPTION "&<caiUxsA2.1160>Current critical maximum threshold, in bytes/s, for the total sent bytes monitoring of the network interface watcher. This value represents a rising threshold and must be equal to or greater than 0.0, but cannot be less than the warning maximum threshold. A value of -1 disables the evaluation of this threshold."
	DEFVAL { "12000000.0" }
	::= { uxsA2StatusNetGroup 30 }

uxsA2StatusNetTotalSentBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.1161>Current monitor level for the total sent bytes monitoring of the network interface watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 1 }
	::= { uxsA2StatusNetGroup 31 }

uxsA2StatusNetTotalSentBytesStatus OBJECT-TYPE
	SYNTAX INTEGER {
		unknown(1),
		up(2),
		down-warning(3),
		down-critical(4)
	}
	ACCESS read-only
	STATUS mandatory
	DESCRIPTION "&<caiUxsA2.1162>Current status for the total sent bytes monitoring of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusNetGroup 32 }

uxsA2StatusNetTotalOutErrValue OBJECT-TYPE
	SYNTAX INTEGER
	ACCESS read-only
	STATUS mandatory
	DESCRIPTION "&<caiUxsA2.1163>Current value, in number/poll, for the total output errors monitoring of the network interface watcher."
	::= { uxsA2StatusNetGroup 33 }

uxsA2StatusNetTotalOutErrWarn OBJECT-TYPE
	SYNTAX INTEGER
	ACCESS read-write
	STATUS mandatory
	DESCRIPTION "&<caiUxsA2.1164>Current warning threshold, in number/poll, for the total output errors monitoring of the network interface watcher. This value represents a rising threshold and must be greater than 0, but cannot be greater than the critical threshold."
	DEFVAL { 5 }
	::= { uxsA2StatusNetGroup 34 }

uxsA2StatusNetTotalOutErrCrit OBJECT-TYPE
	SYNTAX INTEGER
	ACCESS read-write
	STATUS mandatory
	DESCRIPTION "&<caiUxsA2.1165>Current critical threshold, in number/poll, for the total output errors monitoring of the network interface watcher. This value represents a rising threshold and must be greater than 0, but cannot be less than the warning threshold."
	DEFVAL { 10 }
	::= { uxsA2StatusNetGroup 35 }

uxsA2StatusNetTotalOutErrMonitor OBJECT-TYPE
	SYNTAX INTEGER {
		do-not-monitor(1),
		warning-only(2),
		critical-only(3),
		both(4)
	}
	ACCESS read-write
	STATUS mandatory
	DESCRIPTION "&<caiUxsA2.1166>Current monitor level for the total output errors monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { uxsA2StatusNetGroup 36 }

uxsA2StatusNetTotalOutErrStatus OBJECT-TYPE
	SYNTAX INTEGER {
		unknown(1),
		ok(2),
		warning(3),
		critical(4)
	}
	ACCESS read-only
	STATUS mandatory
	DESCRIPTION "&<caiUxsA2.1167>Current status for the total output errors monitoring of the network interface watcher: 1 (unknown) - An error occurred during data collection, 2 (ok) - The resource is operating within the defined limits or status evaluation is turned off and/or polling is disabled, 3 (warning) - The resource has breached the warning threshold, 4 (critical) - The resource has breached the critical threshold."
	::= { uxsA2StatusNetGroup 37 }

uxsA2StatusNetTotalCollValue OBJECT-TYPE
	SYNTAX INTEGER
	ACCESS read-only
	STATUS mandatory
	DESCRIPTION "&<caiUxsA2.1168>Current value, in number/poll, for the total collisions monitoring of the network interface watcher."
	::= { uxsA2StatusNetGroup 38 }

uxsA2StatusNetTotalCollWarn OBJECT-TYPE
	SYNTAX INTEGER
	ACCESS read-write
	STATUS mandatory
	DESCRIPTION "&<caiUxsA2.1169>Current warning threshold, in number/poll, for the total collisions monitoring of the network interface watcher. This value represents a rising threshold and must be greater than 0, but cannot be greater than the critical threshold."
	DEFVAL { 5 }
	::= { uxsA2StatusNetGroup 39 }

uxsA2StatusNetTotalCollCrit OBJECT-TYPE
	SYNTAX INTEGER
	ACCESS read-write
	STATUS mandatory
	DESCRIPTION "&<caiUxsA2.1170>Current critical threshold, in number/poll, for the total collisions monitoring of the network interface watcher. This value represents a rising threshold and must be greater than 0, but cannot be less than the warning threshold."
	DEFVAL { 10 }
	::= { uxsA2StatusNetGroup 40 }

uxsA2StatusNetTotalCollMonitor OBJECT-TYPE
	SYNTAX INTEGER {
		do-not-monitor(1),
		warning-only(2),
		critical-only(3),
		both(4)
	}
	ACCESS read-write
	STATUS mandatory
	DESCRIPTION "&<caiUxsA2.1171>Current monitor level for the total collisions monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { uxsA2StatusNetGroup 41 }

uxsA2StatusNetTotalCollStatus OBJECT-TYPE
	SYNTAX INTEGER {
		unknown(1),
		ok(2),
		warning(3),
		critical(4)
	}
	ACCESS read-only
	STATUS mandatory
	DESCRIPTION "&<caiUxsA2.1172>Current status for the total collisions monitoring of the network interface watcher: 1 (unknown) - An error occurred during data collection, 2 (ok) - The resource is operating within the defined limits or status evaluation is turned off and/or polling is disabled, 3 (warning) - The resource has breached the warning threshold, 4 (critical) - The resource has breached the critical threshold."
	::= { uxsA2StatusNetGroup 42 }

uxsA2StatusNetTotalCallBackRef OBJECT-TYPE
	SYNTAX DisplayString
	ACCESS read-only
	STATUS mandatory
	DESCRIPTION "&<caiUxsA2.1173>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusNetGroup 43 }

uxsA2StatusNetCount OBJECT-TYPE
	SYNTAX INTEGER
	ACCESS read-only
	STATUS mandatory
	DESCRIPTION "&<caiUxsA2.1174>Number of entries in the network interface status table."
	::= { uxsA2StatusNetGroup 44 }

uxsA2StatusNetTable OBJECT-TYPE
	SYNTAX SEQUENCE OF UxsA2StatusNetEntry
	ACCESS not-accessible
	STATUS mandatory
	DESCRIPTION "&<caiUxsA2.1175>The network interface status table containing details about the currently configured network interface watchers."
	::= { uxsA2StatusNetGroup 45 }

uxsA2StatusNetEntry OBJECT-TYPE
	SYNTAX UxsA2StatusNetEntry
	ACCESS not-accessible
	STATUS mandatory
	DESCRIPTION "&<caiUxsA2.1176>Entry in the network interface status table."
	INDEX {
		uxsA2StatusNetName
	}
	::= { uxsA2StatusNetTable 1 }

UxsA2StatusNetEntry ::= SEQUENCE {
	uxsA2StatusNetName DisplayString,
	uxsA2StatusNetAggLagValue INTEGER,
	uxsA2StatusNetAggLag INTEGER,
	uxsA2StatusNetAggStatus INTEGER,
	uxsA2StatusNetIpAndHost DisplayString,
	uxsA2StatusNetInterfaceSpeed INTEGER,
	uxsA2StatusNetInPktValue INTEGER,
	uxsA2StatusNetInPktWarn INTEGER,
	uxsA2StatusNetInPktCrit INTEGER,
	uxsA2StatusNetInPktMonitor INTEGER,
	uxsA2StatusNetInPktStatus INTEGER,
	uxsA2StatusNetRecBytesValue DisplayString,
	uxsA2StatusNetRecBytesWarnMin DisplayString,
	uxsA2StatusNetRecBytesWarnMax DisplayString,
	uxsA2StatusNetRecBytesCritMin DisplayString,
	uxsA2StatusNetRecBytesCritMax DisplayString,
	uxsA2StatusNetRecBytesMonitor INTEGER,
	uxsA2StatusNetRecBytesStatus INTEGER,
	uxsA2StatusNetInErrValue INTEGER,
	uxsA2StatusNetInErrWarn INTEGER,
	uxsA2StatusNetInErrCrit INTEGER,
	uxsA2StatusNetInErrMonitor INTEGER,
	uxsA2StatusNetInErrStatus INTEGER,
	uxsA2StatusNetOutPktValue INTEGER,
	uxsA2StatusNetOutPktWarn INTEGER,
	uxsA2StatusNetOutPktCrit INTEGER,
	uxsA2StatusNetOutPktMonitor INTEGER,
	uxsA2StatusNetOutPktStatus INTEGER,
	uxsA2StatusNetSentBytesValue DisplayString,
	uxsA2StatusNetSentBytesWarnMin DisplayString,
	uxsA2StatusNetSentBytesWarnMax DisplayString,
	uxsA2StatusNetSentBytesCritMin DisplayString,
	uxsA2StatusNetSentBytesCritMax DisplayString,
	uxsA2StatusNetSentBytesMonitor INTEGER,
	uxsA2StatusNetSentBytesStatus INTEGER,
	uxsA2StatusNetOutErrValue INTEGER,
	uxsA2StatusNetOutErrWarn INTEGER,
	uxsA2StatusNetOutErrCrit INTEGER,
	uxsA2StatusNetOutErrMonitor INTEGER,
	uxsA2StatusNetOutErrStatus INTEGER,
	uxsA2StatusNetCollValue INTEGER,
	uxsA2StatusNetCollWarn INTEGER,
	uxsA2StatusNetCollCrit INTEGER,
	uxsA2StatusNetCollMonitor INTEGER,
	uxsA2StatusNetCollStatus INTEGER,
	uxsA2StatusNetInterfaceValue INTEGER,
	uxsA2StatusNetInterfaceMonitor INTEGER,
	uxsA2StatusNetInterfaceStatus INTEGER,
	uxsA2StatusNetLossAction INTEGER,
	uxsA2StatusNetLossStatus INTEGER,
	uxsA2StatusNetCallBackRef DisplayString
}

uxsA2StatusNetName OBJECT-TYPE
	SYNTAX DisplayString
	ACCESS read-only
	STATUS mandatory
	DESCRIPTION "&<caiUxsA2.1177>Name of the network interface."
	::= { uxsA2StatusNetEntry 1 }

uxsA2StatusNetAggLagValue OBJECT-TYPE
	SYNTAX INTEGER
	ACCESS read-only
	STATUS mandatory
	DESCRIPTION "&<caiUxsA2.1178>Current aggregate lag value of the network interface watcher. Indicates the consecutive number of times at which any status was not in the ok state. The aggregate status changes from ok as soon as the aggregate lag value reaches the configured value."
	::= { uxsA2StatusNetEntry 2 }

uxsA2StatusNetAggLag OBJECT-TYPE
	SYNTAX INTEGER
	ACCESS read-write
	STATUS mandatory
	DESCRIPTION "&<caiUxsA2.1179>Current aggregate lag setting for the network interface watcher. Specifies the consecutive number of times at which any status is not in the ok state, before the aggregate status changes. This value must be greater than 0."
	::= { uxsA2StatusNetEntry 3 }

uxsA2StatusNetAggStatus OBJECT-TYPE
	SYNTAX INTEGER {
		unknown(1),
		ok(2),
		warning(3),
		critical(4),
		passive(5)
	}
	ACCESS read-only
	STATUS mandatory
	DESCRIPTION "&<caiUxsA2.1180>Current aggregate status of the network interface watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { uxsA2StatusNetEntry 4 }

uxsA2StatusNetIpAndHost OBJECT-TYPE
	SYNTAX DisplayString
	ACCESS read-only
	STATUS mandatory
	DESCRIPTION "&<caiUxsA2.1181>The IP address and host name assigned to the network interface. On Solaris 10 machines the name of the zone the interface belongs to is added to the attribute: <ip>/<host>@<zone>."
	::= { uxsA2StatusNetEntry 5 }

uxsA2StatusNetInterfaceSpeed OBJECT-TYPE
	SYNTAX INTEGER
	ACCESS read-only
	STATUS mandatory
	DESCRIPTION "&<caiUxsA2.1182>The nominal bandwidth of the network interface, in MBit/s. May be 0 if the setting is not available."
	::= { uxsA2StatusNetEntry 6 }

uxsA2StatusNetInPktValue OBJECT-TYPE
	SYNTAX INTEGER
	ACCESS read-only
	STATUS mandatory
	DESCRIPTION "&<caiUxsA2.1183>Current value, in pkts/s, for the input packets monitoring of the network interface watcher."
	::= { uxsA2StatusNetEntry 7 }

uxsA2StatusNetInPktWarn OBJECT-TYPE
	SYNTAX INTEGER
	ACCESS read-write
	STATUS mandatory
	DESCRIPTION "&<caiUxsA2.1184>Current warning threshold, in pkts/s, for the input packets monitoring of the network interface watcher. This value represents a rising threshold and must be greater than 0, but cannot be greater than the critical threshold."
	::= { uxsA2StatusNetEntry 8 }

uxsA2StatusNetInPktCrit OBJECT-TYPE
	SYNTAX INTEGER
	ACCESS read-write
	STATUS mandatory
	DESCRIPTION "&<caiUxsA2.1185>Current critical threshold, in pkts/s, for the input packets monitoring of the network interface watcher. This value represents a rising threshold and must be greater than 0, but cannot be less than the warning threshold."
	::= { uxsA2StatusNetEntry 9 }

uxsA2StatusNetInPktMonitor OBJECT-TYPE
	SYNTAX INTEGER {
		do-not-monitor(1),
		warning-only(2),
		critical-only(3),
		both(4)
	}
	ACCESS read-write
	STATUS mandatory
	DESCRIPTION "&<caiUxsA2.1186>Current monitor level for the input packets monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusNetEntry 10 }

uxsA2StatusNetInPktStatus OBJECT-TYPE
	SYNTAX INTEGER {
		unknown(1),
		ok(2),
		warning(3),
		critical(4)
	}
	ACCESS read-only
	STATUS mandatory
	DESCRIPTION "&<caiUxsA2.1187>Current status for the input packets monitoring of the network interface watcher: 1 (unknown) - An error occurred during data collection, 2 (ok) - The resource is operating within the defined limits or status evaluation is turned off and/or polling is disabled, 3 (warning) - The resource has breached the warning threshold, 4 (critical) - The resource has breached the critical threshold."
	::= { uxsA2StatusNetEntry 11 }

uxsA2StatusNetRecBytesValue OBJECT-TYPE
	SYNTAX DisplayString
	ACCESS read-only
	STATUS mandatory
	DESCRIPTION "&<caiUxsA2.1188>Current value, in bytes/s, for the received bytes monitoring of the network interface watcher."
	DEFVAL { "0" }
	::= { uxsA2StatusNetEntry 12 }

uxsA2StatusNetRecBytesWarnMin OBJECT-TYPE
	SYNTAX DisplayString
	ACCESS read-write
	STATUS mandatory
	DESCRIPTION "&<caiUxsA2.1189>Current warning minimum threshold, in bytes/s, for the received bytes monitoring of the network interface watcher. This value represents a declining threshold and must be equal to or greater than 0.0, equal to or greater than the critical minimum threshold, but cannot be greater than the warning maximum threshold. A value of -1 disables the evaluation of this threshold."
	DEFVAL { "-2" }
	::= { uxsA2StatusNetEntry 13 }

uxsA2StatusNetRecBytesWarnMax OBJECT-TYPE
	SYNTAX DisplayString
	ACCESS read-write
	STATUS mandatory
	DESCRIPTION "&<caiUxsA2.1190>Current warning maximum threshold, in bytes/s, for the received bytes monitoring of the network interface watcher. This value represents a rising threshold and must be equal to or greater than 0.0, equal to or greater than the warning minimum threshold, but cannot be greater than the critical maximum threshold. A value of -1 disables the evaluation of this threshold."
	DEFVAL { "-2" }
	::= { uxsA2StatusNetEntry 14 }

uxsA2StatusNetRecBytesCritMin OBJECT-TYPE
	SYNTAX DisplayString
	ACCESS read-write
	STATUS mandatory
	DESCRIPTION "&<caiUxsA2.1191>Current critical minimum threshold, in bytes/s, for the received bytes monitoring of the network interface watcher. This value represents a declining threshold and must be equal to or greater than 0.0, but cannot be greater than the warning minimum threshold. A value of -1 disables the evaluation of this threshold."
	DEFVAL { "-2" }
	::= { uxsA2StatusNetEntry 15 }

uxsA2StatusNetRecBytesCritMax OBJECT-TYPE
	SYNTAX DisplayString
	ACCESS read-write
	STATUS mandatory
	DESCRIPTION "&<caiUxsA2.1192>Current critical maximum threshold, in bytes/s, for the received bytes monitoring of the network interface watcher. This value represents a rising threshold and must be equal to or greater than 0.0, but cannot be less than the warning maximum threshold. A value of -1 disables the evaluation of this threshold."
	DEFVAL { "-2" }
	::= { uxsA2StatusNetEntry 16 }

uxsA2StatusNetRecBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.1193>Current monitor level for the received bytes monitoring of the network interface watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2StatusNetEntry 17 }

uxsA2StatusNetRecBytesStatus OBJECT-TYPE
	SYNTAX INTEGER {
		unknown(1),
		up(2),
		down-warning(3),
		down-critical(4)
	}
	ACCESS read-only
	STATUS mandatory
	DESCRIPTION "&<caiUxsA2.1194>Current status for the received bytes monitoring of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusNetEntry 18 }

uxsA2StatusNetInErrValue OBJECT-TYPE
	SYNTAX INTEGER
	ACCESS read-only
	STATUS mandatory
	DESCRIPTION "&<caiUxsA2.1195>Current value, in number/poll, for the input errors monitoring of the network interface watcher."
	::= { uxsA2StatusNetEntry 19 }

uxsA2StatusNetInErrWarn OBJECT-TYPE
	SYNTAX INTEGER
	ACCESS read-write
	STATUS mandatory
	DESCRIPTION "&<caiUxsA2.1196>Current warning threshold, in number/poll, for the input errors monitoring of the network interface watcher. This value represents a rising threshold and must be greater than 0, but cannot be greater than the critical threshold."
	::= { uxsA2StatusNetEntry 20 }

uxsA2StatusNetInErrCrit OBJECT-TYPE
	SYNTAX INTEGER
	ACCESS read-write
	STATUS mandatory
	DESCRIPTION "&<caiUxsA2.1197>Current critical threshold, in number/poll, for the input errors monitoring of the network interface watcher. This value represents a rising threshold and must be greater than 0, but cannot be less than the warning threshold."
	::= { uxsA2StatusNetEntry 21 }

uxsA2StatusNetInErrMonitor OBJECT-TYPE
	SYNTAX INTEGER {
		do-not-monitor(1),
		warning-only(2),
		critical-only(3),
		both(4)
	}
	ACCESS read-write
	STATUS mandatory
	DESCRIPTION "&<caiUxsA2.1198>Current monitor level for the input errors monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusNetEntry 22 }

uxsA2StatusNetInErrStatus OBJECT-TYPE
	SYNTAX INTEGER {
		unknown(1),
		ok(2),
		warning(3),
		critical(4)
	}
	ACCESS read-only
	STATUS mandatory
	DESCRIPTION "&<caiUxsA2.1199>Current status for the input errors monitoring of the network interface watcher: 1 (unknown) - An error occurred during data collection, 2 (ok) - The resource is operating within the defined limits or status evaluation is turned off and/or polling is disabled, 3 (warning) - The resource has breached the warning threshold, 4 (critical) - The resource has breached the critical threshold."
	::= { uxsA2StatusNetEntry 23 }

uxsA2StatusNetOutPktValue OBJECT-TYPE
	SYNTAX INTEGER
	ACCESS read-only
	STATUS mandatory
	DESCRIPTION "&<caiUxsA2.1200>Current value, in pkts/s, for the output packets monitoring of the network interface watcher."
	::= { uxsA2StatusNetEntry 24 }

uxsA2StatusNetOutPktWarn OBJECT-TYPE
	SYNTAX INTEGER
	ACCESS read-write
	STATUS mandatory
	DESCRIPTION "&<caiUxsA2.1201>Current warning threshold, in pkts/s, for the output packets monitoring of the network interface watcher. This value represents a rising threshold and must be greater than 0, but cannot be greater than the critical threshold."
	::= { uxsA2StatusNetEntry 25 }

uxsA2StatusNetOutPktCrit OBJECT-TYPE
	SYNTAX INTEGER
	ACCESS read-write
	STATUS mandatory
	DESCRIPTION "&<caiUxsA2.1202>Current critical threshold, in pkts/s, for the output packets monitoring of the network interface watcher. This value represents a rising threshold and must be greater than 0, but cannot be less than the warning threshold."
	::= { uxsA2StatusNetEntry 26 }

uxsA2StatusNetOutPktMonitor OBJECT-TYPE
	SYNTAX INTEGER {
		do-not-monitor(1),
		warning-only(2),
		critical-only(3),
		both(4)
	}
	ACCESS read-write
	STATUS mandatory
	DESCRIPTION "&<caiUxsA2.1203>Current monitor level for the output packets monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusNetEntry 27 }

uxsA2StatusNetOutPktStatus OBJECT-TYPE
	SYNTAX INTEGER {
		unknown(1),
		ok(2),
		warning(3),
		critical(4)
	}
	ACCESS read-only
	STATUS mandatory
	DESCRIPTION "&<caiUxsA2.1204>Current status for the output packets monitoring of the network interface watcher: 1 (unknown) - An error occurred during data collection, 2 (ok) - The resource is operating within the defined limits or status evaluation is turned off and/or polling is disabled, 3 (warning) - The resource has breached the warning threshold, 4 (critical) - The resource has breached the critical threshold."
	::= { uxsA2StatusNetEntry 28 }

uxsA2StatusNetSentBytesValue OBJECT-TYPE
	SYNTAX DisplayString
	ACCESS read-only
	STATUS mandatory
	DESCRIPTION "&<caiUxsA2.1205>Current value, in bytes/s, for the sent bytes monitoring of the network interface watcher."
	DEFVAL { "0" }
	::= { uxsA2StatusNetEntry 29 }

uxsA2StatusNetSentBytesWarnMin OBJECT-TYPE
	SYNTAX DisplayString
	ACCESS read-write
	STATUS mandatory
	DESCRIPTION "&<caiUxsA2.1206>Current warning minimum threshold, in bytes/s, for the sent bytes monitoring of the network interface watcher. This value represents a declining threshold and must be equal to or greater than 0.0, equal to or greater than the critical minimum threshold, but cannot be greater than the warning maximum threshold. A value of -1 disables the evaluation of this threshold."
	DEFVAL { "-2" }
	::= { uxsA2StatusNetEntry 30 }

uxsA2StatusNetSentBytesWarnMax OBJECT-TYPE
	SYNTAX DisplayString
	ACCESS read-write
	STATUS mandatory
	DESCRIPTION "&<caiUxsA2.1207>Current warning maximum threshold, in bytes/s, for the sent bytes monitoring of the network interface watcher. This value represents a rising threshold and must be equal to or greater than 0.0, equal to or greater than the warning minimum threshold, but cannot be greater than the critical maximum threshold. A value of -1 disables the evaluation of this threshold."
	DEFVAL { "-2" }
	::= { uxsA2StatusNetEntry 31 }

uxsA2StatusNetSentBytesCritMin OBJECT-TYPE
	SYNTAX DisplayString
	ACCESS read-write
	STATUS mandatory
	DESCRIPTION "&<caiUxsA2.1208>Current critical minimum threshold, in bytes/s, for the sent bytes monitoring of the network interface watcher. This value represents a declining threshold and must be equal to or greater than 0.0, but cannot be greater than the warning minimum threshold. A value of -1 disables the evaluation of this threshold."
	DEFVAL { "-2" }
	::= { uxsA2StatusNetEntry 32 }

uxsA2StatusNetSentBytesCritMax OBJECT-TYPE
	SYNTAX DisplayString
	ACCESS read-write
	STATUS mandatory
	DESCRIPTION "&<caiUxsA2.1209>Current critical maximum threshold, in bytes/s, for the sent bytes monitoring of the network interface watcher. This value represents a rising threshold and must be equal to or greater than 0.0, but cannot be less than the warning maximum threshold. A value of -1 disables the evaluation of this threshold."
	DEFVAL { "-2" }
	::= { uxsA2StatusNetEntry 33 }

uxsA2StatusNetSentBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.1210>Current monitor level for the sent bytes monitoring of the network interface watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2StatusNetEntry 34 }

uxsA2StatusNetSentBytesStatus OBJECT-TYPE
	SYNTAX INTEGER {
		unknown(1),
		up(2),
		down-warning(3),
		down-critical(4)
	}
	ACCESS read-only
	STATUS mandatory
	DESCRIPTION "&<caiUxsA2.1211>Current status for the sent bytes monitoring of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusNetEntry 35 }

uxsA2StatusNetOutErrValue OBJECT-TYPE
	SYNTAX INTEGER
	ACCESS read-only
	STATUS mandatory
	DESCRIPTION "&<caiUxsA2.1212>Current value, in number/poll, for the output errors monitoring of the network interface watcher."
	::= { uxsA2StatusNetEntry 36 }

uxsA2StatusNetOutErrWarn OBJECT-TYPE
	SYNTAX INTEGER
	ACCESS read-write
	STATUS mandatory
	DESCRIPTION "&<caiUxsA2.1213>Current warning threshold, in number/poll, for the output errors monitoring of the network interface watcher. This value represents a rising threshold and must be greater than 0, but cannot be greater than the critical threshold."
	::= { uxsA2StatusNetEntry 37 }

uxsA2StatusNetOutErrCrit OBJECT-TYPE
	SYNTAX INTEGER
	ACCESS read-write
	STATUS mandatory
	DESCRIPTION "&<caiUxsA2.1214>Current critical threshold, in number/poll, for the output errors monitoring of the network interface watcher. This value represents a rising threshold and must be greater than 0, but cannot be less than the warning threshold."
	::= { uxsA2StatusNetEntry 38 }

uxsA2StatusNetOutErrMonitor OBJECT-TYPE
	SYNTAX INTEGER {
		do-not-monitor(1),
		warning-only(2),
		critical-only(3),
		both(4)
	}
	ACCESS read-write
	STATUS mandatory
	DESCRIPTION "&<caiUxsA2.1215>Current monitor level for the output errors monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusNetEntry 39 }

uxsA2StatusNetOutErrStatus OBJECT-TYPE
	SYNTAX INTEGER {
		unknown(1),
		ok(2),
		warning(3),
		critical(4)
	}
	ACCESS read-only
	STATUS mandatory
	DESCRIPTION "&<caiUxsA2.1216>Current status for the output errors monitoring of the network interface watcher: 1 (unknown) - An error occurred during data collection, 2 (ok) - The resource is operating within the defined limits or status evaluation is turned off and/or polling is disabled, 3 (warning) - The resource has breached the warning threshold, 4 (critical) - The resource has breached the critical threshold."
	::= { uxsA2StatusNetEntry 40 }

uxsA2StatusNetCollValue OBJECT-TYPE
	SYNTAX INTEGER
	ACCESS read-only
	STATUS mandatory
	DESCRIPTION "&<caiUxsA2.1217>Current value, in number/poll, for the collisions monitoring of the network interface watcher."
	::= { uxsA2StatusNetEntry 41 }

uxsA2StatusNetCollWarn OBJECT-TYPE
	SYNTAX INTEGER
	ACCESS read-write
	STATUS mandatory
	DESCRIPTION "&<caiUxsA2.1218>Current warning threshold, in number/poll, for the collisions monitoring of the network interface watcher. This value represents a rising threshold and must be greater than 0, but cannot be greater than the critical threshold."
	::= { uxsA2StatusNetEntry 42 }

uxsA2StatusNetCollCrit OBJECT-TYPE
	SYNTAX INTEGER
	ACCESS read-write
	STATUS mandatory
	DESCRIPTION "&<caiUxsA2.1219>Current critical threshold, in number/poll, for the collisions monitoring of the network interface watcher. This value represents a rising threshold and must be greater than 0, but cannot be less than the warning threshold."
	::= { uxsA2StatusNetEntry 43 }

uxsA2StatusNetCollMonitor OBJECT-TYPE
	SYNTAX INTEGER {
		do-not-monitor(1),
		warning-only(2),
		critical-only(3),
		both(4)
	}
	ACCESS read-write
	STATUS mandatory
	DESCRIPTION "&<caiUxsA2.1220>Current monitor level for the collisions monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusNetEntry 44 }

uxsA2StatusNetCollStatus OBJECT-TYPE
	SYNTAX INTEGER {
		unknown(1),
		ok(2),
		warning(3),
		critical(4)
	}
	ACCESS read-only
	STATUS mandatory
	DESCRIPTION "&<caiUxsA2.1221>Current status for the collisions monitoring of the network interface watcher: 1 (unknown) - An error occurred during data collection, 2 (ok) - The resource is operating within the defined limits or status evaluation is turned off and/or polling is disabled, 3 (warning) - The resource has breached the warning threshold, 4 (critical) - The resource has breached the critical threshold."
	::= { uxsA2StatusNetEntry 45 }

uxsA2StatusNetInterfaceValue OBJECT-TYPE
	SYNTAX INTEGER {
		up(1),
		down(2),
		cable-loss(3)
	}
	ACCESS read-only
	STATUS mandatory
	DESCRIPTION "&<caiUxsA2.1222>The status of the Interface Status metric. Possible values are: up : The interface is working. down : The interface has been disabled by software. cable-loss : The network connection is down, e.g. because the network cable is dropped."
	::= { uxsA2StatusNetEntry 46 }

uxsA2StatusNetInterfaceMonitor OBJECT-TYPE
	SYNTAX INTEGER {
		do-not-monitor(1),
		down-warning(2),
		down-critical(3)
	}
	ACCESS read-write
	STATUS mandatory
	DESCRIPTION "&<caiUxsA2.1223>Current monitor level for the interface status monitoring of the network interface watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusNetEntry 47 }

uxsA2StatusNetInterfaceStatus OBJECT-TYPE
	SYNTAX INTEGER {
		unknown(1),
		up(2),
		down-warning(3),
		down-critical(4)
	}
	ACCESS read-only
	STATUS mandatory
	DESCRIPTION "&<caiUxsA2.1224>Current status for the interface status monitoring of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusNetEntry 48 }

uxsA2StatusNetLossAction OBJECT-TYPE
	SYNTAX INTEGER {
		remove(1),
		up(2),
		down-warning(3),
		down-critical(4)
	}
	ACCESS read-write
	STATUS mandatory
	DESCRIPTION "&<caiUxsA2.1225>Current loss action for the network interface watcher. Specifies the action to take if the monitored network interface is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusNetEntry 49 }

uxsA2StatusNetLossStatus OBJECT-TYPE
	SYNTAX INTEGER {
		unknown(1),
		up(2),
		down-warning(3),
		down-critical(4)
	}
	ACCESS read-only
	STATUS mandatory
	DESCRIPTION "&<caiUxsA2.1226>Current loss status of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusNetEntry 50 }

uxsA2StatusNetCallBackRef OBJECT-TYPE
	SYNTAX DisplayString
	ACCESS read-only
	STATUS mandatory
	DESCRIPTION "&<caiUxsA2.1227>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusNetEntry 51 }

--
-- The StatusSHM Group
--

uxsA2StatusSHMCount OBJECT-TYPE
	SYNTAX INTEGER
	ACCESS read-only
	STATUS mandatory
	DESCRIPTION "&<caiUxsA2.1228>Number of entries in the shared memory status table."
	::= { uxsA2StatusSHMGroup 1 }

uxsA2StatusSHMTable OBJECT-TYPE
	SYNTAX SEQUENCE OF UxsA2StatusSHMEntry
	ACCESS not-accessible
	STATUS mandatory
	DESCRIPTION "&<caiUxsA2.1229>The shared memory status table containing details about the currently configured shared memory watchers."
	::= { uxsA2StatusSHMGroup 2 }

uxsA2StatusSHMEntry OBJECT-TYPE
	SYNTAX UxsA2StatusSHMEntry
	ACCESS not-accessible
	STATUS mandatory
	DESCRIPTION "&<caiUxsA2.1230>Entry in the shared memory status table."
	INDEX {
		uxsA2StatusSHMId
	}
	::= { uxsA2StatusSHMTable 1 }

UxsA2StatusSHMEntry ::= SEQUENCE {
	uxsA2StatusSHMId DisplayString,
	uxsA2StatusSHMDescription DisplayString,
	uxsA2StatusSHMAutoWatcherName DisplayString,
	uxsA2StatusSHMAggLagValue INTEGER,
	uxsA2StatusSHMAggLag INTEGER,
	uxsA2StatusSHMAggStatus INTEGER,
	uxsA2StatusSHMKey DisplayString,
	uxsA2StatusSHMMode DisplayString,
	uxsA2StatusSHMOwner DisplayString,
	uxsA2StatusSHMGrp DisplayString,
	uxsA2StatusSHMNAttachValue INTEGER,
	uxsA2StatusSHMNAttachMin INTEGER,
	uxsA2StatusSHMNAttachMax INTEGER,
	uxsA2StatusSHMNAttachMonitor INTEGER,
	uxsA2StatusSHMNAttachStatus INTEGER,
	uxsA2StatusSHMSegSzTotal DisplayString,
	uxsA2StatusSHMSegSzValue DisplayString,
	uxsA2StatusSHMSegSzWarnValue DisplayString,
	uxsA2StatusSHMSegSzCritValue DisplayString,
	uxsA2StatusSHMSegSzWarn DisplayString,
	uxsA2StatusSHMSegSzCrit DisplayString,
	uxsA2StatusSHMSegSzMonitor INTEGER,
	uxsA2StatusSHMSegSzStatus INTEGER,
	uxsA2StatusSHMLossAction INTEGER,
	uxsA2StatusSHMLossStatus INTEGER,
	uxsA2StatusSHMCallBackRef DisplayString,
	uxsA2StatusSHMButton INTEGER
}

uxsA2StatusSHMId OBJECT-TYPE
	SYNTAX DisplayString
	ACCESS read-only
	STATUS mandatory
	DESCRIPTION "&<caiUxsA2.1231>Name of the shared memory identifier. The number of used and totally available shared memory identifiers is monitored in the OS Resource Parameters group. Note that resource limits can be set dynamically on Solaris 10: The total value is the current limit for a privileged process in the project the agent belongs to."
	::= { uxsA2StatusSHMEntry 1 }

uxsA2StatusSHMDescription OBJECT-TYPE
	SYNTAX DisplayString
	ACCESS read-write
	STATUS mandatory
	DESCRIPTION "&<caiUxsA2.1232>Current description for the shared memory watcher."
	::= { uxsA2StatusSHMEntry 2 }

uxsA2StatusSHMAutoWatcherName OBJECT-TYPE
	SYNTAX DisplayString
	ACCESS read-only
	STATUS mandatory
	DESCRIPTION "&<caiUxsA2.1233>Name of the shared memory auto watcher which automatically created this watcher. This attribute is left blank if the watcher was added manually."
	::= { uxsA2StatusSHMEntry 3 }

uxsA2StatusSHMAggLagValue OBJECT-TYPE
	SYNTAX INTEGER
	ACCESS read-only
	STATUS mandatory
	DESCRIPTION "&<caiUxsA2.1234>Current aggregate lag value of the shared memory watcher. Indicates the consecutive number of times at which any status was not in the ok state. The aggregate status changes from ok as soon as the aggregate lag value reaches the configured value."
	::= { uxsA2StatusSHMEntry 4 }

uxsA2StatusSHMAggLag OBJECT-TYPE
	SYNTAX INTEGER
	ACCESS read-write
	STATUS mandatory
	DESCRIPTION "&<caiUxsA2.1235>Current aggregate lag setting for the shared memory watcher. Specifies the consecutive number of times at which any status is not in the ok state, before the aggregate status changes. This value must be greater than 0."
	::= { uxsA2StatusSHMEntry 5 }

uxsA2StatusSHMAggStatus OBJECT-TYPE
	SYNTAX INTEGER {
		unknown(1),
		ok(2),
		warning(3),
		critical(4),
		passive(5)
	}
	ACCESS read-only
	STATUS mandatory
	DESCRIPTION "&<caiUxsA2.1236>Current aggregate status of the shared memory watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { uxsA2StatusSHMEntry 6 }

uxsA2StatusSHMKey OBJECT-TYPE
	SYNTAX DisplayString
	ACCESS read-only
	STATUS mandatory
	DESCRIPTION "&<caiUxsA2.1237>Key of the shared memory."
	::= { uxsA2StatusSHMEntry 7 }

uxsA2StatusSHMMode OBJECT-TYPE
	SYNTAX DisplayString
	ACCESS read-only
	STATUS mandatory
	DESCRIPTION "&<caiUxsA2.1238>Access mode and flags of the shared memory."
	::= { uxsA2StatusSHMEntry 8 }

uxsA2StatusSHMOwner OBJECT-TYPE
	SYNTAX DisplayString
	ACCESS read-only
	STATUS mandatory
	DESCRIPTION "&<caiUxsA2.1239>User name of the owner of the shared memory. On Solaris 10 machines the name of the zone the resource belongs to is added to the attribute: <owner>@<zone>."
	::= { uxsA2StatusSHMEntry 9 }

uxsA2StatusSHMGrp OBJECT-TYPE
	SYNTAX DisplayString
	ACCESS read-only
	STATUS mandatory
	DESCRIPTION "&<caiUxsA2.1240>Group name of the owner of the shared memory."
	::= { uxsA2StatusSHMEntry 10 }

uxsA2StatusSHMNAttachValue OBJECT-TYPE
	SYNTAX INTEGER
	ACCESS read-only
	STATUS mandatory
	DESCRIPTION "&<caiUxsA2.1241>Current value for the number of processes attached monitoring of the shared memory watcher."
	::= { uxsA2StatusSHMEntry 11 }

uxsA2StatusSHMNAttachMin OBJECT-TYPE
	SYNTAX INTEGER
	ACCESS read-write
	STATUS mandatory
	DESCRIPTION "&<caiUxsA2.1242>Current minimum threshold for the number of processes attached monitoring of the shared memory watcher. This value represents a declining threshold and must be equal to or greater than 0, but cannot be greater than the maximum threshold. A value of -1 disables the evaluation of this threshold."
	DEFVAL { -2 }
	::= { uxsA2StatusSHMEntry 12 }

uxsA2StatusSHMNAttachMax OBJECT-TYPE
	SYNTAX INTEGER
	ACCESS read-write
	STATUS mandatory
	DESCRIPTION "&<caiUxsA2.1243>Current maximum threshold for the number of processes attached monitoring of the shared memory watcher. This value represents a rising threshold and must be equal to or greater than 0, but cannot be less than the minimum threshold. A value of -1 disables the evaluation of this threshold."
	DEFVAL { -2 }
	::= { uxsA2StatusSHMEntry 13 }

uxsA2StatusSHMNAttachMonitor OBJECT-TYPE
	SYNTAX INTEGER {
		do-not-monitor(1),
		down-warning(2),
		down-critical(3)
	}
	ACCESS read-write
	STATUS mandatory
	DESCRIPTION "&<caiUxsA2.1244>Current monitor level for the number of processes attached monitoring of the shared memory watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusSHMEntry 14 }

uxsA2StatusSHMNAttachStatus OBJECT-TYPE
	SYNTAX INTEGER {
		unknown(1),
		up(2),
		down-warning(3),
		down-critical(4)
	}
	ACCESS read-only
	STATUS mandatory
	DESCRIPTION "&<caiUxsA2.1245>Current status for the number of processes attached monitoring of the shared memory watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusSHMEntry 15 }

uxsA2StatusSHMSegSzTotal OBJECT-TYPE
	SYNTAX DisplayString
	ACCESS read-only
	STATUS mandatory
	DESCRIPTION "&<caiUxsA2.1246>Maximum segment size of the shared memory in megabytes. On Solaris 10 this is the current limit for a privileged process in the project the agent belongs to."
	DEFVAL { "0" }
	::= { uxsA2StatusSHMEntry 16 }

uxsA2StatusSHMSegSzValue OBJECT-TYPE
	SYNTAX DisplayString
	ACCESS read-only
	STATUS mandatory
	DESCRIPTION "&<caiUxsA2.1247>Current value, in megabytes, for the size of associated shared memory segment monitoring of the shared memory watcher."
	DEFVAL { "0" }
	::= { uxsA2StatusSHMEntry 17 }

uxsA2StatusSHMSegSzWarnValue OBJECT-TYPE
	SYNTAX DisplayString
	ACCESS read-only
	STATUS mandatory
	DESCRIPTION "&<caiUxsA2.1248>Active warning threshold, in megabytes, as derived from the configured value for the size of associated shared memory segment monitoring of the shared memory watcher. This value represents a rising threshold and must be greater than 0.0, less than or equal to the total value (maximum capacity) of the monitored resource as specified in uxsA2StatusSHMSegSzTotal, but cannot be greater than the active critical threshold. These constraints will be maintained by the agent during all configuration actions."
	::= { uxsA2StatusSHMEntry 18 }

uxsA2StatusSHMSegSzCritValue OBJECT-TYPE
	SYNTAX DisplayString
	ACCESS read-only
	STATUS mandatory
	DESCRIPTION "&<caiUxsA2.1249>Active critical threshold, in megabytes, as derived from the configured value for the size of associated shared memory segment monitoring of the shared memory watcher. This value represents a rising threshold and must be greater than 0.0, less than or equal to the total value (maximum capacity) of the monitored resource as specified in uxsA2StatusSHMSegSzTotal, but cannot be less than the active warning threshold. These constraints will be maintained by the agent during all configuration actions."
	::= { uxsA2StatusSHMEntry 19 }

uxsA2StatusSHMSegSzWarn OBJECT-TYPE
	SYNTAX DisplayString
	ACCESS read-write
	STATUS mandatory
	DESCRIPTION "&<caiUxsA2.1250>Configured warning threshold from which the active warning threshold is derived for the size of associated shared memory segment monitoring of the shared memory watcher. The threshold can be specified as either an absolute value (n) or a percentage (n%). It can also be specified as the absolute value left free (nF). The value of uxsA2StatusSHMSegSzTotal will be the reference value for n% and nF notations."
	::= { uxsA2StatusSHMEntry 20 }

uxsA2StatusSHMSegSzCrit OBJECT-TYPE
	SYNTAX DisplayString
	ACCESS read-write
	STATUS mandatory
	DESCRIPTION "&<caiUxsA2.1251>Configured critical threshold from which the active critical threshold is derived for the size of associated shared memory segment monitoring of the shared memory watcher. The threshold can be specified as either an absolute value (n) or a percentage (n%). It can also be specified as the absolute value left free (nF). The value of uxsA2StatusSHMSegSzTotal will be the reference value for n% and nF notations."
	::= { uxsA2StatusSHMEntry 21 }

uxsA2StatusSHMSegSzMonitor OBJECT-TYPE
	SYNTAX INTEGER {
		do-not-monitor(1),
		warning-only(2),
		critical-only(3),
		both(4)
	}
	ACCESS read-write
	STATUS mandatory
	DESCRIPTION "&<caiUxsA2.1252>Current monitor level for the size of associated shared memory segment monitoring of the shared memory watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusSHMEntry 22 }

uxsA2StatusSHMSegSzStatus OBJECT-TYPE
	SYNTAX INTEGER {
		unknown(1),
		ok(2),
		warning(3),
		critical(4)
	}
	ACCESS read-only
	STATUS mandatory
	DESCRIPTION "&<caiUxsA2.1253>Current status for the size of associated shared memory segment monitoring of the shared memory watcher: 1 (unknown) - An error occurred during data collection, 2 (ok) - The resource is operating within the defined limits or status evaluation is turned off and/or polling is disabled, 3 (warning) - The resource has breached the warning threshold, 4 (critical) - The resource has breached the critical threshold."
	::= { uxsA2StatusSHMEntry 23 }

uxsA2StatusSHMLossAction OBJECT-TYPE
	SYNTAX INTEGER {
		remove(1),
		up(2),
		down-warning(3),
		down-critical(4)
	}
	ACCESS read-write
	STATUS mandatory
	DESCRIPTION "&<caiUxsA2.1254>Current loss action for the shared memory watcher. Specifies the action to take if the monitored shared memory is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusSHMEntry 24 }

uxsA2StatusSHMLossStatus OBJECT-TYPE
	SYNTAX INTEGER {
		unknown(1),
		up(2),
		down-warning(3),
		down-critical(4)
	}
	ACCESS read-only
	STATUS mandatory
	DESCRIPTION "&<caiUxsA2.1255>Current loss status of the shared memory watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusSHMEntry 25 }

uxsA2StatusSHMCallBackRef OBJECT-TYPE
	SYNTAX DisplayString
	ACCESS read-only
	STATUS mandatory
	DESCRIPTION "&<caiUxsA2.1256>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusSHMEntry 26 }

uxsA2StatusSHMButton OBJECT-TYPE
	SYNTAX INTEGER {
		none(1),
		remove(2)
	}
	ACCESS read-write
	STATUS mandatory
	DESCRIPTION "&<caiUxsA2.1257>This attribute is used to remove the shared memory watcher. If set to 2 (remove), the agent removes the watcher from the table. This attribute cannot be set to 1 (none)."
	DEFVAL { 1 }
	::= { uxsA2StatusSHMEntry 27 }

--
-- The StatusSEM Group
--

uxsA2StatusSEMCount OBJECT-TYPE
	SYNTAX INTEGER
	ACCESS read-only
	STATUS mandatory
	DESCRIPTION "&<caiUxsA2.1258>Number of entries in the semaphore status table."
	::= { uxsA2StatusSEMGroup 1 }

uxsA2StatusSEMTable OBJECT-TYPE
	SYNTAX SEQUENCE OF UxsA2StatusSEMEntry
	ACCESS not-accessible
	STATUS mandatory
	DESCRIPTION "&<caiUxsA2.1259>The semaphore status table containing details about the currently configured semaphore watchers."
	::= { uxsA2StatusSEMGroup 2 }

uxsA2StatusSEMEntry OBJECT-TYPE
	SYNTAX UxsA2StatusSEMEntry
	ACCESS not-accessible
	STATUS mandatory
	DESCRIPTION "&<caiUxsA2.1260>Entry in the semaphore status table."
	INDEX {
		uxsA2StatusSEMId
	}
	::= { uxsA2StatusSEMTable 1 }

UxsA2StatusSEMEntry ::= SEQUENCE {
	uxsA2StatusSEMId DisplayString,
	uxsA2StatusSEMDescription DisplayString,
	uxsA2StatusSEMAutoWatcherName DisplayString,
	uxsA2StatusSEMAggLagValue INTEGER,
	uxsA2StatusSEMAggLag INTEGER,
	uxsA2StatusSEMAggStatus INTEGER,
	uxsA2StatusSEMKey DisplayString,
	uxsA2StatusSEMMode DisplayString,
	uxsA2StatusSEMOwner DisplayString,
	uxsA2StatusSEMGrp DisplayString,
	uxsA2StatusSEMNSemsValue INTEGER,
	uxsA2StatusSEMNSemsWarn INTEGER,
	uxsA2StatusSEMNSemsCrit INTEGER,
	uxsA2StatusSEMNSemsMonitor INTEGER,
	uxsA2StatusSEMNSemsStatus INTEGER,
	uxsA2StatusSEMLossAction INTEGER,
	uxsA2StatusSEMLossStatus INTEGER,
	uxsA2StatusSEMCallBackRef DisplayString,
	uxsA2StatusSEMButton INTEGER
}

uxsA2StatusSEMId OBJECT-TYPE
	SYNTAX DisplayString
	ACCESS read-only
	STATUS mandatory
	DESCRIPTION "&<caiUxsA2.1261>Name of the semaphore identifier. The number of used and totally available semaphore identifiers is monitored in the OS Resource Parameters group. Note that resource limits can be set dynamically on Solaris 10: The total value is the current limit for a privileged process in the project the agent belongs to."
	::= { uxsA2StatusSEMEntry 1 }

uxsA2StatusSEMDescription OBJECT-TYPE
	SYNTAX DisplayString
	ACCESS read-write
	STATUS mandatory
	DESCRIPTION "&<caiUxsA2.1262>Current description for the semaphore watcher."
	::= { uxsA2StatusSEMEntry 2 }

uxsA2StatusSEMAutoWatcherName OBJECT-TYPE
	SYNTAX DisplayString
	ACCESS read-only
	STATUS mandatory
	DESCRIPTION "&<caiUxsA2.1263>Name of the semaphore auto watcher which automatically created this watcher. This attribute is left blank if the watcher was added manually."
	::= { uxsA2StatusSEMEntry 3 }

uxsA2StatusSEMAggLagValue OBJECT-TYPE
	SYNTAX INTEGER
	ACCESS read-only
	STATUS mandatory
	DESCRIPTION "&<caiUxsA2.1264>Current aggregate lag value of the semaphore watcher. Indicates the consecutive number of times at which any status was not in the ok state. The aggregate status changes from ok as soon as the aggregate lag value reaches the configured value."
	::= { uxsA2StatusSEMEntry 4 }

uxsA2StatusSEMAggLag OBJECT-TYPE
	SYNTAX INTEGER
	ACCESS read-write
	STATUS mandatory
	DESCRIPTION "&<caiUxsA2.1265>Current aggregate lag setting for the semaphore watcher. Specifies the consecutive number of times at which any status is not in the ok state, before the aggregate status changes. This value must be greater than 0."
	::= { uxsA2StatusSEMEntry 5 }

uxsA2StatusSEMAggStatus OBJECT-TYPE
	SYNTAX INTEGER {
		unknown(1),
		ok(2),
		warning(3),
		critical(4),
		passive(5)
	}
	ACCESS read-only
	STATUS mandatory
	DESCRIPTION "&<caiUxsA2.1266>Current aggregate status of the semaphore watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { uxsA2StatusSEMEntry 6 }

uxsA2StatusSEMKey OBJECT-TYPE
	SYNTAX DisplayString
	ACCESS read-only
	STATUS mandatory
	DESCRIPTION "&<caiUxsA2.1267>Key of the semaphore."
	::= { uxsA2StatusSEMEntry 7 }

uxsA2StatusSEMMode OBJECT-TYPE
	SYNTAX DisplayString
	ACCESS read-only
	STATUS mandatory
	DESCRIPTION "&<caiUxsA2.1268>Access mode and flags of the semaphore."
	::= { uxsA2StatusSEMEntry 8 }

uxsA2StatusSEMOwner OBJECT-TYPE
	SYNTAX DisplayString
	ACCESS read-only
	STATUS mandatory
	DESCRIPTION "&<caiUxsA2.1269>User name of the owner of the semaphore. On Solaris 10 machines the name of the zone the resource belongs to is added to the attribute: <owner>@<zone>."
	::= { uxsA2StatusSEMEntry 9 }

uxsA2StatusSEMGrp OBJECT-TYPE
	SYNTAX DisplayString
	ACCESS read-only
	STATUS mandatory
	DESCRIPTION "&<caiUxsA2.1270>Group name of the owner of the semaphore."
	::= { uxsA2StatusSEMEntry 10 }

uxsA2StatusSEMNSemsValue OBJECT-TYPE
	SYNTAX INTEGER
	ACCESS read-only
	STATUS mandatory
	DESCRIPTION "&<caiUxsA2.1271>Current value for the number of semaphores in the set monitoring of the semaphore watcher."
	::= { uxsA2StatusSEMEntry 11 }

uxsA2StatusSEMNSemsWarn OBJECT-TYPE
	SYNTAX INTEGER
	ACCESS read-write
	STATUS mandatory
	DESCRIPTION "&<caiUxsA2.1272>Current warning threshold for the number of semaphores in the set monitoring of the semaphore watcher. This value represents a rising threshold and must be greater than 0, but cannot be greater than the critical threshold."
	::= { uxsA2StatusSEMEntry 12 }

uxsA2StatusSEMNSemsCrit OBJECT-TYPE
	SYNTAX INTEGER
	ACCESS read-write
	STATUS mandatory
	DESCRIPTION "&<caiUxsA2.1273>Current critical threshold for the number of semaphores in the set monitoring of the semaphore watcher. This value represents a rising threshold and must be greater than 0, but cannot be less than the warning threshold."
	::= { uxsA2StatusSEMEntry 13 }

uxsA2StatusSEMNSemsMonitor OBJECT-TYPE
	SYNTAX INTEGER {
		do-not-monitor(1),
		warning-only(2),
		critical-only(3),
		both(4)
	}
	ACCESS read-write
	STATUS mandatory
	DESCRIPTION "&<caiUxsA2.1274>Current monitor level for the number of semaphores in the set monitoring of the semaphore watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusSEMEntry 14 }

uxsA2StatusSEMNSemsStatus OBJECT-TYPE
	SYNTAX INTEGER {
		unknown(1),
		ok(2),
		warning(3),
		critical(4)
	}
	ACCESS read-only
	STATUS mandatory
	DESCRIPTION "&<caiUxsA2.1275>Current status for the number of semaphores in the set monitoring of the semaphore watcher: 1 (unknown) - An error occurred during data collection, 2 (ok) - The resource is operating within the defined limits or status evaluation is turned off and/or polling is disabled, 3 (warning) - The resource has breached the warning threshold, 4 (critical) - The resource has breached the critical threshold."
	::= { uxsA2StatusSEMEntry 15 }

uxsA2StatusSEMLossAction OBJECT-TYPE
	SYNTAX INTEGER {
		remove(1),
		up(2),
		down-warning(3),
		down-critical(4)
	}
	ACCESS read-write
	STATUS mandatory
	DESCRIPTION "&<caiUxsA2.1276>Current loss action for the semaphore watcher. Specifies the action to take if the monitored semaphore is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusSEMEntry 16 }

uxsA2StatusSEMLossStatus OBJECT-TYPE
	SYNTAX INTEGER {
		unknown(1),
		up(2),
		down-warning(3),
		down-critical(4)
	}
	ACCESS read-only
	STATUS mandatory
	DESCRIPTION "&<caiUxsA2.1277>Current loss status of the semaphore watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusSEMEntry 17 }

uxsA2StatusSEMCallBackRef OBJECT-TYPE
	SYNTAX DisplayString
	ACCESS read-only
	STATUS mandatory
	DESCRIPTION "&<caiUxsA2.1278>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusSEMEntry 18 }

uxsA2StatusSEMButton OBJECT-TYPE
	SYNTAX INTEGER {
		none(1),
		remove(2)
	}
	ACCESS read-write
	STATUS mandatory
	DESCRIPTION "&<caiUxsA2.1279>This attribute is used to remove the semaphore watcher. If set to 2 (remove), the agent removes the watcher from the table. This attribute cannot be set to 1 (none)."
	DEFVAL { 1 }
	::= { uxsA2StatusSEMEntry 19 }

--
-- The StatusMQ Group
--

uxsA2StatusMQCount OBJECT-TYPE
	SYNTAX INTEGER
	ACCESS read-only
	STATUS mandatory
	DESCRIPTION "&<caiUxsA2.1280>Number of entries in the message queue status table."
	::= { uxsA2StatusMQGroup 1 }

uxsA2StatusMQTable OBJECT-TYPE
	SYNTAX SEQUENCE OF UxsA2StatusMQEntry
	ACCESS not-accessible
	STATUS mandatory
	DESCRIPTION "&<caiUxsA2.1281>The message queue status table containing details about the currently configured message queue watchers."
	::= { uxsA2StatusMQGroup 2 }

uxsA2StatusMQEntry OBJECT-TYPE
	SYNTAX UxsA2StatusMQEntry
	ACCESS not-accessible
	STATUS mandatory
	DESCRIPTION "&<caiUxsA2.1282>Entry in the message queue status table."
	INDEX {
		uxsA2StatusMQId
	}
	::= { uxsA2StatusMQTable 1 }

UxsA2StatusMQEntry ::= SEQUENCE {
	uxsA2StatusMQId DisplayString,
	uxsA2StatusMQDescription DisplayString,
	uxsA2StatusMQAutoWatcherName DisplayString,
	uxsA2StatusMQAggLagValue INTEGER,
	uxsA2StatusMQAggLag INTEGER,
	uxsA2StatusMQAggStatus INTEGER,
	uxsA2StatusMQKey DisplayString,
	uxsA2StatusMQMode DisplayString,
	uxsA2StatusMQOwner DisplayString,
	uxsA2StatusMQGrp DisplayString,
	uxsA2StatusMQCBytesTotal DisplayString,
	uxsA2StatusMQCBytesValue DisplayString,
	uxsA2StatusMQCBytesWarnValue DisplayString,
	uxsA2StatusMQCBytesCritValue DisplayString,
	uxsA2StatusMQCBytesWarn DisplayString,
	uxsA2StatusMQCBytesCrit DisplayString,
	uxsA2StatusMQCBytesMonitor INTEGER,
	uxsA2StatusMQCBytesStatus INTEGER,
	uxsA2StatusMQQNumValue INTEGER,
	uxsA2StatusMQQNumWarn INTEGER,
	uxsA2StatusMQQNumCrit INTEGER,
	uxsA2StatusMQQNumMonitor INTEGER,
	uxsA2StatusMQQNumStatus INTEGER,
	uxsA2StatusMQLossAction INTEGER,
	uxsA2StatusMQLossStatus INTEGER,
	uxsA2StatusMQCallBackRef DisplayString,
	uxsA2StatusMQButton INTEGER
}

uxsA2StatusMQId OBJECT-TYPE
	SYNTAX DisplayString
	ACCESS read-only
	STATUS mandatory
	DESCRIPTION "&<caiUxsA2.1283>Name of the message queue identifier. The number of used and totally available message queue identifiers is monitored in the OS Resource Parameters group. Note that resource limits can be set dynamically on Solaris 10: The total value is the current limit for a privileged process in the project the agent belongs to."
	::= { uxsA2StatusMQEntry 1 }

uxsA2StatusMQDescription OBJECT-TYPE
	SYNTAX DisplayString
	ACCESS read-write
	STATUS mandatory
	DESCRIPTION "&<caiUxsA2.1284>Current description for the message queue watcher."
	::= { uxsA2StatusMQEntry 2 }

uxsA2StatusMQAutoWatcherName OBJECT-TYPE
	SYNTAX DisplayString
	ACCESS read-only
	STATUS mandatory
	DESCRIPTION "&<caiUxsA2.1285>Name of the message queue auto watcher which automatically created this watcher. This attribute is left blank if the watcher was added manually."
	::= { uxsA2StatusMQEntry 3 }

uxsA2StatusMQAggLagValue OBJECT-TYPE
	SYNTAX INTEGER
	ACCESS read-only
	STATUS mandatory
	DESCRIPTION "&<caiUxsA2.1286>Current aggregate lag value of the message queue watcher. Indicates the consecutive number of times at which any status was not in the ok state. The aggregate status changes from ok as soon as the aggregate lag value reaches the configured value."
	::= { uxsA2StatusMQEntry 4 }

uxsA2StatusMQAggLag OBJECT-TYPE
	SYNTAX INTEGER
	ACCESS read-write
	STATUS mandatory
	DESCRIPTION "&<caiUxsA2.1287>Current aggregate lag setting for the message queue watcher. Specifies the consecutive number of times at which any status is not in the ok state, before the aggregate status changes. This value must be greater than 0."
	::= { uxsA2StatusMQEntry 5 }

uxsA2StatusMQAggStatus OBJECT-TYPE
	SYNTAX INTEGER {
		unknown(1),
		ok(2),
		warning(3),
		critical(4),
		passive(5)
	}
	ACCESS read-only
	STATUS mandatory
	DESCRIPTION "&<caiUxsA2.1288>Current aggregate status of the message queue watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { uxsA2StatusMQEntry 6 }

uxsA2StatusMQKey OBJECT-TYPE
	SYNTAX DisplayString
	ACCESS read-only
	STATUS mandatory
	DESCRIPTION "&<caiUxsA2.1289>Key of the message queue."
	::= { uxsA2StatusMQEntry 7 }

uxsA2StatusMQMode OBJECT-TYPE
	SYNTAX DisplayString
	ACCESS read-only
	STATUS mandatory
	DESCRIPTION "&<caiUxsA2.1290>Access mode and flags of the message queue."
	::= { uxsA2StatusMQEntry 8 }

uxsA2StatusMQOwner OBJECT-TYPE
	SYNTAX DisplayString
	ACCESS read-only
	STATUS mandatory
	DESCRIPTION "&<caiUxsA2.1291>User name of the owner of the message queue. On Solaris 10 machines the name of the zone the resource belongs to is added to the attribute: <owner>@<zone>."
	::= { uxsA2StatusMQEntry 9 }

uxsA2StatusMQGrp OBJECT-TYPE
	SYNTAX DisplayString
	ACCESS read-only
	STATUS mandatory
	DESCRIPTION "&<caiUxsA2.1292>Group name of the owner of the message queue."
	::= { uxsA2StatusMQEntry 10 }

uxsA2StatusMQCBytesTotal OBJECT-TYPE
	SYNTAX DisplayString
	ACCESS read-only
	STATUS mandatory
	DESCRIPTION "&<caiUxsA2.1293>Maximum number of bytes allowed in messages outstanding on the associated message queue."
	DEFVAL { "0" }
	::= { uxsA2StatusMQEntry 11 }

uxsA2StatusMQCBytesValue OBJECT-TYPE
	SYNTAX DisplayString
	ACCESS read-only
	STATUS mandatory
	DESCRIPTION "&<caiUxsA2.1294>Current value, in bytes, for the number of bytes in messages currently outstanding monitoring of the message queue watcher."
	DEFVAL { "0" }
	::= { uxsA2StatusMQEntry 12 }

uxsA2StatusMQCBytesWarnValue OBJECT-TYPE
	SYNTAX DisplayString
	ACCESS read-only
	STATUS mandatory
	DESCRIPTION "&<caiUxsA2.1295>Active warning threshold, in bytes, as derived from the configured value for the number of bytes in messages currently outstanding monitoring of the message queue watcher. This value represents a rising threshold and must be greater than 0.0, less than or equal to the total value (maximum capacity) of the monitored resource as specified in uxsA2StatusMQCBytesTotal, but cannot be greater than the active critical threshold. These constraints will be maintained by the agent during all configuration actions."
	::= { uxsA2StatusMQEntry 13 }

uxsA2StatusMQCBytesCritValue OBJECT-TYPE
	SYNTAX DisplayString
	ACCESS read-only
	STATUS mandatory
	DESCRIPTION "&<caiUxsA2.1296>Active critical threshold, in bytes, as derived from the configured value for the number of bytes in messages currently outstanding monitoring of the message queue watcher. This value represents a rising threshold and must be greater than 0.0, less than or equal to the total value (maximum capacity) of the monitored resource as specified in uxsA2StatusMQCBytesTotal, but cannot be less than the active warning threshold. These constraints will be maintained by the agent during all configuration actions."
	::= { uxsA2StatusMQEntry 14 }

uxsA2StatusMQCBytesWarn OBJECT-TYPE
	SYNTAX DisplayString
	ACCESS read-write
	STATUS mandatory
	DESCRIPTION "&<caiUxsA2.1297>Configured warning threshold from which the active warning threshold is derived for the number of bytes in messages currently outstanding monitoring of the message queue watcher. The threshold can be specified as either an absolute value (n) or a percentage (n%). It can also be specified as the absolute value left free (nF). The value of uxsA2StatusMQCBytesTotal will be the reference value for n% and nF notations."
	::= { uxsA2StatusMQEntry 15 }

uxsA2StatusMQCBytesCrit OBJECT-TYPE
	SYNTAX DisplayString
	ACCESS read-write
	STATUS mandatory
	DESCRIPTION "&<caiUxsA2.1298>Configured critical threshold from which the active critical threshold is derived for the number of bytes in messages currently outstanding monitoring of the message queue watcher. The threshold can be specified as either an absolute value (n) or a percentage (n%). It can also be specified as the absolute value left free (nF). The value of uxsA2StatusMQCBytesTotal will be the reference value for n% and nF notations."
	::= { uxsA2StatusMQEntry 16 }

uxsA2StatusMQCBytesMonitor OBJECT-TYPE
	SYNTAX INTEGER {
		do-not-monitor(1),
		warning-only(2),
		critical-only(3),
		both(4)
	}
	ACCESS read-write
	STATUS mandatory
	DESCRIPTION "&<caiUxsA2.1299>Current monitor level for the number of bytes in messages currently outstanding monitoring of the message queue watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusMQEntry 17 }

uxsA2StatusMQCBytesStatus OBJECT-TYPE
	SYNTAX INTEGER {
		unknown(1),
		ok(2),
		warning(3),
		critical(4)
	}
	ACCESS read-only
	STATUS mandatory
	DESCRIPTION "&<caiUxsA2.1300>Current status for the number of bytes in messages currently outstanding monitoring of the message queue watcher: 1 (unknown) - An error occurred during data collection, 2 (ok) - The resource is operating within the defined limits or status evaluation is turned off and/or polling is disabled, 3 (warning) - The resource has breached the warning threshold, 4 (critical) - The resource has breached the critical threshold."
	::= { uxsA2StatusMQEntry 18 }

uxsA2StatusMQQNumValue OBJECT-TYPE
	SYNTAX INTEGER
	ACCESS read-only
	STATUS mandatory
	DESCRIPTION "&<caiUxsA2.1301>Current value for the number of messages currently outstanding monitoring of the message queue watcher."
	::= { uxsA2StatusMQEntry 19 }

uxsA2StatusMQQNumWarn OBJECT-TYPE
	SYNTAX INTEGER
	ACCESS read-write
	STATUS mandatory
	DESCRIPTION "&<caiUxsA2.1302>Current warning threshold for the number of messages currently outstanding monitoring of the message queue watcher. This value represents a rising threshold and must be greater than 0, but cannot be greater than the critical threshold."
	::= { uxsA2StatusMQEntry 20 }

uxsA2StatusMQQNumCrit OBJECT-TYPE
	SYNTAX INTEGER
	ACCESS read-write
	STATUS mandatory
	DESCRIPTION "&<caiUxsA2.1303>Current critical threshold for the number of messages currently outstanding monitoring of the message queue watcher. This value represents a rising threshold and must be greater than 0, but cannot be less than the warning threshold."
	::= { uxsA2StatusMQEntry 21 }

uxsA2StatusMQQNumMonitor OBJECT-TYPE
	SYNTAX INTEGER {
		do-not-monitor(1),
		warning-only(2),
		critical-only(3),
		both(4)
	}
	ACCESS read-write
	STATUS mandatory
	DESCRIPTION "&<caiUxsA2.1304>Current monitor level for the number of messages currently outstanding monitoring of the message queue watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { uxsA2StatusMQEntry 22 }

uxsA2StatusMQQNumStatus OBJECT-TYPE
	SYNTAX INTEGER {
		unknown(1),
		ok(2),
		warning(3),
		critical(4)
	}
	ACCESS read-only
	STATUS mandatory
	DESCRIPTION "&<caiUxsA2.1305>Current status for the number of messages currently outstanding monitoring of the message queue watcher: 1 (unknown) - An error occurred during data collection, 2 (ok) - The resource is operating within the defined limits or status evaluation is turned off and/or polling is disabled, 3 (warning) - The resource has breached the warning threshold, 4 (critical) - The resource has breached the critical threshold."
	::= { uxsA2StatusMQEntry 23 }

uxsA2StatusMQLossAction OBJECT-TYPE
	SYNTAX INTEGER {
		remove(1),
		up(2),
		down-warning(3),
		down-critical(4)
	}
	ACCESS read-write
	STATUS mandatory
	DESCRIPTION "&<caiUxsA2.1306>Current loss action for the message queue watcher. Specifies the action to take if the monitored message queue is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusMQEntry 24 }

uxsA2StatusMQLossStatus OBJECT-TYPE
	SYNTAX INTEGER {
		unknown(1),
		up(2),
		down-warning(3),
		down-critical(4)
	}
	ACCESS read-only
	STATUS mandatory
	DESCRIPTION "&<caiUxsA2.1307>Current loss status of the message queue watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusMQEntry 25 }

uxsA2StatusMQCallBackRef OBJECT-TYPE
	SYNTAX DisplayString
	ACCESS read-only
	STATUS mandatory
	DESCRIPTION "&<caiUxsA2.1308>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusMQEntry 26 }

uxsA2StatusMQButton OBJECT-TYPE
	SYNTAX INTEGER {
		none(1),
		remove(2)
	}
	ACCESS read-write
	STATUS mandatory
	DESCRIPTION "&<caiUxsA2.1309>This attribute is used to remove the message queue watcher. If set to 2 (remove), the agent removes the watcher from the table. This attribute cannot be set to 1 (none)."
	DEFVAL { 1 }
	::= { uxsA2StatusMQEntry 27 }

--
-- The StatusHardwr Group
--

uxsA2StatusHardwrCount OBJECT-TYPE
	SYNTAX INTEGER
	ACCESS read-only
	STATUS mandatory
	DESCRIPTION "&<caiUxsA2.1310>Number of entries in the hardware resource status table."
	::= { uxsA2StatusHardwrGroup 1 }

uxsA2StatusHardwrTable OBJECT-TYPE
	SYNTAX SEQUENCE OF UxsA2StatusHardwrEntry
	ACCESS not-accessible
	STATUS mandatory
	DESCRIPTION "&<caiUxsA2.1311>The hardware resource status table containing details about the currently configured hardware resource watchers."
	::= { uxsA2StatusHardwrGroup 2 }

uxsA2StatusHardwrEntry OBJECT-TYPE
	SYNTAX UxsA2StatusHardwrEntry
	ACCESS not-accessible
	STATUS mandatory
	DESCRIPTION "&<caiUxsA2.1312>Entry in the hardware resource status table."
	INDEX {
		uxsA2StatusHardwrResName,
		uxsA2StatusHardwrResSubName,
		uxsA2StatusHardwrInstName
	}
	::= { uxsA2StatusHardwrTable 1 }

UxsA2StatusHardwrEntry ::= SEQUENCE {
	uxsA2StatusHardwrResName DisplayString,
	uxsA2StatusHardwrResSubName DisplayString,
	uxsA2StatusHardwrInstName DisplayString,
	uxsA2StatusHardwrDescription DisplayString,
	uxsA2StatusHardwrAutoWatcherName DisplayString,
	uxsA2StatusHardwrAggStatus INTEGER,
	uxsA2StatusHardwrCollectScript DisplayString,
	uxsA2StatusHardwrCollectArgs DisplayString,
	uxsA2StatusHardwrUserName DisplayString,
	uxsA2StatusHardwrSkipCount INTEGER,
	uxsA2StatusHardwrInfoMsg DisplayString,
	uxsA2StatusHardwrErrorMsg DisplayString,
	uxsA2StatusHardwrErrorMsgPattern DisplayString,
	uxsA2StatusHardwrErrorMsgMonitor INTEGER,
	uxsA2StatusHardwrErrorMsgStatus INTEGER,
	uxsA2StatusHardwrResultValue DisplayString,
	uxsA2StatusHardwrResultLagValue INTEGER,
	uxsA2StatusHardwrResultLag INTEGER,
	uxsA2StatusHardwrResultWarnMin DisplayString,
	uxsA2StatusHardwrResultWarnMax DisplayString,
	uxsA2StatusHardwrResultCritMin DisplayString,
	uxsA2StatusHardwrResultCritMax DisplayString,
	uxsA2StatusHardwrResultMonitor INTEGER,
	uxsA2StatusHardwrResultStatus INTEGER,
	uxsA2StatusHardwrLossAction INTEGER,
	uxsA2StatusHardwrLossStatus INTEGER,
	uxsA2StatusHardwrCallBackRef DisplayString,
	uxsA2StatusHardwrButton INTEGER
}

uxsA2StatusHardwrResName OBJECT-TYPE
	SYNTAX DisplayString
	ACCESS read-only
	STATUS mandatory
	DESCRIPTION "&<caiUxsA2.1313>The name of the resource. This is the first index used by the agent in the different MIB tables for this resource (e.g. PowerSupply)."
	::= { uxsA2StatusHardwrEntry 1 }

uxsA2StatusHardwrResSubName OBJECT-TYPE
	SYNTAX DisplayString
	ACCESS read-only
	STATUS mandatory
	DESCRIPTION "&<caiUxsA2.1314>The subname of the resource. This is the second index used by the agent in the different MIB tables for this resource (e.g. Voltage)."
	::= { uxsA2StatusHardwrEntry 2 }

uxsA2StatusHardwrInstName OBJECT-TYPE
	SYNTAX DisplayString
	ACCESS read-only
	STATUS mandatory
	DESCRIPTION "&<caiUxsA2.1315>If a resource supports instances, this must be the name of an instance. The instance name is the third index used by the agent in the different MIB tables for this resource. If a resource does not support instances, <none> should be used as third index."
	::= { uxsA2StatusHardwrEntry 3 }

uxsA2StatusHardwrDescription OBJECT-TYPE
	SYNTAX DisplayString
	ACCESS read-write
	STATUS mandatory
	DESCRIPTION "&<caiUxsA2.1316>Current description for the hardware resource watcher."
	::= { uxsA2StatusHardwrEntry 4 }

uxsA2StatusHardwrAutoWatcherName OBJECT-TYPE
	SYNTAX DisplayString
	ACCESS read-only
	STATUS mandatory
	DESCRIPTION "&<caiUxsA2.1317>Name of the hardware resource auto watcher which automatically created this watcher. This attribute is left blank if the watcher was added manually."
	::= { uxsA2StatusHardwrEntry 5 }

uxsA2StatusHardwrAggStatus OBJECT-TYPE
	SYNTAX INTEGER {
		unknown(1),
		ok(2),
		warning(3),
		critical(4),
		passive(5)
	}
	ACCESS read-only
	STATUS mandatory
	DESCRIPTION "&<caiUxsA2.1318>Current aggregate status of the hardware resource watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { uxsA2StatusHardwrEntry 6 }

uxsA2StatusHardwrCollectScript OBJECT-TYPE
	SYNTAX DisplayString
	ACCESS read-only
	STATUS mandatory
	DESCRIPTION "&<caiUxsA2.1319>This attribute can only be configured in the 'Generic.ini' file. Script to be called to retrieve the value for a resource. If a resource supports instances, the script needs to gather the values for all required instances in one call. The script must be in a dedicated directory (agents/config/caiUxsA2). Any path element will be ignored."
	::= { uxsA2StatusHardwrEntry 7 }

uxsA2StatusHardwrCollectArgs OBJECT-TYPE
	SYNTAX DisplayString
	ACCESS read-only
	STATUS mandatory
	DESCRIPTION "&<caiUxsA2.1320>This attribute can only be configured in the 'Generic.ini' file. Arguments passed to the collect script. If a resource supports instances, the names of all monitored instances are always appended and passed as last parameters."
	::= { uxsA2StatusHardwrEntry 8 }

uxsA2StatusHardwrUserName OBJECT-TYPE
	SYNTAX DisplayString
	ACCESS read-only
	STATUS mandatory
	DESCRIPTION "&<caiUxsA2.1321>This attribute can only be configured in the 'Generic.ini' file. Specifies the user ID to be used for the execution of any script."
	::= { uxsA2StatusHardwrEntry 9 }

uxsA2StatusHardwrSkipCount OBJECT-TYPE
	SYNTAX INTEGER
	ACCESS read-only
	STATUS mandatory
	DESCRIPTION "&<caiUxsA2.1322>This attribute can only be configured in the 'Generic.ini' file. Current skip count for the hardware resource watcher. Specifies the number of consecutive poll intervals that should be passed without evaluating the watcher. This value must be equal to or greater than 0."
	::= { uxsA2StatusHardwrEntry 10 }

uxsA2StatusHardwrInfoMsg OBJECT-TYPE
	SYNTAX DisplayString
	ACCESS read-only
	STATUS mandatory
	DESCRIPTION "&<caiUxsA2.1323>The info message string the agent collected from the script. The info message must always start with an arbitrary but unique time prefix. If there is no change in the info message from one poll to the next, the agent will not evaluate the corresponding watcher! The agent uses <...PENDING...> as value for the info message as long as the corresponding collect script of this resource is still running."
	::= { uxsA2StatusHardwrEntry 11 }

uxsA2StatusHardwrErrorMsg OBJECT-TYPE
	SYNTAX DisplayString
	ACCESS read-only
	STATUS mandatory
	DESCRIPTION "&<caiUxsA2.1324>The error message string the agent collected from the script. If the script did not finish and has been killed by the agent, the agent uses <...TIMEOUT...> as value for the error message. Similar, if the script could not be started, the agent uses <...ERROR...> as value for the error message."
	::= { uxsA2StatusHardwrEntry 12 }

uxsA2StatusHardwrErrorMsgPattern OBJECT-TYPE
	SYNTAX DisplayString
	ACCESS read-write
	STATUS mandatory
	DESCRIPTION "&<caiUxsA2.1325>An extended regular expression. If the error message matches this pattern, the error message status changes according to the error message monitor policy."
	::= { uxsA2StatusHardwrEntry 13 }

uxsA2StatusHardwrErrorMsgMonitor OBJECT-TYPE
	SYNTAX INTEGER {
		do-not-monitor(1),
		down-warning(2),
		down-critical(3)
	}
	ACCESS read-write
	STATUS mandatory
	DESCRIPTION "&<caiUxsA2.1326>Current monitor level for the error message monitoring of the hardware resource watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusHardwrEntry 14 }

uxsA2StatusHardwrErrorMsgStatus OBJECT-TYPE
	SYNTAX INTEGER {
		unknown(1),
		up(2),
		down-warning(3),
		down-critical(4)
	}
	ACCESS read-only
	STATUS mandatory
	DESCRIPTION "&<caiUxsA2.1327>Current status for the error message monitoring of the hardware resource watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusHardwrEntry 15 }

uxsA2StatusHardwrResultValue OBJECT-TYPE
	SYNTAX DisplayString
	ACCESS read-only
	STATUS mandatory
	DESCRIPTION "&<caiUxsA2.1328>Current value for the result monitoring of the hardware resource watcher."
	DEFVAL { "0" }
	::= { uxsA2StatusHardwrEntry 16 }

uxsA2StatusHardwrResultLagValue OBJECT-TYPE
	SYNTAX INTEGER
	ACCESS read-only
	STATUS mandatory
	DESCRIPTION "&<caiUxsA2.1329>Current number of consecutive threshold breaches for the result monitoring of the hardware resource watcher. The result state changes from ok as soon as the lag value reaches the configured value. The state reverts back to ok if a threshold is no longer breached."
	::= { uxsA2StatusHardwrEntry 17 }

uxsA2StatusHardwrResultLag OBJECT-TYPE
	SYNTAX INTEGER
	ACCESS read-write
	STATUS mandatory
	DESCRIPTION "&<caiUxsA2.1330>Current lag setting for the result monitoring of the hardware resource watcher. Specifies the number of consecutive threshold breaches on which the result state changes. This value must be greater than 0."
	::= { uxsA2StatusHardwrEntry 18 }

uxsA2StatusHardwrResultWarnMin OBJECT-TYPE
	SYNTAX DisplayString
	ACCESS read-write
	STATUS mandatory
	DESCRIPTION "&<caiUxsA2.1331>Current warning minimum threshold for the result monitoring of the hardware resource watcher. This value represents a declining threshold and must be equal to or greater than 0.0, equal to or greater than the critical minimum threshold, but cannot be greater than the warning maximum threshold. A value of -1 disables the evaluation of this threshold."
	DEFVAL { "-2" }
	::= { uxsA2StatusHardwrEntry 19 }

uxsA2StatusHardwrResultWarnMax OBJECT-TYPE
	SYNTAX DisplayString
	ACCESS read-write
	STATUS mandatory
	DESCRIPTION "&<caiUxsA2.1332>Current warning maximum threshold for the result monitoring of the hardware resource watcher. This value represents a rising threshold and must be equal to or greater than 0.0, equal to or greater than the warning minimum threshold, but cannot be greater than the critical maximum threshold. A value of -1 disables the evaluation of this threshold."
	DEFVAL { "-2" }
	::= { uxsA2StatusHardwrEntry 20 }

uxsA2StatusHardwrResultCritMin OBJECT-TYPE
	SYNTAX DisplayString
	ACCESS read-write
	STATUS mandatory
	DESCRIPTION "&<caiUxsA2.1333>Current critical minimum threshold for the result monitoring of the hardware resource watcher. This value represents a declining threshold and must be equal to or greater than 0.0, but cannot be greater than the warning minimum threshold. A value of -1 disables the evaluation of this threshold."
	DEFVAL { "-2" }
	::= { uxsA2StatusHardwrEntry 21 }

uxsA2StatusHardwrResultCritMax OBJECT-TYPE
	SYNTAX DisplayString
	ACCESS read-write
	STATUS mandatory
	DESCRIPTION "&<caiUxsA2.1334>Current critical maximum threshold for the result monitoring of the hardware resource watcher. This value represents a rising threshold and must be equal to or greater than 0.0, but cannot be less than the warning maximum threshold. A value of -1 disables the evaluation of this threshold."
	DEFVAL { "-2" }
	::= { uxsA2StatusHardwrEntry 22 }

uxsA2StatusHardwrResultMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.1335>Current monitor level for the result monitoring of the hardware resource watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2StatusHardwrEntry 23 }

uxsA2StatusHardwrResultStatus OBJECT-TYPE
	SYNTAX INTEGER {
		unknown(1),
		up(2),
		down-warning(3),
		down-critical(4)
	}
	ACCESS read-only
	STATUS mandatory
	DESCRIPTION "&<caiUxsA2.1336>Current status for the result monitoring of the hardware resource watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusHardwrEntry 24 }

uxsA2StatusHardwrLossAction OBJECT-TYPE
	SYNTAX INTEGER {
		remove(1),
		up(2),
		down-warning(3),
		down-critical(4)
	}
	ACCESS read-write
	STATUS mandatory
	DESCRIPTION "&<caiUxsA2.1337>Current loss action for the hardware resource watcher. Specifies the action to take if the monitored hardware resource is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusHardwrEntry 25 }

uxsA2StatusHardwrLossStatus OBJECT-TYPE
	SYNTAX INTEGER {
		unknown(1),
		up(2),
		down-warning(3),
		down-critical(4)
	}
	ACCESS read-only
	STATUS mandatory
	DESCRIPTION "&<caiUxsA2.1338>Current loss status of the hardware resource watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusHardwrEntry 26 }

uxsA2StatusHardwrCallBackRef OBJECT-TYPE
	SYNTAX DisplayString
	ACCESS read-only
	STATUS mandatory
	DESCRIPTION "&<caiUxsA2.1339>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusHardwrEntry 27 }

uxsA2StatusHardwrButton OBJECT-TYPE
	SYNTAX INTEGER {
		none(1),
		remove(2),
		reset(3)
	}
	ACCESS read-write
	STATUS mandatory
	DESCRIPTION "&<caiUxsA2.1340>This attribute is used to remove the hardware resource watcher. Additionally, this attribute is used to reset the hardware resource monitoring watcher. If set to 3 (reset), the status of the watcher is set to ok. The watcher will be evaluated again at the next poll if the info message has changed. If set to 2 (remove), the agent removes the watcher from the table. This attribute cannot be set to 1 (none)."
	DEFVAL { 1 }
	::= { uxsA2StatusHardwrEntry 28 }

--
-- The StatusProgrm Group
--

uxsA2StatusProgrmCount OBJECT-TYPE
	SYNTAX INTEGER
	ACCESS read-only
	STATUS mandatory
	DESCRIPTION "&<caiUxsA2.1341>Number of entries in the programmable resource status table."
	::= { uxsA2StatusProgrmGroup 1 }

uxsA2StatusProgrmTable OBJECT-TYPE
	SYNTAX SEQUENCE OF UxsA2StatusProgrmEntry
	ACCESS not-accessible
	STATUS mandatory
	DESCRIPTION "&<caiUxsA2.1342>The programmable resource status table containing details about the currently configured programmable resource watchers."
	::= { uxsA2StatusProgrmGroup 2 }

uxsA2StatusProgrmEntry OBJECT-TYPE
	SYNTAX UxsA2StatusProgrmEntry
	ACCESS not-accessible
	STATUS mandatory
	DESCRIPTION "&<caiUxsA2.1343>Entry in the programmable resource status table."
	INDEX {
		uxsA2StatusProgrmResName,
		uxsA2StatusProgrmResSubName,
		uxsA2StatusProgrmInstName
	}
	::= { uxsA2StatusProgrmTable 1 }

UxsA2StatusProgrmEntry ::= SEQUENCE {
	uxsA2StatusProgrmResName DisplayString,
	uxsA2StatusProgrmResSubName DisplayString,
	uxsA2StatusProgrmInstName DisplayString,
	uxsA2StatusProgrmDescription DisplayString,
	uxsA2StatusProgrmAutoWatcherName DisplayString,
	uxsA2StatusProgrmAggStatus INTEGER,
	uxsA2StatusProgrmCollectScript DisplayString,
	uxsA2StatusProgrmCollectArgs DisplayString,
	uxsA2StatusProgrmUserName DisplayString,
	uxsA2StatusProgrmSkipCount INTEGER,
	uxsA2StatusProgrmInfoMsg DisplayString,
	uxsA2StatusProgrmErrorMsg DisplayString,
	uxsA2StatusProgrmErrorMsgPattern DisplayString,
	uxsA2StatusProgrmErrorMsgMonitor INTEGER,
	uxsA2StatusProgrmErrorMsgStatus INTEGER,
	uxsA2StatusProgrmResultValue DisplayString,
	uxsA2StatusProgrmResultLagValue INTEGER,
	uxsA2StatusProgrmResultLag INTEGER,
	uxsA2StatusProgrmResultWarnMin DisplayString,
	uxsA2StatusProgrmResultWarnMax DisplayString,
	uxsA2StatusProgrmResultCritMin DisplayString,
	uxsA2StatusProgrmResultCritMax DisplayString,
	uxsA2StatusProgrmResultMonitor INTEGER,
	uxsA2StatusProgrmResultStatus INTEGER,
	uxsA2StatusProgrmLossAction INTEGER,
	uxsA2StatusProgrmLossStatus INTEGER,
	uxsA2StatusProgrmCallBackRef DisplayString,
	uxsA2StatusProgrmButton INTEGER
}

uxsA2StatusProgrmResName OBJECT-TYPE
	SYNTAX DisplayString
	ACCESS read-only
	STATUS mandatory
	DESCRIPTION "&<caiUxsA2.1344>The name of the resource. This is the first index used by the agent in the different MIB tables for this resource (e.g. PowerSupply)."
	::= { uxsA2StatusProgrmEntry 1 }

uxsA2StatusProgrmResSubName OBJECT-TYPE
	SYNTAX DisplayString
	ACCESS read-only
	STATUS mandatory
	DESCRIPTION "&<caiUxsA2.1345>The subname of the resource. This is the second index used by the agent in the different MIB tables for this resource (e.g. Voltage)."
	::= { uxsA2StatusProgrmEntry 2 }

uxsA2StatusProgrmInstName OBJECT-TYPE
	SYNTAX DisplayString
	ACCESS read-only
	STATUS mandatory
	DESCRIPTION "&<caiUxsA2.1346>If a resource supports instances, this must be the name of an instance. The instance name is the third index used by the agent in the different MIB tables for this resource. If a resource does not support instances, <none> should be used as third index."
	::= { uxsA2StatusProgrmEntry 3 }

uxsA2StatusProgrmDescription OBJECT-TYPE
	SYNTAX DisplayString
	ACCESS read-write
	STATUS mandatory
	DESCRIPTION "&<caiUxsA2.1347>Current description for the programmable resource watcher."
	::= { uxsA2StatusProgrmEntry 4 }

uxsA2StatusProgrmAutoWatcherName OBJECT-TYPE
	SYNTAX DisplayString
	ACCESS read-only
	STATUS mandatory
	DESCRIPTION "&<caiUxsA2.1348>Name of the programmable resource auto watcher which automatically created this watcher. This attribute is left blank if the watcher was added manually."
	::= { uxsA2StatusProgrmEntry 5 }

uxsA2StatusProgrmAggStatus OBJECT-TYPE
	SYNTAX INTEGER {
		unknown(1),
		ok(2),
		warning(3),
		critical(4),
		passive(5)
	}
	ACCESS read-only
	STATUS mandatory
	DESCRIPTION "&<caiUxsA2.1349>Current aggregate status of the programmable resource watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { uxsA2StatusProgrmEntry 6 }

uxsA2StatusProgrmCollectScript OBJECT-TYPE
	SYNTAX DisplayString
	ACCESS read-only
	STATUS mandatory
	DESCRIPTION "&<caiUxsA2.1350>This attribute can only be configured in the 'Generic.ini' file. Script to be called to retrieve the value for a resource. If a resource supports instances, the script needs to gather the values for all required instances in one call. The script must be in a dedicated directory (agents/config/caiUxsA2). Any path element will be ignored."
	::= { uxsA2StatusProgrmEntry 7 }

uxsA2StatusProgrmCollectArgs OBJECT-TYPE
	SYNTAX DisplayString
	ACCESS read-only
	STATUS mandatory
	DESCRIPTION "&<caiUxsA2.1351>This attribute can only be configured in the 'Generic.ini' file. Arguments passed to the collect script. If a resource supports instances, the names of all monitored instances are always appended and passed as last parameters."
	::= { uxsA2StatusProgrmEntry 8 }

uxsA2StatusProgrmUserName OBJECT-TYPE
	SYNTAX DisplayString
	ACCESS read-only
	STATUS mandatory
	DESCRIPTION "&<caiUxsA2.1352>This attribute can only be configured in the 'Generic.ini' file. Specifies the user ID to be used for the execution of any script."
	::= { uxsA2StatusProgrmEntry 9 }

uxsA2StatusProgrmSkipCount OBJECT-TYPE
	SYNTAX INTEGER
	ACCESS read-only
	STATUS mandatory
	DESCRIPTION "&<caiUxsA2.1353>This attribute can only be configured in the 'Generic.ini' file. Current skip count for the programmable resource watcher. Specifies the number of consecutive poll intervals that should be passed without evaluating the watcher. This value must be equal to or greater than 0."
	::= { uxsA2StatusProgrmEntry 10 }

uxsA2StatusProgrmInfoMsg OBJECT-TYPE
	SYNTAX DisplayString
	ACCESS read-only
	STATUS mandatory
	DESCRIPTION "&<caiUxsA2.1354>The info message string the agent collected from the script. The info message must always start with an arbitrary but unique time prefix. If there is no change in the info message from one poll to the next, the agent will not evaluate the corresponding watcher! The agent uses <...PENDING...> as value for the info message as long as the corresponding collect script of this resource is still running."
	::= { uxsA2StatusProgrmEntry 11 }

uxsA2StatusProgrmErrorMsg OBJECT-TYPE
	SYNTAX DisplayString
	ACCESS read-only
	STATUS mandatory
	DESCRIPTION "&<caiUxsA2.1355>The error message string the agent collected from the script. If the script did not finish and has been killed by the agent, the agent uses <...TIMEOUT...> as value for the error message. Similar, if the script could not be started, the agent uses <...ERROR...> as value for the error message."
	::= { uxsA2StatusProgrmEntry 12 }

uxsA2StatusProgrmErrorMsgPattern OBJECT-TYPE
	SYNTAX DisplayString
	ACCESS read-write
	STATUS mandatory
	DESCRIPTION "&<caiUxsA2.1356>An extended regular expression. If the error message matches this pattern, the error message status changes according to the error message monitor policy."
	::= { uxsA2StatusProgrmEntry 13 }

uxsA2StatusProgrmErrorMsgMonitor OBJECT-TYPE
	SYNTAX INTEGER {
		do-not-monitor(1),
		down-warning(2),
		down-critical(3)
	}
	ACCESS read-write
	STATUS mandatory
	DESCRIPTION "&<caiUxsA2.1357>Current monitor level for the error message monitoring of the programmable resource watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { uxsA2StatusProgrmEntry 14 }

uxsA2StatusProgrmErrorMsgStatus OBJECT-TYPE
	SYNTAX INTEGER {
		unknown(1),
		up(2),
		down-warning(3),
		down-critical(4)
	}
	ACCESS read-only
	STATUS mandatory
	DESCRIPTION "&<caiUxsA2.1358>Current status for the error message monitoring of the programmable resource watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusProgrmEntry 15 }

uxsA2StatusProgrmResultValue OBJECT-TYPE
	SYNTAX DisplayString
	ACCESS read-only
	STATUS mandatory
	DESCRIPTION "&<caiUxsA2.1359>Current value for the result monitoring of the programmable resource watcher."
	DEFVAL { "0" }
	::= { uxsA2StatusProgrmEntry 16 }

uxsA2StatusProgrmResultLagValue OBJECT-TYPE
	SYNTAX INTEGER
	ACCESS read-only
	STATUS mandatory
	DESCRIPTION "&<caiUxsA2.1360>Current number of consecutive threshold breaches for the result monitoring of the programmable resource watcher. The result state changes from ok as soon as the lag value reaches the configured value. The state reverts back to ok if a threshold is no longer breached."
	::= { uxsA2StatusProgrmEntry 17 }

uxsA2StatusProgrmResultLag OBJECT-TYPE
	SYNTAX INTEGER
	ACCESS read-write
	STATUS mandatory
	DESCRIPTION "&<caiUxsA2.1361>Current lag setting for the result monitoring of the programmable resource watcher. Specifies the number of consecutive threshold breaches on which the result state changes. This value must be greater than 0."
	::= { uxsA2StatusProgrmEntry 18 }

uxsA2StatusProgrmResultWarnMin OBJECT-TYPE
	SYNTAX DisplayString
	ACCESS read-write
	STATUS mandatory
	DESCRIPTION "&<caiUxsA2.1362>Current warning minimum threshold for the result monitoring of the programmable resource watcher. This value represents a declining threshold and must be equal to or greater than 0.0, equal to or greater than the critical minimum threshold, but cannot be greater than the warning maximum threshold. A value of -1 disables the evaluation of this threshold."
	DEFVAL { "-2" }
	::= { uxsA2StatusProgrmEntry 19 }

uxsA2StatusProgrmResultWarnMax OBJECT-TYPE
	SYNTAX DisplayString
	ACCESS read-write
	STATUS mandatory
	DESCRIPTION "&<caiUxsA2.1363>Current warning maximum threshold for the result monitoring of the programmable resource watcher. This value represents a rising threshold and must be equal to or greater than 0.0, equal to or greater than the warning minimum threshold, but cannot be greater than the critical maximum threshold. A value of -1 disables the evaluation of this threshold."
	DEFVAL { "-2" }
	::= { uxsA2StatusProgrmEntry 20 }

uxsA2StatusProgrmResultCritMin OBJECT-TYPE
	SYNTAX DisplayString
	ACCESS read-write
	STATUS mandatory
	DESCRIPTION "&<caiUxsA2.1364>Current critical minimum threshold for the result monitoring of the programmable resource watcher. This value represents a declining threshold and must be equal to or greater than 0.0, but cannot be greater than the warning minimum threshold. A value of -1 disables the evaluation of this threshold."
	DEFVAL { "-2" }
	::= { uxsA2StatusProgrmEntry 21 }

uxsA2StatusProgrmResultCritMax OBJECT-TYPE
	SYNTAX DisplayString
	ACCESS read-write
	STATUS mandatory
	DESCRIPTION "&<caiUxsA2.1365>Current critical maximum threshold for the result monitoring of the programmable resource watcher. This value represents a rising threshold and must be equal to or greater than 0.0, but cannot be less than the warning maximum threshold. A value of -1 disables the evaluation of this threshold."
	DEFVAL { "-2" }
	::= { uxsA2StatusProgrmEntry 22 }

uxsA2StatusProgrmResultMonitor OBJECT-TYPE
	SYNTAX INTEGER {
		do-not-monitor(1),
		warning-only(2),
		critical-only(3),
		minimum-only(4),
		maximum-only(5),
		all(6)
	}
	ACCESS read-write
	STATUS mandatory
	DESCRIPTION "&<caiUxsA2.1366>Current monitor level for the result monitoring of the programmable resource watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { uxsA2StatusProgrmEntry 23 }

uxsA2StatusProgrmResultStatus OBJECT-TYPE
	SYNTAX INTEGER {
		unknown(1),
		up(2),
		down-warning(3),
		down-critical(4)
	}
	ACCESS read-only
	STATUS mandatory
	DESCRIPTION "&<caiUxsA2.1367>Current status for the result monitoring of the programmable resource watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusProgrmEntry 24 }

uxsA2StatusProgrmLossAction OBJECT-TYPE
	SYNTAX INTEGER {
		remove(1),
		up(2),
		down-warning(3),
		down-critical(4)
	}
	ACCESS read-write
	STATUS mandatory
	DESCRIPTION "&<caiUxsA2.1368>Current loss action for the programmable resource watcher. Specifies the action to take if the monitored programmable resource is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { uxsA2StatusProgrmEntry 25 }

uxsA2StatusProgrmLossStatus OBJECT-TYPE
	SYNTAX INTEGER {
		unknown(1),
		up(2),
		down-warning(3),
		down-critical(4)
	}
	ACCESS read-only
	STATUS mandatory
	DESCRIPTION "&<caiUxsA2.1369>Current loss status of the programmable resource watcher: 1 (unknown) - An error occurred during data collection, 2 (up) - The resource is in good condition or status evaluation is turned off and/or polling is disabled, 3 (down-warning) - The resource is in bad condition and has been given a warning severity, 4 (down-critical) - The resource is in bad condition and has been given a critical severity."
	::= { uxsA2StatusProgrmEntry 26 }

uxsA2StatusProgrmCallBackRef OBJECT-TYPE
	SYNTAX DisplayString
	ACCESS read-only
	STATUS mandatory
	DESCRIPTION "&<caiUxsA2.1370>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { uxsA2StatusProgrmEntry 27 }

uxsA2StatusProgrmButton OBJECT-TYPE
	SYNTAX INTEGER {
		none(1),
		remove(2),
		reset(3)
	}
	ACCESS read-write
	STATUS mandatory
	DESCRIPTION "&<caiUxsA2.1371>This attribute is used to remove the programmable resource watcher. Additionally, this attribute is used to reset the programmable resource monitoring watcher. If set to 3 (reset), the status of the watcher is set to ok. The watcher will be evaluated again at the next poll if the info message has changed. If set to 2 (remove), the agent removes the watcher from the table. This attribute cannot be set to 1 (none)."
	DEFVAL { 1 }
	::= { uxsA2StatusProgrmEntry 28 }

--
-- The AvailQuota Group
--

uxsA2AvailQuotaFSysFilter OBJECT-TYPE
	SYNTAX DisplayString
	ACCESS read-write
	STATUS mandatory
	DESCRIPTION "&<caiUxsA2.1372>File system mount name to be searched for when checking the OS for a list of available quota resources. The name can constitute an extended regular expression pattern."
	DEFVAL { ".*" }
	::= { uxsA2AvailQuotaGroup 1 }

uxsA2AvailQuotaUserFilter OBJECT-TYPE
	SYNTAX DisplayString
	ACCESS read-write
	STATUS mandatory
	DESCRIPTION "&<caiUxsA2.1373>User name to be searched for when checking the OS for a list of available quota resources. The name can constitute an extended regular expression pattern."
	DEFVAL { ".*" }
	::= { uxsA2AvailQuotaGroup 2 }

uxsA2AvailQuotaMatchType OBJECT-TYPE
	SYNTAX INTEGER {
		positive(1),
		negative(2)
	}
	ACCESS read-write
	STATUS mandatory
	DESCRIPTION "&<caiUxsA2.1374>Search algorithm the agent will apply when checking the UNIX System for available quota resources. The filter is the logical AND of all attributes used to identify or otherwise narrow down resources. If set to 1 (positive), the agent searches for quota resources that match the filter. If set to 2 (negative), the agent searches for quota resources that do not match the filter."
	DEFVAL { 1 }
	::= { uxsA2AvailQuotaGroup 3 }

uxsA2AvailQuotaViewWindow OBJECT-TYPE
	SYNTAX DisplayString
	ACCESS read-only
	STATUS mandatory
	DESCRIPTION "&<caiUxsA2.1375>This attribute indicates the number of the currently displayed buffer and the total number of buffers constituting the list of quota resources that are currently known to the agent and are available for monitoring."
	::= { uxsA2AvailQuotaGroup 4 }

uxsA2AvailQuotaButton OBJECT-TYPE
	SYNTAX INTEGER {
		none(1),
		next(2),
		previous(3),
		refresh(4)
	}
	ACCESS read-write
	STATUS mandatory
	DESCRIPTION "&<caiUxsA2.1376>This attribute is used to update the list of quota resources that are currently known to the agent and are available for monitoring. If set to 4 (refresh), the agent checks the UNIX System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { uxsA2AvailQuotaGroup 5 }

uxsA2AvailQuotaCount OBJECT-TYPE
	SYNTAX INTEGER
	ACCESS read-only
	STATUS mandatory
	DESCRIPTION "&<caiUxsA2.1377>Number of quota resources that are currently known to the agent and are available for monitoring."
	::= { uxsA2AvailQuotaGroup 6 }

--uxsA2AvailQuotaTable OBJECT-TYPE
--	SYNTAX SEQUENCE OF UxsA2AvailQuotaEntry
--	ACCESS not-accessible
--	STATUS mandatory
--	DESCRIPTION "&<caiUxsA2.1378>Table containing a list of quota resources that are currently known to the agent and are available for monitoring."
--	::= { uxsA2AvailQuotaGroup 7 }

--uxsA2AvailQuotaEntry OBJECT-TYPE
--	SYNTAX UxsA2AvailQuotaEntry
--	ACCESS not-accessible
--	STATUS mandatory
--	DESCRIPTION "&<caiUxsA2.1379>Entry in the table of available quota resources."
--	::= { uxsA2AvailQuotaTable 1 }

--UxsA2AvailQuotaEntry ::= SEQUENCE {
--	uxsA2AvailQuotaFSys DisplayString,
--	uxsA2AvailQuotaUser DisplayString
--}

--uxsA2AvailQuotaFSys OBJECT-TYPE
--	SYNTAX DisplayString
--	ACCESS read-only
--	STATUS mandatory
--	DESCRIPTION "&<caiUxsA2.1380>File system mount name for which quota information exist."
--	::= { uxsA2AvailQuotaEntry 1 }

--uxsA2AvailQuotaUser OBJECT-TYPE
--	SYNTAX DisplayString
--	ACCESS read-only
--	STATUS mandatory
--	DESCRIPTION "&<caiUxsA2.1381>User for which quota information exist on the mounted file system."
--	::= { uxsA2AvailQuotaEntry 2 }

--
-- The AvailFSys Group
--

uxsA2AvailFSysNameFilter OBJECT-TYPE
	SYNTAX DisplayString
	ACCESS read-write
	STATUS mandatory
	DESCRIPTION "&<caiUxsA2.1382>The file system mount point to be searched for when checking the OS for a list of available file systems. The name can constitute an extended regular expression pattern."
	DEFVAL { ".*" }
	::= { uxsA2AvailFSysGroup 1 }

uxsA2AvailFSysRelatedToFilter OBJECT-TYPE
	SYNTAX DisplayString
	ACCESS read-write
	STATUS mandatory
	DESCRIPTION "&<caiUxsA2.1383>The related device to be searched for when checking the OS for a list of available file systems. The name can constitute an extended regular expression pattern."
	DEFVAL { ".*" }
	::= { uxsA2AvailFSysGroup 2 }

uxsA2AvailFSysTypeFilter OBJECT-TYPE
	SYNTAX DisplayString
	ACCESS read-write
	STATUS mandatory
	DESCRIPTION "&<caiUxsA2.1384>The type of the mounted file system to be searched for when checking the OS for a list of available file systems. The value is platform dependent. The name can constitute an extended regular expression pattern."
	DEFVAL { ".*" }
	::= { uxsA2AvailFSysGroup 3 }

uxsA2AvailFSysClusterTypeFilter OBJECT-TYPE
	SYNTAX INTEGER {
		not-clustered(1),
		clustered-active(2),
		clustered-passive(3),
		any(4)
	}
	ACCESS read-write
	STATUS mandatory
	DESCRIPTION "&<caiUxsA2.1385>Cluster type associated with the file system to be searched for when checking the UNIX System for a list of available resources. If set to 1 (not-clustered), the search is restricted to not-clustered resources only. If set to 2 (clustered-active), the search is restricted to clustered-active resources only. If set to 3 (clustered-passive), the search is restricted to clustered-passive resources only. If set to 4 (any), the cluster type does not affect the search."
	DEFVAL { 4 }
	::= { uxsA2AvailFSysGroup 4 }

uxsA2AvailFSysMatchType OBJECT-TYPE
	SYNTAX INTEGER {
		positive(1),
		negative(2)
	}
	ACCESS read-write
	STATUS mandatory
	DESCRIPTION "&<caiUxsA2.1386>Search algorithm the agent will apply when checking the UNIX System for available file system resources. The filter is the logical AND of all attributes used to identify or otherwise narrow down resources. If set to 1 (positive), the agent searches for file system resources that match the filter. If set to 2 (negative), the agent searches for file system resources that do not match the filter."
	DEFVAL { 1 }
	::= { uxsA2AvailFSysGroup 5 }

uxsA2AvailFSysViewWindow OBJECT-TYPE
	SYNTAX DisplayString
	ACCESS read-only
	STATUS mandatory
	DESCRIPTION "&<caiUxsA2.1387>This attribute indicates the number of the currently displayed buffer and the total number of buffers constituting the list of file system resources that are currently known to the agent and are available for monitoring."
	::= { uxsA2AvailFSysGroup 6 }

uxsA2AvailFSysButton OBJECT-TYPE
	SYNTAX INTEGER {
		none(1),
		next(2),
		previous(3),
		refresh(4)
	}
	ACCESS read-write
	STATUS mandatory
	DESCRIPTION "&<caiUxsA2.1388>This attribute is used to update the list of file system resources that are currently known to the agent and are available for monitoring. If set to 4 (refresh), the agent checks the UNIX System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { uxsA2AvailFSysGroup 7 }

uxsA2AvailFSysCount OBJECT-TYPE
	SYNTAX INTEGER
	ACCESS read-only
	STATUS mandatory
	DESCRIPTION "&<caiUxsA2.1389>Number of file system resources that are currently known to the agent and are available for monitoring."
	::= { uxsA2AvailFSysGroup 8 }

--uxsA2AvailFSysTable OBJECT-TYPE
--	SYNTAX SEQUENCE OF UxsA2AvailFSysEntry
--	ACCESS not-accessible
--	STATUS mandatory
--	DESCRIPTION "&<caiUxsA2.1390>Table containing a list of file system resources that are currently known to the agent and are available for monitoring."
--	::= { uxsA2AvailFSysGroup 9 }

--uxsA2AvailFSysEntry OBJECT-TYPE
--	SYNTAX UxsA2AvailFSysEntry
--	ACCESS not-accessible
--	STATUS mandatory
--	DESCRIPTION "&<caiUxsA2.1391>Entry in the table of available file system resources."
--	::= { uxsA2AvailFSysTable 1 }

--UxsA2AvailFSysEntry ::= SEQUENCE {
--	uxsA2AvailFSysName DisplayString,
--	uxsA2AvailFSysRelatedTo DisplayString,
--	uxsA2AvailFSysType DisplayString,
--	uxsA2AvailFSysClusterType INTEGER
--}

--uxsA2AvailFSysName OBJECT-TYPE
--	SYNTAX DisplayString
--	ACCESS read-only
--	STATUS mandatory
--	DESCRIPTION "&<caiUxsA2.1392>The file system mount point."
--	::= { uxsA2AvailFSysEntry 1 }

--uxsA2AvailFSysRelatedTo OBJECT-TYPE
--	SYNTAX DisplayString
--	ACCESS read-only
--	STATUS mandatory
--	DESCRIPTION "&<caiUxsA2.1393>The device from which the file system is mounted."
--	::= { uxsA2AvailFSysEntry 2 }

--uxsA2AvailFSysType OBJECT-TYPE
--	SYNTAX DisplayString
--	ACCESS read-only
--	STATUS mandatory
--	DESCRIPTION "&<caiUxsA2.1394>The type of the mounted file system. The value is platform dependent."
--	::= { uxsA2AvailFSysEntry 3 }

--uxsA2AvailFSysClusterType OBJECT-TYPE
--	SYNTAX INTEGER {
--		not-clustered(1),
--		clustered-active(2),
--		clustered-passive(3)
--	}
--	ACCESS read-only
--	STATUS mandatory
--	DESCRIPTION "&<caiUxsA2.1395>Cluster type of the file system: 1 (not-clustered) - Resource is not clustered, 2 (clustered-active) - Local cluster node has resource ownership, 3 (clustered-passive) - Another node in the cluster has resource ownership; the agent on the local node does not actively monitor the resource until ownership is transferred back."
--	::= { uxsA2AvailFSysEntry 4 }

--
-- The AvailDisk Group
--

uxsA2AvailDiskNameFilter OBJECT-TYPE
	SYNTAX DisplayString
	ACCESS read-write
	STATUS mandatory
	DESCRIPTION "&<caiUxsA2.1396>Filter condition for disk names to be searched for when compiling a list of available disks. This condition is an extended regular expression pattern."
	DEFVAL { ".*" }
	::= { uxsA2AvailDiskGroup 1 }

uxsA2AvailDiskDescriptiveNameFilter OBJECT-TYPE
	SYNTAX DisplayString
	ACCESS read-write
	STATUS mandatory
	DESCRIPTION "&<caiUxsA2.1397>Filter condition for descriptive names to be searched for when compiling a list of available disks. This condition is an extended regular expression pattern."
	DEFVAL { ".*" }
	::= { uxsA2AvailDiskGroup 2 }

uxsA2AvailDiskClusterTypeFilter OBJECT-TYPE
	SYNTAX INTEGER {
		not-clustered(1),
		clustered-active(2),
		clustered-passive(3),
		any(4)
	}
	ACCESS read-write
	STATUS mandatory
	DESCRIPTION "&<caiUxsA2.1398>Cluster type associated with the disk to be searched for when checking the UNIX System for a list of available resources. If set to 1 (not-clustered), the search is restricted to not-clustered resources only. If set to 2 (clustered-active), the search is restricted to clustered-active resources only. If set to 3 (clustered-passive), the search is restricted to clustered-passive resources only. If set to 4 (any), the cluster type does not affect the search."
	DEFVAL { 4 }
	::= { uxsA2AvailDiskGroup 3 }

uxsA2AvailDiskMatchType OBJECT-TYPE
	SYNTAX INTEGER {
		positive(1),
		negative(2)
	}
	ACCESS read-write
	STATUS mandatory
	DESCRIPTION "&<caiUxsA2.1399>Search algorithm the agent will apply when checking the UNIX System for available disk resources. The filter is the logical AND of all attributes used to identify or otherwise narrow down resources. If set to 1 (positive), the agent searches for disk resources that match the filter. If set to 2 (negative), the agent searches for disk resources that do not match the filter."
	DEFVAL { 1 }
	::= { uxsA2AvailDiskGroup 4 }

uxsA2AvailDiskViewWindow OBJECT-TYPE
	SYNTAX DisplayString
	ACCESS read-only
	STATUS mandatory
	DESCRIPTION "&<caiUxsA2.1400>This attribute indicates the number of the currently displayed buffer and the total number of buffers constituting the list of disk resources that are currently known to the agent and are available for monitoring."
	::= { uxsA2AvailDiskGroup 5 }

uxsA2AvailDiskButton OBJECT-TYPE
	SYNTAX INTEGER {
		none(1),
		next(2),
		previous(3),
		refresh(4)
	}
	ACCESS read-write
	STATUS mandatory
	DESCRIPTION "&<caiUxsA2.1401>This attribute is used to update the list of disk resources that are currently known to the agent and are available for monitoring. If set to 4 (refresh), the agent checks the UNIX System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { uxsA2AvailDiskGroup 6 }

uxsA2AvailDiskCount OBJECT-TYPE
	SYNTAX INTEGER
	ACCESS read-only
	STATUS mandatory
	DESCRIPTION "&<caiUxsA2.1402>Number of disk resources that are currently known to the agent and are available for monitoring."
	::= { uxsA2AvailDiskGroup 7 }

--uxsA2AvailDiskTable OBJECT-TYPE
--	SYNTAX SEQUENCE OF UxsA2AvailDiskEntry
--	ACCESS not-accessible
--	STATUS mandatory
--	DESCRIPTION "&<caiUxsA2.1403>Table containing a list of disk resources that are currently known to the agent and are available for monitoring."
--	::= { uxsA2AvailDiskGroup 8 }

--uxsA2AvailDiskEntry OBJECT-TYPE
--	SYNTAX UxsA2AvailDiskEntry
--	ACCESS not-accessible
--	STATUS mandatory
--	DESCRIPTION "&<caiUxsA2.1404>Entry in the table of available disk resources."
--	::= { uxsA2AvailDiskTable 1 }

--UxsA2AvailDiskEntry ::= SEQUENCE {
--	uxsA2AvailDiskName DisplayString,
--	uxsA2AvailDiskDescriptiveName DisplayString,
--	uxsA2AvailDiskClusterType INTEGER,
--	uxsA2AvailDiskDescription DisplayString
--}

--uxsA2AvailDiskName OBJECT-TYPE
--	SYNTAX DisplayString
--	ACCESS read-only
--	STATUS mandatory
--	DESCRIPTION "&<caiUxsA2.1405>Name of the disk."
--	::= { uxsA2AvailDiskEntry 1 }

--uxsA2AvailDiskDescriptiveName OBJECT-TYPE
--	SYNTAX DisplayString
--	ACCESS read-only
--	STATUS mandatory
--	DESCRIPTION "&<caiUxsA2.1406>A descriptive string ascertained by the agent (platform dependent)."
--	::= { uxsA2AvailDiskEntry 2 }

--uxsA2AvailDiskClusterType OBJECT-TYPE
--	SYNTAX INTEGER {
--		not-clustered(1),
--		clustered-active(2),
--		clustered-passive(3)
--	}
--	ACCESS read-only
--	STATUS mandatory
--	DESCRIPTION "&<caiUxsA2.1407>Cluster type of the disk: 1 (not-clustered) - Resource is not clustered, 2 (clustered-active) - Local cluster node has resource ownership, 3 (clustered-passive) - Another node in the cluster has resource ownership; the agent on the local node does not actively monitor the resource until ownership is transferred back."
--	::= { uxsA2AvailDiskEntry 3 }

--uxsA2AvailDiskDescription OBJECT-TYPE
--	SYNTAX DisplayString
--	ACCESS read-only
--	STATUS mandatory
--	DESCRIPTION "&<caiUxsA2.1408>Description for the disk."
--	::= { uxsA2AvailDiskEntry 4 }

--
-- The AvailProc Group
--

uxsA2AvailProcNameFilter OBJECT-TYPE
	SYNTAX DisplayString
	ACCESS read-write
	STATUS mandatory
	DESCRIPTION "&<caiUxsA2.1409>Filter condition for process names to be searched for when compiling a list of available processes. The name can constitute an extended regular expression pattern."
	DEFVAL { ".*" }
	::= { uxsA2AvailProcGroup 1 }

uxsA2AvailProcPathFilter OBJECT-TYPE
	SYNTAX DisplayString
	ACCESS read-write
	STATUS mandatory
	DESCRIPTION "&<caiUxsA2.1410>Filter condition for process pathes to be searched for when compiling a list of available processes. The path can constitute an extended regular expression pattern."
	DEFVAL { ".*" }
	::= { uxsA2AvailProcGroup 2 }

uxsA2AvailProcArgsFilter OBJECT-TYPE
	SYNTAX DisplayString
	ACCESS read-write
	STATUS mandatory
	DESCRIPTION "&<caiUxsA2.1411>Filter condition for process arguments to be searched for when compiling a list of available processes. The argument list can constitute an extended regular expression pattern."
	DEFVAL { ".*" }
	::= { uxsA2AvailProcGroup 3 }

uxsA2AvailProcUserFilter OBJECT-TYPE
	SYNTAX DisplayString
	ACCESS read-write
	STATUS mandatory
	DESCRIPTION "&<caiUxsA2.1412>Filter condition for process owners to be searched for when compiling a list of available processes. The user can constitute an extended regular expression pattern. On Solaris 10 machines the name of the zone the process belongs to can be added to the attribute: <user>@<zone>. Owner and zone are evaluated as separate regular expressions. When no zone is specified the expression matches processes in the current zone only (<user>@<current>)."
	DEFVAL { ".*" }
	::= { uxsA2AvailProcGroup 4 }

uxsA2AvailProcClusterTypeFilter OBJECT-TYPE
	SYNTAX INTEGER {
		not-clustered(1),
		clustered-active(2),
		clustered-passive(3),
		any(4)
	}
	ACCESS read-write
	STATUS mandatory
	DESCRIPTION "&<caiUxsA2.1413>Reserved for future use."
	DEFVAL { 4 }
	::= { uxsA2AvailProcGroup 5 }

uxsA2AvailProcMatchType OBJECT-TYPE
	SYNTAX INTEGER {
		positive(1),
		negative(2)
	}
	ACCESS read-write
	STATUS mandatory
	DESCRIPTION "&<caiUxsA2.1414>Search algorithm the agent will apply when checking the UNIX System for available process resources. The filter is the logical AND of all attributes used to identify or otherwise narrow down resources. If set to 1 (positive), the agent searches for process resources that match the filter. If set to 2 (negative), the agent searches for process resources that do not match the filter."
	DEFVAL { 1 }
	::= { uxsA2AvailProcGroup 6 }

uxsA2AvailProcViewWindow OBJECT-TYPE
	SYNTAX DisplayString
	ACCESS read-only
	STATUS mandatory
	DESCRIPTION "&<caiUxsA2.1415>This attribute indicates the number of the currently displayed buffer and the total number of buffers constituting the list of process resources that are currently known to the agent and are available for monitoring."
	::= { uxsA2AvailProcGroup 7 }

uxsA2AvailProcButton OBJECT-TYPE
	SYNTAX INTEGER {
		none(1),
		next(2),
		previous(3),
		refresh(4)
	}
	ACCESS read-write
	STATUS mandatory
	DESCRIPTION "&<caiUxsA2.1416>This attribute is used to update the list of process resources that are currently known to the agent and are available for monitoring. If set to 4 (refresh), the agent checks the UNIX System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { uxsA2AvailProcGroup 8 }

uxsA2AvailProcCount OBJECT-TYPE
	SYNTAX INTEGER
	ACCESS read-only
	STATUS mandatory
	DESCRIPTION "&<caiUxsA2.1417>Number of process resources that are currently known to the agent and are available for monitoring."
	::= { uxsA2AvailProcGroup 9 }

--uxsA2AvailProcTable OBJECT-TYPE
--	SYNTAX SEQUENCE OF UxsA2AvailProcEntry
--	ACCESS not-accessible
--	STATUS mandatory
--	DESCRIPTION "&<caiUxsA2.1418>Table containing a list of process resources that are currently known to the agent and are available for monitoring."
--	::= { uxsA2AvailProcGroup 10 }

--uxsA2AvailProcEntry OBJECT-TYPE
--	SYNTAX UxsA2AvailProcEntry
--	ACCESS not-accessible
--	STATUS mandatory
--	DESCRIPTION "&<caiUxsA2.1419>Entry in the table of available process resources."
--	::= { uxsA2AvailProcTable 1 }

--UxsA2AvailProcEntry ::= SEQUENCE {
--	uxsA2AvailProcPid INTEGER,
--	uxsA2AvailProcName DisplayString,
--	uxsA2AvailProcPath DisplayString,
--	uxsA2AvailProcArgs DisplayString,
--	uxsA2AvailProcUser DisplayString,
--	uxsA2AvailProcStartingTime DisplayString,
--	uxsA2AvailProcClusterType INTEGER
--}

--uxsA2AvailProcPid OBJECT-TYPE
--	SYNTAX INTEGER
--	ACCESS read-only
--	STATUS mandatory
--	DESCRIPTION "&<caiUxsA2.1420>PID of the process."
--	::= { uxsA2AvailProcEntry 1 }

--uxsA2AvailProcName OBJECT-TYPE
--	SYNTAX DisplayString
--	ACCESS read-only
--	STATUS mandatory
--	DESCRIPTION "&<caiUxsA2.1421>Name of the process."
--	::= { uxsA2AvailProcEntry 2 }

--uxsA2AvailProcPath OBJECT-TYPE
--	SYNTAX DisplayString
--	ACCESS read-only
--	STATUS mandatory
--	DESCRIPTION "&<caiUxsA2.1422>Path of of the process."
--	::= { uxsA2AvailProcEntry 3 }

--uxsA2AvailProcArgs OBJECT-TYPE
--	SYNTAX DisplayString
--	ACCESS read-only
--	STATUS mandatory
--	DESCRIPTION "&<caiUxsA2.1423>Arguments of the process."
--	::= { uxsA2AvailProcEntry 4 }

--uxsA2AvailProcUser OBJECT-TYPE
--	SYNTAX DisplayString
--	ACCESS read-only
--	STATUS mandatory
--	DESCRIPTION "&<caiUxsA2.1424>User of the process. On Solaris 10 machines the name of the zone the process belongs to is added to the attribute: <user>@<zone>."
--	::= { uxsA2AvailProcEntry 5 }

--uxsA2AvailProcStartingTime OBJECT-TYPE
--	SYNTAX DisplayString
--	ACCESS read-only
--	STATUS mandatory
--	DESCRIPTION "&<caiUxsA2.1425>The starting time of the process (a formatted string)."
--	::= { uxsA2AvailProcEntry 6 }

--uxsA2AvailProcClusterType OBJECT-TYPE
--	SYNTAX INTEGER {
--		not-clustered(1),
--		clustered-active(2),
--		clustered-passive(3)
--	}
--	ACCESS read-only
--	STATUS mandatory
--	DESCRIPTION "&<caiUxsA2.1426>Reserved for future use."
--	::= { uxsA2AvailProcEntry 7 }

--
-- The AvailPrn Group
--

uxsA2AvailPrnNameFilter OBJECT-TYPE
	SYNTAX DisplayString
	ACCESS read-write
	STATUS mandatory
	DESCRIPTION "&<caiUxsA2.1427>Name of the print queue to be searched for when checking the UNIX System for a list of available resources. The name can constitute an extended regular expression pattern."
	DEFVAL { ".*" }
	::= { uxsA2AvailPrnGroup 1 }

uxsA2AvailPrnMatchType OBJECT-TYPE
	SYNTAX INTEGER {
		positive(1),
		negative(2)
	}
	ACCESS read-write
	STATUS mandatory
	DESCRIPTION "&<caiUxsA2.1428>Search algorithm the agent will apply when checking the UNIX System for available print queue resources. The filter is the logical AND of all attributes used to identify or otherwise narrow down resources. If set to 1 (positive), the agent searches for print queue resources that match the filter. If set to 2 (negative), the agent searches for print queue resources that do not match the filter."
	DEFVAL { 1 }
	::= { uxsA2AvailPrnGroup 2 }

uxsA2AvailPrnViewWindow OBJECT-TYPE
	SYNTAX DisplayString
	ACCESS read-only
	STATUS mandatory
	DESCRIPTION "&<caiUxsA2.1429>This attribute indicates the number of the currently displayed buffer and the total number of buffers constituting the list of print queue resources that are currently known to the agent and are available for monitoring."
	::= { uxsA2AvailPrnGroup 3 }

uxsA2AvailPrnButton OBJECT-TYPE
	SYNTAX INTEGER {
		none(1),
		next(2),
		previous(3),
		refresh(4)
	}
	ACCESS read-write
	STATUS mandatory
	DESCRIPTION "&<caiUxsA2.1430>This attribute is used to update the list of print queue resources that are currently known to the agent and are available for monitoring. If set to 4 (refresh), the agent checks the UNIX System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { uxsA2AvailPrnGroup 4 }

uxsA2AvailPrnCount OBJECT-TYPE
	SYNTAX INTEGER
	ACCESS read-only
	STATUS mandatory
	DESCRIPTION "&<caiUxsA2.1431>Number of print queue resources that are currently known to the agent and are available for monitoring."
	::= { uxsA2AvailPrnGroup 5 }

--uxsA2AvailPrnTable OBJECT-TYPE
--	SYNTAX SEQUENCE OF UxsA2AvailPrnEntry
--	ACCESS not-accessible
--	STATUS mandatory
--	DESCRIPTION "&<caiUxsA2.1432>Table containing a list of print queue resources that are currently known to the agent and are available for monitoring."
--	::= { uxsA2AvailPrnGroup 6 }

--uxsA2AvailPrnEntry OBJECT-TYPE
--	SYNTAX UxsA2AvailPrnEntry
--	ACCESS not-accessible
--	STATUS mandatory
--	DESCRIPTION "&<caiUxsA2.1433>Entry in the table of available print queue resources."
--	::= { uxsA2AvailPrnTable 1 }

--UxsA2AvailPrnEntry ::= SEQUENCE {
--	uxsA2AvailPrnName DisplayString
--}

--uxsA2AvailPrnName OBJECT-TYPE
--	SYNTAX DisplayString
--	ACCESS read-only
--	STATUS mandatory
--	DESCRIPTION "&<caiUxsA2.1434>Name of the print queue."
--	::= { uxsA2AvailPrnEntry 1 }

--
-- The AvailSHM Group
--

uxsA2AvailSHMIdFilter OBJECT-TYPE
	SYNTAX DisplayString
	ACCESS read-write
	STATUS mandatory
	DESCRIPTION "&<caiUxsA2.1435>Name of the shared memory identifier to be searched for when compiling a list of available shared memory resources. The name can constitute an extended regular expression pattern."
	DEFVAL { ".*" }
	::= { uxsA2AvailSHMGroup 1 }

uxsA2AvailSHMKeyFilter OBJECT-TYPE
	SYNTAX DisplayString
	ACCESS read-write
	STATUS mandatory
	DESCRIPTION "&<caiUxsA2.1436>Key of the shared memory identifier to be searched for when compiling a list of available shared memory resources. The key can constitute an extended regular expression pattern."
	DEFVAL { ".*" }
	::= { uxsA2AvailSHMGroup 2 }

uxsA2AvailSHMModeFilter OBJECT-TYPE
	SYNTAX DisplayString
	ACCESS read-write
	STATUS mandatory
	DESCRIPTION "&<caiUxsA2.1437>Access mode and flags of the shared memory identifier to be searched for when compiling a list of available shared memory resources. The mode can constitute an extended regular expression pattern."
	DEFVAL { ".*" }
	::= { uxsA2AvailSHMGroup 3 }

uxsA2AvailSHMOwnerFilter OBJECT-TYPE
	SYNTAX DisplayString
	ACCESS read-write
	STATUS mandatory
	DESCRIPTION "&<caiUxsA2.1438>User name of the owner of the shared memory identifier to be searched for when compiling a list of available shared memory resources. The user name can constitute an extended regular expression pattern. On Solaris 10 machines the name of the zone the resource belongs to can be added to the attribute: <owner>@<zone>. Owner and zone are evaluated as separate regular expressions. When no zone is specified the expression matches resources in the current zone only (<owner>@<currentzone>)."
	DEFVAL { ".*" }
	::= { uxsA2AvailSHMGroup 4 }

uxsA2AvailSHMGrpFilter OBJECT-TYPE
	SYNTAX DisplayString
	ACCESS read-write
	STATUS mandatory
	DESCRIPTION "&<caiUxsA2.1439>Group name of the owner of the shared memory identifier to be searched for when compiling a list of available shared memory resources. The group name can constitute an extended regular expression pattern."
	DEFVAL { ".*" }
	::= { uxsA2AvailSHMGroup 5 }

uxsA2AvailSHMMatchType OBJECT-TYPE
	SYNTAX INTEGER {
		positive(1),
		negative(2)
	}
	ACCESS read-write
	STATUS mandatory
	DESCRIPTION "&<caiUxsA2.1440>Search algorithm the agent will apply when checking the UNIX System for available shared memory resources. The filter is the logical AND of all attributes used to identify or otherwise narrow down resources. If set to 1 (positive), the agent searches for shared memory resources that match the filter. If set to 2 (negative), the agent searches for shared memory resources that do not match the filter."
	DEFVAL { 1 }
	::= { uxsA2AvailSHMGroup 6 }

uxsA2AvailSHMViewWindow OBJECT-TYPE
	SYNTAX DisplayString
	ACCESS read-only
	STATUS mandatory
	DESCRIPTION "&<caiUxsA2.1441>This attribute indicates the number of the currently displayed buffer and the total number of buffers constituting the list of shared memory resources that are currently known to the agent and are available for monitoring."
	::= { uxsA2AvailSHMGroup 7 }

uxsA2AvailSHMButton OBJECT-TYPE
	SYNTAX INTEGER {
		none(1),
		next(2),
		previous(3),
		refresh(4)
	}
	ACCESS read-write
	STATUS mandatory
	DESCRIPTION "&<caiUxsA2.1442>This attribute is used to update the list of shared memory resources that are currently known to the agent and are available for monitoring. If set to 4 (refresh), the agent checks the UNIX System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { uxsA2AvailSHMGroup 8 }

uxsA2AvailSHMCount OBJECT-TYPE
	SYNTAX INTEGER
	ACCESS read-only
	STATUS mandatory
	DESCRIPTION "&<caiUxsA2.1443>Number of shared memory resources that are currently known to the agent and are available for monitoring."
	::= { uxsA2AvailSHMGroup 9 }

--uxsA2AvailSHMTable OBJECT-TYPE
--	SYNTAX SEQUENCE OF UxsA2AvailSHMEntry
--	ACCESS not-accessible
--	STATUS mandatory
--	DESCRIPTION "&<caiUxsA2.1444>Table containing a list of shared memory resources that are currently known to the agent and are available for monitoring."
--	::= { uxsA2AvailSHMGroup 10 }

--uxsA2AvailSHMEntry OBJECT-TYPE
--	SYNTAX UxsA2AvailSHMEntry
--	ACCESS not-accessible
--	STATUS mandatory
--	DESCRIPTION "&<caiUxsA2.1445>Entry in the table of available shared memory resources."
--	::= { uxsA2AvailSHMTable 1 }

--UxsA2AvailSHMEntry ::= SEQUENCE {
--	uxsA2AvailSHMId DisplayString,
--	uxsA2AvailSHMKey DisplayString,
--	uxsA2AvailSHMMode DisplayString,
--	uxsA2AvailSHMOwner DisplayString,
--	uxsA2AvailSHMGrp DisplayString
--}

--uxsA2AvailSHMId OBJECT-TYPE
--	SYNTAX DisplayString
--	ACCESS read-only
--	STATUS mandatory
--	DESCRIPTION "&<caiUxsA2.1446>Name of the shared memory identifier. The number of used and totally available shared memory identifiers is monitored in the OS Resource Parameters group."
--	::= { uxsA2AvailSHMEntry 1 }

--uxsA2AvailSHMKey OBJECT-TYPE
--	SYNTAX DisplayString
--	ACCESS read-only
--	STATUS mandatory
--	DESCRIPTION "&<caiUxsA2.1447>Key of the shared memory."
--	::= { uxsA2AvailSHMEntry 2 }

--uxsA2AvailSHMMode OBJECT-TYPE
--	SYNTAX DisplayString
--	ACCESS read-only
--	STATUS mandatory
--	DESCRIPTION "&<caiUxsA2.1448>Access mode and flags of the shared memory."
--	::= { uxsA2AvailSHMEntry 3 }

--uxsA2AvailSHMOwner OBJECT-TYPE
--	SYNTAX DisplayString
--	ACCESS read-only
--	STATUS mandatory
--	DESCRIPTION "&<caiUxsA2.1449>User name of the owner of the shared memory. On Solaris 10 machines the name of the zone the resource belongs to is added to the attribute: <owner>@<zone>."
--	::= { uxsA2AvailSHMEntry 4 }

--uxsA2AvailSHMGrp OBJECT-TYPE
--	SYNTAX DisplayString
--	ACCESS read-only
--	STATUS mandatory
--	DESCRIPTION "&<caiUxsA2.1450>Group name of the owner of the shared memory."
--	::= { uxsA2AvailSHMEntry 5 }

--
-- The AvailSEM Group
--

uxsA2AvailSEMIdFilter OBJECT-TYPE
	SYNTAX DisplayString
	ACCESS read-write
	STATUS mandatory
	DESCRIPTION "&<caiUxsA2.1451>Name of the semaphore identifier to be searched for when compiling a list of available semaphore resources. The name can constitute an extended regular expression pattern."
	DEFVAL { ".*" }
	::= { uxsA2AvailSEMGroup 1 }

uxsA2AvailSEMKeyFilter OBJECT-TYPE
	SYNTAX DisplayString
	ACCESS read-write
	STATUS mandatory
	DESCRIPTION "&<caiUxsA2.1452>Key of the semaphore identifier to be searched for when compiling a list of available semaphore resources. The key can constitute an extended regular expression pattern."
	DEFVAL { ".*" }
	::= { uxsA2AvailSEMGroup 2 }

uxsA2AvailSEMModeFilter OBJECT-TYPE
	SYNTAX DisplayString
	ACCESS read-write
	STATUS mandatory
	DESCRIPTION "&<caiUxsA2.1453>Access mode and flags of the semaphore identifier to be searched for when compiling a list of available semaphore resources. The mode can constitute an extended regular expression pattern."
	DEFVAL { ".*" }
	::= { uxsA2AvailSEMGroup 3 }

uxsA2AvailSEMOwnerFilter OBJECT-TYPE
	SYNTAX DisplayString
	ACCESS read-write
	STATUS mandatory
	DESCRIPTION "&<caiUxsA2.1454>User name of the owner of the semaphore identifier to be searched for when compiling a list of available semaphore resources. The user name can constitute an extended regular expression pattern. On Solaris 10 machines the name of the zone the resource belongs to can be added to the attribute: <owner>@<zone>. Owner and zone are evaluated as separate regular expressions. When no zone is specified the expression matches resources in the current zone only (<owner>@<currentzone>)."
	DEFVAL { ".*" }
	::= { uxsA2AvailSEMGroup 4 }

uxsA2AvailSEMGrpFilter OBJECT-TYPE
	SYNTAX DisplayString
	ACCESS read-write
	STATUS mandatory
	DESCRIPTION "&<caiUxsA2.1455>Group name of the owner of the semaphore identifier to be searched for when compiling a list of available semaphore resources. The group name can constitute an extended regular expression pattern."
	DEFVAL { ".*" }
	::= { uxsA2AvailSEMGroup 5 }

uxsA2AvailSEMMatchType OBJECT-TYPE
	SYNTAX INTEGER {
		positive(1),
		negative(2)
	}
	ACCESS read-write
	STATUS mandatory
	DESCRIPTION "&<caiUxsA2.1456>Search algorithm the agent will apply when checking the UNIX System for available semaphore resources. The filter is the logical AND of all attributes used to identify or otherwise narrow down resources. If set to 1 (positive), the agent searches for semaphore resources that match the filter. If set to 2 (negative), the agent searches for semaphore resources that do not match the filter."
	DEFVAL { 1 }
	::= { uxsA2AvailSEMGroup 6 }

uxsA2AvailSEMViewWindow OBJECT-TYPE
	SYNTAX DisplayString
	ACCESS read-only
	STATUS mandatory
	DESCRIPTION "&<caiUxsA2.1457>This attribute indicates the number of the currently displayed buffer and the total number of buffers constituting the list of semaphore resources that are currently known to the agent and are available for monitoring."
	::= { uxsA2AvailSEMGroup 7 }

uxsA2AvailSEMButton OBJECT-TYPE
	SYNTAX INTEGER {
		none(1),
		next(2),
		previous(3),
		refresh(4)
	}
	ACCESS read-write
	STATUS mandatory
	DESCRIPTION "&<caiUxsA2.1458>This attribute is used to update the list of semaphore resources that are currently known to the agent and are available for monitoring. If set to 4 (refresh), the agent checks the UNIX System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { uxsA2AvailSEMGroup 8 }

uxsA2AvailSEMCount OBJECT-TYPE
	SYNTAX INTEGER
	ACCESS read-only
	STATUS mandatory
	DESCRIPTION "&<caiUxsA2.1459>Number of semaphore resources that are currently known to the agent and are available for monitoring."
	::= { uxsA2AvailSEMGroup 9 }

--uxsA2AvailSEMTable OBJECT-TYPE
--	SYNTAX SEQUENCE OF UxsA2AvailSEMEntry
--	ACCESS not-accessible
--	STATUS mandatory
--	DESCRIPTION "&<caiUxsA2.1460>Table containing a list of semaphore resources that are currently known to the agent and are available for monitoring."
--	::= { uxsA2AvailSEMGroup 10 }

--uxsA2AvailSEMEntry OBJECT-TYPE
--	SYNTAX UxsA2AvailSEMEntry
--	ACCESS not-accessible
--	STATUS mandatory
--	DESCRIPTION "&<caiUxsA2.1461>Entry in the table of available semaphore resources."
--	::= { uxsA2AvailSEMTable 1 }

--UxsA2AvailSEMEntry ::= SEQUENCE {
--	uxsA2AvailSEMId DisplayString,
--	uxsA2AvailSEMKey DisplayString,
--	uxsA2AvailSEMMode DisplayString,
--	uxsA2AvailSEMOwner DisplayString,
--	uxsA2AvailSEMGrp DisplayString
--}

--uxsA2AvailSEMId OBJECT-TYPE
--	SYNTAX DisplayString
--	ACCESS read-only
--	STATUS mandatory
--	DESCRIPTION "&<caiUxsA2.1462>Name of the semaphore identifier. The number of used and totally available semaphore identifiers is monitored in the OS Resource Parameters group."
--	::= { uxsA2AvailSEMEntry 1 }

--uxsA2AvailSEMKey OBJECT-TYPE
--	SYNTAX DisplayString
--	ACCESS read-only
--	STATUS mandatory
--	DESCRIPTION "&<caiUxsA2.1463>Key of the semaphore."
--	::= { uxsA2AvailSEMEntry 2 }

--uxsA2AvailSEMMode OBJECT-TYPE
--	SYNTAX DisplayString
--	ACCESS read-only
--	STATUS mandatory
--	DESCRIPTION "&<caiUxsA2.1464>Access mode and flags of the semaphore."
--	::= { uxsA2AvailSEMEntry 3 }

--uxsA2AvailSEMOwner OBJECT-TYPE
--	SYNTAX DisplayString
--	ACCESS read-only
--	STATUS mandatory
--	DESCRIPTION "&<caiUxsA2.1465>User name of the owner of the semaphore. On Solaris 10 machines the name of the zone the resource belongs to is added to the attribute: <owner>@<zone>."
--	::= { uxsA2AvailSEMEntry 4 }

--uxsA2AvailSEMGrp OBJECT-TYPE
--	SYNTAX DisplayString
--	ACCESS read-only
--	STATUS mandatory
--	DESCRIPTION "&<caiUxsA2.1466>Group name of the owner of the semaphore."
--	::= { uxsA2AvailSEMEntry 5 }

--
-- The AvailMQ Group
--

uxsA2AvailMQIdFilter OBJECT-TYPE
	SYNTAX DisplayString
	ACCESS read-write
	STATUS mandatory
	DESCRIPTION "&<caiUxsA2.1467>Name of the message queue identifier to be searched for when compiling a list of available message queue resources. The name can constitute an extended regular expression pattern."
	DEFVAL { ".*" }
	::= { uxsA2AvailMQGroup 1 }

uxsA2AvailMQKeyFilter OBJECT-TYPE
	SYNTAX DisplayString
	ACCESS read-write
	STATUS mandatory
	DESCRIPTION "&<caiUxsA2.1468>Key of the message queue identifier to be searched for when compiling a list of available message queue resources. The key can constitute an extended regular expression pattern."
	DEFVAL { ".*" }
	::= { uxsA2AvailMQGroup 2 }

uxsA2AvailMQModeFilter OBJECT-TYPE
	SYNTAX DisplayString
	ACCESS read-write
	STATUS mandatory
	DESCRIPTION "&<caiUxsA2.1469>Access mode and flags of the message queue identifier to be searched for when compiling a list of available message queue resources. The mode can constitute an extended regular expression pattern."
	DEFVAL { ".*" }
	::= { uxsA2AvailMQGroup 3 }

uxsA2AvailMQOwnerFilter OBJECT-TYPE
	SYNTAX DisplayString
	ACCESS read-write
	STATUS mandatory
	DESCRIPTION "&<caiUxsA2.1470>User name of the owner of the message queue identifier to be searched for when compiling a list of available message queue resources. The user name can constitute an extended regular expression pattern. On Solaris 10 machines the name of the zone the resource belongs to can be added to the attribute: <owner>@<zone>. Owner and zone are evaluated as separate regular expressions. When no zone is specified the expression matches resources in the current zone only (<owner>@<currentzone>)."
	DEFVAL { ".*" }
	::= { uxsA2AvailMQGroup 4 }

uxsA2AvailMQGrpFilter OBJECT-TYPE
	SYNTAX DisplayString
	ACCESS read-write
	STATUS mandatory
	DESCRIPTION "&<caiUxsA2.1471>Group name of the owner of the message queue identifier to be searched for when compiling a list of available message queue resources. The group name can constitute an extended regular expression pattern."
	DEFVAL { ".*" }
	::= { uxsA2AvailMQGroup 5 }

uxsA2AvailMQMatchType OBJECT-TYPE
	SYNTAX INTEGER {
		positive(1),
		negative(2)
	}
	ACCESS read-write
	STATUS mandatory
	DESCRIPTION "&<caiUxsA2.1472>Search algorithm the agent will apply when checking the UNIX System for available message queue resources. The filter is the logical AND of all attributes used to identify or otherwise narrow down resources. If set to 1 (positive), the agent searches for message queue resources that match the filter. If set to 2 (negative), the agent searches for message queue resources that do not match the filter."
	DEFVAL { 1 }
	::= { uxsA2AvailMQGroup 6 }

uxsA2AvailMQViewWindow OBJECT-TYPE
	SYNTAX DisplayString
	ACCESS read-only
	STATUS mandatory
	DESCRIPTION "&<caiUxsA2.1473>This attribute indicates the number of the currently displayed buffer and the total number of buffers constituting the list of message queue resources that are currently known to the agent and are available for monitoring."
	::= { uxsA2AvailMQGroup 7 }

uxsA2AvailMQButton OBJECT-TYPE
	SYNTAX INTEGER {
		none(1),
		next(2),
		previous(3),
		refresh(4)
	}
	ACCESS read-write
	STATUS mandatory
	DESCRIPTION "&<caiUxsA2.1474>This attribute is used to update the list of message queue resources that are currently known to the agent and are available for monitoring. If set to 4 (refresh), the agent checks the UNIX System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { uxsA2AvailMQGroup 8 }

uxsA2AvailMQCount OBJECT-TYPE
	SYNTAX INTEGER
	ACCESS read-only
	STATUS mandatory
	DESCRIPTION "&<caiUxsA2.1475>Number of message queue resources that are currently known to the agent and are available for monitoring."
	::= { uxsA2AvailMQGroup 9 }

--uxsA2AvailMQTable OBJECT-TYPE
--	SYNTAX SEQUENCE OF UxsA2AvailMQEntry
--	ACCESS not-accessible
--	STATUS mandatory
--	DESCRIPTION "&<caiUxsA2.1476>Table containing a list of message queue resources that are currently known to the agent and are available for monitoring."
--	::= { uxsA2AvailMQGroup 10 }

--uxsA2AvailMQEntry OBJECT-TYPE
--	SYNTAX UxsA2AvailMQEntry
--	ACCESS not-accessible
--	STATUS mandatory
--	DESCRIPTION "&<caiUxsA2.1477>Entry in the table of available message queue resources."
--	::= { uxsA2AvailMQTable 1 }

--UxsA2AvailMQEntry ::= SEQUENCE {
--	uxsA2AvailMQId DisplayString,
--	uxsA2AvailMQKey DisplayString,
--	uxsA2AvailMQMode DisplayString,
--	uxsA2AvailMQOwner DisplayString,
--	uxsA2AvailMQGrp DisplayString
--}

--uxsA2AvailMQId OBJECT-TYPE
--	SYNTAX DisplayString
--	ACCESS read-only
--	STATUS mandatory
--	DESCRIPTION "&<caiUxsA2.1478>Name of the message queue identifier. The number of used and totally available message queue identifiers is monitored in the OS Resource Parameters group."
--	::= { uxsA2AvailMQEntry 1 }

--uxsA2AvailMQKey OBJECT-TYPE
--	SYNTAX DisplayString
--	ACCESS read-only
--	STATUS mandatory
--	DESCRIPTION "&<caiUxsA2.1479>Key of the message queue."
--	::= { uxsA2AvailMQEntry 2 }

--uxsA2AvailMQMode OBJECT-TYPE
--	SYNTAX DisplayString
--	ACCESS read-only
--	STATUS mandatory
--	DESCRIPTION "&<caiUxsA2.1480>Access mode and flags of the message queue."
--	::= { uxsA2AvailMQEntry 3 }

--uxsA2AvailMQOwner OBJECT-TYPE
--	SYNTAX DisplayString
--	ACCESS read-only
--	STATUS mandatory
--	DESCRIPTION "&<caiUxsA2.1481>User name of the owner of the message queue. On Solaris 10 machines the name of the zone the resource belongs to is added to the attribute: <owner>@<zone>."
--	::= { uxsA2AvailMQEntry 4 }

--uxsA2AvailMQGrp OBJECT-TYPE
--	SYNTAX DisplayString
--	ACCESS read-only
--	STATUS mandatory
--	DESCRIPTION "&<caiUxsA2.1482>Group name of the owner of the message queue."
--	::= { uxsA2AvailMQEntry 5 }

--
-- The AvailHardwr Group
--

uxsA2AvailHardwrResNameFilter OBJECT-TYPE
	SYNTAX DisplayString
	ACCESS read-write
	STATUS mandatory
	DESCRIPTION "&<caiUxsA2.1483>An extended regular expression used to filter the resource names in oder to determine the set of rows displayed in the available table."
	DEFVAL { ".*" }
	::= { uxsA2AvailHardwrGroup 1 }

uxsA2AvailHardwrResSubNameFilter OBJECT-TYPE
	SYNTAX DisplayString
	ACCESS read-write
	STATUS mandatory
	DESCRIPTION "&<caiUxsA2.1484>An extended regular expression used to filter the resource subnames in oder to determine the set of rows displayed in the available table."
	DEFVAL { ".*" }
	::= { uxsA2AvailHardwrGroup 2 }

uxsA2AvailHardwrInstNameFilter OBJECT-TYPE
	SYNTAX DisplayString
	ACCESS read-write
	STATUS mandatory
	DESCRIPTION "&<caiUxsA2.1485>An extended regular expression used to filter the instance names in oder to determine the set of rows displayed in the available table."
	DEFVAL { ".*" }
	::= { uxsA2AvailHardwrGroup 3 }

uxsA2AvailHardwrMatchType OBJECT-TYPE
	SYNTAX INTEGER {
		positive(1),
		negative(2)
	}
	ACCESS read-write
	STATUS mandatory
	DESCRIPTION "&<caiUxsA2.1486>Search algorithm the agent will apply when checking the UNIX System for available hardware resources. The filter is the logical AND of all attributes used to identify or otherwise narrow down resources. If set to 1 (positive), the agent searches for hardware resources that match the filter. If set to 2 (negative), the agent searches for hardware resources that do not match the filter."
	DEFVAL { 1 }
	::= { uxsA2AvailHardwrGroup 4 }

uxsA2AvailHardwrViewWindow OBJECT-TYPE
	SYNTAX DisplayString
	ACCESS read-only
	STATUS mandatory
	DESCRIPTION "&<caiUxsA2.1487>This attribute indicates the number of the currently displayed buffer and the total number of buffers constituting the list of hardware resources that are currently known to the agent and are available for monitoring."
	::= { uxsA2AvailHardwrGroup 5 }

uxsA2AvailHardwrButton OBJECT-TYPE
	SYNTAX INTEGER {
		none(1),
		next(2),
		previous(3),
		refresh(4),
		reinit(5),
		recreate(6)
	}
	ACCESS read-write
	STATUS mandatory
	DESCRIPTION "&<caiUxsA2.1488>This attribute is used to update the list of hardware resources that are currently known to the agent and are available for monitoring. If set to 6 (recreate), 5 (reinit), or 4 (refresh), the agent re-reads the 'Generic.ini' file and refreshes its internal data with the current content of this file. If the file defines resources that support instances, the agent starts all corresponding instance scripts to retrieve a list of available instances for automatic watcher creation or for display in the table (see below). Setting the value to 5 (reinit) has the same effect as refresh; in addition, the agent creates watchers from any new definitions in the ini file or for any new instances found by the instance scripts. Setting the value to 6 (recreate) has the same effect as reinit; in addition, the agent deletes all hardware status and auto watchers beforehand. If set to 4 (refresh), the agent checks the UNIX System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { uxsA2AvailHardwrGroup 6 }

uxsA2AvailHardwrCount OBJECT-TYPE
	SYNTAX INTEGER
	ACCESS read-only
	STATUS mandatory
	DESCRIPTION "&<caiUxsA2.1489>Number of hardware resources that are currently known to the agent and are available for monitoring."
	::= { uxsA2AvailHardwrGroup 7 }

--uxsA2AvailHardwrTable OBJECT-TYPE
--	SYNTAX SEQUENCE OF UxsA2AvailHardwrEntry
--	ACCESS not-accessible
--	STATUS mandatory
--	DESCRIPTION "&<caiUxsA2.1490>Table containing a list of hardware resources that are currently known to the agent and are available for monitoring."
--	::= { uxsA2AvailHardwrGroup 8 }

--uxsA2AvailHardwrEntry OBJECT-TYPE
--	SYNTAX UxsA2AvailHardwrEntry
--	ACCESS not-accessible
--	STATUS mandatory
--	DESCRIPTION "&<caiUxsA2.1491>Entry in the table of available hardware resources."
--	::= { uxsA2AvailHardwrTable 1 }

--UxsA2AvailHardwrEntry ::= SEQUENCE {
--	uxsA2AvailHardwrResName DisplayString,
--	uxsA2AvailHardwrResSubName DisplayString,
--	uxsA2AvailHardwrInstName DisplayString,
--	uxsA2AvailHardwrAutoWatch INTEGER,
--	uxsA2AvailHardwrInstSupport INTEGER,
--	uxsA2AvailHardwrInstScript DisplayString,
--	uxsA2AvailHardwrInstArgs DisplayString,
--	uxsA2AvailHardwrCollectScript DisplayString,
--	uxsA2AvailHardwrCollectArgs DisplayString,
--	uxsA2AvailHardwrUserName DisplayString,
--	uxsA2AvailHardwrSkipCount INTEGER,
--	uxsA2AvailHardwrErrorMsgPattern DisplayString,
--	uxsA2AvailHardwrErrorMsgMonitor INTEGER,
--	uxsA2AvailHardwrResultLag INTEGER,
--	uxsA2AvailHardwrResultWarnMin DisplayString,
--	uxsA2AvailHardwrResultWarnMax DisplayString,
--	uxsA2AvailHardwrResultCritMin DisplayString,
--	uxsA2AvailHardwrResultCritMax DisplayString,
--	uxsA2AvailHardwrResultMonitor INTEGER,
--	uxsA2AvailHardwrLossAction INTEGER,
--	uxsA2AvailHardwrDescription DisplayString
--}

--uxsA2AvailHardwrResName OBJECT-TYPE
--	SYNTAX DisplayString
--	ACCESS read-only
--	STATUS mandatory
--	DESCRIPTION "&<caiUxsA2.1492>The name of the resource. This is the first index used by the agent in the different MIB tables for this resource (e.g. PowerSupply)."
--	::= { uxsA2AvailHardwrEntry 1 }

--uxsA2AvailHardwrResSubName OBJECT-TYPE
--	SYNTAX DisplayString
--	ACCESS read-only
--	STATUS mandatory
--	DESCRIPTION "&<caiUxsA2.1493>The subname of the resource. This is the second index used by the agent in the different MIB tables for this resource (e.g. Voltage)."
--	::= { uxsA2AvailHardwrEntry 2 }

--uxsA2AvailHardwrInstName OBJECT-TYPE
--	SYNTAX DisplayString
--	ACCESS read-only
--	STATUS mandatory
--	DESCRIPTION "&<caiUxsA2.1494>If a resource supports instances, this is the name of an instance. The instance names are retrieved by the corresponding instance script. The agent uses <...PENDING...> as value for the instance name as long as the instance script of this resource is still runing. The agent uses <...TIMEOUT...> as value, if the instance script timed out. The instance name is the third index used by the agent in the different MIB tables for this resource. If a resource does not support instances, the agent automatically uses <none> as third index."
--	::= { uxsA2AvailHardwrEntry 3 }

--uxsA2AvailHardwrAutoWatch OBJECT-TYPE
--	SYNTAX INTEGER {
--		no(1),
--		yes(2)
--	}
--	ACCESS read-only
--	STATUS mandatory
--	DESCRIPTION "&<caiUxsA2.1495>Determines if status watchers or auto watchers (in case the resource supports instances) should be automatically created for each available resource or not."
--	::= { uxsA2AvailHardwrEntry 4 }

--uxsA2AvailHardwrInstSupport OBJECT-TYPE
--	SYNTAX INTEGER {
--		no(1),
--		yes(2)
--	}
--	ACCESS read-only
--	STATUS mandatory
--	DESCRIPTION "&<caiUxsA2.1496>Defines whether the resource supports instances or not."
--	::= { uxsA2AvailHardwrEntry 5 }

--uxsA2AvailHardwrInstScript OBJECT-TYPE
--	SYNTAX DisplayString
--	ACCESS read-only
--	STATUS mandatory
--	DESCRIPTION "&<caiUxsA2.1497>Script to be called to retrieve the available instances (could be the same as the CollectScript). The script must be in a dedicated directory (agents/config/caiUxsA2). Any path element will be ignored."
--	::= { uxsA2AvailHardwrEntry 6 }

--uxsA2AvailHardwrInstArgs OBJECT-TYPE
--	SYNTAX DisplayString
--	ACCESS read-only
--	STATUS mandatory
--	DESCRIPTION "&<caiUxsA2.1498>Arguments passed to the instance script."
--	::= { uxsA2AvailHardwrEntry 7 }

--uxsA2AvailHardwrCollectScript OBJECT-TYPE
--	SYNTAX DisplayString
--	ACCESS read-only
--	STATUS mandatory
--	DESCRIPTION "&<caiUxsA2.1499>Script to be called to retrieve the value for a resource. If a resource supports instances, the script needs to gather the values for all required instances in one call. The script must be in a dedicated directory (agents/config/caiUxsA2). Any path element will be ignored."
--	::= { uxsA2AvailHardwrEntry 8 }

--uxsA2AvailHardwrCollectArgs OBJECT-TYPE
--	SYNTAX DisplayString
--	ACCESS read-only
--	STATUS mandatory
--	DESCRIPTION "&<caiUxsA2.1500>Arguments passed to the collect script. If a resource supports instances, the names of all monitored instances are always appended and passed as last parameters."
--	::= { uxsA2AvailHardwrEntry 9 }

--uxsA2AvailHardwrUserName OBJECT-TYPE
--	SYNTAX DisplayString
--	ACCESS read-only
--	STATUS mandatory
--	DESCRIPTION "&<caiUxsA2.1501>Specifies the user ID to be used for the execution of any script."
--	::= { uxsA2AvailHardwrEntry 10 }

--uxsA2AvailHardwrSkipCount OBJECT-TYPE
--	SYNTAX INTEGER
--	ACCESS read-only
--	STATUS mandatory
--	DESCRIPTION "&<caiUxsA2.1502>Number of polls to be skipped before calling the collect script of this resource again."
--	::= { uxsA2AvailHardwrEntry 11 }

--uxsA2AvailHardwrErrorMsgPattern OBJECT-TYPE
--	SYNTAX DisplayString
--	ACCESS read-only
--	STATUS mandatory
--	DESCRIPTION "&<caiUxsA2.1503>The default value for the pattern attribute used if a status watcher is created."
--	::= { uxsA2AvailHardwrEntry 12 }

--uxsA2AvailHardwrErrorMsgMonitor OBJECT-TYPE
--	SYNTAX INTEGER {
--		do-not-monitor(1),
--		down-warning(2),
--		down-critical(3)
--	}
--	ACCESS read-only
--	STATUS mandatory
--	DESCRIPTION "&<caiUxsA2.1504>The default value for the monitor attribute used if a status watcher is created. If set to 1 (do-not-monitor), the agent does not evaluate the actual state of the resource and sets the status to ok. If set to 2 (down-warning), the agent uses a warning severity if the resource is in bad condition. If set to 3 (down-critical), the agent uses a critical severity if the resource is in bad condition."
--	::= { uxsA2AvailHardwrEntry 13 }

--uxsA2AvailHardwrResultLag OBJECT-TYPE
--	SYNTAX INTEGER
--	ACCESS read-only
--	STATUS mandatory
--	DESCRIPTION "&<caiUxsA2.1505>The default value for the lag attribute used if a status watcher is created."
--	::= { uxsA2AvailHardwrEntry 14 }

--uxsA2AvailHardwrResultWarnMin OBJECT-TYPE
--	SYNTAX DisplayString
--	ACCESS read-only
--	STATUS mandatory
--	DESCRIPTION "&<caiUxsA2.1506>The default value for the warning minimum attribute used if a status watcher is created."
--	::= { uxsA2AvailHardwrEntry 15 }

--uxsA2AvailHardwrResultWarnMax OBJECT-TYPE
--	SYNTAX DisplayString
--	ACCESS read-only
--	STATUS mandatory
--	DESCRIPTION "&<caiUxsA2.1507>The default value for the warning maximum attribute used if a status watcher is created."
--	::= { uxsA2AvailHardwrEntry 16 }

--uxsA2AvailHardwrResultCritMin OBJECT-TYPE
--	SYNTAX DisplayString
--	ACCESS read-only
--	STATUS mandatory
--	DESCRIPTION "&<caiUxsA2.1508>The default value for the critical minimum attribute used if a status watcher is created."
--	::= { uxsA2AvailHardwrEntry 17 }

--uxsA2AvailHardwrResultCritMax OBJECT-TYPE
--	SYNTAX DisplayString
--	ACCESS read-only
--	STATUS mandatory
--	DESCRIPTION "&<caiUxsA2.1509>The default value for the critical maximum attribute used if a status watcher is created."
--	::= { uxsA2AvailHardwrEntry 18 }

--uxsA2AvailHardwrResultMonitor OBJECT-TYPE
--	SYNTAX INTEGER {
--		do-not-monitor(1),
--		warning-only(2),
--		critical-only(3),
--		minimum-only(4),
--		maximum-only(5),
--		all(6)
--	}
--	ACCESS read-only
--	STATUS mandatory
--	DESCRIPTION "&<caiUxsA2.1510>The default value for the monitor attribute used if a status watcher is created. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
--	::= { uxsA2AvailHardwrEntry 19 }

--uxsA2AvailHardwrLossAction OBJECT-TYPE
--	SYNTAX INTEGER {
--		remove(1),
--		up(2),
--		down-warning(3),
--		down-critical(4)
--	}
--	ACCESS read-only
--	STATUS mandatory
--	DESCRIPTION "&<caiUxsA2.1511>The default value for the loss action attribute used if a status watcher is created. Specifies the action to take if the monitored hardware resource is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
--	::= { uxsA2AvailHardwrEntry 20 }

--uxsA2AvailHardwrDescription OBJECT-TYPE
--	SYNTAX DisplayString
--	ACCESS read-only
--	STATUS mandatory
--	DESCRIPTION "&<caiUxsA2.1512>Description for the hardware resource."
--	::= { uxsA2AvailHardwrEntry 21 }

--
-- The AvailProgrm Group
--

uxsA2AvailProgrmResNameFilter OBJECT-TYPE
	SYNTAX DisplayString
	ACCESS read-write
	STATUS mandatory
	DESCRIPTION "&<caiUxsA2.1513>An extended regular expression used to filter the resource names in oder to determine the set of rows displayed in the available table."
	DEFVAL { ".*" }
	::= { uxsA2AvailProgrmGroup 1 }

uxsA2AvailProgrmResSubNameFilter OBJECT-TYPE
	SYNTAX DisplayString
	ACCESS read-write
	STATUS mandatory
	DESCRIPTION "&<caiUxsA2.1514>An extended regular expression used to filter the resource subnames in oder to determine the set of rows displayed in the available table."
	DEFVAL { ".*" }
	::= { uxsA2AvailProgrmGroup 2 }

uxsA2AvailProgrmInstNameFilter OBJECT-TYPE
	SYNTAX DisplayString
	ACCESS read-write
	STATUS mandatory
	DESCRIPTION "&<caiUxsA2.1515>An extended regular expression used to filter the instance names in oder to determine the set of rows displayed in the available table."
	DEFVAL { ".*" }
	::= { uxsA2AvailProgrmGroup 3 }

uxsA2AvailProgrmMatchType OBJECT-TYPE
	SYNTAX INTEGER {
		positive(1),
		negative(2)
	}
	ACCESS read-write
	STATUS mandatory
	DESCRIPTION "&<caiUxsA2.1516>Search algorithm the agent will apply when checking the UNIX System for available programmable resources. The filter is the logical AND of all attributes used to identify or otherwise narrow down resources. If set to 1 (positive), the agent searches for programmable resources that match the filter. If set to 2 (negative), the agent searches for programmable resources that do not match the filter."
	DEFVAL { 1 }
	::= { uxsA2AvailProgrmGroup 4 }

uxsA2AvailProgrmViewWindow OBJECT-TYPE
	SYNTAX DisplayString
	ACCESS read-only
	STATUS mandatory
	DESCRIPTION "&<caiUxsA2.1517>This attribute indicates the number of the currently displayed buffer and the total number of buffers constituting the list of programmable resources that are currently known to the agent and are available for monitoring."
	::= { uxsA2AvailProgrmGroup 5 }

uxsA2AvailProgrmButton OBJECT-TYPE
	SYNTAX INTEGER {
		none(1),
		next(2),
		previous(3),
		refresh(4),
		reinit(5),
		recreate(6)
	}
	ACCESS read-write
	STATUS mandatory
	DESCRIPTION "&<caiUxsA2.1518>This attribute is used to update the list of programmable resources that are currently known to the agent and are available for monitoring. If set to 6 (recreate), 5 (reinit), or 4 (refresh), the agent re-reads the 'Generic.ini' file and refreshes its internal data with the current content of this file. If the file defines resources that support instances, the agent starts all corresponding instance scripts to retrieve a list of available instances for automatic watcher creation or for display in the table (see below). Setting the value to 5 (reinit) has the same effect as refresh; in addition, the agent creates watchers from any new definitions in the ini file or for any new instances found by the instance scripts. Setting the value to 6 (recreate) has the same effect as reinit; in addition, the agent deletes all programmable status and auto watchers beforehand. If set to 4 (refresh), the agent checks the UNIX System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { uxsA2AvailProgrmGroup 6 }

uxsA2AvailProgrmCount OBJECT-TYPE
	SYNTAX INTEGER
	ACCESS read-only
	STATUS mandatory
	DESCRIPTION "&<caiUxsA2.1519>Number of programmable resources that are currently known to the agent and are available for monitoring."
	::= { uxsA2AvailProgrmGroup 7 }

--uxsA2AvailProgrmTable OBJECT-TYPE
--	SYNTAX SEQUENCE OF UxsA2AvailProgrmEntry
--	ACCESS not-accessible
--	STATUS mandatory
--	DESCRIPTION "&<caiUxsA2.1520>Table containing a list of programmable resources that are currently known to the agent and are available for monitoring."
--	::= { uxsA2AvailProgrmGroup 8 }

--uxsA2AvailProgrmEntry OBJECT-TYPE
--	SYNTAX UxsA2AvailProgrmEntry
--	ACCESS not-accessible
--	STATUS mandatory
--	DESCRIPTION "&<caiUxsA2.1521>Entry in the table of available programmable resources."
--	::= { uxsA2AvailProgrmTable 1 }

--UxsA2AvailProgrmEntry ::= SEQUENCE {
--	uxsA2AvailProgrmResName DisplayString,
--	uxsA2AvailProgrmResSubName DisplayString,
--	uxsA2AvailProgrmInstName DisplayString,
--	uxsA2AvailProgrmAutoWatch INTEGER,
--	uxsA2AvailProgrmInstSupport INTEGER,
--	uxsA2AvailProgrmInstScript DisplayString,
--	uxsA2AvailProgrmInstArgs DisplayString,
--	uxsA2AvailProgrmCollectScript DisplayString,
--	uxsA2AvailProgrmCollectArgs DisplayString,
--	uxsA2AvailProgrmUserName DisplayString,
--	uxsA2AvailProgrmSkipCount INTEGER,
--	uxsA2AvailProgrmErrorMsgPattern DisplayString,
--	uxsA2AvailProgrmErrorMsgMonitor INTEGER,
--	uxsA2AvailProgrmResultLag INTEGER,
--	uxsA2AvailProgrmResultWarnMin DisplayString,
--	uxsA2AvailProgrmResultWarnMax DisplayString,
--	uxsA2AvailProgrmResultCritMin DisplayString,
--	uxsA2AvailProgrmResultCritMax DisplayString,
--	uxsA2AvailProgrmResultMonitor INTEGER,
--	uxsA2AvailProgrmLossAction INTEGER,
--	uxsA2AvailProgrmDescription DisplayString
--}

--uxsA2AvailProgrmResName OBJECT-TYPE
--	SYNTAX DisplayString
--	ACCESS read-only
--	STATUS mandatory
--	DESCRIPTION "&<caiUxsA2.1522>The name of the resource. This is the first index used by the agent in the different MIB tables for this resource (e.g. PowerSupply)."
--	::= { uxsA2AvailProgrmEntry 1 }

--uxsA2AvailProgrmResSubName OBJECT-TYPE
--	SYNTAX DisplayString
--	ACCESS read-only
--	STATUS mandatory
--	DESCRIPTION "&<caiUxsA2.1523>The subname of the resource. This is the second index used by the agent in the different MIB tables for this resource (e.g. Voltage)."
--	::= { uxsA2AvailProgrmEntry 2 }

--uxsA2AvailProgrmInstName OBJECT-TYPE
--	SYNTAX DisplayString
--	ACCESS read-only
--	STATUS mandatory
--	DESCRIPTION "&<caiUxsA2.1524>If a resource supports instances, this is the name of an instance. The instance names are retrieved by the corresponding instance script. The agent uses <...PENDING...> as value for the instance name as long as the instance script of this resource is still runing. The agent uses <...TIMEOUT...> as value, if the instance script timed out. The instance name is the third index used by the agent in the different MIB tables for this resource. If a resource does not support instances, the agent automatically uses <none> as third index."
--	::= { uxsA2AvailProgrmEntry 3 }

--uxsA2AvailProgrmAutoWatch OBJECT-TYPE
--	SYNTAX INTEGER {
--		no(1),
--		yes(2)
--	}
--	ACCESS read-only
--	STATUS mandatory
--	DESCRIPTION "&<caiUxsA2.1525>Determines if status watchers or auto watchers (in case the resource supports instances) should be automatically created for each available resource or not."
--	::= { uxsA2AvailProgrmEntry 4 }

--uxsA2AvailProgrmInstSupport OBJECT-TYPE
--	SYNTAX INTEGER {
--		no(1),
--		yes(2)
--	}
--	ACCESS read-only
--	STATUS mandatory
--	DESCRIPTION "&<caiUxsA2.1526>Defines whether the resource supports instances or not."
--	::= { uxsA2AvailProgrmEntry 5 }

--uxsA2AvailProgrmInstScript OBJECT-TYPE
--	SYNTAX DisplayString
--	ACCESS read-only
--	STATUS mandatory
--	DESCRIPTION "&<caiUxsA2.1527>Script to be called to retrieve the available instances (could be the same as the CollectScript). The script must be in a dedicated directory (agents/config/caiUxsA2). Any path element will be ignored."
--	::= { uxsA2AvailProgrmEntry 6 }

--uxsA2AvailProgrmInstArgs OBJECT-TYPE
--	SYNTAX DisplayString
--	ACCESS read-only
--	STATUS mandatory
--	DESCRIPTION "&<caiUxsA2.1528>Arguments passed to the instance script."
--	::= { uxsA2AvailProgrmEntry 7 }

--uxsA2AvailProgrmCollectScript OBJECT-TYPE
--	SYNTAX DisplayString
--	ACCESS read-only
--	STATUS mandatory
--	DESCRIPTION "&<caiUxsA2.1529>Script to be called to retrieve the value for a resource. If a resource supports instances, the script needs to gather the values for all required instances in one call. The script must be in a dedicated directory (agents/config/caiUxsA2). Any path element will be ignored."
--	::= { uxsA2AvailProgrmEntry 8 }

--uxsA2AvailProgrmCollectArgs OBJECT-TYPE
--	SYNTAX DisplayString
--	ACCESS read-only
--	STATUS mandatory
--	DESCRIPTION "&<caiUxsA2.1530>Arguments passed to the collect script. If a resource supports instances, the names of all monitored instances are always appended and passed as last parameters."
--	::= { uxsA2AvailProgrmEntry 9 }

--uxsA2AvailProgrmUserName OBJECT-TYPE
--	SYNTAX DisplayString
--	ACCESS read-only
--	STATUS mandatory
--	DESCRIPTION "&<caiUxsA2.1531>Specifies the user ID to be used for the execution of any script."
--	::= { uxsA2AvailProgrmEntry 10 }

--uxsA2AvailProgrmSkipCount OBJECT-TYPE
--	SYNTAX INTEGER
--	ACCESS read-only
--	STATUS mandatory
--	DESCRIPTION "&<caiUxsA2.1532>Number of polls to be skipped before calling the collect script of this resource again."
--	::= { uxsA2AvailProgrmEntry 11 }

--uxsA2AvailProgrmErrorMsgPattern OBJECT-TYPE
--	SYNTAX DisplayString
--	ACCESS read-only
--	STATUS mandatory
--	DESCRIPTION "&<caiUxsA2.1533>The default value for the pattern attribute used if a status watcher is created."
--	::= { uxsA2AvailProgrmEntry 12 }

--uxsA2AvailProgrmErrorMsgMonitor OBJECT-TYPE
--	SYNTAX INTEGER {
--		do-not-monitor(1),
--		down-warning(2),
--		down-critical(3)
--	}
--	ACCESS read-only
--	STATUS mandatory
--	DESCRIPTION "&<caiUxsA2.1534>The default value for the monitor attribute used if a status watcher is created. If set to 1 (do-not-monitor), the agent does not evaluate the actual state of the resource and sets the status to ok. If set to 2 (down-warning), the agent uses a warning severity if the resource is in bad condition. If set to 3 (down-critical), the agent uses a critical severity if the resource is in bad condition."
--	::= { uxsA2AvailProgrmEntry 13 }

--uxsA2AvailProgrmResultLag OBJECT-TYPE
--	SYNTAX INTEGER
--	ACCESS read-only
--	STATUS mandatory
--	DESCRIPTION "&<caiUxsA2.1535>The default value for the lag attribute used if a status watcher is created."
--	::= { uxsA2AvailProgrmEntry 14 }

--uxsA2AvailProgrmResultWarnMin OBJECT-TYPE
--	SYNTAX DisplayString
--	ACCESS read-only
--	STATUS mandatory
--	DESCRIPTION "&<caiUxsA2.1536>The default value for the warning minimum attribute used if a status watcher is created."
--	::= { uxsA2AvailProgrmEntry 15 }

--uxsA2AvailProgrmResultWarnMax OBJECT-TYPE
--	SYNTAX DisplayString
--	ACCESS read-only
--	STATUS mandatory
--	DESCRIPTION "&<caiUxsA2.1537>The default value for the warning maximum attribute used if a status watcher is created."
--	::= { uxsA2AvailProgrmEntry 16 }

--uxsA2AvailProgrmResultCritMin OBJECT-TYPE
--	SYNTAX DisplayString
--	ACCESS read-only
--	STATUS mandatory
--	DESCRIPTION "&<caiUxsA2.1538>The default value for the critical minimum attribute used if a status watcher is created."
--	::= { uxsA2AvailProgrmEntry 17 }

--uxsA2AvailProgrmResultCritMax OBJECT-TYPE
--	SYNTAX DisplayString
--	ACCESS read-only
--	STATUS mandatory
--	DESCRIPTION "&<caiUxsA2.1539>The default value for the critical maximum attribute used if a status watcher is created."
--	::= { uxsA2AvailProgrmEntry 18 }

--uxsA2AvailProgrmResultMonitor OBJECT-TYPE
--	SYNTAX INTEGER {
--		do-not-monitor(1),
--		warning-only(2),
--		critical-only(3),
--		minimum-only(4),
--		maximum-only(5),
--		all(6)
--	}
--	ACCESS read-only
--	STATUS mandatory
--	DESCRIPTION "&<caiUxsA2.1540>The default value for the monitor attribute used if a status watcher is created. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
--	::= { uxsA2AvailProgrmEntry 19 }

--uxsA2AvailProgrmLossAction OBJECT-TYPE
--	SYNTAX INTEGER {
--		remove(1),
--		up(2),
--		down-warning(3),
--		down-critical(4)
--	}
--	ACCESS read-only
--	STATUS mandatory
--	DESCRIPTION "&<caiUxsA2.1541>The default value for the loss action attribute used if a status watcher is created. Specifies the action to take if the monitored programmable resource is removed from the UNIX System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
--	::= { uxsA2AvailProgrmEntry 20 }

--uxsA2AvailProgrmDescription OBJECT-TYPE
--	SYNTAX DisplayString
--	ACCESS read-only
--	STATUS mandatory
--	DESCRIPTION "&<caiUxsA2.1542>Description for the programmable resource."
--	::= { uxsA2AvailProgrmEntry 21 }

--
-- The History Group
--

uxsA2HistoryResParamCollect OBJECT-TYPE
	SYNTAX INTEGER {
		no(1),
		yes(2)
	}
	ACCESS read-write
	STATUS mandatory
	DESCRIPTION "&<caiUxsA2.1543>This attribute is used to enable/disable the collection of OS resource parameter status traps in the history table. If set to 2 (yes), the agent collects status traps in the history table. If set to 1 (no) these traps are not stored in the history table."
	DEFVAL { 1 }
	::= { uxsA2HistoryGroup 1 }

uxsA2HistoryCPUCollect OBJECT-TYPE
	SYNTAX INTEGER {
		no(1),
		yes(2)
	}
	ACCESS read-write
	STATUS mandatory
	DESCRIPTION "&<caiUxsA2.1544>This attribute is used to enable/disable the collection of CPU status traps in the history table. If set to 2 (yes), the agent collects status traps in the history table. If set to 1 (no) these traps are not stored in the history table."
	DEFVAL { 1 }
	::= { uxsA2HistoryGroup 2 }

uxsA2HistoryLoadCollect OBJECT-TYPE
	SYNTAX INTEGER {
		no(1),
		yes(2)
	}
	ACCESS read-write
	STATUS mandatory
	DESCRIPTION "&<caiUxsA2.1545>This attribute is used to enable/disable the collection of load average status traps in the history table. If set to 2 (yes), the agent collects status traps in the history table. If set to 1 (no) these traps are not stored in the history table."
	DEFVAL { 1 }
	::= { uxsA2HistoryGroup 3 }

uxsA2HistoryMemCollect OBJECT-TYPE
	SYNTAX INTEGER {
		no(1),
		yes(2)
	}
	ACCESS read-write
	STATUS mandatory
	DESCRIPTION "&<caiUxsA2.1546>This attribute is used to enable/disable the collection of real memory status traps in the history table. If set to 2 (yes), the agent collects status traps in the history table. If set to 1 (no) these traps are not stored in the history table."
	DEFVAL { 1 }
	::= { uxsA2HistoryGroup 4 }

uxsA2HistorySwapCollect OBJECT-TYPE
	SYNTAX INTEGER {
		no(1),
		yes(2)
	}
	ACCESS read-write
	STATUS mandatory
	DESCRIPTION "&<caiUxsA2.1547>This attribute is used to enable/disable the collection of swap status traps in the history table. If set to 2 (yes), the agent collects status traps in the history table. If set to 1 (no) these traps are not stored in the history table."
	DEFVAL { 1 }
	::= { uxsA2HistoryGroup 5 }

uxsA2HistoryQuotaCollect OBJECT-TYPE
	SYNTAX INTEGER {
		no(1),
		yes(2)
	}
	ACCESS read-write
	STATUS mandatory
	DESCRIPTION "&<caiUxsA2.1548>This attribute is used to enable/disable the collection of quota status traps in the history table. If set to 2 (yes), the agent collects status traps in the history table. If set to 1 (no) these traps are not stored in the history table."
	DEFVAL { 1 }
	::= { uxsA2HistoryGroup 6 }

uxsA2HistoryDirCollect OBJECT-TYPE
	SYNTAX INTEGER {
		no(1),
		yes(2)
	}
	ACCESS read-write
	STATUS mandatory
	DESCRIPTION "&<caiUxsA2.1549>This attribute is used to enable/disable the collection of directory status traps in the history table. If set to 2 (yes), the agent collects status traps in the history table. If set to 1 (no) these traps are not stored in the history table."
	DEFVAL { 1 }
	::= { uxsA2HistoryGroup 7 }

uxsA2HistoryFSysCollect OBJECT-TYPE
	SYNTAX INTEGER {
		no(1),
		yes(2)
	}
	ACCESS read-write
	STATUS mandatory
	DESCRIPTION "&<caiUxsA2.1550>This attribute is used to enable/disable the collection of file system status traps in the history table. If set to 2 (yes), the agent collects status traps in the history table. If set to 1 (no) these traps are not stored in the history table."
	DEFVAL { 1 }
	::= { uxsA2HistoryGroup 8 }

uxsA2HistoryFileCollect OBJECT-TYPE
	SYNTAX INTEGER {
		no(1),
		yes(2)
	}
	ACCESS read-write
	STATUS mandatory
	DESCRIPTION "&<caiUxsA2.1551>This attribute is used to enable/disable the collection of file status traps in the history table. If set to 2 (yes), the agent collects status traps in the history table. If set to 1 (no) these traps are not stored in the history table."
	DEFVAL { 1 }
	::= { uxsA2HistoryGroup 9 }

uxsA2HistoryDiskCollect OBJECT-TYPE
	SYNTAX INTEGER {
		no(1),
		yes(2)
	}
	ACCESS read-write
	STATUS mandatory
	DESCRIPTION "&<caiUxsA2.1552>This attribute is used to enable/disable the collection of disk status traps in the history table. If set to 2 (yes), the agent collects status traps in the history table. If set to 1 (no) these traps are not stored in the history table."
	DEFVAL { 1 }
	::= { uxsA2HistoryGroup 10 }

uxsA2HistoryProcCollect OBJECT-TYPE
	SYNTAX INTEGER {
		no(1),
		yes(2)
	}
	ACCESS read-write
	STATUS mandatory
	DESCRIPTION "&<caiUxsA2.1553>This attribute is used to enable/disable the collection of process status traps in the history table. If set to 2 (yes), the agent collects status traps in the history table. If set to 1 (no) these traps are not stored in the history table."
	DEFVAL { 1 }
	::= { uxsA2HistoryGroup 11 }

uxsA2HistoryPrnCollect OBJECT-TYPE
	SYNTAX INTEGER {
		no(1),
		yes(2)
	}
	ACCESS read-write
	STATUS mandatory
	DESCRIPTION "&<caiUxsA2.1554>This attribute is used to enable/disable the collection of print queue status traps in the history table. If set to 2 (yes), the agent collects status traps in the history table. If set to 1 (no) these traps are not stored in the history table."
	DEFVAL { 1 }
	::= { uxsA2HistoryGroup 12 }

uxsA2HistoryNetCollect OBJECT-TYPE
	SYNTAX INTEGER {
		no(1),
		yes(2)
	}
	ACCESS read-write
	STATUS mandatory
	DESCRIPTION "&<caiUxsA2.1555>This attribute is used to enable/disable the collection of network interface status traps in the history table. If set to 2 (yes), the agent collects status traps in the history table. If set to 1 (no) these traps are not stored in the history table."
	DEFVAL { 1 }
	::= { uxsA2HistoryGroup 13 }

uxsA2HistorySHMCollect OBJECT-TYPE
	SYNTAX INTEGER {
		no(1),
		yes(2)
	}
	ACCESS read-write
	STATUS mandatory
	DESCRIPTION "&<caiUxsA2.1556>This attribute is used to enable/disable the collection of shared memory status traps in the history table. If set to 2 (yes), the agent collects status traps in the history table. If set to 1 (no) these traps are not stored in the history table."
	DEFVAL { 1 }
	::= { uxsA2HistoryGroup 14 }

uxsA2HistorySEMCollect OBJECT-TYPE
	SYNTAX INTEGER {
		no(1),
		yes(2)
	}
	ACCESS read-write
	STATUS mandatory
	DESCRIPTION "&<caiUxsA2.1557>This attribute is used to enable/disable the collection of semaphore status traps in the history table. If set to 2 (yes), the agent collects status traps in the history table. If set to 1 (no) these traps are not stored in the history table."
	DEFVAL { 1 }
	::= { uxsA2HistoryGroup 15 }

uxsA2HistoryMQCollect OBJECT-TYPE
	SYNTAX INTEGER {
		no(1),
		yes(2)
	}
	ACCESS read-write
	STATUS mandatory
	DESCRIPTION "&<caiUxsA2.1558>This attribute is used to enable/disable the collection of message queue status traps in the history table. If set to 2 (yes), the agent collects status traps in the history table. If set to 1 (no) these traps are not stored in the history table."
	DEFVAL { 1 }
	::= { uxsA2HistoryGroup 16 }

uxsA2HistoryHardwrCollect OBJECT-TYPE
	SYNTAX INTEGER {
		no(1),
		yes(2)
	}
	ACCESS read-write
	STATUS mandatory
	DESCRIPTION "&<caiUxsA2.1559>This attribute is used to enable/disable the collection of hardware resource status traps in the history table. If set to 2 (yes), the agent collects status traps in the history table. If set to 1 (no) these traps are not stored in the history table."
	DEFVAL { 1 }
	::= { uxsA2HistoryGroup 17 }

uxsA2HistoryProgrmCollect OBJECT-TYPE
	SYNTAX INTEGER {
		no(1),
		yes(2)
	}
	ACCESS read-write
	STATUS mandatory
	DESCRIPTION "&<caiUxsA2.1560>This attribute is used to enable/disable the collection of programmable resource status traps in the history table. If set to 2 (yes), the agent collects status traps in the history table. If set to 1 (no) these traps are not stored in the history table."
	DEFVAL { 1 }
	::= { uxsA2HistoryGroup 18 }

uxsA2HistoryMaxEntries OBJECT-TYPE
	SYNTAX INTEGER
	ACCESS read-write
	STATUS mandatory
	DESCRIPTION "&<caiUxsA2.1561>Maximum number of entries to be stored in the history table. Valid values are 0 to 100. If set to 0 no history information of traps is stored."
	DEFVAL { 50 }
	::= { uxsA2HistoryGroup 19 }

uxsA2HistoryButton OBJECT-TYPE
	SYNTAX INTEGER {
		none(1),
		clear(2)
	}
	ACCESS read-write
	STATUS mandatory
	DESCRIPTION "&<caiUxsA2.1562>This attribute is used to clear the history table. If set to 2 (clear), the agent empties the history table. This attribute cannot be set to 1 (none)."
	DEFVAL { 1 }
	::= { uxsA2HistoryGroup 20 }

uxsA2HistoryCount OBJECT-TYPE
	SYNTAX INTEGER
	ACCESS read-only
	STATUS mandatory
	DESCRIPTION "&<caiUxsA2.1563>Number of the last enterprise specific status traps raised by the agent."
	::= { uxsA2HistoryGroup 21 }

--uxsA2HistoryTable OBJECT-TYPE
--	SYNTAX SEQUENCE OF UxsA2HistoryEntry
--	ACCESS not-accessible
--	STATUS mandatory
--	DESCRIPTION "&<caiUxsA2.1564>Table containing the last enterprise specific status traps raised by the agent."
--	::= { uxsA2HistoryGroup 22 }

--uxsA2HistoryEntry OBJECT-TYPE
--	SYNTAX UxsA2HistoryEntry
--	ACCESS not-accessible
--	STATUS mandatory
--	DESCRIPTION "&<caiUxsA2.1565>Entry in the history table."
--	::= { uxsA2HistoryTable 1 }

--UxsA2HistoryEntry ::= SEQUENCE {
--	uxsA2HistoryTrapName DisplayString,
--	uxsA2HistoryTrapNumber INTEGER,
--	uxsA2HistoryTrapTime DisplayString,
--	uxsA2HistoryTrapVarBind DisplayString
--}

--uxsA2HistoryTrapName OBJECT-TYPE
--	SYNTAX DisplayString
--	ACCESS read-only
--	STATUS mandatory
--	DESCRIPTION "&<caiUxsA2.1566>Name of the trap as defined in the MIB."
--	::= { uxsA2HistoryEntry 1 }

--uxsA2HistoryTrapNumber OBJECT-TYPE
--	SYNTAX INTEGER
--	ACCESS read-only
--	STATUS mandatory
--	DESCRIPTION "&<caiUxsA2.1567>Enterprise specific trap type number."
--	::= { uxsA2HistoryEntry 2 }

--uxsA2HistoryTrapTime OBJECT-TYPE
--	SYNTAX DisplayString
--	ACCESS read-only
--	STATUS mandatory
--	DESCRIPTION "&<caiUxsA2.1568>Date and time the trap was sent."
--	::= { uxsA2HistoryEntry 3 }

--uxsA2HistoryTrapVarBind OBJECT-TYPE
--	SYNTAX DisplayString
--	ACCESS read-only
--	STATUS mandatory
--	DESCRIPTION "&<caiUxsA2.1569>A comma separated list of the varbinds the agent sent with the trap. Each element has the form 'attribute=value'."
--	::= { uxsA2HistoryEntry 4 }

--
-- The Traps
--

--
-- The ResParam Traps
--

uxsA2ResParamUnknown TRAP-TYPE
	ENTERPRISE caiUxsA2
	VARIABLES {
		uxsA2StatusResParamName,
		uxsA2ConfigGeneralAgentVersion
	}
	DESCRIPTION "&<caiUxsA2.1570>A watcher monitoring an OS resource parameter resource changed its status to 'unknown'. The varbind list contains a varbind with detailed information, encoded as a single string, including the name of the involved resource and the type and value of the involved metric; if applicable, the varbind also includes the current threshold settings and other information useful for automation purposes."
	::= 10980

uxsA2ResParamOk TRAP-TYPE
	ENTERPRISE caiUxsA2
	VARIABLES {
		uxsA2StatusResParamName,
		uxsA2ConfigGeneralAgentVersion
	}
	DESCRIPTION "&<caiUxsA2.1571>A watcher monitoring an OS resource parameter resource changed its status to 'ok'. The varbind list contains a varbind with detailed information, encoded as a single string, including the name of the involved resource and the type and value of the involved metric; if applicable, the varbind also includes the current threshold settings and other information useful for automation purposes."
	::= 10981

uxsA2ResParamWarning TRAP-TYPE
	ENTERPRISE caiUxsA2
	VARIABLES {
		uxsA2StatusResParamName,
		uxsA2ConfigGeneralAgentVersion
	}
	DESCRIPTION "&<caiUxsA2.1572>A watcher monitoring an OS resource parameter resource changed its status to 'warning'. The varbind list contains a varbind with detailed information, encoded as a single string, including the name of the involved resource and the type and value of the involved metric; if applicable, the varbind also includes the current threshold settings and other information useful for automation purposes."
	::= 10982

uxsA2ResParamCritical TRAP-TYPE
	ENTERPRISE caiUxsA2
	VARIABLES {
		uxsA2StatusResParamName,
		uxsA2ConfigGeneralAgentVersion
	}
	DESCRIPTION "&<caiUxsA2.1573>A watcher monitoring an OS resource parameter resource changed its status to 'critical'. The varbind list contains a varbind with detailed information, encoded as a single string, including the name of the involved resource and the type and value of the involved metric; if applicable, the varbind also includes the current threshold settings and other information useful for automation purposes."
	::= 10983

uxsA2ResParamActive TRAP-TYPE
	ENTERPRISE caiUxsA2
	VARIABLES {
		uxsA2StatusResParamName,
		uxsA2ConfigGeneralAgentVersion
	}
	DESCRIPTION "&<caiUxsA2.1574>A watcher monitoring an OS resource parameter resource changed its status from 'passive'. The varbind list contains a varbind with detailed information, encoded as a single string, including the name of the involved resource and the type and value of the involved metric; if applicable, the varbind also includes the current threshold settings and other information useful for automation purposes."
	::= 10984

uxsA2ResParamPassive TRAP-TYPE
	ENTERPRISE caiUxsA2
	VARIABLES {
		uxsA2StatusResParamName,
		uxsA2ConfigGeneralAgentVersion
	}
	DESCRIPTION "&<caiUxsA2.1575>A watcher monitoring an OS resource parameter resource changed its status to 'passive'. The varbind list contains a varbind with detailed information, encoded as a single string, including the name of the involved resource and the type and value of the involved metric; if applicable, the varbind also includes the current threshold settings and other information useful for automation purposes."
	::= 10985

uxsA2ResParamAdded TRAP-TYPE
	ENTERPRISE caiUxsA2
	VARIABLES {
		uxsA2StatusResParamName
	}
	DESCRIPTION "&<caiUxsA2.1576>A watcher monitoring an OS resource parameter resource was added. The varbind list contains the name of the involved resource."
	::= 10986

uxsA2ResParamDeleted TRAP-TYPE
	ENTERPRISE caiUxsA2
	VARIABLES {
		uxsA2StatusResParamName
	}
	DESCRIPTION "&<caiUxsA2.1577>A watcher monitoring an OS resource parameter resource was removed. The varbind list contains the name of the involved resource."
	::= 10987

uxsA2ResParamInfo TRAP-TYPE
	ENTERPRISE caiUxsA2
	VARIABLES {
		uxsA2ConfigGeneralAgentVersion
	}
	DESCRIPTION "&<caiUxsA2.1578>A watcher monitoring an OS resource parameter resource changed a sub-state. The varbind list contains a varbind with detailed information, encoded as a single string, including the name of the involved resource, the old and the new status, and the type and value of the involved metric; if applicable, the varbind also includes the current threshold settings and other information useful for automation purposes."
	::= 10988

uxsA2ResParamModified TRAP-TYPE
	ENTERPRISE caiUxsA2
	VARIABLES {
		uxsA2ConfigGeneralAgentVersion
	}
	DESCRIPTION "&<caiUxsA2.1579>The watcher configuration for an OS resource parameter resource changed. The varbind list contains a varbind with detailed information, encoded as a single string, including the name of the involved resource and the changed attribute with its old value and with its new value."
	::= 10989

--
-- The CPUTotalLoad Traps
--

uxsA2CPUTotalLoadUnknown TRAP-TYPE
	ENTERPRISE caiUxsA2
	VARIABLES {
		uxsA2ConfigGeneralAgentVersion
	}
	DESCRIPTION "&<caiUxsA2.1580>A watcher monitoring the total CPU utilization of a CPU resource changed its status to 'unknown'. The varbind list contains a varbind with detailed information, encoded as a single string, including the type and value of the involved metric; if applicable, the varbind also includes the current threshold settings and other information useful for automation purposes."
	::= 11000

uxsA2CPUTotalLoadOk TRAP-TYPE
	ENTERPRISE caiUxsA2
	VARIABLES {
		uxsA2ConfigGeneralAgentVersion
	}
	DESCRIPTION "&<caiUxsA2.1581>A watcher monitoring the total CPU utilization of a CPU resource changed its status to 'ok'. The varbind list contains a varbind with detailed information, encoded as a single string, including the type and value of the involved metric; if applicable, the varbind also includes the current threshold settings and other information useful for automation purposes."
	::= 11001

uxsA2CPUTotalLoadWarning TRAP-TYPE
	ENTERPRISE caiUxsA2
	VARIABLES {
		uxsA2ConfigGeneralAgentVersion
	}
	DESCRIPTION "&<caiUxsA2.1582>A watcher monitoring the total CPU utilization of a CPU resource changed its status to 'warning'. The varbind list contains a varbind with detailed information, encoded as a single string, including the type and value of the involved metric; if applicable, the varbind also includes the current threshold settings and other information useful for automation purposes."
	::= 11002

uxsA2CPUTotalLoadCritical TRAP-TYPE
	ENTERPRISE caiUxsA2
	VARIABLES {
		uxsA2ConfigGeneralAgentVersion
	}
	DESCRIPTION "&<caiUxsA2.1583>A watcher monitoring the total CPU utilization of a CPU resource changed its status to 'critical'. The varbind list contains a varbind with detailed information, encoded as a single string, including the type and value of the involved metric; if applicable, the varbind also includes the current threshold settings and other information useful for automation purposes."
	::= 11003

uxsA2CPUTotalLoadActive TRAP-TYPE
	ENTERPRISE caiUxsA2
	VARIABLES {
		uxsA2ConfigGeneralAgentVersion
	}
	DESCRIPTION "&<caiUxsA2.1584>A watcher monitoring the total CPU utilization of a CPU resource changed its status from 'passive'. The varbind list contains a varbind with detailed information, encoded as a single string, including the type and value of the involved metric; if applicable, the varbind also includes the current threshold settings and other information useful for automation purposes."
	::= 11004

uxsA2CPUTotalLoadPassive TRAP-TYPE
	ENTERPRISE caiUxsA2
	VARIABLES {
		uxsA2ConfigGeneralAgentVersion
	}
	DESCRIPTION "&<caiUxsA2.1585>A watcher monitoring the total CPU utilization of a CPU resource changed its status to 'passive'. The varbind list contains a varbind with detailed information, encoded as a single string, including the type and value of the involved metric; if applicable, the varbind also includes the current threshold settings and other information useful for automation purposes."
	::= 11005

uxsA2CPUTotalLoadModified TRAP-TYPE
	ENTERPRISE caiUxsA2
	VARIABLES {
		uxsA2ConfigGeneralAgentVersion
	}
	DESCRIPTION "&<caiUxsA2.1586>The watcher configuration for the total CPU utilization monitoring of a CPU resource changed. The varbind list contains a varbind with detailed information, encoded as a single string, including the changed attribute with its old value and with its new value."
	::= 11009

--
-- The CPU Traps
--

uxsA2CPUUnknown TRAP-TYPE
	ENTERPRISE caiUxsA2
	VARIABLES {
		uxsA2StatusCPUName,
		uxsA2ConfigGeneralAgentVersion
	}
	DESCRIPTION "&<caiUxsA2.1587>A watcher monitoring a CPU resource changed its status to 'unknown'. The varbind list contains a varbind with detailed information, encoded as a single string, including the name of the involved resource and the type and value of the involved metric; if applicable, the varbind also includes the current threshold settings and other information useful for automation purposes."
	::= 11990

uxsA2CPUOk TRAP-TYPE
	ENTERPRISE caiUxsA2
	VARIABLES {
		uxsA2StatusCPUName,
		uxsA2ConfigGeneralAgentVersion
	}
	DESCRIPTION "&<caiUxsA2.1588>A watcher monitoring a CPU resource changed its status to 'ok'. The varbind list contains a varbind with detailed information, encoded as a single string, including the name of the involved resource and the type and value of the involved metric; if applicable, the varbind also includes the current threshold settings and other information useful for automation purposes."
	::= 11991

uxsA2CPUWarning TRAP-TYPE
	ENTERPRISE caiUxsA2
	VARIABLES {
		uxsA2StatusCPUName,
		uxsA2ConfigGeneralAgentVersion
	}
	DESCRIPTION "&<caiUxsA2.1589>A watcher monitoring a CPU resource changed its status to 'warning'. The varbind list contains a varbind with detailed information, encoded as a single string, including the name of the involved resource and the type and value of the involved metric; if applicable, the varbind also includes the current threshold settings and other information useful for automation purposes."
	::= 11992

uxsA2CPUCritical TRAP-TYPE
	ENTERPRISE caiUxsA2
	VARIABLES {
		uxsA2StatusCPUName,
		uxsA2ConfigGeneralAgentVersion
	}
	DESCRIPTION "&<caiUxsA2.1590>A watcher monitoring a CPU resource changed its status to 'critical'. The varbind list contains a varbind with detailed information, encoded as a single string, including the name of the involved resource and the type and value of the involved metric; if applicable, the varbind also includes the current threshold settings and other information useful for automation purposes."
	::= 11993

uxsA2CPUActive TRAP-TYPE
	ENTERPRISE caiUxsA2
	VARIABLES {
		uxsA2StatusCPUName,
		uxsA2ConfigGeneralAgentVersion
	}
	DESCRIPTION "&<caiUxsA2.1591>A watcher monitoring a CPU resource changed its status from 'passive'. The varbind list contains a varbind with detailed information, encoded as a single string, including the name of the involved resource and the type and value of the involved metric; if applicable, the varbind also includes the current threshold settings and other information useful for automation purposes."
	::= 11994

uxsA2CPUPassive TRAP-TYPE
	ENTERPRISE caiUxsA2
	VARIABLES {
		uxsA2StatusCPUName,
		uxsA2ConfigGeneralAgentVersion
	}
	DESCRIPTION "&<caiUxsA2.1592>A watcher monitoring a CPU resource changed its status to 'passive'. The varbind list contains a varbind with detailed information, encoded as a single string, including the name of the involved resource and the type and value of the involved metric; if applicable, the varbind also includes the current threshold settings and other information useful for automation purposes."
	::= 11995

uxsA2CPUAdded TRAP-TYPE
	ENTERPRISE caiUxsA2
	VARIABLES {
		uxsA2StatusCPUName
	}
	DESCRIPTION "&<caiUxsA2.1593>A watcher monitoring a CPU resource was added. The varbind list contains the name of the involved resource."
	::= 11996

uxsA2CPUDeleted TRAP-TYPE
	ENTERPRISE caiUxsA2
	VARIABLES {
		uxsA2StatusCPUName
	}
	DESCRIPTION "&<caiUxsA2.1594>A watcher monitoring a CPU resource was removed. The varbind list contains the name of the involved resource."
	::= 11997

uxsA2CPUInfo TRAP-TYPE
	ENTERPRISE caiUxsA2
	VARIABLES {
		uxsA2ConfigGeneralAgentVersion
	}
	DESCRIPTION "&<caiUxsA2.1595>A watcher monitoring a CPU resource changed a sub-state. The varbind list contains a varbind with detailed information, encoded as a single string, including the name of the involved resource, the old and the new status, and the type and value of the involved metric; if applicable, the varbind also includes the current threshold settings and other information useful for automation purposes."
	::= 11998

uxsA2CPUModified TRAP-TYPE
	ENTERPRISE caiUxsA2
	VARIABLES {
		uxsA2ConfigGeneralAgentVersion
	}
	DESCRIPTION "&<caiUxsA2.1596>The watcher configuration for a CPU resource changed. The varbind list contains a varbind with detailed information, encoded as a single string, including the name of the involved resource and the changed attribute with its old value and with its new value."
	::= 11999

--
-- The Load1Min Traps
--

uxsA2Load1MinUnknown TRAP-TYPE
	ENTERPRISE caiUxsA2
	VARIABLES {
		uxsA2ConfigGeneralAgentVersion
	}
	DESCRIPTION "&<caiUxsA2.1597>A watcher monitoring the 1 minute load average of a load average resource changed its status to 'unknown'. The varbind list contains a varbind with detailed information, encoded as a single string, including the type and value of the involved metric; if applicable, the varbind also includes the current threshold settings and other information useful for automation purposes."
	::= 12010

uxsA2Load1MinOk TRAP-TYPE
	ENTERPRISE caiUxsA2
	VARIABLES {
		uxsA2ConfigGeneralAgentVersion
	}
	DESCRIPTION "&<caiUxsA2.1598>A watcher monitoring the 1 minute load average of a load average resource changed its status to 'ok'. The varbind list contains a varbind with detailed information, encoded as a single string, including the type and value of the involved metric; if applicable, the varbind also includes the current threshold settings and other information useful for automation purposes."
	::= 12011

uxsA2Load1MinWarning TRAP-TYPE
	ENTERPRISE caiUxsA2
	VARIABLES {
		uxsA2ConfigGeneralAgentVersion
	}
	DESCRIPTION "&<caiUxsA2.1599>A watcher monitoring the 1 minute load average of a load average resource changed its status to 'warning'. The varbind list contains a varbind with detailed information, encoded as a single string, including the type and value of the involved metric; if applicable, the varbind also includes the current threshold settings and other information useful for automation purposes."
	::= 12012

uxsA2Load1MinCritical TRAP-TYPE
	ENTERPRISE caiUxsA2
	VARIABLES {
		uxsA2ConfigGeneralAgentVersion
	}
	DESCRIPTION "&<caiUxsA2.1600>A watcher monitoring the 1 minute load average of a load average resource changed its status to 'critical'. The varbind list contains a varbind with detailed information, encoded as a single string, including the type and value of the involved metric; if applicable, the varbind also includes the current threshold settings and other information useful for automation purposes."
	::= 12013

uxsA2Load1MinActive TRAP-TYPE
	ENTERPRISE caiUxsA2
	VARIABLES {
		uxsA2ConfigGeneralAgentVersion
	}
	DESCRIPTION "&<caiUxsA2.1601>A watcher monitoring the 1 minute load average of a load average resource changed its status from 'passive'. The varbind list contains a varbind with detailed information, encoded as a single string, including the type and value of the involved metric; if applicable, the varbind also includes the current threshold settings and other information useful for automation purposes."
	::= 12014

uxsA2Load1MinPassive TRAP-TYPE
	ENTERPRISE caiUxsA2
	VARIABLES {
		uxsA2ConfigGeneralAgentVersion
	}
	DESCRIPTION "&<caiUxsA2.1602>A watcher monitoring the 1 minute load average of a load average resource changed its status to 'passive'. The varbind list contains a varbind with detailed information, encoded as a single string, including the type and value of the involved metric; if applicable, the varbind also includes the current threshold settings and other information useful for automation purposes."
	::= 12015

uxsA2Load1MinModified TRAP-TYPE
	ENTERPRISE caiUxsA2
	VARIABLES {
		uxsA2ConfigGeneralAgentVersion
	}
	DESCRIPTION "&<caiUxsA2.1603>The watcher configuration for the 1 minute load average monitoring of a load average resource changed. The varbind list contains a varbind with detailed information, encoded as a single string, including the changed attribute with its old value and with its new value."
	::= 12019

--
-- The Load5Min Traps
--

uxsA2Load5MinUnknown TRAP-TYPE
	ENTERPRISE caiUxsA2
	VARIABLES {
		uxsA2ConfigGeneralAgentVersion
	}
	DESCRIPTION "&<caiUxsA2.1604>A watcher monitoring the 5 minute load average of a load average resource changed its status to 'unknown'. The varbind list contains a varbind with detailed information, encoded as a single string, including the type and value of the involved metric; if applicable, the varbind also includes the current threshold settings and other information useful for automation purposes."
	::= 12020

uxsA2Load5MinOk TRAP-TYPE
	ENTERPRISE caiUxsA2
	VARIABLES {
		uxsA2ConfigGeneralAgentVersion
	}
	DESCRIPTION "&<caiUxsA2.1605>A watcher monitoring the 5 minute load average of a load average resource changed its status to 'ok'. The varbind list contains a varbind with detailed information, encoded as a single string, including the type and value of the involved metric; if applicable, the varbind also includes the current threshold settings and other information useful for automation purposes."
	::= 12021

uxsA2Load5MinWarning TRAP-TYPE
	ENTERPRISE caiUxsA2
	VARIABLES {
		uxsA2ConfigGeneralAgentVersion
	}
	DESCRIPTION "&<caiUxsA2.1606>A watcher monitoring the 5 minute load average of a load average resource changed its status to 'warning'. The varbind list contains a varbind with detailed information, encoded as a single string, including the type and value of the involved metric; if applicable, the varbind also includes the current threshold settings and other information useful for automation purposes."
	::= 12022

uxsA2Load5MinCritical TRAP-TYPE
	ENTERPRISE caiUxsA2
	VARIABLES {
		uxsA2ConfigGeneralAgentVersion
	}
	DESCRIPTION "&<caiUxsA2.1607>A watcher monitoring the 5 minute load average of a load average resource changed its status to 'critical'. The varbind list contains a varbind with detailed information, encoded as a single string, including the type and value of the involved metric; if applicable, the varbind also includes the current threshold settings and other information useful for automation purposes."
	::= 12023

uxsA2Load5MinActive TRAP-TYPE
	ENTERPRISE caiUxsA2
	VARIABLES {
		uxsA2ConfigGeneralAgentVersion
	}
	DESCRIPTION "&<caiUxsA2.1608>A watcher monitoring the 5 minute load average of a load average resource changed its status from 'passive'. The varbind list contains a varbind with detailed information, encoded as a single string, including the type and value of the involved metric; if applicable, the varbind also includes the current threshold settings and other information useful for automation purposes."
	::= 12024

uxsA2Load5MinPassive TRAP-TYPE
	ENTERPRISE caiUxsA2
	VARIABLES {
		uxsA2ConfigGeneralAgentVersion
	}
	DESCRIPTION "&<caiUxsA2.1609>A watcher monitoring the 5 minute load average of a load average resource changed its status to 'passive'. The varbind list contains a varbind with detailed information, encoded as a single string, including the type and value of the involved metric; if applicable, the varbind also includes the current threshold settings and other information useful for automation purposes."
	::= 12025

uxsA2Load5MinModified TRAP-TYPE
	ENTERPRISE caiUxsA2
	VARIABLES {
		uxsA2ConfigGeneralAgentVersion
	}
	DESCRIPTION "&<caiUxsA2.1610>The watcher configuration for the 5 minute load average monitoring of a load average resource changed. The varbind list contains a varbind with detailed information, encoded as a single string, including the changed attribute with its old value and with its new value."
	::= 12029

--
-- The Load15Min Traps
--

uxsA2Load15MinUnknown TRAP-TYPE
	ENTERPRISE caiUxsA2
	VARIABLES {
		uxsA2ConfigGeneralAgentVersion
	}
	DESCRIPTION "&<caiUxsA2.1611>A watcher monitoring the 15 minute load average of a load average resource changed its status to 'unknown'. The varbind list contains a varbind with detailed information, encoded as a single string, including the type and value of the involved metric; if applicable, the varbind also includes the current threshold settings and other information useful for automation purposes."
	::= 12030

uxsA2Load15MinOk TRAP-TYPE
	ENTERPRISE caiUxsA2
	VARIABLES {
		uxsA2ConfigGeneralAgentVersion
	}
	DESCRIPTION "&<caiUxsA2.1612>A watcher monitoring the 15 minute load average of a load average resource changed its status to 'ok'. The varbind list contains a varbind with detailed information, encoded as a single string, including the type and value of the involved metric; if applicable, the varbind also includes the current threshold settings and other information useful for automation purposes."
	::= 12031

uxsA2Load15MinWarning TRAP-TYPE
	ENTERPRISE caiUxsA2
	VARIABLES {
		uxsA2ConfigGeneralAgentVersion
	}
	DESCRIPTION "&<caiUxsA2.1613>A watcher monitoring the 15 minute load average of a load average resource changed its status to 'warning'. The varbind list contains a varbind with detailed information, encoded as a single string, including the type and value of the involved metric; if applicable, the varbind also includes the current threshold settings and other information useful for automation purposes."
	::= 12032

uxsA2Load15MinCritical TRAP-TYPE
	ENTERPRISE caiUxsA2
	VARIABLES {
		uxsA2ConfigGeneralAgentVersion
	}
	DESCRIPTION "&<caiUxsA2.1614>A watcher monitoring the 15 minute load average of a load average resource changed its status to 'critical'. The varbind list contains a varbind with detailed information, encoded as a single string, including the type and value of the involved metric; if applicable, the varbind also includes the current threshold settings and other information useful for automation purposes."
	::= 12033

uxsA2Load15MinActive TRAP-TYPE
	ENTERPRISE caiUxsA2
	VARIABLES {
		uxsA2ConfigGeneralAgentVersion
	}
	DESCRIPTION "&<caiUxsA2.1615>A watcher monitoring the 15 minute load average of a load average resource changed its status from 'passive'. The varbind list contains a varbind with detailed information, encoded as a single string, including the type and value of the involved metric; if applicable, the varbind also includes the current threshold settings and other information useful for automation purposes."
	::= 12034

uxsA2Load15MinPassive TRAP-TYPE
	ENTERPRISE caiUxsA2
	VARIABLES {
		uxsA2ConfigGeneralAgentVersion
	}
	DESCRIPTION "&<caiUxsA2.1616>A watcher monitoring the 15 minute load average of a load average resource changed its status to 'passive'. The varbind list contains a varbind with detailed information, encoded as a single string, including the type and value of the involved metric; if applicable, the varbind also includes the current threshold settings and other information useful for automation purposes."
	::= 12035

uxsA2Load15MinModified TRAP-TYPE
	ENTERPRISE caiUxsA2
	VARIABLES {
		uxsA2ConfigGeneralAgentVersion
	}
	DESCRIPTION "&<caiUxsA2.1617>The watcher configuration for the 15 minute load average monitoring of a load average resource changed. The varbind list contains a varbind with detailed information, encoded as a single string, including the changed attribute with its old value and with its new value."
	::= 12039

--
-- The MemScanRate Traps
--

uxsA2MemScanRateUnknown TRAP-TYPE
	ENTERPRISE caiUxsA2
	VARIABLES {
		uxsA2ConfigGeneralAgentVersion
	}
	DESCRIPTION "&<caiUxsA2.1618>A watcher monitoring the scan rate of a real memory resource changed its status to 'unknown'. The varbind list contains a varbind with detailed information, encoded as a single string, including the type and value of the involved metric; if applicable, the varbind also includes the current threshold settings and other information useful for automation purposes."
	::= 13010

uxsA2MemScanRateOk TRAP-TYPE
	ENTERPRISE caiUxsA2
	VARIABLES {
		uxsA2ConfigGeneralAgentVersion
	}
	DESCRIPTION "&<caiUxsA2.1619>A watcher monitoring the scan rate of a real memory resource changed its status to 'ok'. The varbind list contains a varbind with detailed information, encoded as a single string, including the type and value of the involved metric; if applicable, the varbind also includes the current threshold settings and other information useful for automation purposes."
	::= 13011

uxsA2MemScanRateWarning TRAP-TYPE
	ENTERPRISE caiUxsA2
	VARIABLES {
		uxsA2ConfigGeneralAgentVersion
	}
	DESCRIPTION "&<caiUxsA2.1620>A watcher monitoring the scan rate of a real memory resource changed its status to 'warning'. The varbind list contains a varbind with detailed information, encoded as a single string, including the type and value of the involved metric; if applicable, the varbind also includes the current threshold settings and other information useful for automation purposes."
	::= 13012

uxsA2MemScanRateCritical TRAP-TYPE
	ENTERPRISE caiUxsA2
	VARIABLES {
		uxsA2ConfigGeneralAgentVersion
	}
	DESCRIPTION "&<caiUxsA2.1621>A watcher monitoring the scan rate of a real memory resource changed its status to 'critical'. The varbind list contains a varbind with detailed information, encoded as a single string, including the type and value of the involved metric; if applicable, the varbind also includes the current threshold settings and other information useful for automation purposes."
	::= 13013

uxsA2MemScanRateActive TRAP-TYPE
	ENTERPRISE caiUxsA2
	VARIABLES {
		uxsA2ConfigGeneralAgentVersion
	}
	DESCRIPTION "&<caiUxsA2.1622>A watcher monitoring the scan rate of a real memory resource changed its status from 'passive'. The varbind list contains a varbind with detailed information, encoded as a single string, including the type and value of the involved metric; if applicable, the varbind also includes the current threshold settings and other information useful for automation purposes."
	::= 13014

uxsA2MemScanRatePassive TRAP-TYPE
	ENTERPRISE caiUxsA2
	VARIABLES {
		uxsA2ConfigGeneralAgentVersion
	}
	DESCRIPTION "&<caiUxsA2.1623>A watcher monitoring the scan rate of a real memory resource changed its status to 'passive'. The varbind list contains a varbind with detailed information, encoded as a single string, including the type and value of the involved metric; if applicable, the varbind also includes the current threshold settings and other information useful for automation purposes."
	::= 13015

uxsA2MemScanRateModified TRAP-TYPE
	ENTERPRISE caiUxsA2
	VARIABLES {
		uxsA2ConfigGeneralAgentVersion
	}
	DESCRIPTION "&<caiUxsA2.1624>The watcher configuration for the scan rate monitoring of a real memory resource changed. The varbind list contains a varbind with detailed information, encoded as a single string, including the changed attribute with its old value and with its new value."
	::= 13019

--
-- The MemPageOuts Traps
--

uxsA2MemPageOutsUnknown TRAP-TYPE
	ENTERPRISE caiUxsA2
	VARIABLES {
		uxsA2ConfigGeneralAgentVersion
	}
	DESCRIPTION "&<caiUxsA2.1625>A watcher monitoring the page outs of a real memory resource changed its status to 'unknown'. The varbind list contains a varbind with detailed information, encoded as a single string, including the type and value of the involved metric; if applicable, the varbind also includes the current threshold settings and other information useful for automation purposes."
	::= 13020

uxsA2MemPageOutsOk TRAP-TYPE
	ENTERPRISE caiUxsA2
	VARIABLES {
		uxsA2ConfigGeneralAgentVersion
	}
	DESCRIPTION "&<caiUxsA2.1626>A watcher monitoring the page outs of a real memory resource changed its status to 'ok'. The varbind list contains a varbind with detailed information, encoded as a single string, including the type and value of the involved metric; if applicable, the varbind also includes the current threshold settings and other information useful for automation purposes."
	::= 13021

uxsA2MemPageOutsWarning TRAP-TYPE
	ENTERPRISE caiUxsA2
	VARIABLES {
		uxsA2ConfigGeneralAgentVersion
	}
	DESCRIPTION "&<caiUxsA2.1627>A watcher monitoring the page outs of a real memory resource changed its status to 'warning'. The varbind list contains a varbind with detailed information, encoded as a single string, including the type and value of the involved metric; if applicable, the varbind also includes the current threshold settings and other information useful for automation purposes."
	::= 13022

uxsA2MemPageOutsCritical TRAP-TYPE
	ENTERPRISE caiUxsA2
	VARIABLES {
		uxsA2ConfigGeneralAgentVersion
	}
	DESCRIPTION "&<caiUxsA2.1628>A watcher monitoring the page outs of a real memory resource changed its status to 'critical'. The varbind list contains a varbind with detailed information, encoded as a single string, including the type and value of the involved metric; if applicable, the varbind also includes the current threshold settings and other information useful for automation purposes."
	::= 13023

uxsA2MemPageOutsActive TRAP-TYPE
	ENTERPRISE caiUxsA2
	VARIABLES {
		uxsA2ConfigGeneralAgentVersion
	}
	DESCRIPTION "&<caiUxsA2.1629>A watcher monitoring the page outs of a real memory resource changed its status from 'passive'. The varbind list contains a varbind with detailed information, encoded as a single string, including the type and value of the involved metric; if applicable, the varbind also includes the current threshold settings and other information useful for automation purposes."
	::= 13024

uxsA2MemPageOutsPassive TRAP-TYPE
	ENTERPRISE caiUxsA2
	VARIABLES {
		uxsA2ConfigGeneralAgentVersion
	}
	DESCRIPTION "&<caiUxsA2.1630>A watcher monitoring the page outs of a real memory resource changed its status to 'passive'. The varbind list contains a varbind with detailed information, encoded as a single string, including the type and value of the involved metric; if applicable, the varbind also includes the current threshold settings and other information useful for automation purposes."
	::= 13025

uxsA2MemPageOutsModified TRAP-TYPE
	ENTERPRISE caiUxsA2
	VARIABLES {
		uxsA2ConfigGeneralAgentVersion
	}
	DESCRIPTION "&<caiUxsA2.1631>The watcher configuration for the page outs monitoring of a real memory resource changed. The varbind list contains a varbind with detailed information, encoded as a single string, including the changed attribute with its old value and with its new value."
	::= 13029

--
-- The MemUtil Traps
--

uxsA2MemUtilUnknown TRAP-TYPE
	ENTERPRISE caiUxsA2
	VARIABLES {
		uxsA2ConfigGeneralAgentVersion
	}
	DESCRIPTION "&<caiUxsA2.1632>A watcher monitoring the real memory utilization of a real memory resource changed its status to 'unknown'. The varbind list contains a varbind with detailed information, encoded as a single string, including the type and value of the involved metric; if applicable, the varbind also includes the current threshold settings and other information useful for automation purposes."
	::= 13030

uxsA2MemUtilOk TRAP-TYPE
	ENTERPRISE caiUxsA2
	VARIABLES {
		uxsA2ConfigGeneralAgentVersion
	}
	DESCRIPTION "&<caiUxsA2.1633>A watcher monitoring the real memory utilization of a real memory resource changed its status to 'ok'. The varbind list contains a varbind with detailed information, encoded as a single string, including the type and value of the involved metric; if applicable, the varbind also includes the current threshold settings and other information useful for automation purposes."
	::= 13031

uxsA2MemUtilWarning TRAP-TYPE
	ENTERPRISE caiUxsA2
	VARIABLES {
		uxsA2ConfigGeneralAgentVersion
	}
	DESCRIPTION "&<caiUxsA2.1634>A watcher monitoring the real memory utilization of a real memory resource changed its status to 'warning'. The varbind list contains a varbind with detailed information, encoded as a single string, including the type and value of the involved metric; if applicable, the varbind also includes the current threshold settings and other information useful for automation purposes."
	::= 13032

uxsA2MemUtilCritical TRAP-TYPE
	ENTERPRISE caiUxsA2
	VARIABLES {
		uxsA2ConfigGeneralAgentVersion
	}
	DESCRIPTION "&<caiUxsA2.1635>A watcher monitoring the real memory utilization of a real memory resource changed its status to 'critical'. The varbind list contains a varbind with detailed information, encoded as a single string, including the type and value of the involved metric; if applicable, the varbind also includes the current threshold settings and other information useful for automation purposes."
	::= 13033

uxsA2MemUtilActive TRAP-TYPE
	ENTERPRISE caiUxsA2
	VARIABLES {
		uxsA2ConfigGeneralAgentVersion
	}
	DESCRIPTION "&<caiUxsA2.1636>A watcher monitoring the real memory utilization of a real memory resource changed its status from 'passive'. The varbind list contains a varbind with detailed information, encoded as a single string, including the type and value of the involved metric; if applicable, the varbind also includes the current threshold settings and other information useful for automation purposes."
	::= 13034

uxsA2MemUtilPassive TRAP-TYPE
	ENTERPRISE caiUxsA2
	VARIABLES {
		uxsA2ConfigGeneralAgentVersion
	}
	DESCRIPTION "&<caiUxsA2.1637>A watcher monitoring the real memory utilization of a real memory resource changed its status to 'passive'. The varbind list contains a varbind with detailed information, encoded as a single string, including the type and value of the involved metric; if applicable, the varbind also includes the current threshold settings and other information useful for automation purposes."
	::= 13035

uxsA2MemUtilModified TRAP-TYPE
	ENTERPRISE caiUxsA2
	VARIABLES {
		uxsA2ConfigGeneralAgentVersion
	}
	DESCRIPTION "&<caiUxsA2.1638>The watcher configuration for the real memory utilization monitoring of a real memory resource changed. The varbind list contains a varbind with detailed information, encoded as a single string, including the changed attribute with its old value and with its new value."
	::= 13039

--
-- The MemSize Traps
--

uxsA2MemSizeUnknown TRAP-TYPE
	ENTERPRISE caiUxsA2
	VARIABLES {
		uxsA2ConfigGeneralAgentVersion
	}
	DESCRIPTION "&<caiUxsA2.1639>A watcher monitoring the dynamic memory reconfiguration of a real memory resource changed its status to 'unknown'. The varbind list contains a varbind with detailed information, encoded as a single string, including the type and value of the involved metric; if applicable, the varbind also includes the current threshold settings and other information useful for automation purposes."
	::= 13040

uxsA2MemSizeOk TRAP-TYPE
	ENTERPRISE caiUxsA2
	VARIABLES {
		uxsA2ConfigGeneralAgentVersion
	}
	DESCRIPTION "&<caiUxsA2.1640>A watcher monitoring the dynamic memory reconfiguration of a real memory resource changed its status to 'ok'. The varbind list contains a varbind with detailed information, encoded as a single string, including the type and value of the involved metric; if applicable, the varbind also includes the current threshold settings and other information useful for automation purposes."
	::= 13041

uxsA2MemSizeWarning TRAP-TYPE
	ENTERPRISE caiUxsA2
	VARIABLES {
		uxsA2ConfigGeneralAgentVersion
	}
	DESCRIPTION "&<caiUxsA2.1641>A watcher monitoring the dynamic memory reconfiguration of a real memory resource changed its status to 'warning'. The varbind list contains a varbind with detailed information, encoded as a single string, including the type and value of the involved metric; if applicable, the varbind also includes the current threshold settings and other information useful for automation purposes."
	::= 13042

uxsA2MemSizeCritical TRAP-TYPE
	ENTERPRISE caiUxsA2
	VARIABLES {
		uxsA2ConfigGeneralAgentVersion
	}
	DESCRIPTION "&<caiUxsA2.1642>A watcher monitoring the dynamic memory reconfiguration of a real memory resource changed its status to 'critical'. The varbind list contains a varbind with detailed information, encoded as a single string, including the type and value of the involved metric; if applicable, the varbind also includes the current threshold settings and other information useful for automation purposes."
	::= 13043

uxsA2MemSizeActive TRAP-TYPE
	ENTERPRISE caiUxsA2
	VARIABLES {
		uxsA2ConfigGeneralAgentVersion
	}
	DESCRIPTION "&<caiUxsA2.1643>A watcher monitoring the dynamic memory reconfiguration of a real memory resource changed its status from 'passive'. The varbind list contains a varbind with detailed information, encoded as a single string, including the type and value of the involved metric; if applicable, the varbind also includes the current threshold settings and other information useful for automation purposes."
	::= 13044

uxsA2MemSizePassive TRAP-TYPE
	ENTERPRISE caiUxsA2
	VARIABLES {
		uxsA2ConfigGeneralAgentVersion
	}
	DESCRIPTION "&<caiUxsA2.1644>A watcher monitoring the dynamic memory reconfiguration of a real memory resource changed its status to 'passive'. The varbind list contains a varbind with detailed information, encoded as a single string, including the type and value of the involved metric; if applicable, the varbind also includes the current threshold settings and other information useful for automation purposes."
	::= 13045

uxsA2MemSizeModified TRAP-TYPE
	ENTERPRISE caiUxsA2
	VARIABLES {
		uxsA2ConfigGeneralAgentVersion
	}
	DESCRIPTION "&<caiUxsA2.1645>The watcher configuration for the dynamic memory reconfiguration monitoring of a real memory resource changed. The varbind list contains a varbind with detailed information, encoded as a single string, including the changed attribute with its old value and with its new value."
	::= 13049

--
-- The SwapTotalSpace Traps
--

uxsA2SwapTotalSpaceUnknown TRAP-TYPE
	ENTERPRISE caiUxsA2
	VARIABLES {
		uxsA2ConfigGeneralAgentVersion
	}
	DESCRIPTION "&<caiUxsA2.1646>A watcher monitoring the total swap space utilization of a swap resource changed its status to 'unknown'. The varbind list contains a varbind with detailed information, encoded as a single string, including the type and value of the involved metric; if applicable, the varbind also includes the current threshold settings and other information useful for automation purposes."
	::= 14000

uxsA2SwapTotalSpaceOk TRAP-TYPE
	ENTERPRISE caiUxsA2
	VARIABLES {
		uxsA2ConfigGeneralAgentVersion
	}
	DESCRIPTION "&<caiUxsA2.1647>A watcher monitoring the total swap space utilization of a swap resource changed its status to 'ok'. The varbind list contains a varbind with detailed information, encoded as a single string, including the type and value of the involved metric; if applicable, the varbind also includes the current threshold settings and other information useful for automation purposes."
	::= 14001

uxsA2SwapTotalSpaceWarning TRAP-TYPE
	ENTERPRISE caiUxsA2
	VARIABLES {
		uxsA2ConfigGeneralAgentVersion
	}
	DESCRIPTION "&<caiUxsA2.1648>A watcher monitoring the total swap space utilization of a swap resource changed its status to 'warning'. The varbind list contains a varbind with detailed information, encoded as a single string, including the type and value of the involved metric; if applicable, the varbind also includes the current threshold settings and other information useful for automation purposes."
	::= 14002

uxsA2SwapTotalSpaceCritical TRAP-TYPE
	ENTERPRISE caiUxsA2
	VARIABLES {
		uxsA2ConfigGeneralAgentVersion
	}
	DESCRIPTION "&<caiUxsA2.1649>A watcher monitoring the total swap space utilization of a swap resource changed its status to 'critical'. The varbind list contains a varbind with detailed information, encoded as a single string, including the type and value of the involved metric; if applicable, the varbind also includes the current threshold settings and other information useful for automation purposes."
	::= 14003

uxsA2SwapTotalSpaceActive TRAP-TYPE
	ENTERPRISE caiUxsA2
	VARIABLES {
		uxsA2ConfigGeneralAgentVersion
	}
	DESCRIPTION "&<caiUxsA2.1650>A watcher monitoring the total swap space utilization of a swap resource changed its status from 'passive'. The varbind list contains a varbind with detailed information, encoded as a single string, including the type and value of the involved metric; if applicable, the varbind also includes the current threshold settings and other information useful for automation purposes."
	::= 14004

uxsA2SwapTotalSpacePassive TRAP-TYPE
	ENTERPRISE caiUxsA2
	VARIABLES {
		uxsA2ConfigGeneralAgentVersion
	}
	DESCRIPTION "&<caiUxsA2.1651>A watcher monitoring the total swap space utilization of a swap resource changed its status to 'passive'. The varbind list contains a varbind with detailed information, encoded as a single string, including the type and value of the involved metric; if applicable, the varbind also includes the current threshold settings and other information useful for automation purposes."
	::= 14005

uxsA2SwapTotalSpaceModified TRAP-TYPE
	ENTERPRISE caiUxsA2
	VARIABLES {
		uxsA2ConfigGeneralAgentVersion
	}
	DESCRIPTION "&<caiUxsA2.1652>The watcher configuration for the total swap space utilization monitoring of a swap resource changed. The varbind list contains a varbind with detailed information, encoded as a single string, including the changed attribute with its old value and with its new value."
	::= 14009

--
-- The Swap Traps
--

uxsA2SwapUnknown TRAP-TYPE
	ENTERPRISE caiUxsA2
	VARIABLES {
		uxsA2StatusSwapName,
		uxsA2ConfigGeneralAgentVersion
	}
	DESCRIPTION "&<caiUxsA2.1653>A watcher monitoring a swap resource changed its status to 'unknown'. The varbind list contains a varbind with detailed information, encoded as a single string, including the name of the involved resource and the type and value of the involved metric; if applicable, the varbind also includes the current threshold settings and other information useful for automation purposes."
	::= 14990

uxsA2SwapOk TRAP-TYPE
	ENTERPRISE caiUxsA2
	VARIABLES {
		uxsA2StatusSwapName,
		uxsA2ConfigGeneralAgentVersion
	}
	DESCRIPTION "&<caiUxsA2.1654>A watcher monitoring a swap resource changed its status to 'ok'. The varbind list contains a varbind with detailed information, encoded as a single string, including the name of the involved resource and the type and value of the involved metric; if applicable, the varbind also includes the current threshold settings and other information useful for automation purposes."
	::= 14991

uxsA2SwapWarning TRAP-TYPE
	ENTERPRISE caiUxsA2
	VARIABLES {
		uxsA2StatusSwapName,
		uxsA2ConfigGeneralAgentVersion
	}
	DESCRIPTION "&<caiUxsA2.1655>A watcher monitoring a swap resource changed its status to 'warning'. The varbind list contains a varbind with detailed information, encoded as a single string, including the name of the involved resource and the type and value of the involved metric; if applicable, the varbind also includes the current threshold settings and other information useful for automation purposes."
	::= 14992

uxsA2SwapCritical TRAP-TYPE
	ENTERPRISE caiUxsA2
	VARIABLES {
		uxsA2StatusSwapName,
		uxsA2ConfigGeneralAgentVersion
	}
	DESCRIPTION "&<caiUxsA2.1656>A watcher monitoring a swap resource changed its status to 'critical'. The varbind list contains a varbind with detailed information, encoded as a single string, including the name of the involved resource and the type and value of the involved metric; if applicable, the varbind also includes the current threshold settings and other information useful for automation purposes."
	::= 14993

uxsA2SwapActive TRAP-TYPE
	ENTERPRISE caiUxsA2
	VARIABLES {
		uxsA2StatusSwapName,
		uxsA2ConfigGeneralAgentVersion
	}
	DESCRIPTION "&<caiUxsA2.1657>A watcher monitoring a swap resource changed its status from 'passive'. The varbind list contains a varbind with detailed information, encoded as a single string, including the name of the involved resource and the type and value of the involved metric; if applicable, the varbind also includes the current threshold settings and other information useful for automation purposes."
	::= 14994

uxsA2SwapPassive TRAP-TYPE
	ENTERPRISE caiUxsA2
	VARIABLES {
		uxsA2StatusSwapName,
		uxsA2ConfigGeneralAgentVersion
	}
	DESCRIPTION "&<caiUxsA2.1658>A watcher monitoring a swap resource changed its status to 'passive'. The varbind list contains a varbind with detailed information, encoded as a single string, including the name of the involved resource and the type and value of the involved metric; if applicable, the varbind also includes the current threshold settings and other information useful for automation purposes."
	::= 14995

uxsA2SwapAdded TRAP-TYPE
	ENTERPRISE caiUxsA2
	VARIABLES {
		uxsA2StatusSwapName
	}
	DESCRIPTION "&<caiUxsA2.1659>A watcher monitoring a swap resource was added. The varbind list contains the name of the involved resource."
	::= 14996

uxsA2SwapDeleted TRAP-TYPE
	ENTERPRISE caiUxsA2
	VARIABLES {
		uxsA2StatusSwapName
	}
	DESCRIPTION "&<caiUxsA2.1660>A watcher monitoring a swap resource was removed. The varbind list contains the name of the involved resource."
	::= 14997

uxsA2SwapInfo TRAP-TYPE
	ENTERPRISE caiUxsA2
	VARIABLES {
		uxsA2ConfigGeneralAgentVersion
	}
	DESCRIPTION "&<caiUxsA2.1661>A watcher monitoring a swap resource changed a sub-state. The varbind list contains a varbind with detailed information, encoded as a single string, including the name of the involved resource, the old and the new status, and the type and value of the involved metric; if applicable, the varbind also includes the current threshold settings and other information useful for automation purposes."
	::= 14998

uxsA2SwapModified TRAP-TYPE
	ENTERPRISE caiUxsA2
	VARIABLES {
		uxsA2ConfigGeneralAgentVersion
	}
	DESCRIPTION "&<caiUxsA2.1662>The watcher configuration for a swap resource changed. The varbind list contains a varbind with detailed information, encoded as a single string, including the name of the involved resource and the changed attribute with its old value and with its new value."
	::= 14999

--
-- The Quota Traps
--

uxsA2QuotaUnknown TRAP-TYPE
	ENTERPRISE caiUxsA2
	VARIABLES {
		uxsA2StatusQuotaFSys,
		uxsA2StatusQuotaUser,
		uxsA2ConfigGeneralAgentVersion
	}
	DESCRIPTION "&<caiUxsA2.1663>A watcher monitoring a quota resource changed its status to 'unknown'. The varbind list contains a varbind with detailed information, encoded as a single string, including the name of the involved resource and the type and value of the involved metric; if applicable, the varbind also includes the current threshold settings and other information useful for automation purposes."
	::= 15980

uxsA2QuotaOk TRAP-TYPE
	ENTERPRISE caiUxsA2
	VARIABLES {
		uxsA2StatusQuotaFSys,
		uxsA2StatusQuotaUser,
		uxsA2ConfigGeneralAgentVersion
	}
	DESCRIPTION "&<caiUxsA2.1664>A watcher monitoring a quota resource changed its status to 'ok'. The varbind list contains a varbind with detailed information, encoded as a single string, including the name of the involved resource and the type and value of the involved metric; if applicable, the varbind also includes the current threshold settings and other information useful for automation purposes."
	::= 15981

uxsA2QuotaWarning TRAP-TYPE
	ENTERPRISE caiUxsA2
	VARIABLES {
		uxsA2StatusQuotaFSys,
		uxsA2StatusQuotaUser,
		uxsA2ConfigGeneralAgentVersion
	}
	DESCRIPTION "&<caiUxsA2.1665>A watcher monitoring a quota resource changed its status to 'warning'. The varbind list contains a varbind with detailed information, encoded as a single string, including the name of the involved resource and the type and value of the involved metric; if applicable, the varbind also includes the current threshold settings and other information useful for automation purposes."
	::= 15982

uxsA2QuotaCritical TRAP-TYPE
	ENTERPRISE caiUxsA2
	VARIABLES {
		uxsA2StatusQuotaFSys,
		uxsA2StatusQuotaUser,
		uxsA2ConfigGeneralAgentVersion
	}
	DESCRIPTION "&<caiUxsA2.1666>A watcher monitoring a quota resource changed its status to 'critical'. The varbind list contains a varbind with detailed information, encoded as a single string, including the name of the involved resource and the type and value of the involved metric; if applicable, the varbind also includes the current threshold settings and other information useful for automation purposes."
	::= 15983

uxsA2QuotaActive TRAP-TYPE
	ENTERPRISE caiUxsA2
	VARIABLES {
		uxsA2StatusQuotaFSys,
		uxsA2StatusQuotaUser,
		uxsA2ConfigGeneralAgentVersion
	}
	DESCRIPTION "&<caiUxsA2.1667>A watcher monitoring a quota resource changed its status from 'passive'. The varbind list contains a varbind with detailed information, encoded as a single string, including the name of the involved resource and the type and value of the involved metric; if applicable, the varbind also includes the current threshold settings and other information useful for automation purposes."
	::= 15984

uxsA2QuotaPassive TRAP-TYPE
	ENTERPRISE caiUxsA2
	VARIABLES {
		uxsA2StatusQuotaFSys,
		uxsA2StatusQuotaUser,
		uxsA2ConfigGeneralAgentVersion
	}
	DESCRIPTION "&<caiUxsA2.1668>A watcher monitoring a quota resource changed its status to 'passive'. The varbind list contains a varbind with detailed information, encoded as a single string, including the name of the involved resource and the type and value of the involved metric; if applicable, the varbind also includes the current threshold settings and other information useful for automation purposes."
	::= 15985

uxsA2QuotaAdded TRAP-TYPE
	ENTERPRISE caiUxsA2
	VARIABLES {
		uxsA2StatusQuotaFSys,
		uxsA2StatusQuotaUser
	}
	DESCRIPTION "&<caiUxsA2.1669>A watcher monitoring a quota resource was added. The varbind list contains the name of the involved resource."
	::= 15986

uxsA2QuotaDeleted TRAP-TYPE
	ENTERPRISE caiUxsA2
	VARIABLES {
		uxsA2StatusQuotaFSys,
		uxsA2StatusQuotaUser
	}
	DESCRIPTION "&<caiUxsA2.1670>A watcher monitoring a quota resource was removed. The varbind list contains the name of the involved resource."
	::= 15987

uxsA2QuotaInfo TRAP-TYPE
	ENTERPRISE caiUxsA2
	VARIABLES {
		uxsA2ConfigGeneralAgentVersion
	}
	DESCRIPTION "&<caiUxsA2.1671>A watcher monitoring a quota resource changed a sub-state. The varbind list contains a varbind with detailed information, encoded as a single string, including the name of the involved resource, the old and the new status, and the type and value of the involved metric; if applicable, the varbind also includes the current threshold settings and other information useful for automation purposes."
	::= 15988

uxsA2QuotaModified TRAP-TYPE
	ENTERPRISE caiUxsA2
	VARIABLES {
		uxsA2ConfigGeneralAgentVersion
	}
	DESCRIPTION "&<caiUxsA2.1672>The watcher configuration for a quota resource changed. The varbind list contains a varbind with detailed information, encoded as a single string, including the name of the involved resource and the changed attribute with its old value and with its new value."
	::= 15989

--
-- The Dir Traps
--

uxsA2DirUnknown TRAP-TYPE
	ENTERPRISE caiUxsA2
	VARIABLES {
		uxsA2StatusDirWatcherName,
		uxsA2ConfigGeneralAgentVersion
	}
	DESCRIPTION "&<caiUxsA2.1673>A watcher monitoring a directory resource changed its status to 'unknown'. The varbind list contains a varbind with detailed information, encoded as a single string, including the name of the involved resource and the type and value of the involved metric; if applicable, the varbind also includes the current threshold settings and other information useful for automation purposes."
	::= 16980

uxsA2DirOk TRAP-TYPE
	ENTERPRISE caiUxsA2
	VARIABLES {
		uxsA2StatusDirWatcherName,
		uxsA2ConfigGeneralAgentVersion
	}
	DESCRIPTION "&<caiUxsA2.1674>A watcher monitoring a directory resource changed its status to 'ok'. The varbind list contains a varbind with detailed information, encoded as a single string, including the name of the involved resource and the type and value of the involved metric; if applicable, the varbind also includes the current threshold settings and other information useful for automation purposes."
	::= 16981

uxsA2DirWarning TRAP-TYPE
	ENTERPRISE caiUxsA2
	VARIABLES {
		uxsA2StatusDirWatcherName,
		uxsA2ConfigGeneralAgentVersion
	}
	DESCRIPTION "&<caiUxsA2.1675>A watcher monitoring a directory resource changed its status to 'warning'. The varbind list contains a varbind with detailed information, encoded as a single string, including the name of the involved resource and the type and value of the involved metric; if applicable, the varbind also includes the current threshold settings and other information useful for automation purposes."
	::= 16982

uxsA2DirCritical TRAP-TYPE
	ENTERPRISE caiUxsA2
	VARIABLES {
		uxsA2StatusDirWatcherName,
		uxsA2ConfigGeneralAgentVersion
	}
	DESCRIPTION "&<caiUxsA2.1676>A watcher monitoring a directory resource changed its status to 'critical'. The varbind list contains a varbind with detailed information, encoded as a single string, including the name of the involved resource and the type and value of the involved metric; if applicable, the varbind also includes the current threshold settings and other information useful for automation purposes."
	::= 16983

uxsA2DirActive TRAP-TYPE
	ENTERPRISE caiUxsA2
	VARIABLES {
		uxsA2StatusDirWatcherName,
		uxsA2ConfigGeneralAgentVersion
	}
	DESCRIPTION "&<caiUxsA2.1677>A watcher monitoring a directory resource changed its status from 'passive'. The varbind list contains a varbind with detailed information, encoded as a single string, including the name of the involved resource and the type and value of the involved metric; if applicable, the varbind also includes the current threshold settings and other information useful for automation purposes."
	::= 16984

uxsA2DirPassive TRAP-TYPE
	ENTERPRISE caiUxsA2
	VARIABLES {
		uxsA2StatusDirWatcherName,
		uxsA2ConfigGeneralAgentVersion
	}
	DESCRIPTION "&<caiUxsA2.1678>A watcher monitoring a directory resource changed its status to 'passive'. The varbind list contains a varbind with detailed information, encoded as a single string, including the name of the involved resource and the type and value of the involved metric; if applicable, the varbind also includes the current threshold settings and other information useful for automation purposes."
	::= 16985

uxsA2DirAdded TRAP-TYPE
	ENTERPRISE caiUxsA2
	VARIABLES {
		uxsA2StatusDirWatcherName
	}
	DESCRIPTION "&<caiUxsA2.1679>A watcher monitoring a directory resource was added. The varbind list contains the name of the involved resource."
	::= 16986

uxsA2DirDeleted TRAP-TYPE
	ENTERPRISE caiUxsA2
	VARIABLES {
		uxsA2StatusDirWatcherName
	}
	DESCRIPTION "&<caiUxsA2.1680>A watcher monitoring a directory resource was removed. The varbind list contains the name of the involved resource."
	::= 16987

uxsA2DirInfo TRAP-TYPE
	ENTERPRISE caiUxsA2
	VARIABLES {
		uxsA2ConfigGeneralAgentVersion
	}
	DESCRIPTION "&<caiUxsA2.1681>A watcher monitoring a directory resource changed a sub-state. The varbind list contains a varbind with detailed information, encoded as a single string, including the name of the involved resource, the old and the new status, and the type and value of the involved metric; if applicable, the varbind also includes the current threshold settings and other information useful for automation purposes."
	::= 16988

uxsA2DirModified TRAP-TYPE
	ENTERPRISE caiUxsA2
	VARIABLES {
		uxsA2ConfigGeneralAgentVersion
	}
	DESCRIPTION "&<caiUxsA2.1682>The watcher configuration for a directory resource changed. The varbind list contains a varbind with detailed information, encoded as a single string, including the name of the involved resource and the changed attribute with its old value and with its new value."
	::= 16989

--
-- The FSys Traps
--

uxsA2FSysUnknown TRAP-TYPE
	ENTERPRISE caiUxsA2
	VARIABLES {
		uxsA2StatusFSysName,
		uxsA2ConfigGeneralAgentVersion
	}
	DESCRIPTION "&<caiUxsA2.1683>A watcher monitoring a file system resource changed its status to 'unknown'. The varbind list contains a varbind with detailed information, encoded as a single string, including the name of the involved resource and the type and value of the involved metric; if applicable, the varbind also includes the current threshold settings and other information useful for automation purposes."
	::= 17980

uxsA2FSysOk TRAP-TYPE
	ENTERPRISE caiUxsA2
	VARIABLES {
		uxsA2StatusFSysName,
		uxsA2ConfigGeneralAgentVersion
	}
	DESCRIPTION "&<caiUxsA2.1684>A watcher monitoring a file system resource changed its status to 'ok'. The varbind list contains a varbind with detailed information, encoded as a single string, including the name of the involved resource and the type and value of the involved metric; if applicable, the varbind also includes the current threshold settings and other information useful for automation purposes."
	::= 17981

uxsA2FSysWarning TRAP-TYPE
	ENTERPRISE caiUxsA2
	VARIABLES {
		uxsA2StatusFSysName,
		uxsA2ConfigGeneralAgentVersion
	}
	DESCRIPTION "&<caiUxsA2.1685>A watcher monitoring a file system resource changed its status to 'warning'. The varbind list contains a varbind with detailed information, encoded as a single string, including the name of the involved resource and the type and value of the involved metric; if applicable, the varbind also includes the current threshold settings and other information useful for automation purposes."
	::= 17982

uxsA2FSysCritical TRAP-TYPE
	ENTERPRISE caiUxsA2
	VARIABLES {
		uxsA2StatusFSysName,
		uxsA2ConfigGeneralAgentVersion
	}
	DESCRIPTION "&<caiUxsA2.1686>A watcher monitoring a file system resource changed its status to 'critical'. The varbind list contains a varbind with detailed information, encoded as a single string, including the name of the involved resource and the type and value of the involved metric; if applicable, the varbind also includes the current threshold settings and other information useful for automation purposes."
	::= 17983

uxsA2FSysActive TRAP-TYPE
	ENTERPRISE caiUxsA2
	VARIABLES {
		uxsA2StatusFSysName,
		uxsA2ConfigGeneralAgentVersion
	}
	DESCRIPTION "&<caiUxsA2.1687>A watcher monitoring a file system resource changed its status from 'passive'. The varbind list contains a varbind with detailed information, encoded as a single string, including the name of the involved resource and the type and value of the involved metric; if applicable, the varbind also includes the current threshold settings and other information useful for automation purposes."
	::= 17984

uxsA2FSysPassive TRAP-TYPE
	ENTERPRISE caiUxsA2
	VARIABLES {
		uxsA2StatusFSysName,
		uxsA2ConfigGeneralAgentVersion
	}
	DESCRIPTION "&<caiUxsA2.1688>A watcher monitoring a file system resource changed its status to 'passive'. The varbind list contains a varbind with detailed information, encoded as a single string, including the name of the involved resource and the type and value of the involved metric; if applicable, the varbind also includes the current threshold settings and other information useful for automation purposes."
	::= 17985

uxsA2FSysAdded TRAP-TYPE
	ENTERPRISE caiUxsA2
	VARIABLES {
		uxsA2StatusFSysName
	}
	DESCRIPTION "&<caiUxsA2.1689>A watcher monitoring a file system resource was added. The varbind list contains the name of the involved resource."
	::= 17986

uxsA2FSysDeleted TRAP-TYPE
	ENTERPRISE caiUxsA2
	VARIABLES {
		uxsA2StatusFSysName
	}
	DESCRIPTION "&<caiUxsA2.1690>A watcher monitoring a file system resource was removed. The varbind list contains the name of the involved resource."
	::= 17987

uxsA2FSysInfo TRAP-TYPE
	ENTERPRISE caiUxsA2
	VARIABLES {
		uxsA2ConfigGeneralAgentVersion
	}
	DESCRIPTION "&<caiUxsA2.1691>A watcher monitoring a file system resource changed a sub-state. The varbind list contains a varbind with detailed information, encoded as a single string, including the name of the involved resource, the old and the new status, and the type and value of the involved metric; if applicable, the varbind also includes the current threshold settings and other information useful for automation purposes."
	::= 17988

uxsA2FSysModified TRAP-TYPE
	ENTERPRISE caiUxsA2
	VARIABLES {
		uxsA2ConfigGeneralAgentVersion
	}
	DESCRIPTION "&<caiUxsA2.1692>The watcher configuration for a file system resource changed. The varbind list contains a varbind with detailed information, encoded as a single string, including the name of the involved resource and the changed attribute with its old value and with its new value."
	::= 17989

--
-- The File Traps
--

uxsA2FileUnknown TRAP-TYPE
	ENTERPRISE caiUxsA2
	VARIABLES {
		uxsA2StatusFileWatcherName,
		uxsA2ConfigGeneralAgentVersion
	}
	DESCRIPTION "&<caiUxsA2.1693>A watcher monitoring a file resource changed its status to 'unknown'. The varbind list contains a varbind with detailed information, encoded as a single string, including the name of the involved resource and the type and value of the involved metric; if applicable, the varbind also includes the current threshold settings and other information useful for automation purposes."
	::= 18980

uxsA2FileOk TRAP-TYPE
	ENTERPRISE caiUxsA2
	VARIABLES {
		uxsA2StatusFileWatcherName,
		uxsA2ConfigGeneralAgentVersion
	}
	DESCRIPTION "&<caiUxsA2.1694>A watcher monitoring a file resource changed its status to 'ok'. The varbind list contains a varbind with detailed information, encoded as a single string, including the name of the involved resource and the type and value of the involved metric; if applicable, the varbind also includes the current threshold settings and other information useful for automation purposes."
	::= 18981

uxsA2FileWarning TRAP-TYPE
	ENTERPRISE caiUxsA2
	VARIABLES {
		uxsA2StatusFileWatcherName,
		uxsA2ConfigGeneralAgentVersion
	}
	DESCRIPTION "&<caiUxsA2.1695>A watcher monitoring a file resource changed its status to 'warning'. The varbind list contains a varbind with detailed information, encoded as a single string, including the name of the involved resource and the type and value of the involved metric; if applicable, the varbind also includes the current threshold settings and other information useful for automation purposes."
	::= 18982

uxsA2FileCritical TRAP-TYPE
	ENTERPRISE caiUxsA2
	VARIABLES {
		uxsA2StatusFileWatcherName,
		uxsA2ConfigGeneralAgentVersion
	}
	DESCRIPTION "&<caiUxsA2.1696>A watcher monitoring a file resource changed its status to 'critical'. The varbind list contains a varbind with detailed information, encoded as a single string, including the name of the involved resource and the type and value of the involved metric; if applicable, the varbind also includes the current threshold settings and other information useful for automation purposes."
	::= 18983

uxsA2FileActive TRAP-TYPE
	ENTERPRISE caiUxsA2
	VARIABLES {
		uxsA2StatusFileWatcherName,
		uxsA2ConfigGeneralAgentVersion
	}
	DESCRIPTION "&<caiUxsA2.1697>A watcher monitoring a file resource changed its status from 'passive'. The varbind list contains a varbind with detailed information, encoded as a single string, including the name of the involved resource and the type and value of the involved metric; if applicable, the varbind also includes the current threshold settings and other information useful for automation purposes."
	::= 18984

uxsA2FilePassive TRAP-TYPE
	ENTERPRISE caiUxsA2
	VARIABLES {
		uxsA2StatusFileWatcherName,
		uxsA2ConfigGeneralAgentVersion
	}
	DESCRIPTION "&<caiUxsA2.1698>A watcher monitoring a file resource changed its status to 'passive'. The varbind list contains a varbind with detailed information, encoded as a single string, including the name of the involved resource and the type and value of the involved metric; if applicable, the varbind also includes the current threshold settings and other information useful for automation purposes."
	::= 18985

uxsA2FileAdded TRAP-TYPE
	ENTERPRISE caiUxsA2
	VARIABLES {
		uxsA2StatusFileWatcherName
	}
	DESCRIPTION "&<caiUxsA2.1699>A watcher monitoring a file resource was added. The varbind list contains the name of the involved resource."
	::= 18986

uxsA2FileDeleted TRAP-TYPE
	ENTERPRISE caiUxsA2
	VARIABLES {
		uxsA2StatusFileWatcherName
	}
	DESCRIPTION "&<caiUxsA2.1700>A watcher monitoring a file resource was removed. The varbind list contains the name of the involved resource."
	::= 18987

uxsA2FileInfo TRAP-TYPE
	ENTERPRISE caiUxsA2
	VARIABLES {
		uxsA2ConfigGeneralAgentVersion
	}
	DESCRIPTION "&<caiUxsA2.1701>A watcher monitoring a file resource changed a sub-state. The varbind list contains a varbind with detailed information, encoded as a single string, including the name of the involved resource, the old and the new status, and the type and value of the involved metric; if applicable, the varbind also includes the current threshold settings and other information useful for automation purposes."
	::= 18988

uxsA2FileModified TRAP-TYPE
	ENTERPRISE caiUxsA2
	VARIABLES {
		uxsA2ConfigGeneralAgentVersion
	}
	DESCRIPTION "&<caiUxsA2.1702>The watcher configuration for a file resource changed. The varbind list contains a varbind with detailed information, encoded as a single string, including the name of the involved resource and the changed attribute with its old value and with its new value."
	::= 18989

--
-- The Disk Traps
--

uxsA2DiskUnknown TRAP-TYPE
	ENTERPRISE caiUxsA2
	VARIABLES {
		uxsA2StatusDiskName,
		uxsA2ConfigGeneralAgentVersion
	}
	DESCRIPTION "&<caiUxsA2.1703>A watcher monitoring a disk resource changed its status to 'unknown'. The varbind list contains a varbind with detailed information, encoded as a single string, including the name of the involved resource and the type and value of the involved metric; if applicable, the varbind also includes the current threshold settings and other information useful for automation purposes."
	::= 19980

uxsA2DiskOk TRAP-TYPE
	ENTERPRISE caiUxsA2
	VARIABLES {
		uxsA2StatusDiskName,
		uxsA2ConfigGeneralAgentVersion
	}
	DESCRIPTION "&<caiUxsA2.1704>A watcher monitoring a disk resource changed its status to 'ok'. The varbind list contains a varbind with detailed information, encoded as a single string, including the name of the involved resource and the type and value of the involved metric; if applicable, the varbind also includes the current threshold settings and other information useful for automation purposes."
	::= 19981

uxsA2DiskWarning TRAP-TYPE
	ENTERPRISE caiUxsA2
	VARIABLES {
		uxsA2StatusDiskName,
		uxsA2ConfigGeneralAgentVersion
	}
	DESCRIPTION "&<caiUxsA2.1705>A watcher monitoring a disk resource changed its status to 'warning'. The varbind list contains a varbind with detailed information, encoded as a single string, including the name of the involved resource and the type and value of the involved metric; if applicable, the varbind also includes the current threshold settings and other information useful for automation purposes."
	::= 19982

uxsA2DiskCritical TRAP-TYPE
	ENTERPRISE caiUxsA2
	VARIABLES {
		uxsA2StatusDiskName,
		uxsA2ConfigGeneralAgentVersion
	}
	DESCRIPTION "&<caiUxsA2.1706>A watcher monitoring a disk resource changed its status to 'critical'. The varbind list contains a varbind with detailed information, encoded as a single string, including the name of the involved resource and the type and value of the involved metric; if applicable, the varbind also includes the current threshold settings and other information useful for automation purposes."
	::= 19983

uxsA2DiskActive TRAP-TYPE
	ENTERPRISE caiUxsA2
	VARIABLES {
		uxsA2StatusDiskName,
		uxsA2ConfigGeneralAgentVersion
	}
	DESCRIPTION "&<caiUxsA2.1707>A watcher monitoring a disk resource changed its status from 'passive'. The varbind list contains a varbind with detailed information, encoded as a single string, including the name of the involved resource and the type and value of the involved metric; if applicable, the varbind also includes the current threshold settings and other information useful for automation purposes."
	::= 19984

uxsA2DiskPassive TRAP-TYPE
	ENTERPRISE caiUxsA2
	VARIABLES {
		uxsA2StatusDiskName,
		uxsA2ConfigGeneralAgentVersion
	}
	DESCRIPTION "&<caiUxsA2.1708>A watcher monitoring a disk resource changed its status to 'passive'. The varbind list contains a varbind with detailed information, encoded as a single string, including the name of the involved resource and the type and value of the involved metric; if applicable, the varbind also includes the current threshold settings and other information useful for automation purposes."
	::= 19985

uxsA2DiskAdded TRAP-TYPE
	ENTERPRISE caiUxsA2
	VARIABLES {
		uxsA2StatusDiskName
	}
	DESCRIPTION "&<caiUxsA2.1709>A watcher monitoring a disk resource was added. The varbind list contains the name of the involved resource."
	::= 19986

uxsA2DiskDeleted TRAP-TYPE
	ENTERPRISE caiUxsA2
	VARIABLES {
		uxsA2StatusDiskName
	}
	DESCRIPTION "&<caiUxsA2.1710>A watcher monitoring a disk resource was removed. The varbind list contains the name of the involved resource."
	::= 19987

uxsA2DiskInfo TRAP-TYPE
	ENTERPRISE caiUxsA2
	VARIABLES {
		uxsA2ConfigGeneralAgentVersion
	}
	DESCRIPTION "&<caiUxsA2.1711>A watcher monitoring a disk resource changed a sub-state. The varbind list contains a varbind with detailed information, encoded as a single string, including the name of the involved resource, the old and the new status, and the type and value of the involved metric; if applicable, the varbind also includes the current threshold settings and other information useful for automation purposes."
	::= 19988

uxsA2DiskModified TRAP-TYPE
	ENTERPRISE caiUxsA2
	VARIABLES {
		uxsA2ConfigGeneralAgentVersion
	}
	DESCRIPTION "&<caiUxsA2.1712>The watcher configuration for a disk resource changed. The varbind list contains a varbind with detailed information, encoded as a single string, including the name of the involved resource and the changed attribute with its old value and with its new value."
	::= 19989

--
-- The Proc Traps
--

uxsA2ProcUnknown TRAP-TYPE
	ENTERPRISE caiUxsA2
	VARIABLES {
		uxsA2StatusProcWatcherName,
		uxsA2ConfigGeneralAgentVersion
	}
	DESCRIPTION "&<caiUxsA2.1713>A watcher monitoring a process resource changed its status to 'unknown'. The varbind list contains a varbind with detailed information, encoded as a single string, including the name of the involved resource and the type and value of the involved metric; if applicable, the varbind also includes the current threshold settings and other information useful for automation purposes."
	::= 20980

uxsA2ProcOk TRAP-TYPE
	ENTERPRISE caiUxsA2
	VARIABLES {
		uxsA2StatusProcWatcherName,
		uxsA2ConfigGeneralAgentVersion
	}
	DESCRIPTION "&<caiUxsA2.1714>A watcher monitoring a process resource changed its status to 'ok'. The varbind list contains a varbind with detailed information, encoded as a single string, including the name of the involved resource and the type and value of the involved metric; if applicable, the varbind also includes the current threshold settings and other information useful for automation purposes."
	::= 20981

uxsA2ProcWarning TRAP-TYPE
	ENTERPRISE caiUxsA2
	VARIABLES {
		uxsA2StatusProcWatcherName,
		uxsA2ConfigGeneralAgentVersion
	}
	DESCRIPTION "&<caiUxsA2.1715>A watcher monitoring a process resource changed its status to 'warning'. The varbind list contains a varbind with detailed information, encoded as a single string, including the name of the involved resource and the type and value of the involved metric; if applicable, the varbind also includes the current threshold settings and other information useful for automation purposes."
	::= 20982

uxsA2ProcCritical TRAP-TYPE
	ENTERPRISE caiUxsA2
	VARIABLES {
		uxsA2StatusProcWatcherName,
		uxsA2ConfigGeneralAgentVersion
	}
	DESCRIPTION "&<caiUxsA2.1716>A watcher monitoring a process resource changed its status to 'critical'. The varbind list contains a varbind with detailed information, encoded as a single string, including the name of the involved resource and the type and value of the involved metric; if applicable, the varbind also includes the current threshold settings and other information useful for automation purposes."
	::= 20983

uxsA2ProcActive TRAP-TYPE
	ENTERPRISE caiUxsA2
	VARIABLES {
		uxsA2StatusProcWatcherName,
		uxsA2ConfigGeneralAgentVersion
	}
	DESCRIPTION "&<caiUxsA2.1717>A watcher monitoring a process resource changed its status from 'passive'. The varbind list contains a varbind with detailed information, encoded as a single string, including the name of the involved resource and the type and value of the involved metric; if applicable, the varbind also includes the current threshold settings and other information useful for automation purposes."
	::= 20984

uxsA2ProcPassive TRAP-TYPE
	ENTERPRISE caiUxsA2
	VARIABLES {
		uxsA2StatusProcWatcherName,
		uxsA2ConfigGeneralAgentVersion
	}
	DESCRIPTION "&<caiUxsA2.1718>A watcher monitoring a process resource changed its status to 'passive'. The varbind list contains a varbind with detailed information, encoded as a single string, including the name of the involved resource and the type and value of the involved metric; if applicable, the varbind also includes the current threshold settings and other information useful for automation purposes."
	::= 20985

uxsA2ProcAdded TRAP-TYPE
	ENTERPRISE caiUxsA2
	VARIABLES {
		uxsA2StatusProcWatcherName
	}
	DESCRIPTION "&<caiUxsA2.1719>A watcher monitoring a process resource was added. The varbind list contains the name of the involved resource."
	::= 20986

uxsA2ProcDeleted TRAP-TYPE
	ENTERPRISE caiUxsA2
	VARIABLES {
		uxsA2StatusProcWatcherName
	}
	DESCRIPTION "&<caiUxsA2.1720>A watcher monitoring a process resource was removed. The varbind list contains the name of the involved resource."
	::= 20987

uxsA2ProcInfo TRAP-TYPE
	ENTERPRISE caiUxsA2
	VARIABLES {
		uxsA2ConfigGeneralAgentVersion
	}
	DESCRIPTION "&<caiUxsA2.1721>A watcher monitoring a process resource changed a sub-state. The varbind list contains a varbind with detailed information, encoded as a single string, including the name of the involved resource, the old and the new status, and the type and value of the involved metric; if applicable, the varbind also includes the current threshold settings and other information useful for automation purposes."
	::= 20988

uxsA2ProcModified TRAP-TYPE
	ENTERPRISE caiUxsA2
	VARIABLES {
		uxsA2ConfigGeneralAgentVersion
	}
	DESCRIPTION "&<caiUxsA2.1722>The watcher configuration for a process resource changed. The varbind list contains a varbind with detailed information, encoded as a single string, including the name of the involved resource and the changed attribute with its old value and with its new value."
	::= 20989

--
-- The Prn Traps
--

uxsA2PrnUnknown TRAP-TYPE
	ENTERPRISE caiUxsA2
	VARIABLES {
		uxsA2StatusPrnName,
		uxsA2ConfigGeneralAgentVersion
	}
	DESCRIPTION "&<caiUxsA2.1723>A watcher monitoring a print queue resource changed its status to 'unknown'. The varbind list contains a varbind with detailed information, encoded as a single string, including the name of the involved resource and the type and value of the involved metric; if applicable, the varbind also includes the current threshold settings and other information useful for automation purposes."
	::= 21980

uxsA2PrnOk TRAP-TYPE
	ENTERPRISE caiUxsA2
	VARIABLES {
		uxsA2StatusPrnName,
		uxsA2ConfigGeneralAgentVersion
	}
	DESCRIPTION "&<caiUxsA2.1724>A watcher monitoring a print queue resource changed its status to 'ok'. The varbind list contains a varbind with detailed information, encoded as a single string, including the name of the involved resource and the type and value of the involved metric; if applicable, the varbind also includes the current threshold settings and other information useful for automation purposes."
	::= 21981

uxsA2PrnWarning TRAP-TYPE
	ENTERPRISE caiUxsA2
	VARIABLES {
		uxsA2StatusPrnName,
		uxsA2ConfigGeneralAgentVersion
	}
	DESCRIPTION "&<caiUxsA2.1725>A watcher monitoring a print queue resource changed its status to 'warning'. The varbind list contains a varbind with detailed information, encoded as a single string, including the name of the involved resource and the type and value of the involved metric; if applicable, the varbind also includes the current threshold settings and other information useful for automation purposes."
	::= 21982

uxsA2PrnCritical TRAP-TYPE
	ENTERPRISE caiUxsA2
	VARIABLES {
		uxsA2StatusPrnName,
		uxsA2ConfigGeneralAgentVersion
	}
	DESCRIPTION "&<caiUxsA2.1726>A watcher monitoring a print queue resource changed its status to 'critical'. The varbind list contains a varbind with detailed information, encoded as a single string, including the name of the involved resource and the type and value of the involved metric; if applicable, the varbind also includes the current threshold settings and other information useful for automation purposes."
	::= 21983

uxsA2PrnActive TRAP-TYPE
	ENTERPRISE caiUxsA2
	VARIABLES {
		uxsA2StatusPrnName,
		uxsA2ConfigGeneralAgentVersion
	}
	DESCRIPTION "&<caiUxsA2.1727>A watcher monitoring a print queue resource changed its status from 'passive'. The varbind list contains a varbind with detailed information, encoded as a single string, including the name of the involved resource and the type and value of the involved metric; if applicable, the varbind also includes the current threshold settings and other information useful for automation purposes."
	::= 21984

uxsA2PrnPassive TRAP-TYPE
	ENTERPRISE caiUxsA2
	VARIABLES {
		uxsA2StatusPrnName,
		uxsA2ConfigGeneralAgentVersion
	}
	DESCRIPTION "&<caiUxsA2.1728>A watcher monitoring a print queue resource changed its status to 'passive'. The varbind list contains a varbind with detailed information, encoded as a single string, including the name of the involved resource and the type and value of the involved metric; if applicable, the varbind also includes the current threshold settings and other information useful for automation purposes."
	::= 21985

uxsA2PrnAdded TRAP-TYPE
	ENTERPRISE caiUxsA2
	VARIABLES {
		uxsA2StatusPrnName
	}
	DESCRIPTION "&<caiUxsA2.1729>A watcher monitoring a print queue resource was added. The varbind list contains the name of the involved resource."
	::= 21986

uxsA2PrnDeleted TRAP-TYPE
	ENTERPRISE caiUxsA2
	VARIABLES {
		uxsA2StatusPrnName
	}
	DESCRIPTION "&<caiUxsA2.1730>A watcher monitoring a print queue resource was removed. The varbind list contains the name of the involved resource."
	::= 21987

uxsA2PrnInfo TRAP-TYPE
	ENTERPRISE caiUxsA2
	VARIABLES {
		uxsA2ConfigGeneralAgentVersion
	}
	DESCRIPTION "&<caiUxsA2.1731>A watcher monitoring a print queue resource changed a sub-state. The varbind list contains a varbind with detailed information, encoded as a single string, including the name of the involved resource, the old and the new status, and the type and value of the involved metric; if applicable, the varbind also includes the current threshold settings and other information useful for automation purposes."
	::= 21988

uxsA2PrnModified TRAP-TYPE
	ENTERPRISE caiUxsA2
	VARIABLES {
		uxsA2ConfigGeneralAgentVersion
	}
	DESCRIPTION "&<caiUxsA2.1732>The watcher configuration for a print queue resource changed. The varbind list contains a varbind with detailed information, encoded as a single string, including the name of the involved resource and the changed attribute with its old value and with its new value."
	::= 21989

--
-- The NetTotal Traps
--

uxsA2NetTotalUnknown TRAP-TYPE
	ENTERPRISE caiUxsA2
	VARIABLES {
		uxsA2ConfigGeneralAgentVersion
	}
	DESCRIPTION "&<caiUxsA2.1733>A watcher monitoring a network interface resource changed its status to 'unknown'. The varbind list contains a varbind with detailed information, encoded as a single string, including the type and value of the involved metric; if applicable, the varbind also includes the current threshold settings and other information useful for automation purposes."
	::= 22000

uxsA2NetTotalOk TRAP-TYPE
	ENTERPRISE caiUxsA2
	VARIABLES {
		uxsA2ConfigGeneralAgentVersion
	}
	DESCRIPTION "&<caiUxsA2.1734>A watcher monitoring a network interface resource changed its status to 'ok'. The varbind list contains a varbind with detailed information, encoded as a single string, including the type and value of the involved metric; if applicable, the varbind also includes the current threshold settings and other information useful for automation purposes."
	::= 22001

uxsA2NetTotalWarning TRAP-TYPE
	ENTERPRISE caiUxsA2
	VARIABLES {
		uxsA2ConfigGeneralAgentVersion
	}
	DESCRIPTION "&<caiUxsA2.1735>A watcher monitoring a network interface resource changed its status to 'warning'. The varbind list contains a varbind with detailed information, encoded as a single string, including the type and value of the involved metric; if applicable, the varbind also includes the current threshold settings and other information useful for automation purposes."
	::= 22002

uxsA2NetTotalCritical TRAP-TYPE
	ENTERPRISE caiUxsA2
	VARIABLES {
		uxsA2ConfigGeneralAgentVersion
	}
	DESCRIPTION "&<caiUxsA2.1736>A watcher monitoring a network interface resource changed its status to 'critical'. The varbind list contains a varbind with detailed information, encoded as a single string, including the type and value of the involved metric; if applicable, the varbind also includes the current threshold settings and other information useful for automation purposes."
	::= 22003

uxsA2NetTotalActive TRAP-TYPE
	ENTERPRISE caiUxsA2
	VARIABLES {
		uxsA2ConfigGeneralAgentVersion
	}
	DESCRIPTION "&<caiUxsA2.1737>A watcher monitoring a network interface resource changed its status from 'passive'. The varbind list contains a varbind with detailed information, encoded as a single string, including the type and value of the involved metric; if applicable, the varbind also includes the current threshold settings and other information useful for automation purposes."
	::= 22004

uxsA2NetTotalPassive TRAP-TYPE
	ENTERPRISE caiUxsA2
	VARIABLES {
		uxsA2ConfigGeneralAgentVersion
	}
	DESCRIPTION "&<caiUxsA2.1738>A watcher monitoring a network interface resource changed its status to 'passive'. The varbind list contains a varbind with detailed information, encoded as a single string, including the type and value of the involved metric; if applicable, the varbind also includes the current threshold settings and other information useful for automation purposes."
	::= 22005

uxsA2NetTotalInfo TRAP-TYPE
	ENTERPRISE caiUxsA2
	VARIABLES {
		uxsA2ConfigGeneralAgentVersion
	}
	DESCRIPTION "&<caiUxsA2.1739>A watcher monitoring a network interface resource changed a sub-state. The varbind list contains a varbind with detailed information, encoded as a single string, including the old and the new status, and the type and value of the involved metric; if applicable, the varbind also includes the current threshold settings and other information useful for automation purposes."
	::= 22008

uxsA2NetTotalModified TRAP-TYPE
	ENTERPRISE caiUxsA2
	VARIABLES {
		uxsA2ConfigGeneralAgentVersion
	}
	DESCRIPTION "&<caiUxsA2.1740>The watcher configuration for a network interface resource changed. The varbind list contains a varbind with detailed information, encoded as a single string, including the changed attribute with its old value and with its new value."
	::= 22009

--
-- The Net Traps
--

uxsA2NetUnknown TRAP-TYPE
	ENTERPRISE caiUxsA2
	VARIABLES {
		uxsA2StatusNetName,
		uxsA2ConfigGeneralAgentVersion
	}
	DESCRIPTION "&<caiUxsA2.1741>A watcher monitoring a network interface resource changed its status to 'unknown'. The varbind list contains a varbind with detailed information, encoded as a single string, including the name of the involved resource and the type and value of the involved metric; if applicable, the varbind also includes the current threshold settings and other information useful for automation purposes."
	::= 22990

uxsA2NetOk TRAP-TYPE
	ENTERPRISE caiUxsA2
	VARIABLES {
		uxsA2StatusNetName,
		uxsA2ConfigGeneralAgentVersion
	}
	DESCRIPTION "&<caiUxsA2.1742>A watcher monitoring a network interface resource changed its status to 'ok'. The varbind list contains a varbind with detailed information, encoded as a single string, including the name of the involved resource and the type and value of the involved metric; if applicable, the varbind also includes the current threshold settings and other information useful for automation purposes."
	::= 22991

uxsA2NetWarning TRAP-TYPE
	ENTERPRISE caiUxsA2
	VARIABLES {
		uxsA2StatusNetName,
		uxsA2ConfigGeneralAgentVersion
	}
	DESCRIPTION "&<caiUxsA2.1743>A watcher monitoring a network interface resource changed its status to 'warning'. The varbind list contains a varbind with detailed information, encoded as a single string, including the name of the involved resource and the type and value of the involved metric; if applicable, the varbind also includes the current threshold settings and other information useful for automation purposes."
	::= 22992

uxsA2NetCritical TRAP-TYPE
	ENTERPRISE caiUxsA2
	VARIABLES {
		uxsA2StatusNetName,
		uxsA2ConfigGeneralAgentVersion
	}
	DESCRIPTION "&<caiUxsA2.1744>A watcher monitoring a network interface resource changed its status to 'critical'. The varbind list contains a varbind with detailed information, encoded as a single string, including the name of the involved resource and the type and value of the involved metric; if applicable, the varbind also includes the current threshold settings and other information useful for automation purposes."
	::= 22993

uxsA2NetActive TRAP-TYPE
	ENTERPRISE caiUxsA2
	VARIABLES {
		uxsA2StatusNetName,
		uxsA2ConfigGeneralAgentVersion
	}
	DESCRIPTION "&<caiUxsA2.1745>A watcher monitoring a network interface resource changed its status from 'passive'. The varbind list contains a varbind with detailed information, encoded as a single string, including the name of the involved resource and the type and value of the involved metric; if applicable, the varbind also includes the current threshold settings and other information useful for automation purposes."
	::= 22994

uxsA2NetPassive TRAP-TYPE
	ENTERPRISE caiUxsA2
	VARIABLES {
		uxsA2StatusNetName,
		uxsA2ConfigGeneralAgentVersion
	}
	DESCRIPTION "&<caiUxsA2.1746>A watcher monitoring a network interface resource changed its status to 'passive'. The varbind list contains a varbind with detailed information, encoded as a single string, including the name of the involved resource and the type and value of the involved metric; if applicable, the varbind also includes the current threshold settings and other information useful for automation purposes."
	::= 22995

uxsA2NetAdded TRAP-TYPE
	ENTERPRISE caiUxsA2
	VARIABLES {
		uxsA2StatusNetName
	}
	DESCRIPTION "&<caiUxsA2.1747>A watcher monitoring a network interface resource was added. The varbind list contains the name of the involved resource."
	::= 22996

uxsA2NetDeleted TRAP-TYPE
	ENTERPRISE caiUxsA2
	VARIABLES {
		uxsA2StatusNetName
	}
	DESCRIPTION "&<caiUxsA2.1748>A watcher monitoring a network interface resource was removed. The varbind list contains the name of the involved resource."
	::= 22997

uxsA2NetInfo TRAP-TYPE
	ENTERPRISE caiUxsA2
	VARIABLES {
		uxsA2ConfigGeneralAgentVersion
	}
	DESCRIPTION "&<caiUxsA2.1749>A watcher monitoring a network interface resource changed a sub-state. The varbind list contains a varbind with detailed information, encoded as a single string, including the name of the involved resource, the old and the new status, and the type and value of the involved metric; if applicable, the varbind also includes the current threshold settings and other information useful for automation purposes."
	::= 22998

uxsA2NetModified TRAP-TYPE
	ENTERPRISE caiUxsA2
	VARIABLES {
		uxsA2ConfigGeneralAgentVersion
	}
	DESCRIPTION "&<caiUxsA2.1750>The watcher configuration for a network interface resource changed. The varbind list contains a varbind with detailed information, encoded as a single string, including the name of the involved resource and the changed attribute with its old value and with its new value."
	::= 22999

--
-- The SHM Traps
--

uxsA2SHMUnknown TRAP-TYPE
	ENTERPRISE caiUxsA2
	VARIABLES {
		uxsA2StatusSHMId,
		uxsA2ConfigGeneralAgentVersion
	}
	DESCRIPTION "&<caiUxsA2.1751>A watcher monitoring a shared memory resource changed its status to 'unknown'. The varbind list contains a varbind with detailed information, encoded as a single string, including the name of the involved resource and the type and value of the involved metric; if applicable, the varbind also includes the current threshold settings and other information useful for automation purposes."
	::= 23980

uxsA2SHMOk TRAP-TYPE
	ENTERPRISE caiUxsA2
	VARIABLES {
		uxsA2StatusSHMId,
		uxsA2ConfigGeneralAgentVersion
	}
	DESCRIPTION "&<caiUxsA2.1752>A watcher monitoring a shared memory resource changed its status to 'ok'. The varbind list contains a varbind with detailed information, encoded as a single string, including the name of the involved resource and the type and value of the involved metric; if applicable, the varbind also includes the current threshold settings and other information useful for automation purposes."
	::= 23981

uxsA2SHMWarning TRAP-TYPE
	ENTERPRISE caiUxsA2
	VARIABLES {
		uxsA2StatusSHMId,
		uxsA2ConfigGeneralAgentVersion
	}
	DESCRIPTION "&<caiUxsA2.1753>A watcher monitoring a shared memory resource changed its status to 'warning'. The varbind list contains a varbind with detailed information, encoded as a single string, including the name of the involved resource and the type and value of the involved metric; if applicable, the varbind also includes the current threshold settings and other information useful for automation purposes."
	::= 23982

uxsA2SHMCritical TRAP-TYPE
	ENTERPRISE caiUxsA2
	VARIABLES {
		uxsA2StatusSHMId,
		uxsA2ConfigGeneralAgentVersion
	}
	DESCRIPTION "&<caiUxsA2.1754>A watcher monitoring a shared memory resource changed its status to 'critical'. The varbind list contains a varbind with detailed information, encoded as a single string, including the name of the involved resource and the type and value of the involved metric; if applicable, the varbind also includes the current threshold settings and other information useful for automation purposes."
	::= 23983

uxsA2SHMActive TRAP-TYPE
	ENTERPRISE caiUxsA2
	VARIABLES {
		uxsA2StatusSHMId,
		uxsA2ConfigGeneralAgentVersion
	}
	DESCRIPTION "&<caiUxsA2.1755>A watcher monitoring a shared memory resource changed its status from 'passive'. The varbind list contains a varbind with detailed information, encoded as a single string, including the name of the involved resource and the type and value of the involved metric; if applicable, the varbind also includes the current threshold settings and other information useful for automation purposes."
	::= 23984

uxsA2SHMPassive TRAP-TYPE
	ENTERPRISE caiUxsA2
	VARIABLES {
		uxsA2StatusSHMId,
		uxsA2ConfigGeneralAgentVersion
	}
	DESCRIPTION "&<caiUxsA2.1756>A watcher monitoring a shared memory resource changed its status to 'passive'. The varbind list contains a varbind with detailed information, encoded as a single string, including the name of the involved resource and the type and value of the involved metric; if applicable, the varbind also includes the current threshold settings and other information useful for automation purposes."
	::= 23985

uxsA2SHMAdded TRAP-TYPE
	ENTERPRISE caiUxsA2
	VARIABLES {
		uxsA2StatusSHMId
	}
	DESCRIPTION "&<caiUxsA2.1757>A watcher monitoring a shared memory resource was added. The varbind list contains the name of the involved resource."
	::= 23986

uxsA2SHMDeleted TRAP-TYPE
	ENTERPRISE caiUxsA2
	VARIABLES {
		uxsA2StatusSHMId
	}
	DESCRIPTION "&<caiUxsA2.1758>A watcher monitoring a shared memory resource was removed. The varbind list contains the name of the involved resource."
	::= 23987

uxsA2SHMInfo TRAP-TYPE
	ENTERPRISE caiUxsA2
	VARIABLES {
		uxsA2ConfigGeneralAgentVersion
	}
	DESCRIPTION "&<caiUxsA2.1759>A watcher monitoring a shared memory resource changed a sub-state. The varbind list contains a varbind with detailed information, encoded as a single string, including the name of the involved resource, the old and the new status, and the type and value of the involved metric; if applicable, the varbind also includes the current threshold settings and other information useful for automation purposes."
	::= 23988

uxsA2SHMModified TRAP-TYPE
	ENTERPRISE caiUxsA2
	VARIABLES {
		uxsA2ConfigGeneralAgentVersion
	}
	DESCRIPTION "&<caiUxsA2.1760>The watcher configuration for a shared memory resource changed. The varbind list contains a varbind with detailed information, encoded as a single string, including the name of the involved resource and the changed attribute with its old value and with its new value."
	::= 23989

--
-- The SEM Traps
--

uxsA2SEMUnknown TRAP-TYPE
	ENTERPRISE caiUxsA2
	VARIABLES {
		uxsA2StatusSEMId,
		uxsA2ConfigGeneralAgentVersion
	}
	DESCRIPTION "&<caiUxsA2.1761>A watcher monitoring a semaphore resource changed its status to 'unknown'. The varbind list contains a varbind with detailed information, encoded as a single string, including the name of the involved resource and the type and value of the involved metric; if applicable, the varbind also includes the current threshold settings and other information useful for automation purposes."
	::= 24980

uxsA2SEMOk TRAP-TYPE
	ENTERPRISE caiUxsA2
	VARIABLES {
		uxsA2StatusSEMId,
		uxsA2ConfigGeneralAgentVersion
	}
	DESCRIPTION "&<caiUxsA2.1762>A watcher monitoring a semaphore resource changed its status to 'ok'. The varbind list contains a varbind with detailed information, encoded as a single string, including the name of the involved resource and the type and value of the involved metric; if applicable, the varbind also includes the current threshold settings and other information useful for automation purposes."
	::= 24981

uxsA2SEMWarning TRAP-TYPE
	ENTERPRISE caiUxsA2
	VARIABLES {
		uxsA2StatusSEMId,
		uxsA2ConfigGeneralAgentVersion
	}
	DESCRIPTION "&<caiUxsA2.1763>A watcher monitoring a semaphore resource changed its status to 'warning'. The varbind list contains a varbind with detailed information, encoded as a single string, including the name of the involved resource and the type and value of the involved metric; if applicable, the varbind also includes the current threshold settings and other information useful for automation purposes."
	::= 24982

uxsA2SEMCritical TRAP-TYPE
	ENTERPRISE caiUxsA2
	VARIABLES {
		uxsA2StatusSEMId,
		uxsA2ConfigGeneralAgentVersion
	}
	DESCRIPTION "&<caiUxsA2.1764>A watcher monitoring a semaphore resource changed its status to 'critical'. The varbind list contains a varbind with detailed information, encoded as a single string, including the name of the involved resource and the type and value of the involved metric; if applicable, the varbind also includes the current threshold settings and other information useful for automation purposes."
	::= 24983

uxsA2SEMActive TRAP-TYPE
	ENTERPRISE caiUxsA2
	VARIABLES {
		uxsA2StatusSEMId,
		uxsA2ConfigGeneralAgentVersion
	}
	DESCRIPTION "&<caiUxsA2.1765>A watcher monitoring a semaphore resource changed its status from 'passive'. The varbind list contains a varbind with detailed information, encoded as a single string, including the name of the involved resource and the type and value of the involved metric; if applicable, the varbind also includes the current threshold settings and other information useful for automation purposes."
	::= 24984

uxsA2SEMPassive TRAP-TYPE
	ENTERPRISE caiUxsA2
	VARIABLES {
		uxsA2StatusSEMId,
		uxsA2ConfigGeneralAgentVersion
	}
	DESCRIPTION "&<caiUxsA2.1766>A watcher monitoring a semaphore resource changed its status to 'passive'. The varbind list contains a varbind with detailed information, encoded as a single string, including the name of the involved resource and the type and value of the involved metric; if applicable, the varbind also includes the current threshold settings and other information useful for automation purposes."
	::= 24985

uxsA2SEMAdded TRAP-TYPE
	ENTERPRISE caiUxsA2
	VARIABLES {
		uxsA2StatusSEMId
	}
	DESCRIPTION "&<caiUxsA2.1767>A watcher monitoring a semaphore resource was added. The varbind list contains the name of the involved resource."
	::= 24986

uxsA2SEMDeleted TRAP-TYPE
	ENTERPRISE caiUxsA2
	VARIABLES {
		uxsA2StatusSEMId
	}
	DESCRIPTION "&<caiUxsA2.1768>A watcher monitoring a semaphore resource was removed. The varbind list contains the name of the involved resource."
	::= 24987

uxsA2SEMInfo TRAP-TYPE
	ENTERPRISE caiUxsA2
	VARIABLES {
		uxsA2ConfigGeneralAgentVersion
	}
	DESCRIPTION "&<caiUxsA2.1769>A watcher monitoring a semaphore resource changed a sub-state. The varbind list contains a varbind with detailed information, encoded as a single string, including the name of the involved resource, the old and the new status, and the type and value of the involved metric; if applicable, the varbind also includes the current threshold settings and other information useful for automation purposes."
	::= 24988

uxsA2SEMModified TRAP-TYPE
	ENTERPRISE caiUxsA2
	VARIABLES {
		uxsA2ConfigGeneralAgentVersion
	}
	DESCRIPTION "&<caiUxsA2.1770>The watcher configuration for a semaphore resource changed. The varbind list contains a varbind with detailed information, encoded as a single string, including the name of the involved resource and the changed attribute with its old value and with its new value."
	::= 24989

--
-- The MQ Traps
--

uxsA2MQUnknown TRAP-TYPE
	ENTERPRISE caiUxsA2
	VARIABLES {
		uxsA2StatusMQId,
		uxsA2ConfigGeneralAgentVersion
	}
	DESCRIPTION "&<caiUxsA2.1771>A watcher monitoring a message queue resource changed its status to 'unknown'. The varbind list contains a varbind with detailed information, encoded as a single string, including the name of the involved resource and the type and value of the involved metric; if applicable, the varbind also includes the current threshold settings and other information useful for automation purposes."
	::= 25980

uxsA2MQOk TRAP-TYPE
	ENTERPRISE caiUxsA2
	VARIABLES {
		uxsA2StatusMQId,
		uxsA2ConfigGeneralAgentVersion
	}
	DESCRIPTION "&<caiUxsA2.1772>A watcher monitoring a message queue resource changed its status to 'ok'. The varbind list contains a varbind with detailed information, encoded as a single string, including the name of the involved resource and the type and value of the involved metric; if applicable, the varbind also includes the current threshold settings and other information useful for automation purposes."
	::= 25981

uxsA2MQWarning TRAP-TYPE
	ENTERPRISE caiUxsA2
	VARIABLES {
		uxsA2StatusMQId,
		uxsA2ConfigGeneralAgentVersion
	}
	DESCRIPTION "&<caiUxsA2.1773>A watcher monitoring a message queue resource changed its status to 'warning'. The varbind list contains a varbind with detailed information, encoded as a single string, including the name of the involved resource and the type and value of the involved metric; if applicable, the varbind also includes the current threshold settings and other information useful for automation purposes."
	::= 25982

uxsA2MQCritical TRAP-TYPE
	ENTERPRISE caiUxsA2
	VARIABLES {
		uxsA2StatusMQId,
		uxsA2ConfigGeneralAgentVersion
	}
	DESCRIPTION "&<caiUxsA2.1774>A watcher monitoring a message queue resource changed its status to 'critical'. The varbind list contains a varbind with detailed information, encoded as a single string, including the name of the involved resource and the type and value of the involved metric; if applicable, the varbind also includes the current threshold settings and other information useful for automation purposes."
	::= 25983

uxsA2MQActive TRAP-TYPE
	ENTERPRISE caiUxsA2
	VARIABLES {
		uxsA2StatusMQId,
		uxsA2ConfigGeneralAgentVersion
	}
	DESCRIPTION "&<caiUxsA2.1775>A watcher monitoring a message queue resource changed its status from 'passive'. The varbind list contains a varbind with detailed information, encoded as a single string, including the name of the involved resource and the type and value of the involved metric; if applicable, the varbind also includes the current threshold settings and other information useful for automation purposes."
	::= 25984

uxsA2MQPassive TRAP-TYPE
	ENTERPRISE caiUxsA2
	VARIABLES {
		uxsA2StatusMQId,
		uxsA2ConfigGeneralAgentVersion
	}
	DESCRIPTION "&<caiUxsA2.1776>A watcher monitoring a message queue resource changed its status to 'passive'. The varbind list contains a varbind with detailed information, encoded as a single string, including the name of the involved resource and the type and value of the involved metric; if applicable, the varbind also includes the current threshold settings and other information useful for automation purposes."
	::= 25985

uxsA2MQAdded TRAP-TYPE
	ENTERPRISE caiUxsA2
	VARIABLES {
		uxsA2StatusMQId
	}
	DESCRIPTION "&<caiUxsA2.1777>A watcher monitoring a message queue resource was added. The varbind list contains the name of the involved resource."
	::= 25986

uxsA2MQDeleted TRAP-TYPE
	ENTERPRISE caiUxsA2
	VARIABLES {
		uxsA2StatusMQId
	}
	DESCRIPTION "&<caiUxsA2.1778>A watcher monitoring a message queue resource was removed. The varbind list contains the name of the involved resource."
	::= 25987

uxsA2MQInfo TRAP-TYPE
	ENTERPRISE caiUxsA2
	VARIABLES {
		uxsA2ConfigGeneralAgentVersion
	}
	DESCRIPTION "&<caiUxsA2.1779>A watcher monitoring a message queue resource changed a sub-state. The varbind list contains a varbind with detailed information, encoded as a single string, including the name of the involved resource, the old and the new status, and the type and value of the involved metric; if applicable, the varbind also includes the current threshold settings and other information useful for automation purposes."
	::= 25988

uxsA2MQModified TRAP-TYPE
	ENTERPRISE caiUxsA2
	VARIABLES {
		uxsA2ConfigGeneralAgentVersion
	}
	DESCRIPTION "&<caiUxsA2.1780>The watcher configuration for a message queue resource changed. The varbind list contains a varbind with detailed information, encoded as a single string, including the name of the involved resource and the changed attribute with its old value and with its new value."
	::= 25989

--
-- The Hardwr Traps
--

uxsA2HardwrUnknown TRAP-TYPE
	ENTERPRISE caiUxsA2
	VARIABLES {
		uxsA2StatusHardwrResName,
		uxsA2StatusHardwrResSubName,
		uxsA2StatusHardwrInstName,
		uxsA2ConfigGeneralAgentVersion
	}
	DESCRIPTION "&<caiUxsA2.1781>A watcher monitoring a hardware resource changed its status to 'unknown'. The varbind list contains a varbind with detailed information, encoded as a single string, including the name of the involved resource and the type and value of the involved metric; if applicable, the varbind also includes the current threshold settings and other information useful for automation purposes."
	::= 26980

uxsA2HardwrOk TRAP-TYPE
	ENTERPRISE caiUxsA2
	VARIABLES {
		uxsA2StatusHardwrResName,
		uxsA2StatusHardwrResSubName,
		uxsA2StatusHardwrInstName,
		uxsA2ConfigGeneralAgentVersion
	}
	DESCRIPTION "&<caiUxsA2.1782>A watcher monitoring a hardware resource changed its status to 'ok'. The varbind list contains a varbind with detailed information, encoded as a single string, including the name of the involved resource and the type and value of the involved metric; if applicable, the varbind also includes the current threshold settings and other information useful for automation purposes."
	::= 26981

uxsA2HardwrWarning TRAP-TYPE
	ENTERPRISE caiUxsA2
	VARIABLES {
		uxsA2StatusHardwrResName,
		uxsA2StatusHardwrResSubName,
		uxsA2StatusHardwrInstName,
		uxsA2ConfigGeneralAgentVersion
	}
	DESCRIPTION "&<caiUxsA2.1783>A watcher monitoring a hardware resource changed its status to 'warning'. The varbind list contains a varbind with detailed information, encoded as a single string, including the name of the involved resource and the type and value of the involved metric; if applicable, the varbind also includes the current threshold settings and other information useful for automation purposes."
	::= 26982

uxsA2HardwrCritical TRAP-TYPE
	ENTERPRISE caiUxsA2
	VARIABLES {
		uxsA2StatusHardwrResName,
		uxsA2StatusHardwrResSubName,
		uxsA2StatusHardwrInstName,
		uxsA2ConfigGeneralAgentVersion
	}
	DESCRIPTION "&<caiUxsA2.1784>A watcher monitoring a hardware resource changed its status to 'critical'. The varbind list contains a varbind with detailed information, encoded as a single string, including the name of the involved resource and the type and value of the involved metric; if applicable, the varbind also includes the current threshold settings and other information useful for automation purposes."
	::= 26983

uxsA2HardwrActive TRAP-TYPE
	ENTERPRISE caiUxsA2
	VARIABLES {
		uxsA2StatusHardwrResName,
		uxsA2StatusHardwrResSubName,
		uxsA2StatusHardwrInstName,
		uxsA2ConfigGeneralAgentVersion
	}
	DESCRIPTION "&<caiUxsA2.1785>A watcher monitoring a hardware resource changed its status from 'passive'. The varbind list contains a varbind with detailed information, encoded as a single string, including the name of the involved resource and the type and value of the involved metric; if applicable, the varbind also includes the current threshold settings and other information useful for automation purposes."
	::= 26984

uxsA2HardwrPassive TRAP-TYPE
	ENTERPRISE caiUxsA2
	VARIABLES {
		uxsA2StatusHardwrResName,
		uxsA2StatusHardwrResSubName,
		uxsA2StatusHardwrInstName,
		uxsA2ConfigGeneralAgentVersion
	}
	DESCRIPTION "&<caiUxsA2.1786>A watcher monitoring a hardware resource changed its status to 'passive'. The varbind list contains a varbind with detailed information, encoded as a single string, including the name of the involved resource and the type and value of the involved metric; if applicable, the varbind also includes the current threshold settings and other information useful for automation purposes."
	::= 26985

uxsA2HardwrAdded TRAP-TYPE
	ENTERPRISE caiUxsA2
	VARIABLES {
		uxsA2StatusHardwrResName,
		uxsA2StatusHardwrResSubName,
		uxsA2StatusHardwrInstName
	}
	DESCRIPTION "&<caiUxsA2.1787>A watcher monitoring a hardware resource was added. The varbind list contains the name of the involved resource."
	::= 26986

uxsA2HardwrDeleted TRAP-TYPE
	ENTERPRISE caiUxsA2
	VARIABLES {
		uxsA2StatusHardwrResName,
		uxsA2StatusHardwrResSubName,
		uxsA2StatusHardwrInstName
	}
	DESCRIPTION "&<caiUxsA2.1788>A watcher monitoring a hardware resource was removed. The varbind list contains the name of the involved resource."
	::= 26987

uxsA2HardwrInfo TRAP-TYPE
	ENTERPRISE caiUxsA2
	VARIABLES {
		uxsA2ConfigGeneralAgentVersion
	}
	DESCRIPTION "&<caiUxsA2.1789>A watcher monitoring a hardware resource changed a sub-state. The varbind list contains a varbind with detailed information, encoded as a single string, including the name of the involved resource, the old and the new status, and the type and value of the involved metric; if applicable, the varbind also includes the current threshold settings and other information useful for automation purposes."
	::= 26988

uxsA2HardwrModified TRAP-TYPE
	ENTERPRISE caiUxsA2
	VARIABLES {
		uxsA2ConfigGeneralAgentVersion
	}
	DESCRIPTION "&<caiUxsA2.1790>The watcher configuration for a hardware resource changed. The varbind list contains a varbind with detailed information, encoded as a single string, including the name of the involved resource and the changed attribute with its old value and with its new value."
	::= 26989

--
-- The Progrm Traps
--

uxsA2ProgrmUnknown TRAP-TYPE
	ENTERPRISE caiUxsA2
	VARIABLES {
		uxsA2StatusProgrmResName,
		uxsA2StatusProgrmResSubName,
		uxsA2StatusProgrmInstName,
		uxsA2ConfigGeneralAgentVersion
	}
	DESCRIPTION "&<caiUxsA2.1791>A watcher monitoring a programmable resource changed its status to 'unknown'. The varbind list contains a varbind with detailed information, encoded as a single string, including the name of the involved resource and the type and value of the involved metric; if applicable, the varbind also includes the current threshold settings and other information useful for automation purposes."
	::= 27980

uxsA2ProgrmOk TRAP-TYPE
	ENTERPRISE caiUxsA2
	VARIABLES {
		uxsA2StatusProgrmResName,
		uxsA2StatusProgrmResSubName,
		uxsA2StatusProgrmInstName,
		uxsA2ConfigGeneralAgentVersion
	}
	DESCRIPTION "&<caiUxsA2.1792>A watcher monitoring a programmable resource changed its status to 'ok'. The varbind list contains a varbind with detailed information, encoded as a single string, including the name of the involved resource and the type and value of the involved metric; if applicable, the varbind also includes the current threshold settings and other information useful for automation purposes."
	::= 27981

uxsA2ProgrmWarning TRAP-TYPE
	ENTERPRISE caiUxsA2
	VARIABLES {
		uxsA2StatusProgrmResName,
		uxsA2StatusProgrmResSubName,
		uxsA2StatusProgrmInstName,
		uxsA2ConfigGeneralAgentVersion
	}
	DESCRIPTION "&<caiUxsA2.1793>A watcher monitoring a programmable resource changed its status to 'warning'. The varbind list contains a varbind with detailed information, encoded as a single string, including the name of the involved resource and the type and value of the involved metric; if applicable, the varbind also includes the current threshold settings and other information useful for automation purposes."
	::= 27982

uxsA2ProgrmCritical TRAP-TYPE
	ENTERPRISE caiUxsA2
	VARIABLES {
		uxsA2StatusProgrmResName,
		uxsA2StatusProgrmResSubName,
		uxsA2StatusProgrmInstName,
		uxsA2ConfigGeneralAgentVersion
	}
	DESCRIPTION "&<caiUxsA2.1794>A watcher monitoring a programmable resource changed its status to 'critical'. The varbind list contains a varbind with detailed information, encoded as a single string, including the name of the involved resource and the type and value of the involved metric; if applicable, the varbind also includes the current threshold settings and other information useful for automation purposes."
	::= 27983

uxsA2ProgrmActive TRAP-TYPE
	ENTERPRISE caiUxsA2
	VARIABLES {
		uxsA2StatusProgrmResName,
		uxsA2StatusProgrmResSubName,
		uxsA2StatusProgrmInstName,
		uxsA2ConfigGeneralAgentVersion
	}
	DESCRIPTION "&<caiUxsA2.1795>A watcher monitoring a programmable resource changed its status from 'passive'. The varbind list contains a varbind with detailed information, encoded as a single string, including the name of the involved resource and the type and value of the involved metric; if applicable, the varbind also includes the current threshold settings and other information useful for automation purposes."
	::= 27984

uxsA2ProgrmPassive TRAP-TYPE
	ENTERPRISE caiUxsA2
	VARIABLES {
		uxsA2StatusProgrmResName,
		uxsA2StatusProgrmResSubName,
		uxsA2StatusProgrmInstName,
		uxsA2ConfigGeneralAgentVersion
	}
	DESCRIPTION "&<caiUxsA2.1796>A watcher monitoring a programmable resource changed its status to 'passive'. The varbind list contains a varbind with detailed information, encoded as a single string, including the name of the involved resource and the type and value of the involved metric; if applicable, the varbind also includes the current threshold settings and other information useful for automation purposes."
	::= 27985

uxsA2ProgrmAdded TRAP-TYPE
	ENTERPRISE caiUxsA2
	VARIABLES {
		uxsA2StatusProgrmResName,
		uxsA2StatusProgrmResSubName,
		uxsA2StatusProgrmInstName
	}
	DESCRIPTION "&<caiUxsA2.1797>A watcher monitoring a programmable resource was added. The varbind list contains the name of the involved resource."
	::= 27986

uxsA2ProgrmDeleted TRAP-TYPE
	ENTERPRISE caiUxsA2
	VARIABLES {
		uxsA2StatusProgrmResName,
		uxsA2StatusProgrmResSubName,
		uxsA2StatusProgrmInstName
	}
	DESCRIPTION "&<caiUxsA2.1798>A watcher monitoring a programmable resource was removed. The varbind list contains the name of the involved resource."
	::= 27987

uxsA2ProgrmInfo TRAP-TYPE
	ENTERPRISE caiUxsA2
	VARIABLES {
		uxsA2ConfigGeneralAgentVersion
	}
	DESCRIPTION "&<caiUxsA2.1799>A watcher monitoring a programmable resource changed a sub-state. The varbind list contains a varbind with detailed information, encoded as a single string, including the name of the involved resource, the old and the new status, and the type and value of the involved metric; if applicable, the varbind also includes the current threshold settings and other information useful for automation purposes."
	::= 27988

uxsA2ProgrmModified TRAP-TYPE
	ENTERPRISE caiUxsA2
	VARIABLES {
		uxsA2ConfigGeneralAgentVersion
	}
	DESCRIPTION "&<caiUxsA2.1800>The watcher configuration for a programmable resource changed. The varbind list contains a varbind with detailed information, encoded as a single string, including the name of the involved resource and the changed attribute with its old value and with its new value."
	::= 27989


--  ========================================================================
--
--  Extension groups of caiUxsA2 MIB:
--  ---------------------------------
--  uxsEHGroup added to support reports for Concord eHealth
--
--  ========================================================================
uxsA2ExtensionGroup OBJECT IDENTIFIER ::= { caiUxsA2 5 }

uxsEHGroup OBJECT IDENTIFIER ::= { uxsA2ExtensionGroup 1 }


--  ---------------------------------
--  Poll information
--  ---------------------------------
uxsEHPollMethod OBJECT-TYPE
	SYNTAX INTEGER {
		disabled(1),
		enabled(2)
	}
	ACCESS read-write
	STATUS mandatory
	DESCRIPTION "The poll method for the eHealth group. If set to disabled, polling of this group is not possible."
	DEFVAL { 2 }
	::= { uxsEHGroup 1 }

uxsEHLastPoll OBJECT-TYPE
	SYNTAX TimeTicks
	ACCESS read-only
	STATUS mandatory
	DESCRIPTION "The value of uxsEHSrvSystemUpTime at the point in time the uxsEHSrvGroup group (and all uxsEH tables) was last polled."
	::= { uxsEHGroup 2 }


--  ---------------------------------
--  Server group
--  ---------------------------------
uxsEHSrvGroup OBJECT IDENTIFIER ::= { uxsEHGroup 3 }

uxsEHSrvSystemUpTime OBJECT-TYPE
	SYNTAX TimeTicks
	ACCESS read-only
	STATUS mandatory
	DESCRIPTION "The time (in hundredths of a second) since the system was last started."
	::= { uxsEHSrvGroup 1 }

uxsEHSrvSystemNumUsers OBJECT-TYPE
	SYNTAX Gauge
	ACCESS read-only
	STATUS mandatory
	DESCRIPTION "The number of users."
	::= { uxsEHSrvGroup 2 }

uxsEHSrvSystemProcesses OBJECT-TYPE
	SYNTAX Gauge
	ACCESS read-only
	STATUS mandatory
	DESCRIPTION "The number of processes."
	::= { uxsEHSrvGroup 3 }

uxsEHSrvMemorySize OBJECT-TYPE
	SYNTAX KBytes
	ACCESS read-only
	STATUS mandatory
	DESCRIPTION "The amount of physical main memory contained by the host."
	::= { uxsEHSrvGroup 4 }

uxsEHSrvMemInUse OBJECT-TYPE
	SYNTAX Gauge
	ACCESS read-only
	STATUS mandatory
	DESCRIPTION "The total real KBytes of memory in use."
	::= { uxsEHSrvGroup 5 }

uxsEHSrvTotalSwapSpace OBJECT-TYPE
	SYNTAX INTEGER
	ACCESS read-only
	STATUS mandatory
	DESCRIPTION "Total system swap space in KBytes."
	::= { uxsEHSrvGroup 6 }

uxsEHSrvSwapInUse OBJECT-TYPE
	SYNTAX Gauge
	ACCESS read-only
	STATUS mandatory
	DESCRIPTION "The amount of swap space in KBytes currently in use by the system."
	::= { uxsEHSrvGroup 7 }

uxsEHSrvLoadAverage5Min OBJECT-TYPE
	SYNTAX INTEGER
	ACCESS read-only
	STATUS mandatory
	DESCRIPTION "The load average over the last 5 minutes. The load average represents the average number of jobs in the run queue over the specified time range. The value reported is the load average multiplied by 100."
	::= { uxsEHSrvGroup 8 }

uxsEHSrvNumBreadRequests OBJECT-TYPE
	SYNTAX Counter
	ACCESS read-only
	STATUS mandatory
	DESCRIPTION "The total number of calls to the kernel's bread() function."
	::= { uxsEHSrvGroup 9 }

uxsEHSrvNumBreadHits OBJECT-TYPE
	SYNTAX Counter
	ACCESS read-only
	STATUS mandatory
	DESCRIPTION "The number of kernel buffer cache 'hits'."
	::= { uxsEHSrvGroup 10 }

uxsEHSrvSystemCalls OBJECT-TYPE
	SYNTAX Counter
	ACCESS read-only
	STATUS mandatory
	DESCRIPTION "The number of calls to system service routines."
	::= { uxsEHSrvGroup 11 }

uxsEHSrvInterrupts OBJECT-TYPE
	SYNTAX Counter
	ACCESS read-only
	STATUS mandatory
	DESCRIPTION "The number of hardware interrupts that have occurred."
	::= { uxsEHSrvGroup 12 }

uxsEHSrvPageFaults OBJECT-TYPE
	SYNTAX Counter
	ACCESS read-only
	STATUS mandatory
	DESCRIPTION "Number of page faults in the processor."
	::= { uxsEHSrvGroup 13 }

uxsEHSrvPageSwapIns OBJECT-TYPE
	SYNTAX Counter
	ACCESS read-only
	STATUS mandatory
	DESCRIPTION "The total number of pages that have been swapped in since the kernel was last initialized."
	::= { uxsEHSrvGroup 14 }

uxsEHSrvPageSwapOuts OBJECT-TYPE
	SYNTAX Counter
	ACCESS read-only
	STATUS mandatory
	DESCRIPTION "The total number of pages that have been swapped out since the kernel was last initialized."
	::= { uxsEHSrvGroup 15 }

uxsEHSrvPageIns OBJECT-TYPE
	SYNTAX Counter
	ACCESS read-only
	STATUS mandatory
	DESCRIPTION "The total number of processes that have been swapped in since the kernel was last initialized."
	::= { uxsEHSrvGroup 16 }

uxsEHSrvPageOuts OBJECT-TYPE
	SYNTAX Counter
	ACCESS read-only
	STATUS mandatory
	DESCRIPTION "The total number of processes that have been swapped out since the kernel was last initialized."
	::= { uxsEHSrvGroup 17 }

uxsEHSrvPageScans OBJECT-TYPE
	SYNTAX Counter
	ACCESS read-only
	STATUS mandatory
	DESCRIPTION "Total number of pages examined by pageout daemon."
	::= { uxsEHSrvGroup 18 }

uxsEHSrvIfNumber OBJECT-TYPE
	SYNTAX INTEGER
	ACCESS read-only
	STATUS mandatory
	DESCRIPTION "The number of network interfaces."
	::= { uxsEHSrvGroup 19 }

--  ---------------------------------
--  Cpu table
--  ---------------------------------
uxsEHCpuTable OBJECT-TYPE
	SYNTAX SEQUENCE OF UxsEHCpuEntry
	ACCESS not-accessible
	STATUS mandatory
	DESCRIPTION ""
	::= { uxsEHGroup 4 }

uxsEHCpuEntry OBJECT-TYPE
	SYNTAX UxsEHCpuEntry
	ACCESS not-accessible
	STATUS mandatory
	DESCRIPTION ""
	INDEX { uxsEHCpuIndex }
	::= { uxsEHCpuTable 1 }

UxsEHCpuEntry ::= SEQUENCE {
	uxsEHCpuIndex INTEGER,
	uxsEHCpuName DisplayString,
	uxsEHCpuIdle Counter,
	uxsEHCpuUser Counter,
	uxsEHCpuSys Counter,
	uxsEHCpuWait Counter
}

uxsEHCpuIndex OBJECT-TYPE
	SYNTAX INTEGER (1..2147483647)
	ACCESS read-only
	STATUS mandatory
	DESCRIPTION "The unique index of this table entry."
	::= { uxsEHCpuEntry 1 }

uxsEHCpuName OBJECT-TYPE
	SYNTAX DisplayString
	ACCESS read-only
	STATUS mandatory
	DESCRIPTION "The name of the CPU (in the format 'Cpu-N')."
	::= { uxsEHCpuEntry 2 }

uxsEHCpuIdle OBJECT-TYPE
	SYNTAX Counter
	ACCESS read-only
	STATUS mandatory
	DESCRIPTION "The total number of 'ticks' spent by this CPU in Idle mode."
	::= { uxsEHCpuEntry 3 }

uxsEHCpuUser OBJECT-TYPE
	SYNTAX Counter
	ACCESS read-only
	STATUS mandatory
	DESCRIPTION "The total number of 'ticks' spent by this CPU in User mode."
	::= { uxsEHCpuEntry 4 }

uxsEHCpuSys OBJECT-TYPE
	SYNTAX Counter
	ACCESS read-only
	STATUS mandatory
	DESCRIPTION "The total number of 'ticks' spent by this CPU in System mode."
	::= { uxsEHCpuEntry 5 }

uxsEHCpuWait OBJECT-TYPE
	SYNTAX Counter
	ACCESS read-only
	STATUS mandatory
	DESCRIPTION "The total number of 'ticks' spent by this CPU in Wait mode."
	::= { uxsEHCpuEntry 6 }


--  ---------------------------------
--  Disk table
--  ---------------------------------
uxsEHDiskTable OBJECT-TYPE
	SYNTAX SEQUENCE OF UxsEHDiskEntry
	ACCESS not-accessible
	STATUS mandatory
	DESCRIPTION ""
	::= { uxsEHGroup 5 }

uxsEHDiskEntry OBJECT-TYPE
	SYNTAX UxsEHDiskEntry
	ACCESS not-accessible
	STATUS mandatory
	DESCRIPTION ""
	INDEX { uxsEHDiskIndex }
	::= { uxsEHDiskTable 1 }

UxsEHDiskEntry ::= SEQUENCE {
	uxsEHDiskIndex INTEGER,
	uxsEHDiskName DisplayString,
	uxsEHDiskDeviceErrors Counter,
	uxsEHDiskStorageCapacity INTEGER,
	uxsEHDiskQueueLength Gauge,
	uxsEHDiskUtilization INTEGER,
	uxsEHDiskKBytesTransferred Counter,
	uxsEHDiskReads Counter,
	uxsEHDiskWrites Counter
}

uxsEHDiskIndex OBJECT-TYPE
	SYNTAX INTEGER (1..2147483647)
	ACCESS read-only
	STATUS mandatory
	DESCRIPTION "The unique index of this table entry."
	::= { uxsEHDiskEntry 1 }

uxsEHDiskName OBJECT-TYPE
	SYNTAX DisplayString
	ACCESS read-only
	STATUS mandatory
	DESCRIPTION "The name of the disk (in the format 'HarddiskN')."
	::= { uxsEHDiskEntry 2 }

uxsEHDiskDeviceErrors OBJECT-TYPE
	SYNTAX Counter
	ACCESS read-only
	STATUS mandatory
	DESCRIPTION "The number of errors detected on this disk."
	::= { uxsEHDiskEntry 3 }

uxsEHDiskStorageCapacity OBJECT-TYPE
	SYNTAX INTEGER (0..2147483647)
	ACCESS read-only
	STATUS mandatory
	DESCRIPTION "Disk capacity in KB."
	::= { uxsEHDiskEntry 4 }

uxsEHDiskQueueLength OBJECT-TYPE
	SYNTAX Gauge
	ACCESS read-only
	STATUS mandatory
	DESCRIPTION "The average number of operations waiting in the disk's service queue over the last measurement period."
	::= { uxsEHDiskEntry 5 }

uxsEHDiskUtilization OBJECT-TYPE
	SYNTAX INTEGER (0..100)
	ACCESS read-only
	STATUS mandatory
	DESCRIPTION "The utilization rate (percentage) for this disk over the last measurement period."
	::= { uxsEHDiskEntry 6 }

uxsEHDiskKBytesTransferred OBJECT-TYPE
	SYNTAX Counter
	ACCESS read-only
	STATUS mandatory
	DESCRIPTION "The number of KBytes transferred to/from this disk."
	::= { uxsEHDiskEntry 7}

uxsEHDiskReads OBJECT-TYPE
	SYNTAX Counter
	ACCESS read-only
	STATUS mandatory
	DESCRIPTION "The number of read operations from this disk."
	::= { uxsEHDiskEntry 8 }

uxsEHDiskWrites OBJECT-TYPE
	SYNTAX Counter
	ACCESS read-only
	STATUS mandatory
	DESCRIPTION "The number of write operations to this disk."
	::= { uxsEHDiskEntry 9 }


--  ---------------------------------
--  Device (partition) table
--  ---------------------------------
uxsEHDevTable OBJECT-TYPE
	SYNTAX SEQUENCE OF UxsEHDevEntry
	ACCESS not-accessible
	STATUS mandatory
	DESCRIPTION ""
	::= { uxsEHGroup 6 }

uxsEHDevEntry OBJECT-TYPE
	SYNTAX UxsEHDevEntry
	ACCESS not-accessible
	STATUS mandatory
	DESCRIPTION ""
	INDEX { uxsEHDevIndex }
	::= { uxsEHDevTable 1 }

UxsEHDevEntry ::= SEQUENCE {
	uxsEHDevIndex INTEGER,
	uxsEHDevName DisplayString,
	uxsEHDevBsize INTEGER,
	uxsEHDevTblks INTEGER,
	uxsEHDevCapacity INTEGER,
	uxsEHDevInodeCapacity INTEGER,
	uxsEHDevStorageAllocationFailures Counter
}

uxsEHDevIndex OBJECT-TYPE
	SYNTAX INTEGER (1..2147483647)
	ACCESS read-only
	STATUS mandatory
	DESCRIPTION "The unique index of this table entry."
	::= { uxsEHDevEntry 1 }

uxsEHDevName OBJECT-TYPE
	SYNTAX DisplayString
	ACCESS read-only
	STATUS mandatory
	DESCRIPTION "The name of the device (partition)."
	::= { uxsEHDevEntry 2 }

uxsEHDevBsize OBJECT-TYPE
	SYNTAX INTEGER
	ACCESS read-only
	STATUS mandatory
	DESCRIPTION "The block size of the mounted device in bytes."
	::= { uxsEHDevEntry 3 }

uxsEHDevTblks OBJECT-TYPE
	SYNTAX INTEGER
	ACCESS read-only
	STATUS mandatory
	DESCRIPTION "The total number of blocks contained in the mounted device."
	::= { uxsEHDevEntry 4 }

uxsEHDevCapacity OBJECT-TYPE
	SYNTAX INTEGER (0..100)
	ACCESS read-only
	STATUS mandatory
	DESCRIPTION "The percentage of the device's total capacity in use."
	::= { uxsEHDevEntry 5 }

uxsEHDevInodeCapacity OBJECT-TYPE
	SYNTAX INTEGER (0..100)
	ACCESS read-only
	STATUS mandatory
	DESCRIPTION "The percentage of the device's total file capacity (inodes) in use."
	::= { uxsEHDevEntry 6 }

uxsEHDevStorageAllocationFailures OBJECT-TYPE
	SYNTAX Counter
	ACCESS read-only
	STATUS mandatory
	DESCRIPTION "The number of requests for storage represented by this entry that could not be honored due to not enough storage."
	::= { uxsEHDevEntry 7 }


--  ---------------------------------
--  Network interface table
--  ---------------------------------
uxsEHIfTable OBJECT-TYPE
	SYNTAX SEQUENCE OF UxsEHIfEntry
	ACCESS not-accessible
	STATUS mandatory
	DESCRIPTION ""
	::= { uxsEHGroup 7 }

uxsEHIfEntry OBJECT-TYPE
	SYNTAX UxsEHIfEntry
	ACCESS not-accessible
	STATUS mandatory
	DESCRIPTION ""
	INDEX { uxsEHIfIndex }
	::= { uxsEHIfTable 1 }

UxsEHIfEntry ::= SEQUENCE {
	uxsEHIfIndex INTEGER,
	uxsEHIfDescr DisplayString,
	uxsEHIfType INTEGER,
	uxsEHIfSpeed Gauge,
	uxsEHIfPhysAddress PhysAddress,
	uxsEHIfAdminStatus INTEGER,
	uxsEHIfOperStatus INTEGER,
	uxsEHIfLastChange TimeTicks,
	uxsEHIfInOctets Counter,
	uxsEHIfInUcastPkts Counter,
	uxsEHIfInNUcastPkts Counter,
	uxsEHIfInDiscards Counter,
	uxsEHIfInErrors Counter,
	uxsEHIfInUnknownProtos Counter,
	uxsEHIfOutOctets Counter,
	uxsEHIfOutUcastPkts Counter,
	uxsEHIfOutNUcastPkts Counter,
	uxsEHIfOutDiscards Counter,
	uxsEHIfOutErrors Counter,
	uxsEHIfIpAdEntAddr IpAddress
}

uxsEHIfIndex OBJECT-TYPE
	SYNTAX INTEGER (1..2147483647)
	ACCESS read-only
	STATUS mandatory
	DESCRIPTION "The unique index of this table entry."
	::= { uxsEHIfEntry 1 }

uxsEHIfDescr OBJECT-TYPE
	SYNTAX DisplayString
	ACCESS read-only
	STATUS mandatory
	DESCRIPTION "The description of the network interface."
	::= { uxsEHIfEntry 2 }

uxsEHIfType OBJECT-TYPE
	SYNTAX INTEGER
	ACCESS read-only
	STATUS mandatory
	DESCRIPTION "The type of interface."
	::= { uxsEHIfEntry 3 }

uxsEHIfSpeed OBJECT-TYPE
	SYNTAX Gauge
	ACCESS read-only
	STATUS mandatory
	DESCRIPTION "An estimate of the interface's current bandwidth in bits per second."
	::= { uxsEHIfEntry 4 }

uxsEHIfPhysAddress OBJECT-TYPE
	SYNTAX PhysAddress
	ACCESS read-only
	STATUS mandatory
	DESCRIPTION "The interface's address at the protocol layer."
	::= { uxsEHIfEntry 5 }

uxsEHIfAdminStatus OBJECT-TYPE
	SYNTAX INTEGER {
		up(1),
		down(2),
		testing(3),
		unknown(4),
		dormant(5)
	}
	ACCESS read-only
	STATUS mandatory
	DESCRIPTION "The desired state of the interface."
	::= { uxsEHIfEntry 6 }

uxsEHIfOperStatus OBJECT-TYPE
	SYNTAX INTEGER {
		up(1),
		down(2),
		testing(3),
		unknown(4),
		dormant(5)
	}
	ACCESS read-only
	STATUS mandatory
	DESCRIPTION "The current operational state of the interface."
	::= { uxsEHIfEntry 7 }

uxsEHIfLastChange OBJECT-TYPE
	SYNTAX TimeTicks
	ACCESS read-only
	STATUS mandatory
	DESCRIPTION "The value of sysUpTime at the time the interface entered its current operational state."
	::= { uxsEHIfEntry 8 }

uxsEHIfInOctets OBJECT-TYPE
	SYNTAX Counter
	ACCESS read-only
	STATUS mandatory
	DESCRIPTION "The total number of octets received on the interface, including framing characters."
	::= { uxsEHIfEntry 9 }

uxsEHIfInUcastPkts OBJECT-TYPE
	SYNTAX Counter
	ACCESS read-only
	STATUS mandatory
	DESCRIPTION "The number of subnetwork-unicast packets delivered to a higher-layer protocol."
	::= { uxsEHIfEntry 10 }

uxsEHIfInNUcastPkts OBJECT-TYPE
	SYNTAX Counter
	ACCESS read-only
	STATUS mandatory
	DESCRIPTION "The number of non-unicast (i.e., subnetwork-broadcast or subnetwork-multicast) packets delivered to a higher-layer protocol."
	::= { uxsEHIfEntry 11 }

uxsEHIfInDiscards OBJECT-TYPE
	SYNTAX Counter
	ACCESS read-only
	STATUS mandatory
	DESCRIPTION "The number of inbound packets which were chosen to be discarded even though no errors had been detected to prevent their being deliverable to a higher-layer protocol."
	::= { uxsEHIfEntry 12 }

uxsEHIfInErrors OBJECT-TYPE
	SYNTAX Counter
	ACCESS read-only
	STATUS mandatory
	DESCRIPTION "The number of inbound packets that contained errors preventing them from being deliverable to a higher-layer protocol."
	::= { uxsEHIfEntry 13 }

uxsEHIfInUnknownProtos OBJECT-TYPE
	SYNTAX Counter
	ACCESS read-only
	STATUS mandatory
	DESCRIPTION "The number of packets received via the interface which were discarded because of an unknown or unsupported protocol."
	::= { uxsEHIfEntry 14 }

uxsEHIfOutOctets OBJECT-TYPE
	SYNTAX Counter
	ACCESS read-only
	STATUS mandatory
	DESCRIPTION "The total number of octets transmitted out of the interface, including framing characters."
	::= { uxsEHIfEntry 15 }

uxsEHIfOutUcastPkts OBJECT-TYPE
	SYNTAX Counter
	ACCESS read-only
	STATUS mandatory
	DESCRIPTION "The total number of packets that higher-level protocols requested be transmitted to a subnetwork-unicast address, including those that were discarded or not sent."
	::= { uxsEHIfEntry 16 }

uxsEHIfOutNUcastPkts OBJECT-TYPE
	SYNTAX Counter
	ACCESS read-only
	STATUS mandatory
	DESCRIPTION "The total number of packets that higher-level protocols requested be transmitted to a non-unicast (i.e., a subnetwork-broadcast or subnetwork-multicast) address, including those that were discarded or not sent."
	::= { uxsEHIfEntry 17 }

uxsEHIfOutDiscards OBJECT-TYPE
	SYNTAX Counter
	ACCESS read-only
	STATUS mandatory
	DESCRIPTION "The number of outbound packets which were chosen to be discarded even though no errors had been detected to prevent their being transmitted."
	::= { uxsEHIfEntry 18 }

uxsEHIfOutErrors OBJECT-TYPE
	SYNTAX Counter
	ACCESS read-only
	STATUS mandatory
	DESCRIPTION "The number of outbound packets that could not be transmitted because of errors."
	::= { uxsEHIfEntry 19 }

uxsEHIfIpAdEntAddr OBJECT-TYPE
	SYNTAX IpAddress
	ACCESS read-only
	STATUS mandatory
	DESCRIPTION "The IP address."
	::= { uxsEHIfEntry 20 }


--  ---------------------------------
--  Process table
--  ---------------------------------
uxsEHProcTable OBJECT-TYPE
	SYNTAX SEQUENCE OF UxsEHProcEntry
	ACCESS not-accessible
	STATUS mandatory
	DESCRIPTION ""
	::= { uxsEHGroup 8 }

uxsEHProcEntry OBJECT-TYPE
	SYNTAX UxsEHProcEntry
	ACCESS not-accessible
	STATUS mandatory
	DESCRIPTION ""
	INDEX { uxsEHProcName }
	::= { uxsEHProcTable 1 }

UxsEHProcEntry ::= SEQUENCE {
	uxsEHProcName DisplayString,
	uxsEHProcNumber INTEGER,
	uxsEHProcPid DisplayString,
	uxsEHProcState INTEGER,
	uxsEHProcSize Gauge,
	uxsEHProcRSS Gauge,
	uxsEHProcTime INTEGER,
	uxsEHProcMinorPgFlts Counter,
	uxsEHProcMajorPgFlts Counter
}

uxsEHProcName OBJECT-TYPE
	SYNTAX DisplayString
	ACCESS read-only
	STATUS mandatory
	DESCRIPTION "The unique index (process name) of this table entry. This name is case-sensitive."
	::= { uxsEHProcEntry 1 }

uxsEHProcNumber OBJECT-TYPE
	SYNTAX INTEGER
	ACCESS read-only
	STATUS mandatory
	DESCRIPTION "The number of processes with this name."
	::= { uxsEHProcEntry 2 }

uxsEHProcPid OBJECT-TYPE
	SYNTAX DisplayString
	ACCESS read-only
	STATUS mandatory
	DESCRIPTION "The process identifier (PID). If uxsEHProcNumber is greater one, this attribute lists all PIDs, delimited by a pipe sign."
	::= { uxsEHProcEntry 3 }

uxsEHProcState OBJECT-TYPE
	SYNTAX INTEGER {
		starting(1),
		runnable(2),
		active(3),
		wait(4),
		sleeping(5),
		swapped(6),
		sleep(7),
		stop(8),
		other(9),
		zombie(10)
	}
	ACCESS read-only
	STATUS deprecated
	DESCRIPTION "The process state. Not all states are supported on all platforms. If uxsEHProcNumber is greater one, this attribute is set to other(9)."
	::= { uxsEHProcEntry 4 }

uxsEHProcSize OBJECT-TYPE
	SYNTAX Gauge
	ACCESS read-only
	STATUS mandatory
	DESCRIPTION "The combined size of the text, data and stack segments in KBytes. If uxsEHProcNumber is greater one, this attribute is the accumulated value."
::= { uxsEHProcEntry 5 }

uxsEHProcRSS OBJECT-TYPE
	SYNTAX Gauge
	ACCESS read-only
	STATUS mandatory
	DESCRIPTION "Real memory (resident set) size of the process in KBytes. If uxsEHProcNumber is greater one, this attribute is the accumulated value."
::= { uxsEHProcEntry 6 }

uxsEHProcTime OBJECT-TYPE
	SYNTAX INTEGER
	ACCESS read-only
	STATUS mandatory
	DESCRIPTION "This process' accumulated CPU time in seconds. If uxsEHProcNumber is greater one, this attribute is the accumulated value."
::= { uxsEHProcEntry 7 }

uxsEHProcMinorPgFlts OBJECT-TYPE
	SYNTAX Counter
	ACCESS read-only
	STATUS mandatory
	DESCRIPTION "The number of minor page faults incurred by this process. Minor faults do not require I/O to retrieve the page. If uxsEHProcNumber is greater one, this attribute is the accumulated value."
::= { uxsEHProcEntry 8 }

uxsEHProcMajorPgFlts OBJECT-TYPE
	SYNTAX Counter
	ACCESS read-only
	STATUS mandatory
	DESCRIPTION "The number of major page faults incurred by this process. Major faults require I/O to retrieve the page. If uxsEHProcNumber is greater one, this attribute is the accumulated value."
::= { uxsEHProcEntry 9 }


END
