-- file automatically created


TELDAT-TRAP-IPSE-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ipseTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IPSE event subsystem."
    REVISION "201401200930Z"
    DESCRIPTION "Initial implementation"
        ::= { telEventTraps 138 }


ipseEventsGroup	OBJECT IDENTIFIER	::= { ipseTrapsMIB 1 }

ipseNotifications	OBJECT IDENTIFIER	::= { ipseTrapsMIB 2 }
ipseNotificationsPrefix	OBJECT IDENTIFIER	::= { ipseNotifications 0 }

ipseEventObjects1 OBJECT-IDENTITY
    STATUS current
    DESCRIPTION
        "Event IPSE.1
        It is shown the protocol of the encapsulated packet and the SPI."
    ::= { ipseEventsGroup 1 }

ipse1_packet_type OBJECT-TYPE
    SYNTAX DisplayString
    MAX-ACCESS accessible-for-notify
    STATUS current
    DESCRIPTION
        "Parameter 'packet_type' in event IPSE.1"
    ::= { ipseEventObjects1 1 }

ipse1_SPI OBJECT-TYPE
    SYNTAX Integer32
    MAX-ACCESS accessible-for-notify
    STATUS current
    DESCRIPTION
        "Parameter 'SPI' in event IPSE.1"
    ::= { ipseEventObjects1 2 }

ipseEventObjects2 OBJECT-IDENTITY
    STATUS current
    DESCRIPTION
        "Event IPSE.2
        The received encapsulated packet has an unknown protocol."
    ::= { ipseEventsGroup 2 }

ipse2_protocol_type OBJECT-TYPE
    SYNTAX DisplayString
    MAX-ACCESS accessible-for-notify
    STATUS current
    DESCRIPTION
        "Parameter 'protocol_type' in event IPSE.2"
    ::= { ipseEventObjects2 1 }

ipseEventObjects3 OBJECT-IDENTITY
    STATUS current
    DESCRIPTION
        "Event IPSE.3
        The output function of the tunnel net has encapsulated a ESP or
        AH packet successfully. It is shown the protocol of the encapsulated
        packet, the source and destination direction and the SPI."
    ::= { ipseEventsGroup 3 }

ipse3_protocol_type OBJECT-TYPE
    SYNTAX DisplayString
    MAX-ACCESS accessible-for-notify
    STATUS current
    DESCRIPTION
        "Parameter 'protocol_type' in event IPSE.3"
    ::= { ipseEventObjects3 1 }

ipse3_src_ip_addr OBJECT-TYPE
    SYNTAX IpAddress
    MAX-ACCESS accessible-for-notify
    STATUS current
    DESCRIPTION
        "Parameter 'src_ip_addr' in event IPSE.3"
    ::= { ipseEventObjects3 2 }

ipse3_dest_ip_addr OBJECT-TYPE
    SYNTAX IpAddress
    MAX-ACCESS accessible-for-notify
    STATUS current
    DESCRIPTION
        "Parameter 'dest_ip_addr' in event IPSE.3"
    ::= { ipseEventObjects3 3 }

ipse3_SPI OBJECT-TYPE
    SYNTAX Integer32
    MAX-ACCESS accessible-for-notify
    STATUS current
    DESCRIPTION
        "Parameter 'SPI' in event IPSE.3"
    ::= { ipseEventObjects3 4 }

ipseEventObjects4 OBJECT-IDENTITY
    STATUS current
    DESCRIPTION
        "Event IPSE.4
        The authentication of an ESP or AH packet failed."
    ::= { ipseEventsGroup 4 }

ipse4_protocol_type OBJECT-TYPE
    SYNTAX DisplayString
    MAX-ACCESS accessible-for-notify
    STATUS current
    DESCRIPTION
        "Parameter 'protocol_type' in event IPSE.4"
    ::= { ipseEventObjects4 1 }

ipse4_sa_number OBJECT-TYPE
    SYNTAX Integer32
    MAX-ACCESS accessible-for-notify
    STATUS current
    DESCRIPTION
        "Parameter 'sa_number' in event IPSE.4"
    ::= { ipseEventObjects4 2 }

ipseEventObjects5 OBJECT-IDENTITY
    STATUS current
    DESCRIPTION
        "Event IPSE.5
        A packet was discarded because its secuence number was below
        the minimum admited in the reception window."
    ::= { ipseEventsGroup 5 }

ipse5_protocol_name OBJECT-TYPE
    SYNTAX DisplayString
    MAX-ACCESS accessible-for-notify
    STATUS current
    DESCRIPTION
        "Parameter 'protocol_name' in event IPSE.5"
    ::= { ipseEventObjects5 1 }

ipse5_src_ip_addr OBJECT-TYPE
    SYNTAX IpAddress
    MAX-ACCESS accessible-for-notify
    STATUS current
    DESCRIPTION
        "Parameter 'src_ip_addr' in event IPSE.5"
    ::= { ipseEventObjects5 2 }

ipse5_dest_ip_addr OBJECT-TYPE
    SYNTAX IpAddress
    MAX-ACCESS accessible-for-notify
    STATUS current
    DESCRIPTION
        "Parameter 'dest_ip_addr' in event IPSE.5"
    ::= { ipseEventObjects5 3 }

ipseEventObjects6 OBJECT-IDENTITY
    STATUS current
    DESCRIPTION
        "Event IPSE.6
        A packet was discarded because the antireplay options were active
        and it was already received."
    ::= { ipseEventsGroup 6 }

ipse6_protocol_name OBJECT-TYPE
    SYNTAX DisplayString
    MAX-ACCESS accessible-for-notify
    STATUS current
    DESCRIPTION
        "Parameter 'protocol_name' in event IPSE.6"
    ::= { ipseEventObjects6 1 }

ipse6_src_ip_addr OBJECT-TYPE
    SYNTAX IpAddress
    MAX-ACCESS accessible-for-notify
    STATUS current
    DESCRIPTION
        "Parameter 'src_ip_addr' in event IPSE.6"
    ::= { ipseEventObjects6 2 }

ipse6_dest_ip_addr OBJECT-TYPE
    SYNTAX IpAddress
    MAX-ACCESS accessible-for-notify
    STATUS current
    DESCRIPTION
        "Parameter 'dest_ip_addr' in event IPSE.6"
    ::= { ipseEventObjects6 3 }

ipseEventObjects8 OBJECT-IDENTITY
    STATUS current
    DESCRIPTION
        "Event IPSE.8
        A packet is discarded because it has a wrong length (it is not multiple
        of 32 bits)."
    ::= { ipseEventsGroup 8 }

ipse8_protocol_type OBJECT-TYPE
    SYNTAX DisplayString
    MAX-ACCESS accessible-for-notify
    STATUS current
    DESCRIPTION
        "Parameter 'protocol_type' in event IPSE.8"
    ::= { ipseEventObjects8 1 }

ipse8_src_ip_addr OBJECT-TYPE
    SYNTAX IpAddress
    MAX-ACCESS accessible-for-notify
    STATUS current
    DESCRIPTION
        "Parameter 'src_ip_addr' in event IPSE.8"
    ::= { ipseEventObjects8 2 }

ipse8_dest_ip_addr OBJECT-TYPE
    SYNTAX IpAddress
    MAX-ACCESS accessible-for-notify
    STATUS current
    DESCRIPTION
        "Parameter 'dest_ip_addr' in event IPSE.8"
    ::= { ipseEventObjects8 3 }

ipseEventObjects9 OBJECT-IDENTITY
    STATUS current
    DESCRIPTION
        "Event IPSE.9
        Packet with correct sequence number in window."
    ::= { ipseEventsGroup 9 }

ipse9_protocol_type OBJECT-TYPE
    SYNTAX DisplayString
    MAX-ACCESS accessible-for-notify
    STATUS current
    DESCRIPTION
        "Parameter 'protocol_type' in event IPSE.9"
    ::= { ipseEventObjects9 1 }

ipse9_src_ip_addr OBJECT-TYPE
    SYNTAX IpAddress
    MAX-ACCESS accessible-for-notify
    STATUS current
    DESCRIPTION
        "Parameter 'src_ip_addr' in event IPSE.9"
    ::= { ipseEventObjects9 2 }

ipse9_dest_ip_addr OBJECT-TYPE
    SYNTAX IpAddress
    MAX-ACCESS accessible-for-notify
    STATUS current
    DESCRIPTION
        "Parameter 'dest_ip_addr' in event IPSE.9"
    ::= { ipseEventObjects9 3 }

ipseEventObjects10 OBJECT-IDENTITY
    STATUS current
    DESCRIPTION
        "Event IPSE.10
        The packet has arrived to window secuence with 0 as secuence number."
    ::= { ipseEventsGroup 10 }

ipse10_protocol_type OBJECT-TYPE
    SYNTAX DisplayString
    MAX-ACCESS accessible-for-notify
    STATUS current
    DESCRIPTION
        "Parameter 'protocol_type' in event IPSE.10"
    ::= { ipseEventObjects10 1 }

ipse10_src_ip_addr OBJECT-TYPE
    SYNTAX IpAddress
    MAX-ACCESS accessible-for-notify
    STATUS current
    DESCRIPTION
        "Parameter 'src_ip_addr' in event IPSE.10"
    ::= { ipseEventObjects10 2 }

ipse10_dest_ip_addr OBJECT-TYPE
    SYNTAX IpAddress
    MAX-ACCESS accessible-for-notify
    STATUS current
    DESCRIPTION
        "Parameter 'dest_ip_addr' in event IPSE.10"
    ::= { ipseEventObjects10 3 }

ipseEventObjects11 OBJECT-IDENTITY
    STATUS current
    DESCRIPTION
        "Event IPSE.11
        The protocol, the SA sequence number and the packet sequence number
        are shown."
    ::= { ipseEventsGroup 11 }

ipse11_protocol_type OBJECT-TYPE
    SYNTAX DisplayString
    MAX-ACCESS accessible-for-notify
    STATUS current
    DESCRIPTION
        "Parameter 'protocol_type' in event IPSE.11"
    ::= { ipseEventObjects11 1 }

ipse11_spi OBJECT-TYPE
    SYNTAX Integer32
    MAX-ACCESS accessible-for-notify
    STATUS current
    DESCRIPTION
        "Parameter 'spi' in event IPSE.11"
    ::= { ipseEventObjects11 2 }

ipse11_sa_seq_num OBJECT-TYPE
    SYNTAX Integer32
    MAX-ACCESS accessible-for-notify
    STATUS current
    DESCRIPTION
        "Parameter 'sa_seq_num' in event IPSE.11"
    ::= { ipseEventObjects11 3 }

ipse11_inbound_seq_num OBJECT-TYPE
    SYNTAX Integer32
    MAX-ACCESS accessible-for-notify
    STATUS current
    DESCRIPTION
        "Parameter 'inbound_seq_num' in event IPSE.11"
    ::= { ipseEventObjects11 4 }

ipseEventObjects12 OBJECT-IDENTITY
    STATUS current
    DESCRIPTION
        "Event IPSE.12
        A packet has arrived with the SPI showed and there is not an
        static SA configured for it."
    ::= { ipseEventsGroup 12 }

ipse12_spi OBJECT-TYPE
    SYNTAX Integer32
    MAX-ACCESS accessible-for-notify
    STATUS current
    DESCRIPTION
        "Parameter 'spi' in event IPSE.12"
    ::= { ipseEventObjects12 1 }

ipse12_protocol OBJECT-TYPE
    SYNTAX Integer32
    MAX-ACCESS accessible-for-notify
    STATUS current
    DESCRIPTION
        "Parameter 'protocol' in event IPSE.12"
    ::= { ipseEventObjects12 2 }

ipse12_remote_peer OBJECT-TYPE
    SYNTAX IpAddress
    MAX-ACCESS accessible-for-notify
    STATUS current
    DESCRIPTION
        "Parameter 'remote_peer' in event IPSE.12"
    ::= { ipseEventObjects12 3 }

ipseEventObjects13 OBJECT-IDENTITY
    STATUS current
    DESCRIPTION
        "Event IPSE.13
        Overflow in sequence number the next sequence number is 1."
    ::= { ipseEventsGroup 13 }

ipse13_protocol_type OBJECT-TYPE
    SYNTAX DisplayString
    MAX-ACCESS accessible-for-notify
    STATUS current
    DESCRIPTION
        "Parameter 'protocol_type' in event IPSE.13"
    ::= { ipseEventObjects13 1 }

ipseEventObjects14 OBJECT-IDENTITY
    STATUS current
    DESCRIPTION
        "Event IPSE.14
        A packet has arrived with SPI %x and there is not an
        static SA configured for it."
    ::= { ipseEventsGroup 14 }

ipse14_spi OBJECT-TYPE
    SYNTAX Integer32
    MAX-ACCESS accessible-for-notify
    STATUS current
    DESCRIPTION
        "Parameter 'spi' in event IPSE.14"
    ::= { ipseEventObjects14 1 }

ipse14_protocol OBJECT-TYPE
    SYNTAX Integer32
    MAX-ACCESS accessible-for-notify
    STATUS current
    DESCRIPTION
        "Parameter 'protocol' in event IPSE.14"
    ::= { ipseEventObjects14 2 }

ipse14_remote_peer OBJECT-TYPE
    SYNTAX IpAddress
    MAX-ACCESS accessible-for-notify
    STATUS current
    DESCRIPTION
        "Parameter 'remote_peer' in event IPSE.14"
    ::= { ipseEventObjects14 3 }

ipseEventObjects15 OBJECT-IDENTITY
    STATUS current
    DESCRIPTION
        "Event IPSE.15
        Found entry hasn't policy assigned. (Debug)."
    ::= { ipseEventsGroup 15 }

ipse15_src_ip_addr OBJECT-TYPE
    SYNTAX IpAddress
    MAX-ACCESS accessible-for-notify
    STATUS current
    DESCRIPTION
        "Parameter 'src_ip_addr' in event IPSE.15"
    ::= { ipseEventObjects15 1 }

ipse15_dest_ip_addr OBJECT-TYPE
    SYNTAX IpAddress
    MAX-ACCESS accessible-for-notify
    STATUS current
    DESCRIPTION
        "Parameter 'dest_ip_addr' in event IPSE.15"
    ::= { ipseEventObjects15 2 }

ipseEventObjects16 OBJECT-IDENTITY
    STATUS current
    DESCRIPTION
        "Event IPSE.16
        Attributes are wrong."
    ::= { ipseEventsGroup 16 }

ipse16_message OBJECT-TYPE
    SYNTAX Integer32
    MAX-ACCESS accessible-for-notify
    STATUS current
    DESCRIPTION
        "Parameter 'message' in event IPSE.16"
    ::= { ipseEventObjects16 1 }

ipse16_phase OBJECT-TYPE
    SYNTAX Integer32
    MAX-ACCESS accessible-for-notify
    STATUS current
    DESCRIPTION
        "Parameter 'phase' in event IPSE.16"
    ::= { ipseEventObjects16 2 }

ipse16_src_ip_addr OBJECT-TYPE
    SYNTAX IpAddress
    MAX-ACCESS accessible-for-notify
    STATUS current
    DESCRIPTION
        "Parameter 'src_ip_addr' in event IPSE.16"
    ::= { ipseEventObjects16 3 }

ipse16_dest_ip_addr OBJECT-TYPE
    SYNTAX IpAddress
    MAX-ACCESS accessible-for-notify
    STATUS current
    DESCRIPTION
        "Parameter 'dest_ip_addr' in event IPSE.16"
    ::= { ipseEventObjects16 4 }

ipseEventObjects17 OBJECT-IDENTITY
    STATUS current
    DESCRIPTION
        "Event IPSE.17
        Error allocating memory."
    ::= { ipseEventsGroup 17 }

ipse17_message OBJECT-TYPE
    SYNTAX DisplayString
    MAX-ACCESS accessible-for-notify
    STATUS current
    DESCRIPTION
        "Parameter 'message' in event IPSE.17"
    ::= { ipseEventObjects17 1 }

ipseEventObjects18 OBJECT-IDENTITY
    STATUS current
    DESCRIPTION
        "Event IPSE.18
        Incompatible IKE policies."
    ::= { ipseEventsGroup 18 }

ipse18_src_ip_addr OBJECT-TYPE
    SYNTAX IpAddress
    MAX-ACCESS accessible-for-notify
    STATUS current
    DESCRIPTION
        "Parameter 'src_ip_addr' in event IPSE.18"
    ::= { ipseEventObjects18 1 }

ipse18_dest_ip_addr OBJECT-TYPE
    SYNTAX IpAddress
    MAX-ACCESS accessible-for-notify
    STATUS current
    DESCRIPTION
        "Parameter 'dest_ip_addr' in event IPSE.18"
    ::= { ipseEventObjects18 2 }

ipseEventObjects19 OBJECT-IDENTITY
    STATUS current
    DESCRIPTION
        "Event IPSE.19
        Error building the message."
    ::= { ipseEventsGroup 19 }

ipse19_mes_number OBJECT-TYPE
    SYNTAX Integer32
    MAX-ACCESS accessible-for-notify
    STATUS current
    DESCRIPTION
        "Parameter 'mes_number' in event IPSE.19"
    ::= { ipseEventObjects19 1 }

ipse19_phase_number OBJECT-TYPE
    SYNTAX Integer32
    MAX-ACCESS accessible-for-notify
    STATUS current
    DESCRIPTION
        "Parameter 'phase_number' in event IPSE.19"
    ::= { ipseEventObjects19 2 }

ipse19_remote_peer_addr OBJECT-TYPE
    SYNTAX IpAddress
    MAX-ACCESS accessible-for-notify
    STATUS current
    DESCRIPTION
        "Parameter 'remote_peer_addr' in event IPSE.19"
    ::= { ipseEventObjects19 3 }

ipse19_local_ifc_addr OBJECT-TYPE
    SYNTAX IpAddress
    MAX-ACCESS accessible-for-notify
    STATUS current
    DESCRIPTION
        "Parameter 'local_ifc_addr' in event IPSE.19"
    ::= { ipseEventObjects19 4 }

ipseEventObjects20 OBJECT-IDENTITY
    STATUS current
    DESCRIPTION
        "Event IPSE.20
        Error inicializating IKE protocol."
    ::= { ipseEventsGroup 20 }

ipse20_message OBJECT-TYPE
    SYNTAX DisplayString
    MAX-ACCESS accessible-for-notify
    STATUS current
    DESCRIPTION
        "Parameter 'message' in event IPSE.20"
    ::= { ipseEventObjects20 1 }

ipseEventObjects21 OBJECT-IDENTITY
    STATUS current
    DESCRIPTION
        "Event IPSE.21
        IKE is active."
    ::= { ipseEventsGroup 21 }

ipse21_ike_port OBJECT-TYPE
    SYNTAX Integer32
    MAX-ACCESS accessible-for-notify
    STATUS current
    DESCRIPTION
        "Parameter 'ike_port' in event IPSE.21"
    ::= { ipseEventObjects21 1 }

ipseEventObjects22 OBJECT-IDENTITY
    STATUS current
    DESCRIPTION
        "Event IPSE.22
        A packet is received."
    ::= { ipseEventsGroup 22 }

ipse22_remote_addr OBJECT-TYPE
    SYNTAX IpAddress
    MAX-ACCESS accessible-for-notify
    STATUS current
    DESCRIPTION
        "Parameter 'remote_addr' in event IPSE.22"
    ::= { ipseEventObjects22 1 }

ipse22_message OBJECT-TYPE
    SYNTAX DisplayString
    MAX-ACCESS accessible-for-notify
    STATUS current
    DESCRIPTION
        "Parameter 'message' in event IPSE.22"
    ::= { ipseEventObjects22 2 }

ipseEventObjects23 OBJECT-IDENTITY
    STATUS current
    DESCRIPTION
        "Event IPSE.23
        An ISAKMP SA has been created."
    ::= { ipseEventsGroup 23 }

ipse23_local_addr OBJECT-TYPE
    SYNTAX IpAddress
    MAX-ACCESS accessible-for-notify
    STATUS current
    DESCRIPTION
        "Parameter 'local_addr' in event IPSE.23"
    ::= { ipseEventObjects23 1 }

ipse23_remote_addr OBJECT-TYPE
    SYNTAX IpAddress
    MAX-ACCESS accessible-for-notify
    STATUS current
    DESCRIPTION
        "Parameter 'remote_addr' in event IPSE.23"
    ::= { ipseEventObjects23 2 }

ipseEventObjects24 OBJECT-IDENTITY
    STATUS current
    DESCRIPTION
        "Event IPSE.24
        Error (free format)."
    ::= { ipseEventsGroup 24 }

ipse24_error OBJECT-TYPE
    SYNTAX DisplayString
    MAX-ACCESS accessible-for-notify
    STATUS current
    DESCRIPTION
        "Parameter 'error' in event IPSE.24"
    ::= { ipseEventObjects24 1 }

ipseEventObjects25 OBJECT-IDENTITY
    STATUS current
    DESCRIPTION
        "Event IPSE.25
        Leaving state in IPSec forwarder."
    ::= { ipseEventsGroup 25 }

ipse25_src_ip_addr OBJECT-TYPE
    SYNTAX IpAddress
    MAX-ACCESS accessible-for-notify
    STATUS current
    DESCRIPTION
        "Parameter 'src_ip_addr' in event IPSE.25"
    ::= { ipseEventObjects25 1 }

ipse25_dest_ip_addr OBJECT-TYPE
    SYNTAX IpAddress
    MAX-ACCESS accessible-for-notify
    STATUS current
    DESCRIPTION
        "Parameter 'dest_ip_addr' in event IPSE.25"
    ::= { ipseEventObjects25 2 }

ipse25_state OBJECT-TYPE
    SYNTAX DisplayString
    MAX-ACCESS accessible-for-notify
    STATUS current
    DESCRIPTION
        "Parameter 'state' in event IPSE.25"
    ::= { ipseEventObjects25 3 }

ipseEventObjects26 OBJECT-IDENTITY
    STATUS current
    DESCRIPTION
        "Event IPSE.26
        Checking output control access list in IPSec forwarder."
    ::= { ipseEventsGroup 26 }

ipse26_src_ip_addr OBJECT-TYPE
    SYNTAX IpAddress
    MAX-ACCESS accessible-for-notify
    STATUS current
    DESCRIPTION
        "Parameter 'src_ip_addr' in event IPSE.26"
    ::= { ipseEventObjects26 1 }

ipse26_dest_ip_addr OBJECT-TYPE
    SYNTAX IpAddress
    MAX-ACCESS accessible-for-notify
    STATUS current
    DESCRIPTION
        "Parameter 'dest_ip_addr' in event IPSE.26"
    ::= { ipseEventObjects26 2 }

ipse26_protocol OBJECT-TYPE
    SYNTAX Integer32
    MAX-ACCESS accessible-for-notify
    STATUS current
    DESCRIPTION
        "Parameter 'protocol' in event IPSE.26"
    ::= { ipseEventObjects26 3 }

ipseEventObjects27 OBJECT-IDENTITY
    STATUS current
    DESCRIPTION
        "Event IPSE.27
        Checking input control access list in IPSec forwarder."
    ::= { ipseEventsGroup 27 }

ipse27_src_ip_addr OBJECT-TYPE
    SYNTAX IpAddress
    MAX-ACCESS accessible-for-notify
    STATUS current
    DESCRIPTION
        "Parameter 'src_ip_addr' in event IPSE.27"
    ::= { ipseEventObjects27 1 }

ipse27_dest_ip_addr OBJECT-TYPE
    SYNTAX IpAddress
    MAX-ACCESS accessible-for-notify
    STATUS current
    DESCRIPTION
        "Parameter 'dest_ip_addr' in event IPSE.27"
    ::= { ipseEventObjects27 2 }

ipse27_protocol OBJECT-TYPE
    SYNTAX Integer32
    MAX-ACCESS accessible-for-notify
    STATUS current
    DESCRIPTION
        "Parameter 'protocol' in event IPSE.27"
    ::= { ipseEventObjects27 3 }

ipseEventObjects28 OBJECT-IDENTITY
    STATUS current
    DESCRIPTION
        "Event IPSE.28
        Searching the SA for an ESP packet."
    ::= { ipseEventsGroup 28 }

ipse28_src_ip_addr OBJECT-TYPE
    SYNTAX IpAddress
    MAX-ACCESS accessible-for-notify
    STATUS current
    DESCRIPTION
        "Parameter 'src_ip_addr' in event IPSE.28"
    ::= { ipseEventObjects28 1 }

ipse28_dest_ip_addr OBJECT-TYPE
    SYNTAX IpAddress
    MAX-ACCESS accessible-for-notify
    STATUS current
    DESCRIPTION
        "Parameter 'dest_ip_addr' in event IPSE.28"
    ::= { ipseEventObjects28 2 }

ipseEventObjects29 OBJECT-IDENTITY
    STATUS current
    DESCRIPTION
        "Event IPSE.29
        Decapsulation Id Checking Fail."
    ::= { ipseEventsGroup 29 }

ipse29_src_ip_addr OBJECT-TYPE
    SYNTAX IpAddress
    MAX-ACCESS accessible-for-notify
    STATUS current
    DESCRIPTION
        "Parameter 'src_ip_addr' in event IPSE.29"
    ::= { ipseEventObjects29 1 }

ipse29_dest_ip_addr OBJECT-TYPE
    SYNTAX IpAddress
    MAX-ACCESS accessible-for-notify
    STATUS current
    DESCRIPTION
        "Parameter 'dest_ip_addr' in event IPSE.29"
    ::= { ipseEventObjects29 2 }

ipseEventObjects30 OBJECT-IDENTITY
    STATUS current
    DESCRIPTION
        "Event IPSE.30
        LCA checking fail: packet not protected by IPSec."
    ::= { ipseEventsGroup 30 }

ipse30_src_ip_addr OBJECT-TYPE
    SYNTAX IpAddress
    MAX-ACCESS accessible-for-notify
    STATUS current
    DESCRIPTION
        "Parameter 'src_ip_addr' in event IPSE.30"
    ::= { ipseEventObjects30 1 }

ipse30_dest_ip_addr OBJECT-TYPE
    SYNTAX IpAddress
    MAX-ACCESS accessible-for-notify
    STATUS current
    DESCRIPTION
        "Parameter 'dest_ip_addr' in event IPSE.30"
    ::= { ipseEventObjects30 2 }

ipseEventObjects31 OBJECT-IDENTITY
    STATUS current
    DESCRIPTION
        "Event IPSE.31
        It is shown the source and destination direction, ports and protocols."
    ::= { ipseEventsGroup 31 }

ipse31_protocol_type OBJECT-TYPE
    SYNTAX Integer32
    MAX-ACCESS accessible-for-notify
    STATUS current
    DESCRIPTION
        "Parameter 'protocol_type' in event IPSE.31"
    ::= { ipseEventObjects31 1 }

ipse31_src_ip_addr OBJECT-TYPE
    SYNTAX IpAddress
    MAX-ACCESS accessible-for-notify
    STATUS current
    DESCRIPTION
        "Parameter 'src_ip_addr' in event IPSE.31"
    ::= { ipseEventObjects31 2 }

ipse31_src_port OBJECT-TYPE
    SYNTAX Integer32
    MAX-ACCESS accessible-for-notify
    STATUS current
    DESCRIPTION
        "Parameter 'src_port' in event IPSE.31"
    ::= { ipseEventObjects31 3 }

ipse31_dest_ip_addr OBJECT-TYPE
    SYNTAX IpAddress
    MAX-ACCESS accessible-for-notify
    STATUS current
    DESCRIPTION
        "Parameter 'dest_ip_addr' in event IPSE.31"
    ::= { ipseEventObjects31 4 }

ipse31_dest_port OBJECT-TYPE
    SYNTAX Integer32
    MAX-ACCESS accessible-for-notify
    STATUS current
    DESCRIPTION
        "Parameter 'dest_port' in event IPSE.31"
    ::= { ipseEventObjects31 5 }

ipse31_length OBJECT-TYPE
    SYNTAX Integer32
    MAX-ACCESS accessible-for-notify
    STATUS current
    DESCRIPTION
        "Parameter 'length' in event IPSE.31"
    ::= { ipseEventObjects31 6 }

ipseEventObjects32 OBJECT-IDENTITY
    STATUS current
    DESCRIPTION
        "Event IPSE.32
        The router received an ICMP Path MTU 'too big' message (RFC 1191),
        indicating that a sent packet was too big and was unable
        to be fragmented for some reason. The 'source' IP address indicates
        the router whose next hop MTU is too small for the packet."
    ::= { ipseEventsGroup 32 }

ipse32_rmtu OBJECT-TYPE
    SYNTAX Integer32
    MAX-ACCESS accessible-for-notify
    STATUS current
    DESCRIPTION
        "Parameter 'rmtu' in event IPSE.32"
    ::= { ipseEventObjects32 1 }

ipse32_spi OBJECT-TYPE
    SYNTAX Integer32
    MAX-ACCESS accessible-for-notify
    STATUS current
    DESCRIPTION
        "Parameter 'spi' in event IPSE.32"
    ::= { ipseEventObjects32 2 }

ipse32_src_ip_addr OBJECT-TYPE
    SYNTAX IpAddress
    MAX-ACCESS accessible-for-notify
    STATUS current
    DESCRIPTION
        "Parameter 'src_ip_addr' in event IPSE.32"
    ::= { ipseEventObjects32 3 }

ipse32_dest_ip_addr OBJECT-TYPE
    SYNTAX IpAddress
    MAX-ACCESS accessible-for-notify
    STATUS current
    DESCRIPTION
        "Parameter 'dest_ip_addr' in event IPSE.32"
    ::= { ipseEventObjects32 4 }

ipseEventObjects33 OBJECT-IDENTITY
    STATUS current
    DESCRIPTION
        "Event IPSE.33
        The router is trying to send an IPSec packet which exceeds
        the stored PMTU value for the associated bundle. Packet is dropped,
        and an ICMP PMTU packet is sent back to the source IP address."
    ::= { ipseEventsGroup 33 }

ipse33_mtu OBJECT-TYPE
    SYNTAX Integer32
    MAX-ACCESS accessible-for-notify
    STATUS current
    DESCRIPTION
        "Parameter 'mtu' in event IPSE.33"
    ::= { ipseEventObjects33 1 }

ipse33_spi OBJECT-TYPE
    SYNTAX Integer32
    MAX-ACCESS accessible-for-notify
    STATUS current
    DESCRIPTION
        "Parameter 'spi' in event IPSE.33"
    ::= { ipseEventObjects33 2 }

ipse33_src_ip_addr OBJECT-TYPE
    SYNTAX IpAddress
    MAX-ACCESS accessible-for-notify
    STATUS current
    DESCRIPTION
        "Parameter 'src_ip_addr' in event IPSE.33"
    ::= { ipseEventObjects33 3 }

ipse33_dest_ip_addr OBJECT-TYPE
    SYNTAX IpAddress
    MAX-ACCESS accessible-for-notify
    STATUS current
    DESCRIPTION
        "Parameter 'dest_ip_addr' in event IPSE.33"
    ::= { ipseEventObjects33 4 }

ipseEventObjects34 OBJECT-IDENTITY
    STATUS current
    DESCRIPTION
        "Event IPSE.34
        timestamp error"
    ::= { ipseEventsGroup 34 }

ipse34_rcvd_time OBJECT-TYPE
    SYNTAX Integer32
    MAX-ACCESS accessible-for-notify
    STATUS current
    DESCRIPTION
        "Parameter 'rcvd_time' in event IPSE.34"
    ::= { ipseEventObjects34 1 }

ipse34_expected_time OBJECT-TYPE
    SYNTAX Integer32
    MAX-ACCESS accessible-for-notify
    STATUS current
    DESCRIPTION
        "Parameter 'expected_time' in event IPSE.34"
    ::= { ipseEventObjects34 2 }

ipse34_windows OBJECT-TYPE
    SYNTAX Integer32
    MAX-ACCESS accessible-for-notify
    STATUS current
    DESCRIPTION
        "Parameter 'windows' in event IPSE.34"
    ::= { ipseEventObjects34 3 }

ipseEventObjects35 OBJECT-IDENTITY
    STATUS current
    DESCRIPTION
        "Event IPSE.35
        Usual operation trace (free format)."
    ::= { ipseEventsGroup 35 }

ipse35_trace OBJECT-TYPE
    SYNTAX DisplayString
    MAX-ACCESS accessible-for-notify
    STATUS current
    DESCRIPTION
        "Parameter 'trace' in event IPSE.35"
    ::= { ipseEventObjects35 1 }


ipseNotification1 NOTIFICATION-TYPE
    OBJECTS { 
              ipse1_packet_type, 
              ipse1_SPI 
            }
    STATUS current
    DESCRIPTION
        "Notification of Event IPSE.1

        Message: '$1, spi $2'

        Parameters list:
              $1: ipse1_packet_type
              $2: ipse1_SPI

        It is shown the protocol of the encapsulated packet and the SPI."
    ::= { ipseNotificationsPrefix 1 }

ipseNotification2 NOTIFICATION-TYPE
    OBJECTS { 
              ipse2_protocol_type 
            }
    STATUS current
    DESCRIPTION
        "Notification of Event IPSE.2

        Message: 'Error while unencapsulating packet $1, unknown'

        Parameters list:
              $1: ipse2_protocol_type

        The received encapsulated packet has an unknown protocol."
    ::= { ipseNotificationsPrefix 2 }

ipseNotification3 NOTIFICATION-TYPE
    OBJECTS { 
              ipse3_protocol_type, 
              ipse3_src_ip_addr,
              ipse3_dest_ip_addr,
              ipse3_SPI 
            }
    STATUS current
    DESCRIPTION
        "Notification of Event IPSE.3

        Message: 'Packet $1 successfully encapsulated (source $2 -> destination $3) spi $4'

        Parameters list:
              $1: ipse3_protocol_type
              $2: ipse3_src_ip_addr
              $3: ipse3_dest_ip_addr
              $4: ipse3_SPI

        The output function of the tunnel net has encapsulated a ESP or
        AH packet successfully. It is shown the protocol of the encapsulated
        packet, the source and destination direction and the SPI."
    ::= { ipseNotificationsPrefix 3 }

ipseNotification4 NOTIFICATION-TYPE
    OBJECTS { 
              ipse4_protocol_type, 
              ipse4_sa_number 
            }
    STATUS current
    DESCRIPTION
        "Notification of Event IPSE.4

        Message: 'Error in packet authentication $1 ,spi $2'

        Parameters list:
              $1: ipse4_protocol_type
              $2: ipse4_sa_number

        The authentication of an ESP or AH packet failed."
    ::= { ipseNotificationsPrefix 4 }

ipseNotification5 NOTIFICATION-TYPE
    OBJECTS { 
              ipse5_protocol_name, 
              ipse5_src_ip_addr,
              ipse5_dest_ip_addr 
            }
    STATUS current
    DESCRIPTION
        "Notification of Event IPSE.5

        Message: 'Packet discarded $1 received with delay, (source $2 -> destination $3)'

        Parameters list:
              $1: ipse5_protocol_name
              $2: ipse5_src_ip_addr
              $3: ipse5_dest_ip_addr

        A packet was discarded because its secuence number was below
        the minimum admited in the reception window."
    ::= { ipseNotificationsPrefix 5 }

ipseNotification6 NOTIFICATION-TYPE
    OBJECTS { 
              ipse6_protocol_name, 
              ipse6_src_ip_addr,
              ipse6_dest_ip_addr 
            }
    STATUS current
    DESCRIPTION
        "Notification of Event IPSE.6

        Message: 'Packet discarded $1 because repeated, (source $2 -> destination $3)'

        Parameters list:
              $1: ipse6_protocol_name
              $2: ipse6_src_ip_addr
              $3: ipse6_dest_ip_addr

        A packet was discarded because the antireplay options were active
        and it was already received."
    ::= { ipseNotificationsPrefix 6 }

ipseNotification7 NOTIFICATION-TYPE
    STATUS current
    DESCRIPTION
        "Notification of Event IPSE.7

        Message: 'Packet discarded because used a wrong padding'

        A packet was discarded because the padding had a wrong value."
    ::= { ipseNotificationsPrefix 7 }

ipseNotification8 NOTIFICATION-TYPE
    OBJECTS { 
              ipse8_protocol_type, 
              ipse8_src_ip_addr,
              ipse8_dest_ip_addr 
            }
    STATUS current
    DESCRIPTION
        "Notification of Event IPSE.8

        Message: 'Packet discarded because has a wrong length $1, not multiple of 32 bits (source $2-> destination $3)'

        Parameters list:
              $1: ipse8_protocol_type
              $2: ipse8_src_ip_addr
              $3: ipse8_dest_ip_addr

        A packet is discarded because it has a wrong length (it is not multiple
        of 32 bits)."
    ::= { ipseNotificationsPrefix 8 }

ipseNotification9 NOTIFICATION-TYPE
    OBJECTS { 
              ipse9_protocol_type, 
              ipse9_src_ip_addr,
              ipse9_dest_ip_addr 
            }
    STATUS current
    DESCRIPTION
        "Notification of Event IPSE.9

        Message: 'Packet with correct sequence number, protocol $1, (source $2 -> destination $3)'

        Parameters list:
              $1: ipse9_protocol_type
              $2: ipse9_src_ip_addr
              $3: ipse9_dest_ip_addr

        Packet with correct sequence number in window."
    ::= { ipseNotificationsPrefix 9 }

ipseNotification10 NOTIFICATION-TYPE
    OBJECTS { 
              ipse10_protocol_type, 
              ipse10_src_ip_addr,
              ipse10_dest_ip_addr 
            }
    STATUS current
    DESCRIPTION
        "Notification of Event IPSE.10

        Message: 'Packet discarded in window secuence because as 0 secuence number in protocol $1, source $2, destination $3'

        Parameters list:
              $1: ipse10_protocol_type
              $2: ipse10_src_ip_addr
              $3: ipse10_dest_ip_addr

        The packet has arrived to window secuence with 0 as secuence number."
    ::= { ipseNotificationsPrefix 10 }

ipseNotification11 NOTIFICATION-TYPE
    OBJECTS { 
              ipse11_protocol_type, 
              ipse11_spi,
              ipse11_sa_seq_num,
              ipse11_inbound_seq_num 
            }
    STATUS current
    DESCRIPTION
        "Notification of Event IPSE.11

        Message: 'Prot $1 spi $2 seq num SA $3, seq num pack $4'

        Parameters list:
              $1: ipse11_protocol_type
              $2: ipse11_spi
              $3: ipse11_sa_seq_num
              $4: ipse11_inbound_seq_num

        The protocol, the SA sequence number and the packet sequence number
        are shown."
    ::= { ipseNotificationsPrefix 11 }

ipseNotification12 NOTIFICATION-TYPE
    OBJECTS { 
              ipse12_spi, 
              ipse12_protocol,
              ipse12_remote_peer 
            }
    STATUS current
    DESCRIPTION
        "Notification of Event IPSE.12

        Message: 'SA not found, spi $1 protocol $2 remote peer $3'

        Parameters list:
              $1: ipse12_spi
              $2: ipse12_protocol
              $3: ipse12_remote_peer

        A packet has arrived with the SPI showed and there is not an
        static SA configured for it."
    ::= { ipseNotificationsPrefix 12 }

ipseNotification13 NOTIFICATION-TYPE
    OBJECTS { 
              ipse13_protocol_type 
            }
    STATUS current
    DESCRIPTION
        "Notification of Event IPSE.13

        Message: 'Warning! Overflow of seq num, prot $1'

        Parameters list:
              $1: ipse13_protocol_type

        Overflow in sequence number the next sequence number is 1."
    ::= { ipseNotificationsPrefix 13 }

ipseNotification14 NOTIFICATION-TYPE
    OBJECTS { 
              ipse14_spi, 
              ipse14_protocol,
              ipse14_remote_peer 
            }
    STATUS current
    DESCRIPTION
        "Notification of Event IPSE.14

        Message: 'SA is down, spi $1 protocol $2 remote peer $3'

        Parameters list:
              $1: ipse14_spi
              $2: ipse14_protocol
              $3: ipse14_remote_peer

        A packet has arrived with SPI %x and there is not an
        static SA configured for it."
    ::= { ipseNotificationsPrefix 14 }

ipseNotification15 NOTIFICATION-TYPE
    OBJECTS { 
              ipse15_src_ip_addr, 
              ipse15_dest_ip_addr 
            }
    STATUS current
    DESCRIPTION
        "Notification of Event IPSE.15

        Message: 'Policy not found for packet ($1->$2)'

        Parameters list:
              $1: ipse15_src_ip_addr
              $2: ipse15_dest_ip_addr

        Found entry hasn't policy assigned. (Debug)."
    ::= { ipseNotificationsPrefix 15 }

ipseNotification16 NOTIFICATION-TYPE
    OBJECTS { 
              ipse16_message, 
              ipse16_phase,
              ipse16_src_ip_addr,
              ipse16_dest_ip_addr 
            }
    STATUS current
    DESCRIPTION
        "Notification of Event IPSE.16

        Message: 'ISAKMP - Message $1 fase $2 INVALID ATTRIBUTES.  pack ($3->$4)'

        Parameters list:
              $1: ipse16_message
              $2: ipse16_phase
              $3: ipse16_src_ip_addr
              $4: ipse16_dest_ip_addr

        Attributes are wrong."
    ::= { ipseNotificationsPrefix 16 }

ipseNotification17 NOTIFICATION-TYPE
    OBJECTS { 
              ipse17_message 
            }
    STATUS current
    DESCRIPTION
        "Notification of Event IPSE.17

        Message: 'IKE - Allocating memory error. $1'

        Parameters list:
              $1: ipse17_message

        Error allocating memory."
    ::= { ipseNotificationsPrefix 17 }

ipseNotification18 NOTIFICATION-TYPE
    OBJECTS { 
              ipse18_src_ip_addr, 
              ipse18_dest_ip_addr 
            }
    STATUS current
    DESCRIPTION
        "Notification of Event IPSE.18

        Message: 'ISAKMP-SA proposal incompatible.  remote peer:$1 Local interface:$2'

        Parameters list:
              $1: ipse18_src_ip_addr
              $2: ipse18_dest_ip_addr

        Incompatible IKE policies."
    ::= { ipseNotificationsPrefix 18 }

ipseNotification19 NOTIFICATION-TYPE
    OBJECTS { 
              ipse19_mes_number, 
              ipse19_phase_number,
              ipse19_remote_peer_addr,
              ipse19_local_ifc_addr 
            }
    STATUS current
    DESCRIPTION
        "Notification of Event IPSE.19

        Message: 'IKE -Error building the $1 message in fase $2. remote peer:$3 Local interface:$4'

        Parameters list:
              $1: ipse19_mes_number
              $2: ipse19_phase_number
              $3: ipse19_remote_peer_addr
              $4: ipse19_local_ifc_addr

        Error building the message."
    ::= { ipseNotificationsPrefix 19 }

ipseNotification20 NOTIFICATION-TYPE
    OBJECTS { 
              ipse20_message 
            }
    STATUS current
    DESCRIPTION
        "Notification of Event IPSE.20

        Message: 'Error inicializating IKE protocol. $1'

        Parameters list:
              $1: ipse20_message

        Error inicializating IKE protocol."
    ::= { ipseNotificationsPrefix 20 }

ipseNotification21 NOTIFICATION-TYPE
    OBJECTS { 
              ipse21_ike_port 
            }
    STATUS current
    DESCRIPTION
        "Notification of Event IPSE.21

        Message: 'IKE protocol server active in port: $1'

        Parameters list:
              $1: ipse21_ike_port

        IKE is active."
    ::= { ipseNotificationsPrefix 21 }

ipseNotification22 NOTIFICATION-TYPE
    OBJECTS { 
              ipse22_remote_addr, 
              ipse22_message 
            }
    STATUS current
    DESCRIPTION
        "Notification of Event IPSE.22

        Message: 'IKE($1)$2'

        Parameters list:
              $1: ipse22_remote_addr
              $2: ipse22_message

        A packet is received."
    ::= { ipseNotificationsPrefix 22 }

ipseNotification23 NOTIFICATION-TYPE
    OBJECTS { 
              ipse23_local_addr, 
              ipse23_remote_addr 
            }
    STATUS current
    DESCRIPTION
        "Notification of Event IPSE.23

        Message: 'IKE - ISAKMP SA has been created ($1 <-> $2)'

        Parameters list:
              $1: ipse23_local_addr
              $2: ipse23_remote_addr

        An ISAKMP SA has been created."
    ::= { ipseNotificationsPrefix 23 }

ipseNotification24 NOTIFICATION-TYPE
    OBJECTS { 
              ipse24_error 
            }
    STATUS current
    DESCRIPTION
        "Notification of Event IPSE.24

        Message: 'ISAKMP Error - $1'

        Parameters list:
              $1: ipse24_error

        Error (free format)."
    ::= { ipseNotificationsPrefix 24 }

ipseNotification25 NOTIFICATION-TYPE
    OBJECTS { 
              ipse25_src_ip_addr, 
              ipse25_dest_ip_addr,
              ipse25_state 
            }
    STATUS current
    DESCRIPTION
        "Notification of Event IPSE.25

        Message: 'Packet ($1 -> $2) entered in IpSec Forwarder State $3.'

        Parameters list:
              $1: ipse25_src_ip_addr
              $2: ipse25_dest_ip_addr
              $3: ipse25_state

        Leaving state in IPSec forwarder."
    ::= { ipseNotificationsPrefix 25 }

ipseNotification26 NOTIFICATION-TYPE
    OBJECTS { 
              ipse26_src_ip_addr, 
              ipse26_dest_ip_addr,
              ipse26_protocol 
            }
    STATUS current
    DESCRIPTION
        "Notification of Event IPSE.26

        Message: 'Out.ACL($1->$2) ProtNum $3.'

        Parameters list:
              $1: ipse26_src_ip_addr
              $2: ipse26_dest_ip_addr
              $3: ipse26_protocol

        Checking output control access list in IPSec forwarder."
    ::= { ipseNotificationsPrefix 26 }

ipseNotification27 NOTIFICATION-TYPE
    OBJECTS { 
              ipse27_src_ip_addr, 
              ipse27_dest_ip_addr,
              ipse27_protocol 
            }
    STATUS current
    DESCRIPTION
        "Notification of Event IPSE.27

        Message: 'In.ACL($1->$2) ProtNum $3.'

        Parameters list:
              $1: ipse27_src_ip_addr
              $2: ipse27_dest_ip_addr
              $3: ipse27_protocol

        Checking input control access list in IPSec forwarder."
    ::= { ipseNotificationsPrefix 27 }

ipseNotification28 NOTIFICATION-TYPE
    OBJECTS { 
              ipse28_src_ip_addr, 
              ipse28_dest_ip_addr 
            }
    STATUS current
    DESCRIPTION
        "Notification of Event IPSE.28

        Message: 'Searching SA for an ESP/AH Packet directed to a Local Ifc. Packet ($1->$2).'

        Parameters list:
              $1: ipse28_src_ip_addr
              $2: ipse28_dest_ip_addr

        Searching the SA for an ESP packet."
    ::= { ipseNotificationsPrefix 28 }

ipseNotification29 NOTIFICATION-TYPE
    OBJECTS { 
              ipse29_src_ip_addr, 
              ipse29_dest_ip_addr 
            }
    STATUS current
    DESCRIPTION
        "Notification of Event IPSE.29

        Message: 'Packet ($1 -> $2) decapsulation Id checking Failure.'

        Parameters list:
              $1: ipse29_src_ip_addr
              $2: ipse29_dest_ip_addr

        Decapsulation Id Checking Fail."
    ::= { ipseNotificationsPrefix 29 }

ipseNotification30 NOTIFICATION-TYPE
    OBJECTS { 
              ipse30_src_ip_addr, 
              ipse30_dest_ip_addr 
            }
    STATUS current
    DESCRIPTION
        "Notification of Event IPSE.30

        Message: 'No Ipsec protected : packet ($1 -> $2) drop.'

        Parameters list:
              $1: ipse30_src_ip_addr
              $2: ipse30_dest_ip_addr

        LCA checking fail: packet not protected by IPSec."
    ::= { ipseNotificationsPrefix 30 }

ipseNotification31 NOTIFICATION-TYPE
    OBJECTS { 
              ipse31_protocol_type, 
              ipse31_src_ip_addr,
              ipse31_src_port,
              ipse31_dest_ip_addr,
              ipse31_dest_port,
              ipse31_length 
            }
    STATUS current
    DESCRIPTION
        "Notification of Event IPSE.31

        Message: 'protocol $1 (source $2 port $3-> destination $4 prot $5) length $6'

        Parameters list:
              $1: ipse31_protocol_type
              $2: ipse31_src_ip_addr
              $3: ipse31_src_port
              $4: ipse31_dest_ip_addr
              $5: ipse31_dest_port
              $6: ipse31_length

        It is shown the source and destination direction, ports and protocols."
    ::= { ipseNotificationsPrefix 31 }

ipseNotification32 NOTIFICATION-TYPE
    OBJECTS { 
              ipse32_rmtu, 
              ipse32_spi,
              ipse32_src_ip_addr,
              ipse32_dest_ip_addr 
            }
    STATUS current
    DESCRIPTION
        "Notification of Event IPSE.32

        Message: 'Rcvd ICMP PMTU: Next-hop mtu = $1 bytes. SPI $2, pkt $3 -> $4'

        Parameters list:
              $1: ipse32_rmtu
              $2: ipse32_spi
              $3: ipse32_src_ip_addr
              $4: ipse32_dest_ip_addr

        The router received an ICMP Path MTU 'too big' message (RFC 1191),
        indicating that a sent packet was too big and was unable
        to be fragmented for some reason. The 'source' IP address indicates
        the router whose next hop MTU is too small for the packet."
    ::= { ipseNotificationsPrefix 32 }

ipseNotification33 NOTIFICATION-TYPE
    OBJECTS { 
              ipse33_mtu, 
              ipse33_spi,
              ipse33_src_ip_addr,
              ipse33_dest_ip_addr 
            }
    STATUS current
    DESCRIPTION
        "Notification of Event IPSE.33

        Message: 'Sent ICMP PMTU: Path mtu = $1 bytes. SPI $2, pkt $3 -> $4'

        Parameters list:
              $1: ipse33_mtu
              $2: ipse33_spi
              $3: ipse33_src_ip_addr
              $4: ipse33_dest_ip_addr

        The router is trying to send an IPSec packet which exceeds
        the stored PMTU value for the associated bundle. Packet is dropped,
        and an ICMP PMTU packet is sent back to the source IP address."
    ::= { ipseNotificationsPrefix 33 }

ipseNotification34 NOTIFICATION-TYPE
    OBJECTS { 
              ipse34_rcvd_time, 
              ipse34_expected_time,
              ipse34_windows 
            }
    STATUS current
    DESCRIPTION
        "Notification of Event IPSE.34

        Message: 'GDOI timestamp error rcvd time $1 expected $2 window $3'

        Parameters list:
              $1: ipse34_rcvd_time
              $2: ipse34_expected_time
              $3: ipse34_windows

        timestamp error"
    ::= { ipseNotificationsPrefix 34 }

ipseNotification35 NOTIFICATION-TYPE
    OBJECTS { 
              ipse35_trace 
            }
    STATUS current
    DESCRIPTION
        "Notification of Event IPSE.35

        Message: 'Access list cache - $1'

        Parameters list:
              $1: ipse35_trace

        Usual operation trace (free format)."
    ::= { ipseNotificationsPrefix 35 }


END
