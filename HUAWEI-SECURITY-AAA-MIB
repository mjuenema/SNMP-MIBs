-- =============================================================================
-- Copyright (C) 2010 by HUAWEI TECHNOLOGIES. All rights reserved.
--    
-- Description:  
-- Reference: Huawei Enterprise MIB
-- Version: 1.0
-- History: 
--          V1.0 The initial version created by Liuruirui 90002678. 
-- =============================================================================

HUAWEI-SECURITY-AAA-MIB DEFINITIONS ::= BEGIN
 
	IMPORTS   
    		enterprises			
		    FROM RFC1155-SMI 
            DateAndTime			
			FROM SNMPv2-TC;


    hwAAA MODULE-IDENTITY 
		        LAST-UPDATED "201104211900Z"        -- April 21, 2011 at 19:00 GMT
		        ORGANIZATION 
		            "Huawei Symantec Technologies Co., Ltd."
		        CONTACT-INFO 
		            "3rd Floor,Section D, Keshi Building, No.28, Xinxi Rd., Shangdi,
		         	 Hai-Dian District Beijing P.R. China
			         Zip:100085
			         Http://www.huaweisymantec.com
                     "
		        DESCRIPTION 
		            "V1.00
			         The AAA mib is for Eudemon and USG product series."

		        ::= { hwSecurity 46 } 
           
		
-- ===============================================
-- Node definitions
-- ===============================================
	    
	    -- 1.3.6.1.4.1.2011
		huawei OBJECT IDENTIFIER ::= { enterprises 2011 }
	        
		-- 1.3.6.1.4.1.2011.6
		huaweiUtility OBJECT IDENTIFIER ::= { huawei 6 }
	        
		-- 1.3.6.1.4.1.2011.6.122
		hwSecurity OBJECT IDENTIFIER ::= { huaweiUtility 122 }     
		       
		  
		hwAAANotification OBJECT IDENTIFIER ::= { hwAAA 0 }  
		hwAAATrapObject OBJECT IDENTIFIER ::= { hwAAANotification 1 }   
		hwAAATraps OBJECT IDENTIFIER ::= { hwAAANotification 2 }


-- ===============================================
-- TrapObject.
-- ===============================================
 	        	        		
 		    hwAAADomainName  OBJECT-TYPE
	        	SYNTAX OCTET STRING (SIZE (1..64)) 
	        	MAX-ACCESS accessible-for-notify
	        	STATUS current
	        	DESCRIPTION
	            		"the Domain name."
	        	::= { hwAAATrapObject 1 }     
	        	        
  		        		        
-- ===============================================
-- definition of traps.      
-- ===============================================                        
	        hwAAAIPNearlyExhaust NOTIFICATION-TYPE
			OBJECTS { 
				hwAAADomainName
			        }
			STATUS     current
			DESCRIPTION
			    "Send the message when ip address is nearly exhaust."
			::= { hwAAATraps 1}           
			
			hwAAAIPExhaust NOTIFICATION-TYPE
			OBJECTS { 
				hwAAADomainName  
			        }
			STATUS     current
			DESCRIPTION
			    "Send the message when Send the message when ip address is exhaust."
			::= { hwAAATraps 2} 
	                   			
	END
