-- file automatically created


TELDAT-TRAP-GW-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


gwTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the GW event subsystem."
    REVISION "201401200930Z"
    DESCRIPTION "Initial implementation"
        ::= { telEventTraps 1 }


gwEventsGroup	OBJECT IDENTIFIER	::= { gwTrapsMIB 1 }

gwNotifications	OBJECT IDENTIFIER	::= { gwTrapsMIB 2 }
gwNotificationsPrefix	OBJECT IDENTIFIER	::= { gwNotifications 0 }

gwEventObjects1 OBJECT-IDENTITY
    STATUS current
    DESCRIPTION
        "Event GW.1
        Router cold start."
    ::= { gwEventsGroup 1 }

gw1_router_name OBJECT-TYPE
    SYNTAX DisplayString
    MAX-ACCESS accessible-for-notify
    STATUS current
    DESCRIPTION
        "Parameter 'router name' in event GW.1"
    ::= { gwEventObjects1 1 }

gwEventObjects2 OBJECT-IDENTITY
    STATUS current
    DESCRIPTION
        "Event GW.2
        Prints the name of the router (as indicated in the router), and
        the release level of the software load which has just started
        in the router."
    ::= { gwEventsGroup 2 }

gw2_router_name OBJECT-TYPE
    SYNTAX DisplayString
    MAX-ACCESS accessible-for-notify
    STATUS current
    DESCRIPTION
        "Parameter 'router name' in event GW.2"
    ::= { gwEventObjects2 1 }

gw2_release_level OBJECT-TYPE
    SYNTAX DisplayString
    MAX-ACCESS accessible-for-notify
    STATUS current
    DESCRIPTION
        "Parameter 'release level' in event GW.2"
    ::= { gwEventObjects2 2 }

gwEventObjects3 OBJECT-IDENTITY
    STATUS current
    DESCRIPTION
        "Event GW.3
        The router will not be able to send or receive the last [unused length]
        bytes of maximum size packets."
    ::= { gwEventsGroup 3 }

gw3_unused_length OBJECT-TYPE
    SYNTAX Integer32
    MAX-ACCESS accessible-for-notify
    STATUS current
    DESCRIPTION
        "Parameter 'unused_length' in event GW.3"
    ::= { gwEventObjects3 1 }

gw3_interface OBJECT-TYPE
    SYNTAX DisplayString
    MAX-ACCESS accessible-for-notify
    STATUS current
    DESCRIPTION
        "Parameter 'interface' in event GW.3"
    ::= { gwEventObjects3 2 }

gwEventObjects4 OBJECT-IDENTITY
    STATUS current
    DESCRIPTION
        "Event GW.4
        The system has detected that there are probably an insufficent number
        of buffers for optimal operation.
        On startup, the maximum number of buffers allocated to either
        the permanent device input queue or the transient device output queue
        had exceeded an advisable allocation of the entire buffer pool."
    ::= { gwEventsGroup 4 }

gw4_queue_type OBJECT-TYPE
    SYNTAX DisplayString
    MAX-ACCESS accessible-for-notify
    STATUS current
    DESCRIPTION
        "Parameter 'queue type' in event GW.4"
    ::= { gwEventObjects4 1 }

gw4_advisable_queue_length OBJECT-TYPE
    SYNTAX Integer32
    MAX-ACCESS accessible-for-notify
    STATUS current
    DESCRIPTION
        "Parameter 'advisable queue length' in event GW.4"
    ::= { gwEventObjects4 2 }

gw4_actual_queue_length OBJECT-TYPE
    SYNTAX Integer32
    MAX-ACCESS accessible-for-notify
    STATUS current
    DESCRIPTION
        "Parameter 'actual queue length' in event GW.4"
    ::= { gwEventObjects4 3 }

gwEventObjects5 OBJECT-IDENTITY
    STATUS current
    DESCRIPTION
        "Event GW.5
        The message gives information about the number of buffers created by
        the initialization procedure, as well as some information on parameters
        used by the buffer allocation system. As long as the number of buffers
        currently free in the router is above the low water mark, any user can
        allocate buffers. Below that point, any user can allocate buffers,
        as long as the number is less than the 'fair share'."
    ::= { gwEventsGroup 5 }

gw5_total_created OBJECT-TYPE
    SYNTAX Integer32
    MAX-ACCESS accessible-for-notify
    STATUS current
    DESCRIPTION
        "Parameter 'total created' in event GW.5"
    ::= { gwEventObjects5 1 }

gw5_initially_free OBJECT-TYPE
    SYNTAX Integer32
    MAX-ACCESS accessible-for-notify
    STATUS current
    DESCRIPTION
        "Parameter 'initially free' in event GW.5"
    ::= { gwEventObjects5 2 }

gw5_fair_share_amount OBJECT-TYPE
    SYNTAX Integer32
    MAX-ACCESS accessible-for-notify
    STATUS current
    DESCRIPTION
        "Parameter 'fair share amount' in event GW.5"
    ::= { gwEventObjects5 3 }

gw5_high_water_mark OBJECT-TYPE
    SYNTAX Integer32
    MAX-ACCESS accessible-for-notify
    STATUS current
    DESCRIPTION
        "Parameter 'high water mark' in event GW.5"
    ::= { gwEventObjects5 4 }

gwEventObjects6 OBJECT-IDENTITY
    STATUS current
    DESCRIPTION
        "Event GW.6
        An incoming packet was in a protocol which, although recognized, did not
        have a handler loaded and enabled."
    ::= { gwEventsGroup 6 }

gw6_interface OBJECT-TYPE
    SYNTAX DisplayString
    MAX-ACCESS accessible-for-notify
    STATUS current
    DESCRIPTION
        "Parameter 'interface' in event GW.6"
    ::= { gwEventObjects6 1 }

gwEventObjects7 OBJECT-IDENTITY
    STATUS current
    DESCRIPTION
        "Event GW.7
        A device input operation returned an error, along with a
        device specific error code. The input error counter for that network
        was incrememented, and any packet associated with that error
        was probably discarded."
    ::= { gwEventsGroup 7 }

gw7_error_code OBJECT-TYPE
    SYNTAX Integer32
    MAX-ACCESS accessible-for-notify
    STATUS current
    DESCRIPTION
        "Parameter 'error_code' in event GW.7"
    ::= { gwEventObjects7 1 }

gw7_interface OBJECT-TYPE
    SYNTAX DisplayString
    MAX-ACCESS accessible-for-notify
    STATUS current
    DESCRIPTION
        "Parameter 'interface' in event GW.7"
    ::= { gwEventObjects7 2 }

gwEventObjects9 OBJECT-IDENTITY
    STATUS current
    DESCRIPTION
        "Event GW.9
        When the router attempted to queue additional input operations for
        the interface, the interface had been disabled for input."
    ::= { gwEventsGroup 9 }

gw9_interface OBJECT-TYPE
    SYNTAX DisplayString
    MAX-ACCESS accessible-for-notify
    STATUS current
    DESCRIPTION
        "Parameter 'interface' in event GW.9"
    ::= { gwEventObjects9 1 }

gwEventObjects10 OBJECT-IDENTITY
    STATUS current
    DESCRIPTION
        "Event GW.10
        When the router attempted to queue additional input operations for
        the interface, not enough free buffers were available to refill the
        input queue to the level desired; the actual level attained is listed."
    ::= { gwEventsGroup 10 }

gw10_queue_length OBJECT-TYPE
    SYNTAX Integer32
    MAX-ACCESS accessible-for-notify
    STATUS current
    DESCRIPTION
        "Parameter 'queue_length' in event GW.10"
    ::= { gwEventObjects10 1 }

gw10_interface OBJECT-TYPE
    SYNTAX DisplayString
    MAX-ACCESS accessible-for-notify
    STATUS current
    DESCRIPTION
        "Parameter 'interface' in event GW.10"
    ::= { gwEventObjects10 2 }

gwEventObjects11 OBJECT-IDENTITY
    STATUS current
    DESCRIPTION
        "Event GW.11
        Remote terminal owns console."
    ::= { gwEventsGroup 11 }

gw11_ip_address OBJECT-TYPE
    SYNTAX IpAddress
    MAX-ACCESS accessible-for-notify
    STATUS current
    DESCRIPTION
        "Parameter 'ip_address' in event GW.11"
    ::= { gwEventObjects11 1 }

gwEventObjects14 OBJECT-IDENTITY
    STATUS current
    DESCRIPTION
        "Event GW.14
        When the router attempted to queue additional output operations
        for the interface, the interface had been disabled for output."
    ::= { gwEventsGroup 14 }

gw14_interface OBJECT-TYPE
    SYNTAX DisplayString
    MAX-ACCESS accessible-for-notify
    STATUS current
    DESCRIPTION
        "Parameter 'interface' in event GW.14"
    ::= { gwEventObjects14 1 }

gwEventObjects15 OBJECT-IDENTITY
    STATUS current
    DESCRIPTION
        "Event GW.15
        The specified protocol changed to specified state
        on specified interface."
    ::= { gwEventsGroup 15 }

gw15_state OBJECT-TYPE
    SYNTAX DisplayString
    MAX-ACCESS accessible-for-notify
    STATUS current
    DESCRIPTION
        "Parameter 'state' in event GW.15"
    ::= { gwEventObjects15 1 }

gw15_interface OBJECT-TYPE
    SYNTAX DisplayString
    MAX-ACCESS accessible-for-notify
    STATUS current
    DESCRIPTION
        "Parameter 'interface' in event GW.15"
    ::= { gwEventObjects15 2 }

gw15_protocol_number OBJECT-TYPE
    SYNTAX Integer32
    MAX-ACCESS accessible-for-notify
    STATUS current
    DESCRIPTION
        "Parameter 'protocol_number' in event GW.15"
    ::= { gwEventObjects15 3 }

gw15_protocol_name OBJECT-TYPE
    SYNTAX DisplayString
    MAX-ACCESS accessible-for-notify
    STATUS current
    DESCRIPTION
        "Parameter 'protocol_name' in event GW.15"
    ::= { gwEventObjects15 4 }

gwEventObjects17 OBJECT-IDENTITY
    STATUS current
    DESCRIPTION
        "Event GW.17
        When the router software went to initialize the network interface for
        the first time, the board did not respond on the bus. The board
        is marked 'not present' and ignored from then on."
    ::= { gwEventsGroup 17 }

gw17_interface OBJECT-TYPE
    SYNTAX DisplayString
    MAX-ACCESS accessible-for-notify
    STATUS current
    DESCRIPTION
        "Parameter 'interface' in event GW.17"
    ::= { gwEventObjects17 1 }

gwEventObjects18 OBJECT-IDENTITY
    STATUS current
    DESCRIPTION
        "Event GW.18
        A network self-test (see Software Operator's Manual for more information
        on self-test) has been requested."
    ::= { gwEventsGroup 18 }

gw18_interface OBJECT-TYPE
    SYNTAX DisplayString
    MAX-ACCESS accessible-for-notify
    STATUS current
    DESCRIPTION
        "Parameter 'interface' in event GW.18"
    ::= { gwEventObjects18 1 }

gwEventObjects19 OBJECT-IDENTITY
    STATUS current
    DESCRIPTION
        "Event GW.19
        A network self-test (see Software Operator's Manual for more information
        on self-test) has been started."
    ::= { gwEventsGroup 19 }

gw19_interface OBJECT-TYPE
    SYNTAX DisplayString
    MAX-ACCESS accessible-for-notify
    STATUS current
    DESCRIPTION
        "Parameter 'interface' in event GW.19"
    ::= { gwEventObjects19 1 }

gwEventObjects20 OBJECT-IDENTITY
    STATUS current
    DESCRIPTION
        "Event GW.20
        A network undergoing self-test (see Software Operator's Manual for more
        information on self-test) has passed the self-test."
    ::= { gwEventsGroup 20 }

gw20_interface OBJECT-TYPE
    SYNTAX DisplayString
    MAX-ACCESS accessible-for-notify
    STATUS current
    DESCRIPTION
        "Parameter 'interface' in event GW.20"
    ::= { gwEventObjects20 1 }

gwEventObjects21 OBJECT-IDENTITY
    STATUS current
    DESCRIPTION
        "Event GW.21
        After passing self-test (see Software Operator's Manual for more
        information on self-test), a network that was previously down
        has come up."
    ::= { gwEventsGroup 21 }

gw21_interface OBJECT-TYPE
    SYNTAX DisplayString
    MAX-ACCESS accessible-for-notify
    STATUS current
    DESCRIPTION
        "Parameter 'interface' in event GW.21"
    ::= { gwEventObjects21 1 }

gwEventObjects22 OBJECT-IDENTITY
    STATUS current
    DESCRIPTION
        "Event GW.22
        A network undergoing self-test (see Software Operator's Manual for more
        information on self-test) has failed the self-test."
    ::= { gwEventsGroup 22 }

gw22_interface OBJECT-TYPE
    SYNTAX DisplayString
    MAX-ACCESS accessible-for-notify
    STATUS current
    DESCRIPTION
        "Parameter 'interface' in event GW.22"
    ::= { gwEventObjects22 1 }

gwEventObjects23 OBJECT-IDENTITY
    STATUS current
    DESCRIPTION
        "Event GW.23
        After failing self-test (see Software Operator's Manual for more
        information on self-test), a network that was previously up
        has gone down."
    ::= { gwEventsGroup 23 }

gw23_interface OBJECT-TYPE
    SYNTAX DisplayString
    MAX-ACCESS accessible-for-notify
    STATUS current
    DESCRIPTION
        "Parameter 'interface' in event GW.23"
    ::= { gwEventObjects23 1 }

gwEventObjects25 OBJECT-IDENTITY
    STATUS current
    DESCRIPTION
        "Event GW.25
        The number of maintainence checks (see Software Operator's Manual for
        more information on maintainence) failed in a given interval has
        exceeded the allowed limit (see the appropriate Router Hardware Manual
        for more detail on what the exact numbers are for each interface).
        A self-test (see Software Operator's Manual for more information on
        maintainence) will be started on the interface; if it fails,
        the interface will be marked down."
    ::= { gwEventsGroup 25 }

gw25_interface OBJECT-TYPE
    SYNTAX DisplayString
    MAX-ACCESS accessible-for-notify
    STATUS current
    DESCRIPTION
        "Parameter 'interface' in event GW.25"
    ::= { gwEventObjects25 1 }

gwEventObjects26 OBJECT-IDENTITY
    STATUS current
    DESCRIPTION
        "Event GW.26
        A maintainence check (see Software Operator's Manual for more
        information on maintainence) has been started for
        the indicated interface."
    ::= { gwEventsGroup 26 }

gw26_interface OBJECT-TYPE
    SYNTAX DisplayString
    MAX-ACCESS accessible-for-notify
    STATUS current
    DESCRIPTION
        "Parameter 'interface' in event GW.26"
    ::= { gwEventObjects26 1 }

gwEventObjects27 OBJECT-IDENTITY
    STATUS current
    DESCRIPTION
        "Event GW.27
        A buffer could not be allocated when needed by network maintaince."
    ::= { gwEventsGroup 27 }

gw27_interface OBJECT-TYPE
    SYNTAX DisplayString
    MAX-ACCESS accessible-for-notify
    STATUS current
    DESCRIPTION
        "Parameter 'interface' in event GW.27"
    ::= { gwEventObjects27 1 }

gwEventObjects28 OBJECT-IDENTITY
    STATUS current
    DESCRIPTION
        "Event GW.28
        A buffer was sent to the sink network, which discarded it with
        no indication of error to the forwarder."
    ::= { gwEventsGroup 28 }

gw28_protocol OBJECT-TYPE
    SYNTAX Integer32
    MAX-ACCESS accessible-for-notify
    STATUS current
    DESCRIPTION
        "Parameter 'protocol' in event GW.28"
    ::= { gwEventObjects28 1 }

gwEventObjects29 OBJECT-IDENTITY
    STATUS current
    DESCRIPTION
        "Event GW.29
        The interface in question was disabled in the configuration and
        will not come up; it can be started at any time by testing it."
    ::= { gwEventsGroup 29 }

gw29_interface OBJECT-TYPE
    SYNTAX DisplayString
    MAX-ACCESS accessible-for-notify
    STATUS current
    DESCRIPTION
        "Parameter 'interface' in event GW.29"
    ::= { gwEventObjects29 1 }

gwEventObjects31 OBJECT-IDENTITY
    STATUS current
    DESCRIPTION
        "Event GW.31
        The system has detected that there are probably an insufficent number
        of buffers for optimal operation. On startup, each of the fast devices
        are allocated a fixed number of buffers. If these buffers are not
        available, the particular interface may not perform well."
    ::= { gwEventsGroup 31 }

gw31_interface OBJECT-TYPE
    SYNTAX DisplayString
    MAX-ACCESS accessible-for-notify
    STATUS current
    DESCRIPTION
        "Parameter 'interface' in event GW.31"
    ::= { gwEventObjects31 1 }

gw31_number_of_buffers OBJECT-TYPE
    SYNTAX Integer32
    MAX-ACCESS accessible-for-notify
    STATUS current
    DESCRIPTION
        "Parameter 'number of buffers' in event GW.31"
    ::= { gwEventObjects31 2 }

gwEventObjects35 OBJECT-IDENTITY
    STATUS current
    DESCRIPTION
        "Event GW.35
        When the router went to send a packet to a given host, the network
        interface it had been told to send the packet over to was not up.
        The output discard counter for that interface was incremented, and
        the packet was returned to the protocol forwarder for attention.
        Usually, next_hop_host will be the MAC layer address of
        the next hop router or host that this packet is being sent to.
        The format of this MAC address depends on the network type.
        If next_hop_host starts with an @ (at-sign), then that network does not
        provide a formatted display of MAC addresses, and the following number
        is the hex address in router memory that the next hop host address is
        stored at."
    ::= { gwEventsGroup 35 }

gw35_next_hop_host OBJECT-TYPE
    SYNTAX DisplayString
    MAX-ACCESS accessible-for-notify
    STATUS current
    DESCRIPTION
        "Parameter 'next_hop_host' in event GW.35"
    ::= { gwEventObjects35 1 }

gw35_interface OBJECT-TYPE
    SYNTAX DisplayString
    MAX-ACCESS accessible-for-notify
    STATUS current
    DESCRIPTION
        "Parameter 'interface' in event GW.35"
    ::= { gwEventObjects35 2 }

gwEventObjects36 OBJECT-IDENTITY
    STATUS current
    DESCRIPTION
        "Event GW.36
        When the router went to send a packet to a given host, the interface
        output queue was too full, and the packet had to be discarded.
        The output overflow counter for that interface was incremented,
        and the packet was returned to the protocol forwarder for attention.
        Usually, next_hop_host will be the MAC layer address of the next hop
        router or host that this packet is being sent to. The format of this
        MAC address depends on the network type. If next_hop_host starts
        with an @ (at-sign), then that network does not provide a formatted
        display of MAC addresses, and the following number is the hex address
        in router memory that the next hop host address is stored at."
    ::= { gwEventsGroup 36 }

gw36_next_hop_host OBJECT-TYPE
    SYNTAX DisplayString
    MAX-ACCESS accessible-for-notify
    STATUS current
    DESCRIPTION
        "Parameter 'next_hop_host' in event GW.36"
    ::= { gwEventObjects36 1 }

gw36_interface OBJECT-TYPE
    SYNTAX DisplayString
    MAX-ACCESS accessible-for-notify
    STATUS current
    DESCRIPTION
        "Parameter 'interface' in event GW.36"
    ::= { gwEventObjects36 2 }

gwEventObjects37 OBJECT-IDENTITY
    STATUS current
    DESCRIPTION
        "Event GW.37
        Packets waiting for transmission on the interface in question
        were discarded when the network went down. The discard counter for
        the interface in question is incremented.
        Usually, next_hop_host will be the MAC layer address of
        the next hop router or host that this packet is being sent to.
        The format of this MAC address depends on the network type.
        If next_hop_host starts with an @ (at-sign), then that network does not
        provide a formatted display of MAC addresses, and the following number
        is the hex address in router memory that the next hop host address is
        stored at."
    ::= { gwEventsGroup 37 }

gw37_next_hop_host OBJECT-TYPE
    SYNTAX DisplayString
    MAX-ACCESS accessible-for-notify
    STATUS current
    DESCRIPTION
        "Parameter 'next_hop_host' in event GW.37"
    ::= { gwEventObjects37 1 }

gw37_interface OBJECT-TYPE
    SYNTAX DisplayString
    MAX-ACCESS accessible-for-notify
    STATUS current
    DESCRIPTION
        "Parameter 'interface' in event GW.37"
    ::= { gwEventObjects37 2 }

gwEventObjects38 OBJECT-IDENTITY
    STATUS current
    DESCRIPTION
        "Event GW.38
        Trace for debugging interactions with poolt."
    ::= { gwEventsGroup 38 }

gw38_function OBJECT-TYPE
    SYNTAX DisplayString
    MAX-ACCESS accessible-for-notify
    STATUS current
    DESCRIPTION
        "Parameter 'function' in event GW.38"
    ::= { gwEventObjects38 1 }

gw38_pointer OBJECT-TYPE
    SYNTAX Integer32
    MAX-ACCESS accessible-for-notify
    STATUS current
    DESCRIPTION
        "Parameter 'pointer' in event GW.38"
    ::= { gwEventObjects38 2 }

gw38_caller OBJECT-TYPE
    SYNTAX Integer32
    MAX-ACCESS accessible-for-notify
    STATUS current
    DESCRIPTION
        "Parameter 'caller' in event GW.38"
    ::= { gwEventObjects38 3 }

gw38_size OBJECT-TYPE
    SYNTAX Integer32
    MAX-ACCESS accessible-for-notify
    STATUS current
    DESCRIPTION
        "Parameter 'size' in event GW.38"
    ::= { gwEventObjects38 4 }

gwEventObjects48 OBJECT-IDENTITY
    STATUS current
    DESCRIPTION
        "Event GW.48
        The interface in question has been reserved for WAN restoral in
        the configuration and will not come up until needed by
        the WAN restoral process."
    ::= { gwEventsGroup 48 }

gw48_interface OBJECT-TYPE
    SYNTAX DisplayString
    MAX-ACCESS accessible-for-notify
    STATUS current
    DESCRIPTION
        "Parameter 'interface' in event GW.48"
    ::= { gwEventObjects48 1 }

gwEventObjects50 OBJECT-IDENTITY
    STATUS current
    DESCRIPTION
        "Event GW.50
        rptrPortOperStatus was previously notOperational and
        becomes operational, and that implies that ifAdminStatus of
        the corresponding switch port comes up"
    ::= { gwEventsGroup 50 }

gw50_ifindex OBJECT-TYPE
    SYNTAX Integer32
    MAX-ACCESS accessible-for-notify
    STATUS current
    DESCRIPTION
        "Parameter 'ifindex' in event GW.50"
    ::= { gwEventObjects50 1 }

gwEventObjects51 OBJECT-IDENTITY
    STATUS current
    DESCRIPTION
        "Event GW.51
        rptrPortOperStatus was previously operational and
        becomes notOperational, and that implies that ifAdminStatus
        of the corresponding switch port comes down"
    ::= { gwEventsGroup 51 }

gw51_ifindex OBJECT-TYPE
    SYNTAX Integer32
    MAX-ACCESS accessible-for-notify
    STATUS current
    DESCRIPTION
        "Parameter 'ifindex' in event GW.51"
    ::= { gwEventObjects51 1 }

gwEventObjects52 OBJECT-IDENTITY
    STATUS current
    DESCRIPTION
        "Event GW.52
        A user logged in successfully via specified protocol (console, telnet,
        ssh, etc.)"
    ::= { gwEventsGroup 52 }

gw52_protocol OBJECT-TYPE
    SYNTAX DisplayString
    MAX-ACCESS accessible-for-notify
    STATUS current
    DESCRIPTION
        "Parameter 'protocol' in event GW.52"
    ::= { gwEventObjects52 1 }

gw52_user_name OBJECT-TYPE
    SYNTAX DisplayString
    MAX-ACCESS accessible-for-notify
    STATUS current
    DESCRIPTION
        "Parameter 'user_name' in event GW.52"
    ::= { gwEventObjects52 2 }

gw52_source_ip_address OBJECT-TYPE
    SYNTAX IpAddress
    MAX-ACCESS accessible-for-notify
    STATUS current
    DESCRIPTION
        "Parameter 'source_ip_address' in event GW.52"
    ::= { gwEventObjects52 3 }

gwEventObjects53 OBJECT-IDENTITY
    STATUS current
    DESCRIPTION
        "Event GW.53
        A user login attempt failed via specified protocol (console, telnet,
        ssh, etc.)"
    ::= { gwEventsGroup 53 }

gw53_protocol OBJECT-TYPE
    SYNTAX DisplayString
    MAX-ACCESS accessible-for-notify
    STATUS current
    DESCRIPTION
        "Parameter 'protocol' in event GW.53"
    ::= { gwEventObjects53 1 }

gw53_user_name OBJECT-TYPE
    SYNTAX DisplayString
    MAX-ACCESS accessible-for-notify
    STATUS current
    DESCRIPTION
        "Parameter 'user_name' in event GW.53"
    ::= { gwEventObjects53 2 }

gw53_source_ip_address OBJECT-TYPE
    SYNTAX IpAddress
    MAX-ACCESS accessible-for-notify
    STATUS current
    DESCRIPTION
        "Parameter 'source_ip_address' in event GW.53"
    ::= { gwEventObjects53 3 }

gwEventObjects54 OBJECT-IDENTITY
    STATUS current
    DESCRIPTION
        "Event GW.54
        Packets are arriving on the stated interface too quickly for the
        router's forwarders to process them; they are discarded before being
        examined by the router software because of the overload.
        The count of packets is the number of packets this has happened since
        the last time it was attempted to log this message.
        The input overflow counter for this interface is incremented."
    ::= { gwEventsGroup 54 }

gw54_interface OBJECT-TYPE
    SYNTAX DisplayString
    MAX-ACCESS accessible-for-notify
    STATUS current
    DESCRIPTION
        "Parameter 'interface' in event GW.54"
    ::= { gwEventObjects54 1 }

gw54_count OBJECT-TYPE
    SYNTAX Integer32
    MAX-ACCESS accessible-for-notify
    STATUS current
    DESCRIPTION
        "Parameter 'count' in event GW.54"
    ::= { gwEventObjects54 2 }

gwEventObjects55 OBJECT-IDENTITY
    STATUS current
    DESCRIPTION
        "Event GW.55
        When the router went to send a packet, the network interface
        it had been told to send the packet over to was not up.
        The output discard counter for that network was incremented,
        and the packet was returned to the protocol forwarder for attention."
    ::= { gwEventsGroup 55 }

gw55_interface OBJECT-TYPE
    SYNTAX DisplayString
    MAX-ACCESS accessible-for-notify
    STATUS current
    DESCRIPTION
        "Parameter 'interface' in event GW.55"
    ::= { gwEventObjects55 1 }

gwEventObjects56 OBJECT-IDENTITY
    STATUS current
    DESCRIPTION
        "Event GW.56
        When the router went to send a packet, the network interface
        it had been told to send the packet over had packet transmission
        disabled.
        The output discard counter for that network was incremented."
    ::= { gwEventsGroup 56 }

gw56_interface OBJECT-TYPE
    SYNTAX DisplayString
    MAX-ACCESS accessible-for-notify
    STATUS current
    DESCRIPTION
        "Parameter 'interface' in event GW.56"
    ::= { gwEventObjects56 1 }

gwEventObjects57 OBJECT-IDENTITY
    STATUS current
    DESCRIPTION
        "Event GW.57
        When the router went to send a packet, the interface output queue was
        too full, and the packet had to be discarded.
        The output overflow counter for that interface was incremented, and
        the packet was returned to the protocol forwarder for attention."
    ::= { gwEventsGroup 57 }

gw57_interface OBJECT-TYPE
    SYNTAX DisplayString
    MAX-ACCESS accessible-for-notify
    STATUS current
    DESCRIPTION
        "Parameter 'interface' in event GW.57"
    ::= { gwEventObjects57 1 }

gwEventObjects58 OBJECT-IDENTITY
    STATUS current
    DESCRIPTION
        "Event GW.58
        A packet has not been sucessfully retransmitted.
        The output error counter for that interface is incremented,
        and the packet is discarded. Usually, next_hop_host will be
        the MAC layer address of the next hop router or host that this packet
        is being sent to. The format of this MAC address depends on
        the network type. If next_hop_host starts with an @ (at-sign), then
        that network does not provide formatted display of MAC addresses, and
        the following number is the hex address in router memory that
        the next hop host address is stored at."
    ::= { gwEventsGroup 58 }

gw58_next_hop_host OBJECT-TYPE
    SYNTAX DisplayString
    MAX-ACCESS accessible-for-notify
    STATUS current
    DESCRIPTION
        "Parameter 'next_hop_host' in event GW.58"
    ::= { gwEventObjects58 1 }

gw58_interface OBJECT-TYPE
    SYNTAX DisplayString
    MAX-ACCESS accessible-for-notify
    STATUS current
    DESCRIPTION
        "Parameter 'interface' in event GW.58"
    ::= { gwEventObjects58 2 }

gwEventObjects59 OBJECT-IDENTITY
    STATUS current
    DESCRIPTION
        "Event GW.59
        Parameters for the last configuration change before last restart."
    ::= { gwEventsGroup 59 }

gw59_filename OBJECT-TYPE
    SYNTAX DisplayString
    MAX-ACCESS accessible-for-notify
    STATUS current
    DESCRIPTION
        "Parameter 'filename' in event GW.59"
    ::= { gwEventObjects59 1 }

gw59_srctype OBJECT-TYPE
    SYNTAX DisplayString
    MAX-ACCESS accessible-for-notify
    STATUS current
    DESCRIPTION
        "Parameter 'srctype' in event GW.59"
    ::= { gwEventObjects59 2 }

gw59_srcadd OBJECT-TYPE
    SYNTAX IpAddress
    MAX-ACCESS accessible-for-notify
    STATUS current
    DESCRIPTION
        "Parameter 'srcadd' in event GW.59"
    ::= { gwEventObjects59 3 }

gw59_user OBJECT-TYPE
    SYNTAX DisplayString
    MAX-ACCESS accessible-for-notify
    STATUS current
    DESCRIPTION
        "Parameter 'user' in event GW.59"
    ::= { gwEventObjects59 4 }

gw59_datetime OBJECT-TYPE
    SYNTAX DisplayString
    MAX-ACCESS accessible-for-notify
    STATUS current
    DESCRIPTION
        "Parameter 'datetime' in event GW.59"
    ::= { gwEventObjects59 5 }

gwEventObjects60 OBJECT-IDENTITY
    STATUS current
    DESCRIPTION
        "Event GW.60
        'dotrp' has been called from outside tasker."
    ::= { gwEventsGroup 60 }

gw60_trapnum OBJECT-TYPE
    SYNTAX Integer32
    MAX-ACCESS accessible-for-notify
    STATUS current
    DESCRIPTION
        "Parameter 'trapnum' in event GW.60"
    ::= { gwEventObjects60 1 }

gwEventObjects61 OBJECT-IDENTITY
    STATUS current
    DESCRIPTION
        "Event GW.61
        A buffer was sent to the interface in question, which discarded it
        with no indication of error to the forwarder."
    ::= { gwEventsGroup 61 }

gw61_interface OBJECT-TYPE
    SYNTAX DisplayString
    MAX-ACCESS accessible-for-notify
    STATUS current
    DESCRIPTION
        "Parameter 'interface' in event GW.61"
    ::= { gwEventObjects61 1 }

gw61_protocol OBJECT-TYPE
    SYNTAX Integer32
    MAX-ACCESS accessible-for-notify
    STATUS current
    DESCRIPTION
        "Parameter 'protocol' in event GW.61"
    ::= { gwEventObjects61 2 }

gwEventObjects62 OBJECT-IDENTITY
    STATUS current
    DESCRIPTION
        "Event GW.62
        Firmware file: not found, checksum error, uncompress error, ..."
    ::= { gwEventsGroup 62 }

gw62_filename OBJECT-TYPE
    SYNTAX DisplayString
    MAX-ACCESS accessible-for-notify
    STATUS current
    DESCRIPTION
        "Parameter 'filename' in event GW.62"
    ::= { gwEventObjects62 1 }

gw62_event OBJECT-TYPE
    SYNTAX DisplayString
    MAX-ACCESS accessible-for-notify
    STATUS current
    DESCRIPTION
        "Parameter 'event' in event GW.62"
    ::= { gwEventObjects62 2 }

gwEventObjects64 OBJECT-IDENTITY
    STATUS current
    DESCRIPTION
        "Event GW.64
        Action performed by the licence system"
    ::= { gwEventsGroup 64 }

gw64_description OBJECT-TYPE
    SYNTAX DisplayString
    MAX-ACCESS accessible-for-notify
    STATUS current
    DESCRIPTION
        "Parameter 'description' in event GW.64"
    ::= { gwEventObjects64 1 }

gwEventObjects65 OBJECT-IDENTITY
    STATUS current
    DESCRIPTION
        "Event GW.65
        Multiprocessor subsytem info"
    ::= { gwEventsGroup 65 }

gw65_description OBJECT-TYPE
    SYNTAX DisplayString
    MAX-ACCESS accessible-for-notify
    STATUS current
    DESCRIPTION
        "Parameter 'description' in event GW.65"
    ::= { gwEventObjects65 1 }

gwEventObjects66 OBJECT-IDENTITY
    STATUS current
    DESCRIPTION
        "Event GW.66
        A packet has been received in a interface."
    ::= { gwEventsGroup 66 }

gw66_interface OBJECT-TYPE
    SYNTAX DisplayString
    MAX-ACCESS accessible-for-notify
    STATUS current
    DESCRIPTION
        "Parameter 'interface' in event GW.66"
    ::= { gwEventObjects66 1 }

gw66_source OBJECT-TYPE
    SYNTAX IpAddress
    MAX-ACCESS accessible-for-notify
    STATUS current
    DESCRIPTION
        "Parameter 'source' in event GW.66"
    ::= { gwEventObjects66 2 }

gw66_dest OBJECT-TYPE
    SYNTAX IpAddress
    MAX-ACCESS accessible-for-notify
    STATUS current
    DESCRIPTION
        "Parameter 'dest' in event GW.66"
    ::= { gwEventObjects66 3 }

gw66_protocol OBJECT-TYPE
    SYNTAX Integer32
    MAX-ACCESS accessible-for-notify
    STATUS current
    DESCRIPTION
        "Parameter 'protocol' in event GW.66"
    ::= { gwEventObjects66 4 }

gwEventObjects67 OBJECT-IDENTITY
    STATUS current
    DESCRIPTION
        "Event GW.67
        The interface is down so the interface entry function has discarded the
        packet."
    ::= { gwEventsGroup 67 }

gw67_interface OBJECT-TYPE
    SYNTAX DisplayString
    MAX-ACCESS accessible-for-notify
    STATUS current
    DESCRIPTION
        "Parameter 'interface' in event GW.67"
    ::= { gwEventObjects67 1 }

gwEventObjects69 OBJECT-IDENTITY
    STATUS current
    DESCRIPTION
        "Event GW.69
        The specified fan has failed."
    ::= { gwEventsGroup 69 }

gw69_fan_name OBJECT-TYPE
    SYNTAX DisplayString
    MAX-ACCESS accessible-for-notify
    STATUS current
    DESCRIPTION
        "Parameter 'fan_name' in event GW.69"
    ::= { gwEventObjects69 1 }

gwEventObjects70 OBJECT-IDENTITY
    STATUS current
    DESCRIPTION
        "Event GW.70
        The specified temperature has been reached."
    ::= { gwEventsGroup 70 }

gw70_temperature OBJECT-TYPE
    SYNTAX Integer32
    MAX-ACCESS accessible-for-notify
    STATUS current
    DESCRIPTION
        "Parameter 'temperature' in event GW.70"
    ::= { gwEventObjects70 1 }

gw70_temperature_info OBJECT-TYPE
    SYNTAX DisplayString
    MAX-ACCESS accessible-for-notify
    STATUS current
    DESCRIPTION
        "Parameter 'temperature_info' in event GW.70"
    ::= { gwEventObjects70 2 }

gwEventObjects71 OBJECT-IDENTITY
    STATUS current
    DESCRIPTION
        "Event GW.71
        The buffer is overflow."
    ::= { gwEventsGroup 71 }

gw71_place OBJECT-TYPE
    SYNTAX DisplayString
    MAX-ACCESS accessible-for-notify
    STATUS current
    DESCRIPTION
        "Parameter 'place' in event GW.71"
    ::= { gwEventObjects71 1 }

gw71_caller OBJECT-TYPE
    SYNTAX DisplayString
    MAX-ACCESS accessible-for-notify
    STATUS current
    DESCRIPTION
        "Parameter 'caller' in event GW.71"
    ::= { gwEventObjects71 2 }

gwEventObjects72 OBJECT-IDENTITY
    STATUS current
    DESCRIPTION
        "Event GW.72
        Buffer dump."
    ::= { gwEventsGroup 72 }

gw72_place OBJECT-TYPE
    SYNTAX DisplayString
    MAX-ACCESS accessible-for-notify
    STATUS current
    DESCRIPTION
        "Parameter 'place' in event GW.72"
    ::= { gwEventObjects72 1 }

gw72_dump OBJECT-TYPE
    SYNTAX DisplayString
    MAX-ACCESS accessible-for-notify
    STATUS current
    DESCRIPTION
        "Parameter 'dump' in event GW.72"
    ::= { gwEventObjects72 2 }


gwNotification1 NOTIFICATION-TYPE
    OBJECTS { 
              gw1_router_name 
            }
    STATUS current
    DESCRIPTION
        "Notification of Event GW.1

        Message: 'System restarted -- $1 router cold start'

        Parameters list:
              $1: gw1_router_name

        Router cold start."
    ::= { gwNotificationsPrefix 1 }

gwNotification2 NOTIFICATION-TYPE
    OBJECTS { 
              gw2_router_name, 
              gw2_release_level 
            }
    STATUS current
    DESCRIPTION
        "Notification of Event GW.2

        Message: 'Portable C Gateway $1 Release $2 started'

        Parameters list:
              $1: gw2_router_name
              $2: gw2_release_level

        Prints the name of the router (as indicated in the router), and
        the release level of the software load which has just started
        in the router."
    ::= { gwNotificationsPrefix 2 }

gwNotification3 NOTIFICATION-TYPE
    OBJECTS { 
              gw3_unused_length, 
              gw3_interface 
            }
    STATUS current
    DESCRIPTION
        "Notification of Event GW.3

        Message: 'Unused packet length $1 interface $2'

        Parameters list:
              $1: gw3_unused_length
              $2: gw3_interface

        The router will not be able to send or receive the last [unused length]
        bytes of maximum size packets."
    ::= { gwNotificationsPrefix 3 }

gwNotification4 NOTIFICATION-TYPE
    OBJECTS { 
              gw4_queue_type, 
              gw4_advisable_queue_length,
              gw4_actual_queue_length 
            }
    STATUS current
    DESCRIPTION
        "Notification of Event GW.4

        Message: 'System $1 queue advisory allocation of $2 exceeded $3'

        Parameters list:
              $1: gw4_queue_type
              $2: gw4_advisable_queue_length
              $3: gw4_actual_queue_length

        The system has detected that there are probably an insufficent number
        of buffers for optimal operation.
        On startup, the maximum number of buffers allocated to either
        the permanent device input queue or the transient device output queue
        had exceeded an advisable allocation of the entire buffer pool."
    ::= { gwNotificationsPrefix 4 }

gwNotification5 NOTIFICATION-TYPE
    OBJECTS { 
              gw5_total_created, 
              gw5_initially_free,
              gw5_fair_share_amount,
              gw5_high_water_mark 
            }
    STATUS current
    DESCRIPTION
        "Notification of Event GW.5

        Message: 'Buffers: $1 available $2 idle   fair share $3 low water $4'

        Parameters list:
              $1: gw5_total_created
              $2: gw5_initially_free
              $3: gw5_fair_share_amount
              $4: gw5_high_water_mark

        The message gives information about the number of buffers created by
        the initialization procedure, as well as some information on parameters
        used by the buffer allocation system. As long as the number of buffers
        currently free in the router is above the low water mark, any user can
        allocate buffers. Below that point, any user can allocate buffers,
        as long as the number is less than the 'fair share'."
    ::= { gwNotificationsPrefix 5 }

gwNotification6 NOTIFICATION-TYPE
    OBJECTS { 
              gw6_interface 
            }
    STATUS current
    DESCRIPTION
        "Notification of Event GW.6

        Message: 'Packet from interface $1 for uninitialized protocol discarded'

        Parameters list:
              $1: gw6_interface

        An incoming packet was in a protocol which, although recognized, did not
        have a handler loaded and enabled."
    ::= { gwNotificationsPrefix 6 }

gwNotification7 NOTIFICATION-TYPE
    OBJECTS { 
              gw7_error_code, 
              gw7_interface 
            }
    STATUS current
    DESCRIPTION
        "Notification of Event GW.7

        Message: 'Input error $1 interface $2'

        Parameters list:
              $1: gw7_error_code
              $2: gw7_interface

        A device input operation returned an error, along with a
        device specific error code. The input error counter for that network
        was incrememented, and any packet associated with that error
        was probably discarded."
    ::= { gwNotificationsPrefix 7 }

gwNotification8 NOTIFICATION-TYPE
    STATUS current
    DESCRIPTION
        "Notification of Event GW.8

        Message: 'Configuration has been saved'

        Configuration has been saved in SRAM."
    ::= { gwNotificationsPrefix 8 }

gwNotification9 NOTIFICATION-TYPE
    OBJECTS { 
              gw9_interface 
            }
    STATUS current
    DESCRIPTION
        "Notification of Event GW.9

        Message: 'Net down for input restart interface $1'

        Parameters list:
              $1: gw9_interface

        When the router attempted to queue additional input operations for
        the interface, the interface had been disabled for input."
    ::= { gwNotificationsPrefix 9 }

gwNotification10 NOTIFICATION-TYPE
    OBJECTS { 
              gw10_queue_length, 
              gw10_interface 
            }
    STATUS current
    DESCRIPTION
        "Notification of Event GW.10

        Message: 'Input queue length $1 no input buffer interface $2'

        Parameters list:
              $1: gw10_queue_length
              $2: gw10_interface

        When the router attempted to queue additional input operations for
        the interface, not enough free buffers were available to refill the
        input queue to the level desired; the actual level attained is listed."
    ::= { gwNotificationsPrefix 10 }

gwNotification11 NOTIFICATION-TYPE
    OBJECTS { 
              gw11_ip_address 
            }
    STATUS current
    DESCRIPTION
        "Notification of Event GW.11

        Message: 'Remote terminal $1 has captured console'

        Parameters list:
              $1: gw11_ip_address

        Remote terminal owns console."
    ::= { gwNotificationsPrefix 11 }

gwNotification12 NOTIFICATION-TYPE
    STATUS current
    DESCRIPTION
        "Notification of Event GW.12

        Message: 'Errors building config. as text. Binary mode used.'

        This error means that the configuration has some invalid parameters that
        cause startup errors when parsing text mode configuration. To avoid
        this, the configuration is saved in binary mode."
    ::= { gwNotificationsPrefix 12 }

gwNotification13 NOTIFICATION-TYPE
    STATUS current
    DESCRIPTION
        "Notification of Event GW.13

        Message: 'User lock error building config. as text. Binary mode used.'

        This error means that the configuration couldn't be checked because
        another user locked it. To overcome this the configuration is saved in
        binary mode."
    ::= { gwNotificationsPrefix 13 }

gwNotification14 NOTIFICATION-TYPE
    OBJECTS { 
              gw14_interface 
            }
    STATUS current
    DESCRIPTION
        "Notification of Event GW.14

        Message: 'Net down for output restart interface $1'

        Parameters list:
              $1: gw14_interface

        When the router attempted to queue additional output operations
        for the interface, the interface had been disabled for output."
    ::= { gwNotificationsPrefix 14 }

gwNotification15 NOTIFICATION-TYPE
    OBJECTS { 
              gw15_state, 
              gw15_interface,
              gw15_protocol_number,
              gw15_protocol_name 
            }
    STATUS current
    DESCRIPTION
        "Notification of Event GW.15

        Message: 'New state is $1 on interface $2 protocol $3 ($4)'

        Parameters list:
              $1: gw15_state
              $2: gw15_interface
              $3: gw15_protocol_number
              $4: gw15_protocol_name

        The specified protocol changed to specified state
        on specified interface."
    ::= { gwNotificationsPrefix 15 }

gwNotification16 NOTIFICATION-TYPE
    STATUS current
    DESCRIPTION
        "Notification of Event GW.16

        Message: '---'

        Reserved for possible future use."
    ::= { gwNotificationsPrefix 16 }

gwNotification17 NOTIFICATION-TYPE
    OBJECTS { 
              gw17_interface 
            }
    STATUS current
    DESCRIPTION
        "Notification of Event GW.17

        Message: 'Interface hardware missing on $1'

        Parameters list:
              $1: gw17_interface

        When the router software went to initialize the network interface for
        the first time, the board did not respond on the bus. The board
        is marked 'not present' and ignored from then on."
    ::= { gwNotificationsPrefix 17 }

gwNotification18 NOTIFICATION-TYPE
    OBJECTS { 
              gw18_interface 
            }
    STATUS current
    DESCRIPTION
        "Notification of Event GW.18

        Message: 'Start network self test interface $1'

        Parameters list:
              $1: gw18_interface

        A network self-test (see Software Operator's Manual for more information
        on self-test) has been requested."
    ::= { gwNotificationsPrefix 18 }

gwNotification19 NOTIFICATION-TYPE
    OBJECTS { 
              gw19_interface 
            }
    STATUS current
    DESCRIPTION
        "Notification of Event GW.19

        Message: 'Self test interface $1'

        Parameters list:
              $1: gw19_interface

        A network self-test (see Software Operator's Manual for more information
        on self-test) has been started."
    ::= { gwNotificationsPrefix 19 }

gwNotification20 NOTIFICATION-TYPE
    OBJECTS { 
              gw20_interface 
            }
    STATUS current
    DESCRIPTION
        "Notification of Event GW.20

        Message: 'Network passed self test interface $1'

        Parameters list:
              $1: gw20_interface

        A network undergoing self-test (see Software Operator's Manual for more
        information on self-test) has passed the self-test."
    ::= { gwNotificationsPrefix 20 }

gwNotification21 NOTIFICATION-TYPE
    OBJECTS { 
              gw21_interface 
            }
    STATUS current
    DESCRIPTION
        "Notification of Event GW.21

        Message: 'Network up interface $1'

        Parameters list:
              $1: gw21_interface

        After passing self-test (see Software Operator's Manual for more
        information on self-test), a network that was previously down
        has come up."
    ::= { gwNotificationsPrefix 21 }

gwNotification22 NOTIFICATION-TYPE
    OBJECTS { 
              gw22_interface 
            }
    STATUS current
    DESCRIPTION
        "Notification of Event GW.22

        Message: 'Network failed self test interface $1'

        Parameters list:
              $1: gw22_interface

        A network undergoing self-test (see Software Operator's Manual for more
        information on self-test) has failed the self-test."
    ::= { gwNotificationsPrefix 22 }

gwNotification23 NOTIFICATION-TYPE
    OBJECTS { 
              gw23_interface 
            }
    STATUS current
    DESCRIPTION
        "Notification of Event GW.23

        Message: 'Network down interface $1'

        Parameters list:
              $1: gw23_interface

        After failing self-test (see Software Operator's Manual for more
        information on self-test), a network that was previously up
        has gone down."
    ::= { gwNotificationsPrefix 23 }

gwNotification24 NOTIFICATION-TYPE
    STATUS current
    DESCRIPTION
        "Notification of Event GW.24

        Message: '---'

        Reserved for possible future use."
    ::= { gwNotificationsPrefix 24 }

gwNotification25 NOTIFICATION-TYPE
    OBJECTS { 
              gw25_interface 
            }
    STATUS current
    DESCRIPTION
        "Notification of Event GW.25

        Message: 'Network failed maintainence interface $1'

        Parameters list:
              $1: gw25_interface

        The number of maintainence checks (see Software Operator's Manual for
        more information on maintainence) failed in a given interval has
        exceeded the allowed limit (see the appropriate Router Hardware Manual
        for more detail on what the exact numbers are for each interface).
        A self-test (see Software Operator's Manual for more information on
        maintainence) will be started on the interface; if it fails,
        the interface will be marked down."
    ::= { gwNotificationsPrefix 25 }

gwNotification26 NOTIFICATION-TYPE
    OBJECTS { 
              gw26_interface 
            }
    STATUS current
    DESCRIPTION
        "Notification of Event GW.26

        Message: 'Maintainence interface $1'

        Parameters list:
              $1: gw26_interface

        A maintainence check (see Software Operator's Manual for more
        information on maintainence) has been started for
        the indicated interface."
    ::= { gwNotificationsPrefix 26 }

gwNotification27 NOTIFICATION-TYPE
    OBJECTS { 
              gw27_interface 
            }
    STATUS current
    DESCRIPTION
        "Notification of Event GW.27

        Message: 'No packet for maintainence interface $1'

        Parameters list:
              $1: gw27_interface

        A buffer could not be allocated when needed by network maintaince."
    ::= { gwNotificationsPrefix 27 }

gwNotification28 NOTIFICATION-TYPE
    OBJECTS { 
              gw28_protocol 
            }
    STATUS current
    DESCRIPTION
        "Notification of Event GW.28

        Message: 'Sink network discarding packet protocol $1'

        Parameters list:
              $1: gw28_protocol

        A buffer was sent to the sink network, which discarded it with
        no indication of error to the forwarder."
    ::= { gwNotificationsPrefix 28 }

gwNotification29 NOTIFICATION-TYPE
    OBJECTS { 
              gw29_interface 
            }
    STATUS current
    DESCRIPTION
        "Notification of Event GW.29

        Message: 'Interface $1 disabled in configuration'

        Parameters list:
              $1: gw29_interface

        The interface in question was disabled in the configuration and
        will not come up; it can be started at any time by testing it."
    ::= { gwNotificationsPrefix 29 }

gwNotification30 NOTIFICATION-TYPE
    STATUS current
    DESCRIPTION
        "Notification of Event GW.30

        Message: '---'

        Reserved for possible future use."
    ::= { gwNotificationsPrefix 30 }

gwNotification31 NOTIFICATION-TYPE
    OBJECTS { 
              gw31_interface, 
              gw31_number_of_buffers 
            }
    STATUS current
    DESCRIPTION
        "Notification of Event GW.31

        Message: 'Input queue allocation failed interface $1 available $2'

        Parameters list:
              $1: gw31_interface
              $2: gw31_number_of_buffers

        The system has detected that there are probably an insufficent number
        of buffers for optimal operation. On startup, each of the fast devices
        are allocated a fixed number of buffers. If these buffers are not
        available, the particular interface may not perform well."
    ::= { gwNotificationsPrefix 31 }

gwNotification32 NOTIFICATION-TYPE
    STATUS current
    DESCRIPTION
        "Notification of Event GW.32

        Message: '---'

        Reserved for possible future use."
    ::= { gwNotificationsPrefix 32 }

gwNotification33 NOTIFICATION-TYPE
    STATUS current
    DESCRIPTION
        "Notification of Event GW.33

        Message: '---'

        Reserved for possible future use."
    ::= { gwNotificationsPrefix 33 }

gwNotification34 NOTIFICATION-TYPE
    STATUS current
    DESCRIPTION
        "Notification of Event GW.34

        Message: '---'

        Reserved for possible future use."
    ::= { gwNotificationsPrefix 34 }

gwNotification35 NOTIFICATION-TYPE
    OBJECTS { 
              gw35_next_hop_host, 
              gw35_interface 
            }
    STATUS current
    DESCRIPTION
        "Notification of Event GW.35

        Message: 'Net down transmitting to host $1 interface $2'

        Parameters list:
              $1: gw35_next_hop_host
              $2: gw35_interface

        When the router went to send a packet to a given host, the network
        interface it had been told to send the packet over to was not up.
        The output discard counter for that interface was incremented, and
        the packet was returned to the protocol forwarder for attention.
        Usually, next_hop_host will be the MAC layer address of
        the next hop router or host that this packet is being sent to.
        The format of this MAC address depends on the network type.
        If next_hop_host starts with an @ (at-sign), then that network does not
        provide a formatted display of MAC addresses, and the following number
        is the hex address in router memory that the next hop host address is
        stored at."
    ::= { gwNotificationsPrefix 35 }

gwNotification36 NOTIFICATION-TYPE
    OBJECTS { 
              gw36_next_hop_host, 
              gw36_interface 
            }
    STATUS current
    DESCRIPTION
        "Notification of Event GW.36

        Message: 'Output overflow when transmitting to host $1 interface $2'

        Parameters list:
              $1: gw36_next_hop_host
              $2: gw36_interface

        When the router went to send a packet to a given host, the interface
        output queue was too full, and the packet had to be discarded.
        The output overflow counter for that interface was incremented,
        and the packet was returned to the protocol forwarder for attention.
        Usually, next_hop_host will be the MAC layer address of the next hop
        router or host that this packet is being sent to. The format of this
        MAC address depends on the network type. If next_hop_host starts
        with an @ (at-sign), then that network does not provide a formatted
        display of MAC addresses, and the following number is the hex address
        in router memory that the next hop host address is stored at."
    ::= { gwNotificationsPrefix 36 }

gwNotification37 NOTIFICATION-TYPE
    OBJECTS { 
              gw37_next_hop_host, 
              gw37_interface 
            }
    STATUS current
    DESCRIPTION
        "Notification of Event GW.37

        Message: 'Network down, discarding packet to host $1 interface $2'

        Parameters list:
              $1: gw37_next_hop_host
              $2: gw37_interface

        Packets waiting for transmission on the interface in question
        were discarded when the network went down. The discard counter for
        the interface in question is incremented.
        Usually, next_hop_host will be the MAC layer address of
        the next hop router or host that this packet is being sent to.
        The format of this MAC address depends on the network type.
        If next_hop_host starts with an @ (at-sign), then that network does not
        provide a formatted display of MAC addresses, and the following number
        is the hex address in router memory that the next hop host address is
        stored at."
    ::= { gwNotificationsPrefix 37 }

gwNotification38 NOTIFICATION-TYPE
    OBJECTS { 
              gw38_function, 
              gw38_pointer,
              gw38_caller,
              gw38_size 
            }
    STATUS current
    DESCRIPTION
        "Notification of Event GW.38

        Message: '$1: $2, caller:$3, size:$4'

        Parameters list:
              $1: gw38_function
              $2: gw38_pointer
              $3: gw38_caller
              $4: gw38_size

        Trace for debugging interactions with poolt."
    ::= { gwNotificationsPrefix 38 }

gwNotification39 NOTIFICATION-TYPE
    STATUS current
    DESCRIPTION
        "Notification of Event GW.39

        Message: '---'

        Reserved for possible future use."
    ::= { gwNotificationsPrefix 39 }

gwNotification40 NOTIFICATION-TYPE
    STATUS current
    DESCRIPTION
        "Notification of Event GW.40

        Message: '---'

        Reserved for possible future use."
    ::= { gwNotificationsPrefix 40 }

gwNotification41 NOTIFICATION-TYPE
    STATUS current
    DESCRIPTION
        "Notification of Event GW.41

        Message: '---'

        Reserved for possible future use."
    ::= { gwNotificationsPrefix 41 }

gwNotification42 NOTIFICATION-TYPE
    STATUS current
    DESCRIPTION
        "Notification of Event GW.42

        Message: '---'

        Reserved for possible future use."
    ::= { gwNotificationsPrefix 42 }

gwNotification43 NOTIFICATION-TYPE
    STATUS current
    DESCRIPTION
        "Notification of Event GW.43

        Message: '---'

        Reserved for possible future use."
    ::= { gwNotificationsPrefix 43 }

gwNotification44 NOTIFICATION-TYPE
    STATUS current
    DESCRIPTION
        "Notification of Event GW.44

        Message: '---'

        Reserved for possible future use."
    ::= { gwNotificationsPrefix 44 }

gwNotification45 NOTIFICATION-TYPE
    STATUS current
    DESCRIPTION
        "Notification of Event GW.45

        Message: '---'

        Reserved for possible future use."
    ::= { gwNotificationsPrefix 45 }

gwNotification46 NOTIFICATION-TYPE
    STATUS current
    DESCRIPTION
        "Notification of Event GW.46

        Message: '---'

        Reserved for possible future use."
    ::= { gwNotificationsPrefix 46 }

gwNotification47 NOTIFICATION-TYPE
    STATUS current
    DESCRIPTION
        "Notification of Event GW.47

        Message: '---'

        Reserved for possible future use."
    ::= { gwNotificationsPrefix 47 }

gwNotification48 NOTIFICATION-TYPE
    OBJECTS { 
              gw48_interface 
            }
    STATUS current
    DESCRIPTION
        "Notification of Event GW.48

        Message: 'Interface $1 reserved for WAN restoral in configuration'

        Parameters list:
              $1: gw48_interface

        The interface in question has been reserved for WAN restoral in
        the configuration and will not come up until needed by
        the WAN restoral process."
    ::= { gwNotificationsPrefix 48 }

gwNotification49 NOTIFICATION-TYPE
    STATUS current
    DESCRIPTION
        "Notification of Event GW.49

        Message: '---'

        Reserved for possible future use."
    ::= { gwNotificationsPrefix 49 }

gwNotification50 NOTIFICATION-TYPE
    OBJECTS { 
              gw50_ifindex 
            }
    STATUS current
    DESCRIPTION
        "Notification of Event GW.50

        Message: 'Network up switch port $1'

        Parameters list:
              $1: gw50_ifindex

        rptrPortOperStatus was previously notOperational and
        becomes operational, and that implies that ifAdminStatus of
        the corresponding switch port comes up"
    ::= { gwNotificationsPrefix 50 }

gwNotification51 NOTIFICATION-TYPE
    OBJECTS { 
              gw51_ifindex 
            }
    STATUS current
    DESCRIPTION
        "Notification of Event GW.51

        Message: 'Network down switch port $1'

        Parameters list:
              $1: gw51_ifindex

        rptrPortOperStatus was previously operational and
        becomes notOperational, and that implies that ifAdminStatus
        of the corresponding switch port comes down"
    ::= { gwNotificationsPrefix 51 }

gwNotification52 NOTIFICATION-TYPE
    OBJECTS { 
              gw52_protocol, 
              gw52_user_name,
              gw52_source_ip_address 
            }
    STATUS current
    DESCRIPTION
        "Notification of Event GW.52

        Message: 'Login successful via $1 user $2 from source address $3'

        Parameters list:
              $1: gw52_protocol
              $2: gw52_user_name
              $3: gw52_source_ip_address

        A user logged in successfully via specified protocol (console, telnet,
        ssh, etc.)"
    ::= { gwNotificationsPrefix 52 }

gwNotification53 NOTIFICATION-TYPE
    OBJECTS { 
              gw53_protocol, 
              gw53_user_name,
              gw53_source_ip_address 
            }
    STATUS current
    DESCRIPTION
        "Notification of Event GW.53

        Message: 'Login failed via $1 user $2 from source address $3'

        Parameters list:
              $1: gw53_protocol
              $2: gw53_user_name
              $3: gw53_source_ip_address

        A user login attempt failed via specified protocol (console, telnet,
        ssh, etc.)"
    ::= { gwNotificationsPrefix 53 }

gwNotification54 NOTIFICATION-TYPE
    OBJECTS { 
              gw54_interface, 
              gw54_count 
            }
    STATUS current
    DESCRIPTION
        "Notification of Event GW.54

        Message: 'Input overflow interface $1, $2 packets discarded'

        Parameters list:
              $1: gw54_interface
              $2: gw54_count

        Packets are arriving on the stated interface too quickly for the
        router's forwarders to process them; they are discarded before being
        examined by the router software because of the overload.
        The count of packets is the number of packets this has happened since
        the last time it was attempted to log this message.
        The input overflow counter for this interface is incremented."
    ::= { gwNotificationsPrefix 54 }

gwNotification55 NOTIFICATION-TYPE
    OBJECTS { 
              gw55_interface 
            }
    STATUS current
    DESCRIPTION
        "Notification of Event GW.55

        Message: 'Net down transmitting on interface $1'

        Parameters list:
              $1: gw55_interface

        When the router went to send a packet, the network interface
        it had been told to send the packet over to was not up.
        The output discard counter for that network was incremented,
        and the packet was returned to the protocol forwarder for attention."
    ::= { gwNotificationsPrefix 55 }

gwNotification56 NOTIFICATION-TYPE
    OBJECTS { 
              gw56_interface 
            }
    STATUS current
    DESCRIPTION
        "Notification of Event GW.56

        Message: 'Net output disabled, transmitting on interface $1'

        Parameters list:
              $1: gw56_interface

        When the router went to send a packet, the network interface
        it had been told to send the packet over had packet transmission
        disabled.
        The output discard counter for that network was incremented."
    ::= { gwNotificationsPrefix 56 }

gwNotification57 NOTIFICATION-TYPE
    OBJECTS { 
              gw57_interface 
            }
    STATUS current
    DESCRIPTION
        "Notification of Event GW.57

        Message: 'Output overflow when transmitting on interface $1'

        Parameters list:
              $1: gw57_interface

        When the router went to send a packet, the interface output queue was
        too full, and the packet had to be discarded.
        The output overflow counter for that interface was incremented, and
        the packet was returned to the protocol forwarder for attention."
    ::= { gwNotificationsPrefix 57 }

gwNotification58 NOTIFICATION-TYPE
    OBJECTS { 
              gw58_next_hop_host, 
              gw58_interface 
            }
    STATUS current
    DESCRIPTION
        "Notification of Event GW.58

        Message: 'Output error transmitting to host $1 interface $2'

        Parameters list:
              $1: gw58_next_hop_host
              $2: gw58_interface

        A packet has not been sucessfully retransmitted.
        The output error counter for that interface is incremented,
        and the packet is discarded. Usually, next_hop_host will be
        the MAC layer address of the next hop router or host that this packet
        is being sent to. The format of this MAC address depends on
        the network type. If next_hop_host starts with an @ (at-sign), then
        that network does not provide formatted display of MAC addresses, and
        the following number is the hex address in router memory that
        the next hop host address is stored at."
    ::= { gwNotificationsPrefix 58 }

gwNotification59 NOTIFICATION-TYPE
    OBJECTS { 
              gw59_filename, 
              gw59_srctype,
              gw59_srcadd,
              gw59_user,
              gw59_datetime 
            }
    STATUS current
    DESCRIPTION
        "Notification of Event GW.59

        Message: 'Configuration Changed: Filename $1 Access Type $2 Address $3 User $4 D/T $5'

        Parameters list:
              $1: gw59_filename
              $2: gw59_srctype
              $3: gw59_srcadd
              $4: gw59_user
              $5: gw59_datetime

        Parameters for the last configuration change before last restart."
    ::= { gwNotificationsPrefix 59 }

gwNotification60 NOTIFICATION-TYPE
    OBJECTS { 
              gw60_trapnum 
            }
    STATUS current
    DESCRIPTION
        "Notification of Event GW.60

        Message: 'Event lost, trapnum $1'

        Parameters list:
              $1: gw60_trapnum

        'dotrp' has been called from outside tasker."
    ::= { gwNotificationsPrefix 60 }

gwNotification61 NOTIFICATION-TYPE
    OBJECTS { 
              gw61_interface, 
              gw61_protocol 
            }
    STATUS current
    DESCRIPTION
        "Notification of Event GW.61

        Message: 'Interface $1 discarding packet protocol $2'

        Parameters list:
              $1: gw61_interface
              $2: gw61_protocol

        A buffer was sent to the interface in question, which discarded it
        with no indication of error to the forwarder."
    ::= { gwNotificationsPrefix 61 }

gwNotification62 NOTIFICATION-TYPE
    OBJECTS { 
              gw62_filename, 
              gw62_event 
            }
    STATUS current
    DESCRIPTION
        "Notification of Event GW.62

        Message: 'Firmware file $1 $2'

        Parameters list:
              $1: gw62_filename
              $2: gw62_event

        Firmware file: not found, checksum error, uncompress error, ..."
    ::= { gwNotificationsPrefix 62 }

gwNotification63 NOTIFICATION-TYPE
    STATUS current
    DESCRIPTION
        "Notification of Event GW.63

        Message: 'Reset issued by the user'

        Equipment has been reseted (*restart or *load immediate) by the user."
    ::= { gwNotificationsPrefix 63 }

gwNotification64 NOTIFICATION-TYPE
    OBJECTS { 
              gw64_description 
            }
    STATUS current
    DESCRIPTION
        "Notification of Event GW.64

        Message: '$1'

        Parameters list:
              $1: gw64_description

        Action performed by the licence system"
    ::= { gwNotificationsPrefix 64 }

gwNotification65 NOTIFICATION-TYPE
    OBJECTS { 
              gw65_description 
            }
    STATUS current
    DESCRIPTION
        "Notification of Event GW.65

        Message: 'MPROC $1'

        Parameters list:
              $1: gw65_description

        Multiprocessor subsytem info"
    ::= { gwNotificationsPrefix 65 }

gwNotification66 NOTIFICATION-TYPE
    OBJECTS { 
              gw66_interface, 
              gw66_source,
              gw66_dest,
              gw66_protocol 
            }
    STATUS current
    DESCRIPTION
        "Notification of Event GW.66

        Message: 'Interface $1 has received a packet from $2 to $3, protocol $4'

        Parameters list:
              $1: gw66_interface
              $2: gw66_source
              $3: gw66_dest
              $4: gw66_protocol

        A packet has been received in a interface."
    ::= { gwNotificationsPrefix 66 }

gwNotification67 NOTIFICATION-TYPE
    OBJECTS { 
              gw67_interface 
            }
    STATUS current
    DESCRIPTION
        "Notification of Event GW.67

        Message: 'Incoming packet discarded. The interface is down. Interface $1'

        Parameters list:
              $1: gw67_interface

        The interface is down so the interface entry function has discarded the
        packet."
    ::= { gwNotificationsPrefix 67 }

gwNotification68 NOTIFICATION-TYPE
    STATUS current
    DESCRIPTION
        "Notification of Event GW.68

        Message: 'Restricted console'

        The console is restricted"
    ::= { gwNotificationsPrefix 68 }

gwNotification69 NOTIFICATION-TYPE
    OBJECTS { 
              gw69_fan_name 
            }
    STATUS current
    DESCRIPTION
        "Notification of Event GW.69

        Message: 'Fan '$1' has failed'

        Parameters list:
              $1: gw69_fan_name

        The specified fan has failed."
    ::= { gwNotificationsPrefix 69 }

gwNotification70 NOTIFICATION-TYPE
    OBJECTS { 
              gw70_temperature, 
              gw70_temperature_info 
            }
    STATUS current
    DESCRIPTION
        "Notification of Event GW.70

        Message: 'Router has reached $1—C ($2)'

        Parameters list:
              $1: gw70_temperature
              $2: gw70_temperature_info

        The specified temperature has been reached."
    ::= { gwNotificationsPrefix 70 }

gwNotification71 NOTIFICATION-TYPE
    OBJECTS { 
              gw71_place, 
              gw71_caller 
            }
    STATUS current
    DESCRIPTION
        "Notification of Event GW.71

        Message: 'Buffer overflow in the $1. Caller $2 '

        Parameters list:
              $1: gw71_place
              $2: gw71_caller

        The buffer is overflow."
    ::= { gwNotificationsPrefix 71 }

gwNotification72 NOTIFICATION-TYPE
    OBJECTS { 
              gw72_place, 
              gw72_dump 
            }
    STATUS current
    DESCRIPTION
        "Notification of Event GW.72

        Message: 'Buffer dump $1: $2 '

        Parameters list:
              $1: gw72_place
              $2: gw72_dump

        Buffer dump."
    ::= { gwNotificationsPrefix 72 }


END
