IBM-SYSTEM-PROCESSOR-MIB DEFINITIONS ::= BEGIN

IMPORTS
   OBJECT-TYPE
        FROM RFC-1212

   TRAP-TYPE
        FROM RFC-1215

   ibmSystemProcessor,
   Boolean, Uint8, Sint8, Uint16, Sint16, Uint32,
   Sint32, Uint64, Sint64, Real32, Real64, String, Datetime
      FROM IBM-SYSTEM-MIB;
      

--
-- Primitive types
--
Boolean  ::= INTEGER (0..1)
Uint8    ::= INTEGER (0..255)
Sint8    ::= INTEGER (-128..127)
Uint16   ::= INTEGER (0..65535)
Sint16   ::= INTEGER (-32767..32766)
Uint32   ::= INTEGER (0..4294967295)
Sint32   ::= INTEGER (-2147483647..2147483646)
Uint64   ::= OCTET STRING
Sint64   ::= OCTET STRING
Real32   ::= INTEGER (-1..1)
Real64   ::= INTEGER (-1..1)
String   ::= OCTET STRING
Datetime ::= OCTET STRING

ibmSystemProcessorTable OBJECT-TYPE
   SYNTAX         SEQUENCE OF IbmSystemProcessorEntry
   ACCESS         not-accessible
   STATUS         mandatory
   DESCRIPTION    "The IBMPSG_Processor class represents an IBM managed Memory Array"
   REFERENCE      "IBMPSG_Processor"
::= { ibmSystemProcessor 1 }

ibmSystemProcessorEntry OBJECT-TYPE
   SYNTAX         IbmSystemProcessorEntry
   ACCESS         not-accessible
   STATUS         mandatory
   DESCRIPTION    "This class defines an entry for each IBMPSG_Processor
                    instance. Each instance of the IBMPSG_Processor class 
                    contains status and descriptive information for each memory 
                    bank recognized by the operating system."
   INDEX          { ibmSystemProcessorKeyIndex }
::= { ibmSystemProcessorTable 1 }

IbmSystemProcessorEntry ::= SEQUENCE
{
   ibmSystemProcessorKeyIndex String,   
   ibmSystemProcessorManufacturer String,
   ibmSystemProcessorFamily Uint16,
   ibmSystemProcessorStepping String,
   ibmSystemProcessorDescription String,
   ibmSystemProcessorCurrentClockSpeed Uint32,
   ibmSystemProcessorMaxClockSpeed Uint32,
   ibmSystemProcessorAddressWidth Uint16,
   ibmSystemProcessorDataWidth Uint16,
   ibmSystemProcessorPowerManagementSupported Boolean,
   ibmSystemProcessorUpgradeMethod Uint16,
   ibmSystemProcessorDeviceID String,
   ibmSystemProcessorUniqueID String,
   ibmSystemProcessorCPUStatus Uint16,
   ibmSystemProcessorStatus String
}

ibmSystemProcessorKeyIndex OBJECT-TYPE
   SYNTAX         String
   ACCESS         read-write
   STATUS         mandatory
   DESCRIPTION    ""
   REFERENCE      "IBMPSG_Processor.KeyIndex"
::= { ibmSystemProcessorEntry 1 }

ibmSystemProcessorManufacturer OBJECT-TYPE
   SYNTAX         String
   ACCESS         read-write
   STATUS         mandatory
   DESCRIPTION    ""
   REFERENCE      "IBMPSG_Processor.Manufacturer"
::= { ibmSystemProcessorEntry 2 }

ibmSystemProcessorFamily OBJECT-TYPE
   SYNTAX         Uint16
   ACCESS         read-write
   STATUS         mandatory
   DESCRIPTION    "The Processor family type."
   REFERENCE      "IBMPSG_Processor.Family"
::= { ibmSystemProcessorEntry 3 }

ibmSystemProcessorStepping OBJECT-TYPE
   SYNTAX         String
   ACCESS         read-write
   STATUS         mandatory
   DESCRIPTION    "Stepping is a free-form string indicating the revision level of the Processor within the Processor Family."
   REFERENCE      "IBMPSG_Processor.Stepping"
::= { ibmSystemProcessorEntry 4 }

ibmSystemProcessorDescription OBJECT-TYPE
   SYNTAX         String
   ACCESS         read-write
   STATUS         mandatory
   DESCRIPTION    ""
   REFERENCE      "IBMPSG_Processor.Description"
::= { ibmSystemProcessorEntry 5 }

ibmSystemProcessorCurrentClockSpeed OBJECT-TYPE
   SYNTAX         Uint32
   ACCESS         read-write
   STATUS         mandatory
   DESCRIPTION    "The current speed (in MHz) of this Processor."
   REFERENCE      "IBMPSG_Processor.CurrentClockSpeed"
::= { ibmSystemProcessorEntry 6 }

ibmSystemProcessorMaxClockSpeed OBJECT-TYPE
   SYNTAX         Uint32
   ACCESS         read-write
   STATUS         mandatory
   DESCRIPTION    "The maximum speed (in MHz) of this Processor."
   REFERENCE      "IBMPSG_Processor.MaxClockSpeed"
::= { ibmSystemProcessorEntry 7 }

ibmSystemProcessorAddressWidth OBJECT-TYPE
   SYNTAX         Uint16
   ACCESS         read-write
   STATUS         mandatory
   DESCRIPTION    "Processor address width in bits."
   REFERENCE      "IBMPSG_Processor.AddressWidth"
::= { ibmSystemProcessorEntry 8 }

ibmSystemProcessorDataWidth OBJECT-TYPE
   SYNTAX         Uint16
   ACCESS         read-write
   STATUS         mandatory
   DESCRIPTION    "Processor data width in bits."
   REFERENCE      "IBMPSG_Processor.DataWidth"
::= { ibmSystemProcessorEntry 9 }

ibmSystemProcessorPowerManagementSupported OBJECT-TYPE
   SYNTAX         Boolean
   ACCESS         read-write
   STATUS         mandatory
   DESCRIPTION    ""
   REFERENCE      "IBMPSG_Processor.PowerManagementSupported"
::= { ibmSystemProcessorEntry 10 }

ibmSystemProcessorUpgradeMethod OBJECT-TYPE
   SYNTAX         Uint16
   ACCESS         read-write
   STATUS         mandatory
   DESCRIPTION    "CPU socket information including data on how this Processor can be upgraded (if upgrades are supported)."
   REFERENCE      "IBMPSG_Processor.UpgradeMethod"
::= { ibmSystemProcessorEntry 11 }

ibmSystemProcessorDeviceID OBJECT-TYPE
   SYNTAX         String
   ACCESS         read-write
   STATUS         mandatory
   DESCRIPTION    ""
   REFERENCE      "IBMPSG_Processor.DeviceID"
::= { ibmSystemProcessorEntry 12 }

ibmSystemProcessorUniqueID OBJECT-TYPE
   SYNTAX         String
   ACCESS         read-write
   STATUS         mandatory
   DESCRIPTION    "A globally unique identifier for the Processor. This identifier may only be unique within a Processor Family."
   REFERENCE      "IBMPSG_Processor.UniqueID"
::= { ibmSystemProcessorEntry 13 }

ibmSystemProcessorCPUStatus OBJECT-TYPE
   SYNTAX         Uint16
   ACCESS         read-write
   STATUS         mandatory
   DESCRIPTION    "The CPUStatus property indicates the current status of the Processor. For example, it may be disabled by the user via BIOS (value=2), or disabled due to a POST error (value=3). Information in this property can be obtained from SMBIOS, the Type 4 structure, the Status attribute."
   REFERENCE      "IBMPSG_Processor.CPUStatus"
::= { ibmSystemProcessorEntry 14 }

ibmSystemProcessorStatus OBJECT-TYPE
   SYNTAX         String
   ACCESS         read-write
   STATUS         mandatory
   DESCRIPTION    "The current Status of the CPU."
   REFERENCE      "IBMPSG_Processor.Status"
::= { ibmSystemProcessorEntry 15 }


END
