TROPIC-OPTICALPORT-MIB DEFINITIONS ::= BEGIN

-- (c) Copyright 2016 Nokia.  All rights reserved.
-- This software is the confidential and proprietary property of
-- Nokia and may only be used in accordance with the
-- terms of the license agreement provided with this software.

 IMPORTS  
      SnmpAdminString                         FROM SNMP-FRAMEWORK-MIB
      OBJECT-TYPE, MODULE-IDENTITY,
      Unsigned32, Integer32, Counter64,        
      TimeTicks                               FROM SNMPv2-SMI
      MODULE-COMPLIANCE, OBJECT-GROUP         FROM SNMPv2-CONF
      TEXTUAL-CONVENTION,
      TruthValue                              FROM SNMPv2-TC
      InterfaceIndex, InterfaceIndexOrZero,
      ifIndex                                 FROM IF-MIB
      TnSfpType,
      TnApsGroupId, TnSfpModuleState,
      TnOchStatus, AluWdmTnIfType,
      TropicCardCLEI,
      TropicCardManufacturingPartNumber,
      TropicCardSerialNumber,
      AluWdmDisabledEnabled,
      AluWdmEnabledDisabled,
      TnCommand,
      AluWdmTtiStatus,
      AluWdmDMInfoCurrentStatus,
      AluWdmFecMode,
      AluWdmPortOchOtuRate                    FROM TROPIC-TC
      tnChannel, tnDirection                  FROM TROPIC-WAVEKEY-MIB
      tnPortModules, tnOpticalPortMIB         FROM TROPIC-GLOBAL-REG;

  tnOpticalPortMibModules MODULE-IDENTITY
      LAST-UPDATED    "201609201200Z"
      ORGANIZATION    "Nokia"
      CONTACT-INFO    "Nokia
                       Postal: 600 March Rd.
                       Kanata, Ontario
                       Canada K2K 2E6

                       Phone: +1 613 591 3600
                       Fax:   +1 613 591 3680"

      DESCRIPTION "Optical Port MIB types."

      REVISION    "200802041200Z"
      DESCRIPTION "Change the AHPHG and ALPHG port function SYNTAX
                   value dcm to toDcm and fromDcm."

      REVISION    "200802161200Z"
      DESCRIPTION "Added port specific attributes to the CWR8 port tables."

      REVISION    "200803061200Z"
      DESCRIPTION "Added OT port specific attributes."

      REVISION    "200803101200Z"
      DESCRIPTION "Updated OT port specific attribute descriptions."

      REVISION    "200803141200Z"
      DESCRIPTION "Changed the AHPHG, ALPHG and DCM port tables
                   such that the 2 DCM ports are consolidated into 1."

      REVISION    "200803201200Z"
      DESCRIPTION "1) Renamed OMD44 to SFD44.
                   2) Renamed 11GBART to 11STAR1.
                   3) Renamed 12XGBET to 11STGE12.
                   4) Renamed 12XGBEP2 to 11DPGE12.
                   5) Renamed 10XANYT to 11STMM10.
                   6) Renamed OPS to OPSA.
                   7) Removed 11GUART.
                   8) Added the OSC SFP table."

      REVISION    "200803281200Z"
      DESCRIPTION "1) Added common ingress power to the wave key table.
                   2) Added value unknown to tnOscSfpPortType.
                   3) Changed the following attributes from Unsigned32
                      to INTEGER:
                      tnDwdmCmnLinePortTransmissionMode
                      tnDwdmCmnLinePortOdu2OchSignalDefConsequenceAction
                      tnDwdmCmnLinePortOtu2TimDetectionMode
                      tnDwdmCmnLinePortOdu2MappingMode
                      tnDwdmCmnLinePortOdu2TimDetectionMode
                      tnDwdmCmnClientPortOtu2TimDetectionMode
                   4) Added tnDwdmGpPhyPortConfigTable."

      REVISION    "200804021200Z"
      DESCRIPTION "Changed the FEC mode values in the DWDM Line and
                   Client port FEC attributes."

      REVISION    "200804051200Z"
      DESCRIPTION "1) Added tnWaveKeyPortOutDeviation for FOADM SCOT.
                   2) Changed tnDwdmCmnLinePortOdu2PlmConsequenceAction
                      from Unsigned32 to TruthValue.
                   3) Changed the tnDwdmCmnLinePortFrequency range low
                      from 1 to 0.
                   4) Changed the tnDwdmCmnClientPortLosProp SYNTAX
                      values to laserOn and laserOff.
                   5) Changed the tnDwdmCmnClientPortOchOtu2Rate SYNTAX
                      to INTEGER with values:
                      otm10G709
                      otm11G049
                      otm11G096
                      otm11G27
                   6) Changed the tnOscSfpPortType SYNTAX values to:
                      unknown
                      oc3sh
                      oc3lh
                      oc3ulh
                      fxsh
                      fxlh
                      fxulh
                   7) Added the following to tnDwdmGpPhyPortConfigTable:
                      tnDwdmGpPhyPortErroredFrameDrop
                      tnDwdmGpPhyPortAutoNegotiation.
                   8) Added tnGccPortConfigTable."

      REVISION    "200804111200Z"
      DESCRIPTION "1) Added the remote inventory to the SFP info table.
                   2) Added the following to tnDwdmGpPhyPortInfoTable:
                      tnDwdmGpPhyPortAutoNegotiationStatus.
                   3) Added OPSA port specific attributes.
                   4) Added the following to tnDwdmCmnClientPortConfigTable:
                      tnDwdmCmnClientPortOdu2TransmittedTti
                      tnDwdmCmnClientPortOdu2ExpectedTti
                      tnDwdmCmnClientPortOdu2TimDetectionMode
                   5) Changed SYNTAX of tnDwdmCmnClientPortOtu2TimConsequenceAction
                      to an enumerated integer (disabled, enabled).
                   6) Added the Far-End Time Slot Map against line ports.
                   7) Changed tnWaveKeyPortOutDeviation to:
                      tnWaveKeyPortDefaultPowerDeviationIn,
                      tnWaveKeyPortDefaultPowerDeviationOut.
                   8) Added the following to tnDwdmCmnLinePortInfoTable:
                      tnDwdmCmnLinePortOtu2IncomingTti
                      tnDwdmCmnLinePortOtu2TtiStatus
                      tnDwdmCmnLinePortOdu2IncomingTti
                      tnDwdmCmnLinePortOdu2TtiStatus.
                   9) Added the following to tnRsmonIngrPortInfoTable:
                      tnRsmonIngrPortIncomingTti
                      tnRsmonIngrPortTtiStatus."

      REVISION    "200805021200Z"
      DESCRIPTION "1) Changed Line Loopback to Facility Loopback.
                   2) Updated the tnOpsaPortTransmitAttenuation description.
                   3) Changed the tnDwdmGpPhyPortAutoNegotiationStatus enum
                      values.
                   4) Changed the minimum configurable range of
                      tnDwdmCmnLinePortOdu2PayloadType to 0.
                   5) Added the following to tnDwdmCmnClientPortInfoTable:
                      tnDwdmCmnClientPortOtu2IncomingTti
                      tnDwdmCmnClientPortOtu2TtiStatus
                      tnDwdmCmnClientPortOdu2IncomingTti
                      tnDwdmCmnClientPortOdu2TtiStatus."

      REVISION    "200805221200Z"
      DESCRIPTION "Changed the description of the SFP port tables."

      REVISION    "200805291200Z"
      DESCRIPTION "1) Marked tnDwdmCmnLinePortFrequency as to be obsoleted.
                   2) Added auto and user to tnDwdmCmnPortXfpType.
                   3) Added tnOtPortInfoTable."

      REVISION    "200806051200Z"
      DESCRIPTION "1) Added the following to tnDwdmCmnPortXfpType:
                      ctSul11(43)
                      ct1000BT(44)
                      ct1000BSX(45)
                      ct1000BLX(46)
                      ct1000BZX(47)
                      ctSl162D(48)
                      ct10GBSR(49)
                      ctXL642C(50)
                      ctXL642D(51)
                      ctXS642b(52)
                      ct2FCSNI(53)
                      ct2FCLCL(54)
                      ct4FCSNI(55)
                      ct4FCLCL(56)
                   2) Changed tnMsmonPortAdaptationType to tnMsmonPortMappingMode.
                   3) Deleted tnDwdmCmnLinePortFrequency."

      REVISION    "200806091200Z"
      DESCRIPTION "1) Marked tnOscSfpPortType as to be deleted.
                   2) Marked tnDwdmCmnLinePortLoopType as to be deleted.
                   3) Added the following to tnDwdmCmnPortXfpType:
                      unknown(57)
                      ctOc3sh(58)
                      ctOc3lh(59)
                      ctOc3ulh(60)
                      ctFxsh(61)
                      ctFxlh(62)
                      ctFxulh(63)
                   4) Updated the descriptions of tnDwdmCmnClientPortTs1 and
                      tnDwdmCmnClientPortTs2.
                   5) Added the following to tnDwdmGpPhyPortConfigTable:
                      tnDwdmGpPhyPortPacketFcMode."

      REVISION    "200806111200Z"
      DESCRIPTION "Added the SVAC, SFD and SFC port function attributes."

      REVISION    "200806121200Z"
      DESCRIPTION "Added the EXP port type to the SFD (except SFD44) and
                   SFC (except SFC8) port function attributes."

      REVISION    "200806171200Z"
      DESCRIPTION "Added tnVtsPortConfigTable."

      REVISION    "200806251200Z"
      DESCRIPTION "1) Added the following to tnWaveKeyPortInfoTable:
                      tnWaveKeyPortNwPowerIn
                      tnWaveKeyPortNwPowerOut.
                   2) Added the following to tnDwdmCmnClientPortConfigTable:
                      tnDwdmCmnClientPortProtectionTs1
                      tnDwdmCmnClientPortProtectionTs2."

      REVISION    "200807241200Z"
      DESCRIPTION "Added SFC1 port function attributes."

      REVISION    "200807251200Z"
      DESCRIPTION "1) Corrected the 11DPGE12 current configurable range for
                      tnDwdmCmnClientPortTs1.
                   2) Adjusted the values of tnDwdmCmnPortXfpType.
                   3) Added the following to tnRsmonIngrPortConfigTable:
                      tnRsmonIngrPortTimConsequenceAction
                      tnRsmonIngrPortTimDetectionMode."

      REVISION    "200807281200Z"
      DESCRIPTION "Added new moduletypes to tnDwdmCmnPortXfpType and
                   re-ordered the enum list."

      REVISION    "200808181200Z"
      DESCRIPTION "Added XS64.2_C to tnDwdmCmnPortXfpType and mapped
                   ctXS642b to CT_XS_642."

      REVISION    "200809021200Z"
      DESCRIPTION "1) Added the following to tnDwdmCmnPortXfpType:
                      ctSul120(82),
                      ctSs1620(83),
                      ctSl1620(84).
                   2) Added the following tables:
                      tnOmdPortConfigTable
                      tnOmdPortInfoable."

      REVISION    "200810071200Z"
      DESCRIPTION "Changed SYNTAX of the following from SnmpAdminString
                   to OCTET STRING:
                   tnRsmonIngrPortExpectedTti
                   tnRsmonIngrPortIncomingTti
                   tnRsmonIngrPortTransmittedTti."

      REVISION    "200810161200Z"
      DESCRIPTION "Marked the following as deprecated:
                   tnDwdmCmnLinePortLoopType
                   tnOscSfpPortType
                   tnWssX9PortTotalNwPowerIn
                   tnWssX9PortTotalNwPowerOut
                   tnCwr8PortTotalNwPowerIn
                   tnCwr8PortTotalNwPowerOut."

      REVISION    "200810211200Z"
      DESCRIPTION "1) Changed ctSul120(82), ctSs1620(83), and ctSl1620(84)
                      in tnDwdmCmnPortXfpType from trailing 0 to the
                      letter O.
                   2) Changed ge10Cbr11095 to ge10Cbr11096 in
                      tnDwdmGpPhyPortPacketIfType."

      REVISION    "200811121200Z"
      DESCRIPTION "Changed SYNTAX of the following from SnmpAdminString
                   to OCTET STRING:
                   tnDwdmCmnClientPortOdu2ExpectedTti
                   tnDwdmCmnClientPortOdu2IncomingTti
                   tnDwdmCmnClientPortOdu2TransmittedTti
                   tnDwdmCmnClientPortOtu2ExpectedTti
                   tnDwdmCmnClientPortOtu2IncomingTti
                   tnDwdmCmnClientPortOtu2TransmittedTti
                   tnDwdmCmnLinePortOdu2ExpectedTti
                   tnDwdmCmnLinePortOdu2IncomingTti
                   tnDwdmCmnLinePortOdu2TransmittedTti
                   tnDwdmCmnLinePortOtu2ExpectedTti
                   tnDwdmCmnLinePortOtu2IncomingTti
                   tnDwdmCmnLinePortOtu2TransmittedTti."

      REVISION    "200811231200Z"
      DESCRIPTION "Changed description of tnDwdmCmnPortXfpType from
                   The XFP type
                   to
                   The programmed XFP or SFP type."

      REVISION    "200812161200Z"
      DESCRIPTION "Added the following to tnOpsaPortConfigTable:
                   tnOpsaPortSwitchingThreshCalcControl."

      REVISION    "200901051200Z"
      DESCRIPTION "Changed lower bound of tnOpsaPortSwitchingThreshold
                   from -2500 to -3000."

      REVISION    "200902201200Z"
      DESCRIPTION "Added OTU1/ODU1 attributes for client ports for
                   11STMM10."

      REVISION    "200903011200Z"
      DESCRIPTION "Used the following common enums:
                   AluWdmDisabledEnabled
                   AluWdmPortLaserTunability
                   AluWdmPortOchOtuRate
                   AluWdmTimDetectionMode
                   AluWdmMappingMode."

      REVISION    "200903011200Z"
      DESCRIPTION "Added support for the 4DPA4 card and OTU1/ODU1
                   attributes for line ports for this pack."

      REVISION    "200903021200Z"
      DESCRIPTION "1) Renamed tnOmdPortInfoGroup to <tnOpticalPortInfoGroups
                      73>.
                   2) Moved definition of tnOmdPortInfoGroup to the
                      <Conformance Port Info Group Definitions> section.
                   3) Add the following to AluWdmPortOchOtuRate:
                      otm2G66(5)."

      REVISION    "200903031200Z"
      DESCRIPTION "Used AluWdmDisabledEnabled common enum in TROPIC-TC."

      REVISION    "200903041200Z"
      DESCRIPTION "Renamed tnDwdmCmnClientPortTimeSlotMap to
                   tnDwdmCmnClientPortTsMap."

      REVISION    "200903091200Z"
      DESCRIPTION "1) Removed the following XFP/SFP types defined in
                      tnDwdmCmnPortXfpType:
                      ctOc3sh(85)
                      ctOc3lh(86)
                      ctOc3ulh(87)
                      ctFxsh(88)
                      ctFxlh(89)
                      ctFxulh(90)
                      unknown(91).
                   2) Added the following new XFP/SFP types:
                      ctEvoaFast(85)
                      ctEvoaSlow(86).
                   3) Changed otm226 to otm2G66."

      REVISION     "200903151200Z"
      DESCRIPTION  "Added the CWR8-88, SFD44B, and ITLB cards."

      REVISION     "200903181200Z"
      DESCRIPTION  "Added the AHPLG card."

      REVISION    "200903221200Z"
      DESCRIPTION "Removed tnDwdmCmnLinePortFarEndTimeSlotMap."

      REVISION    "200903221200Z"
      DESCRIPTION "1) Added the following to
                      tnDwdmCmnLinePortTransmissionMode:
                      crossRegen(6).
                   2) Added the following to tnDwdmGpPhyPortPacketFcMode:
                      isc(3).
                   3) Added the following to
                      tnDwdmCmnOtu1Odu1LinePortConfigTable:
                      tnDwdmCmnLinePortOdu1OdukInterwork.
                   4) Added the following to tnRsmonIngrPortConfigTable:
                      tnRsmonIngrPortSigMode."

      REVISION    "200903241200Z"
      DESCRIPTION "1) Renamed tnDwdmCmnLinePortOdu1OdukInterwork to
                      tnDwdmCmnLinePortOdu1Interworking.
                   2) Added table and attributes for NETSMAP/FETSMAP."

      REVISION    "200903251200Z"
      DESCRIPTION "Moved OTU1/ODU1 attributes to new tables."

      REVISION    "200903311200Z"
      DESCRIPTION "Added support for the 43Stx4 card and OTU3/ODU3
                   attributes for this pack."

      REVISION    "200904071200Z"
      DESCRIPTION "Moved tnDwdmCmnClientPortTsMap from
                   TnDwdmCmnOtu1Odu1ClientPortConfigEntry to
                   tnDwdmCmnClientPortConfigGroup."

      REVISION    "200904231200Z"
      DESCRIPTION "1) Added the following to tnDwdmCmnLinePortInfoTable:
                      tnDwdmCmnLinePortAvailableBandwidth.
                   2) Added the following to tnDwdmCmnClientPortInfoTable:
                      tnDwdmCmnClientPortAvailableBandwidth."

      REVISION    "200904241200Z"
      DESCRIPTION "Added the following to tnDwdmCmnPortXfpType:
                   ct10GBZR(87),
                   ct100BLX10(88)."

      REVISION    "200904271200Z"
      DESCRIPTION "1) Added tn11dpge12PortAvailableBandwidth
                      to replace both tnDwdmCmnLinePortAvailableBandwidth
                      and tnDwdmCmnClientPortAvailableBandwidth
                      because of moving these attributes from
                      tnDwdmCmn*PortInfoTable to 11dpge12PortInfoTable.
                   2) Marked the following as deprecated:
                      tnDwdmCmnLinePortAvailableBandwidth
                      and tnDwdmCmnClientPortAvailableBandwidth."

      REVISION    "200905051200Z"
      DESCRIPTION "Added the following to tnSfpPortInfoTable:
                   tnSfpMaximumCaseTemperature."

      REVISION    "200905061200Z"
      DESCRIPTION "1) Renamed tnSfpMaximumCaseTemperature to
                      tnSfpPortMaximumCaseTemperature and changed its
                      SYNTAX to Integer32.
                   2) Added descriptions to the attributes in
                      tnSfpPortInfoTable."

      REVISION    "200905141200Z"
      DESCRIPTION "Updated description for tnSfpPortDate."

      REVISION    "200905211200Z"
      DESCRIPTION "Added the following to tnNetworkPortConfigTable:
                   tnNwPortProgrammedChannelRx."

      REVISION    "200905311200Z"
      DESCRIPTION "Ranamed tnNwPortProgrammedChannelRx as
                   tnNwPortChannelRx and changed it from read-create
                   to read-only."

      REVISION    "200906121200Z"
      DESCRIPTION "Marked tnRsmonIngrPortTimDetectionMode as to be obsoleted."

      REVISION    "200908281200Z"
      DESCRIPTION "Changed tnNwPortChannelRx from read-only to read-create."

      REVISION    "200909091200Z"
      DESCRIPTION "Fixed typo of tnDwdmCmnLinePortOdu1TimDetectionMode
                   in tnDwdmCmnOtu3Odu3LinePortConfigGroup."

      REVISION    "200909251200Z"
      DESCRIPTION "1) Added the Alpfgk, 4dpa2, and Sfd8[a-d] cards.
                   2) Changed the Osc card definitions for 1830."

      REVISION    "200909261200Z"
      DESCRIPTION "Added the following to AluWdmPortOchOtuRate:
                   otm4G55(6)."

      REVISION    "200911011200Z"
      DESCRIPTION "1) Added the 43sta1p and 43stx4p cards.
                   2) Added the following to
                      tnDwdmCmnOtu3Odu3LinePortConfigTable:
                      tnDwdmCmnLinePortOdu3MappingMode."

      REVISION    "200911031200Z"
      DESCRIPTION "Added tnRsmonEgrPortInfoTable for OC48, STM16, and
                   1GBE for line ports for 4DPA2."

      REVISION    "200911181200Z"
      DESCRIPTION "1) Added the following to tnOmdPortConfigTable:
                      tnOmdPortLosOutThreshold
                      tnOmdPortLosOutThresholdTolerance.
                   2) Added the following to tnOmdPortInfoTable:
                      tnOmdPortTransmittedPower.
                   3) Updated descriptions for tnOmdPortLosThreshold,
                      tnOmdPortLosThresholdTolerance, and
                      tnOmdPortReceivedPower."

      REVISION    "200912171200Z"
      DESCRIPTION "Added the following to tnDwdmCmnPortXfpType:
                   ctSEU12O(89)."

      REVISION    "200912111200Z"
      DESCRIPTION "1) Added the 11qpa4, Sfd40, Sfd40b, and A2325a cards.
                   2) Added the following to tnOscSfpPortConfigTable:
                      tnOscSfpTemperature.
                   2) Added the following to tnOtPortInfoTable:
                      tnOtPortBias
                      tnOtPortTemperature.
                   3) Added the following to tnDwdmCmnLinePortConfigTable:
                      tnDwdmCmnLinePortCrossRegPartner
                      tnDwdmCmnLinePortBroadcastFrom.
                   4) Added the following to tnDwdmCmnClientPortInfoTable:
                      tnDwdmCmnClientPortBroadcastPortMap."

      REVISION    "200912281200Z"
      DESCRIPTION "Added the following to tnPortInfoTable:
                   tnOtPortTxPowerLaser."

      REVISION    "201001041200Z"
      DESCRIPTION "1) Added the 112scx10 and 112sca1 cards.
                   2) Added the following to AluWdmPortOchOtuRate:
                      otm111G810(7).
                   3) Added OTU4/ODU4 attributes to new tables:
                      tnDwdmCmnLinePortOchOtu4FecMode
                      tnDwdmCmnLinePortOchOtu4Rate
                      tnDwdmCmnLinePortOtu4TransmittedTti
                      tnDwdmCmnLinePortOtu4ExpectedTti
                      tnDwdmCmnLinePortOtu4TimConsequenceAction
                      tnDwdmCmnLinePortOtu4TimDetectionMode
                      tnDwdmCmnClientPortOchOtu4FecMode
                      tnDwdmCmnClientPortOchOtu4Rate
                      tnDwdmCmnClientPortOtu4TransmittedTti
                      tnDwdmCmnClientPortOtu4ExpectedTti
                      tnDwdmCmnClientPortOtu4TimConsequenceAction
                      tnDwdmCmnClientPortOtu4TimDetectionMode
                      tnDwdmCmnLinePortOdu4PayloadType
                      tnDwdmCmnLinePortOdu4PlmConsequenceAction
                      tnDwdmCmnLinePortOdu4TransmittedTti
                      tnDwdmCmnLinePortOdu4ExpectedTti
                      tnDwdmCmnLinePortOdu4TimConsequenceAction
                      tnDwdmCmnLinePortOdu4TimDetectionMode
                      tnDwdmCmnClientPortOdu4TransmittedTti
                      tnDwdmCmnClientPortOdu4ExpectedTti
                      tnDwdmCmnClientPortOdu4TimDetectionMode
                      tnDwdmCmnClientPortOtu4IncomingTti
                      tnDwdmCmnClientPortOtu4TtiStatus
                      tnDwdmCmnClientPortOdu4IncomingTti
                      tnDwdmCmnClientPortOdu4TtiStatus."

      REVISION    "201001081200Z"
      DESCRIPTION "Moved tnRsmonEgrPortTimod and tnRsmonEgrPortSigMode
                   from tnRsmonEgrPortInfoTable to tnRsmonEgrPortConfigTable
                   (new table)."

      REVISION    "201001131200Z"
      DESCRIPTION "Added the following to tnDwdmCmnOtu4Odu4LinePortInfoTable:
                   tnDwdmCmnLinePortOdu4IncomingTti
                   tnDwdmCmnLinePortOdu4TtiStatus
                   tnDwdmCmnOtu4Odu4LinePortInfoTable."

      REVISION    "201001151200Z"
      DESCRIPTION "Added the following to tnDwdmCmnPortXfpType:
                   ctXl64Tu(90),
                   ctBncdvRx(91),
                   ctBncdvTx(92)."

      REVISION    "201001241200Z"
      DESCRIPTION "Marked the following as obsolete:
                   tnDwdmCmnClientPortLoopType
                   tnDwdmCmnLinePortLoopType."

      REVISION    "201002021200Z"
      DESCRIPTION "Added the following to AluWdmFecMode:
                   aFec(6)."

      REVISION    "201002041200Z"
      DESCRIPTION "Updated descriptions for tnOtPortTxPower and
                   tnOtPortTxPowerLaser."

      REVISION    "201002091200Z"
      DESCRIPTION "Added the evoa port to tn11dpge12PortConfigFunction and
                   tn11dpge12PortInfoFunction."

      REVISION    "201002161200Z"
      DESCRIPTION "1) Added the following to tnDwdmCmnPortXfpType:
                      ctC113G4C(93),
                      ctC113G10C(94).
                   2) Added tnDwdmCbrArPortHdsdiRate to a new table,
                      tnDwdmCbrArPortConfigTable."

      REVISION    "201002171200Z"
      DESCRIPTION "Added the Alpfgt and OscT cards."

      REVISION    "201002191200Z"
      DESCRIPTION "Added the following to tnDwdmCmnPortXfpType:
                   ct4FCOC(95),
                   ct4FCOD(96)."

      REVISION    "201002251200Z"
      DESCRIPTION "1) Marked the following OSC attributes as deprecated:
                      tnOscPortPhyDeviceReset
                      tnOscPortTotalNwPowerIn
                      tnOscPortTotalNwPowerOut
                      tnOscPortPhyDeviceLinkStatus
                      tnOscPortPhyDeviceIdNo
                      tnOscPortPhyDeviceMfgModelNo
                      tnOscPortPhyDeviceMfgRevNo.
                   2) Deleted the following OSCT attributes:
                      tnOsctPortPhyDeviceReset
                      tnOsctPortTotalNwPowerIn
                      tnOsctPortTotalNwPowerOut
                      tnOsctPortPhyDeviceLinkStatus
                      tnOsctPortPhyDeviceIdNo
                      tnOsctPortPhyDeviceMfgModelNo
                      tnOsctPortPhyDeviceMfgRevNo."

      REVISION    "201003011200Z"
      DESCRIPTION "Added the following to tnDwdmCmnPortXfpType:
                   ctGeBx20U(97),
                   ctGeBx20D(98),
                   ctGeBx40U(99),
                   ctGeBx40D(100),
                   ctFeBx40U(101),
                   ctFeBx40D(102)."

      REVISION    "201003051200Z"
      DESCRIPTION "Added the following to tnDwdmCmnPortXfpType:
                   ctL642(103)."

      REVISION    "201003311200Z"
      DESCRIPTION "Marked tnDwdmCmnClientPortOdu4IncomingTti and
                   tnDwdmCmnClientPortOdu4TtiStatus in
                   tnDwdmCmnOtu4Odu4ClientPortConfigTable as obsolete
                   and added these two attributes to
                   tnDwdmCmnOtu4Odu4ClientPortInfoTable."

      REVISION    "201005101200Z"
      DESCRIPTION "1) Added the Wtocm and Wr2c88 cards.
                   2) Added the following to tn11dpge12PortInfoTable:
                      tn11dpge12PortTotalVTS.
                   3) Added backplane(4) port for the 11dpe12 pack.
                   4) Added the following to tnDwdmGpPhyPortPacketIfType:
                      ge10(21)."

      REVISION    "201006041200Z"
      DESCRIPTION "1) Added the Am2017b, Am2325b, and 1dpp21 cards.
                   2) Added E1 signal table."

      REVISION    "201006071200Z"
      DESCRIPTION "Added the following to tnRsmonEgrPortConfigTable:
                   tnRsmonEgrPortTransmittedTti
                   tnRsmonEgrPortExpectedTti
                   tnRsmonEgrPortTimDetection
                   tnRsmonEgrPortTimConsequenceAction."

      REVISION    "201006101200Z"
      DESCRIPTION "1) Added the following to tnGccPortConfigTable:
                      tnGccMtu
                      tnGccStd.
                   2) Added the following to tnOscSfpPortConfigTable:
                      tnOscMtu."

      REVISION    "201006161200Z"
      DESCRIPTION "1) Added the following to tnRsmonEgrPortInfoTable:
                      tnRsmonEgrPortTtiStatus.
                   2) Corrected SYNTAX for the following attributes:
                      tnOpsaPortSwitchingThreshCalcControl
                      tnDwdmCmnClientPortOchOtu1Rate
                      tnDwdmCmnClientPortOchOtu2Rate
                      tnDwdmCmnClientPortOchOtu4Rate."

      REVISION    "201006231200Z"
      DESCRIPTION "Corrected inconsistent type declarations."

      REVISION    "201006281200Z"
      DESCRIPTION "1) Added the Sfd4[a-h] cards.
                   2) Added the following to tnWaveKeyPortInfoTable:
                      tnWavekeyPortWTDecoderUsageStatusIn
                      tnWavekeyPortWTDecoderUsageStatusOut."

      REVISION    "201007111200Z"
      DESCRIPTION "Added the following to tnSfpPortInfoTable:
                   tnSfpPortInterchangeabilityMarking
                   tnSfpPortAcronymCode."

      REVISION    "201007151200Z"
      DESCRIPTION "Changed tnSfpPortModuleVendorSerNo from 16 to 18 bytes."

      REVISION    "201007201200Z"
      DESCRIPTION "1) Added the Mvac card.
                   2) Added the following to tnE1T1PortConfigTable:
                      tnE1T1ClientEgressTimingMode."

      REVISION    "201007211200Z"
      DESCRIPTION "Added the following to tnWtocmPortInfoTable:
                   tnWtocmPortInfoPower
                   tnWtocmPortInfoPowerMonitoredPort."

      REVISION    "201007291200Z"
      DESCRIPTION "1) Added the following to tnDwdmCmnLinePortInfoTable:
                      tnDwdmCmnLinePortOtu2PostFec
                      tnDwdmCmnLinePortOtu2PreFec.
                   2) Added the following to tnDwdmCmnClientPortInfoTable:
                      tnDwdmCmnClientPortOtu2PreFec
                      tnDwdmCmnClientPortOtu2PostFec.
                   3) Added the following to tnDwdmCmnOtu1Odu1ClientPortInfoTable:
                      tnDwdmCmnClientPortOtu1PreFec
                      tnDwdmCmnClientPortOtu1PostFec.
                   4) Added the following to tnDwdmCmnOtu3Odu3LinePortInfoTable:
                      tnDwdmCmnLinePortOtu3PreFec
                      tnDwdmCmnLinePortOtu3PostFec."

      REVISION    "201008091200Z"
      DESCRIPTION "Added the following to tnDwdmCmnPortXfpType:
                   ct100BFXS(104)."

      REVISION    "201008261200Z"
      DESCRIPTION "1) Added the following to tnGccPortConfigTable:
                      tnGccType.
                   2) Added the following to tnDwdmCmnClientPortInfoTable:
                      tnDwdmCmnClientPortOdu2IncFwFTFLTypeID
                      tnDwdmCmnClientPortOdu2IncFwFTFLOperID
                      tnDwdmCmnClientPortOdu2IncBwFTFLTypeID
                      tnDwdmCmnClientPortOdu2IncBwFTFLOperID
                      tnDwdmCmnClientPortOdu2IncResRow2
                      tnDwdmCmnClientPortOdu2IncResRow4
                      tnDwdmCmnClientPortOdu2IncExp
                      tnDwdmCmnClientPortOtu2IncRes.
                   3) Added the following to tnDwdmCmnLinePortInfoTable:
                      tnDwdmCmnLinePortOdu2IncFwFTFLTypeID
                      tnDwdmCmnLinePortOdu2IncFwFTFLOperID
                      tnDwdmCmnLinePortOdu2IncBwFTFLTypeID
                      tnDwdmCmnLinePortOdu2IncBwFTFLOperID
                      tnDwdmCmnLinePortOdu2IncResRow2
                      tnDwdmCmnLinePortOdu2IncResRow4
                      tnDwdmCmnLinePortOdu2IncExp
                      tnDwdmCmnLinePortOtu2IncRes.
                   4) Added the following to tnDwdmCmnOtu3Odu3LinePortInfoTable:
                      tnDwdmCmnLinePortOdu3IncFwFTFLTypeID
                      tnDwdmCmnLinePortOdu3IncFwFTFLOperID
                      tnDwdmCmnLinePortOdu3IncBwFTFLTypeID
                      tnDwdmCmnLinePortOdu3IncBwFTFLOperID
                      tnDwdmCmnLinePortOdu3IncResRow2
                      tnDwdmCmnLinePortOdu3IncResRow4
                      tnDwdmCmnLinePortOdu3IncExp
                      tnDwdmCmnLinePortOtu3IncRes.
                   5) Added the following to tn11dpge12PortInfoTable:
                      tn11dpge12PortIngAvailableBandwidth
                       tn11dpge12PortEgrAvailableBandwidth."

      REVISION    "201009101200Z"
      DESCRIPTION "Added the 43scx4 card."

      REVISION    "201009161200Z"
      DESCRIPTION "Added range of SFD4 to tnOmdPortLosThreshold."

      REVISION    "201009201200Z"
      DESCRIPTION "Added the Ra2p, Am2318a, Am2125a, Itlu, and Wr8c88a
                   cards."

      REVISION    "201009281200Z"
      DESCRIPTION "1) Added the following to tnDwdmCmnPortXfpType:
                      ctX8FCLCL(105).
                   2) Added the 11dpe12e card."

      REVISION    "201010171200Z"
      DESCRIPTION "Added the 112sx10l and 112sa1l cards."

      REVISION    "201010191200Z"
      DESCRIPTION "Added the 11dpm12 card."

      REVISION    "201010241200Z"
      DESCRIPTION "Added the following new tables:
                   tnWr8c88aAttenPortConfigTable
                   tnRamanPortConfigTable
                   tnRamanPortInfoTable."

      REVISION    "201010251200Z"
      DESCRIPTION "Added the following to tnDwdmCmnPortXfpType:
                   ctC113G4Cd(106)."

      REVISION    "201010261200Z"
      DESCRIPTION "Added the following to tnDwdmGpPhyPortPacketIfType:
                   fc8GfpT(22)."

      REVISION    "201011011200Z"
      DESCRIPTION "Added the following to tnDwdmCmnLinePortConfigTable:
                   tnDwdmCmnLinePortRegenResponse."

      REVISION    "201011091200Z"
      DESCRIPTION "Marked the following as obsolete:
                   tnOscPortPhyDeviceReset
                   tnOscSfpPortType
                   tnOC48STM16PortSfpModulePresentType
                   tnOC48STM16PortSfpModuleVendorSerNo
                   tnOC48STM16PortSfpModuleState
                   tnOC48STM16PortSfpModuleVendor
                   tnOC48STM16PortSfpTxDisable
                   tnOC48STM16PortSfpWavelength
                   tnQuadOC48STM16MuxPortSfpModulePresentType
                   tnQuadOC48STM16MuxPortSfpModuleVendorSerNo
                   tnQuadOC48STM16MuxPortSfpModuleState
                   tnQuadOC48STM16MuxPortSfpModuleVendor
                   tnQuadOC48STM16MuxPortSfpTxDisable
                   tnQuadOC48STM16MuxPortSfpWavelength
                   tnQuadOC3or12STM1or4MuxPortSfpModulePresentType
                   tnQuadOC3or12STM1or4MuxPortSfpModuleVendorSerNo
                   tnQuadOC3or12STM1or4MuxPortSfpModuleState
                   tnQuadOC3or12STM1or4MuxPortSfpModuleVendor
                   tnQuadOC3or12STM1or4MuxPortSfpTxDisable
                   tnQuadOC3or12STM1or4MuxPortSfpWavelength
                   tnOscPortTotalNwPowerIn
                   tnOscPortPhyDeviceLinkStatus
                   tnOscPortPhyDeviceIdNo
                   tnOscPortPhyDeviceMfgModelNo
                   tnOscPortPhyDeviceMfgRevNo
                   tnDualGigEMuxPortSfpModulePresentType
                   tnDualGigEMuxPortSfpModuleVendorSerNo
                   tnDualGigEMuxPortSfpModuleState
                   tnDualGigEMuxPortSfpModuleVendor
                   tnDualGigEMuxPortSfpTxDisable
                   tnDualGigEMuxPortSfpWavelength
                   tnDecaGEMuxPortSfpModulePresentType
                   tnDecaGEMuxPortSfpModuleVendorSerNo
                   tnDecaGEMuxPortSfpModuleState
                   tnDecaGEMuxPortSfpModuleVendor
                   tnDecaGEMuxPortSfpTxDisable
                   tnDecaGEMuxPortSfpWavelength
                   tnWssX9PortTotalNwPowerIn
                   tnWssX9PortTotalNwPowerOut
                   tnCwr8PortTotalNwPowerIn
                   tnCwr8PortTotalNwPowerOut
                   tnDwdmCmnClientPortAvailableBandwidth
                   tnDwdmCmnLinePortAvailableBandwidth."

      REVISION    "201011101200Z"
      DESCRIPTION "1) Added the Mesh4 card.
                   2) Changed the following attributes from deprecated to
                      current:
                      tnOscPortTotalNwPowerIn
                      tnOscPortTotalNwPowerOut
                      tnOscPortPhyDeviceLinkStatus
                      tnOscPortPhyDeviceIdNo
                      tnOscPortPhyDeviceMfgModelNo
                      tnOscPortPhyDeviceMfgRevNo."

      REVISION    "201011141200Z"
      DESCRIPTION "Added the following to tnDwdmCmnClientPortConfigTable:
                   tnDwdmCmnClientPortMappingMode."

      REVISION    "201011221200Z"
      DESCRIPTION "Added the following to tnLoopbackPortTable:
                   tnLoopbackPortTSEB."

      REVISION    "201011231200Z"
      DESCRIPTION "Added the following to tnDwdmCmnOtu4Odu4LinePortInfoTable:
                   tnDwdmCmnLinePortOtu4PreFec
                   tnDwdmCmnLinePortOtu4PostFec."

      REVISION    "201011301200Z"
      DESCRIPTION "Renamed tnDwdmCmnClientPortMappingMode to
                   tnDwdmCmnClientPortContainer."

      REVISION    "201012141200Z"
      DESCRIPTION "Added the following to tnRamanPortConfigTable:
                   tnRamanPortAgcTargetGain."

      REVISION    "201101121200Z"
      DESCRIPTION "1) Updated the upper range of the following from 2000
                      to 2500:
                      tnRamanPortGMinExpected
                      tnRamanPortGMaxExpected.
                   2) Updated the default values of tnRamanPortGMinExpected
                      from 1000 to 700, and tnRamanPortGMaxExpected from
                      2000 to 2500."

      REVISION    "201102101200Z"
      DESCRIPTION "Added the following to tnDwdmCmnPortXfpType:
                   ctX8FCSNI(107)."

      REVISION    "201003251200Z"
      DESCRIPTION "1) Added otm43G018(8) to AluWdmPortOchOtuRate.
                   2) Added the following to tnDwdmCmnPortXfpType:
                      ct3GSDISH(108),
                      ct3GSDIMH(109)."

      REVISION    "201103301200Z"
      DESCRIPTION "Updated default value of tnWr8c88aPortConfigWssAtten
                   from 15 to 1500."

      REVISION    "201105021200Z"
      DESCRIPTION "Added support for Tandem Connection Monitoring (TCM)."

      REVISION    "201105041200Z"
      DESCRIPTION "Added the 43sca1 card."

      REVISION    "201105171200Z"
      DESCRIPTION "1) Added the 43scx4l and Am2125b cards.
                   2) Marked test(5) of Wr8c88a as obsolete.
                   3) Renumbered meshOut(7) as meshOut(5)."

      REVISION    "201105231200Z"
      DESCRIPTION "1) Changed range of tnOpticalFiberDispersionRating
                      from (0, 1000) to (-1, 1000).
                   2) Added range (-2650, -400) for
                      tnCwr8c88PortDropTargetPower.
                   3) Added DEFVAL for the following attributes:
                      tnWaveKeyPortUnexpectedWKThreshAutoModeIngress, true
                      tnWaveKeyPortUnexpectedWKThreshAutoModeEgress, true
                      tnWaveKeyPortUnexpectedWKThreshDeltaIngress, 500
                      tnWaveKeyPortUnexpectedWKThreshDeltaEgress, 500
                      tnWaveKeyPortUnexpectedWKThreshAutoMaxOffsetIn, 1200
                      tnWaveKeyPortUnexpectedWKThreshAutoMaxOffsetOut, 1200
                      tnWaveKeyPortCommonEgressPower, -2000
                      tnWaveKeyPortCommonIngressPower, -2000
                      tnWaveKeyPortDefaultPowerDeviationIn, 150
                      tnWaveKeyPortDefaultPowerDeviationOut, 150
                      tnOpticalFiberFixedLoss, 100
                      tnOpticalFiberLength, -1
                      tnOpticalFiberLossRating, 100
                      tnOpticalFiberDispersionRating, -1
                      tnSdhPortRxSignalDegradeThreshold, 7
                      tnSdhPortRxSignalFailThreshold, 5
                      tnSonetPortRxSignalDegradeThreshold, 7
                      tnSonetPortRxSignalFailThreshold, 5
                      tnDwPortRxRSBERSDThresh, 4
                      tnDwPortRxRSBERSFThresh, 3
                      tnOpsaPortSwitchingThreshold, -3000
                      tnOpsaPortSwitchingThresholdTolerance, 200
                      tnOpsaPortTransmitAttenuation, -1
                      tnCwr8PortBlockerAging, 0
                      tnDwdmCmnLinePortOdu2PayloadType, 253
                      tnOmdPortLosThresholdTolerance, 200
                      tnOmdPortLosOutThresholdTolerance, 200
                      tnCwr8c88PortBlockerAging, 0
                      tnCwr8c88PortDropTargetPower, -1200
                      tnDwdmCmnLinePortOdu1PayloadType, 128
                      tnDwdmCmnLinePortOdu3PayloadType, 32
                      tnWr2c88PortBlockerAging, 0."

      REVISION    "201106301200Z"
      DESCRIPTION "Added the 112snx10 and 112sna1 cards."

      REVISION    "201107021200Z"
      DESCRIPTION "Added the following to tnDwdmCmnPortXfpType:
                   ct1000BT2(110),
                   ctSFEBTEE(111)."

      REVISION    "201107071200Z"
      DESCRIPTION "Added the 11qta4 card."

      REVISION    "201107081200Z"
      DESCRIPTION "Added the following to tn1dpp21PortInfoTable:
                   tn1dpp21PortClockSourceIncomingQLStatus
                   tn1dpp21PortClockSourceIncomingQL."

      REVISION    "201107191200Z"
      DESCRIPTION "Added the 1dpp24m card."

      REVISION    "201107221200Z"
      DESCRIPTION "1) Added AluWdmWTDecoderMeasurementType.
                   2) Added the following to tnWaveKeyPortInfoTable:
                      tnWaveKeyPortWTDecoderMeasurementTypeIn
                      tnWaveKeyPortWTDecoderMeasurementTypeOut.
                   3) Added the following tables:
                      tnDwdmCmnOtu3Odu3ClientPortConfigTable
                      tnDwdmCmnOtu3Odu3ClientPortInfoTable."

      REVISION    "201107291200Z"
      DESCRIPTION "1) Added the following to
                      tnDwdmCmnOtu3Odu3ClientPortInfoTable:
                      tnDwdmCmnClientPortOtu3PreFec
                      tnDwdmCmnClientPortOtu3PostFec.
                   2) Added the following to
                      tnDwdmCmnOtu4Odu4ClientPortInfoTable:
                      tnDwdmCmnClientPortOtu4PreFec
                      tnDwdmCmnClientPortOtu4PostFec."

      REVISION    "201108191200Z"
      DESCRIPTION "1) Added the following to tnE1T1PortConfigTable:
                      tnE1T1PortConfigImpedance.
                   2) Marked the following as deprecated:
                      tnE1T1PortInfoTable
                      tnE1T1PortImpedance."

      REVISION    "201108311200Z"
      DESCRIPTION "Added the ul43scup and ul11qcup cards."

      REVISION    "201109061200Z"
      DESCRIPTION "Added the 11qpen4 card."

      REVISION    "201109161200Z"
      DESCRIPTION "Added the 43scx4e card."

      REVISION    "201109301200Z"
      DESCRIPTION "Marked the following as deprecated:
                   tnWavekeyPortWTDecoderUsageStatusIn
                   tnWavekeyPortWTDecoderUsageStatusOut."

      REVISION    "201110241200Z"
      DESCRIPTION "Added the following to tnDwdmCmnLinePortConfigTable:
                   tnDwdmCmnLinePortDemandName."

      REVISION    "201111021200Z"
      DESCRIPTION "Added the following to tnRamanPortInfoTable:
                   tnRamanPortPump[1-2]Power."

      REVISION    "201111091200Z"
      DESCRIPTION "1) Added the following table:
                      tnWssAttenPortInfoTable.
                   2) Added the following to AluWdmFecMode:
                      eFecI(7),
                      eFecE(8),
                      eFecB(9).
                   3) Added the following to AluWdmPortOchOtuRate:
                      otm44G58(9).
                   4) Added the following to tnDwdmCmnPortXfpType:
                      ctC11G4C(112)."

      REVISION    "201111141200Z"
      DESCRIPTION "1) Added the 43scge1 card.
                   2) Added the following to
                      tnDwdmCmnOtu3Odu3LinePortConfigTable:
                      tnDwdmCmnLinePortOchOtu3Rate."

      REVISION    "201111211200Z"
      DESCRIPTION "Added the 11qpe24 card."

      REVISION    "201112211200Z"
      DESCRIPTION "Marked the following as deprecated:
                   tn1dpp24mPortClockSourceIncomingQLStatus
                   tn1dpp24mPortClockSourceIncomingQL."

      REVISION    "201201101200Z"
      DESCRIPTION "Added the 11star1a and Mvac8b cards."

      REVISION    "201201141200Z"
      DESCRIPTION "1) Added the following to tnDwdmCmnLinePortConfigTable:
                      tnDwdmCmnLinePortOtu2holdofftimer.
                   2) Added the following to tnDwdmCmnOtu3Odu3LinePortConfigTable:
                      tnDwdmCmnLinePortOdu3Interworking.
                   3) Added tnWssAttenPortConfigTable with the following:
                      tnWssAttenPortConfigWssAtten.
                   4) Marked the following as deprecated (replaced by
                      tnWssAttenPortConfigTable):
                      tnWr8c88aAttenPortConfigTable."

      REVISION    "201201181200Z"
      DESCRIPTION "Added the Wr8c88af card."

      REVISION    "201201191200Z"
      DESCRIPTION "Added the cl10an10g and cl24anm cards."

      REVISION    "201201231200Z"
      DESCRIPTION "Added the following to tnDwdmCmnPortXfpType:
                   ctC43G4C(113)."

      REVISION    "201203071200Z"
      DESCRIPTION "Added the following to AluWdmPortOchOtuRate:
                   otm11G317(11)."

      REVISION    "201203151200Z"
      DESCRIPTION "Moved the following to TROPIC-TC:
                   AluWdmTtiStatus."

      REVISION    "201203181200Z"
      DESCRIPTION "1) Added the Opsb card.
                   2) Marked the following as deprecated:
                      tnOpsaPortSwitchingThreshold
                      tnOpsaPortSwitchingThresholdTolerance
                      tnOpsaPortTransmitAttenuation
                      tnOpsaPortSwitchingThreshCalcControl
                      tnOpsaPortReceivedPower
                      tnOpsaPortPresentTransmitAttenuation.
                   3) Added the following scalars and tables to replace
                      the attributes that are common to Opsa and Opsb
                      in tnOpsaPortConfigTable and tnOpsaPortInfoTable:
                      tnOpsPortConfigAttributeTotal
                      tnOpsPortConfigTable
                      tnOpsPortInfoAttributeTotal
                      tnOpsPortInfoTable."

      REVISION    "201203291200Z"
      DESCRIPTION "1) Added the 11dpe12a card.
                   2) Updated port names for Wr2c88."

      REVISION    "201204241200Z"
      DESCRIPTION "Added the ul130scup card."

      REVISION    "201204251200Z"
      DESCRIPTION "Added the following to AluWdmPortOchOtuRate:
                   otm10G714(10)."

      REVISION    "201204271200Z"
      DESCRIPTION "1) Added the following to tnDwdmCmnLinePortConfigTable:
                      tnDwdmCmnLinePortApsEnable.
                   2) Added the 130scx10 card."

      REVISION    "201205181200Z"
      DESCRIPTION "1) Added the following to tn11dpe12aPortConfigTable:
                      tn11dpe12aPortConfigMtu.
                   2) Marked the following as obsolete:
                      tnWr8c88aAttenPortConfigTable
                      tnWavekeyPortWTDecoderUsageStatusIn
                      tnWavekeyPortWTDecoderUsageStatusOut
                      tnE1T1PortInfoTable
                      tn1dpp24mPortClockSourceIncomingQLStatus
                      tn1dpp24mPortClockSourceIncomingQL."

      REVISION    "201205251200Z"
      DESCRIPTION "1) Added the following to AluWdmFecMode:
                      eSDFec(10).
                   2) Marked the following as obsolete:
                      tnTcmPortConfigAttributeTotal
                      tnTcmPortConfigTable
                      tnTcmPortInfoAttributeTotal
                      tnTcmPortInfoTable."

      REVISION    "201206151200Z"
      DESCRIPTION "Changed tnDwdmCmnLinePortApsEnable SYNTAX from
                   TruthValue to INTEGER, updated DESCRIPTION, and
                   added DEFVAL."

      REVISION    "201206181200Z"
      DESCRIPTION "1) Added the A2p2125, 4qpa8, Ot112pdm11, Wtocma, Ptpctl,
                      and Ptpio cards.
                   2) Added the following to tnDwdmCmnPortXfpType:
                      ctC113S10(114)."

      REVISION    "201206201200Z"
      DESCRIPTION "1) Added the following to
                      tnDwdmCmnOtu4Odu4LinePortConfigTable:
                      tnDwdmCmnLinePortOtu4RegenResponse.
                   2) Added DEFVAL to other attributes in
                      tnDwdmCmnOtu4Odu4LinePortConfigTable."

      REVISION    "201206261200Z"
      DESCRIPTION "Added the following port to 11dpe12a:
                   tod(5)."

      REVISION    "201207241200Z"
      DESCRIPTION "1) Added the Io24et1gb card.
                   2) Marked the following as obsolete:
                      11qta4."

      REVISION    "201208061200Z"
      DESCRIPTION "1) Added the following to tnDwdmCmnPortXfpType:
                      ct16FCLCL(115),
                      ct16FCSNI(116).
                   2) Added the following to tnDwdmGpPhyPortConfigTable:
                      tnDwdmGpPhyPortGfpcrc."

      REVISION    "201208211200Z"
      DESCRIPTION "1) Added tnDwdmIoPortConfigTable with the following:
                      tnDwdmIoPortRole.
                   2) Added the following to tnDwdmCmnClientPortContainer:
                      odu2(6),
                      to
                      oduflexfc400(15)."

      REVISION    "201208281200Z"
      DESCRIPTION "1) Added the Io4an10g, Io8et1gb, Io10et10g, Ul11qcupc,
                      and Ot520scx4 cards.
                   2) Added the following to tnDwdmCmnPortXfpType:
                      ctC113G4D(117),
                      to
                      ctC1134TU(122).
                   3) Added the following to tn11dpe12aPortConfigTable:
                      tn11dpe12aPortConfigPortRole."

      REVISION    "201209111200Z"
      DESCRIPTION "Added the following to tnWtocmaPortInfoTable:
                   tnWtocmaPortInfoPower
                   tnWtocmaPortInfoPowerMonitoredPort."

      REVISION    "201209181200Z"
      DESCRIPTION "Marked the following as obsolete:
                   tnDwdmGpPhyPortInfoTable."

      REVISION    "201209201200Z"
      DESCRIPTION "1) Added the following to tn11dpe12aPortConfigTable:
                      tn11dpe12aPortConfigPtpTrans.
                   2) Added the following to tnPtpioPortConfigFunction
                      and tnPtpioPortInfoFunction:
                      itp(4)."

      REVISION    "201209251200Z"
      DESCRIPTION "1) Added the following to
                      tnDwdmCmnOtu4Odu4LinePortConfigTable:
                      tnDwdmCmnLinePortOdu4Interworking.
                   2) Added the following to tnNetworkPortConfigTable:
                      tnNwPortChannelSpacing."

      REVISION    "201209271200Z"
      DESCRIPTION "Added the following table:
                   tnWssAprPortConfigTable."

      REVISION    "201210221200Z"
      DESCRIPTION "1) Added the following table:
                      tnSkewInfoTable.
                   2) Added the following to AluWdmPortOchOtuRate:
                      otm129G280(12).
                   3) Updated DESCRIPTION for the following:
                      tnOpsaPortSwitchingThreshold
                      tnOpsPortConfigSwitchingThreshold."

      REVISION    "201210241200Z"
      DESCRIPTION "Added the following to tnDwdmCmnPortXfpType:
                   ctXL64TCW(123)."

      REVISION    "201211121200Z"
      DESCRIPTION "Added the following to tnDwdmCmnPortXfpType:
                   ct100BULHO(124)."

      REVISION    "201211261200Z"
      DESCRIPTION "Added the following to tnPtpioPortConfigTable:
                   tnPtpioPortConfigSigPortConnFromPort
                   tnPtpioPortConfigSigPortConnToPort."

      REVISION    "201212131200Z"
      DESCRIPTION "Added the following to tnDwdmCmnOtu4Odu4LinePortConfigTable:
                   tnDwdmCmnLinePortOtu4holdofftimer."

      REVISION    "201212141200Z"
      DESCRIPTION "Added network port for the following packs:
                   cl10an10g
                   cl24anm
                   Io24et1gb
                   Io4an10g
                   Io8et1gb
                   Io10et10g."

      REVISION    "201212181200Z"
      DESCRIPTION "1) Added the following to tnOtPortInfoTable:
                      tnOtPortRxLanePowers
                      tnOtPortTxLanePowers.
                   2) Added the following to tn4qpa8PortConfigTable:
                      tn4qpa8PortConfigTtpPresent."

      REVISION    "201301071200Z"
      DESCRIPTION "Changed DEFVAL of tnDwdmGpPhyPortGfpcrc to std(2)."

      REVISION    "201301241200Z"
      DESCRIPTION "Marked the following legacy tables as obsolete:
                   tnOC48STM16PortConfigTable
                   tnOC192STM64PortConfigTable
                   tnQuadOC48STM16MuxPortConfigTable
                   tnQuadOC3or12STM1or4MuxPortConfigTable
                   tnBandFilterPortConfigTable
                   tnChFilterPortConfigTable
                   tnChAddDropPortConfigTable
                   tnBbaHgPortConfigTable
                   tnBbaLgPortConfigTable
                   tnPpsPortConfigTable
                   tnDualGigEMuxPortConfigTable
                   tnRoadmPortConfigTable
                   tn10GigELANPortConfigTable
                   tnDecaGigEMuxPortConfigTable
                   tnExternalDcuPortConfigTable
                   tnMsaHgPortConfigTable
                   tnCmd42PortConfigTable
                   tnWssX9PortConfigTable
                   tn1xMR2dot5GPortConfigTable
                   tnBbaHgPortLcConfigTable
                   tnBbaLgPortLcConfigTable
                   tnOC48STM16PortInfoTable
                   tnOC192STM64PortInfoTable
                   tnQuadOC48STM16MuxPortInfoTable
                   tnQuadOC3or12STM1or4MuxPortInfoTable
                   tnBandFilterPortInfoTable
                   tnChFilterPortInfoTable
                   tnChAddDropPortInfoTable
                   tnBbaHgPortInfoTable
                   tnBbaLgPortInfoTable
                   tnPpsPortInfoTable
                   tnDualGigEMuxPortInfoTable
                   tnRoadmPortInfoTable
                   tn10GigELANPortInfoTable
                   tnDecaGigEMuxPortInfoTable
                   tnExternalDcuPortInfoTable
                   tnMsaHgPortInfoTable
                   tnWssX9PortInfoTable
                   tn1xMR2dot5GPortInfoTable."

      REVISION    "201301261200Z"
      DESCRIPTION "1) Added the following to tnDwdmCmnLinePortConfigTable:
                      tnDwdmCmnLinePortHoldOffTimer.
                   2) Marked the following as deprecated:
                      tnDwdmCmnLinePortOtu2holdofftimer
                      tnDwdmCmnLinePortOtu4holdofftimer."

      REVISION    "201301301200Z"
      DESCRIPTION "Added the following table:
                   tnDTVPortTable."

      REVISION    "201303071200Z"
      DESCRIPTION "Added the 11ope8 and 11qce12x cards."

      REVISION    "201303141200Z"
      DESCRIPTION "1) Renamed ge1(5) in tnDwdmGpPhyPortPacketIfType to the
                      following:
                      gmpGfpT(5).
                   2) Added the following tables:
                      tnPowerFilterPortConfigTable
                      tnPowerFilterPortInfoTable."

      REVISION    "201303161200Z"
      DESCRIPTION "1) Added the following table:
                      tnPortInventoryTable.
                   2) Added the Am2625a, Am2032a, and Ot260scx2 cards.
                   3) Updated ranges for the following:
                      tnWaveKeyPortUnexpectedWKThreshIngress
                      tnWaveKeyPortUnexpectedWKThreshEgress."

      REVISION    "201303291200Z"
      DESCRIPTION "Added the following to tn11dpe12aPortConfigTable:
                   tn11dpe12aPortConfigCompatibilityMode."

      REVISION    "201304091200Z"
      DESCRIPTION "Added the following to tnWtocmaPortConfigTable:
                   tnWtocmaPortConfigOsnrMeasure."

      REVISION    "201304111200Z"
      DESCRIPTION "Added the Ot130snx10 and Io24anmb cards."

      REVISION    "201304141200Z"
      DESCRIPTION "Added the following to tnMvacPortConfigTable:
                   tnMvacPortConfigVoaMode
                   tnMvacPortConfigAttenuationModeAtten
                   tnMvacPortConfigConnToPort."

      REVISION    "201304191200Z"
      DESCRIPTION "Added the Ot11dpm8 and Ot11dpm4m cards."

      REVISION    "201305211200Z"
      DESCRIPTION "Marked the following as obsolete:
                   tnOpticalPortLcConfigGroups
                   tnOpticalPortLcConfigCompliances
                   tnOpticalPortEvents
                   tnOpticalPortLcConfig."

      REVISION    "201305231200Z"
      DESCRIPTION "1) Added the following to tnDwdmCmnLinePortConfigTable:
                      tnDwdmCmnLinePortDMConfigCMEPMode
                      tnDwdmCmnLinePortDMConfigEnable.
                   2) Added the following to tnDwdmCmnLinePortInfoTable:
                      tnDwdmCmnLinePortDMInfoCurrentStatus
                      tnDwdmCmnLinePortDMInfoCurrentValue."

      REVISION    "201305241200Z"
      DESCRIPTION "Added the Ul130scupb and Ot112sdx11 cards."

      REVISION    "201306011200Z"
      DESCRIPTION "1) Added the following to tn11dpe12aPortConfigFunction:
                      bits(6).
                   2) Added the following to tn11dpe12aPortConfigTable:
                      tn11dpe12aPortConfigFlowControl."

      REVISION    "201306041200Z"
      DESCRIPTION "Added the following to tnDwdmCmnPortXfpType:
                   ctXs642D(125)."

      REVISION    "201306131200Z"
      DESCRIPTION "Added the following to tnDwdmCmnPortXfpType:
                   ctSxi641(127)
                   ctQ40Gsr4(128)
                   ctQ40Glr4(129)."

      REVISION    "201306211200Z"
      DESCRIPTION "Added the following to tnDwdmCmnPortXfpType:
                   ctC2Clr4E(126)."

      REVISION    "201306241200Z"
      DESCRIPTION "1) Added the following to tnOt112sdx11PortInfoTable:
                      tnOt112sdx11PortInfoAggrRate.
                   2) Added the Aa2donw card."

      REVISION    "201307121200Z"
      DESCRIPTION "Added backplane(4) to:
                   tn11ope8PortConfigFunction
                   tn11qce12xPortConfigFunction
                   tn11ope8PortInfoFunction
                   tn11qce12xPortInfoFunction."

      REVISION    "201308021200Z"
      DESCRIPTION "1) Renamed the following in tnDwdmCmnPortXfpType from:
                      ctC1134TU(122)
                      to
                      ctC113G4T(122).
                   2) Added the following to tnWtocmaPortConfigTable:
                      tnWtocmaPortConfigOsnrClear."

      REVISION    "201308121200Z"
      DESCRIPTION "Added the and Ot130sca1 card."

      REVISION    "201309041200Z"
      DESCRIPTION "Added the Io10an10gb and Io10et10gb cards."

      REVISION    "201309131200Z"
      DESCRIPTION "Added the following to tnDwdmCmnPortXfpType:
                   ctSxs642B(130),
                   ctS1E(131)."

      REVISION    "201310031200Z"
      DESCRIPTION "Added the following to tnDwdmCmnPortXfpType:
                   ctSgS11(132),
                   to
                   ctSgL41(135)."

      REVISION    "201310071200Z"
      DESCRIPTION "Added the Psc1x6 card."

      REVISION    "201310101200Z"
      DESCRIPTION "Added the Wr20tf card."

      REVISION    "201310211200Z"
      DESCRIPTION "1) Added the following to tnWr20tfPortConfigTable:
                      tnWr20tfPortConfigDropInitTargetPower
                      tnWr20tfPortConfigExpressTargetPower
                      tnWr20tfPortConfigDropMaxTargetPower
                      tnWr20tfPortConfigDropMinTargetPower.
                   2) Added the following:
                      tnWssPortInfoTable.
                   3) Added the following to tnDwdmCmnPortXfpType:
                      ctSxs642C(136),
                      ctC2Csr10E(137).
                   4) Marked the following as obsolete:
                      tnCwr8PortBlockerAging
                      tnCwr8c88PortBlockerAging
                      tnWr2c88PortBlockerAging."

      REVISION    "201311061200Z"
      DESCRIPTION "Marked the following as obsolete:
                   tnGccPortConfigTable."

      REVISION    "201311131200Z"
      DESCRIPTION "Added the following to tnDwdmCmnOtu4Odu4LinePortConfigTable:
                   tnDwdmCmnLinePortOdu4112GInterworking."

      REVISION    "201311251200Z"
      DESCRIPTION "Added the Wtocmf card."

      REVISION    "201312051200Z"
      DESCRIPTION "1) Added the following to tnOscSfpPortConfigTable:
                      tnOscMtuNeg.
                   2) Changed DEFVAL of tnOscMtu to 1500."

      REVISION    "201312121200Z"
      DESCRIPTION "Added the following to tnOtPortInfoTable:
                   tnOtPortRxLaneBslPowers
                   tnOtPortTxLaneBslPowers."

      REVISION    "201401071200Z"
      DESCRIPTION "Updated DESCRIPTION of the following from microseconds
                   to 10**(-7) seconds:
                   tnDwdmCmnLinePortDMInfoCurrentValue."

      REVISION    "201401241200Z"
      DESCRIPTION "1) Added the following to tnDwdmCmnOtu4Odu4LinePortConfigTable:
                      tnDwdmCmnLinePortOdu4DMConfigCMEPMode
                      tnDwdmCmnLinePortOdu4DMConfigEnable.
                   2) Added the following to tnDwdmCmnOtu4Odu4LinePortInfoTable:
                      tnDwdmCmnLinePortOdu4DMInfoCurrentStatus
                      tnDwdmCmnLinePortOdu4DMInfoCurrentValue."

      REVISION    "201402261200Z"
      DESCRIPTION "1) Changed SYTAX of the following to use
                      AluWdmDMInfoCurrentStatus:
                      tnDwdmCmnLinePortDMInfoCurrentStatus
                      tnDwdmCmnLinePortOdu4DMInfoCurrentStatus.
                   2) Moved AluWdmFecMode to TROPIC-TC."

      REVISION    "201402271200Z"
      DESCRIPTION "Added the following cards:
                   Aswg
                   A4pswg
                   Otdr
                   Wr20tfm
                   Aar8a
                   Mcs8x16
                   Msh8fsm."

      REVISION    "201403041200Z"
      DESCRIPTION "Added the following table:
                   tnPortOtdrScanTable."

      REVISION    "201403111200Z"
      DESCRIPTION "1) Added the following tables:
                      tnMcsPortConfigTable
                      tnAarPortConfigTable
                      tnMcsPortInfoTable
                      tnMcsPortChannelInfoTable
                      tnAarPortInfoTable.
                   2) Added the following to tnMcs8x16PortInfoTable:
                      tnMcs8x16PortInfoAddInsertionLossToSig[1-8]
                      tnMcs8x16PortInfoDropInsertionLossFromSig[1-8].
                   3) Added the following to tnRamanPortConfigTable:
                      tnRamanPortAprMode.
                   4) Added the following to tnRamanPortInfoTable
                      tnRamanPortPump[3-4]Power."

      REVISION    "201403181200Z"
      DESCRIPTION "1) Added the following tables:
                      tnWr20tfmPortConfigTable
                      tnWr20tfmPortChannelConfigTable
                      tnMpoPortConfigTable
                      tnMpoPortInfoTable
                      tnMpoPortMultiPositionInfoTable
                      tnWr20tfmPortChannelInfoTable.
                   2) Added following textual conventions:
                      AluWdmWRConfigAddDropDisposition
                      AluWdmWRChannelCurrentAddDropDisposition."

      REVISION    "201403191200Z"
      DESCRIPTION "1) Changed SYNTAX of the following from TropicDwMode
                      to AluWdmFecMode:
                      tnDwPortDwMode.
                   2) Marked the following as obsolete:
                      TropicDwMode.
                   3) Moved AluWdmPortOchOtuRate to TROPIC-TC."

      REVISION    "201403301200Z"
      DESCRIPTION "1) Added ranges or DEFVAL to attributes in this MIB file.
                   2) Changed DEFVAL of the following from 1200 to 1000:
                      tnWaveKeyPortUnexpectedWKThreshAutoMaxOffsetIn
                      tnWaveKeyPortUnexpectedWKThreshAutoMaxOffsetOut.
                   3) Changed DEFVAL of the following from maxPower to gain:
                      tnRamanPortOperatingMode.
                   4) Changed DEFVAL of the following from -800 to -900:
                      tnWr20tfPortConfigExpressTargetPower.
                   5) Changed DEFVAL of the following from -800 to -600:
                      tnWr20tfPortConfigDropMaxTargetPower.
                   6) Changed DEFVAL of the following from wtdMeasured
                      to unavailable:
                      tnWaveKeyPortWTDecoderMeasurementTypeIn
                      tnWaveKeyPortWTDecoderMeasurementTypeOut."
      
      REVISION    "201404301200Z"
      DESCRIPTION "Added tnPortOtdrScanLastSuccessfulTimeStamp to
                   tnPortOtdrScanTable"
      
      REVISION    "201405061200Z"
      DESCRIPTION "Added the following cards:
                   Io4an100g
                   Io30an10g."

      REVISION    "201405181200Z"
      DESCRIPTION "1) Added the following cards:
                      Sfd2[a-i,l-r]
                      VwmSfd8[a-d]
                      VwmSfc8.
                   2) Added the following textual convention:
                      AluWdmSfdPortType."

      REVISION    "201405201200Z"
      DESCRIPTION "Changed default value of 
                     tnWaveKeyPortCommonEgressPower from -2000 to 0."

      REVISION    "201406121200Z"
      DESCRIPTION "1) Added the following to tnWr20tfmPortInfoTable:
                      tnWr20tfmPortInfoTestingActive.
                   2) Added the following to tnMcsPortInfoTable:
                      tnMcsPortInfoTestingActive.
                   3) Added the following to tnAarPortInfoTable:
                      tnAarPortInfoTestingActive."
      
      REVISION    "201406201200Z"
      DESCRIPTION "1) Added the following cards:
                      Io30an300 and Io4an400.
                   2) Changed size of tnPortOtdrScanFileName from
                      34 to 25 chars."
      
      REVISION    "201407221200Z"
      DESCRIPTION "1) Marked the following as obsolete:
                      tnWr20tfmPortConfigExecuteForcedDropDisposition
                      tnWr20tfmPortConfigExecuteForcedAddDisposition.
                   2) Modified description of following in tnWr20tfmPortChannelConfigTable:
                      tnWr20tfmPortChannelConfigTargetForcedDropDisposition
                      tnWr20tfmPortChannelConfigTargetForcedAddDisposition."
      
      REVISION    "201408051200Z"
      DESCRIPTION "Changed syntax of  tnPortOtdrScanLastSuccessfulTimeStamp
                   to Unsigned32 from TimeTicks."

      REVISION    "201408081200Z"
      DESCRIPTION "Added the following cards:
                   12p120
                   20p200
                   1ud200."

      REVISION    "201408221200Z"
      DESCRIPTION "Added the following to tnOt112sdx11PortConfigTable:
                   tnOt112sdx11PortConfigLinkGroupId."

      REVISION    "201409181200Z"
      DESCRIPTION "Added the following card:
                   Ot130snq10."

      REVISION    "201409251200Z"
      DESCRIPTION "Added the following cards:
                   Iroadmv
                   Iroadmf."

      REVISION    "201410311200Z"
      DESCRIPTION "Added the following to tnDwdmCmnPortXfpType:
                   ct2CBx10U(138)
                   ct2CBx10D(139)."

      REVISION    "201411131200Z"
      DESCRIPTION "Added the following to tnDwdmCmnClientPortConfigTable:
                   tnDwdmCmnClientPortCSF
                   tnDwdmCmnClientPortSSF."

      REVISION    "201411191200Z"
      DESCRIPTION "Added the following tables:
                   tnIroadmPortConfigTable
                   tnIroadmPortInfoTable
                   tnIroadmPortChannelInfoTable."

      REVISION    "201412031200Z"
      DESCRIPTION "1) Added the following to tnIroadmPortConfigTable
                      tnIroadmPortConfigAprDisable.
                   2) Removed the following from tnIroadmPortInfoTable
                      tnIroadmPortInfoOSCTxPowerIn
                      tnIroadmPortInfoOSCTxPowerOut."

      REVISION    "201412121200Z"
      DESCRIPTION "1) Added the following to tnDwdmCmnPortXfpType 
                      ctC4Clr4E(141)
                      ctC4Clr4D(142)."

      REVISION    "201412221200Z"
      DESCRIPTION "Added the following table:
                   tnWssRefLdPortInfoTable."
      
      REVISION    "201501081200Z"
      DESCRIPTION "1) Added the following to tnDwdmCmnPortXfpType 
                      ctC2Clr4D(138)."

      REVISION    "201501161200Z"
      DESCRIPTION "Added the following card:
                   MonOcm."

      REVISION    "201502201200Z"
      DESCRIPTION "1) Added the following cards:
                      Ul2uc400
                      Ul4uc400
                      Ul20uc200.
                   2) Added new values to tnIroadmPortConfigFiberTypeOut."

      REVISION    "201503261200Z"
      DESCRIPTION "1) Added the following to tnDwdmCmnOtu4Odu4LinePortConfigTable:
                      tnDwdmCmnLinePortOdu4CndRes.
                   2) Added the following to tnDwdmCmnClientPortConfigTable:
                      tnDwdmCmnClientPortScramMode."

      REVISION    "201505151200Z"
      DESCRIPTION "Added the following to tnDwdmCmnPortConfigTable:
                   tnDwdmCmnPortAlmProfName." 

      REVISION    "201505251200Z"
      DESCRIPTION "Added ToD port type to following MIBs:
                    tn11ope8PortConfigFunction
                    tn11ope8PortInfoFunction
                    tn11qce12xPortConfigFunction
                    tn11qce12xPortInfoFunction."

      REVISION    "201505261200Z"
      DESCRIPTION "1) Added the following to tnIroadmvPortConfigTable:
                      tnIroadmPortConfigLineDcmConnAddress.
                   2) Added the following to tnDcmPortInfoTable:
                      tnDcmPortInfoIroadmConnAddress."

      REVISION    "201506011200Z"
      DESCRIPTION "1) Added the following to tnIroadmPortConfigTable:
                      tnIroadmPortConfigForcedTargetPpcOut."

      REVISION    "201506031200Z"
      DESCRIPTION "1) Changed the following from tnIroadmvPortConfigTable
                      to tnIroadmPortConfigTable:
                      tnIroadmPortConfigLineDcmConnAddress."

      REVISION    "201506121200Z"
      DESCRIPTION "1) Added the following to tnD5x500PortConfigTable:
                      tnD5x500PortConfigFunction.
                   2) Added the following to tnD5x500PortInfoTable:
                      tnD5x500PortInfoFunction"

      REVISION    "201506221200Z"
      DESCRIPTION "Added the OtS11M100 cards."

      REVISION    "201507171200Z"
      DESCRIPTION "1) Added the following to tnDwdmCmnOtu4Odu4LinePortConfigTable:
                      tnDwdmCmnLinePortOdu4Encoding."

      REVISION    "201506221200Z"
      DESCRIPTION "Removed DEFVAL as there is inconsistency between 
                   the DEFVAL and the SYNTAX clause"

      REVISION    "201506121200Z"
      DESCRIPTION "1) Added the following to tnDwdmCmnClientPortConfigTable:
                      tnDwdmCmnClientPortOdu2DegInterval
                      tnDwdmCmnClientPortOdu2DegThreshold.
                   2) Added the following to tnDwdmCmnOtu4Odu4LinePortConfigTable:
                      tnDwdmCmnLinePortOdu4DegInterval
                      tnDwdmCmnLinePortOdu4DegThreshold."

      REVISION    "201508061200Z"
      DESCRIPTION "Added the following card:
                      MON-OTDR."

      REVISION    "201508181200Z"
      DESCRIPTION "1) Renamed the following in tnDwdmCmnClientPortConfigTable:
                      tnDwdmCmnClientPortOdu2DegInterval to tnDwdmCmnClientPortDegInterval
                      tnDwdmCmnClientPortOdu2DegThreshold to tnDwdmCmnClientPortDegThreshold.
                   2) Added the following to tnDwdmCmnOtu4Odu4LinePortConfigTable:
                      tnDwdmCmnLinePortOdu4DegInterval to tnDwdmCmnLinePortDegInterval
                      tnDwdmCmnLinePortOdu4DegThreshold to tnDwdmCmnLinePortDegThreshold.
	                 3) Changed range of tnDwdmCmnClientPortDegThreshold:
                      From (1..82026) to (0..128000).
	                 4) Changed the DEFVAL of tnDwdmCmnClientPortDegThreshold: 
		                  From  4000 to 0."

      REVISION    "201508251200Z"
      DESCRIPTION "1) Added the following to tnDwdmCmnLinePortOdu4Encoding:
                      spqpsk(12),
                      qam64(13)."

      REVISION    "201509071200Z"
      DESCRIPTION "1) Added the following to tnDwdmCmnLinePortConfigTable:
                      tnDwdmCmnLinePortCluster."

      REVISION    "201509141200Z"
      DESCRIPTION "1) Added the MAX-ACCESS of tnDwdmCmnLinePortCluster:
                      From read-only to read-write."

      REVISION    "201509291200Z"
      DESCRIPTION "1) Added the following to tnDwdmGpPhyPortPacketIfType:
                      gecbr100(23)."

      REVISION    "201510051200Z"
      DESCRIPTION "1) Added the following to card:
                      PSS96PowerFilter." 

      REVISION    "201510051200Z"
      DESCRIPTION "1) Added the following to tnDwdmCmnPortXfpType:
                      ctCFP2ALUMetro(143),
                      ctCFP2ALULH(144).
                   2) Changed the range of tnDwdmCmnClientPortDegThreshold:
                      From (0..128000) to (0..'ffffffff'h)."

      REVISION    "201510141200Z"
      DESCRIPTION "1) Added the following to tnDwdmCmnPortXfpType:
                      ctC2CER4E(145),
                      ctSL64TUW(146)"

      REVISION    "201510211200Z"
      DESCRIPTION "1) Moved the following from tnDwdmCmnOtu4Odu4LinePortConfigTable to
                      tnDwdmCmnLinePortConfigTable:
                        tnDwdmCmnLinePortDegInterval,
                        tnDwdmCmnLinePortDegThreshold"
      
      REVISION    "201510281200Z"
      DESCRIPTION " Added the following cards:
                    12ce120
                    1ce100."

      REVISION    "201511231200Z"
      DESCRIPTION "1) Added the following to tnDwdmCmnPortXfpType:
                      ctC120G1TC(147)."

      REVISION    "201512071200Z"
      DESCRIPTION "1) Added the following to tnPSS96PowerFilterPortConfigTable:
                      tnPSS96ExpectedAmps.
                   2) Added the following to tnDwdmCmnPortXfpType:
                      ctSWR120(148).
                   3) Added the LcI1000 card."

      REVISION    "201512101200Z"
      DESCRIPTION "1) Added the following to tnOt112sdx11PortConfigTable:
                      tnOt112sdx11ProgrammedNwOutputPower."

      REVISION    "201512151200Z"
      DESCRIPTION "Added the following to tnDwdmCmnPortXfpType:
                   ct2Ac100H(149)."

      REVISION    "201601041200Z"
      DESCRIPTION "Added backplane port to the following tables:
                   tnD5x500PortConfigFunction
                   tnD5X500PortInfoFunction."

      REVISION    "201601081200Z"
      DESCRIPTION "1)Added the following to tnDwdmCmnPortXfpType:
                     ct2Ac100(150)."

      REVISION    "201601121200Z"
      DESCRIPTION "Added the following to tnDwdmCmnLinePortConfigTable:
                   tnDwdmCmnLinePorttxShape."

      REVISION    "201601211200Z"
      DESCRIPTION "1) Added the following to tnDwdmCmnPortXfpType:
                      ctSXL642(151),
                      ctSXL642C(152).
                   2) Marked the below following as obsolete:
                      tnOpsaPortSwitchingThreshold,
                      tnOpsaPortSwitchingThresholdTolerance,
                      tnOpsaPortTransmitAttenuation,
                      tnOpsaPortSwitchingThreshCalcControl."

      REVISION    "2016020811200Z"
      DESCRIPTION "Changes the SYNTAX value of tnDwdmCmnLinePorttxShape."

      REVISION    "2016021911200Z"
      DESCRIPTION "Changed the SYNTAX of following tnOtdrPortConfigConnAddress:
                   From InterfaceIndexOrZero To (-1..2147483647)."

      REVISION    "2016030811200Z"
      DESCRIPTION "Renamed the value of tnDwdmCmnPortXfpType:
                   From ctC120G1TC(147) to ct1Dc100M(147)."

      REVISION    "201603151200Z"
      DESCRIPTION "Added the following to tnDwdmCmnLinePortConfigTable:
                   tnDwdmCmnLinePortCdPreComp,
                   tnDwdmCmnLinePortPhasenCode."

      REVISION    "201604071200Z"
      DESCRIPTION "Added the following to tnDwdmCmnClientPortConfigTable:
                   tnDwdmCmnClientPortMgracd." 

      REVISION    "201604081200Z"
      DESCRIPTION "1) Added the following to tn12ce120PortConfigFunction:
                      tod(3).
                   2) Added the following to tn1ce100PortConfigFunction:
                      tod(3).
                   3) Added the follwoing to tn12ce120PortInfoFunction:
                      tod(3).
                   4) Added the following to tn1ce100PortInfoFunction:
                      tod(3)."

      REVISION    "201604191200Z"
      DESCRIPTION "Added the following to tnDwdmCmnPortXfpType:
                   ctSgE1(153),
                   ctSgS11C(154)."

      REVISION    "201604221200Z"
      DESCRIPTION "Added the following table:
                   tnFlexgridOtsInfoTable."

      REVISION    "201605181200Z"
      DESCRIPTION "Changed the Range of tnDwdmCmnLinePortCdPreComp:
                   From (0..4300) To (-3100..3100)."

      REVISION    "201605211200Z"
      DESCRIPTION "Moved the follwing from tnDwdmCmnClientPortConfigTable
                   to tnDwdmCmnPortConfigTable:
                   tnDwdmCmnClientPortMgracd."

      REVISION    "201609201200Z"
      DESCRIPTION "Added the following to tnDwdmCmnClientPortConfigTable:
                   tnDwdmCmnClientPortHoldOffTimer."

      ::= { tnPortModules 3 }

  tnOpticalPortConf                OBJECT IDENTIFIER ::= { tnOpticalPortMIB 1 }
  tnOpticalPortGroups              OBJECT IDENTIFIER ::= { tnOpticalPortConf 1 }
  tnOpticalPortCompliances         OBJECT IDENTIFIER ::= { tnOpticalPortConf 2 }
  tnOpticalPortConfigGroups        OBJECT IDENTIFIER ::= { tnOpticalPortConf 3 }
  tnOpticalPortInfoGroups          OBJECT IDENTIFIER ::= { tnOpticalPortConf 4 }
--  obsolete
--  tnOpticalPortLcConfigGroups      OBJECT IDENTIFIER ::= { tnOpticalPortConf 5 }
  tnOpticalPortConfigCompliances   OBJECT IDENTIFIER ::= { tnOpticalPortConf 6 }
  tnOpticalPortInfoCompliances     OBJECT IDENTIFIER ::= { tnOpticalPortConf 7 }
--  obsolete
--  tnOpticalPortLcConfigCompliances OBJECT IDENTIFIER ::= { tnOpticalPortConf 8 }
  tnOpticalPortObjs                OBJECT IDENTIFIER ::= { tnOpticalPortMIB 2 }
--  obsolete
--  tnOpticalPortEvents              OBJECT IDENTIFIER ::= { tnOpticalPortMIB 3 }
  tnOpticalPortConfig              OBJECT IDENTIFIER ::= { tnOpticalPortMIB 4 }
  tnOpticalPortInfo                OBJECT IDENTIFIER ::= { tnOpticalPortMIB 5 }
--  obsolete
--  tnOpticalPortLcConfig            OBJECT IDENTIFIER ::= { tnOpticalPortMIB 6 }

--------------------------------------------------------------------------------
-- Type Definitions
--------------------------------------------------------------------------------
--    obsolete
--    TropicDwMode ::= TEXTUAL-CONVENTION

    TropicMauType ::= TEXTUAL-CONVENTION
        STATUS         current
        DESCRIPTION    ""
        SYNTAX         INTEGER {
                         typeInvalid(1),
                         typeNone(2),
                         type10Base5(3),
                         typeFoir1(4),
                         type10Base2(5),
                         type10BaseT(6),
                         type10BaseFP(7),
                         type10BaseFB(8),
                         type10BaseFL(9),
                         type10Broad36(10),
                         type10BaseTHD(11),
                         type10BaseTFD(12),
                         type10BaseFLHD(13),
                         type10BaseFLFD(14),
                         type100BaseT4(15),
                         type100BaseTXHD(16),
                         type100BaseTXFD(17),
                         type100BaseFXHD(18),
                         type100BaseFXFD(19),
                         type100BaseT2HD(20),
                         type100BaseT2FD(21),
                         type1000BaseXHD(22),
                         type1000BaseXFD(23),
                         type1000BaseLXHD(24),
                         type1000BaseLXFD(25),
                         type1000BaseSXHD(26),
                         type1000BaseSXFD(27),
                         type1000BaseCXHD(28),
                         type1000BaseCXFD(29),
                         type1000BaseTHD(30),
                         type1000BaseTFD(31),
                         type10GigBaseX(32),
                         type10GigBaseLX4(33),
                         type10GigBaseR(34),
                         type10GigBaseER(35),
                         type10GigBaseLR(36),
                         type10GigBaseSR(37),
                         type10GigBaseW(38),
                         type10GigBaseEW(39),
                         type10GigBaseLW(40),
                         type10GigBaseSW(41)
                       }

    TropicSonetS1 ::= TEXTUAL-CONVENTION
        STATUS         current
        DESCRIPTION    ""
        SYNTAX         INTEGER {
                         unknown(1),
                         prs(2),       -- Stratum 1 Traceable
                         stu(3),       -- Synchronized - Traceability Unknown
                         st2(4),       -- Stratum 2 Traceable
                         tnc(5),       -- Transit Node Clock Traceable
                         st3e(6),      -- Stratum 3E Traceable
                         st3(7),       -- Stratum 3 Traceable
                         smc(8),       -- SONET Minimum Clock Traceable
                         dus(9),       -- DON'T USE for Synchronization
                         invalid(10)   -- Invalid S1
                       }

    TropicSdhS1 ::= TEXTUAL-CONVENTION
        STATUS         current
        DESCRIPTION    ""
        SYNTAX         INTEGER {
                         unknown(1),
                         prc(2),       -- PRC Clock G.811
                         ssua(3),      -- Type I or V SSU clock G.812
                         ssub(4),      -- Type VI SSU clock G.812
                         sec(5),       -- SEC clock G.813 option 1
                         dnu(6),       -- DON'T USE for Synchronization
                         invalid(7)    -- Invalid S1
                       }

    AluWdmVtsSource ::= TEXTUAL-CONVENTION
        STATUS         current
        DESCRIPTION    "VTS source."
        SYNTAX         INTEGER {
                         none(1),
                         c1(2),
                         c2(3),
                         c3(4),
                         c4(5),
                         c5(6),
                         c6(7),
                         c7(8),
                         c8(9),
                         c9(10),
                         c10(11),
                         c11(12),
                         c12(13),
                         l1slot1(14),
                         l1slot2(15),
                         l1slot3(16),
                         l1slot4(17),
                         l1slot5(18),
                         l1slot6(19),
                         l1slot7(20),
                         l1slot8(21),
                         l1slot9(22),
                         l1slot10(23),
                         l2slot1(24),
                         l2slot2(25),
                         l2slot3(26),
                         l2slot4(27),
                         l2slot5(28),
                         l2slot6(29),
                         l2slot7(30),
                         l2slot8(31),
                         l2slot9(32),
                         l2slot10(33)
                       }

    AluWdmPortLaserTunability ::= TEXTUAL-CONVENTION
        STATUS         current
        DESCRIPTION    "Laser tunability of this port."
        SYNTAX         INTEGER {
                         unknown(1),
                         fixed(2),
                         fixedSpecial(3),
                         fullyTunable(4),
                         semiTunable(5),
                         semiTunableBandAligned(6)
                       }

    AluWdmTimDetectionMode ::= TEXTUAL-CONVENTION
        STATUS         current
        DESCRIPTION    "TIM detection mode."
        SYNTAX         INTEGER {
                         off(1),
                         sapiOnly(2),
                         dapiOnly(3),
                         sapiAndDapiOnly(4),
                         userSpecificOnly(5),
                         userSpecificAndSapiOnly(6),
                         userSpecificAndDapiOnly(7),
                         userSpecificAndSapiAndDapi(8)
                       }

    AluWdmMappingMode ::= TEXTUAL-CONVENTION
        STATUS         current
        DESCRIPTION    "ODU2/ODU1 mapping mode."
        SYNTAX         INTEGER {
                         null(1),
                         prbs(2),
                         cbrA(3),
                         cbrB(4),
                         rsA(5),
                         rsB(6),
                         lanPhyGfp(7)
                       }

    AluWdmOduOchSignalDefConsequenceAction ::= TEXTUAL-CONVENTION
        STATUS         current
        DESCRIPTION    "ODU2/ODU1 OCH signal def consequence action."
        SYNTAX         INTEGER {
                         none(1),
                         ais(2),
                         oduAis(3),
                         msAis(4),
                         genericAis(5),
                         lfi(6),
                         laserOff(7)
                       }

    AluWdmWTDecoderMeasurementType ::= TEXTUAL-CONVENTION
        STATUS         current
        DESCRIPTION    "Indicate the measurement source."
        SYNTAX         INTEGER {
                         wtdMeasured(1),
                         wtocmMeasured(2),
                         calculated(3),
                         unavailable(4)
                       }

    AluWdmWRConfigAddDropDisposition ::= TEXTUAL-CONVENTION
        STATUS         current
        DESCRIPTION    "Configurable Add Drop Disposition"
        SYNTAX         INTEGER {
                         adt1(1),
                         adt2(2),
                         adt3(3),
                         adt4(4),
                         adt5(5),
                         adt6(6),
                         adt7(7),
                         adt8(8),
                         ad9(9),
                         ad10(10),
                         ad11(11),
                         ad12(12),
                         ad13(13),
                         ad14(14),
                         ad15(15),
                         ad16(16),
                         ad17(17),
                         ad18(18),
                         ad19(19),
                         ad20(20),
                         notForced(21)
                       }

    AluWdmWRChannelCurrentAddDropDisposition ::= TEXTUAL-CONVENTION
        STATUS         current
        DESCRIPTION    "Current Add Drop Disposition."
        SYNTAX         INTEGER {
                         adt1(1),
                         adt2(2),
                         adt3(3),
                         adt4(4),
                         adt5(5),
                         adt6(6),
                         adt7(7),
                         adt8(8),
                         ad9(9),
                         ad10(10),
                         ad11(11),
                         ad12(12),
                         ad13(13),
                         ad14(14),
                         ad15(15),
                         ad16(16),
                         ad17(17),
                         ad18(18),
                         ad19(19),
                         ad20(20),
                         blocked(21)
                       }

    AluWdmSfdPortType ::= TEXTUAL-CONVENTION
        STATUS         current
        DESCRIPTION    "SFD Port Type."
        SYNTAX         INTEGER {
                         channel(1),
                         mux(2),
                         exp(3)
                       }



--------------------------------------------------------------------------------
-- Obsoleted OIDs
--------------------------------------------------------------------------------
--    tnOpticalPortTotal OBJECT-TYPE ::= { tnOpticalPortObjs 1 }
--    tnOC48SwsPortTotal OBJECT-TYPE ::= { tnOpticalPortObjs 2 }
--    tnSimpleOpticsPortTotal OBJECT-TYPE ::= { tnOpticalPortObjs 3 }
--    tnOC48SwsUserNwPortTotal OBJECT-TYPE ::= { tnOpticalPortObjs 4 }
--    tnOC48SwsUserNwPortTable OBJECT-TYPE ::= { tnOpticalPortObjs 5 }
--    tnBandFilterPortTotal OBJECT-TYPE ::= { tnOpticalPortObjs 6 }
--    tnBandFilterPortTable OBJECT-TYPE ::= { tnOpticalPortObjs 7 }
--    tnOscPortTotal OBJECT-TYPE ::= { tnOpticalPortObjs 8 }
--    tnOscPortTable OBJECT-TYPE ::= { tnOpticalPortObjs 9 }
--    tnChannelFilterPortTotal OBJECT-TYPE ::= { tnOpticalPortObjs 10 }
--    tnChannelFilterPortTable OBJECT-TYPE ::= { tnOpticalPortObjs 11 }
--    tnBbaLinePortTotal OBJECT-TYPE ::= { tnOpticalPortObjs 12 }
--    tnBbaLinePortTable OBJECT-TYPE ::= { tnOpticalPortObjs 13 }
--    tnPpsPortTotal OBJECT-TYPE ::= { tnOpticalPortObjs 14 }
--    tnPpsPortTable OBJECT-TYPE ::= { tnOpticalPortObjs 15 }
--    tnOC192SwsUserNwPortTotal OBJECT-TYPE ::= { tnOpticalPortObjs 16 }
--    tnOC192SwsUserNwPortTable OBJECT-TYPE ::= { tnOpticalPortObjs 17 }
--    tn2x1GEoSWSPortTotal OBJECT-TYPE ::= { tnOpticalPortObjs 18 }
--    tn2x1GEoSWSPortTable OBJECT-TYPE ::= { tnOpticalPortObjs 19 }
--    tnSonetPortTotal OBJECT-TYPE ::= { tnOpticalPortObjs 20 }
--    tnSonetPortTable OBJECT-TYPE ::= { tnOpticalPortObjs 21 }

--------------------------------------------------------------------------------
-- Optical Port Table
--------------------------------------------------------------------------------
    tnOpticalPortTable OBJECT-TYPE
        SYNTAX         SEQUENCE OF TnOpticalPortEntry
        MAX-ACCESS     not-accessible
        STATUS         current
        DESCRIPTION    "The ports on optical cards."
        ::= { tnOpticalPortObjs 22 }

    tnOpticalPortEntry OBJECT-TYPE
        SYNTAX         TnOpticalPortEntry
        MAX-ACCESS     not-accessible
        STATUS         current
        DESCRIPTION    ""
        INDEX { ifIndex,
                tnOpticalPortDirection }
        ::= { tnOpticalPortTable 1 }

    TnOpticalPortEntry ::=
        SEQUENCE {
            tnOpticalPortDirection     INTEGER,
            tnOpticalPortInsertionLoss Integer32
        }

    tnOpticalPortDirection OBJECT-TYPE
        SYNTAX         INTEGER {
                         out(1),
                         in(2)
                       }
        MAX-ACCESS     not-accessible
        STATUS         current
        DESCRIPTION    "The signal direction."
        ::= { tnOpticalPortEntry 1 }

    tnOpticalPortInsertionLoss OBJECT-TYPE
        SYNTAX         Integer32
        UNITS          "mB"
        MAX-ACCESS     read-only
        STATUS         current
        DESCRIPTION    "The insertion loss.  This will be supported on
                        all input to output flows."
        DEFVAL         { 840 }
        ::= { tnOpticalPortEntry 2 }

--------------------------------------------------------------------------------
-- Obsoleted OIDs
--------------------------------------------------------------------------------
--    tnRoadmPortTotal OBJECT-TYPE ::= { tnOpticalPortObjs 23 }
--    tnRoadmPortTable OBJECT-TYPE ::= { tnOpticalPortObjs 24 }
--    tnWaveKeyPortTotal OBJECT-TYPE ::= { tnOpticalPortObjs 25 }

--------------------------------------------------------------------------------
-- Wave Key Optical Port Table
--------------------------------------------------------------------------------
    tnWaveKeyPortTable OBJECT-TYPE
        SYNTAX         SEQUENCE OF TnWaveKeyPortEntry
        MAX-ACCESS     not-accessible
        STATUS         current
        DESCRIPTION    "This table is a compilation of attributes
                        associated with the ports on a Wave Key decode
                        supported optical card."
        ::= { tnOpticalPortObjs 26 }

    tnWaveKeyPortEntry OBJECT-TYPE
        SYNTAX         TnWaveKeyPortEntry
        MAX-ACCESS     not-accessible
        STATUS         current
        DESCRIPTION    ""
        INDEX { ifIndex }
        ::= { tnWaveKeyPortTable 1 }

    TnWaveKeyPortEntry ::=
        SEQUENCE {
            tnWaveKeyPortUnexpectedWKThreshIngress          Integer32,
            tnWaveKeyPortUnexpectedWKThreshEgress           Integer32,
            tnWaveKeyPortUnexpectedWKThreshAutoModeIngress  TruthValue,
            tnWaveKeyPortUnexpectedWKThreshAutoModeEgress   TruthValue,
            tnWaveKeyPortUnexpectedWKThreshDeltaIngress     Unsigned32,
            tnWaveKeyPortUnexpectedWKThreshDeltaEgress      Unsigned32,
            tnWaveKeyPortPresentUnexpectedWKThreshIngress   Integer32,
            tnWaveKeyPortPresentUnexpectedWKThreshEgress    Integer32,
            tnWaveKeyPortSupportedDirections                INTEGER,
            tnWaveKeyPortUnexpectedWKThreshAutoMaxOffsetIn  Unsigned32,
            tnWaveKeyPortUnexpectedWKThreshAutoMaxOffsetOut Unsigned32,
            tnWaveKeyPortCommonEgressPower                  Integer32,
            tnWaveKeyPortCommonIngressPower                 Integer32,
            tnWaveKeyPortDefaultPowerDeviationIn            Unsigned32,
            tnWaveKeyPortDefaultPowerDeviationOut           Unsigned32
        }

    tnWaveKeyPortUnexpectedWKThreshIngress OBJECT-TYPE
        SYNTAX         Integer32
        UNITS          "mBm"
        MAX-ACCESS     read-create
        STATUS         current
        DESCRIPTION    "Unexpected Wave Key filtering based on power
                        level, with -9900 means no measured power.

                        Current configurable range: -9900, -3000 to 1100."
        ::= { tnWaveKeyPortEntry 1 }

    tnWaveKeyPortUnexpectedWKThreshEgress OBJECT-TYPE
        SYNTAX         Integer32
        UNITS          "mBm"
        MAX-ACCESS     read-create
        STATUS         current
        DESCRIPTION    "Unexpected Wave Key filtering based on power
                        level, with -9900 means no measured power.

                        Current configurable range: -9900, -3000 to 1100."
        ::= { tnWaveKeyPortEntry 2 }

    tnWaveKeyPortUnexpectedWKThreshAutoModeIngress OBJECT-TYPE
        SYNTAX         TruthValue
        MAX-ACCESS     read-create
        STATUS         current
        DESCRIPTION    "An indication as to whether or not unexpected
                        Wave Key filtering is automatic or manual."
        DEFVAL         { true }
        ::= { tnWaveKeyPortEntry 3 }

    tnWaveKeyPortUnexpectedWKThreshAutoModeEgress OBJECT-TYPE
        SYNTAX         TruthValue
        MAX-ACCESS     read-create
        STATUS         current
        DESCRIPTION    "An indication as to whether or not unexpected
                        Wave Key filtering is automatic or manual."
        DEFVAL         { true }
        ::= { tnWaveKeyPortEntry 4 }

    tnWaveKeyPortUnexpectedWKThreshDeltaIngress OBJECT-TYPE
        SYNTAX         Unsigned32
        UNITS          "mB"
        MAX-ACCESS     read-create
        STATUS         current
        DESCRIPTION    "Unexpected Wave Key filtering power level delta.

                        Current configurable range: 0 to 3400."
        DEFVAL         { 500 }
        ::= { tnWaveKeyPortEntry 5 }

    tnWaveKeyPortUnexpectedWKThreshDeltaEgress OBJECT-TYPE
        SYNTAX         Unsigned32
        UNITS          "mB"
        MAX-ACCESS     read-create
        STATUS         current
        DESCRIPTION    "Unexpected Wave Key filtering power level delta.

                        Current configurable range: 0 to 3400."
        DEFVAL         { 500 }
        ::= { tnWaveKeyPortEntry 6 }

    tnWaveKeyPortPresentUnexpectedWKThreshIngress OBJECT-TYPE
        SYNTAX         Integer32
        UNITS          "mBm"
        MAX-ACCESS     read-only
        STATUS         current
        DESCRIPTION    "Present unexpected Wave Key filtering power level."
        ::= { tnWaveKeyPortEntry 7 }

    tnWaveKeyPortPresentUnexpectedWKThreshEgress OBJECT-TYPE
        SYNTAX         Integer32
        UNITS          "mBm"
        MAX-ACCESS     read-only
        STATUS         current
        DESCRIPTION    "Present unexpected Wave Key filtering power level."
        ::= { tnWaveKeyPortEntry 8 }

    tnWaveKeyPortSupportedDirections OBJECT-TYPE
        SYNTAX         INTEGER {
                         in(1),
                         out(2),
                         both(3)
                       }
        MAX-ACCESS     read-only
        STATUS         current
        DESCRIPTION    "The supported directions."
        ::= { tnWaveKeyPortEntry 9 }

    tnWaveKeyPortUnexpectedWKThreshAutoMaxOffsetIn OBJECT-TYPE
        SYNTAX         Unsigned32
        UNITS          "mB"
        MAX-ACCESS     read-create
        STATUS         current
        DESCRIPTION    "This attribute will clamp the total offset from
                        the average provisioned powers to the given power
                        level (ingress).

                        Current configurable range: 0 to 3400."
        DEFVAL         { 1000 }
        ::= { tnWaveKeyPortEntry 10 }

    tnWaveKeyPortUnexpectedWKThreshAutoMaxOffsetOut OBJECT-TYPE
        SYNTAX         Unsigned32
        UNITS          "mB"
        MAX-ACCESS     read-create
        STATUS         current
        DESCRIPTION    "This attribute will clamp the total offset from
                        the average provisioned powers to the given
                        power level (egress).

                        Current configurable range: 0 to 3400."
        DEFVAL         { 1000 }
        ::= { tnWaveKeyPortEntry 11 }

    tnWaveKeyPortCommonEgressPower OBJECT-TYPE
        SYNTAX         Integer32
        UNITS          "mBm"
        MAX-ACCESS     read-create
        STATUS         current
        DESCRIPTION    "Common Egress Power.  This is the per channel
                        default egress power.

                        Current configurable range: -3000 to 1100."
        DEFVAL         { 0 }
        ::= { tnWaveKeyPortEntry 12 }

    tnWaveKeyPortCommonIngressPower OBJECT-TYPE
        SYNTAX         Integer32
        UNITS          "mBm"
        MAX-ACCESS     read-create
        STATUS         current
        DESCRIPTION    "Common Ingress Power.  This is the per channel
                        default ingress power.

                        Current configurable range: -3000 to 1100."
        DEFVAL         { -2000 }
        ::= { tnWaveKeyPortEntry 13 }

    tnWaveKeyPortDefaultPowerDeviationIn OBJECT-TYPE
        SYNTAX         Unsigned32
        UNITS          "mB"
        MAX-ACCESS     read-create
        STATUS         current
        DESCRIPTION    "EPT - Default Deviation In.

                        Current configurable range: 0 to 1000."
        DEFVAL         { 150 }
        ::= { tnWaveKeyPortEntry 14 }

    tnWaveKeyPortDefaultPowerDeviationOut OBJECT-TYPE
        SYNTAX         Unsigned32
        UNITS          "mB"
        MAX-ACCESS     read-create
        STATUS         current
        DESCRIPTION    "EPT - Default Deviation Out.

                        Current configurable range: 0 to 1000."
        DEFVAL         { 150 }
        ::= { tnWaveKeyPortEntry 15 }

--------------------------------------------------------------------------------
-- Obsoleted OIDs
--------------------------------------------------------------------------------
--    tn10GELANPortTotal OBJECT-TYPE ::= { tnOpticalPortObjs 27 }
--    tn10GELANPortTable OBJECT-TYPE ::= { tnOpticalPortObjs 28 }

--------------------------------------------------------------------------------
-- Optical Fiber Table
--------------------------------------------------------------------------------
    tnOpticalFiberTable OBJECT-TYPE
        SYNTAX         SEQUENCE OF TnOpticalFiberEntry
        MAX-ACCESS     not-accessible
        STATUS         current
        DESCRIPTION    "Per port optical fiber characteristics."
        ::= { tnOpticalPortObjs 29 }

    tnOpticalFiberEntry OBJECT-TYPE
        SYNTAX         TnOpticalFiberEntry
        MAX-ACCESS     not-accessible
        STATUS         current
        DESCRIPTION    ""
        INDEX { ifIndex }
        ::= { tnOpticalFiberTable 1 }

    TnOpticalFiberEntry ::=
        SEQUENCE {
            tnOpticalFiberFixedLoss        Integer32,
            tnOpticalFiberLength           Integer32,
            tnOpticalFiberLossRating       Integer32,
            tnOpticalFiberDispersionRating Integer32
        }

    tnOpticalFiberFixedLoss OBJECT-TYPE
        SYNTAX         Integer32
        UNITS          "mB"
        MAX-ACCESS     read-create
        STATUS         current
        DESCRIPTION    "Current configurable range: -10000 to 100."
        DEFVAL         { 100 }
        ::= { tnOpticalFiberEntry 1 }

    tnOpticalFiberLength OBJECT-TYPE
        SYNTAX         Integer32
        UNITS          "km"
        MAX-ACCESS     read-create
        STATUS         current
        DESCRIPTION    "Current configurable range: -1 to 1000."
        DEFVAL         { -1 }
        ::= { tnOpticalFiberEntry 2 }

    tnOpticalFiberLossRating OBJECT-TYPE
        SYNTAX         Integer32
        UNITS          "mB/km"
        MAX-ACCESS     read-create
        STATUS         current
        DESCRIPTION    "Current configurable range: -10000 to 100."
        DEFVAL         { 100 }
        ::= { tnOpticalFiberEntry 3 }

    tnOpticalFiberDispersionRating OBJECT-TYPE
        SYNTAX         Integer32
        UNITS          "ps/(nm*km)"
        MAX-ACCESS     read-create
        STATUS         current
        DESCRIPTION    "Current configurable range: -1 to 1000."
        DEFVAL         { -1 }
        ::= { tnOpticalFiberEntry 4 }

--------------------------------------------------------------------------------
-- Obsoleted OIDs
--------------------------------------------------------------------------------
--    tnChannelAddDropPortTotal OBJECT-TYPE ::= { tnOpticalPortObjs 30 }
--    tnChannelAddDropPortTable OBJECT-TYPE ::= { tnOpticalPortObjs 31 }
--    tnQuadOC48MuxPortTotal OBJECT-TYPE ::= { tnOpticalPortObjs 32 }
--    tnQuadOC48MuxPortTable OBJECT-TYPE ::= { tnOpticalPortObjs 33 }
--    tnBbaLowGainPortTotal OBJECT-TYPE ::= { tnOpticalPortObjs 34 }
--    tnBbaLowGainPortTable OBJECT-TYPE ::= { tnOpticalPortObjs 35 }

--------------------------------------------------------------------------------
-- Loopback Port Table
--------------------------------------------------------------------------------
    tnLoopbackPortTable OBJECT-TYPE
        SYNTAX         SEQUENCE OF TnLoopbackPortEntry
        MAX-ACCESS     not-accessible
        STATUS         current
        DESCRIPTION    "This table is a compilation of attributes
                        associated with the ports on loopback supported
                        optical cards."
        ::= { tnOpticalPortObjs 36 }

    tnLoopbackPortEntry OBJECT-TYPE
        SYNTAX         TnLoopbackPortEntry
        MAX-ACCESS     not-accessible
        STATUS         current
        DESCRIPTION    ""
        INDEX { ifIndex }
        ::= { tnLoopbackPortTable 1 }

    TnLoopbackPortEntry ::=
        SEQUENCE {
            tnLoopbackPortDLEB TruthValue,
            tnLoopbackPortLLEB TruthValue,
            tnLoopbackPortTSEB TruthValue
        }

    tnLoopbackPortDLEB OBJECT-TYPE
        SYNTAX         TruthValue
        MAX-ACCESS     read-create
        STATUS         current
        DESCRIPTION    "Terminal Loopback, also known as diagnostic
                        loopback."
        DEFVAL         { false }
        ::= { tnLoopbackPortEntry 1 }

    tnLoopbackPortLLEB OBJECT-TYPE
        SYNTAX         TruthValue
        MAX-ACCESS     read-create
        STATUS         current
        DESCRIPTION    "Facility Loopback, also known as line loopback."
        DEFVAL         { false }
        ::= { tnLoopbackPortEntry 2 }

    tnLoopbackPortTSEB OBJECT-TYPE
        SYNTAX         TruthValue
        MAX-ACCESS     read-create
        STATUS         current
        DESCRIPTION    "Test signal generator."
        DEFVAL         { false }
        ::= { tnLoopbackPortEntry 3 }

--------------------------------------------------------------------------------
-- Obsoleted OIDs
--------------------------------------------------------------------------------
--    tnDcmPortTotal OBJECT-TYPE ::= { tnOpticalPortObjs 37 }
--    tnDcmPortTable OBJECT-TYPE ::= { tnOpticalPortObjs 38 }

--------------------------------------------------------------------------------
-- Insertion Loss Port Table
--------------------------------------------------------------------------------
    tnInsertionLossPortTable OBJECT-TYPE
        SYNTAX         SEQUENCE OF TnInsertionLossPortEntry
        MAX-ACCESS     not-accessible
        STATUS         current
        DESCRIPTION    "This table provides the same information as
                        tnOpticalPortTable, but with a different index."
        ::= { tnOpticalPortObjs 39 }

    tnInsertionLossPortEntry OBJECT-TYPE
        SYNTAX         TnInsertionLossPortEntry
        MAX-ACCESS     not-accessible
        STATUS         current
        DESCRIPTION    ""
        INDEX { ifIndex }
        ::= { tnInsertionLossPortTable 1 }

    TnInsertionLossPortEntry ::=
        SEQUENCE {
            tnInsertionLossPortEgress  Integer32,
            tnInsertionLossPortIngress Integer32
        }

    tnInsertionLossPortEgress OBJECT-TYPE
        SYNTAX         Integer32
        UNITS          "mB"
        MAX-ACCESS     read-only
        STATUS         current
        DESCRIPTION    "The egress insertion loss."
        ::= { tnInsertionLossPortEntry 1 }

    tnInsertionLossPortIngress OBJECT-TYPE
        SYNTAX         Integer32
        UNITS          "mB"
        MAX-ACCESS     read-only
        STATUS         current
        DESCRIPTION    "The ingress insertion loss."
        ::= { tnInsertionLossPortEntry 2 }

--------------------------------------------------------------------------------
-- Obsoleted OIDs
--------------------------------------------------------------------------------
--    tnQuadOC3or12MuxPortTotal OBJECT-TYPE ::= { tnOpticalPortObjs 40 }
--    tnQuadOC3or12MuxPortTable OBJECT-TYPE ::= { tnOpticalPortObjs 41 }
--    tnDecaGigEMuxPortTotal OBJECT-TYPE ::= { tnOpticalPortObjs 42 }
--    tnDecaGigEMuxPortTable OBJECT-TYPE ::= { tnOpticalPortObjs 43 }

--------------------------------------------------------------------------------
-- Protection Group Optical Port Table
--------------------------------------------------------------------------------
    tnProtectionGroupPortTable OBJECT-TYPE
        SYNTAX         SEQUENCE OF TnProtectionGroupPortEntry
        MAX-ACCESS     not-accessible
        STATUS         current
        DESCRIPTION    ""
        ::= { tnOpticalPortObjs 44 }

    tnProtectionGroupPortEntry OBJECT-TYPE
        SYNTAX         TnProtectionGroupPortEntry
        MAX-ACCESS     not-accessible
        STATUS         current
        DESCRIPTION    ""
        INDEX { ifIndex }
        ::= { tnProtectionGroupPortTable 1 }

    TnProtectionGroupPortEntry ::=
        SEQUENCE {
            tnProtectionGroupId TnApsGroupId
        }

    tnProtectionGroupId OBJECT-TYPE
        SYNTAX         TnApsGroupId
        MAX-ACCESS     read-only
        STATUS         current
        DESCRIPTION    "The APS group ID."
        DEFVAL         { 0 }
        ::= { tnProtectionGroupPortEntry 1 }

--------------------------------------------------------------------------------
-- Decision Threshold Voltage (DTV) Port Table
--------------------------------------------------------------------------------
    tnDTVPortTable OBJECT-TYPE
        SYNTAX         SEQUENCE OF TnDTVPortEntry
        MAX-ACCESS     not-accessible
        STATUS         current
        DESCRIPTION    ""
        ::= { tnOpticalPortObjs 45 }

    tnDTVPortEntry OBJECT-TYPE
        SYNTAX         TnDTVPortEntry
        MAX-ACCESS     not-accessible
        STATUS         current
        DESCRIPTION    ""
        INDEX { ifIndex }
        ::= { tnDTVPortTable 1 }

    TnDTVPortEntry ::=
        SEQUENCE {
            tnDTVPortControl            AluWdmEnabledDisabled,
            tnDTVPortValueAmplitude     Integer32,
            tnDTVPortValuePhase         Integer32
        }

    tnDTVPortControl OBJECT-TYPE
        SYNTAX         AluWdmEnabledDisabled
        MAX-ACCESS     read-create
        STATUS         current
        DESCRIPTION    "When this is set to disabled, the DTV amplitude
                        will be reset to the default value."
        DEFVAL         { enabled }
        ::= { tnDTVPortEntry 1 }

    tnDTVPortValueAmplitude OBJECT-TYPE
        SYNTAX         Integer32
        MAX-ACCESS     read-only
        STATUS         current
        DESCRIPTION    "Reports the current DTV amplitude value.  If the
                        module is not present, it returns -1.

                        Current range: -1 to 100."
        DEFVAL         { -1 }
        ::= { tnDTVPortEntry 2 }

    tnDTVPortValuePhase OBJECT-TYPE
        SYNTAX         Integer32
        MAX-ACCESS     read-only
        STATUS         current
        DESCRIPTION    "Reports the current DTV phase value.  If the module
                        is not present, it returns -1.

                        Current range: -1 to 100."
        DEFVAL         { -1 }
        ::= { tnDTVPortEntry 3 }

--------------------------------------------------------------------------------
-- Port Inventory Table
--------------------------------------------------------------------------------
    tnPortInventoryTable OBJECT-TYPE
        SYNTAX         SEQUENCE OF TnPortInventoryEntry
        MAX-ACCESS     not-accessible
        STATUS         current
        DESCRIPTION    ""
        ::= { tnOpticalPortObjs 46 }

    tnPortInventoryEntry OBJECT-TYPE
        SYNTAX         TnPortInventoryEntry
        MAX-ACCESS     not-accessible
        STATUS         current
        DESCRIPTION    ""
        INDEX { ifIndex }
        ::= { tnPortInventoryTable 1 }

    TnPortInventoryEntry ::= SEQUENCE {
        tnPortInventoryCLEI                     TropicCardCLEI,
        tnPortInventoryCompanyID                SnmpAdminString,
        tnPortInventoryDate                     SnmpAdminString,
        tnPortInventoryExtraData                SnmpAdminString,
        tnPortInventoryFactoryID                SnmpAdminString,
        tnPortInventoryManufacturingPartNumber  TropicCardManufacturingPartNumber,
        tnPortInventoryMnemonic                 SnmpAdminString,
        tnPortInventorySerialNumber             TropicCardSerialNumber,
        tnPortInventorySWPartNumber             SnmpAdminString
    }

    tnPortInventoryCLEI OBJECT-TYPE
        SYNTAX         TropicCardCLEI
        MAX-ACCESS     read-only
        STATUS         current
        DESCRIPTION    ""
        DEFVAL         { "" }
        ::= { tnPortInventoryEntry 1 }

    tnPortInventoryCompanyID OBJECT-TYPE
        SYNTAX         SnmpAdminString
        MAX-ACCESS     read-only
        STATUS         current
        DESCRIPTION    ""
        DEFVAL         { "" }
        ::= { tnPortInventoryEntry 2 }

    tnPortInventoryDate OBJECT-TYPE
        SYNTAX         SnmpAdminString
        MAX-ACCESS     read-only
        STATUS         current
        DESCRIPTION    ""
        DEFVAL         { "" }
        ::= { tnPortInventoryEntry 3 }

    tnPortInventoryExtraData OBJECT-TYPE
        SYNTAX         SnmpAdminString
        MAX-ACCESS     read-only
        STATUS         current
        DESCRIPTION    ""
        DEFVAL         { "" }
        ::= { tnPortInventoryEntry 4 }

    tnPortInventoryFactoryID OBJECT-TYPE
        SYNTAX         SnmpAdminString
        MAX-ACCESS     read-only
        STATUS         current
        DESCRIPTION    ""
        DEFVAL         { "" }
        ::= { tnPortInventoryEntry 5 }

    tnPortInventoryManufacturingPartNumber OBJECT-TYPE
        SYNTAX         TropicCardManufacturingPartNumber
        MAX-ACCESS     read-only
        STATUS         current
        DESCRIPTION    ""
        DEFVAL         { "" }
        ::= { tnPortInventoryEntry 6 }

    tnPortInventoryMnemonic OBJECT-TYPE
        SYNTAX         SnmpAdminString
        MAX-ACCESS     read-only
        STATUS         current
        DESCRIPTION    ""
        DEFVAL         { "" }
        ::= { tnPortInventoryEntry 7 }

    tnPortInventorySerialNumber OBJECT-TYPE
        SYNTAX         TropicCardSerialNumber
        MAX-ACCESS     read-only
        STATUS         current
        DESCRIPTION    ""
        DEFVAL         { "" }
        ::= { tnPortInventoryEntry 8 }

    tnPortInventorySWPartNumber OBJECT-TYPE
        SYNTAX         SnmpAdminString
        MAX-ACCESS     read-only
        STATUS         current
        DESCRIPTION    ""
        DEFVAL         { "" }
        ::= { tnPortInventoryEntry 9 }

--------------------------------------------------------------------------------
-- OTDR(Optical Time Domain Reflectometer) Port Scan Table
--------------------------------------------------------------------------------
    tnPortOtdrScanTable OBJECT-TYPE
        SYNTAX         SEQUENCE OF TnPortOtdrScanEntry
        MAX-ACCESS     not-accessible
        STATUS         current
        DESCRIPTION    "OTDR scan attributes."
        ::= { tnOpticalPortObjs 47 }

    tnPortOtdrScanEntry OBJECT-TYPE
        SYNTAX         TnPortOtdrScanEntry
        MAX-ACCESS     not-accessible
        STATUS         current
        DESCRIPTION    ""
        INDEX { ifIndex }
        ::= { tnPortOtdrScanTable 1 }

    TnPortOtdrScanEntry ::=
        SEQUENCE {
            tnPortOtdrScanProfileId                Integer32,
            tnPortOtdrScanDescription              SnmpAdminString,
            tnPortOtdrScanWaveLength               Integer32,
            tnPortOtdrScanPulseLength              Integer32,
            tnPortOtdrScanRange                    Integer32,
            tnPortOtdrScanResolution               Integer32,
            tnPortOtdrScanAvgTime                  Integer32,
            tnPortOtdrScanConnAddress              InterfaceIndexOrZero,
            tnPortOtdrScanFileName                 SnmpAdminString,
            tnPortOtdrScanControl                  INTEGER,
            tnPortOtdrScanStatus                   INTEGER,
            tnPortOtdrScanResult                   INTEGER,
            tnPortOtdrScanTimeRemaining            Integer32,
            tnPortOtdrScanLastSuccessfulTimeStamp  Unsigned32 
        }
    tnPortOtdrScanProfileId OBJECT-TYPE
        SYNTAX         Integer32
        MAX-ACCESS     read-create
        STATUS         current
        DESCRIPTION    "Profile Id to be used for the scan.

                        Current configurable range: 1 to 16.

                        After selecting a profile Id, if user tries to
                        change any of the parameter, profile id changes
                        to -1."
        DEFVAL         { 1 }
        ::= { tnPortOtdrScanEntry 1 }

    tnPortOtdrScanDescription OBJECT-TYPE
        SYNTAX         SnmpAdminString (SIZE(0..64))
        MAX-ACCESS     read-create
        STATUS         current
        DESCRIPTION    "Describes the different settings for
                        the scan."
        ::= { tnPortOtdrScanEntry 2 }

    tnPortOtdrScanWaveLength OBJECT-TYPE
        SYNTAX         Unsigned32
        UNITS          "nanometers"
        MAX-ACCESS     read-create
        STATUS         current
        DESCRIPTION    "The wavelength used for the OTDR scan.  The
                        wavelength is 1610 nm, and is not configurable."
        DEFVAL         { 1610 }
        ::= { tnPortOtdrScanEntry 3 }

    tnPortOtdrScanPulseLength OBJECT-TYPE
        SYNTAX         Unsigned32
        UNITS          "nanoseconds"
        MAX-ACCESS     read-create
        STATUS         current
        DESCRIPTION    "Pulse length.

                        Current configurable values: 5, 10, 30, 100,
                          300, 1000, 3000, 10000, and 20000."
        DEFVAL         { 300 }
        ::= { tnPortOtdrScanEntry 4 }

    tnPortOtdrScanRange OBJECT-TYPE
        SYNTAX         Unsigned32
        UNITS          "meters"
        MAX-ACCESS     read-create
        STATUS         current
        DESCRIPTION    "The range of the span that is being probed
                        in meters.

                        Current configurable values: 100, 500, 1000, 2000,
                          5000, 10000, 20000, 40000,80000, and 260000."
        DEFVAL         { 260000 }
        ::= { tnPortOtdrScanEntry 5 }

    tnPortOtdrScanResolution OBJECT-TYPE
        SYNTAX         Unsigned32
        UNITS          "centimeters"
        MAX-ACCESS     read-create
        STATUS         current
        DESCRIPTION    "Distance resolution of the OTDR scan.
             
                        Current configurable values are 4, 8, 16,
                        32, 64, 120, 250, 500, 1000, 2000, 4000,
                        8000 and 16000 centimeters."
        DEFVAL         { 250 }
        ::= { tnPortOtdrScanEntry 6 }

    tnPortOtdrScanAvgTime OBJECT-TYPE
        SYNTAX         Unsigned32(5..300)
        UNITS          "seconds"
        MAX-ACCESS     read-create
        STATUS         current
        DESCRIPTION    "Signal averaging time for a scan.

                        Current configurable range: 5 to 300."
        DEFVAL         { 180 }
        ::= { tnPortOtdrScanEntry 7 }

    tnPortOtdrScanConnAddress OBJECT-TYPE
        SYNTAX         InterfaceIndexOrZero
        MAX-ACCESS     read-only
        STATUS         current
        DESCRIPTION    "Specifies the assigned OTDR port that is
                        connected to the LD port."
        ::= { tnPortOtdrScanEntry 8 }

    tnPortOtdrScanFileName OBJECT-TYPE
        SYNTAX         SnmpAdminString (SIZE(0..25))
        MAX-ACCESS     read-create
        STATUS         current
        DESCRIPTION    "Name of the file to be used for scan. If not
                        provided,last filename will be used. The
                        filename needs to be alphanumeric."
        DEFVAL         { "" }
        ::= { tnPortOtdrScanEntry 9 }

    tnPortOtdrScanControl OBJECT-TYPE
        SYNTAX         INTEGER {
                         noCmd(1),
                         abort(2),
                         start(3)
                       }
        MAX-ACCESS     read-create
        STATUS         current
        DESCRIPTION    "Different states of scan."
        DEFVAL         { noCmd }
        ::= { tnPortOtdrScanEntry 10 }

    tnPortOtdrScanStatus OBJECT-TYPE
        SYNTAX         INTEGER {
                         available(1),
                         busy(2)
                       }
        MAX-ACCESS     read-only
        STATUS         current
        DESCRIPTION    "Current Scan status.

                          available: Available for use.
                          busy:      Scan is already running on the connected
                                     OTDR."
        ::= { tnPortOtdrScanEntry 11 }

    tnPortOtdrScanResult OBJECT-TYPE
        SYNTAX         INTEGER {
                         noScan(1),
                         fail(2),
                         inprogress(3),
                         abort(4),
                         complete(5)
                       }
        MAX-ACCESS     read-only
        STATUS         current
        DESCRIPTION    "Most recent scan Results for the LD Port.

                          noScan:     No scan result is available.
                          fail:       Last scan failed.
                          inprogress: Last scan not completed yet.
                          abort:      Last scan aborted.
                          complete:   Last scan completed successfully."
        DEFVAL         { noScan }
        ::= { tnPortOtdrScanEntry 12 }

    tnPortOtdrScanTimeRemaining OBJECT-TYPE
        SYNTAX         Unsigned32
        UNITS          "seconds"
        MAX-ACCESS     read-only
        STATUS         current
        DESCRIPTION    "Time remaining for scan to complete. It should
                        not exceed maximum scan time (300 seconds)."
        ::= { tnPortOtdrScanEntry 13 }

    tnPortOtdrScanLastSuccessfulTimeStamp OBJECT-TYPE
        SYNTAX         Unsigned32
        MAX-ACCESS     read-only
        STATUS         current
        DESCRIPTION    "The date and time when the last OTDR scan was
                        Successful."
        DEFVAL         { 0 }
        ::= { tnPortOtdrScanEntry 14 }

--------------------------------------------------------------------------------
-- FLEX Grid OTS Info Table
--------------------------------------------------------------------------------
    tnFlexgridOtsInfoTable OBJECT-TYPE
        SYNTAX         SEQUENCE OF TnFlexgridOtsInfoEntry
        MAX-ACCESS     not-accessible
        STATUS         current
        DESCRIPTION    ""
        ::= { tnOpticalPortObjs 48 }

    tnFlexgridOtsInfoEntry OBJECT-TYPE
        SYNTAX         TnFlexgridOtsInfoEntry
        MAX-ACCESS     not-accessible
        STATUS         current
        DESCRIPTION    ""
        INDEX { ifIndex }
        ::= { tnFlexgridOtsInfoTable 1 }

    TnFlexgridOtsInfoEntry ::=
        SEQUENCE {
            tnFlexgridOtsInfoLineGranularityMHz                  Unsigned32
    }

  tnFlexgridOtsInfoLineGranularityMHz OBJECT-TYPE
        SYNTAX         Unsigned32(0..100000)
        UNITS          "MHz"
        MAX-ACCESS     read-only
        STATUS         current
        DESCRIPTION    "Indicates the granularity (minimum slice size multiple)
                        of the optical line Wavelength Selective Switch.

                        If tnFlexgridOtsInfoLineWssIsFlexgrid is true, the upper
                        frequency edge of a slice aligns with reference
                        193.1 THz for n=0 (ITU G.694.1).

                        If tnFlexgridOtsInfoLineWssIsFlexgrid is false, the granularity
                        is the channel slot width centered on the regular ITU grid implied
                        by the granularity.

                        Values in MHz. Should be displayed in user interfaces in GHz."
        DEFVAL         { 0 }
        ::= { tnFlexgridOtsInfoEntry 1 }

--------------------------------------------------------------------------------
-- Optical Port Configuration
--------------------------------------------------------------------------------

--------------------------------------------------------------------------------
-- SDH Optical Port Config Scalars
--------------------------------------------------------------------------------
    tnSdhPortConfigAttributeTotal OBJECT-TYPE
        SYNTAX         Integer32
        MAX-ACCESS     read-only
        STATUS         current
        DESCRIPTION    ""
        ::= { tnOpticalPortConfig 1 }

--------------------------------------------------------------------------------
-- SDH Optical Port Config Table
--------------------------------------------------------------------------------
    tnSdhPortConfigTable OBJECT-TYPE
        SYNTAX         SEQUENCE OF TnSdhPortConfigEntry
        MAX-ACCESS     not-accessible
        STATUS         current
        DESCRIPTION    "The ports on SDH supported cards."
        ::= { tnOpticalPortConfig 2 }

    tnSdhPortConfigEntry OBJECT-TYPE
        SYNTAX         TnSdhPortConfigEntry
        MAX-ACCESS     not-accessible
        STATUS         current
        DESCRIPTION    ""
        INDEX { ifIndex }
        ::= { tnSdhPortConfigTable 1 }

    TnSdhPortConfigEntry ::=
        SEQUENCE {
            tnSdhPortRxSignalDegradeThreshold Unsigned32,
            tnSdhPortRxSignalFailThreshold    Unsigned32,
            tnSdhPortExpectedRxSectionTrace   SnmpAdminString,
            tnSdhPortTxSectionTrace           SnmpAdminString,
            tnSdhPortRxTIMSEnabled            TruthValue,
            tnSdhPortRxSectionTraceMode       INTEGER,
            tnSdhPortTxSectionTraceMode       INTEGER,
            tnSdhPortTxSynchStatusMessageDUS  TruthValue
        }

    tnSdhPortRxSignalDegradeThreshold OBJECT-TYPE
        SYNTAX         Unsigned32 (0..12)
        MAX-ACCESS     read-create
        STATUS         current
        DESCRIPTION    "Integer range 5 to 9, representing 10-5 to 10-9.

                        Current configurable range: 5 to 9."
        DEFVAL         { 7 }
        ::= { tnSdhPortConfigEntry 1 }

    tnSdhPortRxSignalFailThreshold OBJECT-TYPE
        SYNTAX         Unsigned32 (0..12)
        MAX-ACCESS     read-create
        STATUS         current
        DESCRIPTION    "Integer range 3 to 5, representing 10-3 to 10-5.

                        Current configurable range: 3 to 5."
        DEFVAL         { 5 }
        ::= { tnSdhPortConfigEntry 2 }

    tnSdhPortExpectedRxSectionTrace OBJECT-TYPE
        SYNTAX         SnmpAdminString (SIZE(0..255))
        MAX-ACCESS     read-create
        STATUS         current
        DESCRIPTION    ""
        DEFVAL         { "" }
        ::= { tnSdhPortConfigEntry 3 }

    tnSdhPortTxSectionTrace OBJECT-TYPE
        SYNTAX         SnmpAdminString (SIZE(0..255))
        MAX-ACCESS     read-create
        STATUS         current
        DESCRIPTION    ""
        DEFVAL         { "" }
        ::= { tnSdhPortConfigEntry 4 }

    tnSdhPortRxTIMSEnabled OBJECT-TYPE
        SYNTAX         TruthValue
        MAX-ACCESS     read-create
        STATUS         current
        DESCRIPTION    ""
        DEFVAL         { false }
        ::= { tnSdhPortConfigEntry 5 }

    tnSdhPortRxSectionTraceMode OBJECT-TYPE
        SYNTAX         INTEGER {
                         off(1),
                         mode15byte(2)
                       }
        MAX-ACCESS     read-create
        STATUS         current
        DESCRIPTION    ""
        DEFVAL         { off }
        ::= { tnSdhPortConfigEntry 6 }

    tnSdhPortTxSectionTraceMode OBJECT-TYPE
        SYNTAX         INTEGER {
                         off(1),
                         mode15byte(2)
                       }
        MAX-ACCESS     read-create
        STATUS         current
        DESCRIPTION    ""
        DEFVAL         { off }
        ::= { tnSdhPortConfigEntry 7 }

    tnSdhPortTxSynchStatusMessageDUS OBJECT-TYPE
        SYNTAX         TruthValue
        MAX-ACCESS     read-create
        STATUS         current
        DESCRIPTION    ""
        DEFVAL         { false }
        ::= { tnSdhPortConfigEntry 8 }

--    obsolete
--    tnOC48STM16PortConfigAttributeTotal OBJECT-TYPE ::= { tnOpticalPortConfig 3 }
--    tnOC48STM16PortConfigTable OBJECT-TYPE ::= { tnOpticalPortConfig 4 }
--    tnOC192STM64PortConfigAttributeTotal OBJECT-TYPE ::= { tnOpticalPortConfig 5 }
--    tnOC192STM64PortConfigTable OBJECT-TYPE ::= { tnOpticalPortConfig 6 }
--    tnQuadOC48STM16MuxPortConfigAttributeTotal OBJECT-TYPE ::= { tnOpticalPortConfig 7 }
--    tnQuadOC48STM16MuxPortConfigTable OBJECT-TYPE ::= { tnOpticalPortConfig 8 }
--    tnQuadOC3or12STM1or4MuxPortConfigAttributeTotal OBJECT-TYPE ::= { tnOpticalPortConfig 9 }
--    tnQuadOC3or12STM1or4MuxPortConfigTable OBJECT-TYPE ::= { tnOpticalPortConfig 10 }
--    tnBandFilterPortConfigAttributeTotal OBJECT-TYPE ::= { tnOpticalPortConfig 11 }
--    tnBandFilterPortConfigTable OBJECT-TYPE ::= { tnOpticalPortConfig 12 }

--------------------------------------------------------------------------------
-- OSC Optical Port Config Scalars
--------------------------------------------------------------------------------
    tnOscPortConfigAttributeTotal OBJECT-TYPE
        SYNTAX         Integer32
        MAX-ACCESS     read-only
        STATUS         current
        DESCRIPTION    ""
        ::= { tnOpticalPortConfig 13 }

--------------------------------------------------------------------------------
-- OSC Optical Port Config Table
--------------------------------------------------------------------------------
    tnOscPortConfigTable OBJECT-TYPE
        SYNTAX         SEQUENCE OF TnOscPortConfigEntry
        MAX-ACCESS     not-accessible
        STATUS         current
        DESCRIPTION    "The ports on an OSC optical card."
        ::= { tnOpticalPortConfig 14 }

    tnOscPortConfigEntry OBJECT-TYPE
        SYNTAX         TnOscPortConfigEntry
        MAX-ACCESS     not-accessible
        STATUS         current
        DESCRIPTION    ""
        INDEX { ifIndex }
        ::= { tnOscPortConfigTable 1 }

    TnOscPortConfigEntry ::=
        SEQUENCE {
            tnOscPortConfigFunction INTEGER
--            obsolete
--            tnOscPortPhyDeviceReset INTEGER
        }

    tnOscPortConfigFunction OBJECT-TYPE
        SYNTAX         INTEGER {
                         signal(1),
                         line(2),
                         inv(3),
                         osc(4),
                         oscSfp(5)
                       }
        MAX-ACCESS     read-only
        STATUS         current
        DESCRIPTION    "Indicates the functional type of this OSC port."
        ::= { tnOscPortConfigEntry 1 }

--    obsolete
--    tnOscPortPhyDeviceReset OBJECT-TYPE ::= { tnOscPortConfigEntry 2 }
--    tnChFilterPortConfigAttributeTotal OBJECT-TYPE ::= { tnOpticalPortConfig 15 }
--    tnChFilterPortConfigTable OBJECT-TYPE ::= { tnOpticalPortConfig 16 }
--    tnChAddDropPortConfigAttributeTotal OBJECT-TYPE ::= { tnOpticalPortConfig 17 }
--    tnChAddDropPortConfigTable OBJECT-TYPE ::= { tnOpticalPortConfig 18 }
--    tnBbaHgPortConfigAttributeTotal OBJECT-TYPE ::= { tnOpticalPortConfig 19 }
--    tnBbaHgPortConfigTable OBJECT-TYPE ::= { tnOpticalPortConfig 20 }
--    tnBbaLgPortConfigAttributeTotal OBJECT-TYPE ::= { tnOpticalPortConfig 21 }
--    tnBbaLgPortConfigTable OBJECT-TYPE ::= { tnOpticalPortConfig 22 }
--    tnPpsPortConfigAttributeTotal OBJECT-TYPE ::= { tnOpticalPortConfig 23 }
--    tnPpsPortConfigTable OBJECT-TYPE ::= { tnOpticalPortConfig 24 }
--    tnDualGigEMuxPortConfigAttributeTotal OBJECT-TYPE ::= { tnOpticalPortConfig 25 }
--    tnDualGigEMuxPortConfigTable OBJECT-TYPE ::= { tnOpticalPortConfig 26 }
--    tnRoadmPortConfigAttributeTotal OBJECT-TYPE ::= { tnOpticalPortConfig 27 }
--    tnRoadmPortConfigTable OBJECT-TYPE ::= { tnOpticalPortConfig 28 }
--    tn10GigELANPortConfigAttributeTotal OBJECT-TYPE ::= { tnOpticalPortConfig 29 }
--    tn10GigELANPortConfigTable OBJECT-TYPE ::= { tnOpticalPortConfig 30 }

--------------------------------------------------------------------------------
-- Dispersion Compensation Module Optical Port Config Scalars
--------------------------------------------------------------------------------
    tnDcmPortConfigAttributeTotal OBJECT-TYPE
        SYNTAX         Integer32
        MAX-ACCESS     read-only
        STATUS         current
        DESCRIPTION    ""
        ::= { tnOpticalPortConfig 31 }

--------------------------------------------------------------------------------
-- Dispersion Compensation Module Optical Port Config Table
--------------------------------------------------------------------------------
    tnDcmPortConfigTable OBJECT-TYPE
        SYNTAX         SEQUENCE OF TnDcmPortConfigEntry
        MAX-ACCESS     not-accessible
        STATUS         current
        DESCRIPTION    "The ports on a DCM optical card."
        ::= { tnOpticalPortConfig 32 }

    tnDcmPortConfigEntry OBJECT-TYPE
        SYNTAX         TnDcmPortConfigEntry
        MAX-ACCESS     not-accessible
        STATUS         current
        DESCRIPTION    ""
        INDEX { ifIndex }
        ::= { tnDcmPortConfigTable 1 }

    TnDcmPortConfigEntry ::=
        SEQUENCE {
            tnDcmPortConfigFunction INTEGER
        }

    tnDcmPortConfigFunction OBJECT-TYPE
        SYNTAX         INTEGER {
                         dcmOutThruIn(1),
                         thruOutDcmIn(2),
                         dcmInOut(3)
                       }
        MAX-ACCESS     read-only
        STATUS         current
        DESCRIPTION    "Indicates the functional type of this Dispersion
                        Compensation Module port."
        ::= { tnDcmPortConfigEntry 1 }

--    obsolete
--    tnDecaGigEMuxPortConfigAttributeTotal OBJECT-TYPE ::= { tnOpticalPortConfig 33 }
--    tnDecaGigEMuxPortConfigTable OBJECT-TYPE ::= { tnOpticalPortConfig 34 }

--------------------------------------------------------------------------------
-- SONET Optical Port Config Scalars
--------------------------------------------------------------------------------
    tnSonetPortConfigAttributeTotal OBJECT-TYPE
        SYNTAX         Integer32
        MAX-ACCESS     read-only
        STATUS         current
        DESCRIPTION    ""
        ::= { tnOpticalPortConfig 35 }

--------------------------------------------------------------------------------
-- SONET Optical Port Config Table
--------------------------------------------------------------------------------
    tnSonetPortConfigTable OBJECT-TYPE
        SYNTAX         SEQUENCE OF TnSonetPortConfigEntry
        MAX-ACCESS     not-accessible
        STATUS         current
        DESCRIPTION    "The ports on SONET supported cards."
        ::= { tnOpticalPortConfig 36 }

    tnSonetPortConfigEntry OBJECT-TYPE
        SYNTAX         TnSonetPortConfigEntry
        MAX-ACCESS     not-accessible
        STATUS         current
        DESCRIPTION    ""
        INDEX { ifIndex }
        ::= { tnSonetPortConfigTable 1 }

    TnSonetPortConfigEntry ::=
        SEQUENCE {
            tnSonetPortRxSignalDegradeThreshold Unsigned32,
            tnSonetPortRxSignalFailThreshold    Unsigned32,
            tnSonetPortExpectedRxSectionTrace   SnmpAdminString,
            tnSonetPortTxSectionTrace           SnmpAdminString,
            tnSonetPortRxTIMSEnabled            TruthValue,
            tnSonetPortRxSectionTraceMode       INTEGER,
            tnSonetPortTxSectionTraceMode       INTEGER,
            tnSonetPortTxSynchStatusMessageDUS  TruthValue
        }

    tnSonetPortRxSignalDegradeThreshold OBJECT-TYPE
        SYNTAX         Unsigned32 (0..12)
        MAX-ACCESS     read-create
        STATUS         current
        DESCRIPTION    "Integer range 5 to 9, representing 10-5 to 10-9.

                        Current configurable range: 5 to 9."
        DEFVAL         { 7 }
        ::= { tnSonetPortConfigEntry 1 }

    tnSonetPortRxSignalFailThreshold OBJECT-TYPE
        SYNTAX         Unsigned32 (0..12)
        MAX-ACCESS     read-create
        STATUS         current
        DESCRIPTION    "Integer range 3 to 5, representing 10-3 to 10-5.

                        Current configurable range: 3 to 5."
        DEFVAL         { 5 }
        ::= { tnSonetPortConfigEntry 2 }

    tnSonetPortExpectedRxSectionTrace OBJECT-TYPE
        SYNTAX         SnmpAdminString (SIZE(0..255))
        MAX-ACCESS     read-create
        STATUS         current
        DESCRIPTION    ""
        DEFVAL         { "" }
        ::= { tnSonetPortConfigEntry 3 }

    tnSonetPortTxSectionTrace OBJECT-TYPE
        SYNTAX         SnmpAdminString (SIZE(0..255))
        MAX-ACCESS     read-create
        STATUS         current
        DESCRIPTION    ""
        DEFVAL         { "" }
        ::= { tnSonetPortConfigEntry 4 }

    tnSonetPortRxTIMSEnabled OBJECT-TYPE
        SYNTAX         TruthValue
        MAX-ACCESS     read-create
        STATUS         current
        DESCRIPTION    ""
        DEFVAL         { false }
        ::= { tnSonetPortConfigEntry 5 }

    tnSonetPortRxSectionTraceMode OBJECT-TYPE
        SYNTAX         INTEGER {
                         off(1),
                         mode64byteCrLf(2)
                       }
        MAX-ACCESS     read-create
        STATUS         current
        DESCRIPTION    ""
        DEFVAL         { off }
        ::= { tnSonetPortConfigEntry 6 }

    tnSonetPortTxSectionTraceMode OBJECT-TYPE
        SYNTAX         INTEGER {
                         off(1),
                         mode64byteCrLf(2)
                       }
        MAX-ACCESS     read-create
        STATUS         current
        DESCRIPTION    ""
        DEFVAL         { off }
        ::= { tnSonetPortConfigEntry 7 }

    tnSonetPortTxSynchStatusMessageDUS OBJECT-TYPE
        SYNTAX         TruthValue
        MAX-ACCESS     read-create
        STATUS         current
        DESCRIPTION    ""
        DEFVAL         { false }
        ::= { tnSonetPortConfigEntry 8 }

--    obsolete
--    tnExternalDcuPortConfigAttributeTotal OBJECT-TYPE ::= { tnOpticalPortConfig 37 }
--    tnExternalDcuPortConfigTable OBJECT-TYPE ::= { tnOpticalPortConfig 38 }

--------------------------------------------------------------------------------
-- Digital Wrapper Optical Port Config Scalars
--------------------------------------------------------------------------------
    tnDigitalWrapperPortConfigAttributeTotal OBJECT-TYPE
        SYNTAX         Integer32
        MAX-ACCESS     read-only
        STATUS         current
        DESCRIPTION    ""
        ::= { tnOpticalPortConfig 39 }

--------------------------------------------------------------------------------
-- Digital Wrapper Optical Port Config Table
--------------------------------------------------------------------------------
    tnDigitalWrapperPortConfigTable OBJECT-TYPE
        SYNTAX         SEQUENCE OF TnDigitalWrapperPortConfigEntry
        MAX-ACCESS     not-accessible
        STATUS         current
        DESCRIPTION    "The ports on Digital Wrapper supported cards."
        ::= { tnOpticalPortConfig 40 }

    tnDigitalWrapperPortConfigEntry OBJECT-TYPE
        SYNTAX         TnDigitalWrapperPortConfigEntry
        MAX-ACCESS     not-accessible
        STATUS         current
        DESCRIPTION    ""
        INDEX { ifIndex }
        ::= { tnDigitalWrapperPortConfigTable 1 }

    TnDigitalWrapperPortConfigEntry ::=
        SEQUENCE {
            tnDwPortRxRSBERSDThresh  Unsigned32,
            tnDwPortRxRSBERSFThresh  Unsigned32,
            tnDwPortDwMode           AluWdmFecMode,
            tnDwPortPMTTIEnabled     TruthValue,
            tnDwPortPTIEnabled       TruthValue
        }

    tnDwPortRxRSBERSDThresh OBJECT-TYPE
        SYNTAX         Unsigned32
        MAX-ACCESS     read-create
        STATUS         current
        DESCRIPTION    "BER threshold to raise SD condition on Rx.
                        Specified value n means BER threshold of 10^-n.

                        Current configurable range: 3 to 9."
        DEFVAL         { 4 }
        ::= { tnDigitalWrapperPortConfigEntry 1 }

    tnDwPortRxRSBERSFThresh OBJECT-TYPE
        SYNTAX         Unsigned32
        MAX-ACCESS     read-create
        STATUS         current
        DESCRIPTION    "Sets BER threshold to raise SF condition on Rx.
                        Specified value n means BER threshold of 10^-n.

                        Current configurable range: 3 to 9."
        DEFVAL         { 3 }
        ::= { tnDigitalWrapperPortConfigEntry 2 }

    tnDwPortDwMode OBJECT-TYPE
        SYNTAX         AluWdmFecMode
        MAX-ACCESS     read-create
        STATUS         current
        DESCRIPTION    "Digital Wrapper mode.  Setting this attribute
                        to a value of disabled is not supported."
        DEFVAL         { g709Fec }
        ::= { tnDigitalWrapperPortConfigEntry 3 }

    tnDwPortPMTTIEnabled OBJECT-TYPE
        SYNTAX         TruthValue
        MAX-ACCESS     read-create
        STATUS         current
        DESCRIPTION    "Digital Wrapper Trail Trace Identifier."
        DEFVAL         { false }
        ::= { tnDigitalWrapperPortConfigEntry 4 }

    tnDwPortPTIEnabled OBJECT-TYPE
        SYNTAX         TruthValue
        MAX-ACCESS     read-create
        STATUS         current
        DESCRIPTION    "Digital Wrapper Payload Type Indication."
        DEFVAL         { false }
        ::= { tnDigitalWrapperPortConfigEntry 5 }

--------------------------------------------------------------------------------
-- Network Port Config Scalars
--------------------------------------------------------------------------------
    tnNetworkPortConfigAttributeTotal OBJECT-TYPE
        SYNTAX         Integer32
        MAX-ACCESS     read-only
        STATUS         current
        DESCRIPTION    ""
        ::= { tnOpticalPortConfig 41 }

--------------------------------------------------------------------------------
-- Network Port Config Table
--------------------------------------------------------------------------------
    tnNetworkPortConfigTable OBJECT-TYPE
        SYNTAX         SEQUENCE OF TnNetworkPortConfigEntry
        MAX-ACCESS     not-accessible
        STATUS         current
        DESCRIPTION    "The network ports on optical transponder cards."
        ::= { tnOpticalPortConfig 42 }

    tnNetworkPortConfigEntry OBJECT-TYPE
        SYNTAX         TnNetworkPortConfigEntry
        MAX-ACCESS     not-accessible
        STATUS         current
        DESCRIPTION    ""
        INDEX { ifIndex }
        ::= { tnNetworkPortConfigTable 1 }

    TnNetworkPortConfigEntry ::=
        SEQUENCE {
--            obsolete
--            tnNwPortOchStatusRx        TnOchStatus,
--            tnNwPortOchStatusTx        TnOchStatus,
            tnNwPortProgrammedChannel  Unsigned32,
            tnNwPortChannelRx          Unsigned32,
            tnNwPortChannelSpacing     Unsigned32
        }

--    obsolete
--    tnNwPortOchStatusRx OBJECT-TYPE ::= { tnNetworkPortConfigEntry 1 }
--    tnNwPortOchStatusTx OBJECT-TYPE ::= { tnNetworkPortConfigEntry 2 }

    tnNwPortProgrammedChannel OBJECT-TYPE
        SYNTAX         Unsigned32
        MAX-ACCESS     read-create
        STATUS         current
        DESCRIPTION    "The programmed ITU channel.

                        Current configurable range: 0 to 10119."
        DEFVAL         { 0 }
        ::= { tnNetworkPortConfigEntry 3 }

    tnNwPortChannelRx OBJECT-TYPE
        SYNTAX         Unsigned32
        MAX-ACCESS     read-create
        STATUS         current
        DESCRIPTION    "The Rx ITU channel.

                        Current configurable range: 0 to 10119."
        DEFVAL         { 0 }
        ::= { tnNetworkPortConfigEntry 4 }

    tnNwPortChannelSpacing OBJECT-TYPE
        SYNTAX         Unsigned32
        UNITS          "GHz"
        MAX-ACCESS     read-create
        STATUS         current
        DESCRIPTION    "This Specifies the channel spacing to use for
                        line ports.
                        1 - 100GHz
                        2 - 50GHz."
        DEFVAL         { 1 }
        ::= { tnNetworkPortConfigEntry 5 }

--    obsolete
--    tnMsaHgPortConfigAttributeTotal OBJECT-TYPE ::= { tnOpticalPortConfig 43 }
--    tnMsaHgPortConfigTable OBJECT-TYPE ::= { tnOpticalPortConfig 44 }
--    tnCmd42PortConfigAttributeTotal OBJECT-TYPE ::= { tnOpticalPortConfig 45 }
--    tnCmd42PortConfigTable OBJECT-TYPE ::= { tnOpticalPortConfig 46 }
--    tnWssX9PortConfigAttributeTotal OBJECT-TYPE ::= { tnOpticalPortConfig 47 }
--    tnWssX9PortConfigTable OBJECT-TYPE ::= { tnOpticalPortConfig 48 }

--------------------------------------------------------------------------------
-- Sfp Port Config Scalars
--------------------------------------------------------------------------------
    tnSfpPortConfigAttributeTotal OBJECT-TYPE
        SYNTAX         Integer32
        MAX-ACCESS     read-only
        STATUS         current
        DESCRIPTION    ""
        ::= { tnOpticalPortConfig 49 }

--------------------------------------------------------------------------------
-- SFP Port Config Table
--------------------------------------------------------------------------------
    tnSfpPortConfigTable OBJECT-TYPE
        SYNTAX         SEQUENCE OF TnSfpPortConfigEntry
        MAX-ACCESS     not-accessible
        STATUS         current
        DESCRIPTION    "The SFP supported ports."
        ::= { tnOpticalPortConfig 50 }

    tnSfpPortConfigEntry OBJECT-TYPE
        SYNTAX         TnSfpPortConfigEntry
        MAX-ACCESS     not-accessible
        STATUS         current
        DESCRIPTION    ""
        INDEX { ifIndex }
        ::= { tnSfpPortConfigTable 1 }

    TnSfpPortConfigEntry ::=
        SEQUENCE {
            tnSfpPortType  TnSfpType
        }

    tnSfpPortType OBJECT-TYPE
        SYNTAX         TnSfpType
        MAX-ACCESS     read-create
        STATUS         current
        DESCRIPTION    ""
        ::= { tnSfpPortConfigEntry 1 }

--    obsolete
--    tn1xMR2dot5GPortConfigAttributeTotal OBJECT-TYPE ::= { tnOpticalPortConfig 51 }
--    tn1xMR2dot5GPortConfigTable OBJECT-TYPE ::= { tnOpticalPortConfig 52 }

--------------------------------------------------------------------------------
-- OPSA Optical Port Config Scalars
--------------------------------------------------------------------------------
    tnOpsaPortConfigAttributeTotal OBJECT-TYPE
        SYNTAX         Integer32
        MAX-ACCESS     read-only
        STATUS         current
        DESCRIPTION    ""
        ::= { tnOpticalPortConfig 53 }

--------------------------------------------------------------------------------
-- OPSA Optical Port Config Table
--------------------------------------------------------------------------------
    tnOpsaPortConfigTable OBJECT-TYPE
        SYNTAX         SEQUENCE OF TnOpsaPortConfigEntry
        MAX-ACCESS     not-accessible
        STATUS         current
        DESCRIPTION    "The ports on an OPSA optical card."
        ::= { tnOpticalPortConfig 54 }

    tnOpsaPortConfigEntry OBJECT-TYPE
        SYNTAX         TnOpsaPortConfigEntry
        MAX-ACCESS     not-accessible
        STATUS         current
        DESCRIPTION    ""
        INDEX { ifIndex }
        ::= { tnOpsaPortConfigTable 1 }

    TnOpsaPortConfigEntry ::=
        SEQUENCE {
            tnOpsaPortConfigFunction              INTEGER
--            obsolete
--            tnOpsaPortSwitchingThreshold          Integer32,   
--            tnOpsaPortSwitchingThresholdTolerance Unsigned32, 
--            tnOpsaPortTransmitAttenuation         Integer32,   
--            tnOpsaPortSwitchingThreshCalcControl  INTEGER      
        }

    tnOpsaPortConfigFunction OBJECT-TYPE
        SYNTAX         INTEGER {
                         signal(1),
                         workingProtected(2)
                       }
        MAX-ACCESS     read-only
        STATUS         current
        DESCRIPTION    "Indicates the functional type of this OPSA port."
        ::= { tnOpsaPortConfigEntry 1 }

--    obsolete
--    tnOpsaPortSwitchingThreshold OBJECT-TYPE ::= { tnOpsaPortConfigEntry 2 }
--    tnOpsaPortSwitchingThresholdTolerance OBJECT-TYPE ::= { tnOpsaPortConfigEntry 3 }
--    tnOpsaPortTransmitAttenuation OBJECT-TYPE ::= { tnOpsaPortConfigEntry 4 }
--    tnOpsaPortSwitchingThreshCalcControl OBJECT-TYPE ::= { tnOpsaPortConfigEntry 5 }

--------------------------------------------------------------------------------
-- 11STMM10 Optical Port Config Scalars
--------------------------------------------------------------------------------
    tn11stmm10PortConfigAttributeTotal OBJECT-TYPE
        SYNTAX         Integer32
        MAX-ACCESS     read-only
        STATUS         current
        DESCRIPTION    ""
        ::= { tnOpticalPortConfig 55 }

--------------------------------------------------------------------------------
-- 11STMM10 Optical Port Config Table
--------------------------------------------------------------------------------
    tn11stmm10PortConfigTable OBJECT-TYPE
        SYNTAX         SEQUENCE OF Tn11stmm10PortConfigEntry
        MAX-ACCESS     not-accessible
        STATUS         current
        DESCRIPTION    "The ports on a 11STMM10 optical card."
        ::= { tnOpticalPortConfig 56 }

    tn11stmm10PortConfigEntry OBJECT-TYPE
        SYNTAX         Tn11stmm10PortConfigEntry
        MAX-ACCESS     not-accessible
        STATUS         current
        DESCRIPTION    ""
        INDEX { ifIndex }
        ::= { tn11stmm10PortConfigTable 1 }

    Tn11stmm10PortConfigEntry ::=
        SEQUENCE {
            tn11stmm10PortConfigFunction INTEGER
        }

    tn11stmm10PortConfigFunction OBJECT-TYPE
        SYNTAX         INTEGER {
                         network(1),
                         client(2)
                       }
        MAX-ACCESS     read-only
        STATUS         current
        DESCRIPTION    "Indicates the functional type of this 11STMM10
                        port."
        ::= { tn11stmm10PortConfigEntry 1 }

--------------------------------------------------------------------------------
-- 11STAR1 Optical Port Config Scalars
--------------------------------------------------------------------------------
    tn11star1PortConfigAttributeTotal OBJECT-TYPE
        SYNTAX         Integer32
        MAX-ACCESS     read-only
        STATUS         current
        DESCRIPTION    ""
        ::= { tnOpticalPortConfig 57 }

--------------------------------------------------------------------------------
-- 11STAR1 Optical Port Config Table
--------------------------------------------------------------------------------
    tn11star1PortConfigTable OBJECT-TYPE
        SYNTAX         SEQUENCE OF Tn11star1PortConfigEntry
        MAX-ACCESS     not-accessible
        STATUS         current
        DESCRIPTION    "The ports on a 11STAR1 optical card."
        ::= { tnOpticalPortConfig 58 }

    tn11star1PortConfigEntry OBJECT-TYPE
        SYNTAX         Tn11star1PortConfigEntry
        MAX-ACCESS     not-accessible
        STATUS         current
        DESCRIPTION    ""
        INDEX { ifIndex }
        ::= { tn11star1PortConfigTable 1 }

    Tn11star1PortConfigEntry ::=
        SEQUENCE {
            tn11star1PortConfigFunction INTEGER
        }

    tn11star1PortConfigFunction OBJECT-TYPE
        SYNTAX         INTEGER {
                         network(1),
                         client(2)
                       }
        MAX-ACCESS     read-only
        STATUS         current
        DESCRIPTION    "Indicates the functional type of this 11STAR1 port."
        ::= { tn11star1PortConfigEntry 1 }

--------------------------------------------------------------------------------
-- AHPHG Optical Port Config Scalars
--------------------------------------------------------------------------------
    tnAhphgPortConfigAttributeTotal OBJECT-TYPE
        SYNTAX         Integer32
        MAX-ACCESS     read-only
        STATUS         current
        DESCRIPTION    ""
        ::= { tnOpticalPortConfig 59 }

--------------------------------------------------------------------------------
-- AHPHG Optical Port Config Table
--------------------------------------------------------------------------------
    tnAhphgPortConfigTable OBJECT-TYPE
        SYNTAX         SEQUENCE OF TnAhphgPortConfigEntry
        MAX-ACCESS     not-accessible
        STATUS         current
        DESCRIPTION    "The ports on an AHPHG optical card."
        ::= { tnOpticalPortConfig 60 }

    tnAhphgPortConfigEntry OBJECT-TYPE
        SYNTAX         TnAhphgPortConfigEntry
        MAX-ACCESS     not-accessible
        STATUS         current
        DESCRIPTION    ""
        INDEX { ifIndex }
        ::= { tnAhphgPortConfigTable 1 }

    TnAhphgPortConfigEntry ::=
        SEQUENCE {
            tnAhphgPortConfigFunction INTEGER
        }

    tnAhphgPortConfigFunction OBJECT-TYPE
        SYNTAX         INTEGER {
                         line(1),
                         signal(2),
                         dcm(3),
                         inv(4),
                         osc(5)
                       }
        MAX-ACCESS     read-only
        STATUS         current
        DESCRIPTION    "Indicates the functional type of this AHPHG port."
        ::= { tnAhphgPortConfigEntry 1 }

--------------------------------------------------------------------------------
-- ALPHG Optical Port Config Scalars
--------------------------------------------------------------------------------
    tnAlphgPortConfigAttributeTotal OBJECT-TYPE
        SYNTAX         Integer32
        MAX-ACCESS     read-only
        STATUS         current
        DESCRIPTION    ""
        ::= { tnOpticalPortConfig 61 }

--------------------------------------------------------------------------------
-- ALPHG Optical Port Config Table
--------------------------------------------------------------------------------
    tnAlphgPortConfigTable OBJECT-TYPE
        SYNTAX         SEQUENCE OF TnAlphgPortConfigEntry
        MAX-ACCESS     not-accessible
        STATUS         current
        DESCRIPTION    "The ports on an ALPHG optical card."
        ::= { tnOpticalPortConfig 62 }

    tnAlphgPortConfigEntry OBJECT-TYPE
        SYNTAX         TnAlphgPortConfigEntry
        MAX-ACCESS     not-accessible
        STATUS         current
        DESCRIPTION    ""
        INDEX { ifIndex }
        ::= { tnAlphgPortConfigTable 1 }

    TnAlphgPortConfigEntry ::=
        SEQUENCE {
            tnAlphgPortConfigFunction INTEGER
        }

    tnAlphgPortConfigFunction OBJECT-TYPE
        SYNTAX         INTEGER {
                         line(1),
                         signal(2),
                         dcm(3),
                         inv(4),
                         osc(5)
                       }
        MAX-ACCESS     read-only
        STATUS         current
        DESCRIPTION    "Indicates the functional type of this ALPHG port."
        ::= { tnAlphgPortConfigEntry 1 }

--------------------------------------------------------------------------------
-- CWR8 Optical Port Config Scalars
--------------------------------------------------------------------------------
    tnCwr8PortConfigAttributeTotal OBJECT-TYPE
        SYNTAX         Integer32
        MAX-ACCESS     read-only
        STATUS         current
        DESCRIPTION    ""
        ::= { tnOpticalPortConfig 63 }

--------------------------------------------------------------------------------
-- CWR8 Optical Port Config Table
--------------------------------------------------------------------------------
    tnCwr8PortConfigTable OBJECT-TYPE
        SYNTAX         SEQUENCE OF TnCwr8PortConfigEntry
        MAX-ACCESS     not-accessible
        STATUS         current
        DESCRIPTION    "The ports on an CWR8 optical card."
        ::= { tnOpticalPortConfig 64 }

    tnCwr8PortConfigEntry OBJECT-TYPE
        SYNTAX         TnCwr8PortConfigEntry
        MAX-ACCESS     not-accessible
        STATUS         current
        DESCRIPTION    ""
        INDEX { ifIndex }
        ::= { tnCwr8PortConfigTable 1 }

    TnCwr8PortConfigEntry ::=
        SEQUENCE {
            tnCwr8PortConfigFunction  INTEGER,
--            obsolete
--            tnCwr8PortBlockerAging    Unsigned32,
            tnCwr8PortDropTargetPower Integer32
        }

    tnCwr8PortConfigFunction OBJECT-TYPE
        SYNTAX         INTEGER {
                         signal(1),
                         test(2),
                         thru(3),
                         colorless(4),
                         omd(5),
                         inv(6)
                       }
        MAX-ACCESS     read-only
        STATUS         current
        DESCRIPTION    "Indicates the functional type of this CWR8 port."
        ::= { tnCwr8PortConfigEntry 1 }

--    obsolete
--    tnCwr8PortBlockerAging OBJECT-TYPE ::= { tnCwr8PortConfigEntry 2 }

    tnCwr8PortDropTargetPower OBJECT-TYPE
        SYNTAX         Integer32
        UNITS          "mBm"
        MAX-ACCESS     read-create
        STATUS         current
        DESCRIPTION    "The following description applies to the
                        colorless port of the CWR8 card:

                        The drop target power.

                        Current configurable range: -2650 to -400."
        DEFVAL         { -1200 }
        ::= { tnCwr8PortConfigEntry 3 }

--------------------------------------------------------------------------------
-- 11STGE12 Optical Port Config Scalars
--------------------------------------------------------------------------------
    tn11stge12PortConfigAttributeTotal OBJECT-TYPE
        SYNTAX         Integer32
        MAX-ACCESS     read-only
        STATUS         current
        DESCRIPTION    ""
        ::= { tnOpticalPortConfig 65 }

--------------------------------------------------------------------------------
-- 11STGE12 Optical Port Config Table
--------------------------------------------------------------------------------
    tn11stge12PortConfigTable OBJECT-TYPE
        SYNTAX         SEQUENCE OF Tn11stge12PortConfigEntry
        MAX-ACCESS     not-accessible
        STATUS         current
        DESCRIPTION    "The ports on a 11STGE12 optical card."
        ::= { tnOpticalPortConfig 66 }

    tn11stge12PortConfigEntry OBJECT-TYPE
        SYNTAX         Tn11stge12PortConfigEntry
        MAX-ACCESS     not-accessible
        STATUS         current
        DESCRIPTION    ""
        INDEX { ifIndex }
        ::= { tn11stge12PortConfigTable 1 }

    Tn11stge12PortConfigEntry ::=
        SEQUENCE {
            tn11stge12PortConfigFunction INTEGER
        }

    tn11stge12PortConfigFunction OBJECT-TYPE
        SYNTAX         INTEGER {
                         network(1),
                         client(2)
                       }
        MAX-ACCESS     read-only
        STATUS         current
        DESCRIPTION    "Indicates the functional type of this 11STGE12 port."
        ::= { tn11stge12PortConfigEntry 1 }

--------------------------------------------------------------------------------
-- 11DPGE12 Optical Port Config Scalars
--------------------------------------------------------------------------------
    tn11dpge12PortConfigAttributeTotal OBJECT-TYPE
        SYNTAX         Integer32
        MAX-ACCESS     read-only
        STATUS         current
        DESCRIPTION    ""
        ::= { tnOpticalPortConfig 67 }

--------------------------------------------------------------------------------
-- 11DPGE12 Optical Port Config Table
--------------------------------------------------------------------------------
    tn11dpge12PortConfigTable OBJECT-TYPE
        SYNTAX         SEQUENCE OF Tn11dpge12PortConfigEntry
        MAX-ACCESS     not-accessible
        STATUS         current
        DESCRIPTION    "The ports on a 11DPGE12 optical card."
        ::= { tnOpticalPortConfig 68 }

    tn11dpge12PortConfigEntry OBJECT-TYPE
        SYNTAX         Tn11dpge12PortConfigEntry
        MAX-ACCESS     not-accessible
        STATUS         current
        DESCRIPTION    ""
        INDEX { ifIndex }
        ::= { tn11dpge12PortConfigTable 1 }

    Tn11dpge12PortConfigEntry ::=
        SEQUENCE {
            tn11dpge12PortConfigFunction INTEGER
        }

    tn11dpge12PortConfigFunction OBJECT-TYPE
        SYNTAX         INTEGER {
                         network(1),
                         client(2),
                         evoa(3),
                         backplane(4)
                       }
        MAX-ACCESS     read-only
        STATUS         current
        DESCRIPTION    "Indicates the functional type of this 11DPGE12 port."
        ::= { tn11dpge12PortConfigEntry 1 }

--------------------------------------------------------------------------------
-- SFD44 Optical Port Config Scalars
--------------------------------------------------------------------------------
    tnSfd44PortConfigAttributeTotal OBJECT-TYPE
        SYNTAX         Integer32
        MAX-ACCESS     read-only
        STATUS         current
        DESCRIPTION    ""
        ::= { tnOpticalPortConfig 69 }

--------------------------------------------------------------------------------
-- SFD44 Optical Port Config Table
--------------------------------------------------------------------------------
    tnSfd44PortConfigTable OBJECT-TYPE
        SYNTAX         SEQUENCE OF TnSfd44PortConfigEntry
        MAX-ACCESS     not-accessible
        STATUS         current
        DESCRIPTION    "The ports on an SFD44 optical card."
        ::= { tnOpticalPortConfig 70 }

    tnSfd44PortConfigEntry OBJECT-TYPE
        SYNTAX         TnSfd44PortConfigEntry
        MAX-ACCESS     not-accessible
        STATUS         current
        DESCRIPTION    ""
        INDEX { ifIndex }
        ::= { tnSfd44PortConfigTable 1 }

    TnSfd44PortConfigEntry ::=
        SEQUENCE {
            tnSfd44PortConfigFunction INTEGER
        }

    tnSfd44PortConfigFunction OBJECT-TYPE
        SYNTAX         INTEGER {
                         channel(1),
                         mux(2)
                       }
        MAX-ACCESS     read-only
        STATUS         current
        DESCRIPTION    "Indicates the functional type of this SFD44 port:

                        port 1-44 - channel
                        port 45 - mux"
        ::= { tnSfd44PortConfigEntry 1 }

--------------------------------------------------------------------------------
-- DWDM Common Port Config Table
--------------------------------------------------------------------------------
    tnDwdmCmnPortConfigTable OBJECT-TYPE
        SYNTAX         SEQUENCE OF TnDwdmCmnPortConfigEntry
        MAX-ACCESS     not-accessible
        STATUS         current
        DESCRIPTION    "Common attributes against DWDM ports."
        ::= { tnOpticalPortConfig 71 }

    tnDwdmCmnPortConfigEntry OBJECT-TYPE
        SYNTAX         TnDwdmCmnPortConfigEntry
        MAX-ACCESS     not-accessible
        STATUS         current
        DESCRIPTION    ""
        INDEX { ifIndex }
        ::= { tnDwdmCmnPortConfigTable 1 }

    TnDwdmCmnPortConfigEntry ::=
        SEQUENCE {
            tnDwdmCmnPortXfpType     INTEGER,
            tnDwdmCmnPortAlmProfName OCTET STRING,
            tnDwdmCmnPortMgracd      INTEGER
        }

    tnDwdmCmnPortXfpType OBJECT-TYPE
        SYNTAX         INTEGER {
                         auto(1),
                         user(2),
                         ctSi11(3),
                         ctSs11(4),
                         ctSs12(5),
                         ctSl11(6),
                         ctSl12(7),
                         ctSi161(8),
                         ctSs161(9),
                         ctSs162(10),
                         ctSl161(11),
                         ctSl162(12),
                         ctXi641(13),
                         ctXi642(14),
                         ctXi643(15),
                         ctXi645(16),
                         ctXs641(17),
                         ctXs642B(18),
                         ctXs643(19),
                         ctXs645(20),
                         ctXl641(21),
                         ctXl642(22),
                         ctXl643(23),
                         ctXv642(24),
                         ctXv643(25),
                         ctSs162C(26),
                         ctSl162C(27),
                         ctXi642C(28),
                         ct1000B(29),
                         ct10GB(30),
                         ctSs161AR(31),
                         ctETHEMR(32),
                         ctXP1L12D2(33),
                         ctS41(34),
                         ctL41(35),
                         ctL42(36),
                         ctAnyOC3(37),
                         ctAnyOC12(38),
                         ctAnyOC48(39),
                         ctAnyOC192(40),
                         ctAnyDATAS(41),
                         ctAnyDATAX(42),
                         ctXL642C(43),
                         ctXL642D(44),
                         ctSl162D(45),
                         ctSul11(46),
                         ctSi41(47),
                         ctSs41(48),
                         ctSs42(49),
                         ctSl41(50),
                         ctSl42(51),
                         ct2FCSNI(52),
                         ct2FCLCL(53),
                         ct4FCSNI(54),
                         ct4FCLCL(55),
                         ct8FCSNI(56),
                         ct8FCLCL(57),
                         ct8FCLCLC(58),
                         ct8FCLCLD(59),
                         ctSul12(60),
                         ctSs161A(61),
                         ct1000BT(62),
                         ct1000BCX(63),
                         ct1000BSX(64),
                         ct1000BLX(65),
                         ct1000BZX(66),
                         ctXi641R(67),
                         ctXi642R(68),
                         ctXs642A(69),
                         ctXs643A(70),
                         ctXs645A(71),
                         ctXl642A(72),
                         ctXv642A(73),
                         ct10GBSR(74),
                         ct10GBLR(75),
                         ct10GBER(76),
                         ct10GBLRM(77),
                         ct10GBSW(78),
                         ct10GBLW(79),
                         ct10GBEW(80),
                         ctXs642C(81),
                         ctSul12O(82),
                         ctSs162O(83),
                         ctSl162O(84),
                         ctEvoaFast(85),
                         ctEvoaSlow(86),
                         ct10GBZR(87),
                         ct100BLX10(88),
                         ctSEU12O(89),
                         ctXl64Tu(90),
                         ctBncdvRx(91),
                         ctBncdvTx(92),
                         ctC113G4C(93),
                         ctC113G10C(94),
                         ct4FCOC(95),
                         ct4FCOD(96),
                         ctGeBx20U(97),
                         ctGeBx20D(98),
                         ctGeBx40U(99),
                         ctGeBx40D(100),
                         ctFeBx40U(101),
                         ctFeBx40D(102),
                         ctL642(103),
                         ct100BFXS(104),
                         ctX8FCLCL(105),
                         ctC113G4Cd(106),
                         ctX8FCSNI(107),
                         ct3GSDISH(108),
                         ct3GSDIMH(109),
                         ct1000BT2(110),
                         ctSFEBTEE(111),
                         ctC11G4C(112),
                         ctC43G4C(113),
                         ctC113S10(114),
                         ct16FCLCL(115),
                         ct16FCSNI(116),
                         ctC113G4D(117),
                         ct1000GT2(118),
                         ctS10GBLR(119),
                         ctS10GBSR(120),
                         ctS8FCLCL(121),
                         ctC113G4T(122),
                         ctXL64TCW(123),
                         ct100BULHO(124),
                         ctXs642D(125),
                         ctC2Clr4E(126),
                         ctSxi641(127),
                         ctQ40Gsr4(128),
                         ctQ40Glr4(129),
                         ctSxs642B(130),
                         ctS1E(131),
                         ctSgS11(132),
                         ctSgL11(133),
                         ctSgS41(134),
                         ctSgL41(135),
                         ctSxs642C(136),
                         ctC2Csr10E(137),
                         ctC2Clr4D(138),
                         ct2CBx10U(139),
                         ct2CBx10D(140),
                         ctC4Clr4E(141),
                         ctC4Clr4D(142),
                         ctCFP2ALUMetro(143),
                         ctCFP2ALULH(144),
                         ctC2CER4E(145),
                         ctSL64TUW(146),
                         ct1DC100M(147),
                         ctSWR120(148),
                         ct2Ac100H(149),
                         ct2Ac100(150),
                         ctSXL642(151),
                         ctSXL642C(152),
                         ctSgE1(153),
                         ctSgS11C(154)
                       }
        MAX-ACCESS     read-create
        STATUS         current
        DESCRIPTION    "The programmed XFP or SFP type."
        ::= { tnDwdmCmnPortConfigEntry 1 }
        
        tnDwdmCmnPortAlmProfName OBJECT-TYPE
        SYNTAX                   OCTET STRING
        MAX-ACCESS               read-create
        STATUS                   current
        DESCRIPTION              ""
        ::= { tnDwdmCmnPortConfigEntry 2 }

    tnDwdmCmnPortMgracd OBJECT-TYPE
        SYNTAX         INTEGER {
                          none(1),
                          cp(2),
                          mgnpln(3),
                          cpmgnpln(4)
                       }
        MAX-ACCESS     read-create
        STATUS         current
        DESCRIPTION    "Indicates if managed by CP, MGNPLN, shared by both or free."
        DEFVAL         { none }
        ::= { tnDwdmCmnPortConfigEntry 3 }

--------------------------------------------------------------------------------
-- DWDM Common and OTU2/ODU2 Line Port Config Table
--------------------------------------------------------------------------------
    tnDwdmCmnLinePortConfigTable OBJECT-TYPE
        SYNTAX         SEQUENCE OF TnDwdmCmnLinePortConfigEntry
        MAX-ACCESS     not-accessible
        STATUS         current
        DESCRIPTION    "Common attributes against DWDM line ports."
        ::= { tnOpticalPortConfig 72 }

    tnDwdmCmnLinePortConfigEntry OBJECT-TYPE
        SYNTAX         TnDwdmCmnLinePortConfigEntry
        MAX-ACCESS     not-accessible
        STATUS         current
        DESCRIPTION    ""
        INDEX { ifIndex }
        ::= { tnDwdmCmnLinePortConfigTable 1 }

    TnDwdmCmnLinePortConfigEntry ::=
        SEQUENCE {
--            obsolete
--            tnDwdmCmnLinePortLoopType                          INTEGER,
            tnDwdmCmnLinePortTransmissionMode                  INTEGER,
            tnDwdmCmnLinePortOchOtu2FecMode                    AluWdmFecMode,
            tnDwdmCmnLinePortOchOtu2Rate                       AluWdmPortOchOtuRate,
            tnDwdmCmnLinePortOtu2TransmittedTti                OCTET STRING,
            tnDwdmCmnLinePortOtu2ExpectedTti                   OCTET STRING,
            tnDwdmCmnLinePortOtu2TimConsequenceAction          AluWdmDisabledEnabled,
            tnDwdmCmnLinePortOtu2TimDetectionMode              AluWdmTimDetectionMode,
            tnDwdmCmnLinePortOdu2PayloadType                   Unsigned32,
            tnDwdmCmnLinePortOdu2OchSignalDefConsequenceAction AluWdmOduOchSignalDefConsequenceAction,
            tnDwdmCmnLinePortOdu2PlmConsequenceAction          TruthValue,
            tnDwdmCmnLinePortOdu2MappingMode                   AluWdmMappingMode,
            tnDwdmCmnLinePortOdu2TpMode                        TruthValue,
            tnDwdmCmnLinePortOdu2TransmittedTti                OCTET STRING,
            tnDwdmCmnLinePortOdu2ExpectedTti                   OCTET STRING,
            tnDwdmCmnLinePortOdu2TimConsequenceAction          AluWdmDisabledEnabled,
            tnDwdmCmnLinePortOdu2TimDetectionMode              AluWdmTimDetectionMode,
            tnDwdmCmnLinePortCrossRegPartner                   Unsigned32,
            tnDwdmCmnLinePortBroadcastFrom                     Unsigned32,
            tnDwdmCmnLinePortRegenResponse                     INTEGER,
            tnDwdmCmnLinePortOtu2holdofftimer                  AluWdmDisabledEnabled,  -- deprecated
            tnDwdmCmnLinePortDemandName                        OCTET STRING,
            tnDwdmCmnLinePortApsEnable                         INTEGER,
            tnDwdmCmnLinePortHoldOffTimer                      AluWdmDisabledEnabled,
            tnDwdmCmnLinePortDMConfigCMEPMode                  INTEGER,
            tnDwdmCmnLinePortDMConfigEnable                    INTEGER,
            tnDwdmCmnLinePortCluster                           OCTET STRING,
            tnDwdmCmnLinePortDegInterval                       Unsigned32,
            tnDwdmCmnLinePortDegThreshold                      Unsigned32,
            tnDwdmCmnLinePorttxShape                           INTEGER,
            tnDwdmCmnLinePortCdPreComp                         Integer32,
            tnDwdmCmnLinePortPhasenCode                        INTEGER
        }

--    obsolete tnDwdmCmnLinePortLoopType OBJECT-TYPE ::= { tnDwdmCmnLinePortConfigEntry 1 }

    tnDwdmCmnLinePortTransmissionMode OBJECT-TYPE
        SYNTAX         INTEGER {
                         addDrop(1),
                         dropOnly(2),
                         addOnly(3),
                         thru(4),
                         dropContinue(5),
                         crossRegen(6)
                       }
        MAX-ACCESS     read-create
        STATUS         current
        DESCRIPTION    "The transmission mode."
        DEFVAL         { addDrop }
        ::= { tnDwdmCmnLinePortConfigEntry 2 }

    tnDwdmCmnLinePortOchOtu2FecMode OBJECT-TYPE
        SYNTAX         AluWdmFecMode
        MAX-ACCESS     read-create
        STATUS         current
        DESCRIPTION    "OTU2 FEC mode."
        ::= { tnDwdmCmnLinePortConfigEntry 3 }

    tnDwdmCmnLinePortOchOtu2Rate OBJECT-TYPE
        SYNTAX         AluWdmPortOchOtuRate
        MAX-ACCESS     read-create
        STATUS         current
        DESCRIPTION    "OTU2 rate."
        DEFVAL         { otm11G096 }
        ::= { tnDwdmCmnLinePortConfigEntry 4 }

    tnDwdmCmnLinePortOtu2TransmittedTti OBJECT-TYPE
        SYNTAX         OCTET STRING
        MAX-ACCESS     read-create
        STATUS         current
        DESCRIPTION    "OTU2 transmitted TTI."
        DEFVAL         { "" }
        ::= { tnDwdmCmnLinePortConfigEntry 5 }

    tnDwdmCmnLinePortOtu2ExpectedTti OBJECT-TYPE
        SYNTAX         OCTET STRING
        MAX-ACCESS     read-create
        STATUS         current
        DESCRIPTION    "OTU2 expected TTI."
        DEFVAL         { "" }
        ::= { tnDwdmCmnLinePortConfigEntry 6 }

    tnDwdmCmnLinePortOtu2TimConsequenceAction OBJECT-TYPE
        SYNTAX         AluWdmDisabledEnabled
        MAX-ACCESS     read-create
        STATUS         current
        DESCRIPTION    "OTU2 TIM consequence action."
        DEFVAL         { disabled }
        ::= { tnDwdmCmnLinePortConfigEntry 7 }

    tnDwdmCmnLinePortOtu2TimDetectionMode OBJECT-TYPE
        SYNTAX         AluWdmTimDetectionMode
        MAX-ACCESS     read-create
        STATUS         current
        DESCRIPTION    "OTU2 TIM detection mode."
        DEFVAL         { off }
        ::= { tnDwdmCmnLinePortConfigEntry 8 }

    tnDwdmCmnLinePortOdu2PayloadType OBJECT-TYPE
        SYNTAX         Unsigned32
        MAX-ACCESS     read-create
        STATUS         current
        DESCRIPTION    "ODU2 payload type.

                        Current configurable range: 0 to 255."
        DEFVAL         { 253 }
        ::= { tnDwdmCmnLinePortConfigEntry 9 }

    tnDwdmCmnLinePortOdu2OchSignalDefConsequenceAction OBJECT-TYPE
        SYNTAX         AluWdmOduOchSignalDefConsequenceAction
        MAX-ACCESS     read-create
        STATUS         current
        DESCRIPTION    "ODU2 OCH signal def consequence action."
        DEFVAL         { genericAis }
        ::= { tnDwdmCmnLinePortConfigEntry 10 }

    tnDwdmCmnLinePortOdu2PlmConsequenceAction OBJECT-TYPE
        SYNTAX         TruthValue
        MAX-ACCESS     read-create
        STATUS         current
        DESCRIPTION    "PLM consequence action."
        DEFVAL         { false }
        ::= { tnDwdmCmnLinePortConfigEntry 11 }

    tnDwdmCmnLinePortOdu2MappingMode OBJECT-TYPE
        SYNTAX         AluWdmMappingMode
        MAX-ACCESS     read-create
        STATUS         current
        DESCRIPTION    "ODU2 mapping mode."
        DEFVAL         { rsB }
        ::= { tnDwdmCmnLinePortConfigEntry 12 }

    tnDwdmCmnLinePortOdu2TpMode OBJECT-TYPE
        SYNTAX         TruthValue
        MAX-ACCESS     read-create
        STATUS         current
        DESCRIPTION    "ODU2 TP mode."
        DEFVAL         { true }
        ::= { tnDwdmCmnLinePortConfigEntry 13 }

    tnDwdmCmnLinePortOdu2TransmittedTti OBJECT-TYPE
        SYNTAX         OCTET STRING
        MAX-ACCESS     read-create
        STATUS         current
        DESCRIPTION    "ODU2 transmitted TTI."
        DEFVAL         { "" }
        ::= { tnDwdmCmnLinePortConfigEntry 14 }

    tnDwdmCmnLinePortOdu2ExpectedTti OBJECT-TYPE
        SYNTAX         OCTET STRING
        MAX-ACCESS     read-create
        STATUS         current
        DESCRIPTION    "ODU2 expected TTI."
        DEFVAL         { "" }
        ::= { tnDwdmCmnLinePortConfigEntry 15 }

    tnDwdmCmnLinePortOdu2TimConsequenceAction OBJECT-TYPE
        SYNTAX         AluWdmDisabledEnabled
        MAX-ACCESS     read-create
        STATUS         current
        DESCRIPTION    "ODU2 TIM consequence action."
        DEFVAL         { disabled }
        ::= { tnDwdmCmnLinePortConfigEntry 16 }

    tnDwdmCmnLinePortOdu2TimDetectionMode OBJECT-TYPE
        SYNTAX         AluWdmTimDetectionMode
        MAX-ACCESS     read-create
        STATUS         current
        DESCRIPTION    "ODU2 TIM detection mode."
        DEFVAL         { off }
        ::= { tnDwdmCmnLinePortConfigEntry 17 }

    tnDwdmCmnLinePortCrossRegPartner OBJECT-TYPE
        SYNTAX         Unsigned32
        MAX-ACCESS     read-create
        STATUS         current
        DESCRIPTION    "Cross reg partner port."
        DEFVAL         { 0 }
        ::= { tnDwdmCmnLinePortConfigEntry 18 }

    tnDwdmCmnLinePortBroadcastFrom OBJECT-TYPE
        SYNTAX         Unsigned32
        MAX-ACCESS     read-create
        STATUS         current
        DESCRIPTION    "Broadcast From Port."
        DEFVAL         { 0 }
        ::= { tnDwdmCmnLinePortConfigEntry 19 }

    tnDwdmCmnLinePortRegenResponse OBJECT-TYPE
        SYNTAX         INTEGER {
                         laserOn(1),
                         laserOff(2)
                       }
        MAX-ACCESS     read-create
        STATUS         current
        DESCRIPTION    "The regen response mode."
        DEFVAL         { laserOn }
        ::= { tnDwdmCmnLinePortConfigEntry 20 }

    tnDwdmCmnLinePortOtu2holdofftimer OBJECT-TYPE
        SYNTAX         AluWdmDisabledEnabled
        MAX-ACCESS     read-create
        STATUS         deprecated
        DESCRIPTION    "Line port consequent action (whether AIS
                        insertion or laser off) must be delayed by
                        a hold-off timer."
        DEFVAL         { disabled }
        ::= { tnDwdmCmnLinePortConfigEntry 21 }

    tnDwdmCmnLinePortDemandName OBJECT-TYPE
        SYNTAX         OCTET STRING (SIZE(0..140))
        MAX-ACCESS     read-create
        STATUS         current
        DESCRIPTION    "Demand name, which is a string of up to 138
                        characters to be used as a signal label or
                        identifier."
        DEFVAL         { "" }
        ::= { tnDwdmCmnLinePortConfigEntry 22 }

    tnDwdmCmnLinePortApsEnable OBJECT-TYPE
        SYNTAX         INTEGER {
                         proprietary(1),
                         standard(2)
                       }
        MAX-ACCESS     read-create
        STATUS         current
        DESCRIPTION    "Enable or disable the proprietary APS bytes
                        insertion in the ODU2 overhead."
        DEFVAL         { proprietary }
        ::= { tnDwdmCmnLinePortConfigEntry 23 }

    tnDwdmCmnLinePortHoldOffTimer OBJECT-TYPE
        SYNTAX         AluWdmDisabledEnabled
        MAX-ACCESS     read-create
        STATUS         current
        DESCRIPTION    "Line port consequent action (whether AIS
                        insertion or laser off) must be delayed by
                        a hold-off timer."
        DEFVAL         { disabled }
        ::= { tnDwdmCmnLinePortConfigEntry 24 }

    tnDwdmCmnLinePortDMConfigCMEPMode OBJECT-TYPE
        SYNTAX         INTEGER {
                         bypass(1),
                         source(2),
                         destination(3)
                       }
        MAX-ACCESS     read-create
        STATUS         current
        DESCRIPTION    "Connection Monitoring End Point Mode defined for
                        delay measurement on the specified entity."
        DEFVAL         { bypass }
        ::= { tnDwdmCmnLinePortConfigEntry 25 }

    tnDwdmCmnLinePortDMConfigEnable OBJECT-TYPE
        SYNTAX         INTEGER {
                         enable(1),
                         disable(2)
                       }
        MAX-ACCESS     read-create
        STATUS         current
        DESCRIPTION    "This attribute is used to enable or disable the
                        DM function."
        DEFVAL         { disable }
        ::= { tnDwdmCmnLinePortConfigEntry 26 }

    tnDwdmCmnLinePortCluster OBJECT-TYPE
        SYNTAX        SnmpAdminString (SIZE(0..64))
        MAX-ACCESS    read-write
        STATUS        current
        DESCRIPTION   "This attribute is used to find the corresponding optical 
                       line node TID and connection point."
        ::= { tnDwdmCmnLinePortConfigEntry 27 }

    tnDwdmCmnLinePortDegInterval OBJECT-TYPE
        SYNTAX         Unsigned32 (2..10)
        MAX-ACCESS     read-create
        STATUS         current
        DESCRIPTION    "Signal Degrade Interval."
        DEFVAL         { 7 }
        ::= { tnDwdmCmnLinePortConfigEntry 28 }

    tnDwdmCmnLinePortDegThreshold OBJECT-TYPE
        SYNTAX         Unsigned32 (1..856388)
        MAX-ACCESS     read-create
        STATUS         current
        DESCRIPTION    "Signal Degrade threshold."
        DEFVAL         { 40000 }
        ::= { tnDwdmCmnLinePortConfigEntry 29 }

    tnDwdmCmnLinePorttxShape OBJECT-TYPE
        SYNTAX         INTEGER {
                         single(1),
                         super(2),
                         alien(3)
                       }
        MAX-ACCESS     read-create
        STATUS         current
        DESCRIPTION    "Specifies the transmit waveshape applied to the
                        optical carrier of a line port."
        DEFVAL         { single }
        ::= { tnDwdmCmnLinePortConfigEntry 30 }

    tnDwdmCmnLinePortCdPreComp OBJECT-TYPE
        SYNTAX         Integer32 (-3100..3100)
        UNITS          "ps/nm"
        MAX-ACCESS     read-create
        STATUS         current
        DESCRIPTION    "Specifies the transmit chromatic dispersion pre-compensation."
        DEFVAL         { 0 }
        ::= { tnDwdmCmnLinePortConfigEntry 31 }

    tnDwdmCmnLinePortPhasenCode OBJECT-TYPE
        SYNTAX         INTEGER {
                         absolute(1),
                         differential(2)
                       }
        MAX-ACCESS     read-create
        STATUS         current
        DESCRIPTION    "Specifies the phase encoding mode."
        DEFVAL         { absolute }
        ::= { tnDwdmCmnLinePortConfigEntry 32 }

--------------------------------------------------------------------------------
-- DWDM Common OTU2/ODU2 Client Port Config Table
--------------------------------------------------------------------------------
    tnDwdmCmnClientPortConfigTable OBJECT-TYPE
        SYNTAX         SEQUENCE OF TnDwdmCmnClientPortConfigEntry
        MAX-ACCESS     not-accessible
        STATUS         current
        DESCRIPTION    "Common attributes against DWDM client ports."
        ::= { tnOpticalPortConfig 73 }

    tnDwdmCmnClientPortConfigEntry OBJECT-TYPE
        SYNTAX         TnDwdmCmnClientPortConfigEntry
        MAX-ACCESS     not-accessible
        STATUS         current
        DESCRIPTION    ""
        INDEX { ifIndex }
        ::= { tnDwdmCmnClientPortConfigTable 1 }

    TnDwdmCmnClientPortConfigEntry ::=
        SEQUENCE {
--            obsolete
--            tnDwdmCmnClientPortLoopType                 INTEGER,
            tnDwdmCmnClientPortLosProp                  INTEGER,
            tnDwdmCmnClientPortTs1                      Unsigned32,
            tnDwdmCmnClientPortTs2                      Unsigned32,
            tnDwdmCmnClientPortOchOtu2FecMode           AluWdmFecMode,
            tnDwdmCmnClientPortOchOtu2Rate              AluWdmPortOchOtuRate,
            tnDwdmCmnClientPortOtu2TransmittedTti       OCTET STRING,
            tnDwdmCmnClientPortOtu2ExpectedTti          OCTET STRING,
            tnDwdmCmnClientPortOtu2TimConsequenceAction AluWdmDisabledEnabled,
            tnDwdmCmnClientPortOtu2TimDetectionMode     AluWdmTimDetectionMode,
            tnDwdmCmnClientPortOdu2TransmittedTti       OCTET STRING,
            tnDwdmCmnClientPortOdu2ExpectedTti          OCTET STRING,
            tnDwdmCmnClientPortOdu2TimDetectionMode     AluWdmTimDetectionMode,
            tnDwdmCmnClientPortProtectionTs1            Unsigned32,
            tnDwdmCmnClientPortProtectionTs2            Unsigned32,
            tnDwdmCmnClientPortTsMap                    OCTET STRING,
            tnDwdmCmnClientPortContainer                INTEGER,
            tnDwdmCmnClientPortCSF                      INTEGER,
            tnDwdmCmnClientPortSSF                      INTEGER,
            tnDwdmCmnClientPortScramMode                INTEGER,
            tnDwdmCmnClientPortDegInterval              Unsigned32,
            tnDwdmCmnClientPortDegThreshold             Unsigned32,
            tnDwdmCmnClientPortHoldOffTimer             INTEGER
        }

--    obsolete tnDwdmCmnClientPortLoopType OBJECT-TYPE ::= { tnDwdmCmnClientPortConfigEntry 1 }

    tnDwdmCmnClientPortLosProp OBJECT-TYPE
        SYNTAX         INTEGER {
                         laserOn(1),
                         laserOff(2)
                       }
        MAX-ACCESS     read-create
        STATUS         current
        DESCRIPTION    "The LOS propagation."
        DEFVAL         { laserOn }
        ::= { tnDwdmCmnClientPortConfigEntry 2 }

    tnDwdmCmnClientPortTs1 OBJECT-TYPE
        SYNTAX         Unsigned32
        MAX-ACCESS     read-create
        STATUS         current
        DESCRIPTION    "Working time slot 1, ODU1 tributary (11STMM10),
                        ODU2-like structure (11DPGE12).  Unassigned is
                        represented by value 0.

                        Current configurable range (11STMM10): 0, 1 to 4
                        Current configurable range (11DPGE12): 0, 1 to 2."
        DEFVAL         { 0 }
        ::= { tnDwdmCmnClientPortConfigEntry 3 }

    tnDwdmCmnClientPortTs2 OBJECT-TYPE
        SYNTAX         Unsigned32
        MAX-ACCESS     read-create
        STATUS         current
        DESCRIPTION    "Working time slot 2, STS1/STS3c (11STMM10).
                        Unassigned is represented by value 0.

                        Current configurable range (11STMM10): 0, 1, 4, 7, 10, ... 46
                        Current configurable range (11DPGE12): 0 to 10."
        DEFVAL         { 0 }
        ::= { tnDwdmCmnClientPortConfigEntry 4 }

    tnDwdmCmnClientPortOchOtu2FecMode OBJECT-TYPE
        SYNTAX         AluWdmFecMode
        MAX-ACCESS     read-create
        STATUS         current
        DESCRIPTION    "OTU2 FEC mode."
        DEFVAL         { g709Fec }
        ::= { tnDwdmCmnClientPortConfigEntry 5 }

    tnDwdmCmnClientPortOchOtu2Rate OBJECT-TYPE
        SYNTAX         AluWdmPortOchOtuRate
        MAX-ACCESS     read-create
        STATUS         current
        DESCRIPTION    "OTU2 rate."
        DEFVAL         { otm10G709 }
        ::= { tnDwdmCmnClientPortConfigEntry 6 }

    tnDwdmCmnClientPortOtu2TransmittedTti OBJECT-TYPE
        SYNTAX         OCTET STRING
        MAX-ACCESS     read-create
        STATUS         current
        DESCRIPTION    "OTU2 transmitted TTI."
        DEFVAL         { "" }
        ::= { tnDwdmCmnClientPortConfigEntry 7 }

    tnDwdmCmnClientPortOtu2ExpectedTti OBJECT-TYPE
        SYNTAX         OCTET STRING
        MAX-ACCESS     read-create
        STATUS         current
        DESCRIPTION    "OTU2 expected TTI."
        DEFVAL         { "" }
        ::= { tnDwdmCmnClientPortConfigEntry 8 }

    tnDwdmCmnClientPortOtu2TimConsequenceAction OBJECT-TYPE
        SYNTAX         AluWdmDisabledEnabled
        MAX-ACCESS     read-create
        STATUS         current
        DESCRIPTION    "OTU2 TIM consequence action."
        DEFVAL         { disabled }
        ::= { tnDwdmCmnClientPortConfigEntry 9 }

    tnDwdmCmnClientPortOtu2TimDetectionMode OBJECT-TYPE
        SYNTAX         AluWdmTimDetectionMode
        MAX-ACCESS     read-create
        STATUS         current
        DESCRIPTION    "OTU2 TIM detection mode."
        DEFVAL         { off }
        ::= { tnDwdmCmnClientPortConfigEntry 10 }

    tnDwdmCmnClientPortOdu2TransmittedTti OBJECT-TYPE
        SYNTAX         OCTET STRING
        MAX-ACCESS     read-create
        STATUS         current
        DESCRIPTION    "ODU2 transmitted TTI."
        DEFVAL         { "" }
        ::= { tnDwdmCmnClientPortConfigEntry 11 }

    tnDwdmCmnClientPortOdu2ExpectedTti OBJECT-TYPE
        SYNTAX         OCTET STRING
        MAX-ACCESS     read-create
        STATUS         current
        DESCRIPTION    "ODU2 expected TTI."
        DEFVAL         { "" }
        ::= { tnDwdmCmnClientPortConfigEntry 12 }

    tnDwdmCmnClientPortOdu2TimDetectionMode OBJECT-TYPE
        SYNTAX         AluWdmTimDetectionMode
        MAX-ACCESS     read-create
        STATUS         current
        DESCRIPTION    "ODU2 TIM detection mode."
        DEFVAL         { off }
        ::= { tnDwdmCmnClientPortConfigEntry 13 }

    tnDwdmCmnClientPortProtectionTs1 OBJECT-TYPE
        SYNTAX         Unsigned32
        MAX-ACCESS     read-create
        STATUS         current
        DESCRIPTION    "Protection time slot 1, ODU1 tributary (11STMM10),
                        line port number (11DPGE12).  Unassigned is
                        represented by value 0.

                        Current configurable range (11STMM10): 0, 1 to 4
                        Current configurable range (11DPGE12): 0, 1 to 2."
        DEFVAL         { 0 }
        ::= { tnDwdmCmnClientPortConfigEntry 14 }

    tnDwdmCmnClientPortProtectionTs2 OBJECT-TYPE
        SYNTAX         Unsigned32
        MAX-ACCESS     read-create
        STATUS         current
        DESCRIPTION    "Protection time slot 2, STS1/STS3c (11STMM10).
                        Unassigned is represented by value 0.

                        Current configurable range (11STMM10): 0, 1, 4, 7, 10, ... 46
                        Current configurable range (11DPGE12): 0 to 10."
        DEFVAL         { 0 }
        ::= { tnDwdmCmnClientPortConfigEntry 15 }

    tnDwdmCmnClientPortTsMap OBJECT-TYPE
        SYNTAX         OCTET STRING (SIZE(0..4))
        MAX-ACCESS     read-create
        STATUS         current
        DESCRIPTION    "Client port time slot bit map.  First 2 bytes
                        are for line 2 and the next 2 bytes are for
                        line 1."
        DEFVAL         { "" }
        ::= { tnDwdmCmnClientPortConfigEntry 16 }

    tnDwdmCmnClientPortContainer OBJECT-TYPE
        SYNTAX         INTEGER {
                         none(1),
                         optsg(2),
                         odu0(3),
                         odu1(4),
                         oduflex(5),
                         odu2(6),
                         odu2e(7),
                         odu3(8),
                         odu3e(9),
                         odu3e2(10),
                         odu4(11),
                         oduf(12),
                         oduflex3gsdi(13),
                         oduflexsdr(14),
                         oduflexfc400(15)
                       }
        MAX-ACCESS     read-create
        STATUS         current
        DESCRIPTION    "Specifies the mapping mode that will be used
                        for client signal."
        DEFVAL         { none }
        ::= { tnDwdmCmnClientPortConfigEntry 17 }

    tnDwdmCmnClientPortCSF OBJECT-TYPE
        SYNTAX         INTEGER {
                         disabled(1),
                         laserOff(2)
                       }
        MAX-ACCESS     read-create
        STATUS         current
        DESCRIPTION    "Defines the port consequent action behavior
                        in case of CSF"
        DEFVAL         { laserOff }
        ::= { tnDwdmCmnClientPortConfigEntry 18 }

    tnDwdmCmnClientPortSSF OBJECT-TYPE
        SYNTAX         INTEGER {
                         disabled(1),
                         laserOff(2)
                       }
        MAX-ACCESS     read-create
        STATUS         current
        DESCRIPTION    "Defines the port consequent action behavior
                        in case of SSF"
        DEFVAL         { disabled }
        ::= { tnDwdmCmnClientPortConfigEntry 19 }

    tnDwdmCmnClientPortScramMode OBJECT-TYPE
        SYNTAX         INTEGER {
                         enable(1),
                         disable(2)
                       }
        MAX-ACCESS     read-create
        STATUS         current
        DESCRIPTION    ""
        DEFVAL         { disable }
        ::= { tnDwdmCmnClientPortConfigEntry 20 }

    tnDwdmCmnClientPortDegInterval OBJECT-TYPE
        SYNTAX         Unsigned32 (2..10)
        MAX-ACCESS     read-create
        STATUS         current
        DESCRIPTION    "ODU2 Degrade Interval."
        DEFVAL         { 7 }
        ::= { tnDwdmCmnClientPortConfigEntry 21 }
    
    tnDwdmCmnClientPortDegThreshold OBJECT-TYPE
        SYNTAX         Unsigned32 (0..'ffffffff'h) 
        MAX-ACCESS     read-create
        STATUS         current
        DESCRIPTION    "Degrade threshold."
        ::= { tnDwdmCmnClientPortConfigEntry 22 }

    tnDwdmCmnClientPortHoldOffTimer OBJECT-TYPE
        SYNTAX         INTEGER {
                         enabled (1),
                         disabled(2)
                       }
        MAX-ACCESS     read-create
        STATUS         current
        DESCRIPTION    "Hold Off Timer for client port."
        DEFVAL         { enabled }
        ::= { tnDwdmCmnClientPortConfigEntry 23 }


--------------------------------------------------------------------------------
-- RSMON Ingress Port Config Table
--------------------------------------------------------------------------------
    tnRsmonIngrPortConfigTable OBJECT-TYPE
        SYNTAX         SEQUENCE OF TnRsmonIngrPortConfigEntry
        MAX-ACCESS     not-accessible
        STATUS         current
        DESCRIPTION    "Common attributes against RSMON Ingress supported ports."
        ::= { tnOpticalPortConfig 74 }

    tnRsmonIngrPortConfigEntry OBJECT-TYPE
        SYNTAX         TnRsmonIngrPortConfigEntry
        MAX-ACCESS     not-accessible
        STATUS         current
        DESCRIPTION    ""
        INDEX { ifIndex }
        ::= { tnRsmonIngrPortConfigTable 1 }

    TnRsmonIngrPortConfigEntry ::=
        SEQUENCE {
            tnRsmonIngrPortTransmittedTti       OCTET STRING,
            tnRsmonIngrPortExpectedTti          OCTET STRING,
            tnRsmonIngrPortTimod                INTEGER,
            tnRsmonIngrPortTimDetection         TruthValue,
            tnRsmonIngrPortTimConsequenceAction AluWdmDisabledEnabled,
--            obsolete
--            tnRsmonIngrPortTimDetectionMode     INTEGER,
            tnRsmonIngrPortSigMode              INTEGER
        }

    tnRsmonIngrPortTransmittedTti OBJECT-TYPE
        SYNTAX         OCTET STRING
        MAX-ACCESS     read-create
        STATUS         current
        DESCRIPTION    "RSMON transmitted TTI."
        DEFVAL         { "" }
        ::= { tnRsmonIngrPortConfigEntry 1 }

    tnRsmonIngrPortExpectedTti OBJECT-TYPE
        SYNTAX         OCTET STRING
        MAX-ACCESS     read-create
        STATUS         current
        DESCRIPTION    "RSMON expected TTI."
        DEFVAL         { "" }
        ::= { tnRsmonIngrPortConfigEntry 2 }

    tnRsmonIngrPortTimod OBJECT-TYPE
        SYNTAX         INTEGER {
                         notApplicable(1),
                         specific16Byte(2),
                         nonSpecificSingleByte(3),
                         specificSingleByte(4),
                         string64(5)
                       }
        MAX-ACCESS     read-create
        STATUS         current
        DESCRIPTION    "RSMON TIMOD."
        DEFVAL         { specific16Byte }
        ::= { tnRsmonIngrPortConfigEntry 3 }

    tnRsmonIngrPortTimDetection OBJECT-TYPE
        SYNTAX         TruthValue
        MAX-ACCESS     read-create
        STATUS         current
        DESCRIPTION    "RSMON TIM detection."
        DEFVAL         { false }
        ::= { tnRsmonIngrPortConfigEntry 4 }

    tnRsmonIngrPortTimConsequenceAction OBJECT-TYPE
        SYNTAX         AluWdmDisabledEnabled
        MAX-ACCESS     read-create
        STATUS         current
        DESCRIPTION    "RSMON TIM consequence action."
        DEFVAL         { disabled }
        ::= { tnRsmonIngrPortConfigEntry 5 }

--    obsolete tnRsmonIngrPortTimDetectionMode OBJECT-TYPE ::= { tnRsmonIngrPortConfigEntry 6 }

    tnRsmonIngrPortSigMode OBJECT-TYPE
        SYNTAX         INTEGER {
                         transparent(1),
                         terminated(2)
                       }
        MAX-ACCESS     read-create
        STATUS         current
        DESCRIPTION    "RSMON signal mode."
        DEFVAL         { transparent }
        ::= { tnRsmonIngrPortConfigEntry 7 }

--------------------------------------------------------------------------------
-- MSMON Port Config Table
--------------------------------------------------------------------------------
    tnMsmonPortConfigTable OBJECT-TYPE
        SYNTAX         SEQUENCE OF TnMsmonPortConfigEntry
        MAX-ACCESS     not-accessible
        STATUS         current
        DESCRIPTION    "Common attributes against MSMON supported ports."
        ::= { tnOpticalPortConfig 75 }

    tnMsmonPortConfigEntry OBJECT-TYPE
        SYNTAX         TnMsmonPortConfigEntry
        MAX-ACCESS     not-accessible
        STATUS         current
        DESCRIPTION    ""
        INDEX { ifIndex }
        ::= { tnMsmonPortConfigTable 1 }

    TnMsmonPortConfigEntry ::=
        SEQUENCE {
            tnMsmonPortMappingMode AluWdmMappingMode,
            tnMsmonPortExcThLevel  INTEGER,
            tnMsmonPortDegThLevel  INTEGER
        }

    tnMsmonPortMappingMode OBJECT-TYPE
        SYNTAX         AluWdmMappingMode
        MAX-ACCESS     read-create
        STATUS         current
        DESCRIPTION    "MSMON mapping mode."
        DEFVAL         { rsB }
        ::= { tnMsmonPortConfigEntry 1 }

    tnMsmonPortExcThLevel OBJECT-TYPE
        SYNTAX         INTEGER {
                         e3(1),
                         e4(2),
                         e5(3)
                       }
        MAX-ACCESS     read-create
        STATUS         current
        DESCRIPTION    "BER Threshold for excessive BER defect (SFTH)."
        DEFVAL         { e3 }
        ::= { tnMsmonPortConfigEntry 2 }

    tnMsmonPortDegThLevel OBJECT-TYPE
        SYNTAX         INTEGER {
                         e5(1),
                         e6(2),
                         e7(3),
                         e8(4),
                         e9(5)
                       }
        MAX-ACCESS     read-create
        STATUS         current
        DESCRIPTION    "BER Threshold for SD defect (SDTH)."
        DEFVAL         { e6 }
        ::= { tnMsmonPortConfigEntry 3 }

--------------------------------------------------------------------------------
-- OSC SFP Port Config Table
--------------------------------------------------------------------------------
    tnOscSfpPortConfigTable OBJECT-TYPE
        SYNTAX         SEQUENCE OF TnOscSfpPortConfigEntry
        MAX-ACCESS     not-accessible
        STATUS         current
        DESCRIPTION    "OSC SFP attributes."
        ::= { tnOpticalPortConfig 76 }

    tnOscSfpPortConfigEntry OBJECT-TYPE
        SYNTAX         TnOscSfpPortConfigEntry
        MAX-ACCESS     not-accessible
        STATUS         current
        DESCRIPTION    ""
        INDEX { ifIndex }
        ::= { tnOscSfpPortConfigTable 1 }

    TnOscSfpPortConfigEntry ::=
        SEQUENCE {
--            obsolete
--            tnOscSfpPortType     INTEGER,
            tnOscSfpTemperature  Integer32,
            tnOscMtu             Integer32,
            tnOscMtuNeg          Integer32
        }

--    obsolete
--    tnOscSfpPortType OBJECT-TYPE ::= { tnOscSfpPortConfigEntry 1 }

    tnOscSfpTemperature OBJECT-TYPE
        SYNTAX         Integer32
        UNITS          "Celsius"
        MAX-ACCESS     read-only
        STATUS         current
        DESCRIPTION    "The current temperature of the Osc Sfp."
        DEFVAL         { 0 }
        ::= { tnOscSfpPortConfigEntry 2 }

    tnOscMtu OBJECT-TYPE
        SYNTAX         Integer32
        MAX-ACCESS     read-create
        STATUS         current
        DESCRIPTION    "The MTU size for OSC interface, which to allow
                        remote monitoring of RAMAN/EDFA devices as well
                        as to limit overall packet fragmentation in the
                        network.

                        Current configurable range: 576 to 1500."
        DEFVAL         { 1500 }
        ::= { tnOscSfpPortConfigEntry 3 }

    tnOscMtuNeg OBJECT-TYPE
        SYNTAX         Integer32 (-1..1500)
        MAX-ACCESS     read-only
        STATUS         current
        DESCRIPTION    "The actual (negotiated) Maximum Transmission Unit
                        size, in units of bytes with default value -1,
                        when the MTU size has not yet been negotiated.
                        The default value -1 should be interpreted by
                        UIs as '-'."
        DEFVAL         { -1 }
        ::= { tnOscSfpPortConfigEntry 4 }

--------------------------------------------------------------------------------
-- DWDM GP Phy Port Config Table
--------------------------------------------------------------------------------
    tnDwdmGpPhyPortConfigTable OBJECT-TYPE
        SYNTAX         SEQUENCE OF TnDwdmGpPhyPortConfigEntry
        MAX-ACCESS     not-accessible
        STATUS         current
        DESCRIPTION    "Attributes against DWDM GP Phy ports."
        ::= { tnOpticalPortConfig 77 }

    tnDwdmGpPhyPortConfigEntry OBJECT-TYPE
        SYNTAX         TnDwdmGpPhyPortConfigEntry
        MAX-ACCESS     not-accessible
        STATUS         current
        DESCRIPTION    ""
        INDEX { ifIndex }
        ::= { tnDwdmGpPhyPortConfigTable 1 }

    TnDwdmGpPhyPortConfigEntry ::=
        SEQUENCE {
            tnDwdmGpPhyPortPacketIfType      INTEGER,
            tnDwdmGpPhyPortErroredFrameDrop  AluWdmDisabledEnabled,
            tnDwdmGpPhyPortAutoNegotiation   AluWdmDisabledEnabled,
            tnDwdmGpPhyPortPacketFcMode      INTEGER,
            tnDwdmGpPhyPortGfpcrc            INTEGER
        }

    tnDwdmGpPhyPortPacketIfType OBJECT-TYPE
        SYNTAX         INTEGER {
                         escon(1),
                         ficon(2),
                         isc3(3),
                         ficonE(4),
                         gmpGfpT(5),
                         fddi(6),
                         fc1G(7),
                         fc2G(8),
                         fc4G(9),
                         base100Fx(10),
                         dvbAsi(11),
                         dvi6000(12),
                         dv6000(13),
                         ge10GfpF(14),
                         ge10GfpFp(15),
                         ge10Cbr11049(16),
                         ge10Cbr11096(17),
                         fc10G(18),
                         ge1GfpF(19),
                         ge1GfpT(20),
                         ge10(21),
                         fc8GfpT(22),
                         gecbr100(23)
                       }
        MAX-ACCESS     read-create
        STATUS         current
        DESCRIPTION    "The packet interface type."
        ::= { tnDwdmGpPhyPortConfigEntry 1 }

    tnDwdmGpPhyPortErroredFrameDrop OBJECT-TYPE
        SYNTAX         AluWdmDisabledEnabled
        MAX-ACCESS     read-create
        STATUS         current
        DESCRIPTION    "The errored frame drop status."
        DEFVAL         { disabled }
        ::= { tnDwdmGpPhyPortConfigEntry 2 }

    tnDwdmGpPhyPortAutoNegotiation OBJECT-TYPE
        SYNTAX         AluWdmDisabledEnabled
        MAX-ACCESS     read-create
        STATUS         current
        DESCRIPTION    "The auto negotiation status."
        DEFVAL         { disabled }
        ::= { tnDwdmGpPhyPortConfigEntry 3 }

    tnDwdmGpPhyPortPacketFcMode OBJECT-TYPE
        SYNTAX         INTEGER {
                         fc(1),
                         ficon(2),
                         isc(3)
                       }
        MAX-ACCESS     read-create
        STATUS         current
        DESCRIPTION    "The fiber channel mode."
        DEFVAL         { fc }
        ::= { tnDwdmGpPhyPortConfigEntry 4 }

    tnDwdmGpPhyPortGfpcrc OBJECT-TYPE
        SYNTAX         INTEGER {
                         nonStd(1),
                         std(2)
                       }
        MAX-ACCESS     read-create
        STATUS         current
        DESCRIPTION    "Indication of the GFP CRC framing.
                        nonStd: Non-standard GFP CRC framing.
                        std :   Standard GFP CRC framing."
        DEFVAL         { std }
        ::= { tnDwdmGpPhyPortConfigEntry 5 }

--------------------------------------------------------------------------------
-- GCC Port Config Table
--------------------------------------------------------------------------------
--    obsolete
--    tnGccPortConfigTable OBJECT-TYPE ::= { tnOpticalPortConfig 78 }

--------------------------------------------------------------------------------
-- SVAC Optical Port Config Table
--------------------------------------------------------------------------------
    tnSvacPortConfigTable OBJECT-TYPE
        SYNTAX         SEQUENCE OF TnSvacPortConfigEntry
        MAX-ACCESS     not-accessible
        STATUS         current
        DESCRIPTION    "The ports on an SVAC optical card."
        ::= { tnOpticalPortConfig 79 }

    tnSvacPortConfigEntry OBJECT-TYPE
        SYNTAX         TnSvacPortConfigEntry
        MAX-ACCESS     not-accessible
        STATUS         current
        DESCRIPTION    ""
        INDEX { ifIndex }
        ::= { tnSvacPortConfigTable 1 }

    TnSvacPortConfigEntry ::=
        SEQUENCE {
            tnSvacPortConfigFunction INTEGER
        }

    tnSvacPortConfigFunction OBJECT-TYPE
        SYNTAX         INTEGER {
                         network(1),
                         client(2)
                       }
        MAX-ACCESS     read-only
        STATUS         current
        DESCRIPTION    "Indicates the functional type of this SVAC port."
        ::= { tnSvacPortConfigEntry 1 }

--------------------------------------------------------------------------------
-- SFD Optical Port Config Table
--------------------------------------------------------------------------------
    tnSfdPortConfigTable OBJECT-TYPE
        SYNTAX         SEQUENCE OF TnSfdPortConfigEntry
        MAX-ACCESS     not-accessible
        STATUS         current
        DESCRIPTION    "The ports on an SFD optical card."
        ::= { tnOpticalPortConfig 80 }

    tnSfdPortConfigEntry OBJECT-TYPE
        SYNTAX         TnSfdPortConfigEntry
        MAX-ACCESS     not-accessible
        STATUS         current
        DESCRIPTION    ""
        INDEX { ifIndex }
        ::= { tnSfdPortConfigTable 1 }

    TnSfdPortConfigEntry ::=
        SEQUENCE {
            tnSfd5aPortConfigFunction  AluWdmSfdPortType,
            tnSfd5bPortConfigFunction  AluWdmSfdPortType,
            tnSfd5cPortConfigFunction  AluWdmSfdPortType,
            tnSfd5dPortConfigFunction  AluWdmSfdPortType,
            tnSfd5ePortConfigFunction  AluWdmSfdPortType,
            tnSfd5fPortConfigFunction  AluWdmSfdPortType,
            tnSfd5gPortConfigFunction  AluWdmSfdPortType,
            tnSfd5hPortConfigFunction  AluWdmSfdPortType,
            tnSfd10aPortConfigFunction AluWdmSfdPortType,
            tnSfd10bPortConfigFunction AluWdmSfdPortType,
            tnSfd10cPortConfigFunction AluWdmSfdPortType,
            tnSfd10dPortConfigFunction AluWdmSfdPortType,
            tnSfd8aPortConfigFunction  AluWdmSfdPortType,
            tnSfd8bPortConfigFunction  AluWdmSfdPortType,
            tnSfd8cPortConfigFunction  AluWdmSfdPortType,
            tnSfd8dPortConfigFunction  AluWdmSfdPortType,
            tnSfd4aPortConfigFunction  AluWdmSfdPortType,
            tnSfd4bPortConfigFunction  AluWdmSfdPortType,
            tnSfd4cPortConfigFunction  AluWdmSfdPortType,
            tnSfd4dPortConfigFunction  AluWdmSfdPortType,
            tnSfd4ePortConfigFunction  AluWdmSfdPortType,
            tnSfd4fPortConfigFunction  AluWdmSfdPortType,
            tnSfd4gPortConfigFunction  AluWdmSfdPortType,
            tnSfd4hPortConfigFunction  AluWdmSfdPortType,
            tnSfd2aPortConfigFunction  AluWdmSfdPortType,
            tnSfd2bPortConfigFunction  AluWdmSfdPortType,
            tnSfd2cPortConfigFunction  AluWdmSfdPortType,
            tnSfd2dPortConfigFunction  AluWdmSfdPortType,
            tnSfd2ePortConfigFunction  AluWdmSfdPortType,
            tnSfd2fPortConfigFunction  AluWdmSfdPortType,
            tnSfd2gPortConfigFunction  AluWdmSfdPortType,
            tnSfd2hPortConfigFunction  AluWdmSfdPortType,
            tnSfd2iPortConfigFunction  AluWdmSfdPortType,
            tnSfd2lPortConfigFunction  AluWdmSfdPortType,
            tnSfd2mPortConfigFunction  AluWdmSfdPortType,
            tnSfd2nPortConfigFunction  AluWdmSfdPortType,
            tnSfd2oPortConfigFunction  AluWdmSfdPortType,
            tnSfd2pPortConfigFunction  AluWdmSfdPortType,
            tnSfd2qPortConfigFunction  AluWdmSfdPortType,
            tnSfd2rPortConfigFunction  AluWdmSfdPortType,
            tnVwmSfd8aPortConfigFunction AluWdmSfdPortType,
            tnVwmSfd8bPortConfigFunction AluWdmSfdPortType,
            tnVwmSfd8cPortConfigFunction AluWdmSfdPortType,
            tnVwmSfd8dPortConfigFunction AluWdmSfdPortType
        }

    tnSfd5aPortConfigFunction OBJECT-TYPE
        SYNTAX         AluWdmSfdPortType
        MAX-ACCESS     read-only
        STATUS         current
        DESCRIPTION    "Indicates the functional type of this SFD5A port."
        ::= { tnSfdPortConfigEntry 1 }

    tnSfd5bPortConfigFunction OBJECT-TYPE
        SYNTAX         AluWdmSfdPortType
        MAX-ACCESS     read-only
        STATUS         current
        DESCRIPTION    "Indicates the functional type of this SFD5B port."
        ::= { tnSfdPortConfigEntry 2 }

    tnSfd5cPortConfigFunction OBJECT-TYPE
        SYNTAX         AluWdmSfdPortType
        MAX-ACCESS     read-only
        STATUS         current
        DESCRIPTION    "Indicates the functional type of this SFD5C port."
        ::= { tnSfdPortConfigEntry 3 }

    tnSfd5dPortConfigFunction OBJECT-TYPE
        SYNTAX         AluWdmSfdPortType
        MAX-ACCESS     read-only
        STATUS         current
        DESCRIPTION    "Indicates the functional type of this SFD5D port."
        ::= { tnSfdPortConfigEntry 4 }

    tnSfd5ePortConfigFunction OBJECT-TYPE
        SYNTAX         AluWdmSfdPortType
        MAX-ACCESS     read-only
        STATUS         current
        DESCRIPTION    "Indicates the functional type of this SFD5E port."
        ::= { tnSfdPortConfigEntry 5 }

    tnSfd5fPortConfigFunction OBJECT-TYPE
        SYNTAX         AluWdmSfdPortType
        MAX-ACCESS     read-only
        STATUS         current
        DESCRIPTION    "Indicates the functional type of this SFD5F port."
        ::= { tnSfdPortConfigEntry 6 }

    tnSfd5gPortConfigFunction OBJECT-TYPE
        SYNTAX         AluWdmSfdPortType
        MAX-ACCESS     read-only
        STATUS         current
        DESCRIPTION    "Indicates the functional type of this SFD5G port."
        ::= { tnSfdPortConfigEntry 7 }

    tnSfd5hPortConfigFunction OBJECT-TYPE
        SYNTAX         AluWdmSfdPortType
        MAX-ACCESS     read-only
        STATUS         current
        DESCRIPTION    "Indicates the functional type of this SFD5H port."
        ::= { tnSfdPortConfigEntry 8 }

    tnSfd10aPortConfigFunction OBJECT-TYPE
        SYNTAX         AluWdmSfdPortType
        MAX-ACCESS     read-only
        STATUS         current
        DESCRIPTION    "Indicates the functional type of this SFD10A port."
        ::= { tnSfdPortConfigEntry 9 }

    tnSfd10bPortConfigFunction OBJECT-TYPE
        SYNTAX         AluWdmSfdPortType
        MAX-ACCESS     read-only
        STATUS         current
        DESCRIPTION    "Indicates the functional type of this SFD10B port."
        ::= { tnSfdPortConfigEntry 10 }

    tnSfd10cPortConfigFunction OBJECT-TYPE
        SYNTAX         AluWdmSfdPortType
        MAX-ACCESS     read-only
        STATUS         current
        DESCRIPTION    "Indicates the functional type of this SFD10C port."
        ::= { tnSfdPortConfigEntry 11 }

    tnSfd10dPortConfigFunction OBJECT-TYPE
        SYNTAX         AluWdmSfdPortType
        MAX-ACCESS     read-only
        STATUS         current
        DESCRIPTION    "Indicates the functional type of this SFD10D port."
        ::= { tnSfdPortConfigEntry 12 }

    tnSfd8aPortConfigFunction OBJECT-TYPE
        SYNTAX         AluWdmSfdPortType
        MAX-ACCESS     read-only
        STATUS         current
        DESCRIPTION    "Indicates the functional type of this SFD8A port."
        ::= { tnSfdPortConfigEntry 13 }

    tnSfd8bPortConfigFunction OBJECT-TYPE
        SYNTAX         AluWdmSfdPortType
        MAX-ACCESS     read-only
        STATUS         current
        DESCRIPTION    "Indicates the functional type of this SFD8B port."
        ::= { tnSfdPortConfigEntry 14 }

    tnSfd8cPortConfigFunction OBJECT-TYPE
        SYNTAX         AluWdmSfdPortType
        MAX-ACCESS     read-only
        STATUS         current
        DESCRIPTION    "Indicates the functional type of this SFD8C port."
        ::= { tnSfdPortConfigEntry 15 }

    tnSfd8dPortConfigFunction OBJECT-TYPE
        SYNTAX         AluWdmSfdPortType
        MAX-ACCESS     read-only
        STATUS         current
        DESCRIPTION    "Indicates the functional type of this SFD8D port."
        ::= { tnSfdPortConfigEntry 16 }

    tnSfd4aPortConfigFunction OBJECT-TYPE
        SYNTAX         AluWdmSfdPortType
        MAX-ACCESS     read-only
        STATUS         current
        DESCRIPTION    "Indicates the functional type of this SFD4A port."
        ::= { tnSfdPortConfigEntry 17 }

    tnSfd4bPortConfigFunction OBJECT-TYPE
        SYNTAX         AluWdmSfdPortType
        MAX-ACCESS     read-only
        STATUS         current
        DESCRIPTION    "Indicates the functional type of this SFD4B port."
        ::= { tnSfdPortConfigEntry 18 }

    tnSfd4cPortConfigFunction OBJECT-TYPE
        SYNTAX         AluWdmSfdPortType
        MAX-ACCESS     read-only
        STATUS         current
        DESCRIPTION    "Indicates the functional type of this SFD4C port."
        ::= { tnSfdPortConfigEntry 19 }

    tnSfd4dPortConfigFunction OBJECT-TYPE
        SYNTAX         AluWdmSfdPortType
        MAX-ACCESS     read-only
        STATUS         current
        DESCRIPTION    "Indicates the functional type of this SFD4D port."
        ::= { tnSfdPortConfigEntry 20 }

    tnSfd4ePortConfigFunction OBJECT-TYPE
        SYNTAX         AluWdmSfdPortType
        MAX-ACCESS     read-only
        STATUS         current
        DESCRIPTION    "Indicates the functional type of this SFD4E port."
        ::= { tnSfdPortConfigEntry 21 }

    tnSfd4fPortConfigFunction OBJECT-TYPE
        SYNTAX         AluWdmSfdPortType
        MAX-ACCESS     read-only
        STATUS         current
        DESCRIPTION    "Indicates the functional type of this SFD4F port."
        ::= { tnSfdPortConfigEntry 22 }

    tnSfd4gPortConfigFunction OBJECT-TYPE
        SYNTAX         AluWdmSfdPortType
        MAX-ACCESS     read-only
        STATUS         current
        DESCRIPTION    "Indicates the functional type of this SFD4G port."
        ::= { tnSfdPortConfigEntry 23 }

    tnSfd4hPortConfigFunction OBJECT-TYPE
        SYNTAX         AluWdmSfdPortType
        MAX-ACCESS     read-only
        STATUS         current
        DESCRIPTION    "Indicates the functional type of this SFD4H port."
        ::= { tnSfdPortConfigEntry 24 }

    tnSfd2aPortConfigFunction OBJECT-TYPE
        SYNTAX         AluWdmSfdPortType
        MAX-ACCESS     read-only
        STATUS         current
        DESCRIPTION    "Indicates the functional type of this SFD2A port."
        ::= { tnSfdPortConfigEntry 25 }

    tnSfd2bPortConfigFunction OBJECT-TYPE
        SYNTAX         AluWdmSfdPortType
        MAX-ACCESS     read-only
        STATUS         current
        DESCRIPTION    "Indicates the functional type of this SFD2B port."
        ::= { tnSfdPortConfigEntry 26 }

    tnSfd2cPortConfigFunction OBJECT-TYPE
        SYNTAX         AluWdmSfdPortType
        MAX-ACCESS     read-only
        STATUS         current
        DESCRIPTION    "Indicates the functional type of this SFD2C port."
        ::= { tnSfdPortConfigEntry 27 }

    tnSfd2dPortConfigFunction OBJECT-TYPE
        SYNTAX         AluWdmSfdPortType
        MAX-ACCESS     read-only
        STATUS         current
        DESCRIPTION    "Indicates the functional type of this SFD2D port."
        ::= { tnSfdPortConfigEntry 28 }

    tnSfd2ePortConfigFunction OBJECT-TYPE
        SYNTAX         AluWdmSfdPortType
        MAX-ACCESS     read-only
        STATUS         current
        DESCRIPTION    "Indicates the functional type of this SFD2E port."
        ::= { tnSfdPortConfigEntry 29 }

    tnSfd2fPortConfigFunction OBJECT-TYPE
        SYNTAX         AluWdmSfdPortType
        MAX-ACCESS     read-only
        STATUS         current
        DESCRIPTION    "Indicates the functional type of this SFD2F port."
        ::= { tnSfdPortConfigEntry 30 }

    tnSfd2gPortConfigFunction OBJECT-TYPE
        SYNTAX         AluWdmSfdPortType
        MAX-ACCESS     read-only
        STATUS         current
        DESCRIPTION    "Indicates the functional type of this SFD2G port."
        ::= { tnSfdPortConfigEntry 31 }

    tnSfd2hPortConfigFunction OBJECT-TYPE
        SYNTAX         AluWdmSfdPortType
        MAX-ACCESS     read-only
        STATUS         current
        DESCRIPTION    "Indicates the functional type of this SFD2H port."
        ::= { tnSfdPortConfigEntry 32 }

    tnSfd2iPortConfigFunction OBJECT-TYPE
        SYNTAX         AluWdmSfdPortType
        MAX-ACCESS     read-only
        STATUS         current
        DESCRIPTION    "Indicates the functional type of this SFD2I port."
        ::= { tnSfdPortConfigEntry 33 }

    tnSfd2lPortConfigFunction OBJECT-TYPE
        SYNTAX         AluWdmSfdPortType
        MAX-ACCESS     read-only
        STATUS         current
        DESCRIPTION    "Indicates the functional type of this SFD2L port."
        ::= { tnSfdPortConfigEntry 34 }

    tnSfd2mPortConfigFunction OBJECT-TYPE
        SYNTAX         AluWdmSfdPortType
        MAX-ACCESS     read-only
        STATUS         current
        DESCRIPTION    "Indicates the functional type of this SFD2M port."
        ::= { tnSfdPortConfigEntry 35 }

    tnSfd2nPortConfigFunction OBJECT-TYPE
        SYNTAX         AluWdmSfdPortType
        MAX-ACCESS     read-only
        STATUS         current
        DESCRIPTION    "Indicates the functional type of this SFD2N port."
        ::= { tnSfdPortConfigEntry 36 }

    tnSfd2oPortConfigFunction OBJECT-TYPE
        SYNTAX         AluWdmSfdPortType
        MAX-ACCESS     read-only
        STATUS         current
        DESCRIPTION    "Indicates the functional type of this SFD2O port."
        ::= { tnSfdPortConfigEntry 37 }

    tnSfd2pPortConfigFunction OBJECT-TYPE
        SYNTAX         AluWdmSfdPortType
        MAX-ACCESS     read-only
        STATUS         current
        DESCRIPTION    "Indicates the functional type of this SFD2P port."
        ::= { tnSfdPortConfigEntry 38 }

    tnSfd2qPortConfigFunction OBJECT-TYPE
        SYNTAX         AluWdmSfdPortType
        MAX-ACCESS     read-only
        STATUS         current
        DESCRIPTION    "Indicates the functional type of this SFD2Q port."
        ::= { tnSfdPortConfigEntry 39 }

    tnSfd2rPortConfigFunction OBJECT-TYPE
        SYNTAX         AluWdmSfdPortType
        MAX-ACCESS     read-only
        STATUS         current
        DESCRIPTION    "Indicates the functional type of this SFD2R port."
        ::= { tnSfdPortConfigEntry 40 }

     tnVwmSfd8aPortConfigFunction OBJECT-TYPE
        SYNTAX         AluWdmSfdPortType
        MAX-ACCESS     read-only
        STATUS         current
        DESCRIPTION    "Indicates the functional type of this VWMSFD8A port."
        ::= { tnSfdPortConfigEntry 41 } 
       
     tnVwmSfd8bPortConfigFunction OBJECT-TYPE
        SYNTAX         AluWdmSfdPortType
        MAX-ACCESS     read-only
        STATUS         current
        DESCRIPTION    "Indicates the functional type of this VWMSFD8B port."
        ::= { tnSfdPortConfigEntry 42 }      
        
     tnVwmSfd8cPortConfigFunction OBJECT-TYPE
        SYNTAX         AluWdmSfdPortType
        MAX-ACCESS     read-only
        STATUS         current
        DESCRIPTION    "Indicates the functional type of this VWMSFD8C port."
        ::= { tnSfdPortConfigEntry 43 }
        
     tnVwmSfd8dPortConfigFunction OBJECT-TYPE
        SYNTAX         AluWdmSfdPortType
        MAX-ACCESS     read-only
        STATUS         current
        DESCRIPTION    "Indicates the functional type of this VWMSFD8D port."
        ::= { tnSfdPortConfigEntry 44 }  

--------------------------------------------------------------------------------
-- SFC Optical Port Config Table
--------------------------------------------------------------------------------
    tnSfcPortConfigTable OBJECT-TYPE
        SYNTAX         SEQUENCE OF TnSfcPortConfigEntry
        MAX-ACCESS     not-accessible
        STATUS         current
        DESCRIPTION    "The ports on an SFC optical card."
        ::= { tnOpticalPortConfig 81 }

    tnSfcPortConfigEntry OBJECT-TYPE
        SYNTAX         TnSfcPortConfigEntry
        MAX-ACCESS     not-accessible
        STATUS         current
        DESCRIPTION    ""
        INDEX { ifIndex }
        ::= { tnSfcPortConfigTable 1 }

    TnSfcPortConfigEntry ::=
        SEQUENCE {
            tnSfc2aPortConfigFunction INTEGER,
            tnSfc2bPortConfigFunction INTEGER,
            tnSfc2cPortConfigFunction INTEGER,
            tnSfc2dPortConfigFunction INTEGER,
            tnSfc4aPortConfigFunction INTEGER,
            tnSfc4bPortConfigFunction INTEGER,
            tnSfc8PortConfigFunction  INTEGER,
            tnSfc1aPortConfigFunction INTEGER,
            tnSfc1bPortConfigFunction INTEGER,
            tnSfc1cPortConfigFunction INTEGER,
            tnSfc1dPortConfigFunction INTEGER,
            tnSfc1ePortConfigFunction INTEGER,
            tnSfc1fPortConfigFunction INTEGER,
            tnSfc1gPortConfigFunction INTEGER,
            tnSfc1hPortConfigFunction INTEGER,
            tnVwmSfc8PortConfigFunction INTEGER
        }

    tnSfc2aPortConfigFunction OBJECT-TYPE
        SYNTAX         INTEGER {
                         channel(1),
                         mux(2),
                         exp(3)
                       }
        MAX-ACCESS     read-only
        STATUS         current
        DESCRIPTION    "Indicates the functional type of this SFC2A port."
        ::= { tnSfcPortConfigEntry 1 }

    tnSfc2bPortConfigFunction OBJECT-TYPE
        SYNTAX         INTEGER {
                         channel(1),
                         mux(2),
                         exp(3)
                       }
        MAX-ACCESS     read-only
        STATUS         current
        DESCRIPTION    "Indicates the functional type of this SFC2B port."
        ::= { tnSfcPortConfigEntry 2 }

    tnSfc2cPortConfigFunction OBJECT-TYPE
        SYNTAX         INTEGER {
                         channel(1),
                         mux(2),
                         exp(3)
                       }
        MAX-ACCESS     read-only
        STATUS         current
        DESCRIPTION    "Indicates the functional type of this SFC2C port."
        ::= { tnSfcPortConfigEntry 3 }

    tnSfc2dPortConfigFunction OBJECT-TYPE
        SYNTAX         INTEGER {
                         channel(1),
                         mux(2),
                         exp(3)
                       }
        MAX-ACCESS     read-only
        STATUS         current
        DESCRIPTION    "Indicates the functional type of this SFC2D port."
        ::= { tnSfcPortConfigEntry 4 }

    tnSfc4aPortConfigFunction OBJECT-TYPE
        SYNTAX         INTEGER {
                         channel(1),
                         mux(2),
                         exp(3)
                       }
        MAX-ACCESS     read-only
        STATUS         current
        DESCRIPTION    "Indicates the functional type of this SFC4A port."
        ::= { tnSfcPortConfigEntry 5 }

    tnSfc4bPortConfigFunction OBJECT-TYPE
        SYNTAX         INTEGER {
                         channel(1),
                         mux(2),
                         exp(3)
                       }
        MAX-ACCESS     read-only
        STATUS         current
        DESCRIPTION    "Indicates the functional type of this SFC4B port."
        ::= { tnSfcPortConfigEntry 6 }

    tnSfc8PortConfigFunction OBJECT-TYPE
        SYNTAX         INTEGER {
                         channel(1),
                         mux(2)
                       }
        MAX-ACCESS     read-only
        STATUS         current
        DESCRIPTION    "Indicates the functional type of this SFC8 port."
        ::= { tnSfcPortConfigEntry 7 }

    tnSfc1aPortConfigFunction OBJECT-TYPE
        SYNTAX         INTEGER {
                         channel(1),
                         mux(2),
                         exp(3)
                       }
        MAX-ACCESS     read-only
        STATUS         current
        DESCRIPTION    "Indicates the functional type of this SFC1A port."
        ::= { tnSfcPortConfigEntry 8 }

    tnSfc1bPortConfigFunction OBJECT-TYPE
        SYNTAX         INTEGER {
                         channel(1),
                         mux(2),
                         exp(3)
                       }
        MAX-ACCESS     read-only
        STATUS         current
        DESCRIPTION    "Indicates the functional type of this SFC1B port."
        ::= { tnSfcPortConfigEntry 9 }

    tnSfc1cPortConfigFunction OBJECT-TYPE
        SYNTAX         INTEGER {
                         channel(1),
                         mux(2),
                         exp(3)
                       }
        MAX-ACCESS     read-only
        STATUS         current
        DESCRIPTION    "Indicates the functional type of this SFC1C port."
        ::= { tnSfcPortConfigEntry 10 }

    tnSfc1dPortConfigFunction OBJECT-TYPE
        SYNTAX         INTEGER {
                         channel(1),
                         mux(2),
                         exp(3)
                       }
        MAX-ACCESS     read-only
        STATUS         current
        DESCRIPTION    "Indicates the functional type of this SFC1D port."
        ::= { tnSfcPortConfigEntry 11 }

    tnSfc1ePortConfigFunction OBJECT-TYPE
        SYNTAX         INTEGER {
                         channel(1),
                         mux(2),
                         exp(3)
                       }
        MAX-ACCESS     read-only
        STATUS         current
        DESCRIPTION    "Indicates the functional type of this SFC1E port."
        ::= { tnSfcPortConfigEntry 12 }

    tnSfc1fPortConfigFunction OBJECT-TYPE
        SYNTAX         INTEGER {
                         channel(1),
                         mux(2),
                         exp(3)
                       }
        MAX-ACCESS     read-only
        STATUS         current
        DESCRIPTION    "Indicates the functional type of this SFC1F port."
        ::= { tnSfcPortConfigEntry 13 }

    tnSfc1gPortConfigFunction OBJECT-TYPE
        SYNTAX         INTEGER {
                         channel(1),
                         mux(2),
                         exp(3)
                       }
        MAX-ACCESS     read-only
        STATUS         current
        DESCRIPTION    "Indicates the functional type of this SFC1G port."
        ::= { tnSfcPortConfigEntry 14 }

    tnSfc1hPortConfigFunction OBJECT-TYPE
        SYNTAX         INTEGER {
                         channel(1),
                         mux(2),
                         exp(3)
                       }
        MAX-ACCESS     read-only
        STATUS         current
        DESCRIPTION    "Indicates the functional type of this SFC1H port."
        ::= { tnSfcPortConfigEntry 15 }

    tnVwmSfc8PortConfigFunction OBJECT-TYPE
        SYNTAX         INTEGER {
                         channel(1),
                         mux(2),
                         exp(3)
                       }
        MAX-ACCESS     read-only
        STATUS         current
        DESCRIPTION    "Indicates the functional type of this VWMSFC8 port."
        ::= { tnSfcPortConfigEntry 16 }  

--------------------------------------------------------------------------------
-- VTS Port Config Table
--------------------------------------------------------------------------------
    tnVtsPortConfigTable OBJECT-TYPE
        SYNTAX         SEQUENCE OF TnVtsPortConfigEntry
        MAX-ACCESS     not-accessible
        STATUS         current
        DESCRIPTION    "The VTS attributes on OT ports."
        ::= { tnOpticalPortConfig 82 }

    tnVtsPortConfigEntry OBJECT-TYPE
        SYNTAX         TnVtsPortConfigEntry
        MAX-ACCESS     not-accessible
        STATUS         current
        DESCRIPTION    ""
        INDEX { ifIndex }
        ::= { tnVtsPortConfigTable 1 }

    TnVtsPortConfigEntry ::=
        SEQUENCE {
            tnVtsPortVts1Source AluWdmVtsSource,
            tnVtsPortVts2Source AluWdmVtsSource,
            tnVtsPortVts3Source AluWdmVtsSource,
            tnVtsPortVts4Source AluWdmVtsSource,
            tnVtsPortVts5Source AluWdmVtsSource,
            tnVtsPortVts6Source AluWdmVtsSource,
            tnVtsPortVts7Source AluWdmVtsSource,
            tnVtsPortVts8Source AluWdmVtsSource,
            tnVtsPortVts9Source AluWdmVtsSource,
            tnVtsPortVts10Source AluWdmVtsSource
        }

    tnVtsPortVts1Source OBJECT-TYPE
        SYNTAX         AluWdmVtsSource
        MAX-ACCESS     read-create
        STATUS         current
        DESCRIPTION    ""
        DEFVAL         { none }
        ::= { tnVtsPortConfigEntry 1 }

    tnVtsPortVts2Source OBJECT-TYPE
        SYNTAX         AluWdmVtsSource
        MAX-ACCESS     read-create
        STATUS         current
        DESCRIPTION    ""
        DEFVAL         { none }
        ::= { tnVtsPortConfigEntry 2 }

    tnVtsPortVts3Source OBJECT-TYPE
        SYNTAX         AluWdmVtsSource
        MAX-ACCESS     read-create
        STATUS         current
        DESCRIPTION    ""
        DEFVAL         { none }
        ::= { tnVtsPortConfigEntry 3 }

    tnVtsPortVts4Source OBJECT-TYPE
        SYNTAX         AluWdmVtsSource
        MAX-ACCESS     read-create
        STATUS         current
        DESCRIPTION    ""
        DEFVAL         { none }
        ::= { tnVtsPortConfigEntry 4 }

    tnVtsPortVts5Source OBJECT-TYPE
        SYNTAX         AluWdmVtsSource
        MAX-ACCESS     read-create
        STATUS         current
        DESCRIPTION    ""
        DEFVAL         { none }
        ::= { tnVtsPortConfigEntry 5 }

    tnVtsPortVts6Source OBJECT-TYPE
        SYNTAX         AluWdmVtsSource
        MAX-ACCESS     read-create
        STATUS         current
        DESCRIPTION    ""
        DEFVAL         { none }
        ::= { tnVtsPortConfigEntry 6 }

    tnVtsPortVts7Source OBJECT-TYPE
        SYNTAX         AluWdmVtsSource
        MAX-ACCESS     read-create
        STATUS         current
        DESCRIPTION    ""
        DEFVAL         { none }
        ::= { tnVtsPortConfigEntry 7 }

    tnVtsPortVts8Source OBJECT-TYPE
        SYNTAX         AluWdmVtsSource
        MAX-ACCESS     read-create
        STATUS         current
        DESCRIPTION    ""
        DEFVAL         { none }
        ::= { tnVtsPortConfigEntry 8 }

    tnVtsPortVts9Source OBJECT-TYPE
        SYNTAX         AluWdmVtsSource
        MAX-ACCESS     read-create
        STATUS         current
        DESCRIPTION    ""
        DEFVAL         { none }
        ::= { tnVtsPortConfigEntry 9 }

    tnVtsPortVts10Source OBJECT-TYPE
        SYNTAX         AluWdmVtsSource
        MAX-ACCESS     read-create
        STATUS         current
        DESCRIPTION    ""
        DEFVAL         { none }
        ::= { tnVtsPortConfigEntry 10 }

--------------------------------------------------------------------------------
-- OMD Common Port Config Table
--------------------------------------------------------------------------------
    tnOmdPortConfigTable OBJECT-TYPE
        SYNTAX         SEQUENCE OF TnOmdPortConfigEntry
        MAX-ACCESS     not-accessible
        STATUS         current
        DESCRIPTION    "Common attributes against OMD ports for SFC and
                        SFD packs."
        ::= { tnOpticalPortConfig 83 }

    tnOmdPortConfigEntry OBJECT-TYPE
        SYNTAX         TnOmdPortConfigEntry
        MAX-ACCESS     not-accessible
        STATUS         current
        DESCRIPTION    ""
        INDEX { ifIndex }
        ::= { tnOmdPortConfigTable 1 }

    TnOmdPortConfigEntry ::=
        SEQUENCE {
            tnOmdPortLosThreshold              Integer32,
            tnOmdPortLosThresholdTolerance     Unsigned32,
            tnOmdPortLosOutThreshold           Integer32,
            tnOmdPortLosOutThresholdTolerance  Unsigned32
        }

    tnOmdPortLosThreshold OBJECT-TYPE
        SYNTAX         Integer32
        UNITS          "mBm"
        MAX-ACCESS     read-create
        STATUS         current
        DESCRIPTION    "The following description applies to the SIG_IN
                        of the OMD port of the SFC1, SFC2, SFC4, SFC8,
                        SFD5, and SFD8 cards:

                        Current configurable ranges and defaults:

                        SFC1:  (-2600.. 980), -2600
                        SFC2:  (-2600.. 980), -2600
                        SFC4:  (-2600.. 980), -2600
                        SFC8:  (-2600.. 980), -2600
                        SFD4:  (-3200..2000), -3200
                        SFD5:  (-3200..2000), -3200
                        SFD8:  (-3200..1700), -3200."
        ::= { tnOmdPortConfigEntry 1 }

    tnOmdPortLosThresholdTolerance OBJECT-TYPE
        SYNTAX         Unsigned32
        UNITS          "mB"
        MAX-ACCESS     read-create
        STATUS         current
        DESCRIPTION    "This is the difference above the LOS set and
                        clear points and applies to the SIG_IN of the
                        OMD port of the SFC1, SFC2, SFC4, SFC8, SFD5,
                        and SFD8 cards:

                        Current configurable range: 50 to 600."
        DEFVAL         { 200 }
        ::= { tnOmdPortConfigEntry 2 }

    tnOmdPortLosOutThreshold OBJECT-TYPE
        SYNTAX         Integer32
        UNITS          "mBm"
        MAX-ACCESS     read-create
        STATUS         current
        DESCRIPTION    "The following description applies to the SIG_OUT
                        of the OMD port of the SFD5 and SFD8 cards:

                        Current configurable range:

                        SFD5: -3200 to 2000
                        SFD8: -3200 to 1700."
        DEFVAL         { -3200 }
        ::= { tnOmdPortConfigEntry 3 }

    tnOmdPortLosOutThresholdTolerance OBJECT-TYPE
        SYNTAX         Unsigned32
        UNITS          "mB"
        MAX-ACCESS     read-create
        STATUS         current
        DESCRIPTION    "This is the difference above the LOS set and
                        clear points and applies to the SIG_out of the
                        OMD port of the SFD5 and SFD8 cards:

                        Current configurable range: 50 to 600."
        DEFVAL         { 200 }
        ::= { tnOmdPortConfigEntry 4 }

--------------------------------------------------------------------------------
-- 4DPA4 Optical Port Config Scalars
--------------------------------------------------------------------------------
    tn4dpa4PortConfigAttributeTotal OBJECT-TYPE
        SYNTAX         Integer32
        MAX-ACCESS     read-only
        STATUS         current
        DESCRIPTION    ""
        ::= { tnOpticalPortConfig 84 }

--------------------------------------------------------------------------------
-- 4DPA4 Optical Port Config Table
--------------------------------------------------------------------------------
    tn4dpa4PortConfigTable OBJECT-TYPE
        SYNTAX         SEQUENCE OF Tn4dpa4PortConfigEntry
        MAX-ACCESS     not-accessible
        STATUS         current
        DESCRIPTION    "The ports on a 4DPA4 optical card."
        ::= { tnOpticalPortConfig 85 }

    tn4dpa4PortConfigEntry OBJECT-TYPE
        SYNTAX         Tn4dpa4PortConfigEntry
        MAX-ACCESS     not-accessible
        STATUS         current
        DESCRIPTION    ""
        INDEX { ifIndex }
        ::= { tn4dpa4PortConfigTable 1 }

    Tn4dpa4PortConfigEntry ::=
        SEQUENCE {
            tn4dpa4PortConfigFunction INTEGER
        }

    tn4dpa4PortConfigFunction OBJECT-TYPE
        SYNTAX         INTEGER {
                         network(1),
                         client(2),
                         evoa(3)
                       }
        MAX-ACCESS     read-only
        STATUS         current
        DESCRIPTION    "Indicates the functional type of this 4DPA4 port."
        ::= { tn4dpa4PortConfigEntry 1 }

--------------------------------------------------------------------------------
-- CWR8-88 Optical Port Config Scalars
--------------------------------------------------------------------------------
    tnCwr8c88PortConfigAttributeTotal OBJECT-TYPE
        SYNTAX         Integer32
        MAX-ACCESS     read-only
        STATUS         current
        DESCRIPTION    ""
        ::= { tnOpticalPortConfig 86 }

--------------------------------------------------------------------------------
-- CWR8-88 Optical Port Config Table
--------------------------------------------------------------------------------
    tnCwr8c88PortConfigTable OBJECT-TYPE
        SYNTAX         SEQUENCE OF TnCwr8c88PortConfigEntry
        MAX-ACCESS     not-accessible
        STATUS         current
        DESCRIPTION    "The ports on a CWR8-88 optical card."
        ::= { tnOpticalPortConfig 87 }

    tnCwr8c88PortConfigEntry OBJECT-TYPE
        SYNTAX         TnCwr8c88PortConfigEntry
        MAX-ACCESS     not-accessible
        STATUS         current
        DESCRIPTION    ""
        INDEX { ifIndex }
        ::= { tnCwr8c88PortConfigTable 1 }

    TnCwr8c88PortConfigEntry ::=
        SEQUENCE {
            tnCwr8c88PortConfigFunction  INTEGER,
--            obsolete
--            tnCwr8c88PortBlockerAging    Unsigned32,
            tnCwr8c88PortDropTargetPower Integer32
        }

    tnCwr8c88PortConfigFunction OBJECT-TYPE
        SYNTAX         INTEGER {
                         signal(1),
                         test(2),
                         thru(3),
                         colorless(4),
                         omd(5),
                         inv(6)
                       }
        MAX-ACCESS     read-only
        STATUS         current
        DESCRIPTION    "Indicates the functional type of this CWR8-88 port."
        ::= { tnCwr8c88PortConfigEntry 1 }

--    obsolete
--    tnCwr8c88PortBlockerAging OBJECT-TYPE ::= { tnCwr8c88PortConfigEntry 2 }

    tnCwr8c88PortDropTargetPower OBJECT-TYPE
        SYNTAX         Integer32
        UNITS          "mBm"
        MAX-ACCESS     read-create
        STATUS         current
        DESCRIPTION    "The following description applies to the
                        colorless port of the CWR8-88 card:

                        The drop target power.

                        Current configurable range: -2650 to -400."
        DEFVAL         { -1200 }
        ::= { tnCwr8c88PortConfigEntry 3 }

--------------------------------------------------------------------------------
-- SFD44B Optical Port Config Scalars
--------------------------------------------------------------------------------
    tnSfd44bPortConfigAttributeTotal OBJECT-TYPE
        SYNTAX         Integer32
        MAX-ACCESS     read-only
        STATUS         current
        DESCRIPTION    ""
        ::= { tnOpticalPortConfig 88 }

--------------------------------------------------------------------------------
-- SFD44B Optical Port Config Table
--------------------------------------------------------------------------------
    tnSfd44bPortConfigTable OBJECT-TYPE
        SYNTAX         SEQUENCE OF TnSfd44bPortConfigEntry
        MAX-ACCESS     not-accessible
        STATUS         current
        DESCRIPTION    "The ports on an SFD44B optical card."
        ::= { tnOpticalPortConfig 89 }

    tnSfd44bPortConfigEntry OBJECT-TYPE
        SYNTAX         TnSfd44bPortConfigEntry
        MAX-ACCESS     not-accessible
        STATUS         current
        DESCRIPTION    ""
        INDEX { ifIndex }
        ::= { tnSfd44bPortConfigTable 1 }

    TnSfd44bPortConfigEntry ::=
        SEQUENCE {
            tnSfd44bPortConfigFunction INTEGER
        }

    tnSfd44bPortConfigFunction OBJECT-TYPE
        SYNTAX         INTEGER {
                         channel(1),
                         mux(2)
                       }
        MAX-ACCESS     read-only
        STATUS         current
        DESCRIPTION    "Indicates the functional type of this SFD44B port:

                        port 1-44 - channel
                        port 45 - mux"
        ::= { tnSfd44bPortConfigEntry 1 }

--------------------------------------------------------------------------------
-- ITLB Optical Port Config Scalars
--------------------------------------------------------------------------------
    tnItlbPortConfigAttributeTotal OBJECT-TYPE
        SYNTAX         Integer32
        MAX-ACCESS     read-only
        STATUS         current
        DESCRIPTION    ""
        ::= { tnOpticalPortConfig 90 }

--------------------------------------------------------------------------------
-- ITLB Optical Port Config Table
--------------------------------------------------------------------------------
    tnItlbPortConfigTable OBJECT-TYPE
        SYNTAX         SEQUENCE OF TnItlbPortConfigEntry
        MAX-ACCESS     not-accessible
        STATUS         current
        DESCRIPTION    "The ports on an ITLB optical card."
        ::= { tnOpticalPortConfig 91 }

    tnItlbPortConfigEntry OBJECT-TYPE
        SYNTAX         TnItlbPortConfigEntry
        MAX-ACCESS     not-accessible
        STATUS         current
        DESCRIPTION    ""
        INDEX { ifIndex }
        ::= { tnItlbPortConfigTable 1 }

    TnItlbPortConfigEntry ::=
        SEQUENCE {
            tnItlbPortConfigFunction INTEGER
        }

    tnItlbPortConfigFunction OBJECT-TYPE
        SYNTAX         INTEGER {
                         signal(1),
                         even(2),
                         odd(3)
                       }
        MAX-ACCESS     read-only
        STATUS         current
        DESCRIPTION    "Indicates the functional type of this ITLB port:

                        port 1 - signal
                        port 2 - even
                        port 3 - odd"
        ::= { tnItlbPortConfigEntry 1 }

--------------------------------------------------------------------------------
-- AHPLG Optical Port Config Scalars
--------------------------------------------------------------------------------
    tnAhplgPortConfigAttributeTotal OBJECT-TYPE
        SYNTAX         Integer32
        MAX-ACCESS     read-only
        STATUS         current
        DESCRIPTION    ""
        ::= { tnOpticalPortConfig 92 }

--------------------------------------------------------------------------------
-- AHPLG Optical Port Config Table
--------------------------------------------------------------------------------
    tnAhplgPortConfigTable OBJECT-TYPE
        SYNTAX         SEQUENCE OF TnAhplgPortConfigEntry
        MAX-ACCESS     not-accessible
        STATUS         current
        DESCRIPTION    "The ports on an AHPLG optical card."
        ::= { tnOpticalPortConfig 93 }

    tnAhplgPortConfigEntry OBJECT-TYPE
        SYNTAX         TnAhplgPortConfigEntry
        MAX-ACCESS     not-accessible
        STATUS         current
        DESCRIPTION    ""
        INDEX { ifIndex }
        ::= { tnAhplgPortConfigTable 1 }

    TnAhplgPortConfigEntry ::=
        SEQUENCE {
            tnAhplgPortConfigFunction INTEGER
        }

    tnAhplgPortConfigFunction OBJECT-TYPE
        SYNTAX         INTEGER {
                         line(1),
                         signal(2),
                         dcm(3),
                         inv(4),
                         osc(5)
                       }
        MAX-ACCESS     read-only
        STATUS         current
        DESCRIPTION    "Indicates the functional type of this AHPLG port."
        ::= { tnAhplgPortConfigEntry 1 }

--------------------------------------------------------------------------------
-- DWDM Common OTU1/ODU1 Line Port Config Table
--------------------------------------------------------------------------------
    tnDwdmCmnOtu1Odu1LinePortConfigTable OBJECT-TYPE
        SYNTAX         SEQUENCE OF TnDwdmCmnOtu1Odu1LinePortConfigEntry
        MAX-ACCESS     not-accessible
        STATUS         current
        DESCRIPTION    "Common attributes against DWDM line ports."
        ::= { tnOpticalPortConfig 94 }

    tnDwdmCmnOtu1Odu1LinePortConfigEntry OBJECT-TYPE
        SYNTAX         TnDwdmCmnOtu1Odu1LinePortConfigEntry
        MAX-ACCESS     not-accessible
        STATUS         current
        DESCRIPTION    ""
        INDEX { ifIndex }
        ::= { tnDwdmCmnOtu1Odu1LinePortConfigTable 1 }

    TnDwdmCmnOtu1Odu1LinePortConfigEntry ::=
        SEQUENCE {
            tnDwdmCmnLinePortOchOtu1FecMode                    AluWdmFecMode,
            tnDwdmCmnLinePortOchOtu1Rate                       AluWdmPortOchOtuRate,
            tnDwdmCmnLinePortOtu1TransmittedTti                OCTET STRING,
            tnDwdmCmnLinePortOtu1ExpectedTti                   OCTET STRING,
            tnDwdmCmnLinePortOtu1TimConsequenceAction          AluWdmDisabledEnabled,
            tnDwdmCmnLinePortOtu1TimDetectionMode              AluWdmTimDetectionMode,
            tnDwdmCmnLinePortOdu1PayloadType                   Unsigned32,
            tnDwdmCmnLinePortOdu1OchSignalDefConsequenceAction AluWdmOduOchSignalDefConsequenceAction,
            tnDwdmCmnLinePortOdu1PlmConsequenceAction          TruthValue,
            tnDwdmCmnLinePortOdu1MappingMode                   AluWdmMappingMode,
            tnDwdmCmnLinePortOdu1TpMode                        TruthValue,
            tnDwdmCmnLinePortOdu1TransmittedTti                OCTET STRING,
            tnDwdmCmnLinePortOdu1ExpectedTti                   OCTET STRING,
            tnDwdmCmnLinePortOdu1TimConsequenceAction          AluWdmDisabledEnabled,
            tnDwdmCmnLinePortOdu1TimDetectionMode              AluWdmTimDetectionMode,
            tnDwdmCmnLinePortOdu1Interworking                  TruthValue
        }

    tnDwdmCmnLinePortOchOtu1FecMode OBJECT-TYPE
        SYNTAX         AluWdmFecMode
        MAX-ACCESS     read-create
        STATUS         current
        DESCRIPTION    "OTU1 FEC mode."
        DEFVAL         { g709Fec }
        ::= { tnDwdmCmnOtu1Odu1LinePortConfigEntry 1 }

    tnDwdmCmnLinePortOchOtu1Rate OBJECT-TYPE
        SYNTAX         AluWdmPortOchOtuRate
        MAX-ACCESS     read-create
        STATUS         current
        DESCRIPTION    "OTU1 rate."
        DEFVAL         { otm2G66 }
        ::= { tnDwdmCmnOtu1Odu1LinePortConfigEntry 2 }

    tnDwdmCmnLinePortOtu1TransmittedTti OBJECT-TYPE
        SYNTAX         OCTET STRING
        MAX-ACCESS     read-create
        STATUS         current
        DESCRIPTION    "OTU1 transmitted TTI."
        DEFVAL         { "" }
        ::= { tnDwdmCmnOtu1Odu1LinePortConfigEntry 3 }

    tnDwdmCmnLinePortOtu1ExpectedTti OBJECT-TYPE
        SYNTAX         OCTET STRING
        MAX-ACCESS     read-create
        STATUS         current
        DESCRIPTION    "OTU1 expected TTI."
        DEFVAL         { "" }
        ::= { tnDwdmCmnOtu1Odu1LinePortConfigEntry 4 }

    tnDwdmCmnLinePortOtu1TimConsequenceAction OBJECT-TYPE
        SYNTAX         AluWdmDisabledEnabled
        MAX-ACCESS     read-create
        STATUS         current
        DESCRIPTION    "OTU1 TIM consequence action."
        DEFVAL         { 0 }
        ::= { tnDwdmCmnOtu1Odu1LinePortConfigEntry 5 }

    tnDwdmCmnLinePortOtu1TimDetectionMode OBJECT-TYPE
        SYNTAX         AluWdmTimDetectionMode
        MAX-ACCESS     read-create
        STATUS         current
        DESCRIPTION    "OTU1 TIM detection mode."
        DEFVAL         { off }
        ::= { tnDwdmCmnOtu1Odu1LinePortConfigEntry 6 }

    tnDwdmCmnLinePortOdu1PayloadType OBJECT-TYPE
        SYNTAX         Unsigned32
        MAX-ACCESS     read-create
        STATUS         current
        DESCRIPTION    "ODU1 payload type.

                        Current configurable range: 0 to 255."
        DEFVAL         { 128 }
        ::= { tnDwdmCmnOtu1Odu1LinePortConfigEntry 7 }

    tnDwdmCmnLinePortOdu1OchSignalDefConsequenceAction OBJECT-TYPE
        SYNTAX         AluWdmOduOchSignalDefConsequenceAction
        MAX-ACCESS     read-create
        STATUS         current
        DESCRIPTION    "ODU1 OCH signal def consequence action."
        DEFVAL         { genericAis }
        ::= { tnDwdmCmnOtu1Odu1LinePortConfigEntry 8 }

    tnDwdmCmnLinePortOdu1PlmConsequenceAction OBJECT-TYPE
        SYNTAX         TruthValue
        MAX-ACCESS     read-create
        STATUS         current
        DESCRIPTION    "PLM consequence action."
        DEFVAL         { false }
        ::= { tnDwdmCmnOtu1Odu1LinePortConfigEntry 9 }

    tnDwdmCmnLinePortOdu1MappingMode OBJECT-TYPE
        SYNTAX         AluWdmMappingMode
        MAX-ACCESS     read-create
        STATUS         current
        DESCRIPTION    "ODU1 mapping mode."
        DEFVAL         { rsB }
        ::= { tnDwdmCmnOtu1Odu1LinePortConfigEntry 10 }

    tnDwdmCmnLinePortOdu1TpMode OBJECT-TYPE
        SYNTAX         TruthValue
        MAX-ACCESS     read-create
        STATUS         current
        DESCRIPTION    "ODU1 TP mode."
        DEFVAL         { true }
        ::= { tnDwdmCmnOtu1Odu1LinePortConfigEntry 11 }

    tnDwdmCmnLinePortOdu1TransmittedTti OBJECT-TYPE
        SYNTAX         OCTET STRING
        MAX-ACCESS     read-create
        STATUS         current
        DESCRIPTION    "ODU1 transmitted TTI."
        DEFVAL         { "" }
        ::= { tnDwdmCmnOtu1Odu1LinePortConfigEntry 12 }

    tnDwdmCmnLinePortOdu1ExpectedTti OBJECT-TYPE
        SYNTAX         OCTET STRING
        MAX-ACCESS     read-create
        STATUS         current
        DESCRIPTION    "ODU1 expected TTI."
        DEFVAL         { "" }
        ::= { tnDwdmCmnOtu1Odu1LinePortConfigEntry 13 }

    tnDwdmCmnLinePortOdu1TimConsequenceAction OBJECT-TYPE
        SYNTAX         AluWdmDisabledEnabled
        MAX-ACCESS     read-create
        STATUS         current
        DESCRIPTION    "ODU1 TIM consequence action."
        DEFVAL         { disabled }
        ::= { tnDwdmCmnOtu1Odu1LinePortConfigEntry 14 }

    tnDwdmCmnLinePortOdu1TimDetectionMode OBJECT-TYPE
        SYNTAX         AluWdmTimDetectionMode
        MAX-ACCESS     read-create
        STATUS         current
        DESCRIPTION    "ODU1 TIM detection mode."
        DEFVAL         { off }
        ::= { tnDwdmCmnOtu1Odu1LinePortConfigEntry 15 }

    tnDwdmCmnLinePortOdu1Interworking OBJECT-TYPE
        SYNTAX         TruthValue
        MAX-ACCESS     read-create
        STATUS         current
        DESCRIPTION    "ODU1 interworking."
        DEFVAL         { false }
        ::= { tnDwdmCmnOtu1Odu1LinePortConfigEntry 16 }

--------------------------------------------------------------------------------
-- DWDM Common OTU1/ODU1 Client Port Config Table
--------------------------------------------------------------------------------
    tnDwdmCmnOtu1Odu1ClientPortConfigTable OBJECT-TYPE
        SYNTAX         SEQUENCE OF TnDwdmCmnOtu1Odu1ClientPortConfigEntry
        MAX-ACCESS     not-accessible
        STATUS         current
        DESCRIPTION    "Common attributes against DWDM client ports."
        ::= { tnOpticalPortConfig 95 }

    tnDwdmCmnOtu1Odu1ClientPortConfigEntry OBJECT-TYPE
        SYNTAX         TnDwdmCmnOtu1Odu1ClientPortConfigEntry
        MAX-ACCESS     not-accessible
        STATUS         current
        DESCRIPTION    ""
        INDEX { ifIndex }
        ::= { tnDwdmCmnOtu1Odu1ClientPortConfigTable 1 }

    TnDwdmCmnOtu1Odu1ClientPortConfigEntry ::=
        SEQUENCE {
            tnDwdmCmnClientPortOchOtu1FecMode           AluWdmFecMode,
            tnDwdmCmnClientPortOchOtu1Rate              AluWdmPortOchOtuRate,
            tnDwdmCmnClientPortOtu1TransmittedTti       OCTET STRING,
            tnDwdmCmnClientPortOtu1ExpectedTti          OCTET STRING,
            tnDwdmCmnClientPortOtu1TimConsequenceAction AluWdmDisabledEnabled,
            tnDwdmCmnClientPortOtu1TimDetectionMode     AluWdmTimDetectionMode,
            tnDwdmCmnClientPortOdu1TransmittedTti       OCTET STRING,
            tnDwdmCmnClientPortOdu1ExpectedTti          OCTET STRING,
            tnDwdmCmnClientPortOdu1TimDetectionMode     AluWdmTimDetectionMode
        }

    tnDwdmCmnClientPortOchOtu1FecMode OBJECT-TYPE
        SYNTAX         AluWdmFecMode
        MAX-ACCESS     read-create
        STATUS         current
        DESCRIPTION    "OTU1 FEC mode."
        DEFVAL         { g709Fec }
        ::= { tnDwdmCmnOtu1Odu1ClientPortConfigEntry 1 }

    tnDwdmCmnClientPortOchOtu1Rate OBJECT-TYPE
        SYNTAX         AluWdmPortOchOtuRate
        MAX-ACCESS     read-create
        STATUS         current
        DESCRIPTION    "OTU1 rate."
        DEFVAL         { otm10G709 }
        ::= { tnDwdmCmnOtu1Odu1ClientPortConfigEntry 2 }

    tnDwdmCmnClientPortOtu1TransmittedTti OBJECT-TYPE
        SYNTAX         OCTET STRING
        MAX-ACCESS     read-create
        STATUS         current
        DESCRIPTION    "OTU1 transmitted TTI."
        DEFVAL         { "" }
        ::= { tnDwdmCmnOtu1Odu1ClientPortConfigEntry 3 }

    tnDwdmCmnClientPortOtu1ExpectedTti OBJECT-TYPE
        SYNTAX         OCTET STRING
        MAX-ACCESS     read-create
        STATUS         current
        DESCRIPTION    "OTU1 expected TTI."
        DEFVAL         { "" }
        ::= { tnDwdmCmnOtu1Odu1ClientPortConfigEntry 4 }

    tnDwdmCmnClientPortOtu1TimConsequenceAction OBJECT-TYPE
        SYNTAX         AluWdmDisabledEnabled
        MAX-ACCESS     read-create
        STATUS         current
        DESCRIPTION    "OTU1 TIM consequence action."
        DEFVAL         { disabled }
        ::= { tnDwdmCmnOtu1Odu1ClientPortConfigEntry 5 }

    tnDwdmCmnClientPortOtu1TimDetectionMode OBJECT-TYPE
        SYNTAX         AluWdmTimDetectionMode
        MAX-ACCESS     read-create
        STATUS         current
        DESCRIPTION    "OTU1 TIM detection mode."
        DEFVAL         { off }
        ::= { tnDwdmCmnOtu1Odu1ClientPortConfigEntry 6 }

    tnDwdmCmnClientPortOdu1TransmittedTti OBJECT-TYPE
        SYNTAX         OCTET STRING
        MAX-ACCESS     read-create
        STATUS         current
        DESCRIPTION    "ODU1 transmitted TTI."
        DEFVAL         { "" }
        ::= { tnDwdmCmnOtu1Odu1ClientPortConfigEntry 7 }

    tnDwdmCmnClientPortOdu1ExpectedTti OBJECT-TYPE
        SYNTAX         OCTET STRING
        MAX-ACCESS     read-create
        STATUS         current
        DESCRIPTION    "ODU1 expected TTI."
        DEFVAL         { "" }
        ::= { tnDwdmCmnOtu1Odu1ClientPortConfigEntry 8 }

    tnDwdmCmnClientPortOdu1TimDetectionMode OBJECT-TYPE
        SYNTAX         AluWdmTimDetectionMode
        MAX-ACCESS     read-create
        STATUS         current
        DESCRIPTION    "ODU1 TIM detection mode."
        DEFVAL         { off }
        ::= { tnDwdmCmnOtu1Odu1ClientPortConfigEntry 9 }

--------------------------------------------------------------------------------
-- 43STX4 Optical Port Config Scalars
--------------------------------------------------------------------------------
    tn43stx4PortConfigAttributeTotal OBJECT-TYPE
        SYNTAX         Integer32
        MAX-ACCESS     read-only
        STATUS         current
        DESCRIPTION    ""
        ::= { tnOpticalPortConfig 96 }

--------------------------------------------------------------------------------
-- 43STX4 Optical Port Config Table
--------------------------------------------------------------------------------
    tn43stx4PortConfigTable OBJECT-TYPE
        SYNTAX         SEQUENCE OF Tn43stx4PortConfigEntry
        MAX-ACCESS     not-accessible
        STATUS         current
        DESCRIPTION    "The ports on a 43STX4 optical card."
        ::= { tnOpticalPortConfig 97 }

    tn43stx4PortConfigEntry OBJECT-TYPE
        SYNTAX         Tn43stx4PortConfigEntry
        MAX-ACCESS     not-accessible
        STATUS         current
        DESCRIPTION    ""
        INDEX { ifIndex }
        ::= { tn43stx4PortConfigTable 1 }

    Tn43stx4PortConfigEntry ::=
        SEQUENCE {
            tn43stx4PortConfigFunction INTEGER
        }

    tn43stx4PortConfigFunction OBJECT-TYPE
        SYNTAX         INTEGER {
                         network(1),
                         client(2)
                       }
        MAX-ACCESS     read-only
        STATUS         current
        DESCRIPTION    "Indicates the functional type of this 43STX4 port."
        ::= { tn43stx4PortConfigEntry 1 }

--------------------------------------------------------------------------------
-- DWDM Common OTU3/ODU3 Line Port Config Table
--------------------------------------------------------------------------------
    tnDwdmCmnOtu3Odu3LinePortConfigTable OBJECT-TYPE
        SYNTAX         SEQUENCE OF TnDwdmCmnOtu3Odu3LinePortConfigEntry
        MAX-ACCESS     not-accessible
        STATUS         current
        DESCRIPTION    "Common attributes against DWDM line ports."
        ::= { tnOpticalPortConfig 98 }

    tnDwdmCmnOtu3Odu3LinePortConfigEntry OBJECT-TYPE
        SYNTAX         TnDwdmCmnOtu3Odu3LinePortConfigEntry
        MAX-ACCESS     not-accessible
        STATUS         current
        DESCRIPTION    ""
        INDEX { ifIndex }
        ::= { tnDwdmCmnOtu3Odu3LinePortConfigTable 1 }

    TnDwdmCmnOtu3Odu3LinePortConfigEntry ::=
        SEQUENCE {
            tnDwdmCmnLinePortOchOtu3FecMode            AluWdmFecMode,
            tnDwdmCmnLinePortOtu3TransmittedTti        OCTET STRING,
            tnDwdmCmnLinePortOtu3ExpectedTti           OCTET STRING,
            tnDwdmCmnLinePortOtu3TimConsequenceAction  AluWdmDisabledEnabled,
            tnDwdmCmnLinePortOtu3TimDetectionMode      AluWdmTimDetectionMode,
            tnDwdmCmnLinePortOdu3PayloadType           Unsigned32,
            tnDwdmCmnLinePortOdu3PlmConsequenceAction  TruthValue,
            tnDwdmCmnLinePortOdu3TransmittedTti        OCTET STRING,
            tnDwdmCmnLinePortOdu3ExpectedTti           OCTET STRING,
            tnDwdmCmnLinePortOdu3TimConsequenceAction  AluWdmDisabledEnabled,
            tnDwdmCmnLinePortOdu3TimDetectionMode      AluWdmTimDetectionMode,
            tnDwdmCmnLinePortOdu3MappingMode           AluWdmMappingMode,
            tnDwdmCmnLinePortOchOtu3Rate               AluWdmPortOchOtuRate,
            tnDwdmCmnLinePortOdu3Interworking          TruthValue
        }

    tnDwdmCmnLinePortOchOtu3FecMode OBJECT-TYPE
        SYNTAX         AluWdmFecMode
        MAX-ACCESS     read-create
        STATUS         current
        DESCRIPTION    "OTU3 FEC mode.  Default is uFec for 43STA1P and
                        aFec for other supported cards."
        ::= { tnDwdmCmnOtu3Odu3LinePortConfigEntry 1 }

    tnDwdmCmnLinePortOtu3TransmittedTti OBJECT-TYPE
        SYNTAX         OCTET STRING
        MAX-ACCESS     read-create
        STATUS         current
        DESCRIPTION    "OTU3 transmitted TTI."
        DEFVAL         { "" }
        ::= { tnDwdmCmnOtu3Odu3LinePortConfigEntry 2 }

    tnDwdmCmnLinePortOtu3ExpectedTti OBJECT-TYPE
        SYNTAX         OCTET STRING
        MAX-ACCESS     read-create
        STATUS         current
        DESCRIPTION    "OTU3 expected TTI."
        DEFVAL         { "" }
        ::= { tnDwdmCmnOtu3Odu3LinePortConfigEntry 3 }

    tnDwdmCmnLinePortOtu3TimConsequenceAction OBJECT-TYPE
        SYNTAX         AluWdmDisabledEnabled
        MAX-ACCESS     read-create
        STATUS         current
        DESCRIPTION    "OTU3 TIM consequence action."
        DEFVAL         { disabled }
        ::= { tnDwdmCmnOtu3Odu3LinePortConfigEntry 4 }

    tnDwdmCmnLinePortOtu3TimDetectionMode OBJECT-TYPE
        SYNTAX         AluWdmTimDetectionMode
        MAX-ACCESS     read-create
        STATUS         current
        DESCRIPTION    "OTU3 TIM detection mode."
        DEFVAL         { off }
        ::= { tnDwdmCmnOtu3Odu3LinePortConfigEntry 5 }

    tnDwdmCmnLinePortOdu3PayloadType OBJECT-TYPE
        SYNTAX         Unsigned32
        MAX-ACCESS     read-create
        STATUS         current
        DESCRIPTION    "ODU3 payload type.

                        Current configurable range: 0 to 255."
        DEFVAL         { 32 }
        ::= { tnDwdmCmnOtu3Odu3LinePortConfigEntry 6 }

    tnDwdmCmnLinePortOdu3PlmConsequenceAction OBJECT-TYPE
        SYNTAX         TruthValue
        MAX-ACCESS     read-create
        STATUS         current
        DESCRIPTION    "PLM consequence action."
        DEFVAL         { false }
        ::= { tnDwdmCmnOtu3Odu3LinePortConfigEntry 7 }

    tnDwdmCmnLinePortOdu3TransmittedTti OBJECT-TYPE
        SYNTAX         OCTET STRING
        MAX-ACCESS     read-create
        STATUS         current
        DESCRIPTION    "ODU3 transmitted TTI."
        DEFVAL         { "" }
        ::= { tnDwdmCmnOtu3Odu3LinePortConfigEntry 8 }

    tnDwdmCmnLinePortOdu3ExpectedTti OBJECT-TYPE
        SYNTAX         OCTET STRING
        MAX-ACCESS     read-create
        STATUS         current
        DESCRIPTION    "ODU3 expected TTI."
        DEFVAL         { "" }
        ::= { tnDwdmCmnOtu3Odu3LinePortConfigEntry 9 }

    tnDwdmCmnLinePortOdu3TimConsequenceAction OBJECT-TYPE
        SYNTAX         AluWdmDisabledEnabled
        MAX-ACCESS     read-create
        STATUS         current
        DESCRIPTION    "ODU3 TIM consequence action."
        DEFVAL         { disabled }
        ::= { tnDwdmCmnOtu3Odu3LinePortConfigEntry 10 }

    tnDwdmCmnLinePortOdu3TimDetectionMode OBJECT-TYPE
        SYNTAX         AluWdmTimDetectionMode
        MAX-ACCESS     read-create
        STATUS         current
        DESCRIPTION    "ODU3 TIM detection mode."
        DEFVAL         { off }
        ::= { tnDwdmCmnOtu3Odu3LinePortConfigEntry 11 }

    tnDwdmCmnLinePortOdu3MappingMode OBJECT-TYPE
        SYNTAX         AluWdmMappingMode
        MAX-ACCESS     read-create
        STATUS         current
        DESCRIPTION    "ODU3 mapping mode."
        DEFVAL         { rsB }
        ::= { tnDwdmCmnOtu3Odu3LinePortConfigEntry 12 }

    tnDwdmCmnLinePortOchOtu3Rate OBJECT-TYPE
        SYNTAX         AluWdmPortOchOtuRate
        MAX-ACCESS     read-create
        STATUS         current
        DESCRIPTION    "OTU3 rate."
        DEFVAL         { otm43G018 }
        ::= { tnDwdmCmnOtu3Odu3LinePortConfigEntry 13 }

    tnDwdmCmnLinePortOdu3Interworking OBJECT-TYPE
        SYNTAX         TruthValue
        MAX-ACCESS     read-create
        STATUS         current
        DESCRIPTION    "ODU3 interworking Mode."
        DEFVAL         { false }
        ::= { tnDwdmCmnOtu3Odu3LinePortConfigEntry 14 }

--------------------------------------------------------------------------------
-- ALPFGK Optical Port Config Scalars
--------------------------------------------------------------------------------
    tnAlpfgkPortConfigAttributeTotal OBJECT-TYPE
        SYNTAX         Integer32
        MAX-ACCESS     read-only
        STATUS         current
        DESCRIPTION    ""
        ::= { tnOpticalPortConfig 99 }

--------------------------------------------------------------------------------
-- ALPFGK Optical Port Config Table
--------------------------------------------------------------------------------
    tnAlpfgkPortConfigTable OBJECT-TYPE
        SYNTAX         SEQUENCE OF TnAlpfgkPortConfigEntry
        MAX-ACCESS     not-accessible
        STATUS         current
        DESCRIPTION    "The ports on an ALPFGK optical card."
        ::= { tnOpticalPortConfig 100 }

    tnAlpfgkPortConfigEntry OBJECT-TYPE
        SYNTAX         TnAlpfgkPortConfigEntry
        MAX-ACCESS     not-accessible
        STATUS         current
        DESCRIPTION    ""
        INDEX { ifIndex }
        ::= { tnAlpfgkPortConfigTable 1 }

    TnAlpfgkPortConfigEntry ::=
        SEQUENCE {
            tnAlpfgkPortConfigFunction  INTEGER
        }

    tnAlpfgkPortConfigFunction OBJECT-TYPE
        SYNTAX         INTEGER {
                         line(1),
                         signal(2),
                         inv(3),
                         osc(4),
                         oscSfp(5)
                       }
        MAX-ACCESS     read-only
        STATUS         current
        DESCRIPTION    "Indicates the functional type of this ALPFGK port."
        ::= { tnAlpfgkPortConfigEntry 1 }

--------------------------------------------------------------------------------
-- 4DPA2 Optical Port Config Scalars
--------------------------------------------------------------------------------
    tn4dpa2PortConfigAttributeTotal OBJECT-TYPE
        SYNTAX         Integer32
        MAX-ACCESS     read-only
        STATUS         current
        DESCRIPTION    ""
        ::= { tnOpticalPortConfig 101 }

--------------------------------------------------------------------------------
-- 4DPA2 Optical Port Config Table
--------------------------------------------------------------------------------
    tn4dpa2PortConfigTable OBJECT-TYPE
        SYNTAX         SEQUENCE OF Tn4dpa2PortConfigEntry
        MAX-ACCESS     not-accessible
        STATUS         current
        DESCRIPTION    "The ports on a 4DPA2 optical card."
        ::= { tnOpticalPortConfig 102 }

    tn4dpa2PortConfigEntry OBJECT-TYPE
        SYNTAX         Tn4dpa2PortConfigEntry
        MAX-ACCESS     not-accessible
        STATUS         current
        DESCRIPTION    ""
        INDEX { ifIndex }
        ::= { tn4dpa2PortConfigTable 1 }

    Tn4dpa2PortConfigEntry ::=
        SEQUENCE {
            tn4dpa2PortConfigFunction INTEGER
        }

    tn4dpa2PortConfigFunction OBJECT-TYPE
        SYNTAX         INTEGER {
                         network(1),
                         client(2)
                       }
        MAX-ACCESS     read-only
        STATUS         current
        DESCRIPTION    "Indicates the functional type of this 4DPA2 port."
        ::= { tn4dpa2PortConfigEntry 1 }

--------------------------------------------------------------------------------
-- 43STA1P Optical Port Config Scalars
--------------------------------------------------------------------------------
    tn43sta1pPortConfigAttributeTotal OBJECT-TYPE
        SYNTAX         Integer32
        MAX-ACCESS     read-only
        STATUS         current
        DESCRIPTION    ""
        ::= { tnOpticalPortConfig 103 }

--------------------------------------------------------------------------------
-- 43STA1P Optical Port Config Table
--------------------------------------------------------------------------------
    tn43sta1pPortConfigTable OBJECT-TYPE
        SYNTAX         SEQUENCE OF Tn43sta1pPortConfigEntry
        MAX-ACCESS     not-accessible
        STATUS         current
        DESCRIPTION    "The ports on a 43STA1P optical card."
        ::= { tnOpticalPortConfig 104 }

    tn43sta1pPortConfigEntry OBJECT-TYPE
        SYNTAX         Tn43sta1pPortConfigEntry
        MAX-ACCESS     not-accessible
        STATUS         current
        DESCRIPTION    ""
        INDEX { ifIndex }
        ::= { tn43sta1pPortConfigTable 1 }

    Tn43sta1pPortConfigEntry ::=
        SEQUENCE {
            tn43sta1pPortConfigFunction INTEGER
        }

    tn43sta1pPortConfigFunction OBJECT-TYPE
        SYNTAX         INTEGER {
                         network(1),
                         client(2)
                       }
        MAX-ACCESS     read-only
        STATUS         current
        DESCRIPTION    "Indicates the functional type of this 43STA1P port."
        ::= { tn43sta1pPortConfigEntry 1 }

--------------------------------------------------------------------------------
-- 43STX4P Optical Port Config Scalars
--------------------------------------------------------------------------------
    tn43stx4pPortConfigAttributeTotal OBJECT-TYPE
        SYNTAX         Integer32
        MAX-ACCESS     read-only
        STATUS         current
        DESCRIPTION    ""
        ::= { tnOpticalPortConfig 105 }

--------------------------------------------------------------------------------
-- 43STX4P Optical Port Config Table
--------------------------------------------------------------------------------
    tn43stx4pPortConfigTable OBJECT-TYPE
        SYNTAX         SEQUENCE OF Tn43stx4pPortConfigEntry
        MAX-ACCESS     not-accessible
        STATUS         current
        DESCRIPTION    "The ports on a 43STX4P optical card."
        ::= { tnOpticalPortConfig 106 }

    tn43stx4pPortConfigEntry OBJECT-TYPE
        SYNTAX         Tn43stx4pPortConfigEntry
        MAX-ACCESS     not-accessible
        STATUS         current
        DESCRIPTION    ""
        INDEX { ifIndex }
        ::= { tn43stx4pPortConfigTable 1 }

    Tn43stx4pPortConfigEntry ::=
        SEQUENCE {
            tn43stx4pPortConfigFunction INTEGER
        }

    tn43stx4pPortConfigFunction OBJECT-TYPE
        SYNTAX         INTEGER {
                         network(1),
                         client(2)
                       }
        MAX-ACCESS     read-only
        STATUS         current
        DESCRIPTION    "Indicates the functional type of this 43STX4P port."
        ::= { tn43stx4pPortConfigEntry 1 }

--------------------------------------------------------------------------------
-- A2325A Optical Port Config Scalars
--------------------------------------------------------------------------------
    tnA2325aPortConfigAttributeTotal OBJECT-TYPE
        SYNTAX         Integer32
        MAX-ACCESS     read-only
        STATUS         current
        DESCRIPTION    ""
        ::= { tnOpticalPortConfig 109 }

--------------------------------------------------------------------------------
-- A2325A Optical Port Config Table
--------------------------------------------------------------------------------
    tnA2325aPortConfigTable OBJECT-TYPE
        SYNTAX         SEQUENCE OF TnA2325aPortConfigEntry
        MAX-ACCESS     not-accessible
        STATUS         current
        DESCRIPTION    "The ports on an A2325A optical card."
        ::= { tnOpticalPortConfig 110 }

    tnA2325aPortConfigEntry OBJECT-TYPE
        SYNTAX         TnA2325aPortConfigEntry
        MAX-ACCESS     not-accessible
        STATUS         current
        DESCRIPTION    ""
        INDEX { ifIndex }
        ::= { tnA2325aPortConfigTable 1 }

    TnA2325aPortConfigEntry ::=
        SEQUENCE {
            tnA2325aPortConfigFunction INTEGER
        }

    tnA2325aPortConfigFunction OBJECT-TYPE
        SYNTAX         INTEGER {
                         line(1),
                         signal(2),
                         dcm(3),
                         inv(4),
                         osc(5)
                       }
        MAX-ACCESS     read-only
        STATUS         current
        DESCRIPTION    "Indicates the functional type of this A2325A port."
        ::= { tnA2325aPortConfigEntry 1 }

--------------------------------------------------------------------------------
-- SFD40 Optical Port Config Scalars
--------------------------------------------------------------------------------
    tnSfd40PortConfigAttributeTotal OBJECT-TYPE
        SYNTAX         Integer32
        MAX-ACCESS     read-only
        STATUS         current
        DESCRIPTION    ""
        ::= { tnOpticalPortConfig 111 }

--------------------------------------------------------------------------------
-- SFD40 Optical Port Config Table
--------------------------------------------------------------------------------
    tnSfd40PortConfigTable OBJECT-TYPE
        SYNTAX         SEQUENCE OF TnSfd40PortConfigEntry
        MAX-ACCESS     not-accessible
        STATUS         current
        DESCRIPTION    "The ports on an SFD40 optical card."
        ::= { tnOpticalPortConfig 112 }

    tnSfd40PortConfigEntry OBJECT-TYPE
        SYNTAX         TnSfd40PortConfigEntry
        MAX-ACCESS     not-accessible
        STATUS         current
        DESCRIPTION    ""
        INDEX { ifIndex }
        ::= { tnSfd40PortConfigTable 1 }

    TnSfd40PortConfigEntry ::=
        SEQUENCE {
            tnSfd40PortConfigFunction INTEGER
        }

    tnSfd40PortConfigFunction OBJECT-TYPE
        SYNTAX         INTEGER {
                         channel(1),
                         mux(2)
                       }
        MAX-ACCESS     read-only
        STATUS         current
        DESCRIPTION    "."
        ::= { tnSfd40PortConfigEntry 1 }

--------------------------------------------------------------------------------
-- SFD40B Optical Port Config Scalars
--------------------------------------------------------------------------------
    tnSfd40bPortConfigAttributeTotal OBJECT-TYPE
        SYNTAX         Integer32
        MAX-ACCESS     read-only
        STATUS         current
        DESCRIPTION    ""
        ::= { tnOpticalPortConfig 113 }

--------------------------------------------------------------------------------
-- SFD40B Optical Port Config Table
--------------------------------------------------------------------------------
    tnSfd40bPortConfigTable OBJECT-TYPE
        SYNTAX         SEQUENCE OF TnSfd40bPortConfigEntry
        MAX-ACCESS     not-accessible
        STATUS         current
        DESCRIPTION    "The ports on an SFD40B optical card."
        ::= { tnOpticalPortConfig 114 }

    tnSfd40bPortConfigEntry OBJECT-TYPE
        SYNTAX         TnSfd40bPortConfigEntry
        MAX-ACCESS     not-accessible
        STATUS         current
        DESCRIPTION    ""
        INDEX { ifIndex }
        ::= { tnSfd40bPortConfigTable 1 }

    TnSfd40bPortConfigEntry ::=
        SEQUENCE {
            tnSfd40bPortConfigFunction INTEGER
        }

    tnSfd40bPortConfigFunction OBJECT-TYPE
        SYNTAX         INTEGER {
                         channel(1),
                         mux(2)
                       }
        MAX-ACCESS     read-only
        STATUS         current
        DESCRIPTION    "."
        ::= { tnSfd40bPortConfigEntry 1 }

--------------------------------------------------------------------------------
-- 11QPA4 Optical Port Config Scalars
--------------------------------------------------------------------------------
    tn11qpa4PortConfigAttributeTotal OBJECT-TYPE
        SYNTAX         Integer32
        MAX-ACCESS     read-only
        STATUS         current
        DESCRIPTION    ""
        ::= { tnOpticalPortConfig 115 }

--------------------------------------------------------------------------------
-- 11QPA4 Optical Port Config Table
--------------------------------------------------------------------------------
    tn11qpa4PortConfigTable OBJECT-TYPE
        SYNTAX         SEQUENCE OF Tn11qpa4PortConfigEntry
        MAX-ACCESS     not-accessible
        STATUS         current
        DESCRIPTION    "The ports on a 11QPA4 optical card."
        ::= { tnOpticalPortConfig 116 }

    tn11qpa4PortConfigEntry OBJECT-TYPE
        SYNTAX         Tn11qpa4PortConfigEntry
        MAX-ACCESS     not-accessible
        STATUS         current
        DESCRIPTION    ""
        INDEX { ifIndex }
        ::= { tn11qpa4PortConfigTable 1 }

    Tn11qpa4PortConfigEntry ::=
        SEQUENCE {
            tn11qpa4PortConfigFunction INTEGER
        }

    tn11qpa4PortConfigFunction OBJECT-TYPE
        SYNTAX         INTEGER {
                         network(1),
                         client(2),
                         evoa(3)
                       }
        MAX-ACCESS     read-only
        STATUS         current
        DESCRIPTION    "Indicates the functional type of this 11QPA4 port."
        ::= { tn11qpa4PortConfigEntry 1 }

    
--------------------------------------------------------------------------------
-- 112SCX10 Optical Port Config Scalars
--------------------------------------------------------------------------------
    tn112scx10PortConfigAttributeTotal OBJECT-TYPE
        SYNTAX         Integer32
        MAX-ACCESS     read-only
        STATUS         current
        DESCRIPTION    ""
        ::= { tnOpticalPortConfig 117 }

--------------------------------------------------------------------------------
-- 112SCX10 Optical Port Config Table
--------------------------------------------------------------------------------
    tn112scx10PortConfigTable OBJECT-TYPE
        SYNTAX         SEQUENCE OF Tn112scx10PortConfigEntry
        MAX-ACCESS     not-accessible
        STATUS         current
        DESCRIPTION    "The ports on a 112SCX10 optical card."
        ::= { tnOpticalPortConfig 118 }

    tn112scx10PortConfigEntry OBJECT-TYPE
        SYNTAX         Tn112scx10PortConfigEntry
        MAX-ACCESS     not-accessible
        STATUS         current
        DESCRIPTION    ""
        INDEX { ifIndex }
        ::= { tn112scx10PortConfigTable 1 }

    Tn112scx10PortConfigEntry ::=
        SEQUENCE {
            tn112scx10PortConfigFunction INTEGER
        }

    tn112scx10PortConfigFunction OBJECT-TYPE
        SYNTAX         INTEGER {
                         network(1),
                         client(2)
                       }
        MAX-ACCESS     read-only
        STATUS         current
        DESCRIPTION    "Indicates the functional type of this 112SCX10 port."
        ::= { tn112scx10PortConfigEntry 1 }

--------------------------------------------------------------------------------
-- 112SCA1 Optical Port Config Scalars
--------------------------------------------------------------------------------
    tn112sca1PortConfigAttributeTotal OBJECT-TYPE
        SYNTAX         Integer32
        MAX-ACCESS     read-only
        STATUS         current
        DESCRIPTION    ""
        ::= { tnOpticalPortConfig 119 }

--------------------------------------------------------------------------------
-- 112SCA1 Optical Port Config Table
--------------------------------------------------------------------------------
    tn112sca1PortConfigTable OBJECT-TYPE
        SYNTAX         SEQUENCE OF Tn112sca1PortConfigEntry
        MAX-ACCESS     not-accessible
        STATUS         current
        DESCRIPTION    "The ports on a 112SCA1 optical card."
        ::= { tnOpticalPortConfig 120 }

    tn112sca1PortConfigEntry OBJECT-TYPE
        SYNTAX         Tn112sca1PortConfigEntry
        MAX-ACCESS     not-accessible
        STATUS         current
        DESCRIPTION    ""
        INDEX { ifIndex }
        ::= { tn112sca1PortConfigTable 1 }

    Tn112sca1PortConfigEntry ::=
        SEQUENCE {
            tn112sca1PortConfigFunction INTEGER
        }

    tn112sca1PortConfigFunction OBJECT-TYPE
        SYNTAX         INTEGER {
                         network(1),
                         client(2)
                       }
        MAX-ACCESS     read-only
        STATUS         current
        DESCRIPTION    "Indicates the functional type of this 112SCA1 port."
        ::= { tn112sca1PortConfigEntry 1 }

--------------------------------------------------------------------------------
-- DWDM Common OTU4/ODU4 Line Port Config Table
--------------------------------------------------------------------------------
    tnDwdmCmnOtu4Odu4LinePortConfigTable OBJECT-TYPE
        SYNTAX         SEQUENCE OF TnDwdmCmnOtu4Odu4LinePortConfigEntry
        MAX-ACCESS     not-accessible
        STATUS         current
        DESCRIPTION    "Common attributes against DWDM line ports."
        ::= { tnOpticalPortConfig 121 }

    tnDwdmCmnOtu4Odu4LinePortConfigEntry OBJECT-TYPE
        SYNTAX         TnDwdmCmnOtu4Odu4LinePortConfigEntry
        MAX-ACCESS     not-accessible
        STATUS         current
        DESCRIPTION    ""
        INDEX { ifIndex }
        ::= { tnDwdmCmnOtu4Odu4LinePortConfigTable 1 }

    TnDwdmCmnOtu4Odu4LinePortConfigEntry ::=
        SEQUENCE {
            tnDwdmCmnLinePortOchOtu4FecMode            AluWdmFecMode,
            tnDwdmCmnLinePortOchOtu4Rate               AluWdmPortOchOtuRate,
            tnDwdmCmnLinePortOtu4TransmittedTti        OCTET STRING,
            tnDwdmCmnLinePortOtu4ExpectedTti           OCTET STRING,
            tnDwdmCmnLinePortOtu4TimConsequenceAction  AluWdmDisabledEnabled,
            tnDwdmCmnLinePortOtu4TimDetectionMode      AluWdmTimDetectionMode,
            tnDwdmCmnLinePortOdu4PayloadType           Unsigned32,
            tnDwdmCmnLinePortOdu4PlmConsequenceAction  TruthValue,
            tnDwdmCmnLinePortOdu4TransmittedTti        OCTET STRING,
            tnDwdmCmnLinePortOdu4ExpectedTti           OCTET STRING,
            tnDwdmCmnLinePortOdu4TimConsequenceAction  AluWdmDisabledEnabled,
            tnDwdmCmnLinePortOdu4TimDetectionMode      AluWdmTimDetectionMode,
            tnDwdmCmnLinePortOtu4RegenResponse         INTEGER,
            tnDwdmCmnLinePortOdu4Interworking          TruthValue,
            tnDwdmCmnLinePortOtu4holdofftimer          AluWdmDisabledEnabled,  -- deprecated
            tnDwdmCmnLinePortOdu4112GInterworking      TruthValue,
            tnDwdmCmnLinePortOdu4DMConfigCMEPMode      INTEGER,
            tnDwdmCmnLinePortOdu4DMConfigEnable        INTEGER,
            tnDwdmCmnLinePortOdu4CndRes                INTEGER,
            tnDwdmCmnLinePortOdu4Encoding              INTEGER
        }

    tnDwdmCmnLinePortOchOtu4FecMode OBJECT-TYPE
        SYNTAX         AluWdmFecMode
        MAX-ACCESS     read-create
        STATUS         current
        DESCRIPTION    "OTU4 FEC mode.  Default is sdFec for 130SCX10,
                        130SNX10, 130SCA1, 130SCUP, 130SCUPB, and 130SCUPC;
                        and aFec for other cards."
        ::= { tnDwdmCmnOtu4Odu4LinePortConfigEntry 1 }

    tnDwdmCmnLinePortOchOtu4Rate OBJECT-TYPE
        SYNTAX         AluWdmPortOchOtuRate
        MAX-ACCESS     read-create
        STATUS         current
        DESCRIPTION    "OTU4 rate."
        DEFVAL         { otm111G810 }
        ::= { tnDwdmCmnOtu4Odu4LinePortConfigEntry 2 }

    tnDwdmCmnLinePortOtu4TransmittedTti OBJECT-TYPE
        SYNTAX         OCTET STRING
        MAX-ACCESS     read-create
        STATUS         current
        DESCRIPTION    "OTU4 transmitted TTI."
        DEFVAL         { "" }
        ::= { tnDwdmCmnOtu4Odu4LinePortConfigEntry 3 }

    tnDwdmCmnLinePortOtu4ExpectedTti OBJECT-TYPE
        SYNTAX         OCTET STRING
        MAX-ACCESS     read-create
        STATUS         current
        DESCRIPTION    "OTU4 expected TTI."
        DEFVAL         { "" }
        ::= { tnDwdmCmnOtu4Odu4LinePortConfigEntry 4 }

    tnDwdmCmnLinePortOtu4TimConsequenceAction OBJECT-TYPE
        SYNTAX         AluWdmDisabledEnabled
        MAX-ACCESS     read-create
        STATUS         current
        DESCRIPTION    "OTU4 TIM consequence action."
        DEFVAL         { disabled }
        ::= { tnDwdmCmnOtu4Odu4LinePortConfigEntry 5 }

    tnDwdmCmnLinePortOtu4TimDetectionMode OBJECT-TYPE
        SYNTAX         AluWdmTimDetectionMode
        MAX-ACCESS     read-create
        STATUS         current
        DESCRIPTION    "OTU4 TIM detection mode."
        DEFVAL         { off }
        ::= { tnDwdmCmnOtu4Odu4LinePortConfigEntry 6 }

    tnDwdmCmnLinePortOdu4PayloadType OBJECT-TYPE
        SYNTAX         Unsigned32
        MAX-ACCESS     read-create
        STATUS         current
        DESCRIPTION    "ODU4 payload type.

                        Current configurable range: 0 to 255."
        ::= { tnDwdmCmnOtu4Odu4LinePortConfigEntry 7 }

    tnDwdmCmnLinePortOdu4PlmConsequenceAction OBJECT-TYPE
        SYNTAX         TruthValue
        MAX-ACCESS     read-create
        STATUS         current
        DESCRIPTION    "PLM consequence action."
        DEFVAL         { false }
        ::= { tnDwdmCmnOtu4Odu4LinePortConfigEntry 8 }

    tnDwdmCmnLinePortOdu4TransmittedTti OBJECT-TYPE
        SYNTAX         OCTET STRING
        MAX-ACCESS     read-create
        STATUS         current
        DESCRIPTION    "ODU4 transmitted TTI."
        DEFVAL         { "" }
        ::= { tnDwdmCmnOtu4Odu4LinePortConfigEntry 9 }

    tnDwdmCmnLinePortOdu4ExpectedTti OBJECT-TYPE
        SYNTAX         OCTET STRING
        MAX-ACCESS     read-create
        STATUS         current
        DESCRIPTION    "ODU4 expected TTI."
        DEFVAL         { "" }
        ::= { tnDwdmCmnOtu4Odu4LinePortConfigEntry 10 }

    tnDwdmCmnLinePortOdu4TimConsequenceAction OBJECT-TYPE
        SYNTAX         AluWdmDisabledEnabled
        MAX-ACCESS     read-create
        STATUS         current
        DESCRIPTION    "ODU4 TIM consequence action."
        DEFVAL         { disabled }
        ::= { tnDwdmCmnOtu4Odu4LinePortConfigEntry 11 }

    tnDwdmCmnLinePortOdu4TimDetectionMode OBJECT-TYPE
        SYNTAX         AluWdmTimDetectionMode
        MAX-ACCESS     read-create
        STATUS         current
        DESCRIPTION    "ODU4 TIM detection mode."
        DEFVAL         { off }
        ::= { tnDwdmCmnOtu4Odu4LinePortConfigEntry 12 }

    tnDwdmCmnLinePortOtu4RegenResponse OBJECT-TYPE
        SYNTAX         INTEGER {
                         laserOn(1),
                         laserOff(2)
                       }
        MAX-ACCESS     read-create
        STATUS         current
        DESCRIPTION    "The regen response mode."
        DEFVAL         { laserOn }
        ::= { tnDwdmCmnOtu4Odu4LinePortConfigEntry 13 }

    tnDwdmCmnLinePortOdu4Interworking OBJECT-TYPE
        SYNTAX         TruthValue
        MAX-ACCESS     read-create
        STATUS         current
        DESCRIPTION    "ODU4 interworking mode."
        DEFVAL         { false }
        ::= { tnDwdmCmnOtu4Odu4LinePortConfigEntry 14 }

    tnDwdmCmnLinePortOtu4holdofftimer OBJECT-TYPE
        SYNTAX         AluWdmDisabledEnabled
        MAX-ACCESS     read-create
        STATUS         deprecated
        DESCRIPTION    "Line port consequent action (whether it's AIS
                        insertion or laser off) must be delayed by a
                        hold-off timer."
        DEFVAL         { disabled }
        ::= { tnDwdmCmnOtu4Odu4LinePortConfigEntry 15 }

    tnDwdmCmnLinePortOdu4112GInterworking OBJECT-TYPE
        SYNTAX         TruthValue
        MAX-ACCESS     read-create
        STATUS         current
        DESCRIPTION    "ODU4 112G card interworking mode."
        DEFVAL         { false }
        ::= { tnDwdmCmnOtu4Odu4LinePortConfigEntry 16 }

    tnDwdmCmnLinePortOdu4DMConfigCMEPMode OBJECT-TYPE
        SYNTAX         INTEGER {
                         bypass(1),
                         source(2),
                         destination(3)
                       }
        MAX-ACCESS     read-create
        STATUS         current
        DESCRIPTION    "Connection Monitoring End Point Mode defined for
                        delay measurement on the specified entity."
        DEFVAL         { bypass }
        ::= { tnDwdmCmnOtu4Odu4LinePortConfigEntry 17 }

    tnDwdmCmnLinePortOdu4DMConfigEnable OBJECT-TYPE
        SYNTAX         INTEGER {
                         enable(1),
                         disable(2)
                       }
        MAX-ACCESS     read-create
        STATUS         current
        DESCRIPTION    "This attribute is used to enable or disable the
                        DM function."
        DEFVAL         { disable }
        ::= { tnDwdmCmnOtu4Odu4LinePortConfigEntry 18 }
    
    tnDwdmCmnLinePortOdu4CndRes OBJECT-TYPE
        SYNTAX         INTEGER {
                         c1d(1),
                         c8d(2)
                       }
        MAX-ACCESS     read-create
        STATUS         current
        DESCRIPTION    ""
        DEFVAL         { c1d }
        ::= { tnDwdmCmnOtu4Odu4LinePortConfigEntry 19 }

    tnDwdmCmnLinePortOdu4Encoding OBJECT-TYPE
        SYNTAX         INTEGER {
                        nrz(0),
                        pdpsk(1),
                        dpsk(2),
                        bpsk(3),   
                        qpsk(4),
                        qpskEnhOsnr(5),  
                        nrzCFP1(6), 
                        icohpmqpsk(7), 
                        duobinary(8),
                        qpskhperf2(9), 
                        qam16(10), 
                        qam8(11),
                        spqpsk(12),
                        qam64(13),
                        unassigned(9997), 
                        alien(9998),
                        unknown(9999) 
             }
        MAX-ACCESS     read-create
        STATUS         current
        DESCRIPTION    ""
        ::= { tnDwdmCmnOtu4Odu4LinePortConfigEntry 20 }

--------------------------------------------------------------------------------
-- DWDM Common OTU4/ODU4 Client Port Config Table
--------------------------------------------------------------------------------
    tnDwdmCmnOtu4Odu4ClientPortConfigTable OBJECT-TYPE
        SYNTAX         SEQUENCE OF TnDwdmCmnOtu4Odu4ClientPortConfigEntry
        MAX-ACCESS     not-accessible
        STATUS         current
        DESCRIPTION    "Common attributes against DWDM client ports."
        ::= { tnOpticalPortConfig 122 }

    tnDwdmCmnOtu4Odu4ClientPortConfigEntry OBJECT-TYPE
        SYNTAX         TnDwdmCmnOtu4Odu4ClientPortConfigEntry
        MAX-ACCESS     not-accessible
        STATUS         current
        DESCRIPTION    ""
        INDEX { ifIndex }
        ::= { tnDwdmCmnOtu4Odu4ClientPortConfigTable 1 }

    TnDwdmCmnOtu4Odu4ClientPortConfigEntry ::=
        SEQUENCE {
            tnDwdmCmnClientPortOchOtu4FecMode            AluWdmFecMode,
            tnDwdmCmnClientPortOchOtu4Rate               AluWdmPortOchOtuRate,
            tnDwdmCmnClientPortOtu4TransmittedTti        OCTET STRING,
            tnDwdmCmnClientPortOtu4ExpectedTti           OCTET STRING,
            tnDwdmCmnClientPortOtu4TimConsequenceAction  AluWdmDisabledEnabled,
            tnDwdmCmnClientPortOtu4TimDetectionMode      AluWdmTimDetectionMode,
            tnDwdmCmnClientPortOdu4TransmittedTti        OCTET STRING,
            tnDwdmCmnClientPortOdu4ExpectedTti           OCTET STRING,
            tnDwdmCmnClientPortOdu4TimDetectionMode      AluWdmTimDetectionMode
--          obsolete
--            tnDwdmCmnClientPortOdu4IncomingTti           OCTET STRING,
--            tnDwdmCmnClientPortOdu4TtiStatus             AluWdmTtiStatus
    }

    tnDwdmCmnClientPortOchOtu4FecMode OBJECT-TYPE
        SYNTAX         AluWdmFecMode
        MAX-ACCESS     read-create
        STATUS         current
        DESCRIPTION    "OTU4 FEC mode."
        DEFVAL         { g709Fec }
        ::= { tnDwdmCmnOtu4Odu4ClientPortConfigEntry 1 }

    tnDwdmCmnClientPortOchOtu4Rate OBJECT-TYPE
        SYNTAX         AluWdmPortOchOtuRate
        MAX-ACCESS     read-create
        STATUS         current
        DESCRIPTION    "OTU4 rate."
        DEFVAL         { otm111G810 }
        ::= { tnDwdmCmnOtu4Odu4ClientPortConfigEntry 2 }

    tnDwdmCmnClientPortOtu4TransmittedTti OBJECT-TYPE
        SYNTAX         OCTET STRING
        MAX-ACCESS     read-create
        STATUS         current
        DESCRIPTION    "OTU4 transmitted TTI."
        DEFVAL         { "" }
        ::= { tnDwdmCmnOtu4Odu4ClientPortConfigEntry 3 }

    tnDwdmCmnClientPortOtu4ExpectedTti OBJECT-TYPE
        SYNTAX         OCTET STRING
        MAX-ACCESS     read-create
        STATUS         current
        DESCRIPTION    "OTU4 expected TTI."
        DEFVAL         { "" }
        ::= { tnDwdmCmnOtu4Odu4ClientPortConfigEntry 4 }

    tnDwdmCmnClientPortOtu4TimConsequenceAction OBJECT-TYPE
        SYNTAX         AluWdmDisabledEnabled
        MAX-ACCESS     read-create
        STATUS         current
        DESCRIPTION    "OTU4 TIM consequence action."
        DEFVAL         { disabled }
        ::= { tnDwdmCmnOtu4Odu4ClientPortConfigEntry 5 }

    tnDwdmCmnClientPortOtu4TimDetectionMode OBJECT-TYPE
        SYNTAX         AluWdmTimDetectionMode
        MAX-ACCESS     read-create
        STATUS         current
        DESCRIPTION    "OTU4 TIM detection mode."
        DEFVAL         { off }
        ::= { tnDwdmCmnOtu4Odu4ClientPortConfigEntry 6 }

    tnDwdmCmnClientPortOdu4TransmittedTti OBJECT-TYPE
        SYNTAX         OCTET STRING
        MAX-ACCESS     read-create
        STATUS         current
        DESCRIPTION    "ODU4 transmitted TTI."
        DEFVAL         { "" }
        ::= { tnDwdmCmnOtu4Odu4ClientPortConfigEntry 7 }

    tnDwdmCmnClientPortOdu4ExpectedTti OBJECT-TYPE
        SYNTAX         OCTET STRING
        MAX-ACCESS     read-create
        STATUS         current
        DESCRIPTION    "ODU4 expected TTI."
        DEFVAL         { "" }
        ::= { tnDwdmCmnOtu4Odu4ClientPortConfigEntry 8 }

    tnDwdmCmnClientPortOdu4TimDetectionMode OBJECT-TYPE
        SYNTAX         AluWdmTimDetectionMode
        MAX-ACCESS     read-create
        STATUS         current
        DESCRIPTION    "ODU4 TIM detection mode."
        DEFVAL         { off }
        ::= { tnDwdmCmnOtu4Odu4ClientPortConfigEntry 9 }

--    obsolete
--    tnDwdmCmnClientPortOdu4IncomingTti OBJECT-TYPE ::= { tnDwdmCmnOtu4Odu4ClientPortConfigEntry 10 }
--    tnDwdmCmnClientPortOdu4TtiStatus OBJECT-TYPE ::= { tnDwdmCmnOtu4Odu4ClientPortConfigEntry 11 }

--------------------------------------------------------------------------------
-- RSMON Egress Port Config Table
--------------------------------------------------------------------------------
    tnRsmonEgrPortConfigTable OBJECT-TYPE
        SYNTAX         SEQUENCE OF TnRsmonEgrPortConfigEntry
        MAX-ACCESS     not-accessible
        STATUS         current
        DESCRIPTION    "Common attributes against RSMON Egress supported ports."
        ::= { tnOpticalPortConfig 123 }

    tnRsmonEgrPortConfigEntry OBJECT-TYPE
        SYNTAX         TnRsmonEgrPortConfigEntry
        MAX-ACCESS     not-accessible
        STATUS         current
        DESCRIPTION    ""
        INDEX { ifIndex }
        ::= { tnRsmonEgrPortConfigTable 1 }

    TnRsmonEgrPortConfigEntry ::=
        SEQUENCE {
            tnRsmonEgrPortTimod                 INTEGER,
            tnRsmonEgrPortSigMode               INTEGER,
            tnRsmonEgrPortTransmittedTti        OCTET STRING,
            tnRsmonEgrPortExpectedTti           OCTET STRING,
            tnRsmonEgrPortTimDetection          TruthValue,
            tnRsmonEgrPortTimConsequenceAction  AluWdmDisabledEnabled
        }

    tnRsmonEgrPortTimod OBJECT-TYPE
        SYNTAX         INTEGER {
                         notApplicable(1),
                         specific16Byte(2),
                         nonSpecificSingleByte(3),
                         specificSingleByte(4),
                         string64(5)
                       }
        MAX-ACCESS     read-create
        STATUS         current
        DESCRIPTION    "RSMON TIMOD."
        DEFVAL         { specific16Byte }
        ::= { tnRsmonEgrPortConfigEntry 1 }

    tnRsmonEgrPortSigMode OBJECT-TYPE
        SYNTAX         INTEGER {
                         transparent(1),
                         terminated(2)
                       }
        MAX-ACCESS     read-create
        STATUS         current
        DESCRIPTION    "RSMON signal mode."
        DEFVAL         { transparent }
        ::= { tnRsmonEgrPortConfigEntry 2 }

    tnRsmonEgrPortTransmittedTti OBJECT-TYPE
        SYNTAX         OCTET STRING
        MAX-ACCESS     read-create
        STATUS         current
        DESCRIPTION    "RSMON transmitted TTI."
        DEFVAL         { "" }
        ::= { tnRsmonEgrPortConfigEntry 3 }

    tnRsmonEgrPortExpectedTti OBJECT-TYPE
        SYNTAX         OCTET STRING
        MAX-ACCESS     read-create
        STATUS         current
        DESCRIPTION    "RSMON expected TTI."
        DEFVAL         { "" }
        ::= { tnRsmonEgrPortConfigEntry 4 }

    tnRsmonEgrPortTimDetection OBJECT-TYPE
        SYNTAX         TruthValue
        MAX-ACCESS     read-create
        STATUS         current
        DESCRIPTION    "RSMON TIM detection."
        DEFVAL         { false }
        ::= { tnRsmonEgrPortConfigEntry 5 }

    tnRsmonEgrPortTimConsequenceAction OBJECT-TYPE
        SYNTAX         AluWdmDisabledEnabled
        MAX-ACCESS     read-create
        STATUS         current
        DESCRIPTION    "RSMON TIM consequence action."
        DEFVAL         { disabled }
        ::= { tnRsmonEgrPortConfigEntry 6 }

--------------------------------------------------------------------------------
-- DWDM Common Rate Port Config Table
--------------------------------------------------------------------------------
    tnDwdmCbrArPortConfigTable OBJECT-TYPE
        SYNTAX         SEQUENCE OF TnDwdmCbrArPortConfigEntry
        MAX-ACCESS     not-accessible
        STATUS         current
        DESCRIPTION    "Common attributes for client port signal entities."
        ::= { tnOpticalPortConfig 124 }

    tnDwdmCbrArPortConfigEntry OBJECT-TYPE
        SYNTAX         TnDwdmCbrArPortConfigEntry
        MAX-ACCESS     not-accessible
        STATUS         current
        DESCRIPTION    ""
        INDEX { ifIndex }
        ::= { tnDwdmCbrArPortConfigTable 1 }

    TnDwdmCbrArPortConfigEntry ::=
        SEQUENCE {
            tnDwdmCbrArPortHdsdiRate  INTEGER
        }

    tnDwdmCbrArPortHdsdiRate OBJECT-TYPE
        SYNTAX         INTEGER {
                         hdSdi-1-485(1),
                         hdSdi-1-485-1-001(2)
                       }
        MAX-ACCESS     read-create
        STATUS         current
        DESCRIPTION    "HDSDI rate, which is compatible with existing NTSC
                        systems."
        DEFVAL         { hdSdi-1-485-1-001 }
        ::= { tnDwdmCbrArPortConfigEntry 1 }

--------------------------------------------------------------------------------
-- ALPFGT Optical Port Config Scalars
--------------------------------------------------------------------------------
    tnAlpfgtPortConfigAttributeTotal OBJECT-TYPE
        SYNTAX         Integer32
        MAX-ACCESS     read-only
        STATUS         current
        DESCRIPTION    ""
        ::= { tnOpticalPortConfig 125 }

--------------------------------------------------------------------------------
-- ALPFGT Optical Port Config Table
--------------------------------------------------------------------------------
    tnAlpfgtPortConfigTable OBJECT-TYPE
        SYNTAX         SEQUENCE OF TnAlpfgtPortConfigEntry
        MAX-ACCESS     not-accessible
        STATUS         current
        DESCRIPTION    "The ports on an ALPFGT optical card."
        ::= { tnOpticalPortConfig 126 }

    tnAlpfgtPortConfigEntry OBJECT-TYPE
        SYNTAX         TnAlpfgtPortConfigEntry
        MAX-ACCESS     not-accessible
        STATUS         current
        DESCRIPTION    ""
        INDEX { ifIndex }
        ::= { tnAlpfgtPortConfigTable 1 }

    TnAlpfgtPortConfigEntry ::=
        SEQUENCE {
            tnAlpfgtPortConfigFunction  INTEGER
        }

    tnAlpfgtPortConfigFunction OBJECT-TYPE
        SYNTAX         INTEGER {
                         line(1),
                         signal(2),
                         inv(3),
                         osc(4),
                         oscSfp(5)
                       }
        MAX-ACCESS     read-only
        STATUS         current
        DESCRIPTION    "Indicates the functional type of this ALPFGT port."
        ::= { tnAlpfgtPortConfigEntry 1 }

--------------------------------------------------------------------------------
-- OSCT Optical Port Config Scalars
--------------------------------------------------------------------------------
    tnOsctPortConfigAttributeTotal OBJECT-TYPE
        SYNTAX         Integer32
        MAX-ACCESS     read-only
        STATUS         current
        DESCRIPTION    ""
        ::= { tnOpticalPortConfig 127 }

--------------------------------------------------------------------------------
-- OSCT Optical Port Config Table
--------------------------------------------------------------------------------
    tnOsctPortConfigTable OBJECT-TYPE
        SYNTAX         SEQUENCE OF TnOsctPortConfigEntry
        MAX-ACCESS     not-accessible
        STATUS         current
        DESCRIPTION    "The ports on an OSCT optical card."
        ::= { tnOpticalPortConfig 128 }

    tnOsctPortConfigEntry OBJECT-TYPE
        SYNTAX         TnOsctPortConfigEntry
        MAX-ACCESS     not-accessible
        STATUS         current
        DESCRIPTION    ""
        INDEX { ifIndex }
        ::= { tnOsctPortConfigTable 1 }

    TnOsctPortConfigEntry ::=
        SEQUENCE {
            tnOsctPortConfigFunction  INTEGER
        }

    tnOsctPortConfigFunction OBJECT-TYPE
        SYNTAX         INTEGER {
                         signal(1),
                         line(2),
                         inv(3),
                         osc(4),
                         oscSfp(5)
                       }
        MAX-ACCESS     read-only
        STATUS         current
        DESCRIPTION    "Indicates the functional type of this OSCT port."
        ::= { tnOsctPortConfigEntry 1 }

--------------------------------------------------------------------------------
-- WTOCM Optical Port Config Scalars
--------------------------------------------------------------------------------
    tnWtocmPortConfigAttributeTotal OBJECT-TYPE
        SYNTAX         Integer32
        MAX-ACCESS     read-only
        STATUS         current
        DESCRIPTION    ""
        ::= { tnOpticalPortConfig 129 }

--------------------------------------------------------------------------------
-- WTOCM Optical Port Config Table
--------------------------------------------------------------------------------
    tnWtocmPortConfigTable OBJECT-TYPE
        SYNTAX         SEQUENCE OF TnWtocmPortConfigEntry
        MAX-ACCESS     not-accessible
        STATUS         current
        DESCRIPTION    "The ports on a WTOCM optical card."
        ::= { tnOpticalPortConfig 130 }

    tnWtocmPortConfigEntry OBJECT-TYPE
        SYNTAX         TnWtocmPortConfigEntry
        MAX-ACCESS     not-accessible
        STATUS         current
        DESCRIPTION    ""
        INDEX { ifIndex }
        ::= { tnWtocmPortConfigTable 1 }

    TnWtocmPortConfigEntry ::=
        SEQUENCE {
            tnWtocmPortConfigFunction  INTEGER
        }

    tnWtocmPortConfigFunction OBJECT-TYPE
        SYNTAX         INTEGER {
                         detect(1)
                       }
        MAX-ACCESS     read-only
        STATUS         current
        DESCRIPTION    "Indicates the functional type of this WTOCM port."
        ::= { tnWtocmPortConfigEntry 1 }

--------------------------------------------------------------------------------
-- WR2-88 Optical Port Config Scalars
--------------------------------------------------------------------------------
    tnWr2c88PortConfigAttributeTotal OBJECT-TYPE
        SYNTAX         Integer32
        MAX-ACCESS     read-only
        STATUS         current
        DESCRIPTION    ""
        ::= { tnOpticalPortConfig 131 }

--------------------------------------------------------------------------------
-- WR2-88 Optical Port Config Table
--------------------------------------------------------------------------------
    tnWr2c88PortConfigTable OBJECT-TYPE
        SYNTAX         SEQUENCE OF TnWr2c88PortConfigEntry
        MAX-ACCESS     not-accessible
        STATUS         current
        DESCRIPTION    "The ports on a WR2-88 optical card."
        ::= { tnOpticalPortConfig 132 }

    tnWr2c88PortConfigEntry OBJECT-TYPE
        SYNTAX         TnWr2c88PortConfigEntry
        MAX-ACCESS     not-accessible
        STATUS         current
        DESCRIPTION    ""
        INDEX { ifIndex }
        ::= { tnWr2c88PortConfigTable 1 }

    TnWr2c88PortConfigEntry ::=
        SEQUENCE {
            tnWr2c88PortConfigFunction  INTEGER
--            obsolete
--            tnWr2c88PortBlockerAging    Unsigned32
        }

    tnWr2c88PortConfigFunction OBJECT-TYPE
        SYNTAX         INTEGER {
                         signal(1),
                         thru(2),
                         dropOut(3),
                         addIn(4),
                         inv(5)
                       }
        MAX-ACCESS     read-only
        STATUS         current
        DESCRIPTION    "Indicates the functional type of this WR2-88 port."
        ::= { tnWr2c88PortConfigEntry 1 }

--    obsolete
--    tnWr2c88PortBlockerAging OBJECT-TYPE ::= { tnWr2c88PortConfigEntry 2 }

--------------------------------------------------------------------------------
-- AM2017B Optical Port Config Scalars
--------------------------------------------------------------------------------
    tnAm2017bPortConfigAttributeTotal OBJECT-TYPE
        SYNTAX         Integer32
        MAX-ACCESS     read-only
        STATUS         current
        DESCRIPTION    ""
        ::= { tnOpticalPortConfig 133 }

--------------------------------------------------------------------------------
-- AM2017B Optical Port Config Table
--------------------------------------------------------------------------------
    tnAm2017bPortConfigTable OBJECT-TYPE
        SYNTAX         SEQUENCE OF TnAm2017bPortConfigEntry
        MAX-ACCESS     not-accessible
        STATUS         current
        DESCRIPTION    "The ports on an AM2017B optical card."
        ::= { tnOpticalPortConfig 134 }

    tnAm2017bPortConfigEntry OBJECT-TYPE
        SYNTAX         TnAm2017bPortConfigEntry
        MAX-ACCESS     not-accessible
        STATUS         current
        DESCRIPTION    ""
        INDEX { ifIndex }
        ::= { tnAm2017bPortConfigTable 1 }

    TnAm2017bPortConfigEntry ::=
        SEQUENCE {
            tnAm2017bPortConfigFunction INTEGER
        }

    tnAm2017bPortConfigFunction OBJECT-TYPE
        SYNTAX         INTEGER {
                         line(1),
                         signal(2),
                         dcm(3),
                         inv(4),
                         osc(5)
                       }
        MAX-ACCESS     read-only
        STATUS         current
        DESCRIPTION    "Indicates the functional type of this AM2017B port."
        ::= { tnAm2017bPortConfigEntry 1 }

--------------------------------------------------------------------------------
-- AM2325B Optical Port Config Scalars
--------------------------------------------------------------------------------
    tnAm2325bPortConfigAttributeTotal OBJECT-TYPE
        SYNTAX         Integer32
        MAX-ACCESS     read-only
        STATUS         current
        DESCRIPTION    ""
        ::= { tnOpticalPortConfig 135 }

--------------------------------------------------------------------------------
-- AM2325B Optical Port Config Table
--------------------------------------------------------------------------------
    tnAm2325bPortConfigTable OBJECT-TYPE
        SYNTAX         SEQUENCE OF TnAm2325bPortConfigEntry
        MAX-ACCESS     not-accessible
        STATUS         current
        DESCRIPTION    "The ports on an AM2325B optical card."
        ::= { tnOpticalPortConfig 136 }

    tnAm2325bPortConfigEntry OBJECT-TYPE
        SYNTAX         TnAm2325bPortConfigEntry
        MAX-ACCESS     not-accessible
        STATUS         current
        DESCRIPTION    ""
        INDEX { ifIndex }
        ::= { tnAm2325bPortConfigTable 1 }

    TnAm2325bPortConfigEntry ::=
        SEQUENCE {
            tnAm2325bPortConfigFunction INTEGER
        }

    tnAm2325bPortConfigFunction OBJECT-TYPE
        SYNTAX         INTEGER {
                         line(1),
                         signal(2),
                         dcm(3),
                         inv(4),
                         osc(5)
                       }
        MAX-ACCESS     read-only
        STATUS         current
        DESCRIPTION    "Indicates the functional type of this AM2325B port."
        ::= { tnAm2325bPortConfigEntry 1 }

--------------------------------------------------------------------------------
-- 1DPP21 Optical Port Config Scalars
--------------------------------------------------------------------------------
    tn1dpp21PortConfigAttributeTotal OBJECT-TYPE
        SYNTAX         Integer32
        MAX-ACCESS     read-only
        STATUS         current
        DESCRIPTION    ""
        ::= { tnOpticalPortConfig 137 }

--------------------------------------------------------------------------------
-- 1DPP21 Optical Port Config Table
--------------------------------------------------------------------------------
    tn1dpp21PortConfigTable OBJECT-TYPE
        SYNTAX         SEQUENCE OF Tn1dpp21PortConfigEntry
        MAX-ACCESS     not-accessible
        STATUS         current
        DESCRIPTION    "The ports on a 1DPP21 optical card."
        ::= { tnOpticalPortConfig 138 }

    tn1dpp21PortConfigEntry OBJECT-TYPE
        SYNTAX         Tn1dpp21PortConfigEntry
        MAX-ACCESS     not-accessible
        STATUS         current
        DESCRIPTION    ""
        INDEX { ifIndex }
        ::= { tn1dpp21PortConfigTable 1 }

    Tn1dpp21PortConfigEntry ::=
        SEQUENCE {
            tn1dpp21PortConfigFunction INTEGER
        }

    tn1dpp21PortConfigFunction OBJECT-TYPE
        SYNTAX         INTEGER {
                         network(1),
                         client(2)
                       }
        MAX-ACCESS     read-only
        STATUS         current
        DESCRIPTION    "Indicates the functional type of this 1DPP21 port."
        ::= { tn1dpp21PortConfigEntry 1 }

--------------------------------------------------------------------------------
-- E1 T1 Port Config Table
--------------------------------------------------------------------------------
    tnE1T1PortConfigTable OBJECT-TYPE
        SYNTAX         SEQUENCE OF TnE1T1PortConfigEntry
        MAX-ACCESS     not-accessible
        STATUS         current
        DESCRIPTION    "Common attributes against E1 T1 supported ports."
        ::= { tnOpticalPortConfig 139 }

    tnE1T1PortConfigEntry OBJECT-TYPE
        SYNTAX         TnE1T1PortConfigEntry
        MAX-ACCESS     not-accessible
        STATUS         current
        DESCRIPTION    ""
        INDEX { ifIndex }
        ::= { tnE1T1PortConfigTable 1 }

    TnE1T1PortConfigEntry ::=
        SEQUENCE {
            tnE1T1MappingMode             INTEGER,
            tnE1T1Format                  INTEGER,
            tnE1T1ClientEgressTimingMode  INTEGER,
            tnE1T1PortConfigImpedance     INTEGER
        }

    tnE1T1MappingMode OBJECT-TYPE
        SYNTAX         INTEGER {
                         async(1)
                       }
        MAX-ACCESS     read-create
        STATUS         current
        DESCRIPTION    "E1 T1 MAP MODE."
        DEFVAL         { async }
        ::= { tnE1T1PortConfigEntry 1 }

    tnE1T1Format OBJECT-TYPE
        SYNTAX         INTEGER {
                         crc4mfrm(1),
                         dfrm(2)
                       }
        MAX-ACCESS     read-create
        STATUS         current
        DESCRIPTION    "E1 Frame Format."
        DEFVAL         { crc4mfrm }
        ::= { tnE1T1PortConfigEntry 2 }

    tnE1T1ClientEgressTimingMode OBJECT-TYPE
        SYNTAX         INTEGER {
                         system(1),
                         normal(2)
                       }
        MAX-ACCESS     read-create
        STATUS         current
        DESCRIPTION    "E1 T1 Client Egress Timing Mode."
        DEFVAL         { system }
        ::= { tnE1T1PortConfigEntry 3 }

    tnE1T1PortConfigImpedance OBJECT-TYPE
        SYNTAX         INTEGER {
                         imp75ohm(1),
                         imp120ohm(2)
                       }
        MAX-ACCESS     read-create
        STATUS         current
        DESCRIPTION    "E1 T1 port configurable impedance."
        DEFVAL         { imp75ohm }
        ::= { tnE1T1PortConfigEntry 4 }

--------------------------------------------------------------------------------
-- MVAC Optical Port Config Scalars
--------------------------------------------------------------------------------
    tnMvacPortConfigAttributeTotal OBJECT-TYPE
        SYNTAX         Integer32
        MAX-ACCESS     read-only
        STATUS         current
        DESCRIPTION    ""
        ::= { tnOpticalPortConfig 140 }

--------------------------------------------------------------------------------
-- MVAC Optical Port Config Table
--------------------------------------------------------------------------------
    tnMvacPortConfigTable OBJECT-TYPE
        SYNTAX         SEQUENCE OF TnMvacPortConfigEntry
        MAX-ACCESS     not-accessible
        STATUS         current
        DESCRIPTION    "The ports on a MVAC optical card."
        ::= { tnOpticalPortConfig 141 }

    tnMvacPortConfigEntry OBJECT-TYPE
        SYNTAX         TnMvacPortConfigEntry
        MAX-ACCESS     not-accessible
        STATUS         current
        DESCRIPTION    ""
        INDEX { ifIndex }
        ::= { tnMvacPortConfigTable 1 }

    TnMvacPortConfigEntry ::=
        SEQUENCE {
            tnMvacPortConfigFunction              INTEGER,
            tnMvacPortConfigVoaMode               INTEGER,
            tnMvacPortConfigAttenuationModeAtten  Integer32,
            tnMvacPortConfigConnToPort            InterfaceIndexOrZero
        }

    tnMvacPortConfigFunction OBJECT-TYPE
        SYNTAX         INTEGER {
                         general(1)
                       }
        MAX-ACCESS     read-only
        STATUS         current
        DESCRIPTION    "Indicates the functional type of this MVAC port."
        ::= { tnMvacPortConfigEntry 1 }

    tnMvacPortConfigVoaMode OBJECT-TYPE
        SYNTAX         INTEGER {
                         power(1),
                         attenuation(2)
                       }
        MAX-ACCESS     read-create
        STATUS         current
        DESCRIPTION    "Sets the port operating mode."
        DEFVAL         { power }
        ::= { tnMvacPortConfigEntry 2 }

    tnMvacPortConfigAttenuationModeAtten OBJECT-TYPE
        SYNTAX         Integer32
         UNITS         "mB"
        MAX-ACCESS     read-create
        STATUS         current
        DESCRIPTION    "Sets attenuation value in attenuation mode."
        DEFVAL         { 0 }
        ::= { tnMvacPortConfigEntry 3 }

    tnMvacPortConfigConnToPort OBJECT-TYPE
        SYNTAX         InterfaceIndexOrZero
        MAX-ACCESS     read-create
        STATUS         current
        DESCRIPTION    "Sets reference to degree input port when MVAC
                        port used external."
        DEFVAL         { 0 }
        ::= { tnMvacPortConfigEntry 4 }

--------------------------------------------------------------------------------
-- 43SCX4 Optical Port Config Scalars
--------------------------------------------------------------------------------
    tn43scx4PortConfigAttributeTotal OBJECT-TYPE
        SYNTAX         Integer32
        MAX-ACCESS     read-only
        STATUS         current
        DESCRIPTION    ""
        ::= { tnOpticalPortConfig 144 }

--------------------------------------------------------------------------------
-- 43SCX4 Optical Port Config Table
--------------------------------------------------------------------------------
    tn43scx4PortConfigTable OBJECT-TYPE
        SYNTAX         SEQUENCE OF Tn43scx4PortConfigEntry
        MAX-ACCESS     not-accessible
        STATUS         current
        DESCRIPTION    "The ports on a 43SCX4 optical card."
        ::= { tnOpticalPortConfig 145 }

    tn43scx4PortConfigEntry OBJECT-TYPE
        SYNTAX         Tn43scx4PortConfigEntry
        MAX-ACCESS     not-accessible
        STATUS         current
        DESCRIPTION    ""
        INDEX { ifIndex }
        ::= { tn43scx4PortConfigTable 1 }

    Tn43scx4PortConfigEntry ::=
        SEQUENCE {
            tn43scx4PortConfigFunction INTEGER
        }

    tn43scx4PortConfigFunction OBJECT-TYPE
        SYNTAX         INTEGER {
                         network(1),
                         client(2)
                       }
        MAX-ACCESS     read-only
        STATUS         current
        DESCRIPTION    "Indicates the functional type of this 43SCX4 port."
        ::= { tn43scx4PortConfigEntry 1 }

--------------------------------------------------------------------------------
-- RA2P Optical Port Config Scalars
--------------------------------------------------------------------------------
    tnRa2pPortConfigAttributeTotal OBJECT-TYPE
        SYNTAX         Integer32
        MAX-ACCESS     read-only
        STATUS         current
        DESCRIPTION    ""
        ::= { tnOpticalPortConfig 146 }

--------------------------------------------------------------------------------
-- RA2P Optical Port Config Table
--------------------------------------------------------------------------------
    tnRa2pPortConfigTable OBJECT-TYPE
        SYNTAX         SEQUENCE OF TnRa2pPortConfigEntry
        MAX-ACCESS     not-accessible
        STATUS         current
        DESCRIPTION    "The ports on a RA2P optical card."
        ::= { tnOpticalPortConfig 147 }

    tnRa2pPortConfigEntry OBJECT-TYPE
        SYNTAX         TnRa2pPortConfigEntry
        MAX-ACCESS     not-accessible
        STATUS         current
        DESCRIPTION    ""
        INDEX { ifIndex }
        ::= { tnRa2pPortConfigTable 1 }

    TnRa2pPortConfigEntry ::=
        SEQUENCE {
            tnRa2pPortConfigFunction INTEGER
        }

    tnRa2pPortConfigFunction OBJECT-TYPE
        SYNTAX         INTEGER {
                         lineIn(1),
                         lineOut(2)
                       }
        MAX-ACCESS     read-only
        STATUS         current
        DESCRIPTION    "Indicates the functional type of this RA2P port."
        ::= { tnRa2pPortConfigEntry 1 }

--------------------------------------------------------------------------------
-- AM2318A Optical Port Config Scalars
--------------------------------------------------------------------------------
    tnAm2318aPortConfigAttributeTotal OBJECT-TYPE
        SYNTAX         Integer32
        MAX-ACCESS     read-only
        STATUS         current
        DESCRIPTION    ""
        ::= { tnOpticalPortConfig 148 }

--------------------------------------------------------------------------------
-- AM2318A Optical Port Config Table
--------------------------------------------------------------------------------
    tnAm2318aPortConfigTable OBJECT-TYPE
        SYNTAX         SEQUENCE OF TnAm2318aPortConfigEntry
        MAX-ACCESS     not-accessible
        STATUS         current
        DESCRIPTION    "The ports on an AM2318A optical card."
        ::= { tnOpticalPortConfig 149 }

    tnAm2318aPortConfigEntry OBJECT-TYPE
        SYNTAX         TnAm2318aPortConfigEntry
        MAX-ACCESS     not-accessible
        STATUS         current
        DESCRIPTION    ""
        INDEX { ifIndex }
        ::= { tnAm2318aPortConfigTable 1 }

    TnAm2318aPortConfigEntry ::=
        SEQUENCE {
            tnAm2318aPortConfigFunction INTEGER
        }

    tnAm2318aPortConfigFunction OBJECT-TYPE
        SYNTAX         INTEGER {
                         lineIn(1),
                         inv(2),
                         osc(3),
                         lineOut(4),
                         oscSfp(5),
                         det(6)
                       }
        MAX-ACCESS     read-only
        STATUS         current
        DESCRIPTION    "Indicates the functional type of this AM2318A port."
        ::= { tnAm2318aPortConfigEntry 1 }

--------------------------------------------------------------------------------
-- AM2125A Optical Port Config Scalars
--------------------------------------------------------------------------------
    tnAm2125aPortConfigAttributeTotal OBJECT-TYPE
        SYNTAX         Integer32
        MAX-ACCESS     read-only
        STATUS         current
        DESCRIPTION    ""
        ::= { tnOpticalPortConfig 150 }

--------------------------------------------------------------------------------
-- AM2125A Optical Port Config Table
--------------------------------------------------------------------------------
    tnAm2125aPortConfigTable OBJECT-TYPE
        SYNTAX         SEQUENCE OF TnAm2125aPortConfigEntry
        MAX-ACCESS     not-accessible
        STATUS         current
        DESCRIPTION    "The ports on an AM2125A optical card."
        ::= { tnOpticalPortConfig 151 }

    tnAm2125aPortConfigEntry OBJECT-TYPE
        SYNTAX         TnAm2125aPortConfigEntry
        MAX-ACCESS     not-accessible
        STATUS         current
        DESCRIPTION    ""
        INDEX { ifIndex }
        ::= { tnAm2125aPortConfigTable 1 }

    TnAm2125aPortConfigEntry ::=
        SEQUENCE {
            tnAm2125aPortConfigFunction INTEGER
        }

    tnAm2125aPortConfigFunction OBJECT-TYPE
        SYNTAX         INTEGER {
                         lineIn(1),
                         inv(2),
                         dcm(3),
                         lineOut(4),
                         oscSfp(5),
                         det(6),
                         osc(7)
                       }
        MAX-ACCESS     read-only
        STATUS         current
        DESCRIPTION    "Indicates the functional type of this AM2125A port."
        ::= { tnAm2125aPortConfigEntry 1 }

--------------------------------------------------------------------------------
-- ITLU Optical Port Config Scalars
--------------------------------------------------------------------------------
    tnItluPortConfigAttributeTotal OBJECT-TYPE
        SYNTAX         Integer32
        MAX-ACCESS     read-only
        STATUS         current
        DESCRIPTION    ""
        ::= { tnOpticalPortConfig 152 }

--------------------------------------------------------------------------------
-- ITLU Optical Port Config Table
--------------------------------------------------------------------------------
    tnItluPortConfigTable OBJECT-TYPE
        SYNTAX         SEQUENCE OF TnItluPortConfigEntry
        MAX-ACCESS     not-accessible
        STATUS         current
        DESCRIPTION    "The ports on an ITLU optical card."
        ::= { tnOpticalPortConfig 153 }

    tnItluPortConfigEntry OBJECT-TYPE
        SYNTAX         TnItluPortConfigEntry
        MAX-ACCESS     not-accessible
        STATUS         current
        DESCRIPTION    ""
        INDEX { ifIndex }
        ::= { tnItluPortConfigTable 1 }

    TnItluPortConfigEntry ::=
        SEQUENCE {
            tnItluPortConfigFunction INTEGER
        }

    tnItluPortConfigFunction OBJECT-TYPE
        SYNTAX         INTEGER {
                         sigIn(1),
                         eOut(2),
                         oOut(3)
                       }
        MAX-ACCESS     read-only
        STATUS         current
        DESCRIPTION    "Indicates the functional type of this ITLU port:

                        port 1 - signal in
                        port 2 - even out
                        port 3 - odd out"
        ::= { tnItluPortConfigEntry 1 }

--------------------------------------------------------------------------------
-- WR8-88A Optical Port Config Scalars
--------------------------------------------------------------------------------
    tnWr8c88aPortConfigAttributeTotal OBJECT-TYPE
        SYNTAX         Integer32
        MAX-ACCESS     read-only
        STATUS         current
        DESCRIPTION    ""
        ::= { tnOpticalPortConfig 154 }

--------------------------------------------------------------------------------
-- WR8-88A Optical Port Config Table
--------------------------------------------------------------------------------
    tnWr8c88aPortConfigTable OBJECT-TYPE
        SYNTAX         SEQUENCE OF TnWr8c88aPortConfigEntry
        MAX-ACCESS     not-accessible
        STATUS         current
        DESCRIPTION    "The ports on a WR8-88A optical card."
        ::= { tnOpticalPortConfig 155 }

    tnWr8c88aPortConfigEntry OBJECT-TYPE
        SYNTAX         TnWr8c88aPortConfigEntry
        MAX-ACCESS     not-accessible
        STATUS         current
        DESCRIPTION    ""
        INDEX { ifIndex }
        ::= { tnWr8c88aPortConfigTable 1 }

    TnWr8c88aPortConfigEntry ::=
        SEQUENCE {
            tnWr8c88aPortConfigFunction  INTEGER
        }

    tnWr8c88aPortConfigFunction OBJECT-TYPE
        SYNTAX         INTEGER {
                         signal(1),
                         thru(2),
                         dropOut(3),
                         addIn(4),
--                       obsolete
--                         test(5),
                         meshOut(5),
                         inv(6)
                       }
        MAX-ACCESS     read-only
        STATUS         current
        DESCRIPTION    "Indicates the functional type of this WR8-88A port."
        ::= { tnWr8c88aPortConfigEntry 1 }

--------------------------------------------------------------------------------
-- 11DPE12E Optical Port Config Scalars
--------------------------------------------------------------------------------
    tn11dpe12ePortConfigAttributeTotal OBJECT-TYPE
        SYNTAX         Integer32
        MAX-ACCESS     read-only
        STATUS         current
        DESCRIPTION    ""
        ::= { tnOpticalPortConfig 156 }

--------------------------------------------------------------------------------
-- 11DPE12E Optical Port Config Table
--------------------------------------------------------------------------------
    tn11dpe12ePortConfigTable OBJECT-TYPE
        SYNTAX         SEQUENCE OF Tn11dpe12ePortConfigEntry
        MAX-ACCESS     not-accessible
        STATUS         current
        DESCRIPTION    "The ports on a 11DPE12E optical card."
        ::= { tnOpticalPortConfig 157 }

    tn11dpe12ePortConfigEntry OBJECT-TYPE
        SYNTAX         Tn11dpe12ePortConfigEntry
        MAX-ACCESS     not-accessible
        STATUS         current
        DESCRIPTION    ""
        INDEX { ifIndex }
        ::= { tn11dpe12ePortConfigTable 1 }

    Tn11dpe12ePortConfigEntry ::=
        SEQUENCE {
            tn11dpe12ePortConfigFunction INTEGER,
            tn11dpe12ePortQinQModeTPID   INTEGER,
            tn11dpe12ePortQinQModePVID   Unsigned32
        }

    tn11dpe12ePortConfigFunction OBJECT-TYPE
        SYNTAX         INTEGER {
                         network(1),
                         client(2),
                         evoa(3),
                         backplane(4)
                       }
        MAX-ACCESS     read-only
        STATUS         current
        DESCRIPTION    "Indicates the functional type of this 11DPGE12 port."
        ::= { tn11dpe12ePortConfigEntry 1 }

    tn11dpe12ePortQinQModeTPID OBJECT-TYPE
        SYNTAX         INTEGER {
                         qinqtpid1(1),
                         qinqtpid2(2),
                         qinqtpid3(3),
                         qinqtpid4(4)
                       }
        MAX-ACCESS     read-create
        STATUS         current
        DESCRIPTION    "The QinQ mode TPID for 11DPE12E port."
        DEFVAL         { qinqtpid1 }
        ::= { tn11dpe12ePortConfigEntry 2 }

    tn11dpe12ePortQinQModePVID OBJECT-TYPE
        SYNTAX         Unsigned32
        MAX-ACCESS     read-create
        STATUS         current
        DESCRIPTION    "The PVID for 11DPE12E port.

                        Current configurable range: 0 to 0x0FFE."
        DEFVAL         { 0 }
        ::= { tn11dpe12ePortConfigEntry 3 }

--------------------------------------------------------------------------------
-- 112SX10L Optical Port Config Scalars
--------------------------------------------------------------------------------
    tn112sx10lPortConfigAttributeTotal OBJECT-TYPE
        SYNTAX         Integer32
        MAX-ACCESS     read-only
        STATUS         current
        DESCRIPTION    ""
        ::= { tnOpticalPortConfig 158 }

--------------------------------------------------------------------------------
-- 112SX10L Optical Port Config Table
--------------------------------------------------------------------------------
    tn112sx10lPortConfigTable OBJECT-TYPE
        SYNTAX         SEQUENCE OF Tn112sx10lPortConfigEntry
        MAX-ACCESS     not-accessible
        STATUS         current
        DESCRIPTION    "The ports on a 112SX10L optical card."
        ::= { tnOpticalPortConfig 159 }

    tn112sx10lPortConfigEntry OBJECT-TYPE
        SYNTAX         Tn112sx10lPortConfigEntry
        MAX-ACCESS     not-accessible
        STATUS         current
        DESCRIPTION    ""
        INDEX { ifIndex }
        ::= { tn112sx10lPortConfigTable 1 }

    Tn112sx10lPortConfigEntry ::=
        SEQUENCE {
            tn112sx10lPortConfigFunction INTEGER
        }

    tn112sx10lPortConfigFunction OBJECT-TYPE
        SYNTAX         INTEGER {
                         network(1),
                         client(2)
                       }
        MAX-ACCESS     read-only
        STATUS         current
        DESCRIPTION    "Indicates the functional type of this 112SX10L port."
        ::= { tn112sx10lPortConfigEntry 1 }

--------------------------------------------------------------------------------
-- 112SA1L Optical Port Config Scalars
--------------------------------------------------------------------------------
    tn112sa1lPortConfigAttributeTotal OBJECT-TYPE
        SYNTAX         Integer32
        MAX-ACCESS     read-only
        STATUS         current
        DESCRIPTION    ""
        ::= { tnOpticalPortConfig 160 }

--------------------------------------------------------------------------------
-- 112SA1L Optical Port Config Table
--------------------------------------------------------------------------------
    tn112sa1lPortConfigTable OBJECT-TYPE
        SYNTAX         SEQUENCE OF Tn112sa1lPortConfigEntry
        MAX-ACCESS     not-accessible
        STATUS         current
        DESCRIPTION    "The ports on a 112SA1L optical card."
        ::= { tnOpticalPortConfig 161 }

    tn112sa1lPortConfigEntry OBJECT-TYPE
        SYNTAX         Tn112sa1lPortConfigEntry
        MAX-ACCESS     not-accessible
        STATUS         current
        DESCRIPTION    ""
        INDEX { ifIndex }
        ::= { tn112sa1lPortConfigTable 1 }

    Tn112sa1lPortConfigEntry ::=
        SEQUENCE {
            tn112sa1lPortConfigFunction INTEGER
        }

    tn112sa1lPortConfigFunction OBJECT-TYPE
        SYNTAX         INTEGER {
                         network(1),
                         client(2)
                       }
        MAX-ACCESS     read-only
        STATUS         current
        DESCRIPTION    "Indicates the functional type of this 112SA1L port."
        ::= { tn112sa1lPortConfigEntry 1 }

--------------------------------------------------------------------------------
-- 11DPM12 Optical Port Config Scalars
--------------------------------------------------------------------------------
    tn11dpm12PortConfigAttributeTotal OBJECT-TYPE
        SYNTAX         Integer32
        MAX-ACCESS     read-only
        STATUS         current
        DESCRIPTION    ""
        ::= { tnOpticalPortConfig 162 }

--------------------------------------------------------------------------------
-- 11DPM12 Optical Port Config Table
--------------------------------------------------------------------------------
    tn11dpm12PortConfigTable OBJECT-TYPE
        SYNTAX         SEQUENCE OF Tn11dpm12PortConfigEntry
        MAX-ACCESS     not-accessible
        STATUS         current
        DESCRIPTION    "The ports on a 11DPM12 optical card."
        ::= { tnOpticalPortConfig 163 }

    tn11dpm12PortConfigEntry OBJECT-TYPE
        SYNTAX         Tn11dpm12PortConfigEntry
        MAX-ACCESS     not-accessible
        STATUS         current
        DESCRIPTION    ""
        INDEX { ifIndex }
        ::= { tn11dpm12PortConfigTable 1 }

    Tn11dpm12PortConfigEntry ::=
        SEQUENCE {
            tn11dpm12PortConfigFunction INTEGER
        }

    tn11dpm12PortConfigFunction OBJECT-TYPE
        SYNTAX         INTEGER {
                         network(1),
                         client(2),
                         evoa(3)
                       }
        MAX-ACCESS     read-only
        STATUS         current
        DESCRIPTION    "Indicates the functional type of this 11DPM12 port."
        ::= { tn11dpm12PortConfigEntry 1 }

--------------------------------------------------------------------------------
-- WR8-88A WSS Channel Attenuation Config Table
--------------------------------------------------------------------------------
--    obsolete
--    tnWr8c88aAttenPortConfigTable OBJECT-TYPE ::= { tnOpticalPortConfig 164 }

--------------------------------------------------------------------------------
-- Raman Optical Port Config Table
--------------------------------------------------------------------------------
    tnRamanPortConfigTable OBJECT-TYPE
        SYNTAX         SEQUENCE OF TnRamanPortConfigEntry
        MAX-ACCESS     not-accessible
        STATUS         current
        DESCRIPTION    "The ports on an Raman optical card."
        ::= { tnOpticalPortConfig 165 }

    tnRamanPortConfigEntry OBJECT-TYPE
        SYNTAX         TnRamanPortConfigEntry
        MAX-ACCESS     not-accessible
        STATUS         current
        DESCRIPTION    ""
        INDEX { ifIndex }
        ::= { tnRamanPortConfigTable 1 }

    TnRamanPortConfigEntry ::=
        SEQUENCE {
            tnRamanPortFiberType         INTEGER,
            tnRamanPortGMinExpected      Integer32,
            tnRamanPortGMaxExpected      Integer32,
            tnRamanPortTiltTarget        Integer32,
            tnRamanPortOperatingMode     INTEGER,
            tnRamanPortAgcTargetGain     Integer32,
            tnRamanPortAprMode           INTEGER
        }

    tnRamanPortFiberType OBJECT-TYPE
        SYNTAX         INTEGER {
                         ssmf(1),
                         twrs(2),
                         eleaf(3)
                      }
        MAX-ACCESS     read-create
        STATUS         current
        DESCRIPTION    "Indicates the fiber type."
        DEFVAL         { ssmf }
        ::= { tnRamanPortConfigEntry 1 }

    tnRamanPortGMinExpected OBJECT-TYPE
        SYNTAX         Integer32
        UNITS          "mB"
        MAX-ACCESS     read-create
        STATUS         current
        DESCRIPTION    "The minimum gain expected.

                        Current configurable range: 0 to 2500."
        DEFVAL         { 700 }
        ::= { tnRamanPortConfigEntry 2 }

    tnRamanPortGMaxExpected OBJECT-TYPE
        SYNTAX         Integer32
        UNITS          "mB"
        MAX-ACCESS     read-create
        STATUS         current
        DESCRIPTION    "The maximum gain expected.

                        Current configurable range: 0 to 2500."
        DEFVAL         { 2500 }
        ::= { tnRamanPortConfigEntry 3 }

    tnRamanPortTiltTarget OBJECT-TYPE
        SYNTAX         Integer32
        UNITS          "mB"
        MAX-ACCESS     read-create
        STATUS         current
        DESCRIPTION    "The tilt target.

                        Current configurable range: -300 to 300."
        DEFVAL         { 0 }
        ::= { tnRamanPortConfigEntry 4 }

    tnRamanPortOperatingMode OBJECT-TYPE
        SYNTAX         INTEGER {
                         power(1),
                         gain(2),
                         maxPower(3)
                       }
        MAX-ACCESS     read-create
        STATUS         current
        DESCRIPTION    "This attribute determines the operating mode."
        DEFVAL         { gain }
        ::= { tnRamanPortConfigEntry 5 }

    tnRamanPortAgcTargetGain OBJECT-TYPE
        SYNTAX         Integer32
        UNITS          "mB"
        MAX-ACCESS     read-create
        STATUS         current
        DESCRIPTION    "The AGC mode target gain.

                        Current configurable range: 200 to 2000."
        DEFVAL         { 1000 }
        ::= { tnRamanPortConfigEntry 6 }

    tnRamanPortAprMode OBJECT-TYPE
        SYNTAX         INTEGER {
                         auto(1),
                         force(2)
                      }
        MAX-ACCESS     read-create
        STATUS         current
        DESCRIPTION    "Indicates APR mode."
        DEFVAL         { auto }
        ::= { tnRamanPortConfigEntry 7 }

--------------------------------------------------------------------------------
-- MESH4 Optical Port Config Scalars
--------------------------------------------------------------------------------
    tnMesh4PortConfigAttributeTotal OBJECT-TYPE
        SYNTAX         Integer32
        MAX-ACCESS     read-only
        STATUS         current
        DESCRIPTION    ""
        ::= { tnOpticalPortConfig 166 }

--------------------------------------------------------------------------------
-- MESH4 Optical Port Config Table
--------------------------------------------------------------------------------
    tnMesh4PortConfigTable OBJECT-TYPE
        SYNTAX         SEQUENCE OF TnMesh4PortConfigEntry
        MAX-ACCESS     not-accessible
        STATUS         current
        DESCRIPTION    "The ports on a MESH4 card."
        ::= { tnOpticalPortConfig 167 }

    tnMesh4PortConfigEntry OBJECT-TYPE
        SYNTAX         TnMesh4PortConfigEntry
        MAX-ACCESS     not-accessible
        STATUS         current
        DESCRIPTION    ""
        INDEX { ifIndex }
        ::= { tnMesh4PortConfigTable 1 }

    TnMesh4PortConfigEntry ::=
        SEQUENCE {
            tnMesh4PortConfigFunction  INTEGER
        }

    tnMesh4PortConfigFunction OBJECT-TYPE
        SYNTAX         INTEGER {
                         sigIn(1),
                         sigOut(2)
                       }
        MAX-ACCESS     read-only
        STATUS         current
        DESCRIPTION    "Indicates the functional type of this MESH4 port."
        ::= { tnMesh4PortConfigEntry 1 }

--------------------------------------------------------------------------------
-- Tandem Connection Monitoring (TCM) Optical Port Config Scalars
--------------------------------------------------------------------------------
--    obsolete
--    tnTcmPortConfigAttributeTotal OBJECT-TYPE ::= { tnOpticalPortConfig 168 }

--------------------------------------------------------------------------------
--  Tandem Connection Monitoring (TCM) Optical Port Config Table
--------------------------------------------------------------------------------
--    obsolete
--    tnTcmPortConfigTable OBJECT-TYPE OBJECT-TYPE ::= { tnOpticalPortConfig 169 }

--------------------------------------------------------------------------------
-- 43SCA1 Optical Port Config Scalars
--------------------------------------------------------------------------------
    tn43sca1PortConfigAttributeTotal OBJECT-TYPE
        SYNTAX         Integer32
        MAX-ACCESS     read-only
        STATUS         current
        DESCRIPTION    ""
        ::= { tnOpticalPortConfig 170 }

--------------------------------------------------------------------------------
-- 43SCA1 Optical Port Config Table
--------------------------------------------------------------------------------
    tn43sca1PortConfigTable OBJECT-TYPE
        SYNTAX         SEQUENCE OF Tn43sca1PortConfigEntry
        MAX-ACCESS     not-accessible
        STATUS         current
        DESCRIPTION    "The ports on a 43SCA1 optical card."
        ::= { tnOpticalPortConfig 171 }

    tn43sca1PortConfigEntry OBJECT-TYPE
        SYNTAX         Tn43sca1PortConfigEntry
        MAX-ACCESS     not-accessible
        STATUS         current
        DESCRIPTION    ""
        INDEX { ifIndex }
        ::= { tn43sca1PortConfigTable 1 }

    Tn43sca1PortConfigEntry ::=
        SEQUENCE {
            tn43sca1PortConfigFunction INTEGER
        }

    tn43sca1PortConfigFunction OBJECT-TYPE
        SYNTAX         INTEGER {
                         network(1),
                         client(2)
                       }
        MAX-ACCESS     read-only
        STATUS         current
        DESCRIPTION    "Indicates the functional type of this 43SCA1 port."
        ::= { tn43sca1PortConfigEntry 1 }

--------------------------------------------------------------------------------
-- 43SCX4L Optical Port Config Scalars
--------------------------------------------------------------------------------
    tn43scx4lPortConfigAttributeTotal OBJECT-TYPE
        SYNTAX         Integer32
        MAX-ACCESS     read-only
        STATUS         current
        DESCRIPTION    ""
        ::= { tnOpticalPortConfig 172 }

--------------------------------------------------------------------------------
-- 43SCX4L Optical Port Config Table
--------------------------------------------------------------------------------
    tn43scx4lPortConfigTable OBJECT-TYPE
        SYNTAX         SEQUENCE OF Tn43scx4lPortConfigEntry
        MAX-ACCESS     not-accessible
        STATUS         current
        DESCRIPTION    "The ports on a 43SCX4L optical card."
        ::= { tnOpticalPortConfig 173 }

    tn43scx4lPortConfigEntry OBJECT-TYPE
        SYNTAX         Tn43scx4lPortConfigEntry
        MAX-ACCESS     not-accessible
        STATUS         current
        DESCRIPTION    ""
        INDEX { ifIndex }
        ::= { tn43scx4lPortConfigTable 1 }

    Tn43scx4lPortConfigEntry ::=
        SEQUENCE {
            tn43scx4lPortConfigFunction INTEGER
        }

    tn43scx4lPortConfigFunction OBJECT-TYPE
        SYNTAX         INTEGER {
                         network(1),
                         client(2)
                       }
        MAX-ACCESS     read-only
        STATUS         current
        DESCRIPTION    "Indicates the functional type of this 43SCX4L port."
        ::= { tn43scx4lPortConfigEntry 1 }

--------------------------------------------------------------------------------
-- AM2125B Optical Port Config Scalars
--------------------------------------------------------------------------------
    tnAm2125bPortConfigAttributeTotal OBJECT-TYPE
        SYNTAX         Integer32
        MAX-ACCESS     read-only
        STATUS         current
        DESCRIPTION    ""
        ::= { tnOpticalPortConfig 174 }

--------------------------------------------------------------------------------
-- AM2125B Optical Port Config Table
--------------------------------------------------------------------------------
    tnAm2125bPortConfigTable OBJECT-TYPE
        SYNTAX         SEQUENCE OF TnAm2125bPortConfigEntry
        MAX-ACCESS     not-accessible
        STATUS         current
        DESCRIPTION    "The ports on an AM2125B optical card."
        ::= { tnOpticalPortConfig 175 }

    tnAm2125bPortConfigEntry OBJECT-TYPE
        SYNTAX         TnAm2125bPortConfigEntry
        MAX-ACCESS     not-accessible
        STATUS         current
        DESCRIPTION    ""
        INDEX { ifIndex }
        ::= { tnAm2125bPortConfigTable 1 }

    TnAm2125bPortConfigEntry ::=
        SEQUENCE {
            tnAm2125bPortConfigFunction INTEGER
        }

    tnAm2125bPortConfigFunction OBJECT-TYPE
        SYNTAX         INTEGER {
                         lineIn(1),
                         inv(2),
                         dcm(3),
                         lineOut(4),
                         oscSfp(5),
                         det(6),
                         osc(7)
                       }
        MAX-ACCESS     read-only
        STATUS         current
        DESCRIPTION    "Indicates the functional type of this AM2125B port."
        ::= { tnAm2125bPortConfigEntry 1 }

--------------------------------------------------------------------------------
-- 112SNX10 Optical Port Config Scalars
--------------------------------------------------------------------------------
    tn112snx10PortConfigAttributeTotal OBJECT-TYPE
        SYNTAX         Integer32
        MAX-ACCESS     read-only
        STATUS         current
        DESCRIPTION    ""
        ::= { tnOpticalPortConfig 176 }

--------------------------------------------------------------------------------
-- 112SNX10 Optical Port Config Table
--------------------------------------------------------------------------------
    tn112snx10PortConfigTable OBJECT-TYPE
        SYNTAX         SEQUENCE OF Tn112snx10PortConfigEntry
        MAX-ACCESS     not-accessible
        STATUS         current
        DESCRIPTION    "The ports on a 112SNX10 optical card."
        ::= { tnOpticalPortConfig 177 }

    tn112snx10PortConfigEntry OBJECT-TYPE
        SYNTAX         Tn112snx10PortConfigEntry
        MAX-ACCESS     not-accessible
        STATUS         current
        DESCRIPTION    ""
        INDEX { ifIndex }
        ::= { tn112snx10PortConfigTable 1 }

    Tn112snx10PortConfigEntry ::=
        SEQUENCE {
            tn112snx10PortConfigFunction INTEGER
        }

    tn112snx10PortConfigFunction OBJECT-TYPE
        SYNTAX         INTEGER {
                         network(1),
                         client(2)
                       }
        MAX-ACCESS     read-only
        STATUS         current
        DESCRIPTION    "Indicates the functional type of this 112SNX10 port."
        ::= { tn112snx10PortConfigEntry 1 }

--------------------------------------------------------------------------------
-- 112SNA1 Optical Port Config Scalars
--------------------------------------------------------------------------------
    tn112sna1PortConfigAttributeTotal OBJECT-TYPE
        SYNTAX         Integer32
        MAX-ACCESS     read-only
        STATUS         current
        DESCRIPTION    ""
        ::= { tnOpticalPortConfig 178 }

--------------------------------------------------------------------------------
-- 112SNA1 Optical Port Config Table
--------------------------------------------------------------------------------
    tn112sna1PortConfigTable OBJECT-TYPE
        SYNTAX         SEQUENCE OF Tn112sna1PortConfigEntry
        MAX-ACCESS     not-accessible
        STATUS         current
        DESCRIPTION    "The ports on a 112SNA1 optical card."
        ::= { tnOpticalPortConfig 179 }

    tn112sna1PortConfigEntry OBJECT-TYPE
        SYNTAX         Tn112sna1PortConfigEntry
        MAX-ACCESS     not-accessible
        STATUS         current
        DESCRIPTION    ""
        INDEX { ifIndex }
        ::= { tn112sna1PortConfigTable 1 }

    Tn112sna1PortConfigEntry ::=
        SEQUENCE {
            tn112sna1PortConfigFunction INTEGER
        }

    tn112sna1PortConfigFunction OBJECT-TYPE
        SYNTAX         INTEGER {
                         network(1),
                         client(2)
                       }
        MAX-ACCESS     read-only
        STATUS         current
        DESCRIPTION    "Indicates the functional type of this 112SNA1 port."
        ::= { tn112sna1PortConfigEntry 1 }

--------------------------------------------------------------------------------
-- 11QTA4 Optical Port Config Scalars
--------------------------------------------------------------------------------
--    obsolete
--    tn11qta4PortConfigAttributeTotal OBJECT-TYPE ::= { tnOpticalPortConfig 180 }

--------------------------------------------------------------------------------
-- 11QTA4 Optical Port Config Table
--------------------------------------------------------------------------------
--    obsolete
--    tn11qta4PortConfigTable OBJECT-TYPE ::= { tnOpticalPortConfig 181 }

--------------------------------------------------------------------------------
-- 1DPP24M Optical Port Config Scalars
--------------------------------------------------------------------------------
    tn1dpp24mPortConfigAttributeTotal OBJECT-TYPE
        SYNTAX         Integer32
        MAX-ACCESS     read-only
        STATUS         current
        DESCRIPTION    ""
        ::= { tnOpticalPortConfig 182 }

--------------------------------------------------------------------------------
-- 1DPP24M Optical Port Config Table
--------------------------------------------------------------------------------
    tn1dpp24mPortConfigTable OBJECT-TYPE
        SYNTAX         SEQUENCE OF Tn1dpp24mPortConfigEntry
        MAX-ACCESS     not-accessible
        STATUS         current
        DESCRIPTION    "The ports on a 1DPP24M optical card."
        ::= { tnOpticalPortConfig 183 }

    tn1dpp24mPortConfigEntry OBJECT-TYPE
        SYNTAX         Tn1dpp24mPortConfigEntry
        MAX-ACCESS     not-accessible
        STATUS         current
        DESCRIPTION    ""
        INDEX { ifIndex }
        ::= { tn1dpp24mPortConfigTable 1 }

    Tn1dpp24mPortConfigEntry ::=
        SEQUENCE {
            tn1dpp24mPortConfigFunction INTEGER
        }

    tn1dpp24mPortConfigFunction OBJECT-TYPE
        SYNTAX         INTEGER {
                         network(1),
                         client(2)
                       }
        MAX-ACCESS     read-only
        STATUS         current
        DESCRIPTION    "Indicates the functional type of this 1DPP24M port."
        ::= { tn1dpp24mPortConfigEntry 1 }

--------------------------------------------------------------------------------
-- DWDM Common OTU3/ODU3 Client Port Config Table
--------------------------------------------------------------------------------
    tnDwdmCmnOtu3Odu3ClientPortConfigTable OBJECT-TYPE
        SYNTAX         SEQUENCE OF TnDwdmCmnOtu3Odu3ClientPortConfigEntry
        MAX-ACCESS     not-accessible
        STATUS         current
        DESCRIPTION    "Common attributes against DWDM client ports."
        ::= { tnOpticalPortConfig 184 }

    tnDwdmCmnOtu3Odu3ClientPortConfigEntry OBJECT-TYPE
        SYNTAX         TnDwdmCmnOtu3Odu3ClientPortConfigEntry
        MAX-ACCESS     not-accessible
        STATUS         current
        DESCRIPTION    ""
        INDEX { ifIndex }
        ::= { tnDwdmCmnOtu3Odu3ClientPortConfigTable 1 }

    TnDwdmCmnOtu3Odu3ClientPortConfigEntry ::=
        SEQUENCE {
            tnDwdmCmnClientPortOchOtu3FecMode            AluWdmFecMode,
            tnDwdmCmnClientPortOchOtu3Rate               AluWdmPortOchOtuRate,
            tnDwdmCmnClientPortOtu3TransmittedTti        OCTET STRING,
            tnDwdmCmnClientPortOtu3ExpectedTti           OCTET STRING,
            tnDwdmCmnClientPortOtu3TimConsequenceAction  AluWdmDisabledEnabled,
            tnDwdmCmnClientPortOtu3TimDetectionMode      AluWdmTimDetectionMode,
            tnDwdmCmnClientPortOdu3TransmittedTti        OCTET STRING,
            tnDwdmCmnClientPortOdu3ExpectedTti           OCTET STRING,
            tnDwdmCmnClientPortOdu3TimDetectionMode      AluWdmTimDetectionMode
    }

    tnDwdmCmnClientPortOchOtu3FecMode OBJECT-TYPE
        SYNTAX         AluWdmFecMode
        MAX-ACCESS     read-create
        STATUS         current
        DESCRIPTION    "OTU3 FEC mode."
        DEFVAL         { g709Fec }
        ::= { tnDwdmCmnOtu3Odu3ClientPortConfigEntry 1 }

    tnDwdmCmnClientPortOchOtu3Rate OBJECT-TYPE
        SYNTAX         AluWdmPortOchOtuRate
        MAX-ACCESS     read-create
        STATUS         current
        DESCRIPTION    "OTU3 rate."
        DEFVAL         { otm43G018 }
        ::= { tnDwdmCmnOtu3Odu3ClientPortConfigEntry 2 }

    tnDwdmCmnClientPortOtu3TransmittedTti OBJECT-TYPE
        SYNTAX         OCTET STRING
        MAX-ACCESS     read-create
        STATUS         current
        DESCRIPTION    "OTU3 transmitted TTI."
        DEFVAL         { "" }
        ::= { tnDwdmCmnOtu3Odu3ClientPortConfigEntry 3 }

    tnDwdmCmnClientPortOtu3ExpectedTti OBJECT-TYPE
        SYNTAX         OCTET STRING
        MAX-ACCESS     read-create
        STATUS         current
        DESCRIPTION    "OTU3 expected TTI."
        DEFVAL         { "" }
        ::= { tnDwdmCmnOtu3Odu3ClientPortConfigEntry 4 }

    tnDwdmCmnClientPortOtu3TimConsequenceAction OBJECT-TYPE
        SYNTAX         AluWdmDisabledEnabled
        MAX-ACCESS     read-create
        STATUS         current
        DESCRIPTION    "OTU3 TIM consequence action."
        DEFVAL         { disabled }
        ::= { tnDwdmCmnOtu3Odu3ClientPortConfigEntry 5 }

    tnDwdmCmnClientPortOtu3TimDetectionMode OBJECT-TYPE
        SYNTAX         AluWdmTimDetectionMode
        MAX-ACCESS     read-create
        STATUS         current
        DESCRIPTION    "OTU3 TIM detection mode."
        DEFVAL         { off }
        ::= { tnDwdmCmnOtu3Odu3ClientPortConfigEntry 6 }

    tnDwdmCmnClientPortOdu3TransmittedTti OBJECT-TYPE
        SYNTAX         OCTET STRING
        MAX-ACCESS     read-create
        STATUS         current
        DESCRIPTION    "ODU3 transmitted TTI."
        DEFVAL         { "" }
        ::= { tnDwdmCmnOtu3Odu3ClientPortConfigEntry 7 }

    tnDwdmCmnClientPortOdu3ExpectedTti OBJECT-TYPE
        SYNTAX         OCTET STRING
        MAX-ACCESS     read-create
        STATUS         current
        DESCRIPTION    "ODU3 expected TTI."
        DEFVAL         { "" }
        ::= { tnDwdmCmnOtu3Odu3ClientPortConfigEntry 8 }

    tnDwdmCmnClientPortOdu3TimDetectionMode OBJECT-TYPE
        SYNTAX         AluWdmTimDetectionMode
        MAX-ACCESS     read-create
        STATUS         current
        DESCRIPTION    "ODU3 TIM detection mode."
        DEFVAL         { off }
        ::= { tnDwdmCmnOtu3Odu3ClientPortConfigEntry 9 }

--------------------------------------------------------------------------------
-- UL43SCUP Optical Port Config Scalars
--------------------------------------------------------------------------------
    tnul43scupPortConfigAttributeTotal OBJECT-TYPE
        SYNTAX         Integer32
        MAX-ACCESS     read-only
        STATUS         current
        DESCRIPTION    ""
        ::= { tnOpticalPortConfig 185 }

--------------------------------------------------------------------------------
-- UL43SCUP Optical Port Config Table
--------------------------------------------------------------------------------
    tnul43scupPortConfigTable OBJECT-TYPE
        SYNTAX         SEQUENCE OF Tnul43scupPortConfigEntry
        MAX-ACCESS     not-accessible
        STATUS         current
        DESCRIPTION    "The ports on a UL43SCUP optical card."
        ::= { tnOpticalPortConfig 186 }

    tnul43scupPortConfigEntry OBJECT-TYPE
        SYNTAX         Tnul43scupPortConfigEntry
        MAX-ACCESS     not-accessible
        STATUS         current
        DESCRIPTION    ""
        INDEX { ifIndex }
        ::= { tnul43scupPortConfigTable 1 }

    Tnul43scupPortConfigEntry ::=
        SEQUENCE {
            tnul43scupPortConfigFunction  INTEGER
        }

    tnul43scupPortConfigFunction OBJECT-TYPE
        SYNTAX         INTEGER {
                         network(1)
                       }
        MAX-ACCESS     read-only
        STATUS         current
        DESCRIPTION    "Indicates the functional type of this UL43SCUP port."
        ::= { tnul43scupPortConfigEntry 1 }

--------------------------------------------------------------------------------
-- UL11QCUP Optical Port Config Scalars
--------------------------------------------------------------------------------
    tnul11qcupPortConfigAttributeTotal OBJECT-TYPE
        SYNTAX         Integer32
        MAX-ACCESS     read-only
        STATUS         current
        DESCRIPTION    ""
        ::= { tnOpticalPortConfig 187 }

--------------------------------------------------------------------------------
-- UL11QCUP Optical Port Config Table
--------------------------------------------------------------------------------
    tnul11qcupPortConfigTable OBJECT-TYPE
        SYNTAX         SEQUENCE OF Tnul11qcupPortConfigEntry
        MAX-ACCESS     not-accessible
        STATUS         current
        DESCRIPTION    "The ports on a UL11QCUP optical card."
        ::= { tnOpticalPortConfig 188 }

    tnul11qcupPortConfigEntry OBJECT-TYPE
        SYNTAX         Tnul11qcupPortConfigEntry
        MAX-ACCESS     not-accessible
        STATUS         current
        DESCRIPTION    ""
        INDEX { ifIndex }
        ::= { tnul11qcupPortConfigTable 1 }

    Tnul11qcupPortConfigEntry ::=
        SEQUENCE {
            tnul11qcupPortConfigFunction INTEGER
        }

    tnul11qcupPortConfigFunction OBJECT-TYPE
        SYNTAX         INTEGER {
                         network(1)
                       }
        MAX-ACCESS     read-only
        STATUS         current
        DESCRIPTION    "Indicates the functional type of this UL11QCUP port."
        ::= { tnul11qcupPortConfigEntry 1 }

--------------------------------------------------------------------------------
-- 11QPEN4 Optical Port Config Scalars
--------------------------------------------------------------------------------
    tn11qpen4PortConfigAttributeTotal OBJECT-TYPE
        SYNTAX         Integer32
        MAX-ACCESS     read-only
        STATUS         current
        DESCRIPTION    ""
        ::= { tnOpticalPortConfig 189 }

--------------------------------------------------------------------------------
-- 11QPEN4 Optical Port Config Table
--------------------------------------------------------------------------------
    tn11qpen4PortConfigTable OBJECT-TYPE
        SYNTAX         SEQUENCE OF Tn11qpen4PortConfigEntry
        MAX-ACCESS     not-accessible
        STATUS         current
        DESCRIPTION    "The ports on a 11QPEN4 optical card."
        ::= { tnOpticalPortConfig 190 }

    tn11qpen4PortConfigEntry OBJECT-TYPE
        SYNTAX         Tn11qpen4PortConfigEntry
        MAX-ACCESS     not-accessible
        STATUS         current
        DESCRIPTION    ""
        INDEX { ifIndex }
        ::= { tn11qpen4PortConfigTable 1 }

    Tn11qpen4PortConfigEntry ::=
        SEQUENCE {
            tn11qpen4PortConfigFunction                    INTEGER,
            tn11qpen4PortConfigEncryptionOperateKeySwitch  INTEGER,
            tn11qpen4PortConfigEncryptionState             TruthValue,
            tn11qpen4PortConfigEncryptionNextKey           SnmpAdminString,
            tn11qpen4PortConfigEncryptionWKAT              SnmpAdminString
        }

    tn11qpen4PortConfigFunction OBJECT-TYPE
        SYNTAX         INTEGER {
                         network(1),
                         client(2),
                         evoa(3)
                       }
        MAX-ACCESS     read-only
        STATUS         current
        DESCRIPTION    "Indicates the functional type of this 11QPEN4 port."
        ::= { tn11qpen4PortConfigEntry 1 }

    tn11qpen4PortConfigEncryptionOperateKeySwitch OBJECT-TYPE
        SYNTAX         INTEGER {
                         idle(1),
                         swapKeys(2)
                       }
        MAX-ACCESS     read-create
        STATUS         current
        DESCRIPTION    "Request the port to switch to the standby
                        encryption key."
        DEFVAL         { idle }
        ::= { tn11qpen4PortConfigEntry 2 }

    tn11qpen4PortConfigEncryptionState OBJECT-TYPE
        SYNTAX         TruthValue
        MAX-ACCESS     read-create
        STATUS         current
        DESCRIPTION    "Encryption State.
                        true  - on
                        false - off."
        DEFVAL         { false }
        ::= { tn11qpen4PortConfigEntry 3 }

    tn11qpen4PortConfigEncryptionNextKey OBJECT-TYPE
        SYNTAX         SnmpAdminString (SIZE(64))
        MAX-ACCESS     read-create
        STATUS         current
        DESCRIPTION    "The next encryption key to use."
        ::= { tn11qpen4PortConfigEntry 4 }

    tn11qpen4PortConfigEncryptionWKAT OBJECT-TYPE
        SYNTAX         SnmpAdminString (SIZE(0..256))
        MAX-ACCESS     read-create
        STATUS         current
        DESCRIPTION    "The WKAT string used to authenticate the far
                        end and validate the keys are correct."
        DEFVAL         { "" }
        ::= { tn11qpen4PortConfigEntry 5 }

--------------------------------------------------------------------------------
-- 43SCX4E Optical Port Config Scalars
--------------------------------------------------------------------------------
    tn43scx4ePortConfigAttributeTotal OBJECT-TYPE
        SYNTAX         Integer32
        MAX-ACCESS     read-only
        STATUS         current
        DESCRIPTION    ""
        ::= { tnOpticalPortConfig 191 }

--------------------------------------------------------------------------------
-- 43SCX4E Optical Port Config Table
--------------------------------------------------------------------------------
    tn43scx4ePortConfigTable OBJECT-TYPE
        SYNTAX         SEQUENCE OF Tn43scx4ePortConfigEntry
        MAX-ACCESS     not-accessible
        STATUS         current
        DESCRIPTION    "The ports on a 43SCX4E optical card."
        ::= { tnOpticalPortConfig 192 }

    tn43scx4ePortConfigEntry OBJECT-TYPE
        SYNTAX         Tn43scx4ePortConfigEntry
        MAX-ACCESS     not-accessible
        STATUS         current
        DESCRIPTION    ""
        INDEX { ifIndex }
        ::= { tn43scx4ePortConfigTable 1 }

    Tn43scx4ePortConfigEntry ::=
        SEQUENCE {
            tn43scx4ePortConfigFunction INTEGER
        }

    tn43scx4ePortConfigFunction OBJECT-TYPE
        SYNTAX         INTEGER {
                         network(1),
                         client(2)
                       }
        MAX-ACCESS     read-only
        STATUS         current
        DESCRIPTION    "Indicates the functional type of this 43SCX4E port."
        ::= { tn43scx4ePortConfigEntry 1 }

--------------------------------------------------------------------------------
-- 43SCGE1 Optical Port Config Scalars
--------------------------------------------------------------------------------
    tn43scge1PortConfigAttributeTotal OBJECT-TYPE
        SYNTAX         Integer32
        MAX-ACCESS     read-only
        STATUS         current
        DESCRIPTION    ""
        ::= { tnOpticalPortConfig 193 }

--------------------------------------------------------------------------------
-- 43SCGE1 Optical Port Config Table
--------------------------------------------------------------------------------
    tn43scge1PortConfigTable OBJECT-TYPE
        SYNTAX         SEQUENCE OF Tn43scge1PortConfigEntry
        MAX-ACCESS     not-accessible
        STATUS         current
        DESCRIPTION    "The ports on a 43SCGE1 optical card."
        ::= { tnOpticalPortConfig 194 }

    tn43scge1PortConfigEntry OBJECT-TYPE
        SYNTAX         Tn43scge1PortConfigEntry
        MAX-ACCESS     not-accessible
        STATUS         current
        DESCRIPTION    ""
        INDEX { ifIndex }
        ::= { tn43scge1PortConfigTable 1 }

    Tn43scge1PortConfigEntry ::=
        SEQUENCE {
            tn43scge1PortConfigFunction INTEGER
        }

    tn43scge1PortConfigFunction OBJECT-TYPE
        SYNTAX         INTEGER {
                         network(1),
                         client(2)
                       }
        MAX-ACCESS     read-only
        STATUS         current
        DESCRIPTION    "Indicates the functional type of this 43SCGE1 port."
        ::= { tn43scge1PortConfigEntry 1 }

--------------------------------------------------------------------------------
-- 11QPE24 Optical Port Config Scalars
--------------------------------------------------------------------------------
    tn11qpe24PortConfigAttributeTotal OBJECT-TYPE
        SYNTAX         Integer32
        MAX-ACCESS     read-only
        STATUS         current
        DESCRIPTION    ""
        ::= { tnOpticalPortConfig 195 }

--------------------------------------------------------------------------------
-- 11QPE24 Optical Port Config Table
--------------------------------------------------------------------------------
    tn11qpe24PortConfigTable OBJECT-TYPE
        SYNTAX         SEQUENCE OF Tn11qpe24PortConfigEntry
        MAX-ACCESS     not-accessible
        STATUS         current
        DESCRIPTION    "The ports on a 11QPE24 optical card."
        ::= { tnOpticalPortConfig 196 }

    tn11qpe24PortConfigEntry OBJECT-TYPE
        SYNTAX         Tn11qpe24PortConfigEntry
        MAX-ACCESS     not-accessible
        STATUS         current
        DESCRIPTION    ""
        INDEX { ifIndex }
        ::= { tn11qpe24PortConfigTable 1 }

    Tn11qpe24PortConfigEntry ::=
        SEQUENCE {
            tn11qpe24PortConfigFunction INTEGER
        }

    tn11qpe24PortConfigFunction OBJECT-TYPE
        SYNTAX         INTEGER {
                         network(1),
                         client(2),
                         evoa(3)
                       }
        MAX-ACCESS     read-only
        STATUS         current
        DESCRIPTION    "Indicates the functional type of this 11QPE24 port."
        ::= { tn11qpe24PortConfigEntry 1 }

--------------------------------------------------------------------------------
-- 11STAR1A Optical Port Config Scalars
--------------------------------------------------------------------------------
    tn11star1aPortConfigAttributeTotal OBJECT-TYPE
        SYNTAX         Integer32
        MAX-ACCESS     read-only
        STATUS         current
        DESCRIPTION    ""
        ::= { tnOpticalPortConfig 197 }

--------------------------------------------------------------------------------
-- 11STAR1A Optical Port Config Table
--------------------------------------------------------------------------------
    tn11star1aPortConfigTable OBJECT-TYPE
        SYNTAX         SEQUENCE OF Tn11star1aPortConfigEntry
        MAX-ACCESS     not-accessible
        STATUS         current
        DESCRIPTION    "The ports on a 11STAR1A optical card."
        ::= { tnOpticalPortConfig 198 }

    tn11star1aPortConfigEntry OBJECT-TYPE
        SYNTAX         Tn11star1aPortConfigEntry
        MAX-ACCESS     not-accessible
        STATUS         current
        DESCRIPTION    ""
        INDEX { ifIndex }
        ::= { tn11star1aPortConfigTable 1 }

    Tn11star1aPortConfigEntry ::=
        SEQUENCE {
            tn11star1aPortConfigFunction INTEGER
        }

    tn11star1aPortConfigFunction OBJECT-TYPE
        SYNTAX         INTEGER {
                         network(1),
                         client(2)
                       }
        MAX-ACCESS     read-only
        STATUS         current
        DESCRIPTION    "Indicates the functional type of this 11STAR1A port."
        ::= { tn11star1aPortConfigEntry 1 }

--------------------------------------------------------------------------------
-- MVAC8B Optical Port Config Scalars
--------------------------------------------------------------------------------
    tnMvac8bPortConfigAttributeTotal OBJECT-TYPE
        SYNTAX         Integer32
        MAX-ACCESS     read-only
        STATUS         current
        DESCRIPTION    ""
        ::= { tnOpticalPortConfig 199 }

--------------------------------------------------------------------------------
-- MVAC8B Optical Port Config Table
--------------------------------------------------------------------------------
    tnMvac8bPortConfigTable OBJECT-TYPE
        SYNTAX         SEQUENCE OF TnMvac8bPortConfigEntry
        MAX-ACCESS     not-accessible
        STATUS         current
        DESCRIPTION    "The ports on a MVAC8B optical card."
        ::= { tnOpticalPortConfig 200 }

    tnMvac8bPortConfigEntry OBJECT-TYPE
        SYNTAX         TnMvac8bPortConfigEntry
        MAX-ACCESS     not-accessible
        STATUS         current
        DESCRIPTION    ""
        INDEX { ifIndex }
        ::= { tnMvac8bPortConfigTable 1 }

    TnMvac8bPortConfigEntry ::=
        SEQUENCE {
            tnMvac8bPortConfigFunction INTEGER
        }

    tnMvac8bPortConfigFunction OBJECT-TYPE
        SYNTAX         INTEGER {
                         network(1),
                         client(2)
                       }
        MAX-ACCESS     read-only
        STATUS         current
        DESCRIPTION    "Indicates the functional type of this MVAC8B port."
        ::= { tnMvac8bPortConfigEntry 1 }

--------------------------------------------------------------------------------
-- WSS Channel Attenuation Config Scalars
--------------------------------------------------------------------------------
    tnWssAttenPortConfigAttributeTotal OBJECT-TYPE
        SYNTAX         Integer32
        MAX-ACCESS     read-only
        STATUS         current
        DESCRIPTION    ""
        ::= { tnOpticalPortConfig 201 }

--------------------------------------------------------------------------------
-- WSS Channel Attenuation Config Table
--------------------------------------------------------------------------------
    tnWssAttenPortConfigTable OBJECT-TYPE
        SYNTAX         SEQUENCE OF TnWssAttenPortConfigEntry
        MAX-ACCESS     not-accessible
        STATUS         current
        DESCRIPTION    "Through this table, a network operator may set
                        the WSS attenuation."
        ::= { tnOpticalPortConfig 202 }

    tnWssAttenPortConfigEntry OBJECT-TYPE
        SYNTAX         TnWssAttenPortConfigEntry
        MAX-ACCESS     not-accessible
        STATUS         current
        DESCRIPTION    ""
        INDEX { ifIndex,
                tnChannel }
        ::= { tnWssAttenPortConfigTable 1 }

    TnWssAttenPortConfigEntry ::=
        SEQUENCE {
            tnWssAttenPortConfigWssAtten   Unsigned32
        }

    tnWssAttenPortConfigWssAtten OBJECT-TYPE
        SYNTAX         Unsigned32
        UNITS          "mB"
        MAX-ACCESS     read-create
        STATUS         current
        DESCRIPTION    "The attenuation, expressed in units of mB, is
                        associated with the WSS channel attenuation.
                        This attributes pplies to the following ports:

                        CWR8:     THRU and CLS ports
                        CWR8-88:  THRU and CLS ports
                        WR8-88A:  SIG port
                        WR8-88AF: SIG port
                        WR2-88:   SIG port
                        WR20-TF:  SIG, ADT, and AD ports
                        WR20-TFM: SIG, ADT, and AD ports

                        Current configurable range: 0 to 1500."
        DEFVAL         { 1500 }
        ::= { tnWssAttenPortConfigEntry 1 }

--------------------------------------------------------------------------------
-- WR8-88AF Optical Port Config Scalars
--------------------------------------------------------------------------------
    tnWr8c88afPortConfigAttributeTotal OBJECT-TYPE
        SYNTAX         Integer32
        MAX-ACCESS     read-only
        STATUS         current
        DESCRIPTION    ""
        ::= { tnOpticalPortConfig 203 }

--------------------------------------------------------------------------------
-- WR8-88AF Optical Port Config Table
--------------------------------------------------------------------------------
    tnWr8c88afPortConfigTable OBJECT-TYPE
        SYNTAX         SEQUENCE OF TnWr8c88afPortConfigEntry
        MAX-ACCESS     not-accessible
        STATUS         current
        DESCRIPTION    "The ports on a WR8-88AF optical card."
        ::= { tnOpticalPortConfig 204 }

    tnWr8c88afPortConfigEntry OBJECT-TYPE
        SYNTAX         TnWr8c88afPortConfigEntry
        MAX-ACCESS     not-accessible
        STATUS         current
        DESCRIPTION    ""
        INDEX { ifIndex }
        ::= { tnWr8c88afPortConfigTable 1 }

    TnWr8c88afPortConfigEntry ::=
        SEQUENCE {
            tnWr8c88afPortConfigFunction  INTEGER
        }

    tnWr8c88afPortConfigFunction OBJECT-TYPE
        SYNTAX         INTEGER {
                         signal(1),
                         thru(2),
                         dropOut(3),
                         addIn(4),
                         meshOut(5),
                         inv(6)
                       }
        MAX-ACCESS     read-only
        STATUS         current
        DESCRIPTION    "Indicates the functional type of this WR8-88AF port."
        ::= { tnWr8c88afPortConfigEntry 1 }

--------------------------------------------------------------------------------
-- 10AN10G Optical Port Config Scalars
--------------------------------------------------------------------------------
    tncl10an10gPortConfigAttributeTotal OBJECT-TYPE
        SYNTAX         Integer32
        MAX-ACCESS     read-only
        STATUS         current
        DESCRIPTION    ""
        ::= { tnOpticalPortConfig 205 }

--------------------------------------------------------------------------------
-- 10AN10G Optical Port Config Table
--------------------------------------------------------------------------------
    tncl10an10gPortConfigTable OBJECT-TYPE
        SYNTAX         SEQUENCE OF Tncl10an10gPortConfigEntry
        MAX-ACCESS     not-accessible
        STATUS         current
        DESCRIPTION    "The ports on a 10AN10G optical card."
        ::= { tnOpticalPortConfig 206 }

    tncl10an10gPortConfigEntry OBJECT-TYPE
        SYNTAX         Tncl10an10gPortConfigEntry
        MAX-ACCESS     not-accessible
        STATUS         current
        DESCRIPTION    ""
        INDEX { ifIndex }
        ::= { tncl10an10gPortConfigTable 1 }

    Tncl10an10gPortConfigEntry ::=
        SEQUENCE {
            tncl10an10gPortConfigFunction INTEGER
        }

    tncl10an10gPortConfigFunction OBJECT-TYPE
        SYNTAX         INTEGER {
                         network(1),
                         client(2)
                       }
        MAX-ACCESS     read-only
        STATUS         current
        DESCRIPTION    "Indicates the functional type of this 10AN10G port."
        ::= { tncl10an10gPortConfigEntry 1 }

--------------------------------------------------------------------------------
-- 24ANM Optical Port Config Scalars
--------------------------------------------------------------------------------
    tncl24anmPortConfigAttributeTotal OBJECT-TYPE
        SYNTAX         Integer32
        MAX-ACCESS     read-only
        STATUS         current
        DESCRIPTION    ""
        ::= { tnOpticalPortConfig 207 }

--------------------------------------------------------------------------------
-- 24ANM Optical Port Config Table
--------------------------------------------------------------------------------
    tncl24anmPortConfigTable OBJECT-TYPE
        SYNTAX         SEQUENCE OF Tncl24anmPortConfigEntry
        MAX-ACCESS     not-accessible
        STATUS         current
        DESCRIPTION    "The ports on a 24ANM optical card."
        ::= { tnOpticalPortConfig 208 }

    tncl24anmPortConfigEntry OBJECT-TYPE
        SYNTAX         Tncl24anmPortConfigEntry
        MAX-ACCESS     not-accessible
        STATUS         current
        DESCRIPTION    ""
        INDEX { ifIndex }
        ::= { tncl24anmPortConfigTable 1 }

    Tncl24anmPortConfigEntry ::=
        SEQUENCE {
            tncl24anmPortConfigFunction INTEGER
        }

    tncl24anmPortConfigFunction OBJECT-TYPE
        SYNTAX         INTEGER {
                         network(1),
                         client(2)
                       }
        MAX-ACCESS     read-only
        STATUS         current
        DESCRIPTION    "Indicates the functional type of this 24ANM port."
        ::= { tncl24anmPortConfigEntry 1 }

--------------------------------------------------------------------------------
-- OPSB Optical Port Config Scalars
--------------------------------------------------------------------------------
    tnOpsbPortConfigAttributeTotal OBJECT-TYPE
        SYNTAX         Integer32
        MAX-ACCESS     read-only
        STATUS         current
        DESCRIPTION    ""
        ::= { tnOpticalPortConfig 209 }

--------------------------------------------------------------------------------
-- OPSB Optical Port Config Table
--------------------------------------------------------------------------------
    tnOpsbPortConfigTable OBJECT-TYPE
        SYNTAX         SEQUENCE OF TnOpsbPortConfigEntry
        MAX-ACCESS     not-accessible
        STATUS         current
        DESCRIPTION    "The ports on an OPSB optical card."
        ::= { tnOpticalPortConfig 210 }

    tnOpsbPortConfigEntry OBJECT-TYPE
        SYNTAX         TnOpsbPortConfigEntry
        MAX-ACCESS     not-accessible
        STATUS         current
        DESCRIPTION    ""
        INDEX { ifIndex }
        ::= { tnOpsbPortConfigTable 1 }

    TnOpsbPortConfigEntry ::=
        SEQUENCE {
            tnOpsbPortConfigFunction     INTEGER
        }

    tnOpsbPortConfigFunction OBJECT-TYPE
        SYNTAX         INTEGER {
                         signal(1),
                         workingProtected(2)
                       }
        MAX-ACCESS     read-only
        STATUS         current
        DESCRIPTION    "Indicates the functional type of this OPSB port."
        ::= { tnOpsbPortConfigEntry 1 }

--------------------------------------------------------------------------------
-- OPS Optical Port Config Scalars
--------------------------------------------------------------------------------
    tnOpsPortConfigAttributeTotal OBJECT-TYPE
        SYNTAX         Integer32
        MAX-ACCESS     read-only
        STATUS         current
        DESCRIPTION    ""
        ::= { tnOpticalPortConfig 211 }

--------------------------------------------------------------------------------
-- OPS Optical Port Config Table
--------------------------------------------------------------------------------
    tnOpsPortConfigTable OBJECT-TYPE
        SYNTAX         SEQUENCE OF TnOpsPortConfigEntry
        MAX-ACCESS     not-accessible
        STATUS         current
        DESCRIPTION    "The attributes for an OPS optical card."
        ::= { tnOpticalPortConfig 212 }

    tnOpsPortConfigEntry OBJECT-TYPE
        SYNTAX         TnOpsPortConfigEntry
        MAX-ACCESS     not-accessible
        STATUS         current
        DESCRIPTION    ""
        INDEX { ifIndex }
        ::= { tnOpsPortConfigTable 1 }

    TnOpsPortConfigEntry ::=
        SEQUENCE {
            tnOpsPortConfigSwitchingThreshold              Integer32,
            tnOpsPortConfigSwitchingThresholdTolerance     Unsigned32,
            tnOpsPortConfigTransmitAttenuation             Integer32,
            tnOpsPortConfigSwitchingThreshCalcControl      INTEGER
        }

    tnOpsPortConfigSwitchingThreshold OBJECT-TYPE
        SYNTAX         Integer32
        UNITS          "mBm"
        MAX-ACCESS     read-create
        STATUS         current
        DESCRIPTION    "If the power drops below this threshold, a
                        protection switch will be executed.  This is
                        accessible from ports 2 and 3 (working or
                        protected) exclusively.  This command applies
                        to ports A and B only.  Default is -3000 for
                        OCH protection, -2800 for OMS protection, and
                        -3200 for OLP protection.

                        Current configurable ranges and defaults:

                        OLP (OPSA):       (-3200..500), -3000
                        OCH/OMSP (OPSB):  (-3000..500), -1000."
        ::= { tnOpsPortConfigEntry 1 }

    tnOpsPortConfigSwitchingThresholdTolerance OBJECT-TYPE
        SYNTAX         Unsigned32
        UNITS          "mB"
        MAX-ACCESS     read-create
        STATUS         current
        DESCRIPTION    "The tolerance applied to the port switching
                        threshold.  This is accessible from ports 2 and
                        3 (working or protected) exclusively.

                        Current configurable range: 0 to 500."
        DEFVAL         { 200 }
        ::= { tnOpsPortConfigEntry 2 }

    tnOpsPortConfigTransmitAttenuation OBJECT-TYPE
        SYNTAX         Integer32
        UNITS          "mB"
        MAX-ACCESS     read-create
        STATUS         current
        DESCRIPTION    "The attenuation of the attenuator - applies to
                        ports 2 and 3 (A and B) of the OPS optical card.

                        Current configurable range: -1 to 2000.
                        -1 means that max attenuation is applied."
        DEFVAL         { -1 }
        ::= { tnOpsPortConfigEntry 3 }

    tnOpsPortConfigSwitchingThreshCalcControl OBJECT-TYPE
        SYNTAX         INTEGER {
                         auto(1),
                         manual(2)
                       }
        MAX-ACCESS     read-create
        STATUS         current
        DESCRIPTION    "Indicates if the OPS switch threshold is
                        calculated by the NE (auto) or set by the user
                        (manual) - applies to ports 2 and 3 (A and B)
                        of the OPS card.  Default is auto for OPSA and
                        manual for OPSB."
        ::= { tnOpsPortConfigEntry 4 }

--------------------------------------------------------------------------------
-- 11DPE12A Optical Port Config Scalars
--------------------------------------------------------------------------------
    tn11dpe12aPortConfigAttributeTotal OBJECT-TYPE
        SYNTAX         Integer32
        MAX-ACCESS     read-only
        STATUS         current
        DESCRIPTION    ""
        ::= { tnOpticalPortConfig 213 }

--------------------------------------------------------------------------------
-- 11DPE12A Optical Port Config Table
--------------------------------------------------------------------------------
    tn11dpe12aPortConfigTable OBJECT-TYPE
        SYNTAX         SEQUENCE OF Tn11dpe12aPortConfigEntry
        MAX-ACCESS     not-accessible
        STATUS         current
        DESCRIPTION    "The ports on a 11DPE12A optical card."
        ::= { tnOpticalPortConfig 214 }

    tn11dpe12aPortConfigEntry OBJECT-TYPE
        SYNTAX         Tn11dpe12aPortConfigEntry
        MAX-ACCESS     not-accessible
        STATUS         current
        DESCRIPTION    ""
        INDEX { ifIndex }
        ::= { tn11dpe12aPortConfigTable 1 }

    Tn11dpe12aPortConfigEntry ::=
        SEQUENCE {
            tn11dpe12aPortConfigFunction              INTEGER,
            tn11dpe12aPortConfigQinQModeTPID          INTEGER,
            tn11dpe12aPortConfigQinQModePVID          Unsigned32,
            tn11dpe12aPortConfigLPTConsequenceAction  INTEGER,
            tn11dpe12aPortConfigMtu                   Integer32,
            tn11dpe12aPortConfigPortRole              INTEGER,
            tn11dpe12aPortConfigPtpTrans              INTEGER,
            tn11dpe12aPortConfigCompatibilityMode     INTEGER,
            tn11dpe12aPortConfigFlowControl           AluWdmEnabledDisabled
        }

    tn11dpe12aPortConfigFunction OBJECT-TYPE
        SYNTAX         INTEGER {
                         network(1),
                         client(2),
                         evoa(3),
                         backplane(4),
                         tod(5),
                         bits(6)
                       }
        MAX-ACCESS     read-only
        STATUS         current
        DESCRIPTION    "Indicates the functional type of this 11DPE12A port."
        ::= { tn11dpe12aPortConfigEntry 1 }

    tn11dpe12aPortConfigQinQModeTPID OBJECT-TYPE
        SYNTAX         INTEGER {
                         qinqtpid1(1),
                         qinqtpid2(2),
                         qinqtpid3(3),
                         qinqtpid4(4)
                       }
        MAX-ACCESS     read-create
        STATUS         current
        DESCRIPTION    "The QinQ mode TPID for 11dpe12a port."
        DEFVAL         { qinqtpid1 }
        ::= { tn11dpe12aPortConfigEntry 2 }

    tn11dpe12aPortConfigQinQModePVID OBJECT-TYPE
        SYNTAX         Unsigned32
        MAX-ACCESS     read-create
        STATUS         current
        DESCRIPTION    "The PVID for 11dpe12a port.

                        Current configurable range: 0 to 0x0FFE."
        DEFVAL         { 0 }
        ::= { tn11dpe12aPortConfigEntry 3 }

    tn11dpe12aPortConfigLPTConsequenceAction OBJECT-TYPE
        SYNTAX         INTEGER {
                         noAction(1),
                         oneShutDown(2),
                         allShutDown(3)
                       }
        MAX-ACCESS     read-create
        STATUS         current
        DESCRIPTION    "Indicates the 11dpe12a port LPT ConsequenceAction."
        DEFVAL         { noAction }
        ::= { tn11dpe12aPortConfigEntry 4 }

    tn11dpe12aPortConfigMtu OBJECT-TYPE
        SYNTAX         Integer32
        MAX-ACCESS     read-create
        STATUS         current
        DESCRIPTION    "The MTU size for 11dpe12a client interface.

                        Current configurable range: 1518 to 9600."
        DEFVAL         { 9600 }
        ::= { tn11dpe12aPortConfigEntry 5 }

    tn11dpe12aPortConfigPortRole OBJECT-TYPE
        SYNTAX         INTEGER {
                         uni(1),
                         nni(2)
                       }
        MAX-ACCESS     read-create
        STATUS         current
        DESCRIPTION    "The role for an 11dpe12a port:
                        uni - the port acts like a client port.
                        nni - the port acts like a line port."
        DEFVAL         { nni }
        ::= { tn11dpe12aPortConfigEntry 6 }

    tn11dpe12aPortConfigPtpTrans OBJECT-TYPE
        SYNTAX         INTEGER {
                         inPayload(1),
                         inOverhead(2)
                       }
        MAX-ACCESS     read-create
        STATUS         current
        DESCRIPTION    "Specifies how to transport the ptp packets.  This
                        attribute is valid for the OTU2 line ports only."
        DEFVAL         { inPayload }
        ::= { tn11dpe12aPortConfigEntry 7 }

    tn11dpe12aPortConfigCompatibilityMode OBJECT-TYPE
        SYNTAX         INTEGER {
                         default(1),
                         intMode11dpe12(2)
                       }
        MAX-ACCESS     read-create
        STATUS         current
        DESCRIPTION    "This parameter is used to set the compatible
                        mode of the OTU2 port.

                          default:        The port operates in the default
                                          mode which is supported by all
                                          12xGE cards except the 11DPE12.
                          intMode11dpe12: The port operates in the 11DPE12
                                          interworking mode."
        DEFVAL         { default }
        ::= { tn11dpe12aPortConfigEntry 8 }

    tn11dpe12aPortConfigFlowControl OBJECT-TYPE
        SYNTAX         AluWdmEnabledDisabled
        MAX-ACCESS     read-create
        STATUS         current
        DESCRIPTION    "The attribute is used to enable/disable flow
                        control (PAUSE frame processing) on the port."
        DEFVAL         { enabled }
        ::= { tn11dpe12aPortConfigEntry 9 }

--------------------------------------------------------------------------------
-- UL130SCUP Optical Port Config Scalars
--------------------------------------------------------------------------------
    tnul130scupPortConfigAttributeTotal OBJECT-TYPE
        SYNTAX         Integer32
        MAX-ACCESS     read-only
        STATUS         current
        DESCRIPTION    ""
        ::= { tnOpticalPortConfig 215 }

--------------------------------------------------------------------------------
-- UL130SCUP Optical Port Config Table
--------------------------------------------------------------------------------
    tnul130scupPortConfigTable OBJECT-TYPE
        SYNTAX         SEQUENCE OF Tnul130scupPortConfigEntry
        MAX-ACCESS     not-accessible
        STATUS         current
        DESCRIPTION    "The ports on a UL130SCUP optical card."
        ::= { tnOpticalPortConfig 216 }

    tnul130scupPortConfigEntry OBJECT-TYPE
        SYNTAX         Tnul130scupPortConfigEntry
        MAX-ACCESS     not-accessible
        STATUS         current
        DESCRIPTION    ""
        INDEX { ifIndex }
        ::= { tnul130scupPortConfigTable 1 }

    Tnul130scupPortConfigEntry ::=
        SEQUENCE {
            tnul130scupPortConfigFunction  INTEGER
        }

    tnul130scupPortConfigFunction OBJECT-TYPE
        SYNTAX         INTEGER {
                         network(1)
                       }
        MAX-ACCESS     read-only
        STATUS         current
        DESCRIPTION    "Indicates the functional type of this UL130SCUP port."
        ::= { tnul130scupPortConfigEntry 1 }

--------------------------------------------------------------------------------
-- 130SCX10 Optical Port Config Scalars
--------------------------------------------------------------------------------
    tn130scx10PortConfigAttributeTotal OBJECT-TYPE
        SYNTAX         Integer32
        MAX-ACCESS     read-only
        STATUS         current
        DESCRIPTION    ""
        ::= { tnOpticalPortConfig 217 }

--------------------------------------------------------------------------------
-- 130SCX10 Optical Port Config Table
--------------------------------------------------------------------------------
    tn130scx10PortConfigTable OBJECT-TYPE
        SYNTAX         SEQUENCE OF Tn130scx10PortConfigEntry
        MAX-ACCESS     not-accessible
        STATUS         current
        DESCRIPTION    "The ports on a 130SCX10 optical card."
        ::= { tnOpticalPortConfig 218 }

    tn130scx10PortConfigEntry OBJECT-TYPE
        SYNTAX         Tn130scx10PortConfigEntry
        MAX-ACCESS     not-accessible
        STATUS         current
        DESCRIPTION    ""
        INDEX { ifIndex }
        ::= { tn130scx10PortConfigTable 1 }

    Tn130scx10PortConfigEntry ::=
        SEQUENCE {
            tn130scx10PortConfigFunction  INTEGER
        }

    tn130scx10PortConfigFunction OBJECT-TYPE
        SYNTAX         INTEGER {
                         network(1),
                         client(2)
                       }
        MAX-ACCESS     read-only
        STATUS         current
        DESCRIPTION    "Indicates the functional type of this 130SCX10 port."
        ::= { tn130scx10PortConfigEntry 1 }

--------------------------------------------------------------------------------
-- A2P2125 Optical Port Config Scalars
--------------------------------------------------------------------------------
    tnA2p2125PortConfigAttributeTotal OBJECT-TYPE
        SYNTAX         Integer32
        MAX-ACCESS     read-only
        STATUS         current
        DESCRIPTION    ""
        ::= { tnOpticalPortConfig 219 }

--------------------------------------------------------------------------------
-- A2P2125 Optical Port Config Table
--------------------------------------------------------------------------------
    tnA2p2125PortConfigTable OBJECT-TYPE
        SYNTAX         SEQUENCE OF TnA2p2125PortConfigEntry
        MAX-ACCESS     not-accessible
        STATUS         current
        DESCRIPTION    "The ports on a A2P2125 optical card."
        ::= { tnOpticalPortConfig 220 }

    tnA2p2125PortConfigEntry OBJECT-TYPE
        SYNTAX         TnA2p2125PortConfigEntry
        MAX-ACCESS     not-accessible
        STATUS         current
        DESCRIPTION    ""
        INDEX { ifIndex }
        ::= { tnA2p2125PortConfigTable 1 }

    TnA2p2125PortConfigEntry ::=
        SEQUENCE {
            tnA2p2125PortConfigFunction  INTEGER
        }

    tnA2p2125PortConfigFunction OBJECT-TYPE
        SYNTAX         INTEGER {
                         lineIn(1),
                         inv(2),
                         dcm(3),
                         lineOut(4),
                         oscSfp(5),
                         osc(6)
                       }
        MAX-ACCESS     read-only
        STATUS         current
        DESCRIPTION    "Indicates the functional type of this A2P2125 port."
        ::= { tnA2p2125PortConfigEntry 1 }

--------------------------------------------------------------------------------
-- 4QPA8 Optical Port Config Scalars
--------------------------------------------------------------------------------
    tn4qpa8PortConfigAttributeTotal OBJECT-TYPE
        SYNTAX         Integer32
        MAX-ACCESS     read-only
        STATUS         current
        DESCRIPTION    ""
        ::= { tnOpticalPortConfig 221 }

--------------------------------------------------------------------------------
-- 4QPA8 Optical Port Config Table
--------------------------------------------------------------------------------
    tn4qpa8PortConfigTable OBJECT-TYPE
        SYNTAX         SEQUENCE OF Tn4qpa8PortConfigEntry
        MAX-ACCESS     not-accessible
        STATUS         current
        DESCRIPTION    "The ports on a 4QPA8 optical card."
        ::= { tnOpticalPortConfig 222 }

    tn4qpa8PortConfigEntry OBJECT-TYPE
        SYNTAX         Tn4qpa8PortConfigEntry
        MAX-ACCESS     not-accessible
        STATUS         current
        DESCRIPTION    ""
        INDEX { ifIndex }
        ::= { tn4qpa8PortConfigTable 1 }

    Tn4qpa8PortConfigEntry ::=
        SEQUENCE {
            tn4qpa8PortConfigFunction    INTEGER,
            tn4qpa8PortConfigTtpPresent  TruthValue
        }

    tn4qpa8PortConfigFunction OBJECT-TYPE
        SYNTAX         INTEGER {
                         network(1),
                         client(2),
                         evoa(3)
                       }
        MAX-ACCESS     read-only
        STATUS         current
        DESCRIPTION    "Indicates the functional type of this 4QPA8 port."
        ::= { tn4qpa8PortConfigEntry 1 }

    tn4qpa8PortConfigTtpPresent OBJECT-TYPE
        SYNTAX         TruthValue
        MAX-ACCESS     read-create
        STATUS         current
        DESCRIPTION    "Ttp present:
                        true  - TP facility is present
                        false - NIM facility is present."
        DEFVAL         { false }
        ::= { tn4qpa8PortConfigEntry 2 }

--------------------------------------------------------------------------------
-- 112PDM11 Optical Port Config Scalars
--------------------------------------------------------------------------------
    tnOt112pdm11PortConfigAttributeTotal OBJECT-TYPE
        SYNTAX         Integer32
        MAX-ACCESS     read-only
        STATUS         current
        DESCRIPTION    ""
        ::= { tnOpticalPortConfig 223 }

--------------------------------------------------------------------------------
-- 112PDM11 Optical Port Config Table
--------------------------------------------------------------------------------
    tnOt112pdm11PortConfigTable OBJECT-TYPE
        SYNTAX         SEQUENCE OF TnOt112pdm11PortConfigEntry
        MAX-ACCESS     not-accessible
        STATUS         current
        DESCRIPTION    "The ports on a 112PDM11 optical card."
        ::= { tnOpticalPortConfig 224 }

    tnOt112pdm11PortConfigEntry OBJECT-TYPE
        SYNTAX         TnOt112pdm11PortConfigEntry
        MAX-ACCESS     not-accessible
        STATUS         current
        DESCRIPTION    ""
        INDEX { ifIndex }
        ::= { tnOt112pdm11PortConfigTable 1 }

    TnOt112pdm11PortConfigEntry ::=
        SEQUENCE {
            tnOt112pdm11PortConfigFunction  INTEGER
        }

    tnOt112pdm11PortConfigFunction OBJECT-TYPE
        SYNTAX         INTEGER {
                         network(1),
                         client(2)
                       }
        MAX-ACCESS     read-only
        STATUS         current
        DESCRIPTION    "Indicates the functional type of this 112PDM11 port."
        ::= { tnOt112pdm11PortConfigEntry 1 }

--------------------------------------------------------------------------------
-- WTOCMA Optical Port Config Scalars
--------------------------------------------------------------------------------
    tnWtocmaPortConfigAttributeTotal OBJECT-TYPE
        SYNTAX         Integer32
        MAX-ACCESS     read-only
        STATUS         current
        DESCRIPTION    ""
        ::= { tnOpticalPortConfig 225 }

--------------------------------------------------------------------------------
-- WTOCMA Optical Port Config Table
--------------------------------------------------------------------------------
    tnWtocmaPortConfigTable OBJECT-TYPE
        SYNTAX         SEQUENCE OF TnWtocmaPortConfigEntry
        MAX-ACCESS     not-accessible
        STATUS         current
        DESCRIPTION    "The ports on a WTOCMA optical card."
        ::= { tnOpticalPortConfig 226 }

    tnWtocmaPortConfigEntry OBJECT-TYPE
        SYNTAX         TnWtocmaPortConfigEntry
        MAX-ACCESS     not-accessible
        STATUS         current
        DESCRIPTION    ""
        INDEX { ifIndex }
        ::= { tnWtocmaPortConfigTable 1 }

    TnWtocmaPortConfigEntry ::=
        SEQUENCE {
            tnWtocmaPortConfigFunction     INTEGER,
            tnWtocmaPortConfigOsnrMeasure  TruthValue,
            tnWtocmaPortConfigOsnrClear    TnCommand
        }

    tnWtocmaPortConfigFunction OBJECT-TYPE
        SYNTAX         INTEGER {
                         detect(1)
                       }
        MAX-ACCESS     read-only
        STATUS         current
        DESCRIPTION    "Indicates the functional type of this WTOCMA port."
        ::= { tnWtocmaPortConfigEntry 1 }

    tnWtocmaPortConfigOsnrMeasure OBJECT-TYPE
        SYNTAX         TruthValue
        MAX-ACCESS     read-create
        STATUS         current
        DESCRIPTION    "Turn OFF/ON OSNR scan."
        DEFVAL         { false }
        ::= { tnWtocmaPortConfigEntry 2 }

    tnWtocmaPortConfigOsnrClear OBJECT-TYPE
        SYNTAX         TnCommand
        MAX-ACCESS     read-create
        STATUS         current
        DESCRIPTION    "This attribute is used to clear OSNR value for
                        all the channels on the specified port."
        DEFVAL         { noCmd }
        ::= { tnWtocmaPortConfigEntry 3 }

--------------------------------------------------------------------------------
-- PTPCTL Optical Port Config Scalars
--------------------------------------------------------------------------------
    tnPtpctlPortConfigAttributeTotal OBJECT-TYPE
        SYNTAX         Integer32
        MAX-ACCESS     read-only
        STATUS         current
        DESCRIPTION    ""
        ::= { tnOpticalPortConfig 227 }

--------------------------------------------------------------------------------
-- PTPCTL Optical Port Config Table
--------------------------------------------------------------------------------
    tnPtpctlPortConfigTable OBJECT-TYPE
        SYNTAX         SEQUENCE OF TnPtpctlPortConfigEntry
        MAX-ACCESS     not-accessible
        STATUS         current
        DESCRIPTION    "The ports on a PTPCTL optical card."
        ::= { tnOpticalPortConfig 228 }

    tnPtpctlPortConfigEntry OBJECT-TYPE
        SYNTAX         TnPtpctlPortConfigEntry
        MAX-ACCESS     not-accessible
        STATUS         current
        DESCRIPTION    ""
        INDEX { ifIndex }
        ::= { tnPtpctlPortConfigTable 1 }

    TnPtpctlPortConfigEntry ::=
        SEQUENCE {
            tnPtpctlPortConfigFunction  INTEGER
        }

    tnPtpctlPortConfigFunction OBJECT-TYPE
        SYNTAX         INTEGER {
                         tp(1),
                         bits(2),
                         tod(3)
                       }
        MAX-ACCESS     read-only
        STATUS         current
        DESCRIPTION    "Indicates the functional type of this PTPCTL port."
        ::= { tnPtpctlPortConfigEntry 1 }

--------------------------------------------------------------------------------
-- PTPIO Optical Port Config Scalars
--------------------------------------------------------------------------------
    tnPtpioPortConfigAttributeTotal OBJECT-TYPE
        SYNTAX         Integer32
        MAX-ACCESS     read-only
        STATUS         current
        DESCRIPTION    ""
        ::= { tnOpticalPortConfig 229 }

--------------------------------------------------------------------------------
-- PTPIO Optical Port Config Table
--------------------------------------------------------------------------------
    tnPtpioPortConfigTable OBJECT-TYPE
        SYNTAX         SEQUENCE OF TnPtpioPortConfigEntry
        MAX-ACCESS     not-accessible
        STATUS         current
        DESCRIPTION    "The ports on a PTPIO optical card."
        ::= { tnOpticalPortConfig 230 }

    tnPtpioPortConfigEntry OBJECT-TYPE
        SYNTAX         TnPtpioPortConfigEntry
        MAX-ACCESS     not-accessible
        STATUS         current
        DESCRIPTION    ""
        INDEX { ifIndex }
        ::= { tnPtpioPortConfigTable 1 }

    TnPtpioPortConfigEntry ::=
        SEQUENCE {
            tnPtpioPortConfigFunction             INTEGER,
            tnPtpioPortConfigSigPortConnFromPort  InterfaceIndexOrZero,
            tnPtpioPortConfigSigPortConnToPort    InterfaceIndexOrZero
        }

    tnPtpioPortConfigFunction OBJECT-TYPE
        SYNTAX         INTEGER {
                         tp(1),
                         line(2),
                         sig(3),
                         itp(4)
                       }
        MAX-ACCESS     read-only
        STATUS         current
        DESCRIPTION    "Indicates the functional type of this PTPIO port."
        ::= { tnPtpioPortConfigEntry 1 }

    tnPtpioPortConfigSigPortConnFromPort OBJECT-TYPE
        SYNTAX         InterfaceIndexOrZero
        MAX-ACCESS     read-create
        STATUS         current
        DESCRIPTION    "The line port that is connected to the PTPIO SIG
                        port in the receive direction."
        DEFVAL         { 0 }
        ::= { tnPtpioPortConfigEntry 2 }

    tnPtpioPortConfigSigPortConnToPort OBJECT-TYPE
        SYNTAX         InterfaceIndexOrZero
        MAX-ACCESS     read-create
        STATUS         current
        DESCRIPTION    "The line port that is connected to the PTPIO SIG
                        port in the transmit direction."
        DEFVAL         { 0 }
        ::= { tnPtpioPortConfigEntry 3 }

--------------------------------------------------------------------------------
-- 24ET1GB Optical Port Config Scalars
--------------------------------------------------------------------------------
    tnIo24et1gbPortConfigAttributeTotal OBJECT-TYPE
        SYNTAX         Integer32
        MAX-ACCESS     read-only
        STATUS         current
        DESCRIPTION    ""
        ::= { tnOpticalPortConfig 231 }

--------------------------------------------------------------------------------
-- 24ET1GB Optical Port Config Table
--------------------------------------------------------------------------------
    tnIo24et1gbPortConfigTable OBJECT-TYPE
        SYNTAX         SEQUENCE OF TnIo24et1gbPortConfigEntry
        MAX-ACCESS     not-accessible
        STATUS         current
        DESCRIPTION    "The ports on a 24ET1GB optical card."
        ::= { tnOpticalPortConfig 232 }

    tnIo24et1gbPortConfigEntry OBJECT-TYPE
        SYNTAX         TnIo24et1gbPortConfigEntry
        MAX-ACCESS     not-accessible
        STATUS         current
        DESCRIPTION    ""
        INDEX { ifIndex }
        ::= { tnIo24et1gbPortConfigTable 1 }

    TnIo24et1gbPortConfigEntry ::=
        SEQUENCE {
            tnIo24et1gbPortConfigFunction  INTEGER
        }

    tnIo24et1gbPortConfigFunction OBJECT-TYPE
        SYNTAX         INTEGER {
                         network(1),
                         client(2)
                       }
        MAX-ACCESS     read-only
        STATUS         current
        DESCRIPTION    "Indicates the functional type of this 24ET1GB port."
        ::= { tnIo24et1gbPortConfigEntry 1 }

--------------------------------------------------------------------------------
-- DWDM IO Optical Port Config Scalars
--------------------------------------------------------------------------------
    tnDwdmIoPortConfigAttributeTotal OBJECT-TYPE
        SYNTAX         Integer32
        MAX-ACCESS     read-only
        STATUS         current
        DESCRIPTION    ""
        ::= { tnOpticalPortConfig 233 }

--------------------------------------------------------------------------------
-- DWDM IO Optical Port Config Table
--------------------------------------------------------------------------------
    tnDwdmIoPortConfigTable OBJECT-TYPE
        SYNTAX         SEQUENCE OF TnDwdmIoPortConfigEntry
        MAX-ACCESS     not-accessible
        STATUS         current
        DESCRIPTION    "The attributes for an optical port."
        ::= { tnOpticalPortConfig 234 }

    tnDwdmIoPortConfigEntry OBJECT-TYPE
        SYNTAX         TnDwdmIoPortConfigEntry
        MAX-ACCESS     not-accessible
        STATUS         current
        DESCRIPTION    ""
        INDEX { ifIndex }
        ::= { tnDwdmIoPortConfigTable 1 }

    TnDwdmIoPortConfigEntry ::=
        SEQUENCE {
            tnDwdmIoPortRole  INTEGER
        }

    tnDwdmIoPortRole OBJECT-TYPE
        SYNTAX         INTEGER {
                         line(1),
                         client(2)
                       }
        MAX-ACCESS     read-create
        STATUS         current
        DESCRIPTION    "Indicates if this port is line or client."
        DEFVAL         { client }
        ::= { tnDwdmIoPortConfigEntry 1 }

--------------------------------------------------------------------------------
-- 4AN10G Optical Port Config Scalars
--------------------------------------------------------------------------------
    tnIo4an10gPortConfigAttributeTotal OBJECT-TYPE
        SYNTAX         Integer32
        MAX-ACCESS     read-only
        STATUS         current
        DESCRIPTION    ""
        ::= { tnOpticalPortConfig 235 }

--------------------------------------------------------------------------------
-- 4AN10G Optical Port Config Table
--------------------------------------------------------------------------------
    tnIo4an10gPortConfigTable OBJECT-TYPE
        SYNTAX         SEQUENCE OF TnIo4an10gPortConfigEntry
        MAX-ACCESS     not-accessible
        STATUS         current
        DESCRIPTION    "The ports on a 4AN10G optical card."
        ::= { tnOpticalPortConfig 236 }

    tnIo4an10gPortConfigEntry OBJECT-TYPE
        SYNTAX         TnIo4an10gPortConfigEntry
        MAX-ACCESS     not-accessible
        STATUS         current
        DESCRIPTION    ""
        INDEX { ifIndex }
        ::= { tnIo4an10gPortConfigTable 1 }

    TnIo4an10gPortConfigEntry ::=
        SEQUENCE {
            tnIo4an10gPortConfigFunction  INTEGER
        }

    tnIo4an10gPortConfigFunction OBJECT-TYPE
        SYNTAX         INTEGER {
                         network(1),
                         client(2)
                       }
        MAX-ACCESS     read-only
        STATUS         current
        DESCRIPTION    "Indicates the functional type of this 4AN10G port."
        ::= { tnIo4an10gPortConfigEntry 1 }

--------------------------------------------------------------------------------
-- 8ET1GB Optical Port Config Scalars
--------------------------------------------------------------------------------
    tnIo8et1gbPortConfigAttributeTotal OBJECT-TYPE
        SYNTAX         Integer32
        MAX-ACCESS     read-only
        STATUS         current
        DESCRIPTION    ""
        ::= { tnOpticalPortConfig 237 }

--------------------------------------------------------------------------------
-- 8ET1GB Optical Port Config Table
--------------------------------------------------------------------------------
    tnIo8et1gbPortConfigTable OBJECT-TYPE
        SYNTAX         SEQUENCE OF TnIo8et1gbPortConfigEntry
        MAX-ACCESS     not-accessible
        STATUS         current
        DESCRIPTION    "The ports on a 8ET1GB optical card."
        ::= { tnOpticalPortConfig 238 }

    tnIo8et1gbPortConfigEntry OBJECT-TYPE
        SYNTAX         TnIo8et1gbPortConfigEntry
        MAX-ACCESS     not-accessible
        STATUS         current
        DESCRIPTION    ""
        INDEX { ifIndex }
        ::= { tnIo8et1gbPortConfigTable 1 }

    TnIo8et1gbPortConfigEntry ::=
        SEQUENCE {
            tnIo8et1gbPortConfigFunction  INTEGER
        }

    tnIo8et1gbPortConfigFunction OBJECT-TYPE
        SYNTAX         INTEGER {
                         network(1),
                         client(2)
                       }
        MAX-ACCESS     read-only
        STATUS         current
        DESCRIPTION    "Indicates the functional type of this 8ET1GB port."
        ::= { tnIo8et1gbPortConfigEntry 1 }

--------------------------------------------------------------------------------
-- 10ET10G Optical Port Config Scalars
--------------------------------------------------------------------------------
    tnIo10et10gPortConfigAttributeTotal OBJECT-TYPE
        SYNTAX         Integer32
        MAX-ACCESS     read-only
        STATUS         current
        DESCRIPTION    ""
        ::= { tnOpticalPortConfig 239 }

--------------------------------------------------------------------------------
-- 10ET10G Optical Port Config Table
--------------------------------------------------------------------------------
    tnIo10et10gPortConfigTable OBJECT-TYPE
        SYNTAX         SEQUENCE OF TnIo10et10gPortConfigEntry
        MAX-ACCESS     not-accessible
        STATUS         current
        DESCRIPTION    "The ports on a 10ET10G optical card."
        ::= { tnOpticalPortConfig 240 }

    tnIo10et10gPortConfigEntry OBJECT-TYPE
        SYNTAX         TnIo10et10gPortConfigEntry
        MAX-ACCESS     not-accessible
        STATUS         current
        DESCRIPTION    ""
        INDEX { ifIndex }
        ::= { tnIo10et10gPortConfigTable 1 }

    TnIo10et10gPortConfigEntry ::=
        SEQUENCE {
            tnIo10et10gPortConfigFunction  INTEGER
        }

    tnIo10et10gPortConfigFunction OBJECT-TYPE
        SYNTAX         INTEGER {
                         network(1),
                         client(2)
                       }
        MAX-ACCESS     read-only
        STATUS         current
        DESCRIPTION    "Indicates the functional type of this 10ET10G port."
        ::= { tnIo10et10gPortConfigEntry 1 }

--------------------------------------------------------------------------------
-- UL11QCUPC Optical Port Config Scalars
--------------------------------------------------------------------------------
    tnUl11qcupcPortConfigAttributeTotal OBJECT-TYPE
        SYNTAX         Integer32
        MAX-ACCESS     read-only
        STATUS         current
        DESCRIPTION    ""
        ::= { tnOpticalPortConfig 241 }

--------------------------------------------------------------------------------
-- UL11QCUPC Optical Port Config Table
--------------------------------------------------------------------------------
    tnUl11qcupcPortConfigTable OBJECT-TYPE
        SYNTAX         SEQUENCE OF TnUl11qcupcPortConfigEntry
        MAX-ACCESS     not-accessible
        STATUS         current
        DESCRIPTION    "The ports on a UL11QCUPC optical card."
        ::= { tnOpticalPortConfig 242 }

    tnUl11qcupcPortConfigEntry OBJECT-TYPE
        SYNTAX         TnUl11qcupcPortConfigEntry
        MAX-ACCESS     not-accessible
        STATUS         current
        DESCRIPTION    ""
        INDEX { ifIndex }
        ::= { tnUl11qcupcPortConfigTable 1 }

    TnUl11qcupcPortConfigEntry ::=
        SEQUENCE {
            tnUl11qcupcPortConfigFunction  INTEGER
        }

    tnUl11qcupcPortConfigFunction OBJECT-TYPE
        SYNTAX         INTEGER {
                         network(1),
                         evoa(2)
                       }
        MAX-ACCESS     read-only
        STATUS         current
        DESCRIPTION    "Indicates the functional type of this UL11QCUPC port."
        ::= { tnUl11qcupcPortConfigEntry 1 }

--------------------------------------------------------------------------------
-- 520SCX4 Optical Port Config Scalars
--------------------------------------------------------------------------------
    tnOt520scx4PortConfigAttributeTotal OBJECT-TYPE
        SYNTAX         Integer32
        MAX-ACCESS     read-only
        STATUS         current
        DESCRIPTION    ""
        ::= { tnOpticalPortConfig 243 }

--------------------------------------------------------------------------------
-- 520SCX4 Optical Port Config Table
--------------------------------------------------------------------------------
    tnOt520scx4PortConfigTable OBJECT-TYPE
        SYNTAX         SEQUENCE OF TnOt520scx4PortConfigEntry
        MAX-ACCESS     not-accessible
        STATUS         current
        DESCRIPTION    "The ports on a 520SCX4 optical card."
        ::= { tnOpticalPortConfig 244 }

    tnOt520scx4PortConfigEntry OBJECT-TYPE
        SYNTAX         TnOt520scx4PortConfigEntry
        MAX-ACCESS     not-accessible
        STATUS         current
        DESCRIPTION    ""
        INDEX { ifIndex }
        ::= { tnOt520scx4PortConfigTable 1 }

    TnOt520scx4PortConfigEntry ::=
        SEQUENCE {
            tnOt520scx4PortConfigFunction  INTEGER
        }

    tnOt520scx4PortConfigFunction OBJECT-TYPE
        SYNTAX         INTEGER {
                         network(1),
                         client(2)
                       }
        MAX-ACCESS     read-only
        STATUS         current
        DESCRIPTION    "Indicates the functional type of this 520SCX4 port."
        ::= { tnOt520scx4PortConfigEntry 1 }

--------------------------------------------------------------------------------
-- WSS APR Port Config Scalars
--------------------------------------------------------------------------------
    tnWssAprPortConfigAttributeTotal OBJECT-TYPE
        SYNTAX         Integer32
        MAX-ACCESS     read-only
        STATUS         current
        DESCRIPTION    ""
        ::= { tnOpticalPortConfig 245 }

--------------------------------------------------------------------------------
-- WSS APR Port Config Table
--------------------------------------------------------------------------------
    tnWssAprPortConfigTable OBJECT-TYPE
        SYNTAX         SEQUENCE OF TnWssAprPortConfigEntry
        MAX-ACCESS     not-accessible
        STATUS         current
        DESCRIPTION    "The APR attribute for a WSS port."
        ::= { tnOpticalPortConfig 246 }

    tnWssAprPortConfigEntry OBJECT-TYPE
        SYNTAX         TnWssAprPortConfigEntry
        MAX-ACCESS     not-accessible
        STATUS         current
        DESCRIPTION    ""
        INDEX { ifIndex }
        ::= { tnWssAprPortConfigTable 1 }

    TnWssAprPortConfigEntry ::=
        SEQUENCE {
            tnWssAprPortConfigAprHoldOffTime     INTEGER
        }

    tnWssAprPortConfigAprHoldOffTime OBJECT-TYPE
        SYNTAX         INTEGER {
                         time0ms(1),
                         time250ms(4)
                       }
        MAX-ACCESS     read-create
        STATUS         current
        DESCRIPTION    "The auto power recovery hold off time."
        DEFVAL         { time0ms }
        ::= { tnWssAprPortConfigEntry 1 }

--------------------------------------------------------------------------------
-- Power Filter Port Config Scalars
--------------------------------------------------------------------------------
    tnPowerFilterPortConfigAttributeTotal OBJECT-TYPE
        SYNTAX         Integer32
        MAX-ACCESS     read-only
        STATUS         current
        DESCRIPTION    ""
        ::= { tnOpticalPortConfig 247 }

--------------------------------------------------------------------------------
-- Power Filter Port Config Table
--------------------------------------------------------------------------------
    tnPowerFilterPortConfigTable OBJECT-TYPE
        SYNTAX         SEQUENCE OF TnPowerFilterPortConfigEntry
        MAX-ACCESS     not-accessible
        STATUS         current
        DESCRIPTION    "The ports on a PowerFilter optical card."
        ::= { tnOpticalPortConfig 248 }

    tnPowerFilterPortConfigEntry OBJECT-TYPE
        SYNTAX         TnPowerFilterPortConfigEntry
        MAX-ACCESS     not-accessible
        STATUS         current
        DESCRIPTION    ""
        INDEX { ifIndex }
        ::= { tnPowerFilterPortConfigTable 1 }

    TnPowerFilterPortConfigEntry ::=
        SEQUENCE {
            tnPowerFilterPortConfigFunction  INTEGER
        }

    tnPowerFilterPortConfigFunction OBJECT-TYPE
        SYNTAX         INTEGER {
                         oneTru(1)
                       }
        MAX-ACCESS     read-only
        STATUS         current
        DESCRIPTION    "Indicates the functional type of this PowerFilter port."
        ::= { tnPowerFilterPortConfigEntry 1 }

--------------------------------------------------------------------------------
-- 11OPE8 Optical Port Config Scalars
--------------------------------------------------------------------------------
    tn11ope8PortConfigAttributeTotal OBJECT-TYPE
        SYNTAX         Integer32
        MAX-ACCESS     read-only
        STATUS         current
        DESCRIPTION    ""
        ::= { tnOpticalPortConfig 249 }

--------------------------------------------------------------------------------
-- 11OPE8 Optical Port Config Table
--------------------------------------------------------------------------------
    tn11ope8PortConfigTable OBJECT-TYPE
        SYNTAX         SEQUENCE OF Tn11ope8PortConfigEntry
        MAX-ACCESS     not-accessible
        STATUS         current
        DESCRIPTION    "The ports on a 11OPE8 optical card."
        ::= { tnOpticalPortConfig 250 }

    tn11ope8PortConfigEntry OBJECT-TYPE
        SYNTAX         Tn11ope8PortConfigEntry
        MAX-ACCESS     not-accessible
        STATUS         current
        DESCRIPTION    ""
        INDEX { ifIndex }
        ::= { tn11ope8PortConfigTable 1 }

    Tn11ope8PortConfigEntry ::=
        SEQUENCE {
            tn11ope8PortConfigFunction  INTEGER
        }

    tn11ope8PortConfigFunction OBJECT-TYPE
        SYNTAX         INTEGER {
                         network(1),
                         client(2),
                         evoa(3),
                         backplane(4),
                         tod(5)
                       }
        MAX-ACCESS     read-only
        STATUS         current
        DESCRIPTION    "Indicates the functional type of this 11OPE8 port."
        ::= { tn11ope8PortConfigEntry 1 }

--------------------------------------------------------------------------------
-- 11QCE12X Optical Port Config Scalars
--------------------------------------------------------------------------------
    tn11qce12xPortConfigAttributeTotal OBJECT-TYPE
        SYNTAX         Integer32
        MAX-ACCESS     read-only
        STATUS         current
        DESCRIPTION    ""
        ::= { tnOpticalPortConfig 251 }

--------------------------------------------------------------------------------
-- 11QCE12X Optical Port Config Table
--------------------------------------------------------------------------------
    tn11qce12xPortConfigTable OBJECT-TYPE
        SYNTAX         SEQUENCE OF Tn11qce12xPortConfigEntry
        MAX-ACCESS     not-accessible
        STATUS         current
        DESCRIPTION    "The ports on a 11QCE12X optical card."
        ::= { tnOpticalPortConfig 252 }

    tn11qce12xPortConfigEntry OBJECT-TYPE
        SYNTAX         Tn11qce12xPortConfigEntry
        MAX-ACCESS     not-accessible
        STATUS         current
        DESCRIPTION    ""
        INDEX { ifIndex }
        ::= { tn11qce12xPortConfigTable 1 }

    Tn11qce12xPortConfigEntry ::=
        SEQUENCE {
            tn11qce12xPortConfigFunction  INTEGER
        }

    tn11qce12xPortConfigFunction OBJECT-TYPE
        SYNTAX         INTEGER {
                         network(1),
                         client(2),
                         evoa(3),
                         backplane(4),
                         tod(5)
                       }
        MAX-ACCESS     read-only
        STATUS         current
        DESCRIPTION    "Indicates the functional type of this 11QCE12X port."
        ::= { tn11qce12xPortConfigEntry 1 }

--------------------------------------------------------------------------------
-- AM2625A Optical Port Config Scalars
--------------------------------------------------------------------------------
    tnAm2625aPortConfigAttributeTotal OBJECT-TYPE
        SYNTAX         Integer32
        MAX-ACCESS     read-only
        STATUS         current
        DESCRIPTION    ""
        ::= { tnOpticalPortConfig 253 }

--------------------------------------------------------------------------------
-- AM2625A Optical Port Config Table
--------------------------------------------------------------------------------
    tnAm2625aPortConfigTable OBJECT-TYPE
        SYNTAX         SEQUENCE OF TnAm2625aPortConfigEntry
        MAX-ACCESS     not-accessible
        STATUS         current
        DESCRIPTION    "The ports on an AM2625A optical card."
        ::= { tnOpticalPortConfig 254 }

    tnAm2625aPortConfigEntry OBJECT-TYPE
        SYNTAX         TnAm2625aPortConfigEntry
        MAX-ACCESS     not-accessible
        STATUS         current
        DESCRIPTION    ""
        INDEX { ifIndex }
        ::= { tnAm2625aPortConfigTable 1 }

    TnAm2625aPortConfigEntry ::=
        SEQUENCE {
            tnAm2625aPortConfigFunction INTEGER
        }

    tnAm2625aPortConfigFunction OBJECT-TYPE
        SYNTAX         INTEGER {
                         lineIn(1),
                         inv(2),
                         dcm(3),
                         lineOut(4),
                         oscSfp(5),
                         det(6),
                         osc(7)
                       }
        MAX-ACCESS     read-only
        STATUS         current
        DESCRIPTION    "Indicates the functional type of this AM2625A port."
        ::= { tnAm2625aPortConfigEntry 1 }

--------------------------------------------------------------------------------
-- AM2032A Optical Port Config Scalars
--------------------------------------------------------------------------------
    tnAm2032aPortConfigAttributeTotal OBJECT-TYPE
        SYNTAX         Integer32
        MAX-ACCESS     read-only
        STATUS         current
        DESCRIPTION    ""
        ::= { tnOpticalPortConfig 255 }

--------------------------------------------------------------------------------
-- AM2032A Optical Port Config Table
--------------------------------------------------------------------------------
    tnAm2032aPortConfigTable OBJECT-TYPE
        SYNTAX         SEQUENCE OF TnAm2032aPortConfigEntry
        MAX-ACCESS     not-accessible
        STATUS         current
        DESCRIPTION    "The ports on an AM2032A optical card."
        ::= { tnOpticalPortConfig 256 }

    tnAm2032aPortConfigEntry OBJECT-TYPE
        SYNTAX         TnAm2032aPortConfigEntry
        MAX-ACCESS     not-accessible
        STATUS         current
        DESCRIPTION    ""
        INDEX { ifIndex }
        ::= { tnAm2032aPortConfigTable 1 }

    TnAm2032aPortConfigEntry ::=
        SEQUENCE {
            tnAm2032aPortConfigFunction INTEGER
        }

    tnAm2032aPortConfigFunction OBJECT-TYPE
        SYNTAX         INTEGER {
                         lineIn(1),
                         inv(2),
                         dcm(3),
                         lineOut(4),
                         oscSfp(5),
                         det(6),
                         osc(7)
                       }
        MAX-ACCESS     read-only
        STATUS         current
        DESCRIPTION    "Indicates the functional type of this AM2032A port."
        ::= { tnAm2032aPortConfigEntry 1 }

--------------------------------------------------------------------------------
-- OT260SCX2 Optical Port Config Scalars
--------------------------------------------------------------------------------
    tnOt260scx2PortConfigAttributeTotal OBJECT-TYPE
        SYNTAX         Integer32
        MAX-ACCESS     read-only
        STATUS         current
        DESCRIPTION    ""
        ::= { tnOpticalPortConfig 257 }

--------------------------------------------------------------------------------
-- OT260SCX2 Optical Port Config Table
--------------------------------------------------------------------------------
    tnOt260scx2PortConfigTable OBJECT-TYPE
        SYNTAX         SEQUENCE OF TnOt260scx2PortConfigEntry
        MAX-ACCESS     not-accessible
        STATUS         current
        DESCRIPTION    "The ports on a OT260SCX2 optical card."
        ::= { tnOpticalPortConfig 258 }

    tnOt260scx2PortConfigEntry OBJECT-TYPE
        SYNTAX         TnOt260scx2PortConfigEntry
        MAX-ACCESS     not-accessible
        STATUS         current
        DESCRIPTION    ""
        INDEX { ifIndex }
        ::= { tnOt260scx2PortConfigTable 1 }

    TnOt260scx2PortConfigEntry ::=
        SEQUENCE {
            tnOt260scx2PortConfigFunction  INTEGER
        }

    tnOt260scx2PortConfigFunction OBJECT-TYPE
        SYNTAX         INTEGER {
                         network(1),
                         client(2)
                       }
        MAX-ACCESS     read-only
        STATUS         current
        DESCRIPTION    "Indicates the functional type of this OT260SCX2 port."
        ::= { tnOt260scx2PortConfigEntry 1 }

--------------------------------------------------------------------------------
-- OT130SNX10 Optical Port Config Scalars
--------------------------------------------------------------------------------
    tnOt130snx10PortConfigAttributeTotal OBJECT-TYPE
        SYNTAX         Integer32
        MAX-ACCESS     read-only
        STATUS         current
        DESCRIPTION    ""
        ::= { tnOpticalPortConfig 259 }

--------------------------------------------------------------------------------
-- OT130SNX10 Optical Port Config Table
--------------------------------------------------------------------------------
    tnOt130snx10PortConfigTable OBJECT-TYPE
        SYNTAX         SEQUENCE OF TnOt130snx10PortConfigEntry
        MAX-ACCESS     not-accessible
        STATUS         current
        DESCRIPTION    "The ports on a OT130SNX10 optical card."
        ::= { tnOpticalPortConfig 260 }

    tnOt130snx10PortConfigEntry OBJECT-TYPE
        SYNTAX         TnOt130snx10PortConfigEntry
        MAX-ACCESS     not-accessible
        STATUS         current
        DESCRIPTION    ""
        INDEX { ifIndex }
        ::= { tnOt130snx10PortConfigTable 1 }

    TnOt130snx10PortConfigEntry ::=
        SEQUENCE {
            tnOt130snx10PortConfigFunction  INTEGER
        }

    tnOt130snx10PortConfigFunction OBJECT-TYPE
        SYNTAX         INTEGER {
                         network(1),
                         client(2)
                       }
        MAX-ACCESS     read-only
        STATUS         current
        DESCRIPTION    "Indicates the functional type of this OT130SNX10 port."
        ::= { tnOt130snx10PortConfigEntry 1 }

--------------------------------------------------------------------------------
-- IO24ANMB Optical Port Config Scalars
--------------------------------------------------------------------------------
    tnIo24anmbPortConfigAttributeTotal OBJECT-TYPE
        SYNTAX         Integer32
        MAX-ACCESS     read-only
        STATUS         current
        DESCRIPTION    ""
        ::= { tnOpticalPortConfig 261 }

--------------------------------------------------------------------------------
-- IO24ANMB Optical Port Config Table
--------------------------------------------------------------------------------
    tnIo24anmbPortConfigTable OBJECT-TYPE
        SYNTAX         SEQUENCE OF TnIo24anmbPortConfigEntry
        MAX-ACCESS     not-accessible
        STATUS         current
        DESCRIPTION    "The ports on a IO24ANMB optical card."
        ::= { tnOpticalPortConfig 262 }

    tnIo24anmbPortConfigEntry OBJECT-TYPE
        SYNTAX         TnIo24anmbPortConfigEntry
        MAX-ACCESS     not-accessible
        STATUS         current
        DESCRIPTION    ""
        INDEX { ifIndex }
        ::= { tnIo24anmbPortConfigTable 1 }

    TnIo24anmbPortConfigEntry ::=
        SEQUENCE {
            tnIo24anmbPortConfigFunction INTEGER
        }

    tnIo24anmbPortConfigFunction OBJECT-TYPE
        SYNTAX         INTEGER {
                         client(1)
                       }
        MAX-ACCESS     read-only
        STATUS         current
        DESCRIPTION    "Indicates the functional type of this IO24ANMB port."
        ::= { tnIo24anmbPortConfigEntry 1 }

--------------------------------------------------------------------------------
-- OT11DPM8 Optical Port Config Scalars
--------------------------------------------------------------------------------
    tnOt11dpm8PortConfigAttributeTotal OBJECT-TYPE
        SYNTAX         Integer32
        MAX-ACCESS     read-only
        STATUS         current
        DESCRIPTION    ""
        ::= { tnOpticalPortConfig 263 }

--------------------------------------------------------------------------------
-- OT11DPM8 Optical Port Config Table
--------------------------------------------------------------------------------
    tnOt11dpm8PortConfigTable OBJECT-TYPE
        SYNTAX         SEQUENCE OF TnOt11dpm8PortConfigEntry
        MAX-ACCESS     not-accessible
        STATUS         current
        DESCRIPTION    "The ports on a OT11DPM8 optical card."
        ::= { tnOpticalPortConfig 264 }

    tnOt11dpm8PortConfigEntry OBJECT-TYPE
        SYNTAX         TnOt11dpm8PortConfigEntry
        MAX-ACCESS     not-accessible
        STATUS         current
        DESCRIPTION    ""
        INDEX { ifIndex }
        ::= { tnOt11dpm8PortConfigTable 1 }

    TnOt11dpm8PortConfigEntry ::=
        SEQUENCE {
            tnOt11dpm8PortConfigFunction INTEGER
        }

    tnOt11dpm8PortConfigFunction OBJECT-TYPE
        SYNTAX         INTEGER {
                         network(1),
                         client(2),
                         evoa(3)
                       }
        MAX-ACCESS     read-only
        STATUS         current
        DESCRIPTION    "Indicates the functional type of this OT11DPM8 port."
        ::= { tnOt11dpm8PortConfigEntry 1 }

--------------------------------------------------------------------------------
-- OT11DPM4M Optical Port Config Scalars
--------------------------------------------------------------------------------
    tnOt11dpm4mPortConfigAttributeTotal OBJECT-TYPE
        SYNTAX         Integer32
        MAX-ACCESS     read-only
        STATUS         current
        DESCRIPTION    ""
        ::= { tnOpticalPortConfig 265 }

--------------------------------------------------------------------------------
-- OT11DPM4M Optical Port Config Table
--------------------------------------------------------------------------------
    tnOt11dpm4mPortConfigTable OBJECT-TYPE
        SYNTAX         SEQUENCE OF TnOt11dpm4mPortConfigEntry
        MAX-ACCESS     not-accessible
        STATUS         current
        DESCRIPTION    "The ports on a OT11DPM4M optical card."
        ::= { tnOpticalPortConfig 266 }

    tnOt11dpm4mPortConfigEntry OBJECT-TYPE
        SYNTAX         TnOt11dpm4mPortConfigEntry
        MAX-ACCESS     not-accessible
        STATUS         current
        DESCRIPTION    ""
        INDEX { ifIndex }
        ::= { tnOt11dpm4mPortConfigTable 1 }

    TnOt11dpm4mPortConfigEntry ::=
        SEQUENCE {
            tnOt11dpm4mPortConfigFunction INTEGER
        }

    tnOt11dpm4mPortConfigFunction OBJECT-TYPE
        SYNTAX         INTEGER {
                         network(1),
                         client(2)
                       }
        MAX-ACCESS     read-only
        STATUS         current
        DESCRIPTION    "Indicates the functional type of this OT11DPM4M port."
        ::= { tnOt11dpm4mPortConfigEntry 1 }

--------------------------------------------------------------------------------
-- UL130SCUPB Optical Port Config Scalars
--------------------------------------------------------------------------------
    tnUl130scupbPortConfigAttributeTotal OBJECT-TYPE
        SYNTAX         Integer32
        MAX-ACCESS     read-only
        STATUS         current
        DESCRIPTION    ""
        ::= { tnOpticalPortConfig 267 }

--------------------------------------------------------------------------------
-- UL130SCUPB Optical Port Config Table
--------------------------------------------------------------------------------
    tnUl130scupbPortConfigTable OBJECT-TYPE
        SYNTAX         SEQUENCE OF TnUl130scupbPortConfigEntry
        MAX-ACCESS     not-accessible
        STATUS         current
        DESCRIPTION    "The ports on a UL130SCUPB optical card."
        ::= { tnOpticalPortConfig 268 }

    tnUl130scupbPortConfigEntry OBJECT-TYPE
        SYNTAX         TnUl130scupbPortConfigEntry
        MAX-ACCESS     not-accessible
        STATUS         current
        DESCRIPTION    ""
        INDEX { ifIndex }
        ::= { tnUl130scupbPortConfigTable 1 }

    TnUl130scupbPortConfigEntry ::=
        SEQUENCE {
            tnUl130scupbPortConfigFunction  INTEGER
        }

    tnUl130scupbPortConfigFunction OBJECT-TYPE
        SYNTAX         INTEGER {
                         network(1)
                       }
        MAX-ACCESS     read-only
        STATUS         current
        DESCRIPTION    "Indicates the functional type of this UL130SCUPB port."
        ::= { tnUl130scupbPortConfigEntry 1 }

--------------------------------------------------------------------------------
-- OT112SDX11 Optical Port Config Scalars
--------------------------------------------------------------------------------
    tnOt112sdx11PortConfigAttributeTotal OBJECT-TYPE
        SYNTAX         Integer32
        MAX-ACCESS     read-only
        STATUS         current
        DESCRIPTION    ""
        ::= { tnOpticalPortConfig 269 }

--------------------------------------------------------------------------------
-- OT112SDX11 Optical Port Config Table
--------------------------------------------------------------------------------
    tnOt112sdx11PortConfigTable OBJECT-TYPE
        SYNTAX         SEQUENCE OF TnOt112sdx11PortConfigEntry
        MAX-ACCESS     not-accessible
        STATUS         current
        DESCRIPTION    "The ports on a OT112SDX11 optical card."
        ::= { tnOpticalPortConfig 270 }

    tnOt112sdx11PortConfigEntry OBJECT-TYPE
        SYNTAX         TnOt112sdx11PortConfigEntry
        MAX-ACCESS     not-accessible
        STATUS         current
        DESCRIPTION    ""
        INDEX { ifIndex }
        ::= { tnOt112sdx11PortConfigTable 1 }

    TnOt112sdx11PortConfigEntry ::=
        SEQUENCE {
            tnOt112sdx11PortConfigFunction  INTEGER,
            tnOt112sdx11PortConfigLinkGroupId INTEGER,
            tnOt112sdx11ProgrammedNwOutputPower Integer32
        }

    tnOt112sdx11PortConfigFunction OBJECT-TYPE
        SYNTAX         INTEGER {
                         network(1),
                         client(2)
                       }
        MAX-ACCESS     read-only
        STATUS         current
        DESCRIPTION    "Indicates the functional type of this OT112SDX11 port."
        ::= { tnOt112sdx11PortConfigEntry 1 }
    
   tnOt112sdx11PortConfigLinkGroupId OBJECT-TYPE
        SYNTAX         INTEGER {
                         notApplicable(1),
                         islGroupId1(2), 
                         islGroupId2(3),
                         islGroupId3(4),
                         islGroupId4(5),
                         islGroupId5(6)
                       }
        MAX-ACCESS     read-write
        STATUS         current
        DESCRIPTION    "port ISL group Id."
        DEFVAL         { notApplicable }
        ::= { tnOt112sdx11PortConfigEntry 2 }

    tnOt112sdx11ProgrammedNwOutputPower OBJECT-TYPE
        SYNTAX         Integer32
        UNITS          "mBm"
        MAX-ACCESS     read-create
        STATUS         current
        DESCRIPTION    "The programmed DC output power of 
                         the port with Coherent CFP, measured in mBm. 
                         It is the power of the full optical signal.
                        Current configurable range:
                         -1500 to 300 (C120G1TC coherent cfp on 112SDX11)"
        ::= { tnOt112sdx11PortConfigEntry 3 }

--------------------------------------------------------------------------------
-- AA2DONW Port Config Scalars
--------------------------------------------------------------------------------
    tnAa2donwPortConfigAttributeTotal OBJECT-TYPE
        SYNTAX         Integer32
        MAX-ACCESS     read-only
        STATUS         current
        DESCRIPTION    ""
        ::= { tnOpticalPortConfig 271 }

--------------------------------------------------------------------------------
-- AA2DONW Port Config Table
--------------------------------------------------------------------------------
    tnAa2donwPortConfigTable OBJECT-TYPE
        SYNTAX         SEQUENCE OF TnAa2donwPortConfigEntry
        MAX-ACCESS     not-accessible
        STATUS         current
        DESCRIPTION    "The ports on an AA2DONW optical card."
        ::= { tnOpticalPortConfig 272 }

    tnAa2donwPortConfigEntry OBJECT-TYPE
        SYNTAX         TnAa2donwPortConfigEntry
        MAX-ACCESS     not-accessible
        STATUS         current
        DESCRIPTION    ""
        INDEX { ifIndex }
        ::= { tnAa2donwPortConfigTable 1 }

    TnAa2donwPortConfigEntry ::=
        SEQUENCE {
            tnAa2donwPortConfigFunction  INTEGER
        }

    tnAa2donwPortConfigFunction OBJECT-TYPE
        SYNTAX         INTEGER {
                         line(1),
                         signal(2),
                         inv(3),
                         osc(4),
                         oscSfp(5)
                       }
        MAX-ACCESS     read-only
        STATUS         current
        DESCRIPTION    "Indicates the functional type of this AA2DONW port."
        ::= { tnAa2donwPortConfigEntry 1 }

--------------------------------------------------------------------------------
-- 130SCA1 Optical Port Config Scalars
--------------------------------------------------------------------------------
    tnOt130sca1PortConfigAttributeTotal OBJECT-TYPE
        SYNTAX         Integer32
        MAX-ACCESS     read-only
        STATUS         current
        DESCRIPTION    ""
        ::= { tnOpticalPortConfig 273 }

--------------------------------------------------------------------------------
-- 130SCA1 Optical Port Config Table
--------------------------------------------------------------------------------
    tnOt130sca1PortConfigTable OBJECT-TYPE
        SYNTAX         SEQUENCE OF TnOt130sca1PortConfigEntry
        MAX-ACCESS     not-accessible
        STATUS         current
        DESCRIPTION    "The ports on a 130SCA1 optical card."
        ::= { tnOpticalPortConfig 274 }

    tnOt130sca1PortConfigEntry OBJECT-TYPE
        SYNTAX         TnOt130sca1PortConfigEntry
        MAX-ACCESS     not-accessible
        STATUS         current
        DESCRIPTION    ""
        INDEX { ifIndex }
        ::= { tnOt130sca1PortConfigTable 1 }

    TnOt130sca1PortConfigEntry ::=
        SEQUENCE {
            tnOt130sca1PortConfigFunction INTEGER
        }

    tnOt130sca1PortConfigFunction OBJECT-TYPE
        SYNTAX         INTEGER {
                         network(1),
                         client(2)
                       }
        MAX-ACCESS     read-only
        STATUS         current
        DESCRIPTION    "Indicates the functional type of this 130SCA1 port."
        ::= { tnOt130sca1PortConfigEntry 1 }

--------------------------------------------------------------------------------
-- 10AN10GB Optical Port Config Scalars
--------------------------------------------------------------------------------
    tnIo10an10gbPortConfigAttributeTotal OBJECT-TYPE
        SYNTAX         Integer32
        MAX-ACCESS     read-only
        STATUS         current
        DESCRIPTION    ""
        ::= { tnOpticalPortConfig 275 }

--------------------------------------------------------------------------------
-- 10AN10GB Optical Port Config Table
--------------------------------------------------------------------------------
    tnIo10an10gbPortConfigTable OBJECT-TYPE
        SYNTAX         SEQUENCE OF TnIo10an10gbPortConfigEntry
        MAX-ACCESS     not-accessible
        STATUS         current
        DESCRIPTION    "The ports on a 10AN10GB optical card."
        ::= { tnOpticalPortConfig 276 }

    tnIo10an10gbPortConfigEntry OBJECT-TYPE
        SYNTAX         TnIo10an10gbPortConfigEntry
        MAX-ACCESS     not-accessible
        STATUS         current
        DESCRIPTION    ""
        INDEX { ifIndex }
        ::= { tnIo10an10gbPortConfigTable 1 }

    TnIo10an10gbPortConfigEntry ::=
        SEQUENCE {
            tnIo10an10gbPortConfigFunction INTEGER
        }

    tnIo10an10gbPortConfigFunction OBJECT-TYPE
        SYNTAX         INTEGER {
                         network(1),
                         client(2)
                       }
        MAX-ACCESS     read-only
        STATUS         current
        DESCRIPTION    "Indicates the functional type of this 10AN10GB port."
        ::= { tnIo10an10gbPortConfigEntry 1 }

--------------------------------------------------------------------------------
-- 10ET10GB Optical Port Config Scalars
--------------------------------------------------------------------------------
    tnIo10et10gbPortConfigAttributeTotal OBJECT-TYPE
        SYNTAX         Integer32
        MAX-ACCESS     read-only
        STATUS         current
        DESCRIPTION    ""
        ::= { tnOpticalPortConfig 277 }

--------------------------------------------------------------------------------
-- 10ET10GB Optical Port Config Table
--------------------------------------------------------------------------------
    tnIo10et10gbPortConfigTable OBJECT-TYPE
        SYNTAX         SEQUENCE OF TnIo10et10gbPortConfigEntry
        MAX-ACCESS     not-accessible
        STATUS         current
        DESCRIPTION    "The ports on a 10ET10GB optical card."
        ::= { tnOpticalPortConfig 278 }

    tnIo10et10gbPortConfigEntry OBJECT-TYPE
        SYNTAX         TnIo10et10gbPortConfigEntry
        MAX-ACCESS     not-accessible
        STATUS         current
        DESCRIPTION    ""
        INDEX { ifIndex }
        ::= { tnIo10et10gbPortConfigTable 1 }

    TnIo10et10gbPortConfigEntry ::=
        SEQUENCE {
            tnIo10et10gbPortConfigFunction  INTEGER
        }

    tnIo10et10gbPortConfigFunction OBJECT-TYPE
        SYNTAX         INTEGER {
                         network(1),
                         client(2)
                       }
        MAX-ACCESS     read-only
        STATUS         current
        DESCRIPTION    "Indicates the functional type of this 10ET10GB port."
        ::= { tnIo10et10gbPortConfigEntry 1 }

--------------------------------------------------------------------------------
-- PSC1-6 Optical Port Config Scalars
--------------------------------------------------------------------------------
    tnPsc1x6PortConfigAttributeTotal OBJECT-TYPE
        SYNTAX         Integer32
        MAX-ACCESS     read-only
        STATUS         current
        DESCRIPTION    ""
        ::= { tnOpticalPortConfig 279 }

--------------------------------------------------------------------------------
-- PSC1-6 Optical Port Config Table
--------------------------------------------------------------------------------
    tnPsc1x6PortConfigTable OBJECT-TYPE
        SYNTAX         SEQUENCE OF TnPsc1x6PortConfigEntry
        MAX-ACCESS     not-accessible
        STATUS         current
        DESCRIPTION    "The ports on an PSC1-6 optical card."
        ::= { tnOpticalPortConfig 280 }

    tnPsc1x6PortConfigEntry OBJECT-TYPE
        SYNTAX         TnPsc1x6PortConfigEntry
        MAX-ACCESS     not-accessible
        STATUS         current
        DESCRIPTION    ""
        INDEX { ifIndex }
        ::= { tnPsc1x6PortConfigTable 1 }

    TnPsc1x6PortConfigEntry ::=
        SEQUENCE {
            tnPsc1x6PortConfigFunction  INTEGER
        }

    tnPsc1x6PortConfigFunction OBJECT-TYPE
        SYNTAX         INTEGER {
                         signal(1),
                         channel(2)
                       }
        MAX-ACCESS     read-only
        STATUS         current
        DESCRIPTION    "Indicates the functional type of this PSC1-6 port."
        ::= { tnPsc1x6PortConfigEntry 1 }

--------------------------------------------------------------------------------
-- WR20-TF Optical Port Config Scalars
--------------------------------------------------------------------------------
    tnWr20tfPortConfigAttributeTotal OBJECT-TYPE
        SYNTAX         Integer32
        MAX-ACCESS     read-only
        STATUS         current
        DESCRIPTION    ""
        ::= { tnOpticalPortConfig 281 }

--------------------------------------------------------------------------------
-- WR20-TF Optical Port Config Table
--------------------------------------------------------------------------------
    tnWr20tfPortConfigTable OBJECT-TYPE
        SYNTAX         SEQUENCE OF TnWr20tfPortConfigEntry
        MAX-ACCESS     not-accessible
        STATUS         current
        DESCRIPTION    "The ports on an WR20-TF optical card."
        ::= { tnOpticalPortConfig 282 }

    tnWr20tfPortConfigEntry OBJECT-TYPE
        SYNTAX         TnWr20tfPortConfigEntry
        MAX-ACCESS     not-accessible
        STATUS         current
        DESCRIPTION    ""
        INDEX { ifIndex }
        ::= { tnWr20tfPortConfigTable 1 }

    TnWr20tfPortConfigEntry ::=
        SEQUENCE {
            tnWr20tfPortConfigFunction             INTEGER,
            tnWr20tfPortConfigDropInitTargetPower  Integer32,
            tnWr20tfPortConfigExpressTargetPower   Integer32,
            tnWr20tfPortConfigDropMaxTargetPower   Integer32,
            tnWr20tfPortConfigDropMinTargetPower   Integer32
        }

    tnWr20tfPortConfigFunction OBJECT-TYPE
        SYNTAX         INTEGER {
                         signal(1),
                         adt(2),
                         ad(3),
                         inv(4)
                       }
        MAX-ACCESS     read-only
        STATUS         current
        DESCRIPTION    "Indicates the functional type of this WR20-TF port."
        ::= { tnWr20tfPortConfigEntry 1 }

    tnWr20tfPortConfigDropInitTargetPower OBJECT-TYPE
        SYNTAX         Integer32 (-2000..0)
        UNITS          "mBm"
        MAX-ACCESS     read-create
        STATUS         current
        DESCRIPTION    "The initial target power used for dropped channels.

                        Current configurable range: -2000 to 0."
        DEFVAL         { -800 }
        ::= { tnWr20tfPortConfigEntry 2 }

    tnWr20tfPortConfigExpressTargetPower OBJECT-TYPE
        SYNTAX         Integer32 (-2000..0)
        UNITS          "mBm"
        MAX-ACCESS     read-create
        STATUS         current
        DESCRIPTION    "The target power used to set drop side WSS
                        attenuation value for expressed channels.

                        Current configurable range: -2000 to 0."
        DEFVAL         { -900 }
        ::= { tnWr20tfPortConfigEntry 3 }

    tnWr20tfPortConfigDropMaxTargetPower OBJECT-TYPE
        SYNTAX         Integer32 (-2000..0)
        UNITS          "mBm"
        MAX-ACCESS     read-create
        STATUS         current
        DESCRIPTION    "Upper limit for SCOT drop target adjustment loop.
                        For advanced users only.

                        Current configurable range: -2000 to 0."
        DEFVAL         { -600 }
        ::= { tnWr20tfPortConfigEntry 4 }

    tnWr20tfPortConfigDropMinTargetPower OBJECT-TYPE
        SYNTAX         Integer32 (-2000..0)
        UNITS          "mBm"
        MAX-ACCESS     read-create
        STATUS         current
        DESCRIPTION    "Lower limit for SCOT drop target adjustment loop.
                        For advanced users only.

                        Current configurable range: -2000 to 0."
        DEFVAL         { -1200 }
        ::= { tnWr20tfPortConfigEntry 5 }

--------------------------------------------------------------------------------
-- WTOCMF Optical Port Config Scalars
--------------------------------------------------------------------------------
    tnWtocmfPortConfigAttributeTotal OBJECT-TYPE
        SYNTAX         Integer32
        MAX-ACCESS     read-only
        STATUS         current
        DESCRIPTION    ""
        ::= { tnOpticalPortConfig 283 }

--------------------------------------------------------------------------------
-- WTOCMF Optical Port Config Table
--------------------------------------------------------------------------------
    tnWtocmfPortConfigTable OBJECT-TYPE
        SYNTAX         SEQUENCE OF TnWtocmfPortConfigEntry
        MAX-ACCESS     not-accessible
        STATUS         current
        DESCRIPTION    "The ports on a WTOCMF optical card."
        ::= { tnOpticalPortConfig 284 }

    tnWtocmfPortConfigEntry OBJECT-TYPE
        SYNTAX         TnWtocmfPortConfigEntry
        MAX-ACCESS     not-accessible
        STATUS         current
        DESCRIPTION    ""
        INDEX { ifIndex }
        ::= { tnWtocmfPortConfigTable 1 }

    TnWtocmfPortConfigEntry ::=
        SEQUENCE {
            tnWtocmfPortConfigFunction  INTEGER
        }

    tnWtocmfPortConfigFunction OBJECT-TYPE
        SYNTAX         INTEGER {
                         detect(1)
                       }
        MAX-ACCESS     read-only
        STATUS         current
        DESCRIPTION    "Indicates the functional type of this WTOCMF port."
        ::= { tnWtocmfPortConfigEntry 1 }

--------------------------------------------------------------------------------
-- ASWG Optical Port Config Scalars
--------------------------------------------------------------------------------
    tnAswgPortConfigAttributeTotal OBJECT-TYPE
        SYNTAX         Integer32
        MAX-ACCESS     read-only
        STATUS         current
        DESCRIPTION    ""
        ::= { tnOpticalPortConfig 285 }

--------------------------------------------------------------------------------
-- ASWG Optical Port Config Table
--------------------------------------------------------------------------------
    tnAswgPortConfigTable OBJECT-TYPE
        SYNTAX         SEQUENCE OF TnAswgPortConfigEntry
        MAX-ACCESS     not-accessible
        STATUS         current
        DESCRIPTION    "The ports on an ASWG optical card."
        ::= { tnOpticalPortConfig 286 }

    tnAswgPortConfigEntry OBJECT-TYPE
        SYNTAX         TnAswgPortConfigEntry
        MAX-ACCESS     not-accessible
        STATUS         current
        DESCRIPTION    ""
        INDEX { ifIndex }
        ::= { tnAswgPortConfigTable 1 }

    TnAswgPortConfigEntry ::=
        SEQUENCE {
            tnAswgPortConfigFunction INTEGER
        }

    tnAswgPortConfigFunction OBJECT-TYPE
        SYNTAX         INTEGER {
                         lineIn(1),
                         otdrRx(2),
                         otdrTx(3),
                         lineOut(4),
                         oscSfp(5),
                         osc(6)
                       }
        MAX-ACCESS     read-only
        STATUS         current
        DESCRIPTION    "Indicates the functional type of this ASWG port."
        ::= { tnAswgPortConfigEntry 1 }

--------------------------------------------------------------------------------
-- A4PSWG Optical Port Config Scalars
--------------------------------------------------------------------------------
    tnA4pswgPortConfigAttributeTotal OBJECT-TYPE
        SYNTAX         Integer32
        MAX-ACCESS     read-only
        STATUS         current
        DESCRIPTION    ""
        ::= { tnOpticalPortConfig 287 }

--------------------------------------------------------------------------------
-- A4PSWG Optical Port Config Table
--------------------------------------------------------------------------------
    tnA4pswgPortConfigTable OBJECT-TYPE
        SYNTAX         SEQUENCE OF TnA4pswgPortConfigEntry
        MAX-ACCESS     not-accessible
        STATUS         current
        DESCRIPTION    "The ports on an A4PSWG optical card."
        ::= { tnOpticalPortConfig 288 }

    tnA4pswgPortConfigEntry OBJECT-TYPE
        SYNTAX         TnA4pswgPortConfigEntry
        MAX-ACCESS     not-accessible
        STATUS         current
        DESCRIPTION    ""
        INDEX { ifIndex }
        ::= { tnA4pswgPortConfigTable 1 }

    TnA4pswgPortConfigEntry ::=
        SEQUENCE {
            tnA4pswgPortConfigFunction INTEGER
        }

    tnA4pswgPortConfigFunction OBJECT-TYPE
        SYNTAX         INTEGER {
                         lineIn(1),
                         otdrRx(2),
                         otdrTx(3),
                         lineOut(4),
                         oscSfp(5),
                         osc(6)
                       }
        MAX-ACCESS     read-only
        STATUS         current
        DESCRIPTION    "Indicates the functional type of this A4PSWG port."
        ::= { tnA4pswgPortConfigEntry 1 }

--------------------------------------------------------------------------------
-- OTDR(Optical Time Domain Reflectometer) Optical Port Config Scalars
--------------------------------------------------------------------------------
    tnOtdrPortConfigAttributeTotal OBJECT-TYPE
        SYNTAX         Integer32
        MAX-ACCESS     read-only
        STATUS         current
        DESCRIPTION    ""
        ::= { tnOpticalPortConfig 289 }

--------------------------------------------------------------------------------
-- OTDR(Optical Time Domain Reflectometer)Optical Port Config Table
--------------------------------------------------------------------------------
    tnOtdrPortConfigTable OBJECT-TYPE
        SYNTAX         SEQUENCE OF TnOtdrPortConfigEntry
        MAX-ACCESS     not-accessible
        STATUS         current
        DESCRIPTION    "The ports on an OTDR optical card."
        ::= { tnOpticalPortConfig 290 }

    tnOtdrPortConfigEntry OBJECT-TYPE
        SYNTAX         TnOtdrPortConfigEntry
        MAX-ACCESS     not-accessible
        STATUS         current
        DESCRIPTION    ""
        INDEX { ifIndex }
        ::= { tnOtdrPortConfigTable 1 }

    TnOtdrPortConfigEntry ::=
        SEQUENCE {
            tnOtdrPortConfigFunction INTEGER,
            tnOtdrPortConfigConnAddress  Integer32 
        }

    tnOtdrPortConfigFunction OBJECT-TYPE
        SYNTAX         INTEGER {
                         px(1)
                       }
        MAX-ACCESS     read-only
        STATUS         current
        DESCRIPTION    "Indicates the functional type of this OTDR port."
        ::= { tnOtdrPortConfigEntry 1 }

    tnOtdrPortConfigConnAddress OBJECT-TYPE
        SYNTAX         Integer32 (-1..2147483647) 
        MAX-ACCESS     read-create
        STATUS         current
        DESCRIPTION    "Specifies the assigned LD port that
                        is connected to the OTDR port."
        ::= { tnOtdrPortConfigEntry 2 }

--------------------------------------------------------------------------------
-- WR20-TFM Optical Port Config Scalars
--------------------------------------------------------------------------------
    tnWr20tfmPortConfigAttributeTotal OBJECT-TYPE
        SYNTAX         Integer32
        MAX-ACCESS     read-only
        STATUS         current
        DESCRIPTION    ""
        ::= { tnOpticalPortConfig 291 }

--------------------------------------------------------------------------------
-- WR20-TFM Optical Port Config Table
--------------------------------------------------------------------------------
    tnWr20tfmPortConfigTable OBJECT-TYPE
        SYNTAX         SEQUENCE OF TnWr20tfmPortConfigEntry
        MAX-ACCESS     not-accessible
        STATUS         current
        DESCRIPTION    "The ports on an WR20-TFM optical card."
        ::= { tnOpticalPortConfig 292 }

    tnWr20tfmPortConfigEntry OBJECT-TYPE
        SYNTAX         TnWr20tfmPortConfigEntry
        MAX-ACCESS     not-accessible
        STATUS         current
        DESCRIPTION    ""
        INDEX { ifIndex }
        ::= { tnWr20tfmPortConfigTable 1 }

    TnWr20tfmPortConfigEntry ::=
        SEQUENCE {
            tnWr20tfmPortConfigFunction                        INTEGER,
            tnWr20tfmPortConfigDropInitTargetPower             Integer32,
            tnWr20tfmPortConfigExpressTargetPower              Integer32,
            tnWr20tfmPortConfigDropMaxTargetPower              Integer32,
            tnWr20tfmPortConfigDropMinTargetPower              Integer32,
--          obsolete
--          tnWr20tfmPortConfigExecuteForcedDropDisposition    TnCommand,
            tnWr20tfmPortConfigEndForcedDropDisposition        TnCommand,
--          obsolete
--          tnWr20tfmPortConfigExecuteForcedAddDisposition     TnCommand,
            tnWr20tfmPortConfigEndForcedAddDisposition         TnCommand,
            tnWr20tfmPortConfigForceAllchannelsDropDisposition AluWdmWRConfigAddDropDisposition,
            tnWr20tfmPortConfigForceAllchannelsAddDisposition  AluWdmWRConfigAddDropDisposition
        }

    tnWr20tfmPortConfigFunction OBJECT-TYPE
        SYNTAX         INTEGER {
                         signal(1),
                         adt(2),
                         ad(3),
                         inv(4),
                         mpoDropOut(5),
                         mpoAddIn(6)
                       }
        MAX-ACCESS     read-only
        STATUS         current
        DESCRIPTION    "Indicates the functional type of this WR20-TFM port."
        ::= { tnWr20tfmPortConfigEntry 1 }

    tnWr20tfmPortConfigDropInitTargetPower OBJECT-TYPE
        SYNTAX         Integer32(-2000..0)
        UNITS          "mB"
        MAX-ACCESS     read-create
        STATUS         current
        DESCRIPTION    "The initial target power used for
                        dropped channels.

                        Current Configurable Range: -2000 to 0
                        and default is -1200."
        DEFVAL         { -1200 }
        ::= { tnWr20tfmPortConfigEntry 2 }

    tnWr20tfmPortConfigExpressTargetPower OBJECT-TYPE
        SYNTAX         Integer32(-2000..0)
        UNITS          "mB"
        MAX-ACCESS     read-create
        STATUS         current
        DESCRIPTION    "The target power used to set drop
                        side WSS attenuation value for
                        expressed channels.

                        Current Configurable Range: -2000 to 0
                        and default is -700."
        DEFVAL         { -700 }
        ::= { tnWr20tfmPortConfigEntry 3 }

    tnWr20tfmPortConfigDropMaxTargetPower OBJECT-TYPE
        SYNTAX         Integer32(-2000..0)
        UNITS          "mB"
        MAX-ACCESS     read-create
        STATUS         current
        DESCRIPTION    "Upper limit for SCOT drop target
                        adjustment loop.  For advanced
                        users only.

                        Current Configurable Range: -2000 to 0
                        and default is -1200."
        DEFVAL         { -1200 }
        ::= { tnWr20tfmPortConfigEntry 4 }

    tnWr20tfmPortConfigDropMinTargetPower OBJECT-TYPE
        SYNTAX         Integer32(-2000..0)
        UNITS          "mB"
        MAX-ACCESS     read-create
        STATUS         current
        DESCRIPTION    "Lower limit for SCOT drop target
                        adjustment loop.  For advanced
                        users only.

                        Current Configurable Range: -2000 to 0
                        and default is -1400."
        DEFVAL         { -1400 }
        ::= { tnWr20tfmPortConfigEntry 5 }

--  obsolete
--  tnWr20tfmPortConfigExecuteForcedDropDisposition OBJECT-TYPE ::= { tnWr20tfmPortConfigEntry 6 }

    tnWr20tfmPortConfigEndForcedDropDisposition OBJECT-TYPE
        SYNTAX         TnCommand
        MAX-ACCESS     read-create
        STATUS         current
        DESCRIPTION    "Ends forced disposition in drop direction
                        of test channels.  All non-cross connected
                        channels are blocked.  For advanced users
                        only."
        DEFVAL         { noCmd }
        ::= { tnWr20tfmPortConfigEntry 7 }
--  obsolete
--  tnWr20tfmPortConfigExecuteForcedAddDisposition OBJECT-TYPE ::= { tnWr20tfmPortConfigEntry 8 }

    tnWr20tfmPortConfigEndForcedAddDisposition OBJECT-TYPE
        SYNTAX         TnCommand
        MAX-ACCESS     read-create
        STATUS         current
        DESCRIPTION    "Ends forced disposition in add direction of
                        test channels.  All non-cross connected
                        channels are blocked.  For advanced users
                        only."
        DEFVAL         { noCmd }
        ::= { tnWr20tfmPortConfigEntry 9 }

    tnWr20tfmPortConfigForceAllchannelsDropDisposition OBJECT-TYPE
        SYNTAX         AluWdmWRConfigAddDropDisposition
        MAX-ACCESS     read-create
        STATUS         current
        DESCRIPTION    "Set disposition of ALL channels to a given
                        AD/ADT port in drop direction. Use
                        tnWr20tfmPortConfigEndForcedDropDisposition
                        to cancel and revert to blocked.
                        This attribute returns to notForced when
                        force is ended."
        DEFVAL         { notForced }
        ::= { tnWr20tfmPortConfigEntry 10 }

    tnWr20tfmPortConfigForceAllchannelsAddDisposition OBJECT-TYPE
        SYNTAX         AluWdmWRConfigAddDropDisposition
        MAX-ACCESS     read-create
        STATUS         current
        DESCRIPTION    "Set disposition of ALL channels from a given
                        AD/ADT port in add direction.  Use
                        tnWr20tfmPortConfigEndForcedAddDisposition
                        to cancel and revert to blocked.
                        This attribute returns to notForced when
                        force is ended"
        DEFVAL         { notForced }
        ::= { tnWr20tfmPortConfigEntry 11 }

--------------------------------------------------------------------------------
-- AAR-8A Optical Port Config Scalars
--------------------------------------------------------------------------------
    tnAar8aPortConfigAttributeTotal OBJECT-TYPE
        SYNTAX         Integer32
        MAX-ACCESS     read-only
        STATUS         current
        DESCRIPTION    ""
        ::= { tnOpticalPortConfig 293 }

--------------------------------------------------------------------------------
-- AAR-8A Optical Port Config Table
--------------------------------------------------------------------------------
    tnAar8aPortConfigTable OBJECT-TYPE
        SYNTAX         SEQUENCE OF TnAar8aPortConfigEntry
        MAX-ACCESS     not-accessible
        STATUS         current
        DESCRIPTION    "The ports on an AAR-8A optical card."
        ::= { tnOpticalPortConfig 294 }

    tnAar8aPortConfigEntry OBJECT-TYPE
        SYNTAX         TnAar8aPortConfigEntry
        MAX-ACCESS     not-accessible
        STATUS         current
        DESCRIPTION    ""
        INDEX { ifIndex }
        ::= { tnAar8aPortConfigTable 1 }

    TnAar8aPortConfigEntry ::=
        SEQUENCE {
            tnAar8aPortConfigFunction   INTEGER
        }

    tnAar8aPortConfigFunction OBJECT-TYPE
        SYNTAX         INTEGER {
                         ampIn(1),
                         ampOut(2),
                         mpoFsm(3),
                         mpoMcs(4)
                       }
        MAX-ACCESS     read-only
        STATUS         current
        DESCRIPTION    "Indicates the functional type of this AAR-8A port."
        ::= { tnAar8aPortConfigEntry 1 }

--------------------------------------------------------------------------------
-- MCS8-16 Optical Port Config Scalars
--------------------------------------------------------------------------------
    tnMcs8x16PortConfigAttributeTotal OBJECT-TYPE
        SYNTAX         Integer32
        MAX-ACCESS     read-only
        STATUS         current
        DESCRIPTION    ""
        ::= { tnOpticalPortConfig 295 }

--------------------------------------------------------------------------------
-- MCS8-16 Optical Port Config Table
--------------------------------------------------------------------------------
    tnMcs8x16PortConfigTable OBJECT-TYPE
        SYNTAX         SEQUENCE OF TnMcs8x16PortConfigEntry
        MAX-ACCESS     not-accessible
        STATUS         current
        DESCRIPTION    "The ports on an MCS8-16 optical card."
        ::= { tnOpticalPortConfig 296 }

    tnMcs8x16PortConfigEntry OBJECT-TYPE
        SYNTAX         TnMcs8x16PortConfigEntry
        MAX-ACCESS     not-accessible
        STATUS         current
        DESCRIPTION    ""
        INDEX { ifIndex }
        ::= { tnMcs8x16PortConfigTable 1 }

    TnMcs8x16PortConfigEntry ::=
        SEQUENCE {
            tnMcs8x16PortConfigFunction   INTEGER
        }

    tnMcs8x16PortConfigFunction OBJECT-TYPE
        SYNTAX         INTEGER {
                         signal(1),
                         ad(2),
                         mpoAar(3)
                       }
        MAX-ACCESS     read-only
        STATUS         current
        DESCRIPTION    "Indicates the functional type of this MCS8-16 port."
        ::= { tnMcs8x16PortConfigEntry 1 }

--------------------------------------------------------------------------------
-- MSH8-FSM Optical Port Config Scalars
--------------------------------------------------------------------------------
    tnMsh8fsmPortConfigAttributeTotal OBJECT-TYPE
        SYNTAX         Integer32
        MAX-ACCESS     read-only
        STATUS         current
        DESCRIPTION    ""
        ::= { tnOpticalPortConfig 297 }

--------------------------------------------------------------------------------
-- MSH8-FSM Optical Port Config Table
--------------------------------------------------------------------------------
    tnMsh8fsmPortConfigTable OBJECT-TYPE
        SYNTAX         SEQUENCE OF TnMsh8fsmPortConfigEntry
        MAX-ACCESS     not-accessible
        STATUS         current
        DESCRIPTION    "The ports on an MSH8-FSM optical card."
        ::= { tnOpticalPortConfig 298 }

    tnMsh8fsmPortConfigEntry OBJECT-TYPE
        SYNTAX         TnMsh8fsmPortConfigEntry
        MAX-ACCESS     not-accessible
        STATUS         current
        DESCRIPTION    ""
        INDEX { ifIndex }
        ::= { tnMsh8fsmPortConfigTable 1 }

    TnMsh8fsmPortConfigEntry ::=
        SEQUENCE {
            tnMsh8fsmPortConfigFunction   INTEGER
        }

    tnMsh8fsmPortConfigFunction OBJECT-TYPE
        SYNTAX         INTEGER {
                         mpoWssDropIn(1),
                         mpoWssAddOut(2),
                         mpoWssAd(3),
                         expIn(4),
                         expOut(5)
                       }
        MAX-ACCESS     read-only
        STATUS         current
        DESCRIPTION    "Indicates the functional type of this MSH8-FSM port."
        ::= { tnMsh8fsmPortConfigEntry 1 }

--------------------------------------------------------------------------------
-- Multi Cast Switch(MCS) Port Config Scalars
--------------------------------------------------------------------------------
    tnMcsPortConfigAttributeTotal OBJECT-TYPE
        SYNTAX         Integer32
        MAX-ACCESS     read-only
        STATUS         current
        DESCRIPTION    ""
        ::= { tnOpticalPortConfig 299 }

--------------------------------------------------------------------------------
-- Multi Cast Switch(MCS) Port Config Table
--------------------------------------------------------------------------------
    tnMcsPortConfigTable OBJECT-TYPE
        SYNTAX         SEQUENCE OF TnMcsPortConfigEntry
        MAX-ACCESS     not-accessible
        STATUS         current
        DESCRIPTION    "MCS configurable force disposition
                        attributes."
        ::= { tnOpticalPortConfig 300 }

    tnMcsPortConfigEntry OBJECT-TYPE
        SYNTAX         TnMcsPortConfigEntry
        MAX-ACCESS     not-accessible
        STATUS         current
        DESCRIPTION    ""
        INDEX { ifIndex }
        ::= { tnMcsPortConfigTable 1 }

    TnMcsPortConfigEntry ::=
        SEQUENCE {
            tnMcsPortConfigTargetForDispositionForce       INTEGER,
            tnMcsPortConfigExecuteForceDispositionToTarget INTEGER
        }

    tnMcsPortConfigTargetForDispositionForce OBJECT-TYPE
        SYNTAX         INTEGER {
                         blocked(1),
                         sig1(2),
                         sig2(3),
                         sig3(4),
                         sig4(5),
                         sig5(6),
                         sig6(7),
                         sig7(8),
                         sig8(9)
                       }
        MAX-ACCESS     read-create
        STATUS         current
        DESCRIPTION    "Set desired target routing for forcing disposition
                        of add and drop directions to given port.  Use
                        tnMcsPortConfigExecuteForceDispositionToTarget
                        to execute switch to this targeted routing."
        DEFVAL         { blocked }
        ::= { tnMcsPortConfigEntry 1 }

    tnMcsPortConfigExecuteForceDispositionToTarget OBJECT-TYPE
        SYNTAX         INTEGER {
                         noCmd(1),
                         execute(2)
                       }
        MAX-ACCESS     read-create
        STATUS         current
        DESCRIPTION    "Use Execute to force add and drop
                        disposition to the value given in
                        tnMcsPortConfigTargetForDispositionForce.
                        Only allowed if no cross-connects
                        are using target disposition."
        DEFVAL         { noCmd }
        ::= { tnMcsPortConfigEntry 2 }

--------------------------------------------------------------------------------
-- Amplifier ARray (AAR) Port Config Scalars
--------------------------------------------------------------------------------
    tnAarPortConfigAttributeTotal OBJECT-TYPE
        SYNTAX         Integer32
        MAX-ACCESS     read-only
        STATUS         current
        DESCRIPTION    ""
        ::= { tnOpticalPortConfig 301 }

--------------------------------------------------------------------------------
-- Amplifier ARray (AAR) Port Config Table
--------------------------------------------------------------------------------
    tnAarPortConfigTable OBJECT-TYPE
        SYNTAX         SEQUENCE OF TnAarPortConfigEntry
        MAX-ACCESS     not-accessible
        STATUS         current
        DESCRIPTION    "The optical amplifier array card configurable
                        attributes."
        ::= { tnOpticalPortConfig 302 }

    tnAarPortConfigEntry OBJECT-TYPE
        SYNTAX         TnAarPortConfigEntry
        MAX-ACCESS     not-accessible
        STATUS         current
        DESCRIPTION    ""
        INDEX { ifIndex }
        ::= { tnAarPortConfigTable 1 }

    TnAarPortConfigEntry ::=
        SEQUENCE {
            tnAarPortConfigOperatingMode     INTEGER,
            tnAarPortConfigPowerGainTarget   Unsigned32,
            tnAarPortConfigSignalPowerTarget Integer32
        }

    tnAarPortConfigOperatingMode OBJECT-TYPE
        SYNTAX         INTEGER {
                         power(1),
                         gain(2),
                         disabled(3)
                       }
        MAX-ACCESS     read-create
        STATUS         current
        DESCRIPTION    "Configures the amplifier operating mode:

                        Power: constant signal output power.
                        Gain: constant signal gain.
                        Disabled: pumps are powered down.

                        Only users operating the amplifier for
                        test purposes should set this attribute."
        DEFVAL         { disabled }
        ::= { tnAarPortConfigEntry 1 }

    tnAarPortConfigPowerGainTarget OBJECT-TYPE
        SYNTAX         Unsigned32(1000..2000)
        UNITS          "mB"
        MAX-ACCESS     read-create
        STATUS         current
        DESCRIPTION    "Configures the gain setting for signal
                        gain.  The operating mode
                        tnAarPortConfigOperatingMode must be
                        configured to Gain prior to setting the
                        gain.  Only use for test purposes.

                        Current configurable range: 1000 to 2000."
        DEFVAL         { 1500 }
        ::= { tnAarPortConfigEntry 2 }

    tnAarPortConfigSignalPowerTarget OBJECT-TYPE
        SYNTAX         Integer32(-500..1000)
        UNITS          "mB"
        MAX-ACCESS     read-create
        STATUS         current
        DESCRIPTION    "Configures the power setting for signal
                        output power in power mode.  The operating
                        mode tnAarPortConfigOperatingMode must be
                        configured to Power prior to setting the
                        power.  Only use for test purposes.

                        Current configurable range: -500 to 1000."
        DEFVAL         { 300 }
        ::= { tnAarPortConfigEntry 3 }

--------------------------------------------------------------------------------
-- WR20-TFM Port Channel Config Scalars
--------------------------------------------------------------------------------
    tnWr20tfmPortChannelConfigAttributeTotal OBJECT-TYPE
        SYNTAX         Integer32
        MAX-ACCESS     read-only
        STATUS         current
        DESCRIPTION    ""
        ::= { tnOpticalPortConfig 303 }

--------------------------------------------------------------------------------
-- WR20-TFM Port Channel Config Table
--------------------------------------------------------------------------------
    tnWr20tfmPortChannelConfigTable OBJECT-TYPE
        SYNTAX         SEQUENCE OF TnWr20tfmPortChannelConfigEntry
        MAX-ACCESS     not-accessible
        STATUS         current
        DESCRIPTION    "Set target port for add/drop disposition
                        force for test channel(s) on an WR20-TFM
                        card."
        ::= { tnOpticalPortConfig 304 }

    tnWr20tfmPortChannelConfigEntry OBJECT-TYPE
        SYNTAX         TnWr20tfmPortChannelConfigEntry
        MAX-ACCESS     not-accessible
        STATUS         current
        DESCRIPTION    ""
        INDEX { ifIndex,
                tnChannel }
        ::= { tnWr20tfmPortChannelConfigTable 1 }

    TnWr20tfmPortChannelConfigEntry ::=
        SEQUENCE {
            tnWr20tfmPortChannelConfigTargetForcedDropDisposition     AluWdmWRConfigAddDropDisposition,
            tnWr20tfmPortChannelConfigTargetForcedAddDisposition      AluWdmWRConfigAddDropDisposition
        }

    tnWr20tfmPortChannelConfigTargetForcedDropDisposition OBJECT-TYPE
        SYNTAX         AluWdmWRConfigAddDropDisposition
        MAX-ACCESS     read-create
        STATUS         current
        DESCRIPTION    "Target port to drop test channel(s) to.
                        Use tnWr20tfmPortConfigExecuteForcedDropDisposition
                        attribute to execute.  Note only one port
                        can be used at a time in this mode.
                        For advanced users only.
                        
                        Not supported in current(7.0.2) release."
        DEFVAL          { notForced }
        ::= { tnWr20tfmPortChannelConfigEntry 1 }

    tnWr20tfmPortChannelConfigTargetForcedAddDisposition OBJECT-TYPE
        SYNTAX         AluWdmWRConfigAddDropDisposition
        MAX-ACCESS     read-create
        STATUS         current
        DESCRIPTION    "Target port to add test channel(s) from.
                        Use tnWr20tfmPortConfigExecuteForcedAddDisposition
                        attribute to execute.  Note only one port
                        can be used at a time in this mode.
                        For advanced users only.

                        Not supported in current(7.0.2) release."
        DEFVAL          { notForced }
        ::= { tnWr20tfmPortChannelConfigEntry 2 }

--------------------------------------------------------------------------------
-- MPO Port Config Scalars
--------------------------------------------------------------------------------
    tnMpoPortConfigAttributeTotal OBJECT-TYPE
        SYNTAX         Integer32
        MAX-ACCESS     read-only
        STATUS         current
        DESCRIPTION    ""
        ::= { tnOpticalPortConfig 305 }

--------------------------------------------------------------------------------
-- MPO Optical Port Config Table
--------------------------------------------------------------------------------
    tnMpoPortConfigTable OBJECT-TYPE
        SYNTAX         SEQUENCE OF TnMpoPortConfigEntry
        MAX-ACCESS     not-accessible
        STATUS         current
        DESCRIPTION    "MPO port details"
        ::= { tnOpticalPortConfig 306 }

    tnMpoPortConfigEntry OBJECT-TYPE
        SYNTAX         TnMpoPortConfigEntry
        MAX-ACCESS     not-accessible
        STATUS         current
        DESCRIPTION    ""
        INDEX { ifIndex }
        ::= { tnMpoPortConfigTable 1 }

    TnMpoPortConfigEntry ::=
        SEQUENCE {
            tnMpoPortConfigFarEndIfIndex InterfaceIndexOrZero,
            tnMpoPortConfigFarEndType    INTEGER,
            tnMpoPortConfigDescription   SnmpAdminString
        }

    tnMpoPortConfigFarEndIfIndex  OBJECT-TYPE
        SYNTAX         InterfaceIndexOrZero
        MAX-ACCESS     read-create
        STATUS         current
        DESCRIPTION    "Connects the multi-fiber port to a far end
                        multi-fiber port if not connected.  View
                        the current far end multi-fiber port if
                        connected and 0 if not connected."
        DEFVAL         { 0 }
        ::= { tnMpoPortConfigEntry 1 }

    tnMpoPortConfigFarEndType OBJECT-TYPE
        SYNTAX         INTEGER {
                         notConnected(1),
                         internal(2)
                       }
        MAX-ACCESS     read-create
        STATUS         current
        DESCRIPTION    "The type of multi-fiber port connection.
                        notConnected(1): The port is not
                        connected.
                        internal(2): The port is internally
                        connected."
        DEFVAL         { notConnected }
        ::= { tnMpoPortConfigEntry 2 }

    tnMpoPortConfigDescription OBJECT-TYPE
        SYNTAX         SnmpAdminString
        MAX-ACCESS     read-create
        STATUS         current
        DESCRIPTION    "Configures the description of the
                        multi-fiber port.  Default is the
                        port name."
        DEFVAL         { "" }
        ::= { tnMpoPortConfigEntry 3 }

--------------------------------------------------------------------------------
-- 4AN100G Optical Port Config Scalars
--------------------------------------------------------------------------------
    tnIo4an100gPortConfigAttributeTotal OBJECT-TYPE
        SYNTAX         Integer32
        MAX-ACCESS     read-only
        STATUS         current
        DESCRIPTION    ""
        ::= { tnOpticalPortConfig 307 }

--------------------------------------------------------------------------------
-- 4AN100G Optical Port Config Table
--------------------------------------------------------------------------------
    tnIo4an100gPortConfigTable OBJECT-TYPE
        SYNTAX         SEQUENCE OF TnIo4an100gPortConfigEntry
        MAX-ACCESS     not-accessible
        STATUS         current
        DESCRIPTION    "The ports on a 4AN100G optical card."
        ::= { tnOpticalPortConfig 308 }

    tnIo4an100gPortConfigEntry OBJECT-TYPE
        SYNTAX         TnIo4an100gPortConfigEntry
        MAX-ACCESS     not-accessible
        STATUS         current
        DESCRIPTION    ""
        INDEX { ifIndex }
        ::= { tnIo4an100gPortConfigTable 1 }

    TnIo4an100gPortConfigEntry ::=
        SEQUENCE {
            tnIo4an100gPortConfigFunction  INTEGER
        }

    tnIo4an100gPortConfigFunction OBJECT-TYPE
        SYNTAX         INTEGER {
                         client(1)
                       }
        MAX-ACCESS     read-only
        STATUS         current
        DESCRIPTION    "Indicates the functional type of this 4AN100G port."
        ::= { tnIo4an100gPortConfigEntry 1 }

--------------------------------------------------------------------------------
-- 30AN10G Optical Port Config Scalars
--------------------------------------------------------------------------------
    tnIo30an10gPortConfigAttributeTotal OBJECT-TYPE
        SYNTAX         Integer32
        MAX-ACCESS     read-only
        STATUS         current
        DESCRIPTION    ""
        ::= { tnOpticalPortConfig 309 }

--------------------------------------------------------------------------------
-- 30AN10G Optical Port Config Table
--------------------------------------------------------------------------------
    tnIo30an10gPortConfigTable OBJECT-TYPE
        SYNTAX         SEQUENCE OF TnIo30an10gPortConfigEntry
        MAX-ACCESS     not-accessible
        STATUS         current
        DESCRIPTION    "The ports on a 30AN10G optical card."
        ::= { tnOpticalPortConfig 310 }

    tnIo30an10gPortConfigEntry OBJECT-TYPE
        SYNTAX         TnIo30an10gPortConfigEntry
        MAX-ACCESS     not-accessible
        STATUS         current
        DESCRIPTION    ""
        INDEX { ifIndex }
        ::= { tnIo30an10gPortConfigTable 1 }

    TnIo30an10gPortConfigEntry ::=
        SEQUENCE {
            tnIo30an10gPortConfigFunction  INTEGER
        }

    tnIo30an10gPortConfigFunction OBJECT-TYPE
        SYNTAX         INTEGER {
                         client(1)
                       }
        MAX-ACCESS     read-only
        STATUS         current
        DESCRIPTION    "Indicates the functional type of this 30AN10G port."
        ::= { tnIo30an10gPortConfigEntry 1 }

--------------------------------------------------------------------------------
-- 30AN300 Optical Port Config Scalars
--------------------------------------------------------------------------------
    tnIo30an300PortConfigAttributeTotal OBJECT-TYPE
        SYNTAX         Integer32
        MAX-ACCESS     read-only
        STATUS         current
        DESCRIPTION    ""
        ::= { tnOpticalPortConfig 311 }

--------------------------------------------------------------------------------
-- 30AN300 Optical Port Config Table
--------------------------------------------------------------------------------
    tnIo30an300PortConfigTable OBJECT-TYPE
        SYNTAX         SEQUENCE OF TnIo30an300PortConfigEntry
        MAX-ACCESS     not-accessible
        STATUS         current
        DESCRIPTION    "The ports on a 30AN300 optical card."
        ::= { tnOpticalPortConfig 312 }

    tnIo30an300PortConfigEntry OBJECT-TYPE
        SYNTAX         TnIo30an300PortConfigEntry
        MAX-ACCESS     not-accessible
        STATUS         current
        DESCRIPTION    ""
        INDEX { ifIndex }
        ::= { tnIo30an300PortConfigTable 1 }

    TnIo30an300PortConfigEntry ::=
        SEQUENCE {
            tnIo30an300PortConfigFunction  INTEGER
        }

    tnIo30an300PortConfigFunction OBJECT-TYPE
        SYNTAX         INTEGER {
                         client(1)
                       }
        MAX-ACCESS     read-only
        STATUS         current
        DESCRIPTION    "Indicates the functional type of this 30AN300 port."
        ::= { tnIo30an300PortConfigEntry 1 }

--------------------------------------------------------------------------------
-- 4AN400 Optical Port Config Scalars
--------------------------------------------------------------------------------
    tnIo4an400PortConfigAttributeTotal OBJECT-TYPE
        SYNTAX         Integer32
        MAX-ACCESS     read-only
        STATUS         current
        DESCRIPTION    ""
        ::= { tnOpticalPortConfig 313 }

--------------------------------------------------------------------------------
-- 4AN400 Optical Port Config Table
--------------------------------------------------------------------------------
    tnIo4an400PortConfigTable OBJECT-TYPE
        SYNTAX         SEQUENCE OF TnIo4an400PortConfigEntry
        MAX-ACCESS     not-accessible
        STATUS         current
        DESCRIPTION    "The ports on a 4AN400 optical card."
        ::= { tnOpticalPortConfig 314 }

    tnIo4an400PortConfigEntry OBJECT-TYPE
        SYNTAX         TnIo4an400PortConfigEntry
        MAX-ACCESS     not-accessible
        STATUS         current
        DESCRIPTION    ""
        INDEX { ifIndex }
        ::= { tnIo4an400PortConfigTable 1 }

    TnIo4an400PortConfigEntry ::=
        SEQUENCE {
            tnIo4an400PortConfigFunction  INTEGER
        }

    tnIo4an400PortConfigFunction OBJECT-TYPE
        SYNTAX         INTEGER {
                         client(1)
                       }
        MAX-ACCESS     read-only
        STATUS         current
        DESCRIPTION    "Indicates the functional type of this 4AN400 port."
        ::= { tnIo4an400PortConfigEntry 1 }

--------------------------------------------------------------------------------
-- 12P120 Optical Port Config Scalars
--------------------------------------------------------------------------------
    tn12p120PortConfigAttributeTotal OBJECT-TYPE
        SYNTAX         Integer32
        MAX-ACCESS     read-only
        STATUS         current
        DESCRIPTION    ""
        ::= { tnOpticalPortConfig 315 }

--------------------------------------------------------------------------------
-- 12P120 Optical Port Config Table
--------------------------------------------------------------------------------
    tn12p120PortConfigTable OBJECT-TYPE
        SYNTAX         SEQUENCE OF Tn12p120PortConfigEntry
        MAX-ACCESS     not-accessible
        STATUS         current
        DESCRIPTION    "The ports on a 12P120 optical card."
        ::= { tnOpticalPortConfig 316 }

    tn12p120PortConfigEntry OBJECT-TYPE
        SYNTAX         Tn12p120PortConfigEntry
        MAX-ACCESS     not-accessible
        STATUS         current
        DESCRIPTION    ""
        INDEX { ifIndex }
        ::= { tn12p120PortConfigTable 1 }

    Tn12p120PortConfigEntry ::=
        SEQUENCE {
            tn12p120PortConfigFunction  INTEGER
        }

    tn12p120PortConfigFunction OBJECT-TYPE
        SYNTAX         INTEGER {
                         network(1),
                         client(2),
                         evoa(3),
                         backplane(4)
                       }
        MAX-ACCESS     read-only
        STATUS         current
        DESCRIPTION    "Indicates the functional type of this 12P120 port."
        ::= { tn12p120PortConfigEntry 1 }

--------------------------------------------------------------------------------
-- 20P200 Optical Port Config Scalars
--------------------------------------------------------------------------------
    tn20p200PortConfigAttributeTotal OBJECT-TYPE
        SYNTAX         Integer32
        MAX-ACCESS     read-only
        STATUS         current
        DESCRIPTION    ""
        ::= { tnOpticalPortConfig 317 }

--------------------------------------------------------------------------------
-- 20P200 Optical Port Config Table
--------------------------------------------------------------------------------
    tn20p200PortConfigTable OBJECT-TYPE
        SYNTAX         SEQUENCE OF Tn20p200PortConfigEntry
        MAX-ACCESS     not-accessible
        STATUS         current
        DESCRIPTION    "The ports on a 20P200 optical card."
        ::= { tnOpticalPortConfig 318 }

    tn20p200PortConfigEntry OBJECT-TYPE
        SYNTAX         Tn20p200PortConfigEntry
        MAX-ACCESS     not-accessible
        STATUS         current
        DESCRIPTION    ""
        INDEX { ifIndex }
        ::= { tn20p200PortConfigTable 1 }

    Tn20p200PortConfigEntry ::=
        SEQUENCE {
            tn20p200PortConfigFunction  INTEGER
        }

    tn20p200PortConfigFunction OBJECT-TYPE
        SYNTAX         INTEGER {
                         network(1),
                         client(2),
                         backplane(3)
                       }
        MAX-ACCESS     read-only
        STATUS         current
        DESCRIPTION    "Indicates the functional type of this 20P200 port."
        ::= { tn20p200PortConfigEntry 1 }

--------------------------------------------------------------------------------
-- 1UD200 Optical Port Config Scalars
--------------------------------------------------------------------------------
    tn1ud200PortConfigAttributeTotal OBJECT-TYPE
        SYNTAX         Integer32
        MAX-ACCESS     read-only
        STATUS         current
        DESCRIPTION    ""
        ::= { tnOpticalPortConfig 319 }

--------------------------------------------------------------------------------
-- 1UD200 Optical Port Config Table
--------------------------------------------------------------------------------
    tn1ud200PortConfigTable OBJECT-TYPE
        SYNTAX         SEQUENCE OF Tn1ud200PortConfigEntry
        MAX-ACCESS     not-accessible
        STATUS         current
        DESCRIPTION    "The ports on a 1UD200 optical card."
        ::= { tnOpticalPortConfig 320 }

    tn1ud200PortConfigEntry OBJECT-TYPE
        SYNTAX         Tn1ud200PortConfigEntry
        MAX-ACCESS     not-accessible
        STATUS         current
        DESCRIPTION    ""
        INDEX { ifIndex }
        ::= { tn1ud200PortConfigTable 1 }

    Tn1ud200PortConfigEntry ::=
        SEQUENCE {
            tn1ud200PortConfigFunction  INTEGER
        }

    tn1ud200PortConfigFunction OBJECT-TYPE
        SYNTAX         INTEGER {
                         network(1),
                         backplane(2)
                       }
        MAX-ACCESS     read-only
        STATUS         current
        DESCRIPTION    "Indicates the functional type of this 1UD200 port."
        ::= { tn1ud200PortConfigEntry 1 }

--------------------------------------------------------------------------------
-- OT130SNQ10 Optical Port Config Scalars
--------------------------------------------------------------------------------
    tnOt130snq10PortConfigAttributeTotal OBJECT-TYPE
        SYNTAX         Integer32
        MAX-ACCESS     read-only
        STATUS         current
        DESCRIPTION    ""
        ::= { tnOpticalPortConfig 321 }

--------------------------------------------------------------------------------
-- OT130SNQ10 Optical Port Config Table
--------------------------------------------------------------------------------
    tnOt130snq10PortConfigTable OBJECT-TYPE
        SYNTAX         SEQUENCE OF TnOt130snq10PortConfigEntry
        MAX-ACCESS     not-accessible
        STATUS         current
        DESCRIPTION    "The ports on a OT130SNQ10 optical card."
        ::= { tnOpticalPortConfig 322 }

    tnOt130snq10PortConfigEntry OBJECT-TYPE
        SYNTAX         TnOt130snq10PortConfigEntry
        MAX-ACCESS     not-accessible
        STATUS         current
        DESCRIPTION    ""
        INDEX { ifIndex }
        ::= { tnOt130snq10PortConfigTable 1 }

    TnOt130snq10PortConfigEntry ::=
        SEQUENCE {
            tnOt130snq10PortConfigFunction  INTEGER
        }

    tnOt130snq10PortConfigFunction OBJECT-TYPE
        SYNTAX         INTEGER {
                         network(1),
                         client(2)
                       }
        MAX-ACCESS     read-only
        STATUS         current
        DESCRIPTION    "Indicates the functional type of this OT130SNQ10 port."
        ::= { tnOt130snq10PortConfigEntry 1 }

--------------------------------------------------------------------------------
-- IROADMV Optical Port Config Scalars
--------------------------------------------------------------------------------
    tnIroadmvPortConfigAttributeTotal OBJECT-TYPE
        SYNTAX         Integer32
        MAX-ACCESS     read-only
        STATUS         current
        DESCRIPTION    ""
        ::= { tnOpticalPortConfig 323 }

--------------------------------------------------------------------------------
-- IROADMV Optical Port Config Table
--------------------------------------------------------------------------------
    tnIroadmvPortConfigTable OBJECT-TYPE
        SYNTAX         SEQUENCE OF TnIroadmvPortConfigEntry
        MAX-ACCESS     not-accessible
        STATUS         current
        DESCRIPTION    "The ports on a IROADMV optical card."
        ::= { tnOpticalPortConfig 324 }

    tnIroadmvPortConfigEntry OBJECT-TYPE
        SYNTAX         TnIroadmvPortConfigEntry
        MAX-ACCESS     not-accessible
        STATUS         current
        DESCRIPTION    ""
        INDEX { ifIndex }
        ::= { tnIroadmvPortConfigTable 1 }

    TnIroadmvPortConfigEntry ::=
        SEQUENCE {
            tnIroadmvPortConfigFunction           INTEGER
        }

    tnIroadmvPortConfigFunction OBJECT-TYPE
        SYNTAX         INTEGER {
                         lineIn(1),
                         inv(2),
                         osc(3),
                         lineOut(4),
                         oscSfp(5),
                         adt(6),
                         dcm(7)
                       }
        MAX-ACCESS     read-only
        STATUS         current
        DESCRIPTION    "Indicates the functional type of this IROADMV port."
        ::= { tnIroadmvPortConfigEntry 1 }

--------------------------------------------------------------------------------
-- IROADMF Optical Port Config Scalars
--------------------------------------------------------------------------------
    tnIroadmfPortConfigAttributeTotal OBJECT-TYPE
        SYNTAX         Integer32
        MAX-ACCESS     read-only
        STATUS         current
        DESCRIPTION    ""
        ::= { tnOpticalPortConfig 325 }

--------------------------------------------------------------------------------
-- IROADMF Optical Port Config Table
--------------------------------------------------------------------------------
    tnIroadmfPortConfigTable OBJECT-TYPE
        SYNTAX         SEQUENCE OF TnIroadmfPortConfigEntry
        MAX-ACCESS     not-accessible
        STATUS         current
        DESCRIPTION    "The ports on a IROADMF optical card."
        ::= { tnOpticalPortConfig 326 }

    tnIroadmfPortConfigEntry OBJECT-TYPE
        SYNTAX         TnIroadmfPortConfigEntry
        MAX-ACCESS     not-accessible
        STATUS         current
        DESCRIPTION    ""
        INDEX { ifIndex }
        ::= { tnIroadmfPortConfigTable 1 }

    TnIroadmfPortConfigEntry ::=
        SEQUENCE {
            tnIroadmfPortConfigFunction  INTEGER
        }

    tnIroadmfPortConfigFunction OBJECT-TYPE
        SYNTAX         INTEGER {
                         lineIn(1),
                         inv(2),
                         osc(3),
                         lineOut(4),
                         oscSfp(5),
                         adt(6)
                       }
        MAX-ACCESS     read-only
        STATUS         current
        DESCRIPTION    "Indicates the functional type of this IROADMF port."
        ::= { tnIroadmfPortConfigEntry 1 }

--------------------------------------------------------------------------------
-- IROADM Optical Port Config Scalars
--------------------------------------------------------------------------------
    tnIroadmPortConfigAttributeTotal OBJECT-TYPE
        SYNTAX         Integer32
        MAX-ACCESS     read-only
        STATUS         current
        DESCRIPTION    "Total no of attributes in
                        tnIroadmPortConfigTable."
        ::= { tnOpticalPortConfig 327 }

--------------------------------------------------------------------------------
-- IROADM Optical Port Config Table
--------------------------------------------------------------------------------
    tnIroadmPortConfigTable OBJECT-TYPE
        SYNTAX         SEQUENCE OF TnIroadmPortConfigEntry
        MAX-ACCESS     not-accessible
        STATUS         current
        DESCRIPTION    "Attributes related to IROADM optical cards."
        ::= { tnOpticalPortConfig 328 }

    tnIroadmPortConfigEntry OBJECT-TYPE
        SYNTAX         TnIroadmPortConfigEntry
        MAX-ACCESS     not-accessible
        STATUS         current
        DESCRIPTION    ""
        INDEX { ifIndex }
        ::= { tnIroadmPortConfigTable 1 }

    TnIroadmPortConfigEntry ::=
        SEQUENCE {
            tnIroadmPortConfigPowerGain              Unsigned32,
            tnIroadmPortConfigPowerGainBackoff       Unsigned32,
            tnIroadmPortConfigTargetTilt             Integer32,
            tnIroadmPortConfigVoaSet                 Unsigned32,
            tnIroadmPortConfigNominalSpanLossOut     Integer32,
            tnIroadmPortConfigFiberTypeOut           INTEGER,
            tnIroadmPortConfigFiberLengthKm          Unsigned32,
            tnIroadmPortConfigAddMinChannelPower     Integer32,
            tnIroadmPortConfigEgressOaRippleToRemove Unsigned32,
            tnIroadmPortConfigExpressMinChannelPower Integer32,
            tnIroadmPortConfigIngressOaGainMin       Unsigned32,
            tnIroadmPortConfigIngressOaGainMax       Unsigned32,
            tnIroadmPortConfigTargetPpcOut           Integer32,
            tnIroadmPortConfigIngressOaTargetPpcOut  Integer32,
            tnIroadmPortConfigIngressOaTargetPpcAdj  Integer32,
            tnIroadmPortConfigSignalFailThreshold    Unsigned32,
            tnIroadmPortConfigSignalDegradeThreshold Unsigned32,
            tnIroadmPortConfigAprDisable             TruthValue,
            tnIroadmPortConfigForcedTargetPpcOut     Integer32,
            tnIroadmPortConfigLineDcmConnAddress     InterfaceIndexOrZero 
        }

    tnIroadmPortConfigPowerGain OBJECT-TYPE
        SYNTAX         Unsigned32
        UNITS          "mB"
        MAX-ACCESS     read-create
        STATUS         current
        DESCRIPTION    "Current configurable range:
                       
                       For LineOut: 
                       Iroadmv: 1500 to 2500
                       Iroadmf: 1500 to 2100.
                       For LineIn: 
                       Iroadmv: 1500 to 3100
                       Iroadmf: 1300 to 1900.

                       Current defaults:
                       
                       For LineOut: 
                       Iroadmv: 2000
                       Iroadmf: 1800.
                       For LineIn:
                       Iroadmv: 1500
                       Iroadmf: 1600."
        ::= { tnIroadmPortConfigEntry 1 }

    tnIroadmPortConfigPowerGainBackoff OBJECT-TYPE
        SYNTAX         Unsigned32
        UNITS          "mB"
        MAX-ACCESS     read-create
        STATUS         current
        DESCRIPTION    "Current configurable range:

                        0 to 1000."
        DEFVAL         { 0 }
        ::= { tnIroadmPortConfigEntry 2 }

    tnIroadmPortConfigTargetTilt OBJECT-TYPE
        SYNTAX         Integer32
        UNITS          "mB"
        MAX-ACCESS     read-create
        STATUS         current
        DESCRIPTION    "Current configurable range:
                        
                        For LineOut:
                        No configurable range.
                        
                        For LineIn:
                        Iroadmf: 0
                        Iroadmv: -300 to 300."
        DEFVAL         { 0 }
        ::= { tnIroadmPortConfigEntry 3 }

    tnIroadmPortConfigVoaSet OBJECT-TYPE
        SYNTAX         Unsigned32
        UNITS          "mB"
        MAX-ACCESS     read-create
        STATUS         current
        DESCRIPTION    ""
        ::= { tnIroadmPortConfigEntry 4 }

    tnIroadmPortConfigNominalSpanLossOut OBJECT-TYPE
        SYNTAX         Integer32
        UNITS          "mB"
        MAX-ACCESS     read-create
        STATUS         current
        DESCRIPTION    ""
        ::= { tnIroadmPortConfigEntry 5 }

    tnIroadmPortConfigFiberTypeOut OBJECT-TYPE
        SYNTAX         INTEGER {
                         notConfigured(1),
                         ssmf(2),
                         eleaf(3),
                         twrs(4),
                         dsf(5),
                         twc(6),
                         twp(7),
                         ls(8)
                       }
        MAX-ACCESS     read-create
        STATUS         current
        DESCRIPTION    ""
        DEFVAL         { ssmf }
        ::= { tnIroadmPortConfigEntry 6 }

    tnIroadmPortConfigFiberLengthKm OBJECT-TYPE
        SYNTAX         Unsigned32
        UNITS          "kilometers"
        MAX-ACCESS     read-create
        STATUS         current
        DESCRIPTION    "Current configurable range:
                        
                        0 to 150
                        Current default:
                        
                        Iroadmv:70
                        Iroadmf:40."
        ::= { tnIroadmPortConfigEntry 7 }

    tnIroadmPortConfigAddMinChannelPower OBJECT-TYPE
        SYNTAX         Integer32
        UNITS          "mBm"
        MAX-ACCESS     read-create
        STATUS         current
        DESCRIPTION    "Current configurable range:
                         
                        -2000 to -500."  
        DEFVAL         { -1300 }
        ::= { tnIroadmPortConfigEntry 8 }

    tnIroadmPortConfigEgressOaRippleToRemove OBJECT-TYPE
        SYNTAX         Unsigned32
        UNITS          "mB"
        MAX-ACCESS     read-create
        STATUS         current
        DESCRIPTION    "Current configurable range:

                        0 to 600. 
                        Current default:
                        
                        Iroadmv:150
                        Iroadmf:150."
        ::= { tnIroadmPortConfigEntry 9 }

    tnIroadmPortConfigExpressMinChannelPower OBJECT-TYPE
        SYNTAX         Integer32
        UNITS          "mBm"
        MAX-ACCESS     read-create
        STATUS         current
        DESCRIPTION    "Current configurable range:

                        -2000 to -500."
        DEFVAL         { -1300 }
        ::= { tnIroadmPortConfigEntry 10 }

    tnIroadmPortConfigIngressOaGainMin OBJECT-TYPE
        SYNTAX         Unsigned32
        UNITS          "mB"
        MAX-ACCESS     read-create
        STATUS         current
        DESCRIPTION    "Current configurable range:
                        Iroadmv: 1500 to 2500.

                        Current default:
                        
                        Iroadmv:1500."
        ::= { tnIroadmPortConfigEntry 11 }

    tnIroadmPortConfigIngressOaGainMax OBJECT-TYPE
        SYNTAX         Unsigned32
        UNITS          "mB"
        MAX-ACCESS     read-create
        STATUS         current
        DESCRIPTION    "Current configurable range:
                        Iroadmv: 1500 to 3100

                        Current default:
        
                        Iroadmv:2500."
        ::= { tnIroadmPortConfigEntry 12 }

    tnIroadmPortConfigTargetPpcOut OBJECT-TYPE
        SYNTAX         Integer32
        UNITS          "mBm"
        MAX-ACCESS     read-create
        STATUS         current
        DESCRIPTION    "Current configurable range:

                        -3000 to 1100
                        Current default:
                        
                        Iroadmv:56
                        Iroadmf:56."
        ::= { tnIroadmPortConfigEntry 13 }

    tnIroadmPortConfigIngressOaTargetPpcOut OBJECT-TYPE
        SYNTAX         Integer32
        UNITS          "mBm"
        MAX-ACCESS     read-create
        STATUS         current
        DESCRIPTION    "Current configurable range:
                        -3000 to 1100

                        Current default:
                        Iroadmv:50
                        Iroadmf:550."
        ::= { tnIroadmPortConfigEntry 14 }

    tnIroadmPortConfigIngressOaTargetPpcAdj OBJECT-TYPE
        SYNTAX         Integer32
        UNITS          "mB"
        MAX-ACCESS     read-create
        STATUS         current
        DESCRIPTION    "Current configurable range:
                        
                        -1000 to 0."
        DEFVAL         { 0 }
        ::= { tnIroadmPortConfigEntry 15 }

    tnIroadmPortConfigSignalFailThreshold OBJECT-TYPE
        SYNTAX         Unsigned32
        MAX-ACCESS     read-create
        STATUS         current
        DESCRIPTION    "Current configurable range:

                        4 or 5."
        DEFVAL         { 4 }
        ::= { tnIroadmPortConfigEntry 16 }

    tnIroadmPortConfigSignalDegradeThreshold OBJECT-TYPE
        SYNTAX         Unsigned32
        MAX-ACCESS     read-create
        STATUS         current
        DESCRIPTION    "Current configurable range:

                        5 to 9."
        DEFVAL         { 6 }
        ::= { tnIroadmPortConfigEntry 17 }

    tnIroadmPortConfigAprDisable OBJECT-TYPE
        SYNTAX         TruthValue
        MAX-ACCESS     read-create
        STATUS         current
        DESCRIPTION    "Auto Power Reduction disable."
        DEFVAL         { false }
        ::= { tnIroadmPortConfigEntry 18 }

    tnIroadmPortConfigForcedTargetPpcOut OBJECT-TYPE
        SYNTAX         Integer32
        UNITS          "mBm"
        MAX-ACCESS     read-create
        STATUS         current
        DESCRIPTION    "Current configurable range:

                        -9900,
                        -1500 to 1000"
        DEFVAL         { -9900 }
        ::= { tnIroadmPortConfigEntry 19 }

    tnIroadmPortConfigLineDcmConnAddress OBJECT-TYPE
        SYNTAX         InterfaceIndexOrZero
        MAX-ACCESS     read-write
        STATUS         current
        DESCRIPTION    " "
        ::= { tnIroadmPortConfigEntry 20 }

--------------------------------------------------------------------------------
-- MON-OCM Optical Port Config Scalars
--------------------------------------------------------------------------------
    tnMonOcmPortConfigAttributeTotal OBJECT-TYPE
        SYNTAX         Integer32
        MAX-ACCESS     read-only
        STATUS         current
        DESCRIPTION    "Total no of attributes in tnMonOcmPortConfigTable."
        ::= { tnOpticalPortConfig 329 }

--------------------------------------------------------------------------------
-- MON-OCM Optical Port Config Table
--------------------------------------------------------------------------------
    tnMonOcmPortConfigTable OBJECT-TYPE
        SYNTAX         SEQUENCE OF TnMonOcmPortConfigEntry
        MAX-ACCESS     not-accessible
        STATUS         current
        DESCRIPTION    "The ports on a MON-OCM card."
        ::= { tnOpticalPortConfig 330 }

    tnMonOcmPortConfigEntry OBJECT-TYPE
        SYNTAX         TnMonOcmPortConfigEntry
        MAX-ACCESS     not-accessible
        STATUS         current
        DESCRIPTION    ""
        INDEX { ifIndex }
        ::= { tnMonOcmPortConfigTable 1 }

    TnMonOcmPortConfigEntry ::=
        SEQUENCE {
            tnMonOcmPortConfigFunction  INTEGER,
            tnMonOcmPortConfigUserLabel SnmpAdminString (SIZE(0..255))
        }

    tnMonOcmPortConfigFunction OBJECT-TYPE
        SYNTAX         INTEGER {
                         output(1),
                         input(2),
                         monitor(3)
                       }
        MAX-ACCESS     read-only
        STATUS         current
        DESCRIPTION    "Indicates the functional type of this MON-OCM port."
        ::= { tnMonOcmPortConfigEntry 1 }

    tnMonOcmPortConfigUserLabel OBJECT-TYPE
        SYNTAX         SnmpAdminString (SIZE(0..255))
        MAX-ACCESS     read-create
        STATUS         current
        DESCRIPTION    "User text field for labeling port usage."
        ::= { tnMonOcmPortConfigEntry 2 }

--------------------------------------------------------------------------------
-- Ul2uc400 Optical Port Config Scalars
--------------------------------------------------------------------------------
    tnUl2uc400PortConfigAttributeTotal OBJECT-TYPE
        SYNTAX         Integer32
        MAX-ACCESS     read-only
        STATUS         current
        DESCRIPTION    "Total no of attributes in  tnUl2uc400PortConfigTable"
        ::= { tnOpticalPortConfig 331 }

--------------------------------------------------------------------------------
-- Ul2uc400 Optical Port Config Table
--------------------------------------------------------------------------------
    tnUl2uc400PortConfigTable OBJECT-TYPE
        SYNTAX         SEQUENCE OF TnUl2uc400PortConfigEntry
        MAX-ACCESS     not-accessible
        STATUS         current
        DESCRIPTION    "The ports on a Ul2uc400 optical card."
        ::= { tnOpticalPortConfig 332 }

    tnUl2uc400PortConfigEntry OBJECT-TYPE
        SYNTAX         TnUl2uc400PortConfigEntry
        MAX-ACCESS     not-accessible
        STATUS         current
        DESCRIPTION    ""
        INDEX { ifIndex }
        ::= { tnUl2uc400PortConfigTable 1 }

    TnUl2uc400PortConfigEntry ::=
        SEQUENCE {
            tnUl2uc400PortConfigFunction  INTEGER
        }

    tnUl2uc400PortConfigFunction OBJECT-TYPE
        SYNTAX         INTEGER {
                         network(1)
                       }
        MAX-ACCESS     read-only
        STATUS         current
        DESCRIPTION    "Indicates the functional type of this Ul2uc400 port."
        ::= { tnUl2uc400PortConfigEntry 1 }


--------------------------------------------------------------------------------
-- Ul4uc400 Optical Port Config Scalars
--------------------------------------------------------------------------------
    tnUl4uc400PortConfigAttributeTotal OBJECT-TYPE
        SYNTAX         Integer32
        MAX-ACCESS     read-only
        STATUS         current
        DESCRIPTION    "Total no of attributes in tnUl4uc400PortConfigTable."
        ::= { tnOpticalPortConfig 333 }

--------------------------------------------------------------------------------
-- Ul4uc400 Optical Port Config Table
--------------------------------------------------------------------------------
    tnUl4uc400PortConfigTable OBJECT-TYPE
        SYNTAX         SEQUENCE OF TnUl4uc400PortConfigEntry
        MAX-ACCESS     not-accessible
        STATUS         current
        DESCRIPTION    "The ports on a Ul4uc400 optical card."
        ::= { tnOpticalPortConfig 334 }

    tnUl4uc400PortConfigEntry OBJECT-TYPE
        SYNTAX         TnUl4uc400PortConfigEntry
        MAX-ACCESS     not-accessible
        STATUS         current
        DESCRIPTION    ""
        INDEX { ifIndex }
        ::= { tnUl4uc400PortConfigTable 1 }

    TnUl4uc400PortConfigEntry ::=
        SEQUENCE {
            tnUl4uc400PortConfigFunction  INTEGER
        }

    tnUl4uc400PortConfigFunction OBJECT-TYPE
        SYNTAX         INTEGER {
                         network(1)
                       }
        MAX-ACCESS     read-only
        STATUS         current
        DESCRIPTION    "Indicates the functional type of this Ul4uc400 port."
        ::= { tnUl4uc400PortConfigEntry 1 }

--------------------------------------------------------------------------------
-- Ul20uc200 Optical Port Config Scalars
--------------------------------------------------------------------------------
    tnUl20uc200PortConfigAttributeTotal OBJECT-TYPE
        SYNTAX         Integer32
        MAX-ACCESS     read-only
        STATUS         current
        DESCRIPTION    "Total no of attributes in tnUl20uc200PortConfigTable."
        ::= { tnOpticalPortConfig 335 }

--------------------------------------------------------------------------------
-- Ul20uc200 Optical Port Config Table
--------------------------------------------------------------------------------
    tnUl20uc200PortConfigTable OBJECT-TYPE
        SYNTAX         SEQUENCE OF TnUl20uc200PortConfigEntry
        MAX-ACCESS     not-accessible
        STATUS         current
        DESCRIPTION    "The ports on a Ul20uc200 optical card."
        ::= { tnOpticalPortConfig 336 }

    tnUl20uc200PortConfigEntry OBJECT-TYPE
        SYNTAX         TnUl20uc200PortConfigEntry
        MAX-ACCESS     not-accessible
        STATUS         current
        DESCRIPTION    ""
        INDEX { ifIndex }
        ::= { tnUl20uc200PortConfigTable 1 }

    TnUl20uc200PortConfigEntry ::=
        SEQUENCE {
            tnUl20uc200PortConfigFunction  INTEGER
        }

    tnUl20uc200PortConfigFunction OBJECT-TYPE
        SYNTAX         INTEGER {
                         network(1)
                       }
        MAX-ACCESS     read-only
        STATUS         current
        DESCRIPTION    "Indicates the functional type of this Ul20uc200 port."
        ::= { tnUl20uc200PortConfigEntry 1 }

--------------------------------------------------------------------------------
-- D5X500 Optical Port Config Scalars
--------------------------------------------------------------------------------
    tnD5x500PortConfigAttributeTotal OBJECT-TYPE
        SYNTAX         Integer32
        MAX-ACCESS     read-only
        STATUS         current
        DESCRIPTION    ""
        ::= { tnOpticalPortConfig 337 }

--------------------------------------------------------------------------------
-- D5X500 Optical Port Config Table
--------------------------------------------------------------------------------
    tnD5x500PortConfigTable OBJECT-TYPE
        SYNTAX         SEQUENCE OF TnD5x500PortConfigEntry
        MAX-ACCESS     not-accessible
        STATUS         current
        DESCRIPTION    "The ports on a D5X500 optical card."
        ::= { tnOpticalPortConfig 338 }

    tnD5x500PortConfigEntry OBJECT-TYPE
        SYNTAX         TnD5x500PortConfigEntry
        MAX-ACCESS     not-accessible
        STATUS         current
        DESCRIPTION    ""
        INDEX { ifIndex }
        ::= { tnD5x500PortConfigTable 1 }

    TnD5x500PortConfigEntry ::=
        SEQUENCE {
            tnD5x500PortConfigFunction INTEGER
        }

    tnD5x500PortConfigFunction OBJECT-TYPE
        SYNTAX         INTEGER {
                         network(1),
                         client(2),
                         backplane(3)
                       }
        MAX-ACCESS     read-only
        STATUS         current
        DESCRIPTION    "Indicates the functional type of this D5X500 port."
        ::= { tnD5x500PortConfigEntry 1 }

--------------------------------------------------------------------------------
-- OTS11M100 Optical Port Config Scalars
--------------------------------------------------------------------------------
    tnOtS11M100PortConfigAttributeTotal OBJECT-TYPE
        SYNTAX         Integer32
        MAX-ACCESS     read-only
        STATUS         current
        DESCRIPTION    ""
        ::= { tnOpticalPortConfig 339 }

--------------------------------------------------------------------------------
-- OTS11M100 Optical Port Config Table
--------------------------------------------------------------------------------
    tnOtS11M100PortConfigTable OBJECT-TYPE
        SYNTAX         SEQUENCE OF TnOtS11M100PortConfigEntry
        MAX-ACCESS     not-accessible
        STATUS         current
        DESCRIPTION    "The ports on a OTS11M100 optical card."
        ::= { tnOpticalPortConfig 340 }

    tnOtS11M100PortConfigEntry OBJECT-TYPE
        SYNTAX         TnOtS11M100PortConfigEntry
        MAX-ACCESS     not-accessible
        STATUS         current
        DESCRIPTION    ""
        INDEX { ifIndex }
        ::= { tnOtS11M100PortConfigTable 1 }

    TnOtS11M100PortConfigEntry ::=
        SEQUENCE {
            tnOtS11M100PortConfigFunction  INTEGER
        }

    tnOtS11M100PortConfigFunction OBJECT-TYPE
        SYNTAX         INTEGER {
                         network(1),
                         client(2)
                       }
        MAX-ACCESS     read-only
        STATUS         current
        DESCRIPTION    "Indicates the functional type of this OtS11M100 port."
        ::= { tnOtS11M100PortConfigEntry 1 }

--------------------------------------------------------------------------------
-- MON-OTDR(MON-Optical Time Domain Reflectometer) Optical Port Config Scalars
--------------------------------------------------------------------------------
    tnMonOtdrPortConfigAttributeTotal OBJECT-TYPE
        SYNTAX         Integer32
        MAX-ACCESS     read-only
        STATUS         current
        DESCRIPTION    ""
        ::= { tnOpticalPortConfig 341 }
--------------------------------------------------------------------------------
-- MON-OTDR(MON-Optical Time Domain Reflectometer)Optical Port Config Table
--------------------------------------------------------------------------------
    tnMonOtdrPortConfigTable OBJECT-TYPE
        SYNTAX         SEQUENCE OF TnMonOtdrPortConfigEntry
        MAX-ACCESS     not-accessible
        STATUS         current
        DESCRIPTION    "The ports on an MON-OTDR optical card."
        ::= { tnOpticalPortConfig 342 }

    tnMonOtdrPortConfigEntry OBJECT-TYPE
        SYNTAX         TnMonOtdrPortConfigEntry
        MAX-ACCESS     not-accessible
        STATUS         current
        DESCRIPTION    ""
        INDEX { ifIndex }
        ::= { tnMonOtdrPortConfigTable 1 }

    TnMonOtdrPortConfigEntry ::=
        SEQUENCE {
            tnMonOtdrPortConfigFunction     INTEGER,
            tnMonOtdrPortConfigConnAddress  InterfaceIndexOrZero
        }

    tnMonOtdrPortConfigFunction OBJECT-TYPE
        SYNTAX         INTEGER {
                         lineIn(1),
                         otdrRx(2),
                         otdrTx(3),
                         lineOut(4),
                         sigIn(5),
                         sigOut(6)
                       }
        MAX-ACCESS     read-only
        STATUS         current
        DESCRIPTION    "Indicates the functional type of this MON-OTDR port."
        ::= { tnMonOtdrPortConfigEntry 1 }

    tnMonOtdrPortConfigConnAddress OBJECT-TYPE
        SYNTAX         InterfaceIndexOrZero
        MAX-ACCESS     read-create
        STATUS         current
        DESCRIPTION    "Specifies the assigned LD port that
                        is connected to the MON-OTDR port."
        ::= { tnMonOtdrPortConfigEntry 2 }

--------------------------------------------------------------------------------
-- PSS96 Power Filter Port Config Scalars
--------------------------------------------------------------------------------
    tnPSS96PowerFilterPortConfigAttributeTotal OBJECT-TYPE
        SYNTAX         Integer32
        MAX-ACCESS     read-only
        STATUS         current
        DESCRIPTION    ""
        ::= { tnOpticalPortConfig 343 }

--------------------------------------------------------------------------------
-- PSS96 Power Filter Port Config Table
--------------------------------------------------------------------------------
    tnPSS96PowerFilterPortConfigTable OBJECT-TYPE
        SYNTAX         SEQUENCE OF TnPSS96PowerFilterPortConfigEntry
        MAX-ACCESS     not-accessible
        STATUS         current
        DESCRIPTION    "The ports on a PSS96PowerFilter optical card."
        ::= { tnOpticalPortConfig 344 }

    tnPSS96PowerFilterPortConfigEntry OBJECT-TYPE
        SYNTAX         TnPSS96PowerFilterPortConfigEntry
        MAX-ACCESS     not-accessible
        STATUS         current
        DESCRIPTION    ""
        INDEX { ifIndex }
        ::= { tnPSS96PowerFilterPortConfigTable 1 }

    TnPSS96PowerFilterPortConfigEntry ::=
        SEQUENCE {
            tnPSS96PowerFilterPortConfigFunction  INTEGER,
            tnPSS96ExpectedAmps                   Unsigned32
        }

    tnPSS96PowerFilterPortConfigFunction OBJECT-TYPE
        SYNTAX         INTEGER {
                         powerFilterPort1(1),
                         powerFilterPort2(2),
                         powerFilterPort3(3)
                       }
        MAX-ACCESS     read-only
        STATUS         current
        DESCRIPTION    "Indicates the functional type of this PSS96 PowerFilter port."
        ::= { tnPSS96PowerFilterPortConfigEntry 1 } 

    tnPSS96ExpectedAmps OBJECT-TYPE
        SYNTAX         Unsigned32
        MAX-ACCESS     read-write
        STATUS         current
        DESCRIPTION    "Displays the configured expected amps of the circuit breaker of the power branch "
        DEFVAL         { 60 }
        ::= { tnPSS96PowerFilterPortConfigEntry 2 }

--------------------------------------------------------------------------------
-- 12CE120 Optical Port Config Scalars
--------------------------------------------------------------------------------
     tn12ce120PortConfigAttributeTotal OBJECT-TYPE
         SYNTAX         Integer32
         MAX-ACCESS     read-only
         STATUS         current
         DESCRIPTION    ""
         ::= { tnOpticalPortConfig 345}

-------------------------------------------------------------------------------
-- 12CE120 Optical Port Config Table
-------------------------------------------------------------------------------
     tn12ce120PortConfigTable OBJECT-TYPE
         SYNTAX         SEQUENCE OF Tn12ce120PortConfigEntry
         MAX-ACCESS     not-accessible
         STATUS         current
         DESCRIPTION    "The ports on a 12CE120 optical card."
         ::= { tnOpticalPortConfig 346}

     tn12ce120PortConfigEntry OBJECT-TYPE
         SYNTAX         Tn12ce120PortConfigEntry
         MAX-ACCESS     not-accessible
         STATUS         current
         DESCRIPTION    ""
         INDEX { ifIndex }
         ::= { tn12ce120PortConfigTable 1 }

     Tn12ce120PortConfigEntry ::=
         SEQUENCE {
             tn12ce120PortConfigFunction INTEGER
         }

     tn12ce120PortConfigFunction OBJECT-TYPE
         SYNTAX         INTEGER {
                          network(1),
                          backplane(2),
                          tod(3)
                         }
         MAX-ACCESS     read-only
         STATUS         current
         DESCRIPTION    "Indicates the functional type of this 12CE120 port."
         ::= { tn12ce120PortConfigEntry 1 }

-------------------------------------------------------------------------------
-- 1CE100 Optical Port Config Scalars
-------------------------------------------------------------------------------
     tn1ce100PortConfigAttributeTotal OBJECT-TYPE
         SYNTAX         Integer32
         MAX-ACCESS     read-only
         STATUS         current
         DESCRIPTION    ""
         ::= { tnOpticalPortConfig 347}

-------------------------------------------------------------------------------
-- 1CE100 Optical Port Config Table
-------------------------------------------------------------------------------
     tn1ce100PortConfigTable OBJECT-TYPE
         SYNTAX         SEQUENCE OF Tn1ce100PortConfigEntry
         MAX-ACCESS     not-accessible
         STATUS         current
         DESCRIPTION    "The ports on a 1CE100 optical card."
         ::= { tnOpticalPortConfig 348}

     tn1ce100PortConfigEntry OBJECT-TYPE
         SYNTAX         Tn1ce100PortConfigEntry
         MAX-ACCESS     not-accessible
         STATUS         current
         DESCRIPTION    ""
         INDEX { ifIndex }
         ::= { tn1ce100PortConfigTable 1 }

     Tn1ce100PortConfigEntry ::=
         SEQUENCE {
             tn1ce100PortConfigFunction INTEGER
         }

     tn1ce100PortConfigFunction OBJECT-TYPE
         SYNTAX         INTEGER {
                          client(1),
                          backplane(2),
                          tod(3)
                         }
         MAX-ACCESS     read-only
         STATUS         current
         DESCRIPTION    "Indicates the functional type of this 1CE100 port."
         ::= { tn1ce100PortConfigEntry 1 }

--------------------------------------------------------------------------------
-- LCI1000 Optical Port Config Scalars
--------------------------------------------------------------------------------
    tnLcI1000PortConfigAttributeTotal OBJECT-TYPE
        SYNTAX         Integer32 
        MAX-ACCESS     read-only 
        STATUS         current
        DESCRIPTION    ""
        ::= { tnOpticalPortConfig 349 }

--------------------------------------------------------------------------------
-- LCI1000 Optical Port Config Table
--------------------------------------------------------------------------------
    tnLcI1000PortConfigTable OBJECT-TYPE
        SYNTAX         SEQUENCE OF TnLcI1000PortConfigEntry
        MAX-ACCESS     not-accessible
        STATUS         current
        DESCRIPTION    "The ports on an LcI1000 optical card."
        ::= { tnOpticalPortConfig 350 }
 
    tnLcI1000PortConfigEntry  OBJECT-TYPE
        SYNTAX         TnLcI1000PortConfigEntry 
        MAX-ACCESS     not-accessible
        STATUS         current
        DESCRIPTION    ""
        INDEX { ifIndex }
        ::= { tnLcI1000PortConfigTable 1 }
 
    TnLcI1000PortConfigEntry ::= SEQUENCE {
        tnLcI1000PortConfigFunction INTEGER
    }

    tnLcI1000PortConfigFunction OBJECT-TYPE
        SYNTAX         INTEGER{
                         network(1),
                         client(2)
                       }
        MAX-ACCESS     read-only 
        STATUS         current
        DESCRIPTION    "Indicates the functional type of
                        this LcI1000 port."
        ::= { tnLcI1000PortConfigEntry 1 }

-------------------------------------------------------------------------------
-- Optical Port Information
--------------------------------------------------------------------------------

--------------------------------------------------------------------------------
-- SDH Optical Port Info Scalars
--------------------------------------------------------------------------------
    tnSdhPortInfoAttributeTotal OBJECT-TYPE
        SYNTAX         Integer32
        MAX-ACCESS     read-only
        STATUS         current
        DESCRIPTION    ""
        ::= { tnOpticalPortInfo 1 }

--------------------------------------------------------------------------------
-- SDH Optical Port Info Table
--------------------------------------------------------------------------------
    tnSdhPortInfoTable OBJECT-TYPE
        SYNTAX         SEQUENCE OF TnSdhPortInfoEntry
        MAX-ACCESS     not-accessible
        STATUS         current
        DESCRIPTION    "The ports on SDH supported cards."
        ::= { tnOpticalPortInfo 2 }

    tnSdhPortInfoEntry OBJECT-TYPE
        SYNTAX         TnSdhPortInfoEntry
        MAX-ACCESS     not-accessible
        STATUS         current
        DESCRIPTION    ""
        INDEX { ifIndex }
        ::= { tnSdhPortInfoTable 1 }

    TnSdhPortInfoEntry ::=
        SEQUENCE {
            tnSdhPortRxSectionTrace       SnmpAdminString,
--            obsolete
--            tnSdhPortTxSynchStatusMessage TropicSonetS1,
            tnSdhPortTiming               INTEGER,
--            obsolete
--            tnSdhPortRxSynchStatusMessage TropicSonetS1,
            tnSdhPortRxSectionTraceValid  TruthValue,
            tnSdhPortTxSynchronizeStatusMessage TropicSdhS1,
            tnSdhPortRxSynchronizeStatusMessage TropicSdhS1
        }

    tnSdhPortRxSectionTrace OBJECT-TYPE
        SYNTAX         SnmpAdminString (SIZE(0..255))
        MAX-ACCESS     read-only
        STATUS         current
        DESCRIPTION    ""
        ::= { tnSdhPortInfoEntry 1 }

--    obsolete
--    tnSdhPortTxSynchStatusMessage OBJECT-TYPE ::= { tnSdhPortInfoEntry 2 }

    tnSdhPortTiming OBJECT-TYPE
        SYNTAX         INTEGER {
                         unknown(1),
                         external(2),
                         line(3),
                         through(4),
                         loop(5),
                         local(6)
                       }
        MAX-ACCESS     read-only
        STATUS         current
        DESCRIPTION    ""
        DEFVAL         { unknown }
        ::= { tnSdhPortInfoEntry 3 }

--    obsolete
--    tnSdhPortRxSynchStatusMessage OBJECT-TYPE ::= { tnSdhPortInfoEntry 4 }

    tnSdhPortRxSectionTraceValid OBJECT-TYPE
        SYNTAX         TruthValue
        MAX-ACCESS     read-only
        STATUS         current
        DESCRIPTION    ""
        DEFVAL         { false }
        ::= { tnSdhPortInfoEntry 5 }

    tnSdhPortTxSynchronizeStatusMessage OBJECT-TYPE
        SYNTAX         TropicSdhS1
        MAX-ACCESS     read-only
        STATUS         current
        DESCRIPTION    "Current range: 0 to 15."
        DEFVAL         { 15 }
        ::= { tnSdhPortInfoEntry 6 }

    tnSdhPortRxSynchronizeStatusMessage OBJECT-TYPE
        SYNTAX         TropicSdhS1
        MAX-ACCESS     read-only
        STATUS         current
        DESCRIPTION    "Current range:  0 to 255."
        DEFVAL         { 0 }
        ::= { tnSdhPortInfoEntry 7 }

--    obsolete
--    tnOC48STM16PortInfoAttributeTotal OBJECT-TYPE ::= { tnOpticalPortInfo 3 }
--    tnOC48STM16PortInfoTable OBJECT-TYPE ::= { tnOpticalPortInfo 4 }
--    tnOC192STM64PortInfoAttributeTotal OBJECT-TYPE ::= { tnOpticalPortInfo 5 }
--    tnOC192STM64PortInfoTable OBJECT-TYPE ::= { tnOpticalPortInfo 6 }
--    tnQuadOC48STM16MuxPortInfoAttributeTotal OBJECT-TYPE
--    tnQuadOC48STM16MuxPortInfoTable OBJECT-TYPE ::= { tnOpticalPortInfo 8 }
--    tnQuadOC3or12STM1or4MuxPortInfoAttributeTotal OBJECT-TYPE ::= { tnOpticalPortInfo 9 }
--    tnQuadOC3or12STM1or4MuxPortInfoTable OBJECT-TYPE ::= { tnOpticalPortInfo 10 }
--    tnBandFilterPortInfoAttributeTotal OBJECT-TYPE ::= { tnOpticalPortInfo 11 }
--    tnBandFilterPortInfoTable OBJECT-TYPE ::= { tnOpticalPortInfo 12 }

--------------------------------------------------------------------------------
-- OSC Optical Port Info Scalars
--------------------------------------------------------------------------------
    tnOscPortInfoAttributeTotal OBJECT-TYPE
        SYNTAX         Integer32
        MAX-ACCESS     read-only
        STATUS         current
        DESCRIPTION    ""
        ::= { tnOpticalPortInfo 13 }

--------------------------------------------------------------------------------
-- OSC Optical Port Info Table
--------------------------------------------------------------------------------
    tnOscPortInfoTable OBJECT-TYPE
        SYNTAX         SEQUENCE OF TnOscPortInfoEntry
        MAX-ACCESS     not-accessible
        STATUS         current
        DESCRIPTION    "The ports on an OSC optical card."
        ::= { tnOpticalPortInfo 14 }

    tnOscPortInfoEntry OBJECT-TYPE
        SYNTAX         TnOscPortInfoEntry
        MAX-ACCESS     not-accessible
        STATUS         current
        DESCRIPTION    ""
        INDEX { ifIndex }
        ::= { tnOscPortInfoTable 1 }

    TnOscPortInfoEntry ::=
        SEQUENCE {
            tnOscPortInfoFunction         INTEGER,
            tnOscPortTotalNwPowerIn       Integer32,
            tnOscPortTotalNwPowerOut      Integer32,
            tnOscPortPhyDeviceLinkStatus  INTEGER,
            tnOscPortPhyDeviceIdNo        Unsigned32,
            tnOscPortPhyDeviceMfgModelNo  Unsigned32,
            tnOscPortPhyDeviceMfgRevNo    Unsigned32
        }

    tnOscPortInfoFunction OBJECT-TYPE
        SYNTAX         INTEGER {
                         signal(1),
                         line(2),
                         inv(3),
                         osc(4),
                         oscSfp(5)
                       }
        MAX-ACCESS     read-only
        STATUS         current
        DESCRIPTION    "Indicates the functional type of this OSC port."
        ::= { tnOscPortInfoEntry 1 }

    tnOscPortTotalNwPowerIn OBJECT-TYPE
        SYNTAX         Integer32
        UNITS          "mBm"
        MAX-ACCESS     read-only
        STATUS         current
        DESCRIPTION    "The following description applies to the wdm
                        port of the OSC card:

                        The total ingress power of the optical signal."
        DEFVAL         { -9900 }
        ::= { tnOscPortInfoEntry 2 }

    tnOscPortTotalNwPowerOut OBJECT-TYPE
        SYNTAX         Integer32
        UNITS          "mBm"
        MAX-ACCESS     read-only
        STATUS         current
        DESCRIPTION    "The following description applies to the wdm
                        port of the OSC card:

                        The total egress power of the optical signal."
        ::= { tnOscPortInfoEntry 3 }

    tnOscPortPhyDeviceLinkStatus OBJECT-TYPE
        SYNTAX         INTEGER {
                         up(1),
                         down(2)
                       }
        MAX-ACCESS     read-only
        STATUS         current
        DESCRIPTION    "The following description applies to the wdm
                        port of the OSC card:

                        PHY chip link status."
        ::= { tnOscPortInfoEntry 4 }

    tnOscPortPhyDeviceIdNo OBJECT-TYPE
        SYNTAX         Unsigned32
        MAX-ACCESS     read-only
        STATUS         current
        DESCRIPTION    "The following description applies to the wdm
                        port of the OSC card:

                        PHY chip ID."
        ::= { tnOscPortInfoEntry 5 }

    tnOscPortPhyDeviceMfgModelNo OBJECT-TYPE
        SYNTAX         Unsigned32
        MAX-ACCESS     read-only
        STATUS         current
        DESCRIPTION    "The following description applies to the wdm
                        port of the OSC card:

                        PHY chip manufacturing model number."
        ::= { tnOscPortInfoEntry 6 }

    tnOscPortPhyDeviceMfgRevNo OBJECT-TYPE
        SYNTAX         Unsigned32
        MAX-ACCESS     read-only
        STATUS         current
        DESCRIPTION    "The following description applies to the wdm
                        port of the OSC card:

                        PHY chip manufacturing revision number."
        ::= { tnOscPortInfoEntry 7 }

--    obsolete
--    tnChFilterPortInfoAttributeTotal OBJECT-TYPE ::= { tnOpticalPortInfo 15 }
--    tnChFilterPortInfoTable OBJECT-TYPE ::= { tnOpticalPortInfo 16 }
--    tnChAddDropPortInfoAttributeTotal OBJECT-TYPE ::= { tnOpticalPortInfo 17 }
--    tnChAddDropPortInfoTable OBJECT-TYPE ::= { tnOpticalPortInfo 18 }
--    tnBbaHgPortInfoAttributeTotal OBJECT-TYPE ::= { tnOpticalPortInfo 19 }
--    tnBbaHgPortInfoTable OBJECT-TYPE ::= { tnOpticalPortInfo 20 }
--    tnBbaLgPortInfoAttributeTotal OBJECT-TYPE ::= { tnOpticalPortInfo 21 }
--    tnBbaLgPortInfoTable OBJECT-TYPE ::= { tnOpticalPortInfo 22 }
--    tnPpsPortInfoAttributeTotal OBJECT-TYPE ::= { tnOpticalPortInfo 23 }
--    tnPpsPortInfoTable OBJECT-TYPE ::= { tnOpticalPortInfo 24 }
--    tnDualGigEMuxPortInfoAttributeTotal OBJECT-TYPE ::= { tnOpticalPortInfo 25 }
--    tnDualGigEMuxPortInfoTable OBJECT-TYPE ::= { tnOpticalPortInfo 26 }
--    tnRoadmPortInfoAttributeTotal OBJECT-TYPE ::= { tnOpticalPortInfo 27 }
--    tnRoadmPortInfoTable OBJECT-TYPE ::= { tnOpticalPortInfo 28 }
--    tn10GigELANPortInfoAttributeTotal OBJECT-TYPE ::= { tnOpticalPortInfo 29 }
--    tn10GigELANPortInfoTable OBJECT-TYPE ::= { tnOpticalPortInfo 30 }

--------------------------------------------------------------------------------
-- Dispersion Compensation Module Optical Port Info Scalars
--------------------------------------------------------------------------------
    tnDcmPortInfoAttributeTotal OBJECT-TYPE
        SYNTAX         Integer32
        MAX-ACCESS     read-only
        STATUS         current
        DESCRIPTION    ""
        ::= { tnOpticalPortInfo 31 }

--------------------------------------------------------------------------------
-- Dispersion Compensation Module Optical Port Info Table
--------------------------------------------------------------------------------
    tnDcmPortInfoTable OBJECT-TYPE
        SYNTAX         SEQUENCE OF TnDcmPortInfoEntry
        MAX-ACCESS     not-accessible
        STATUS         current
        DESCRIPTION    "The ports on a DCM optical card."
        ::= { tnOpticalPortInfo 32 }

    tnDcmPortInfoEntry OBJECT-TYPE
        SYNTAX         TnDcmPortInfoEntry
        MAX-ACCESS     not-accessible
        STATUS         current
        DESCRIPTION    ""
        INDEX { ifIndex }
        ::= { tnDcmPortInfoTable 1 }

    TnDcmPortInfoEntry ::=
        SEQUENCE {
            tnDcmPortInfoFunction           INTEGER,
            tnDcmPortInfoIroadmConnAddress  InterfaceIndexOrZero
        }

    tnDcmPortInfoFunction OBJECT-TYPE
        SYNTAX         INTEGER {
                         dcmOutThruIn(1),
                         thruOutDcmIn(2),
                         dcmInOut(3)
                       }
        MAX-ACCESS     read-only
        STATUS         current
        DESCRIPTION    "Indicates the functional type of this Dispersion
                        Compensation Module port."
        ::= { tnDcmPortInfoEntry 1 }

    tnDcmPortInfoIroadmConnAddress OBJECT-TYPE
        SYNTAX         InterfaceIndexOrZero
        MAX-ACCESS     read-only
        STATUS         current
        DESCRIPTION    " "
        ::= { tnDcmPortInfoEntry 2 }

--    obsolete
--    tnDecaGigEMuxPortInfoAttributeTotal OBJECT-TYPE ::= { tnOpticalPortInfo 33 }
--    tnDecaGigEMuxPortInfoTable OBJECT-TYPE ::= { tnOpticalPortInfo 34 }

--------------------------------------------------------------------------------
-- SONET Optical Port Info Scalars
--------------------------------------------------------------------------------
    tnSonetPortInfoAttributeTotal OBJECT-TYPE
        SYNTAX         Integer32
        MAX-ACCESS     read-only
        STATUS         current
        DESCRIPTION    ""
        ::= { tnOpticalPortInfo 35 }

--------------------------------------------------------------------------------
-- SONET Optical Port Info Table
--------------------------------------------------------------------------------
    tnSonetPortInfoTable OBJECT-TYPE
        SYNTAX         SEQUENCE OF TnSonetPortInfoEntry
        MAX-ACCESS     not-accessible
        STATUS         current
        DESCRIPTION    "The ports on SONET supported cards."
        ::= { tnOpticalPortInfo 36 }

    tnSonetPortInfoEntry OBJECT-TYPE
        SYNTAX         TnSonetPortInfoEntry
        MAX-ACCESS     not-accessible
        STATUS         current
        DESCRIPTION    ""
        INDEX { ifIndex }
        ::= { tnSonetPortInfoTable 1 }

    TnSonetPortInfoEntry ::=
        SEQUENCE {
            tnSonetPortRxSectionTrace       SnmpAdminString,
            tnSonetPortTxSynchStatusMessage TropicSonetS1,
            tnSonetPortTiming               INTEGER,
            tnSonetPortRxSynchStatusMessage TropicSonetS1,
            tnSonetPortRxSectionTraceValid  TruthValue
        }

    tnSonetPortRxSectionTrace OBJECT-TYPE
        SYNTAX         SnmpAdminString (SIZE(0..255))
        MAX-ACCESS     read-only
        STATUS         current
        DESCRIPTION    ""
        ::= { tnSonetPortInfoEntry 1 }

    tnSonetPortTxSynchStatusMessage OBJECT-TYPE
        SYNTAX         TropicSonetS1
        MAX-ACCESS     read-only
        STATUS         current
        DESCRIPTION    ""
        ::= { tnSonetPortInfoEntry 2 }

    tnSonetPortTiming OBJECT-TYPE
        SYNTAX         INTEGER {
                         unknown(1),
                         external(2),
                         line(3),
                         through(4),
                         loop(5),
                         local(6)
                       }
        MAX-ACCESS     read-only
        STATUS         current
        DESCRIPTION    ""
        ::= { tnSonetPortInfoEntry 3 }

    tnSonetPortRxSynchStatusMessage OBJECT-TYPE
        SYNTAX         TropicSonetS1
        MAX-ACCESS     read-only
        STATUS         current
        DESCRIPTION    ""
        ::= { tnSonetPortInfoEntry 4 }

    tnSonetPortRxSectionTraceValid OBJECT-TYPE
        SYNTAX         TruthValue
        MAX-ACCESS     read-only
        STATUS         current
        DESCRIPTION    ""
        ::= { tnSonetPortInfoEntry 5 }

--    obsolete
--    tnExternalDcuPortInfoAttributeTotal OBJECT-TYPE ::= { tnOpticalPortInfo 37 }
--    tnExternalDcuPortInfoTable OBJECT-TYPE ::= { tnOpticalPortInfo 38 }

--------------------------------------------------------------------------------
-- Digital Wrapper Optical Port Info Scalars
--------------------------------------------------------------------------------
    tnDigitalWrapperPortInfoAttributeTotal OBJECT-TYPE
        SYNTAX         Integer32
        MAX-ACCESS     read-only
        STATUS         current
        DESCRIPTION    ""
        ::= { tnOpticalPortInfo 39 }

--------------------------------------------------------------------------------
-- Digital Wrapper Optical Port Info Table
--------------------------------------------------------------------------------
    tnDigitalWrapperPortInfoTable OBJECT-TYPE
        SYNTAX         SEQUENCE OF TnDigitalWrapperPortInfoEntry
        MAX-ACCESS     not-accessible
        STATUS         current
        DESCRIPTION    "The ports on Digital Wrapper supported cards."
        ::= { tnOpticalPortInfo 40 }

    tnDigitalWrapperPortInfoEntry OBJECT-TYPE
        SYNTAX         TnDigitalWrapperPortInfoEntry
        MAX-ACCESS     not-accessible
        STATUS         current
        DESCRIPTION    ""
        INDEX { ifIndex }
        ::= { tnDigitalWrapperPortInfoTable 1 }

    TnDigitalWrapperPortInfoEntry ::=
        SEQUENCE {
            tnDwPortRxPMTTI                SnmpAdminString,
            tnDwPortRxPMExpectedTTI        SnmpAdminString,
            tnDwPortTxPMTTI                SnmpAdminString
        }

    tnDwPortRxPMTTI OBJECT-TYPE
        SYNTAX         SnmpAdminString (SIZE(0..255))
        MAX-ACCESS     read-only
        STATUS         current
        DESCRIPTION    ""
        ::= { tnDigitalWrapperPortInfoEntry 1 }

    tnDwPortRxPMExpectedTTI OBJECT-TYPE
        SYNTAX         SnmpAdminString (SIZE(0..255))
        MAX-ACCESS     read-only
        STATUS         current
        DESCRIPTION    ""
        ::= { tnDigitalWrapperPortInfoEntry 2 }

    tnDwPortTxPMTTI OBJECT-TYPE
        SYNTAX         SnmpAdminString (SIZE(0..255))
        MAX-ACCESS     read-only
        STATUS         current
        DESCRIPTION    ""
        ::= { tnDigitalWrapperPortInfoEntry 3 }

--    obsolete
--    tnMsaHgPortInfoAttributeTotal OBJECT-TYPE ::= { tnOpticalPortInfo 41 }
--    tnMsaHgPortInfoTable OBJECT-TYPE ::= { tnOpticalPortInfo 42 }
--    tnWssX9PortInfoAttributeTotal OBJECT-TYPE ::= { tnOpticalPortInfo 43 }
--    tnWssX9PortInfoTable OBJECT-TYPE ::= { tnOpticalPortInfo 44 }

--------------------------------------------------------------------------------
-- SFP Port Info Scalars
--------------------------------------------------------------------------------
    tnSfpPortInfoAttributeTotal OBJECT-TYPE
        SYNTAX         Integer32
        MAX-ACCESS     read-only
        STATUS         current
        DESCRIPTION    ""
        ::= { tnOpticalPortInfo 45 }

--------------------------------------------------------------------------------
-- SFP Port Info Table
--------------------------------------------------------------------------------
    tnSfpPortInfoTable OBJECT-TYPE
        SYNTAX         SEQUENCE OF TnSfpPortInfoEntry
        MAX-ACCESS     not-accessible
        STATUS         current
        DESCRIPTION    "The SFP supported ports."
        ::= { tnOpticalPortInfo 46 }

    tnSfpPortInfoEntry OBJECT-TYPE
        SYNTAX         TnSfpPortInfoEntry
        MAX-ACCESS     not-accessible
        STATUS         current
        DESCRIPTION    ""
        INDEX { ifIndex }
        ::= { tnSfpPortInfoTable 1 }

    TnSfpPortInfoEntry ::=
        SEQUENCE {
            tnSfpPortModulePresentType             Unsigned32,
            tnSfpPortModuleVendorSerNo             SnmpAdminString,
            tnSfpPortModuleState                   TnSfpModuleState,
            tnSfpPortModuleVendor                  SnmpAdminString,
            tnSfpPortTxDisable                     TruthValue,
            tnSfpPortWavelength                    Unsigned32,
            tnSfpPortModuleType                    SnmpAdminString,
            tnSfpPortCLEI                          SnmpAdminString,
            tnSfpPortUnitPartNum                   SnmpAdminString,
            tnSfpPortSWPartNum                     SnmpAdminString,
            tnSfpPortFactoryID                     SnmpAdminString,
            tnSfpPortDate                          SnmpAdminString,
            tnSfpPortExtraData                     SnmpAdminString,
            tnSfpPortMaximumCaseTemperature        Integer32,
            tnSfpPortInterchangeabilityMarking     SnmpAdminString,
            tnSfpPortAcronymCode                   SnmpAdminString
        }

    tnSfpPortModulePresentType OBJECT-TYPE
        SYNTAX         Unsigned32
        MAX-ACCESS     read-only
        STATUS         current
        DESCRIPTION    "XFP/SFP module present type."
        ::= { tnSfpPortInfoEntry 1 }

    tnSfpPortModuleVendorSerNo OBJECT-TYPE
        SYNTAX         SnmpAdminString (SIZE(0..18))
        MAX-ACCESS     read-only
        STATUS         current
        DESCRIPTION    "XFP/SFP module vendor serial number."
        ::= { tnSfpPortInfoEntry 2 }

    tnSfpPortModuleState OBJECT-TYPE
        SYNTAX         TnSfpModuleState
        MAX-ACCESS     read-only
        STATUS         current
        DESCRIPTION    "XFP/SFP module state."
        ::= { tnSfpPortInfoEntry 3 }

    tnSfpPortModuleVendor OBJECT-TYPE
        SYNTAX         SnmpAdminString (SIZE(0..16))
        MAX-ACCESS     read-only
        STATUS         current
        DESCRIPTION    "XFP/SFP module vendor."
        ::= { tnSfpPortInfoEntry 4 }

    tnSfpPortTxDisable OBJECT-TYPE
        SYNTAX         TruthValue
        MAX-ACCESS     read-only
        STATUS         current
        DESCRIPTION    "XFP/SFP TX disable."
        ::= { tnSfpPortInfoEntry 5 }

    tnSfpPortWavelength OBJECT-TYPE
        SYNTAX         Unsigned32
        MAX-ACCESS     read-only
        STATUS         current
        DESCRIPTION    "XFP/SFP wavelength."
        ::= { tnSfpPortInfoEntry 6 }

    tnSfpPortModuleType OBJECT-TYPE
        SYNTAX         SnmpAdminString
        MAX-ACCESS     read-only
        STATUS         current
        DESCRIPTION    "XFP/SFP module type."
        ::= { tnSfpPortInfoEntry 7 }

    tnSfpPortCLEI OBJECT-TYPE
        SYNTAX         SnmpAdminString
        MAX-ACCESS     read-only
        STATUS         current
        DESCRIPTION    "XFP/SFP CLEI."
        ::= { tnSfpPortInfoEntry 8 }

    tnSfpPortUnitPartNum OBJECT-TYPE
        SYNTAX         SnmpAdminString
        MAX-ACCESS     read-only
        STATUS         current
        DESCRIPTION    "XFP/SFP unit part number."
        ::= { tnSfpPortInfoEntry 9 }

    tnSfpPortSWPartNum OBJECT-TYPE
        SYNTAX         SnmpAdminString
        MAX-ACCESS     read-only
        STATUS         current
        DESCRIPTION    "XFP/SFP software part number."
        ::= { tnSfpPortInfoEntry 10 }

    tnSfpPortFactoryID OBJECT-TYPE
        SYNTAX         SnmpAdminString
        MAX-ACCESS     read-only
        STATUS         current
        DESCRIPTION    "XFP/SFP factory ID."
        ::= { tnSfpPortInfoEntry 11 }

    tnSfpPortDate OBJECT-TYPE
        SYNTAX         SnmpAdminString
        MAX-ACCESS     read-only
        STATUS         current
        DESCRIPTION    "XFP/SFP date."
        ::= { tnSfpPortInfoEntry 12 }

    tnSfpPortExtraData OBJECT-TYPE
        SYNTAX         SnmpAdminString
        MAX-ACCESS     read-only
        STATUS         current
        DESCRIPTION    "XFP/SFP extra data."
        ::= { tnSfpPortInfoEntry 13 }

    tnSfpPortMaximumCaseTemperature OBJECT-TYPE
        SYNTAX         Integer32
        MAX-ACCESS     read-only
        STATUS         current
        DESCRIPTION    "XFP/SFP maximum case temperature."
        ::= { tnSfpPortInfoEntry 14 }

    tnSfpPortInterchangeabilityMarking OBJECT-TYPE
        SYNTAX         SnmpAdminString (SIZE(0..6))
        MAX-ACCESS     read-only
        STATUS         current
        DESCRIPTION    "XFP/SFP interchangeability marking."
        ::= { tnSfpPortInfoEntry 15 }

    tnSfpPortAcronymCode OBJECT-TYPE
        SYNTAX         SnmpAdminString (SIZE(0..12))
        MAX-ACCESS     read-only
        STATUS         current
        DESCRIPTION    "XFP/SFP acronym code."
        ::= { tnSfpPortInfoEntry 16 }

--    obsolete
--    tn1xMR2dot5GPortInfoAttributeTotal OBJECT-TYPE ::= { tnOpticalPortInfo 47 }
--    tn1xMR2dot5GPortInfoTable OBJECT-TYPE ::= { tnOpticalPortInfo 48 }

--------------------------------------------------------------------------------
-- Network Port Info Scalars
--------------------------------------------------------------------------------
    tnNetworkPortInfoAttributeTotal OBJECT-TYPE
        SYNTAX         Integer32
        MAX-ACCESS     read-only
        STATUS         current
        DESCRIPTION    ""
        ::= { tnOpticalPortInfo 49 }

--------------------------------------------------------------------------------
-- Network Port Info Table
--------------------------------------------------------------------------------
    tnNetworkPortInfoTable OBJECT-TYPE
        SYNTAX         SEQUENCE OF TnNetworkPortInfoEntry
        MAX-ACCESS     not-accessible
        STATUS         current
        DESCRIPTION    "The network ports on optical transponder cards."
        ::= { tnOpticalPortInfo 50 }

    tnNetworkPortInfoEntry OBJECT-TYPE
        SYNTAX         TnNetworkPortInfoEntry
        MAX-ACCESS     not-accessible
        STATUS         current
        DESCRIPTION    ""
        INDEX { ifIndex }
        ::= { tnNetworkPortInfoTable 1 }

    TnNetworkPortInfoEntry ::=
        SEQUENCE {
            tnNwPortOchRxStatus    TnOchStatus,
            tnNwPortOchTxStatus    TnOchStatus,
            tnNwPortPresentChannel Unsigned32
        }

    tnNwPortOchRxStatus OBJECT-TYPE
        SYNTAX         TnOchStatus
        MAX-ACCESS     read-only
        STATUS         current
        DESCRIPTION    ""
        ::= { tnNetworkPortInfoEntry 1 }

    tnNwPortOchTxStatus OBJECT-TYPE
        SYNTAX         TnOchStatus
        MAX-ACCESS     read-only
        STATUS         current
        DESCRIPTION    ""
        ::= { tnNetworkPortInfoEntry 2 }

    tnNwPortPresentChannel OBJECT-TYPE
        SYNTAX         Unsigned32
        MAX-ACCESS     read-only
        STATUS         current
        DESCRIPTION    "The present ITU channel."
        ::= { tnNetworkPortInfoEntry 3 }

--------------------------------------------------------------------------------
-- OPSA Optical Port Info Scalars
--------------------------------------------------------------------------------
    tnOpsaPortInfoAttributeTotal OBJECT-TYPE
        SYNTAX         Integer32
        MAX-ACCESS     read-only
        STATUS         current
        DESCRIPTION    ""
        ::= { tnOpticalPortInfo 51 }

--------------------------------------------------------------------------------
-- OPSA Optical Port Info Table
--------------------------------------------------------------------------------
    tnOpsaPortInfoTable OBJECT-TYPE
        SYNTAX         SEQUENCE OF TnOpsaPortInfoEntry
        MAX-ACCESS     not-accessible
        STATUS         current
        DESCRIPTION    "The ports on an OPSA optical card."
        ::= { tnOpticalPortInfo 52 }

    tnOpsaPortInfoEntry OBJECT-TYPE
        SYNTAX         TnOpsaPortInfoEntry
        MAX-ACCESS     not-accessible
        STATUS         current
        DESCRIPTION    ""
        INDEX { ifIndex }
        ::= { tnOpsaPortInfoTable 1 }

    TnOpsaPortInfoEntry ::=
        SEQUENCE {
            tnOpsaPortInfoFunction               INTEGER,
            tnOpsaPortReceivedPower              Integer32,  -- deprecated
            tnOpsaPortPresentTransmitAttenuation Integer32   -- deprecated
        }

    tnOpsaPortInfoFunction OBJECT-TYPE
        SYNTAX         INTEGER {
                         signal(1),
                         workingProtected(2)
                       }
        MAX-ACCESS     read-only
        STATUS         current
        DESCRIPTION    "Indicates the functional type of this OPSA port."
        ::= { tnOpsaPortInfoEntry 1 }

    tnOpsaPortReceivedPower OBJECT-TYPE
        SYNTAX         Integer32
        UNITS          "mBm"
        MAX-ACCESS     read-only
        STATUS         deprecated
        DESCRIPTION    "The received power in mBm.  This is accessible
                        from ports 2 and 3 (working or protected)
                        exclusively."
        ::= { tnOpsaPortInfoEntry 2 }

    tnOpsaPortPresentTransmitAttenuation OBJECT-TYPE
        SYNTAX         Integer32
        UNITS          "mB"
        MAX-ACCESS     read-only
        STATUS         deprecated
        DESCRIPTION    "The present attenuation of the attenuator -
                        applies to the network ports of the OPSA card
                        with attenuators."
        ::= { tnOpsaPortInfoEntry 3 }

--------------------------------------------------------------------------------
-- 11STMM10 Optical Port Info Scalars
--------------------------------------------------------------------------------
    tn11stmm10PortInfoAttributeTotal OBJECT-TYPE
        SYNTAX         Integer32
        MAX-ACCESS     read-only
        STATUS         current
        DESCRIPTION    ""
        ::= { tnOpticalPortInfo 53 }

--------------------------------------------------------------------------------
-- 11STMM10 Optical Port Info Table
--------------------------------------------------------------------------------
    tn11stmm10PortInfoTable OBJECT-TYPE
        SYNTAX         SEQUENCE OF Tn11stmm10PortInfoEntry
        MAX-ACCESS     not-accessible
        STATUS         current
        DESCRIPTION    "The ports on a 11STMM10 optical card."
        ::= { tnOpticalPortInfo 54 }

    tn11stmm10PortInfoEntry OBJECT-TYPE
        SYNTAX         Tn11stmm10PortInfoEntry
        MAX-ACCESS     not-accessible
        STATUS         current
        DESCRIPTION    ""
        INDEX { ifIndex }
        ::= { tn11stmm10PortInfoTable 1 }

    Tn11stmm10PortInfoEntry ::=
        SEQUENCE {
            tn11stmm10PortInfoFunction INTEGER
        }

    tn11stmm10PortInfoFunction OBJECT-TYPE
        SYNTAX         INTEGER {
                         network(1),
                         client(2)
                       }
        MAX-ACCESS     read-only
        STATUS         current
        DESCRIPTION    "Indicates the functional type of this 11STMM10 port."
        ::= { tn11stmm10PortInfoEntry 1 }

--------------------------------------------------------------------------------
-- 11STAR1 Optical Port Info Scalars
--------------------------------------------------------------------------------
    tn11star1PortInfoAttributeTotal OBJECT-TYPE
        SYNTAX         Integer32
        MAX-ACCESS     read-only
        STATUS         current
        DESCRIPTION    ""
        ::= { tnOpticalPortInfo 55 }

--------------------------------------------------------------------------------
-- 11STAR1 Optical Port Info Table
--------------------------------------------------------------------------------
    tn11star1PortInfoTable OBJECT-TYPE
        SYNTAX         SEQUENCE OF Tn11star1PortInfoEntry
        MAX-ACCESS     not-accessible
        STATUS         current
        DESCRIPTION    "The ports on a 11STAR1 optical card."
        ::= { tnOpticalPortInfo 56 }

    tn11star1PortInfoEntry OBJECT-TYPE
        SYNTAX         Tn11star1PortInfoEntry
        MAX-ACCESS     not-accessible
        STATUS         current
        DESCRIPTION    ""
        INDEX { ifIndex }
        ::= { tn11star1PortInfoTable 1 }

    Tn11star1PortInfoEntry ::=
        SEQUENCE {
            tn11star1PortInfoFunction INTEGER
        }

    tn11star1PortInfoFunction OBJECT-TYPE
        SYNTAX         INTEGER {
                         network(1),
                         client(2)
                       }
        MAX-ACCESS     read-only
        STATUS         current
        DESCRIPTION    "Indicates the functional type of this 11STAR1 port."
        ::= { tn11star1PortInfoEntry 1 }

--------------------------------------------------------------------------------
-- AHPHG Optical Port Info Scalars
--------------------------------------------------------------------------------
    tnAhphgPortInfoAttributeTotal OBJECT-TYPE
        SYNTAX         Integer32
        MAX-ACCESS     read-only
        STATUS         current
        DESCRIPTION    ""
        ::= { tnOpticalPortInfo 57 }

--------------------------------------------------------------------------------
-- AHPHG Optical Port Info Table
--------------------------------------------------------------------------------
    tnAhphgPortInfoTable OBJECT-TYPE
        SYNTAX         SEQUENCE OF TnAhphgPortInfoEntry
        MAX-ACCESS     not-accessible
        STATUS         current
        DESCRIPTION    "The ports on an AHPHG optical card."
        ::= { tnOpticalPortInfo 58 }

    tnAhphgPortInfoEntry OBJECT-TYPE
        SYNTAX         TnAhphgPortInfoEntry
        MAX-ACCESS     not-accessible
        STATUS         current
        DESCRIPTION    ""
        INDEX { ifIndex }
        ::= { tnAhphgPortInfoTable 1 }

    TnAhphgPortInfoEntry ::=
        SEQUENCE {
            tnAhphgPortInfoFunction INTEGER
        }

    tnAhphgPortInfoFunction OBJECT-TYPE
        SYNTAX         INTEGER {
                         line(1),
                         signal(2),
                         dcm(3),
                         inv(4),
                         osc(5)
                       }
        MAX-ACCESS     read-only
        STATUS         current
        DESCRIPTION    "Indicates the functional type of this AHPHG port."
        ::= { tnAhphgPortInfoEntry 1 }

--------------------------------------------------------------------------------
-- ALPHG Optical Port Info Scalars
--------------------------------------------------------------------------------
    tnAlphgPortInfoAttributeTotal OBJECT-TYPE
        SYNTAX         Integer32
        MAX-ACCESS     read-only
        STATUS         current
        DESCRIPTION    ""
        ::= { tnOpticalPortInfo 59 }

--------------------------------------------------------------------------------
-- ALPHG Optical Port Info Table
--------------------------------------------------------------------------------
    tnAlphgPortInfoTable OBJECT-TYPE
        SYNTAX         SEQUENCE OF TnAlphgPortInfoEntry
        MAX-ACCESS     not-accessible
        STATUS         current
        DESCRIPTION    "The ports on an ALPHG optical card."
        ::= { tnOpticalPortInfo 60 }

    tnAlphgPortInfoEntry OBJECT-TYPE
        SYNTAX         TnAlphgPortInfoEntry
        MAX-ACCESS     not-accessible
        STATUS         current
        DESCRIPTION    ""
        INDEX { ifIndex }
        ::= { tnAlphgPortInfoTable 1 }

    TnAlphgPortInfoEntry ::=
        SEQUENCE {
            tnAlphgPortInfoFunction INTEGER
        }

    tnAlphgPortInfoFunction OBJECT-TYPE
        SYNTAX         INTEGER {
                         line(1),
                         signal(2),
                         dcm(3),
                         inv(4),
                         osc(5)
                       }
        MAX-ACCESS     read-only
        STATUS         current
        DESCRIPTION    "Indicates the functional type of this ALPHG port."
        ::= { tnAlphgPortInfoEntry 1 }

--------------------------------------------------------------------------------
-- CWR8 Optical Port Info Scalars
--------------------------------------------------------------------------------
    tnCwr8PortInfoAttributeTotal OBJECT-TYPE
        SYNTAX         Integer32
        MAX-ACCESS     read-only
        STATUS         current
        DESCRIPTION    ""
        ::= { tnOpticalPortInfo 61 }

--------------------------------------------------------------------------------
-- CWR8 Optical Port Info Table
--------------------------------------------------------------------------------
    tnCwr8PortInfoTable OBJECT-TYPE
        SYNTAX         SEQUENCE OF TnCwr8PortInfoEntry
        MAX-ACCESS     not-accessible
        STATUS         current
        DESCRIPTION    "The ports on a CWR8 optical card."
        ::= { tnOpticalPortInfo 62 }

    tnCwr8PortInfoEntry OBJECT-TYPE
        SYNTAX         TnCwr8PortInfoEntry
        MAX-ACCESS     not-accessible
        STATUS         current
        DESCRIPTION    ""
        INDEX { ifIndex }
        ::= { tnCwr8PortInfoTable 1 }

    TnCwr8PortInfoEntry ::=
        SEQUENCE {
            tnCwr8PortInfoFunction           INTEGER,
--            obsolete
--            tnCwr8PortTotalNwPowerIn         Integer32,
--            tnCwr8PortTotalNwPowerOut        Integer32,
            tnCwr8PortRelativeAttenuationMin Unsigned32,
            tnCwr8PortAverageAttenuationOut  Unsigned32
        }

    tnCwr8PortInfoFunction OBJECT-TYPE
        SYNTAX         INTEGER {
                         signal(1),
                         test(2),
                         thru(3),
                         colorless(4),
                         omd(5),
                         inv(6)
                       }
        MAX-ACCESS     read-only
        STATUS         current
        DESCRIPTION    "Indicates the functional type of this CWR8 port."
        ::= { tnCwr8PortInfoEntry 1 }

--    obsolete
--    tnCwr8PortTotalNwPowerIn OBJECT-TYPE ::= { tnCwr8PortInfoEntry 2 }
--    tnCwr8PortTotalNwPowerOut OBJECT-TYPE ::= { tnCwr8PortInfoEntry 3 }

    tnCwr8PortRelativeAttenuationMin OBJECT-TYPE
        SYNTAX         Unsigned32
        UNITS          "mB"
        MAX-ACCESS     read-only
        STATUS         current
        DESCRIPTION    "The following description applies to the Thru
                        port of the CWR8 card:

                        The minimum attenuation on the blocker across
                        all of the channels."
        ::= { tnCwr8PortInfoEntry 4 }

    tnCwr8PortAverageAttenuationOut OBJECT-TYPE
        SYNTAX         Unsigned32
        UNITS          "mB"
        MAX-ACCESS     read-only
        STATUS         current
        DESCRIPTION    "The following description applies to the Thru
                        port of the CWR8 card:

                        The average attenuation on the blocker across
                        all of the channels."
        ::= { tnCwr8PortInfoEntry 5 }

--------------------------------------------------------------------------------
-- 11STGE12 Optical Port Info Scalars
--------------------------------------------------------------------------------
    tn11stge12PortInfoAttributeTotal OBJECT-TYPE
        SYNTAX         Integer32
        MAX-ACCESS     read-only
        STATUS         current
        DESCRIPTION    ""
        ::= { tnOpticalPortInfo 63 }

--------------------------------------------------------------------------------
-- 11STGE12 Optical Port Info Table
--------------------------------------------------------------------------------
    tn11stge12PortInfoTable OBJECT-TYPE
        SYNTAX         SEQUENCE OF Tn11stge12PortInfoEntry
        MAX-ACCESS     not-accessible
        STATUS         current
        DESCRIPTION    "The ports on a 11STGE12 optical card."
        ::= { tnOpticalPortInfo 64 }

    tn11stge12PortInfoEntry OBJECT-TYPE
        SYNTAX         Tn11stge12PortInfoEntry
        MAX-ACCESS     not-accessible
        STATUS         current
        DESCRIPTION    ""
        INDEX { ifIndex }
        ::= { tn11stge12PortInfoTable 1 }

    Tn11stge12PortInfoEntry ::=
        SEQUENCE {
            tn11stge12PortInfoFunction INTEGER
        }

    tn11stge12PortInfoFunction OBJECT-TYPE
        SYNTAX         INTEGER {
                         network(1),
                         client(2)
                       }
        MAX-ACCESS     read-only
        STATUS         current
        DESCRIPTION    "Indicates the functional type of this 11STGE12 port."
        ::= { tn11stge12PortInfoEntry 1 }

--------------------------------------------------------------------------------
-- 11DPGE12 Optical Port Info Scalars
--------------------------------------------------------------------------------
    tn11dpge12PortInfoAttributeTotal OBJECT-TYPE
        SYNTAX         Integer32
        MAX-ACCESS     read-only
        STATUS         current
        DESCRIPTION    ""
        ::= { tnOpticalPortInfo 65 }

--------------------------------------------------------------------------------
-- 11DPGE12 Optical Port Info Table
--------------------------------------------------------------------------------
    tn11dpge12PortInfoTable OBJECT-TYPE
        SYNTAX         SEQUENCE OF Tn11dpge12PortInfoEntry
        MAX-ACCESS     not-accessible
        STATUS         current
        DESCRIPTION    "The ports on a 11DPGE12 optical card."
        ::= { tnOpticalPortInfo 66 }

    tn11dpge12PortInfoEntry OBJECT-TYPE
        SYNTAX         Tn11dpge12PortInfoEntry
        MAX-ACCESS     not-accessible
        STATUS         current
        DESCRIPTION    ""
        INDEX { ifIndex }
        ::= { tn11dpge12PortInfoTable 1 }

    Tn11dpge12PortInfoEntry ::=
        SEQUENCE {
            tn11dpge12PortInfoFunction           INTEGER,
            tn11dpge12PortAvailableBandwidth     Unsigned32,
            tn11dpge12PortTotalVTS               Unsigned32,
            tn11dpge12PortIngAvailableBandwidth  Unsigned32,
            tn11dpge12PortEgrAvailableBandwidth  Unsigned32
        }

    tn11dpge12PortInfoFunction OBJECT-TYPE
        SYNTAX         INTEGER {
                         network(1),
                         client(2),
                         evoa(3),
                         backplane(4)
                       }
        MAX-ACCESS     read-only
        STATUS         current
        DESCRIPTION    "Indicates the functional type of this 11DPGE12 port."
        ::= { tn11dpge12PortInfoEntry 1 }

    tn11dpge12PortAvailableBandwidth OBJECT-TYPE
        SYNTAX         Unsigned32
        MAX-ACCESS     read-only
        STATUS         current
        DESCRIPTION    "Available bandwidth for 11DPGE12 ports."
        ::= { tn11dpge12PortInfoEntry 2 }

    tn11dpge12PortTotalVTS OBJECT-TYPE
        SYNTAX         Unsigned32
        MAX-ACCESS     read-only
        STATUS         current
        DESCRIPTION    "Total VTS for 11DPGE12 ports."
        ::= { tn11dpge12PortInfoEntry 3 }

    tn11dpge12PortIngAvailableBandwidth OBJECT-TYPE
        SYNTAX         Unsigned32
        MAX-ACCESS     read-only
        STATUS         current
        DESCRIPTION    "Available bandwidth for Ingress 11DPGE12 ports."
        ::= { tn11dpge12PortInfoEntry 4 }

    tn11dpge12PortEgrAvailableBandwidth OBJECT-TYPE
        SYNTAX         Unsigned32
        MAX-ACCESS     read-only
        STATUS         current
        DESCRIPTION    "Available bandwidth for Egress 11DPGE12 ports."
        ::= { tn11dpge12PortInfoEntry 5 }

--------------------------------------------------------------------------------
-- DWDM GP Phy Port Info Table
--------------------------------------------------------------------------------
--    obsolete
--    tnDwdmGpPhyPortInfoTable OBJECT-TYPE ::= { tnOpticalPortInfo 67 }

--------------------------------------------------------------------------------
-- DWDM Common Line Port Info Table
--------------------------------------------------------------------------------
    tnDwdmCmnLinePortInfoTable OBJECT-TYPE
        SYNTAX         SEQUENCE OF TnDwdmCmnLinePortInfoEntry
        MAX-ACCESS     not-accessible
        STATUS         current
        DESCRIPTION    "Common attributes against DWDM line ports."
        ::= { tnOpticalPortInfo 68 }

    tnDwdmCmnLinePortInfoEntry OBJECT-TYPE
        SYNTAX         TnDwdmCmnLinePortInfoEntry
        MAX-ACCESS     not-accessible
        STATUS         current
        DESCRIPTION    ""
        INDEX { ifIndex }
        ::= { tnDwdmCmnLinePortInfoTable 1 }

    TnDwdmCmnLinePortInfoEntry ::=
        SEQUENCE {
            tnDwdmCmnLinePortOtu2IncomingTti       OCTET STRING,
            tnDwdmCmnLinePortOtu2TtiStatus         AluWdmTtiStatus,
            tnDwdmCmnLinePortOdu2IncomingTti       OCTET STRING,
            tnDwdmCmnLinePortOdu2TtiStatus         AluWdmTtiStatus,
--            obsolete
--            tnDwdmCmnLinePortAvailableBandwidth    Unsigned32,
            tnDwdmCmnLinePortOtu2PreFec            Counter64,
            tnDwdmCmnLinePortOtu2PostFec           Counter64,
            tnDwdmCmnLinePortOdu2IncFwFTFLTypeID   OCTET STRING,
            tnDwdmCmnLinePortOdu2IncFwFTFLOperID   OCTET STRING,
            tnDwdmCmnLinePortOdu2IncBwFTFLTypeID   OCTET STRING,
            tnDwdmCmnLinePortOdu2IncBwFTFLOperID   OCTET STRING,
            tnDwdmCmnLinePortOdu2IncResRow2        OCTET STRING,
            tnDwdmCmnLinePortOdu2IncResRow4        OCTET STRING,
            tnDwdmCmnLinePortOdu2IncExp            OCTET STRING,
            tnDwdmCmnLinePortOtu2IncRes            OCTET STRING,
            tnDwdmCmnLinePortDMInfoCurrentStatus   AluWdmDMInfoCurrentStatus,
            tnDwdmCmnLinePortDMInfoCurrentValue    Unsigned32
        }

    tnDwdmCmnLinePortOtu2IncomingTti OBJECT-TYPE
        SYNTAX         OCTET STRING
        MAX-ACCESS     read-only
        STATUS         current
        DESCRIPTION    "OTU2 incoming TTI."
        ::= { tnDwdmCmnLinePortInfoEntry 1 }

    tnDwdmCmnLinePortOtu2TtiStatus OBJECT-TYPE
        SYNTAX         AluWdmTtiStatus
        MAX-ACCESS     read-only
        STATUS         current
        DESCRIPTION    "OTU2 TTI status."
        ::= { tnDwdmCmnLinePortInfoEntry 2 }

    tnDwdmCmnLinePortOdu2IncomingTti OBJECT-TYPE
        SYNTAX         OCTET STRING
        MAX-ACCESS     read-only
        STATUS         current
        DESCRIPTION    "ODU2 incoming TTI."
        ::= { tnDwdmCmnLinePortInfoEntry 3 }

    tnDwdmCmnLinePortOdu2TtiStatus OBJECT-TYPE
        SYNTAX         AluWdmTtiStatus
        MAX-ACCESS     read-only
        STATUS         current
        DESCRIPTION    "ODU2 TTI status."
        ::= { tnDwdmCmnLinePortInfoEntry 4 }

--    obsolete
--    tnDwdmCmnLinePortAvailableBandwidth OBJECT-TYPE ::= { tnDwdmCmnLinePortInfoEntry 5 }

    tnDwdmCmnLinePortOtu2PreFec OBJECT-TYPE
        SYNTAX         Counter64
        MAX-ACCESS     read-only
        STATUS         current
        DESCRIPTION    "Real time error bit rate of pre-FEC (Forward
                        Error Correction)."
        ::= { tnDwdmCmnLinePortInfoEntry 6 }

    tnDwdmCmnLinePortOtu2PostFec OBJECT-TYPE
        SYNTAX         Counter64
        MAX-ACCESS     read-only
        STATUS         current
        DESCRIPTION    "Real time error bit rate of post-FEC (Forward
                        Error Correction)."
        ::= { tnDwdmCmnLinePortInfoEntry 7 }

    tnDwdmCmnLinePortOdu2IncFwFTFLTypeID OBJECT-TYPE
        SYNTAX         OCTET STRING
        MAX-ACCESS     read-only
        STATUS         current
        DESCRIPTION    "ODU2 Incoming Forward FTFL Type ID"
        ::= { tnDwdmCmnLinePortInfoEntry 8 }

    tnDwdmCmnLinePortOdu2IncFwFTFLOperID OBJECT-TYPE
        SYNTAX         OCTET STRING
        MAX-ACCESS     read-only
        STATUS         current
        DESCRIPTION    "ODU2 Incoming Forward FTFL Operator ID."
        ::= { tnDwdmCmnLinePortInfoEntry 9 }

    tnDwdmCmnLinePortOdu2IncBwFTFLTypeID OBJECT-TYPE
        SYNTAX         OCTET STRING
        MAX-ACCESS     read-only
        STATUS         current
        DESCRIPTION    "ODU2 Incoming Backward FTFL Type ID."
        ::= { tnDwdmCmnLinePortInfoEntry 10 }

    tnDwdmCmnLinePortOdu2IncBwFTFLOperID OBJECT-TYPE
        SYNTAX         OCTET STRING
        MAX-ACCESS     read-only
        STATUS         current
        DESCRIPTION    "ODU2 Incoming Backward FTFL Operator ID."
        ::= { tnDwdmCmnLinePortInfoEntry 11 }

    tnDwdmCmnLinePortOdu2IncResRow2 OBJECT-TYPE
        SYNTAX         OCTET STRING
        MAX-ACCESS     read-only
        STATUS         current
        DESCRIPTION    "ODU2 Incoming Res Row2."
        ::= { tnDwdmCmnLinePortInfoEntry 12 }

    tnDwdmCmnLinePortOdu2IncResRow4 OBJECT-TYPE
        SYNTAX         OCTET STRING
        MAX-ACCESS     read-only
        STATUS         current
        DESCRIPTION    "ODU2 Incoming Res Row4."
        ::= { tnDwdmCmnLinePortInfoEntry 13 }

    tnDwdmCmnLinePortOdu2IncExp OBJECT-TYPE
        SYNTAX         OCTET STRING
        MAX-ACCESS     read-only
        STATUS         current
        DESCRIPTION    "ODU2 Incoming Exp."
        ::= { tnDwdmCmnLinePortInfoEntry 14 }

    tnDwdmCmnLinePortOtu2IncRes OBJECT-TYPE
        SYNTAX         OCTET STRING
        MAX-ACCESS     read-only
        STATUS         current
        DESCRIPTION    "OTU2 Incoming Res."
        ::= { tnDwdmCmnLinePortInfoEntry 15 }

    tnDwdmCmnLinePortDMInfoCurrentStatus OBJECT-TYPE
        SYNTAX         AluWdmDMInfoCurrentStatus
        MAX-ACCESS     read-only
        STATUS         current
        DESCRIPTION    "Indicates whether this DM test is valid."
        ::= { tnDwdmCmnLinePortInfoEntry 16 }

    tnDwdmCmnLinePortDMInfoCurrentValue OBJECT-TYPE
        SYNTAX         Unsigned32
        MAX-ACCESS     read-only
        STATUS         current
        DESCRIPTION    "Reports the DM value in 10**(-7) seconds in the
                        current Interval."
        ::= { tnDwdmCmnLinePortInfoEntry 17 }

--------------------------------------------------------------------------------
-- DWDM Common Client Port Info Table
--------------------------------------------------------------------------------
    tnDwdmCmnClientPortInfoTable OBJECT-TYPE
        SYNTAX         SEQUENCE OF TnDwdmCmnClientPortInfoEntry
        MAX-ACCESS     not-accessible
        STATUS         current
        DESCRIPTION    "Common attributes against DWDM client ports."
        ::= { tnOpticalPortInfo 69 }

    tnDwdmCmnClientPortInfoEntry OBJECT-TYPE
        SYNTAX         TnDwdmCmnClientPortInfoEntry
        MAX-ACCESS     not-accessible
        STATUS         current
        DESCRIPTION    ""
        INDEX { ifIndex }
        ::= { tnDwdmCmnClientPortInfoTable 1 }

    TnDwdmCmnClientPortInfoEntry ::=
        SEQUENCE {
            tnDwdmCmnClientPortOtu2IncomingTti       OCTET STRING,
            tnDwdmCmnClientPortOtu2TtiStatus         AluWdmTtiStatus,
            tnDwdmCmnClientPortOdu2IncomingTti       OCTET STRING,
            tnDwdmCmnClientPortOdu2TtiStatus         AluWdmTtiStatus,
--            obsolete
--            tnDwdmCmnClientPortAvailableBandwidth    Unsigned32,
            tnDwdmCmnClientPortBroadcastPortMap      OCTET STRING,
            tnDwdmCmnClientPortOtu2PreFec            Counter64,
            tnDwdmCmnClientPortOtu2PostFec           Counter64,
            tnDwdmCmnClientPortOdu2IncFwFTFLTypeID   OCTET STRING,
            tnDwdmCmnClientPortOdu2IncFwFTFLOperID   OCTET STRING,
            tnDwdmCmnClientPortOdu2IncBwFTFLTypeID   OCTET STRING,
            tnDwdmCmnClientPortOdu2IncBwFTFLOperID   OCTET STRING,
            tnDwdmCmnClientPortOdu2IncResRow2        OCTET STRING,
            tnDwdmCmnClientPortOdu2IncResRow4        OCTET STRING,
            tnDwdmCmnClientPortOdu2IncExp            OCTET STRING,
            tnDwdmCmnClientPortOtu2IncRes            OCTET STRING
        }

    tnDwdmCmnClientPortOtu2IncomingTti OBJECT-TYPE
        SYNTAX         OCTET STRING
        MAX-ACCESS     read-only
        STATUS         current
        DESCRIPTION    "OTU2 incoming TTI."
        ::= { tnDwdmCmnClientPortInfoEntry 1 }

    tnDwdmCmnClientPortOtu2TtiStatus OBJECT-TYPE
        SYNTAX         AluWdmTtiStatus
        MAX-ACCESS     read-only
        STATUS         current
        DESCRIPTION    "OTU2 TTI status."
        ::= { tnDwdmCmnClientPortInfoEntry 2 }

    tnDwdmCmnClientPortOdu2IncomingTti OBJECT-TYPE
        SYNTAX         OCTET STRING
        MAX-ACCESS     read-only
        STATUS         current
        DESCRIPTION    "ODU2 incoming TTI."
        ::= { tnDwdmCmnClientPortInfoEntry 3 }

    tnDwdmCmnClientPortOdu2TtiStatus OBJECT-TYPE
        SYNTAX         AluWdmTtiStatus
        MAX-ACCESS     read-only
        STATUS         current
        DESCRIPTION    "ODU2 TTI status."
        ::= { tnDwdmCmnClientPortInfoEntry 4 }

--    obsolete
--    tnDwdmCmnClientPortAvailableBandwidth OBJECT-TYPE ::= { tnDwdmCmnClientPortInfoEntry 5 }

    tnDwdmCmnClientPortBroadcastPortMap OBJECT-TYPE
        SYNTAX         OCTET STRING (SIZE(0..255))
        MAX-ACCESS     read-only
        STATUS         current
        DESCRIPTION    "Client Broadcast port map."
        ::= { tnDwdmCmnClientPortInfoEntry 6 }

    tnDwdmCmnClientPortOtu2PreFec OBJECT-TYPE
        SYNTAX         Counter64
        MAX-ACCESS     read-only
        STATUS         current
        DESCRIPTION    "Real time error bit rate of pre-FEC (Forward
                        Error Correction)."
        ::= { tnDwdmCmnClientPortInfoEntry 7 }

    tnDwdmCmnClientPortOtu2PostFec OBJECT-TYPE
        SYNTAX         Counter64
        MAX-ACCESS     read-only
        STATUS         current
        DESCRIPTION    "Real time error bit rate of post-FEC (Forward
                        Error Correction)."
        ::= { tnDwdmCmnClientPortInfoEntry 8 }

    tnDwdmCmnClientPortOdu2IncFwFTFLTypeID OBJECT-TYPE
        SYNTAX         OCTET STRING
        MAX-ACCESS     read-only
        STATUS         current
        DESCRIPTION    "ODU2 Incoming Forward FTFL Type ID."
        ::= { tnDwdmCmnClientPortInfoEntry 9 }

    tnDwdmCmnClientPortOdu2IncFwFTFLOperID OBJECT-TYPE
        SYNTAX         OCTET STRING
        MAX-ACCESS     read-only
        STATUS         current
        DESCRIPTION    "ODU2 Incoming Forward FTFL Operator ID."
        ::= { tnDwdmCmnClientPortInfoEntry 10 }

    tnDwdmCmnClientPortOdu2IncBwFTFLTypeID OBJECT-TYPE
        SYNTAX         OCTET STRING
        MAX-ACCESS     read-only
        STATUS         current
        DESCRIPTION    "ODU2 Incoming Backward FTFL Type ID."
        ::= { tnDwdmCmnClientPortInfoEntry 11 }

    tnDwdmCmnClientPortOdu2IncBwFTFLOperID OBJECT-TYPE
        SYNTAX         OCTET STRING
        MAX-ACCESS     read-only
        STATUS         current
        DESCRIPTION    "ODU2 Incoming Backward FTFL Operator ID."
        ::= { tnDwdmCmnClientPortInfoEntry 12 }

    tnDwdmCmnClientPortOdu2IncResRow2 OBJECT-TYPE
        SYNTAX         OCTET STRING
        MAX-ACCESS     read-only
        STATUS         current
        DESCRIPTION    "ODU2 Incoming Res Row2."
        ::= { tnDwdmCmnClientPortInfoEntry 13 }

    tnDwdmCmnClientPortOdu2IncResRow4 OBJECT-TYPE
        SYNTAX         OCTET STRING
        MAX-ACCESS     read-only
        STATUS         current
        DESCRIPTION    "ODU2 Incoming Res Row4."
        ::= { tnDwdmCmnClientPortInfoEntry 14 }

    tnDwdmCmnClientPortOdu2IncExp OBJECT-TYPE
        SYNTAX         OCTET STRING
        MAX-ACCESS     read-only
        STATUS         current
        DESCRIPTION    "ODU2 Incoming Exp."
        ::= { tnDwdmCmnClientPortInfoEntry 15 }

    tnDwdmCmnClientPortOtu2IncRes OBJECT-TYPE
        SYNTAX         OCTET STRING
        MAX-ACCESS     read-only
        STATUS         current
        DESCRIPTION    "OTU2 Incoming Res."
        ::= { tnDwdmCmnClientPortInfoEntry 16 }

--------------------------------------------------------------------------------
-- RSMON Ingress Port Info Table
--------------------------------------------------------------------------------
    tnRsmonIngrPortInfoTable OBJECT-TYPE
        SYNTAX         SEQUENCE OF TnRsmonIngrPortInfoEntry
        MAX-ACCESS     not-accessible
        STATUS         current
        DESCRIPTION    "Common attributes against RSMON Ingress
                        supported ports."
        ::= { tnOpticalPortInfo 70 }

    tnRsmonIngrPortInfoEntry OBJECT-TYPE
        SYNTAX         TnRsmonIngrPortInfoEntry
        MAX-ACCESS     not-accessible
        STATUS         current
        DESCRIPTION    ""
        INDEX { ifIndex }
        ::= { tnRsmonIngrPortInfoTable 1 }

    TnRsmonIngrPortInfoEntry ::=
        SEQUENCE {
            tnRsmonIngrPortIncomingTti OCTET STRING,
            tnRsmonIngrPortTtiStatus   INTEGER
        }

    tnRsmonIngrPortIncomingTti OBJECT-TYPE
        SYNTAX         OCTET STRING
        MAX-ACCESS     read-only
        STATUS         current
        DESCRIPTION    "RSMON incoming TTI."
        ::= { tnRsmonIngrPortInfoEntry 1 }

    tnRsmonIngrPortTtiStatus OBJECT-TYPE
        SYNTAX         INTEGER {
                         unavailable(1),
                         normal(2),
                         mismatch(3),
                         unspecified(4)
                       }
        MAX-ACCESS     read-only
        STATUS         current
        DESCRIPTION    "RSMON TTI status."
        ::= { tnRsmonIngrPortInfoEntry 2 }

--------------------------------------------------------------------------------
-- OT Port Info Table
--------------------------------------------------------------------------------
    tnOtPortInfoTable OBJECT-TYPE
        SYNTAX         SEQUENCE OF TnOtPortInfoEntry
        MAX-ACCESS     not-accessible
        STATUS         current
        DESCRIPTION    "The ports on an OT card."
        ::= { tnOpticalPortInfo 71 }

    tnOtPortInfoEntry OBJECT-TYPE
        SYNTAX         TnOtPortInfoEntry
        MAX-ACCESS     not-accessible
        STATUS         current
        DESCRIPTION    ""
        INDEX { ifIndex }
        ::= { tnOtPortInfoTable 1 }

    TnOtPortInfoEntry ::=
        SEQUENCE {
            tnOtPortRxPower             Integer32,
            tnOtPortTxPower             Integer32,
            tnOtPortBias                Integer32,
            tnOtPortTemperature         Integer32,
            tnOtPortTxPowerLaser        Integer32,
            tnOtPortRxLanePowers        SnmpAdminString,
            tnOtPortTxLanePowers        SnmpAdminString,
            tnOtPortRxLaneBslPowers     SnmpAdminString,
            tnOtPortTxLaneBslPowers     SnmpAdminString
        }

    tnOtPortRxPower OBJECT-TYPE
        SYNTAX         Integer32
        UNITS          "mBm"
        MAX-ACCESS     read-only
        STATUS         current
        DESCRIPTION    "OT RX power."
        ::= { tnOtPortInfoEntry 1 }

    tnOtPortTxPower OBJECT-TYPE
        SYNTAX         Integer32
        UNITS          "mBm"
        MAX-ACCESS     read-only
        STATUS         current
        DESCRIPTION    "The transmit power after the VOA."
        ::= { tnOtPortInfoEntry 2 }

    tnOtPortBias OBJECT-TYPE
        SYNTAX         Integer32
        UNITS          "mA"
        MAX-ACCESS     read-only
        STATUS         current
        DESCRIPTION    "OT Bias."
        ::= { tnOtPortInfoEntry 3 }

    tnOtPortTemperature OBJECT-TYPE
        SYNTAX         Integer32
        UNITS          "Celsius"
        MAX-ACCESS     read-only
        STATUS         current
        DESCRIPTION    "OT Temperature."
        ::= { tnOtPortInfoEntry 4 }

    tnOtPortTxPowerLaser OBJECT-TYPE
        SYNTAX         Integer32
        UNITS          "mBm"
        MAX-ACCESS     read-only
        STATUS         current
        DESCRIPTION    "The transmit power after the MSA transponder and
                        before the VOA."
        ::= { tnOtPortInfoEntry 5 }

    tnOtPortRxLanePowers OBJECT-TYPE
        SYNTAX         SnmpAdminString (SIZE(0..400))
        MAX-ACCESS     read-only
        STATUS         current
        DESCRIPTION    "Displays CFP receive lane powers for the number
                        of lanes supported by a CFP type.  Receive lane
                        powers will not be displayed for the following
                        conditions:
                          - A CFP does not provide lane powers
                          - A CFP is not equipped (not present)
                          - A port is not provisioned.
                        For a CFP with 4 lanes, here is a sample output:
                          'RxPwr Lane 1  : -40.00 dBm
                           RxPwr Lane 2  : -40.00 dBm
                           RxPwr Lane 3  : -40.00 dBm
                           RxPwr Lane 4  : -40.00 dBm'
                        including the new line characters."
        ::= { tnOtPortInfoEntry 6 }

    tnOtPortTxLanePowers OBJECT-TYPE
        SYNTAX         SnmpAdminString (SIZE(0..400))
        MAX-ACCESS     read-only
        STATUS         current
        DESCRIPTION    "Displays CFP transmit lane powers for the number
                        of lanes supported by a CFP type.  Transmit lane
                        powers will not be displayed for the following
                        conditions:
                          - A CFP does not provide lane powers
                          - A CFP is not equipped (not present)
                          - A port is not provisioned.
                        For a CFP with 4 lanes, here is a sample output:
                          'TxPwr Lane 1  : -40.00 dBm
                           TxPwr Lane 2  : -40.00 dBm
                           TxPwr Lane 3  : -40.00 dBm
                           TxPwr Lane 4  : -40.00 dBm'
                        including the new line characters."
        ::= { tnOtPortInfoEntry 7 }

    tnOtPortRxLaneBslPowers OBJECT-TYPE
        SYNTAX         SnmpAdminString (SIZE(0..400))
        MAX-ACCESS     read-only
        STATUS         current
        DESCRIPTION    "Displays CFP receive lane Baseline powers
                        for the number of lanes supported by a CFP
                        type.  Receive lane powers will not be
                        displayed for the following conditions:
                          - A CFP does not provide lane powers
                          - A CFP is not equipped (not present)
                          - A port is not provisioned.
                          - A CFP port Total RX power is not Baselined
                        For a CFP with 4 lanes, here is a sample output:
                          'RxPwr Lane 1  : -8.00 dBm
                           RxPwr Lane 2  : -8.10 dBm
                           RxPwr Lane 3  : -7.80 dBm
                           RxPwr Lane 4  : -8.30 dBm'
                        including the new line characters."
        ::= { tnOtPortInfoEntry 8 }

    tnOtPortTxLaneBslPowers OBJECT-TYPE
        SYNTAX         SnmpAdminString (SIZE(0..400))
        MAX-ACCESS     read-only
        STATUS         current
        DESCRIPTION    "Displays CFP transmit lane Baseline powers
                        for the number of lanes supported by a CFP
                        type.  Receive lane powers will not be
                        displayed for the following conditions:
                          - A CFP does not provide lane powers
                          - A CFP is not equipped (not present)
                          - A port is not provisioned.
                          - A CFP port Total RX power is not Baselined
                        For a CFP with 4 lanes, here is a sample output:
                          'TxPwr Lane 1  : -8.00 dBm
                           TxPwr Lane 2  : -8.10 dBm
                           TxPwr Lane 3  : -7.80 dBm
                           TxPwr Lane 4  : -8.30 dBm'
                        including the new line characters."
        ::= { tnOtPortInfoEntry 9 }

--------------------------------------------------------------------------------
-- Wave Key Optical Port Info Table
--------------------------------------------------------------------------------
    tnWaveKeyPortInfoTable OBJECT-TYPE
        SYNTAX         SEQUENCE OF TnWaveKeyPortInfoEntry
        MAX-ACCESS     not-accessible
        STATUS         current
        DESCRIPTION    "This table is a compilation of attributes
                        associated with the ports on a Wave Key
                        decode supported optical card."
        ::= { tnOpticalPortInfo 72 }

    tnWaveKeyPortInfoEntry OBJECT-TYPE
        SYNTAX         TnWaveKeyPortInfoEntry
        MAX-ACCESS     not-accessible
        STATUS         current
        DESCRIPTION    ""
        INDEX { ifIndex }
        ::= { tnWaveKeyPortInfoTable 1 }

    TnWaveKeyPortInfoEntry ::=
        SEQUENCE {
            tnWaveKeyPortNwPowerIn                    Integer32,
            tnWaveKeyPortNwPowerOut                   Integer32,
--            obsolete
--            tnWavekeyPortWTDecoderUsageStatusIn       AluWdmWTDecoderUsageType,
--            tnWavekeyPortWTDecoderUsageStatusOut      AluWdmWTDecoderUsageType,
            tnWaveKeyPortWTDecoderMeasurementTypeIn   AluWdmWTDecoderMeasurementType,
            tnWaveKeyPortWTDecoderMeasurementTypeOut  AluWdmWTDecoderMeasurementType
        }

    tnWaveKeyPortNwPowerIn OBJECT-TYPE
        SYNTAX         Integer32
        UNITS          "mBm"
        MAX-ACCESS     read-only
        STATUS         current
        DESCRIPTION    "The total ingress power of the optical signal.
                        Current Ranges:

                        ASWG:   -9900, -3600 to 1700
                        A4PSWG: -9900, -3600 to 1700."
        ::= { tnWaveKeyPortInfoEntry 1 }

    tnWaveKeyPortNwPowerOut OBJECT-TYPE
        SYNTAX         Integer32
        UNITS          "mBm"
        MAX-ACCESS     read-only
        STATUS         current
        DESCRIPTION    "The total egress power of the optical signal.
                        Current Ranges:

                        ASWG:   -9900, -1100 to 2550
                        A4PSWG: -9900, -1100 to 2550."
        ::= { tnWaveKeyPortInfoEntry 2 }

--    obsolete
--    tnWavekeyPortWTDecoderUsageStatusIn OBJECT-TYPE ::= { tnWaveKeyPortInfoEntry 3 }
--    tnWavekeyPortWTDecoderUsageStatusOut OBJECT-TYPE ::= { tnWaveKeyPortInfoEntry 4 }

    tnWaveKeyPortWTDecoderMeasurementTypeIn OBJECT-TYPE
        SYNTAX         AluWdmWTDecoderMeasurementType
        MAX-ACCESS     read-only
        STATUS         current
        DESCRIPTION    "The measurement source for the WTD in the
                        ingress direction."
        DEFVAL         { unavailable }
        ::= { tnWaveKeyPortInfoEntry 5 }

    tnWaveKeyPortWTDecoderMeasurementTypeOut OBJECT-TYPE
        SYNTAX         AluWdmWTDecoderMeasurementType
        MAX-ACCESS     read-only
        STATUS         current
        DESCRIPTION    "The measurement source for the WTD in the
                        egress direction."
        DEFVAL         { unavailable }
        ::= { tnWaveKeyPortInfoEntry 6 }

--------------------------------------------------------------------------------
-- OMD Common Port Info Table
--------------------------------------------------------------------------------
    tnOmdPortInfoTable OBJECT-TYPE
        SYNTAX         SEQUENCE OF TnOmdPortInfoEntry
        MAX-ACCESS     not-accessible
        STATUS         current
        DESCRIPTION    "Common attributes against OMD ports for SFC and
                        SFD packs."
        ::= { tnOpticalPortInfo 73 }

    tnOmdPortInfoEntry OBJECT-TYPE
        SYNTAX         TnOmdPortInfoEntry
        MAX-ACCESS     not-accessible
        STATUS         current
        DESCRIPTION    ""
        INDEX { ifIndex }
        ::= { tnOmdPortInfoTable 1 }

    TnOmdPortInfoEntry ::=
        SEQUENCE {
            tnOmdPortReceivedPower     Integer32,
            tnOmdPortTransmittedPower  Integer32
        }

    tnOmdPortReceivedPower OBJECT-TYPE
        SYNTAX         Integer32
        UNITS          "mBm"
        MAX-ACCESS     read-only
        STATUS         current
        DESCRIPTION    "The measured power at the SIG_IN of the OMD port."
        DEFVAL         { 0 }
        ::= { tnOmdPortInfoEntry 1 }

    tnOmdPortTransmittedPower OBJECT-TYPE
        SYNTAX         Integer32
        UNITS          "mBm"
        MAX-ACCESS     read-only
        STATUS         current
        DESCRIPTION    "The measured power at the SIG_OUT of the OMD port."
        DEFVAL         { 0 }
        ::= { tnOmdPortInfoEntry 2 }

--------------------------------------------------------------------------------
-- 4DPA4 Optical Port Info Scalars
--------------------------------------------------------------------------------
    tn4dpa4PortInfoAttributeTotal OBJECT-TYPE
        SYNTAX         Integer32
        MAX-ACCESS     read-only
        STATUS         current
        DESCRIPTION    ""
        ::= { tnOpticalPortInfo 74 }

--------------------------------------------------------------------------------
-- 4DPA4 Optical Port Info Table
--------------------------------------------------------------------------------
    tn4dpa4PortInfoTable OBJECT-TYPE
        SYNTAX         SEQUENCE OF Tn4dpa4PortInfoEntry
        MAX-ACCESS     not-accessible
        STATUS         current
        DESCRIPTION    "The ports on a 4DPA4 optical card."
        ::= { tnOpticalPortInfo 75 }

    tn4dpa4PortInfoEntry OBJECT-TYPE
        SYNTAX         Tn4dpa4PortInfoEntry
        MAX-ACCESS     not-accessible
        STATUS         current
        DESCRIPTION    ""
        INDEX { ifIndex }
        ::= { tn4dpa4PortInfoTable 1 }

    Tn4dpa4PortInfoEntry ::=
        SEQUENCE {
            tn4dpa4PortInfoFunction INTEGER
        }

    tn4dpa4PortInfoFunction OBJECT-TYPE
        SYNTAX         INTEGER {
                         network(1),
                         client(2),
                         evoa(3)
                       }
        MAX-ACCESS     read-only
        STATUS         current
        DESCRIPTION    "Indicates the functional type of this 4DPA4 port."
        ::= { tn4dpa4PortInfoEntry 1 }

--------------------------------------------------------------------------------
-- CWR8-88 Optical Port Info Scalars
--------------------------------------------------------------------------------
    tnCwr8c88PortInfoAttributeTotal OBJECT-TYPE
        SYNTAX         Integer32
        MAX-ACCESS     read-only
        STATUS         current
        DESCRIPTION    ""
        ::= { tnOpticalPortInfo 76 }

--------------------------------------------------------------------------------
-- CWR8-88 Optical Port Info Table
--------------------------------------------------------------------------------
    tnCwr8c88PortInfoTable OBJECT-TYPE
        SYNTAX         SEQUENCE OF TnCwr8c88PortInfoEntry
        MAX-ACCESS     not-accessible
        STATUS         current
        DESCRIPTION    "The ports on a CWR8-88 optical card."
        ::= { tnOpticalPortInfo 77 }

    tnCwr8c88PortInfoEntry OBJECT-TYPE
        SYNTAX         TnCwr8c88PortInfoEntry
        MAX-ACCESS     not-accessible
        STATUS         current
        DESCRIPTION    ""
        INDEX { ifIndex }
        ::= { tnCwr8c88PortInfoTable 1 }

    TnCwr8c88PortInfoEntry ::=
        SEQUENCE {
            tnCwr8c88PortInfoFunction           INTEGER,
            tnCwr8c88PortRelativeAttenuationMin Unsigned32,
            tnCwr8c88PortAverageAttenuationOut  Unsigned32
        }

    tnCwr8c88PortInfoFunction OBJECT-TYPE
        SYNTAX         INTEGER {
                         signal(1),
                         test(2),
                         thru(3),
                         colorless(4),
                         omd(5),
                         inv(6)
                       }
        MAX-ACCESS     read-only
        STATUS         current
        DESCRIPTION    "Indicates the functional type of this CWR8-88 port."
        ::= { tnCwr8c88PortInfoEntry 1 }

    tnCwr8c88PortRelativeAttenuationMin OBJECT-TYPE
        SYNTAX         Unsigned32
        UNITS          "mB"
        MAX-ACCESS     read-only
        STATUS         current
        DESCRIPTION    "The following description applies to the Thru
                        port of the CWR8-88 card:

                        The minimum attenuation on the blocker across
                        all of the channels."
        DEFVAL         { 0 }
        ::= { tnCwr8c88PortInfoEntry 2 }

    tnCwr8c88PortAverageAttenuationOut OBJECT-TYPE
        SYNTAX         Unsigned32
        UNITS          "mB"
        MAX-ACCESS     read-only
        STATUS         current
        DESCRIPTION    "The following description applies to the Thru
                        port of the CWR8-88 card:

                        The average attenuation on the blocker across
                        all of the channels."
        DEFVAL         { 0 }
        ::= { tnCwr8c88PortInfoEntry 3 }

--------------------------------------------------------------------------------
-- AHPLG Optical Port Info Scalars
--------------------------------------------------------------------------------
    tnAhplgPortInfoAttributeTotal OBJECT-TYPE
        SYNTAX         Integer32
        MAX-ACCESS     read-only
        STATUS         current
        DESCRIPTION    ""
        ::= { tnOpticalPortInfo 78 }

--------------------------------------------------------------------------------
-- AHPLG Optical Port Info Table
--------------------------------------------------------------------------------
    tnAhplgPortInfoTable OBJECT-TYPE
        SYNTAX         SEQUENCE OF TnAhplgPortInfoEntry
        MAX-ACCESS     not-accessible
        STATUS         current
        DESCRIPTION    "The ports on an AHPLG optical card."
        ::= { tnOpticalPortInfo 79 }

    tnAhplgPortInfoEntry OBJECT-TYPE
        SYNTAX         TnAhplgPortInfoEntry
        MAX-ACCESS     not-accessible
        STATUS         current
        DESCRIPTION    ""
        INDEX { ifIndex }
        ::= { tnAhplgPortInfoTable 1 }

    TnAhplgPortInfoEntry ::=
        SEQUENCE {
            tnAhplgPortInfoFunction INTEGER
        }

    tnAhplgPortInfoFunction OBJECT-TYPE
        SYNTAX         INTEGER {
                         line(1),
                         signal(2),
                         dcm(3),
                         inv(4),
                         osc(5)
                       }
        MAX-ACCESS     read-only
        STATUS         current
        DESCRIPTION    "Indicates the functional type of this AHPLG port."
        ::= { tnAhplgPortInfoEntry 1 }

--------------------------------------------------------------------------------
-- Line Port Timeslot Info Table
--------------------------------------------------------------------------------
    tnTimeSlotLinePortInfoTable OBJECT-TYPE
        SYNTAX         SEQUENCE OF TnTimeSlotLinePortInfoEntry
        MAX-ACCESS     not-accessible
        STATUS         current
        DESCRIPTION    "The line port timeslots on an optical card."
        ::= { tnOpticalPortInfo 80 }

    tnTimeSlotLinePortInfoEntry OBJECT-TYPE
        SYNTAX         TnTimeSlotLinePortInfoEntry
        MAX-ACCESS     not-accessible
        STATUS         current
        DESCRIPTION    ""
        INDEX { ifIndex,
                tnTimeSlot }
        ::= { tnTimeSlotLinePortInfoTable 1 }

    TnTimeSlotLinePortInfoEntry ::=
        SEQUENCE {
            tnTimeSlot                               Unsigned32,
            tnTimeSlotLinePortFarEndIfType           AluWdmTnIfType,
            tnTimeSlotLinePortFarEndInterfaceIndex   InterfaceIndex,
            tnTimeSlotLinePortNearEndIfType          AluWdmTnIfType,
            tnTimeSlotLinePortNearEndInterfaceIndex  InterfaceIndex
        }

    tnTimeSlot OBJECT-TYPE
        SYNTAX         Unsigned32
        MAX-ACCESS     not-accessible
        STATUS         current
        DESCRIPTION    "Timeslot index."
        ::= { tnTimeSlotLinePortInfoEntry 1 }

    tnTimeSlotLinePortFarEndIfType OBJECT-TYPE
        SYNTAX         AluWdmTnIfType
        MAX-ACCESS     read-only
        STATUS         current
        DESCRIPTION    "Far end line port interface type."
        ::= { tnTimeSlotLinePortInfoEntry 2 }

    tnTimeSlotLinePortFarEndInterfaceIndex OBJECT-TYPE
        SYNTAX         InterfaceIndex
        MAX-ACCESS     read-only
        STATUS         current
        DESCRIPTION    "Far end line port interface index."
        ::= { tnTimeSlotLinePortInfoEntry 3 }

    tnTimeSlotLinePortNearEndIfType OBJECT-TYPE
        SYNTAX         AluWdmTnIfType
        MAX-ACCESS     read-only
        STATUS         current
        DESCRIPTION    "Near end line port interface type."
        ::= { tnTimeSlotLinePortInfoEntry 4 }

    tnTimeSlotLinePortNearEndInterfaceIndex OBJECT-TYPE
        SYNTAX         InterfaceIndex
        MAX-ACCESS     read-only
        STATUS         current
        DESCRIPTION    "Near end line port interface index."
        ::= { tnTimeSlotLinePortInfoEntry 5 }

--------------------------------------------------------------------------------
-- DWDM Common OTU1/ODU1 Line Port Info Table
--------------------------------------------------------------------------------
    tnDwdmCmnOtu1Odu1LinePortInfoTable OBJECT-TYPE
        SYNTAX         SEQUENCE OF TnDwdmCmnOtu1Odu1LinePortInfoEntry
        MAX-ACCESS     not-accessible
        STATUS         current
        DESCRIPTION    "Common attributes against DWDM line ports."
        ::= { tnOpticalPortInfo 81 }

    tnDwdmCmnOtu1Odu1LinePortInfoEntry OBJECT-TYPE
        SYNTAX         TnDwdmCmnOtu1Odu1LinePortInfoEntry
        MAX-ACCESS     not-accessible
        STATUS         current
        DESCRIPTION    ""
        INDEX { ifIndex }
        ::= { tnDwdmCmnOtu1Odu1LinePortInfoTable 1 }

    TnDwdmCmnOtu1Odu1LinePortInfoEntry ::=
        SEQUENCE {
            tnDwdmCmnLinePortOtu1IncomingTti OCTET STRING,
            tnDwdmCmnLinePortOtu1TtiStatus   AluWdmTtiStatus,
            tnDwdmCmnLinePortOdu1IncomingTti OCTET STRING,
            tnDwdmCmnLinePortOdu1TtiStatus   AluWdmTtiStatus
        }

    tnDwdmCmnLinePortOtu1IncomingTti OBJECT-TYPE
        SYNTAX         OCTET STRING
        MAX-ACCESS     read-only
        STATUS         current
        DESCRIPTION    "OTU1 incoming TTI."
        DEFVAL         { "" }
        ::= { tnDwdmCmnOtu1Odu1LinePortInfoEntry 1 }

    tnDwdmCmnLinePortOtu1TtiStatus OBJECT-TYPE
        SYNTAX         AluWdmTtiStatus
        MAX-ACCESS     read-only
        STATUS         current
        DESCRIPTION    "OTU1 TTI status."
        DEFVAL         { unspecified }
        ::= { tnDwdmCmnOtu1Odu1LinePortInfoEntry 2 }

    tnDwdmCmnLinePortOdu1IncomingTti OBJECT-TYPE
        SYNTAX         OCTET STRING
        MAX-ACCESS     read-only
        STATUS         current
        DESCRIPTION    "ODU1 incoming TTI."
        DEFVAL         { "" }
        ::= { tnDwdmCmnOtu1Odu1LinePortInfoEntry 3 }

    tnDwdmCmnLinePortOdu1TtiStatus OBJECT-TYPE
        SYNTAX         AluWdmTtiStatus
        MAX-ACCESS     read-only
        STATUS         current
        DESCRIPTION    "ODU1 TTI status."
        DEFVAL         { unspecified }
        ::= { tnDwdmCmnOtu1Odu1LinePortInfoEntry 4 }

--------------------------------------------------------------------------------
-- DWDM Common OTU1/ODU1 Client Port Info Table
--------------------------------------------------------------------------------
    tnDwdmCmnOtu1Odu1ClientPortInfoTable OBJECT-TYPE
        SYNTAX         SEQUENCE OF TnDwdmCmnOtu1Odu1ClientPortInfoEntry
        MAX-ACCESS     not-accessible
        STATUS         current
        DESCRIPTION    "Common attributes against DWDM client ports."
        ::= { tnOpticalPortInfo 82 }

    tnDwdmCmnOtu1Odu1ClientPortInfoEntry OBJECT-TYPE
        SYNTAX         TnDwdmCmnOtu1Odu1ClientPortInfoEntry
        MAX-ACCESS     not-accessible
        STATUS         current
        DESCRIPTION    ""
        INDEX { ifIndex }
        ::= { tnDwdmCmnOtu1Odu1ClientPortInfoTable 1 }

    TnDwdmCmnOtu1Odu1ClientPortInfoEntry ::=
        SEQUENCE {
            tnDwdmCmnClientPortOtu1IncomingTti OCTET STRING,
            tnDwdmCmnClientPortOtu1TtiStatus   AluWdmTtiStatus,
            tnDwdmCmnClientPortOdu1IncomingTti OCTET STRING,
            tnDwdmCmnClientPortOdu1TtiStatus   AluWdmTtiStatus,
            tnDwdmCmnClientPortOtu1PreFec      Counter64,
            tnDwdmCmnClientPortOtu1PostFec     Counter64
        }

    tnDwdmCmnClientPortOtu1IncomingTti OBJECT-TYPE
        SYNTAX         OCTET STRING
        MAX-ACCESS     read-only
        STATUS         current
        DESCRIPTION    "OTU1 incoming TTI."
        DEFVAL         { "" }
        ::= { tnDwdmCmnOtu1Odu1ClientPortInfoEntry 1 }

    tnDwdmCmnClientPortOtu1TtiStatus OBJECT-TYPE
        SYNTAX         AluWdmTtiStatus
        MAX-ACCESS     read-only
        STATUS         current
        DESCRIPTION    "OTU1 TTI status."
        DEFVAL         { unspecified }
        ::= { tnDwdmCmnOtu1Odu1ClientPortInfoEntry 2 }

    tnDwdmCmnClientPortOdu1IncomingTti OBJECT-TYPE
        SYNTAX         OCTET STRING
        MAX-ACCESS     read-only
        STATUS         current
        DESCRIPTION    "ODU1 incoming TTI."
        DEFVAL         { "" }
        ::= { tnDwdmCmnOtu1Odu1ClientPortInfoEntry 3 }

    tnDwdmCmnClientPortOdu1TtiStatus OBJECT-TYPE
        SYNTAX         AluWdmTtiStatus
        MAX-ACCESS     read-only
        STATUS         current
        DESCRIPTION    "ODU1 TTI status."
        DEFVAL         { unspecified }
        ::= { tnDwdmCmnOtu1Odu1ClientPortInfoEntry 4 }

    tnDwdmCmnClientPortOtu1PreFec OBJECT-TYPE
        SYNTAX         Counter64
        MAX-ACCESS     read-only
        STATUS         current
        DESCRIPTION    "Real time error bit rate of pre-FEC (Forward
                        Error Correction).

                        Current configurable range: 0 to 4000."
        ::= { tnDwdmCmnOtu1Odu1ClientPortInfoEntry 5 }

    tnDwdmCmnClientPortOtu1PostFec OBJECT-TYPE
        SYNTAX         Counter64
        MAX-ACCESS     read-only
        STATUS         current
        DESCRIPTION    "Real time error bit rate of post-FEC (Forward
                        Error Correction).

                        Current configurable range: 0 to 4000."
        ::= { tnDwdmCmnOtu1Odu1ClientPortInfoEntry 6 }

--------------------------------------------------------------------------------
-- 43STX4 Optical Port Info Scalars
--------------------------------------------------------------------------------
    tn43stx4PortInfoAttributeTotal OBJECT-TYPE
        SYNTAX         Integer32
        MAX-ACCESS     read-only
        STATUS         current
        DESCRIPTION    ""
        ::= { tnOpticalPortInfo 83 }

--------------------------------------------------------------------------------
-- 43STX4 Optical Port Info Table
--------------------------------------------------------------------------------
    tn43stx4PortInfoTable OBJECT-TYPE
        SYNTAX         SEQUENCE OF Tn43stx4PortInfoEntry
        MAX-ACCESS     not-accessible
        STATUS         current
        DESCRIPTION    "The ports on a 43STX4 optical card."
        ::= { tnOpticalPortInfo 84 }

    tn43stx4PortInfoEntry OBJECT-TYPE
        SYNTAX         Tn43stx4PortInfoEntry
        MAX-ACCESS     not-accessible
        STATUS         current
        DESCRIPTION    ""
        INDEX { ifIndex }
        ::= { tn43stx4PortInfoTable 1 }

    Tn43stx4PortInfoEntry ::=
        SEQUENCE {
            tn43stx4PortInfoFunction INTEGER
        }

    tn43stx4PortInfoFunction OBJECT-TYPE
        SYNTAX         INTEGER {
                         network(1),
                         client(2)
                       }
        MAX-ACCESS     read-only
        STATUS         current
        DESCRIPTION    "Indicates the functional type of this 43STX4 port."
        ::= { tn43stx4PortInfoEntry 1 }

--------------------------------------------------------------------------------
-- DWDM Common OTU3/ODU3 Line Port Info Table
--------------------------------------------------------------------------------
    tnDwdmCmnOtu3Odu3LinePortInfoTable OBJECT-TYPE
        SYNTAX         SEQUENCE OF TnDwdmCmnOtu3Odu3LinePortInfoEntry
        MAX-ACCESS     not-accessible
        STATUS         current
        DESCRIPTION    "Common attributes against DWDM line ports."
        ::= { tnOpticalPortInfo 85 }

    tnDwdmCmnOtu3Odu3LinePortInfoEntry OBJECT-TYPE
        SYNTAX         TnDwdmCmnOtu3Odu3LinePortInfoEntry
        MAX-ACCESS     not-accessible
        STATUS         current
        DESCRIPTION    ""
        INDEX { ifIndex }
        ::= { tnDwdmCmnOtu3Odu3LinePortInfoTable 1 }

    TnDwdmCmnOtu3Odu3LinePortInfoEntry ::=
        SEQUENCE {
            tnDwdmCmnLinePortOtu3IncomingTti      OCTET STRING,
            tnDwdmCmnLinePortOtu3TtiStatus        AluWdmTtiStatus,
            tnDwdmCmnLinePortOdu3IncomingTti      OCTET STRING,
            tnDwdmCmnLinePortOdu3TtiStatus        AluWdmTtiStatus,
            tnDwdmCmnLinePortOtu3PreFec           Counter64,
            tnDwdmCmnLinePortOtu3PostFec          Counter64,
            tnDwdmCmnLinePortOdu3IncFwFTFLTypeID  OCTET STRING,
            tnDwdmCmnLinePortOdu3IncFwFTFLOperID  OCTET STRING,
            tnDwdmCmnLinePortOdu3IncBwFTFLTypeID  OCTET STRING,
            tnDwdmCmnLinePortOdu3IncBwFTFLOperID  OCTET STRING,
            tnDwdmCmnLinePortOdu3IncResRow2       OCTET STRING,
            tnDwdmCmnLinePortOdu3IncResRow4       OCTET STRING,
            tnDwdmCmnLinePortOdu3IncExp           OCTET STRING,
            tnDwdmCmnLinePortOtu3IncRes           OCTET STRING
        }

    tnDwdmCmnLinePortOtu3IncomingTti OBJECT-TYPE
        SYNTAX         OCTET STRING
        MAX-ACCESS     read-only
        STATUS         current
        DESCRIPTION    "OTU3 incoming TTI."
        DEFVAL         { "" }
        ::= { tnDwdmCmnOtu3Odu3LinePortInfoEntry 1 }

    tnDwdmCmnLinePortOtu3TtiStatus OBJECT-TYPE
        SYNTAX         AluWdmTtiStatus
        MAX-ACCESS     read-only
        STATUS         current
        DESCRIPTION    "OTU3 TTI status."
        DEFVAL         { unspecified }
        ::= { tnDwdmCmnOtu3Odu3LinePortInfoEntry 2 }

    tnDwdmCmnLinePortOdu3IncomingTti OBJECT-TYPE
        SYNTAX         OCTET STRING
        MAX-ACCESS     read-only
        STATUS         current
        DESCRIPTION    "ODU3 incoming TTI."
        DEFVAL         { "" }
        ::= { tnDwdmCmnOtu3Odu3LinePortInfoEntry 3 }

    tnDwdmCmnLinePortOdu3TtiStatus OBJECT-TYPE
        SYNTAX         AluWdmTtiStatus
        MAX-ACCESS     read-only
        STATUS         current
        DESCRIPTION    "ODU3 TTI status."
        DEFVAL         { unspecified }
        ::= { tnDwdmCmnOtu3Odu3LinePortInfoEntry 4 }

    tnDwdmCmnLinePortOtu3PreFec OBJECT-TYPE
        SYNTAX         Counter64
        MAX-ACCESS     read-only
        STATUS         current
        DESCRIPTION    "Real time error bit rate of pre-FEC (Forward
                        Error Correction).

                        Current configurable range: 0 to 4000."
        ::= { tnDwdmCmnOtu3Odu3LinePortInfoEntry 5 }

    tnDwdmCmnLinePortOtu3PostFec OBJECT-TYPE
        SYNTAX         Counter64
        MAX-ACCESS     read-only
        STATUS         current
        DESCRIPTION    "Real time error bit rate of post-FEC (Forward
                        Error Correction).

                        Current configurable range: 0 to 4000."
        ::= { tnDwdmCmnOtu3Odu3LinePortInfoEntry 6 }

    tnDwdmCmnLinePortOdu3IncFwFTFLTypeID OBJECT-TYPE
        SYNTAX         OCTET STRING
        MAX-ACCESS     read-only
        STATUS         current
        DESCRIPTION    "ODU3 Incoming Forward FTFL Type ID."
        DEFVAL         { "" }
        ::= { tnDwdmCmnOtu3Odu3LinePortInfoEntry 7 }

    tnDwdmCmnLinePortOdu3IncFwFTFLOperID OBJECT-TYPE
        SYNTAX         OCTET STRING
        MAX-ACCESS     read-only
        STATUS         current
        DESCRIPTION    "ODU3 Incoming Forward FTFL Operator ID."
        DEFVAL         { "" }
        ::= { tnDwdmCmnOtu3Odu3LinePortInfoEntry 8 }

    tnDwdmCmnLinePortOdu3IncBwFTFLTypeID OBJECT-TYPE
        SYNTAX         OCTET STRING
        MAX-ACCESS     read-only
        STATUS         current
        DESCRIPTION    "ODU3 Incoming Backward FTFL Type ID."
        DEFVAL         { "" }
        ::= { tnDwdmCmnOtu3Odu3LinePortInfoEntry 9 }

    tnDwdmCmnLinePortOdu3IncBwFTFLOperID OBJECT-TYPE
        SYNTAX         OCTET STRING
        MAX-ACCESS     read-only
        STATUS         current
        DESCRIPTION    "ODU3 Incoming Backward FTFL Operator ID."
        DEFVAL         { "" }
        ::= { tnDwdmCmnOtu3Odu3LinePortInfoEntry 10 }

    tnDwdmCmnLinePortOdu3IncResRow2 OBJECT-TYPE
        SYNTAX         OCTET STRING
        MAX-ACCESS     read-only
        STATUS         current
        DESCRIPTION    "ODU3 Incoming Res Row2."
        DEFVAL         { "" }
        ::= { tnDwdmCmnOtu3Odu3LinePortInfoEntry 11 }

    tnDwdmCmnLinePortOdu3IncResRow4 OBJECT-TYPE
        SYNTAX         OCTET STRING
        MAX-ACCESS     read-only
        STATUS         current
        DESCRIPTION    "ODU3 Incoming Res Row4."
        DEFVAL         { "" }
        ::= { tnDwdmCmnOtu3Odu3LinePortInfoEntry 12 }

    tnDwdmCmnLinePortOdu3IncExp OBJECT-TYPE
        SYNTAX         OCTET STRING
        MAX-ACCESS     read-only
        STATUS         current
        DESCRIPTION    "ODU3 Incoming Exp."
        DEFVAL         { "" }
        ::= { tnDwdmCmnOtu3Odu3LinePortInfoEntry 13 }

    tnDwdmCmnLinePortOtu3IncRes OBJECT-TYPE
        SYNTAX         OCTET STRING
        MAX-ACCESS     read-only
        STATUS         current
        DESCRIPTION    "OTU3 Incoming Res."
        DEFVAL         { "" }
        ::= { tnDwdmCmnOtu3Odu3LinePortInfoEntry 14 }

--------------------------------------------------------------------------------
-- ALPFGK Optical Port Info Scalars
--------------------------------------------------------------------------------
    tnAlpfgkPortInfoAttributeTotal OBJECT-TYPE
        SYNTAX         Integer32
        MAX-ACCESS     read-only
        STATUS         current
        DESCRIPTION    ""
        ::= { tnOpticalPortInfo 86 }

--------------------------------------------------------------------------------
-- ALPFGK Optical Port Info Table
--------------------------------------------------------------------------------
    tnAlpfgkPortInfoTable OBJECT-TYPE
        SYNTAX         SEQUENCE OF TnAlpfgkPortInfoEntry
        MAX-ACCESS     not-accessible
        STATUS         current
        DESCRIPTION    "The ports on an ALPFGK optical card."
        ::= { tnOpticalPortInfo 87 }

    tnAlpfgkPortInfoEntry OBJECT-TYPE
        SYNTAX         TnAlpfgkPortInfoEntry
        MAX-ACCESS     not-accessible
        STATUS         current
        DESCRIPTION    ""
        INDEX { ifIndex }
        ::= { tnAlpfgkPortInfoTable 1 }

    TnAlpfgkPortInfoEntry ::=
        SEQUENCE {
            tnAlpfgkPortInfoFunction  INTEGER
        }

    tnAlpfgkPortInfoFunction OBJECT-TYPE
        SYNTAX         INTEGER {
                         line(1),
                         signal(2),
                         inv(3),
                         osc(4),
                         oscSfp(5)
                       }
        MAX-ACCESS     read-only
        STATUS         current
        DESCRIPTION    "Indicates the functional type of this ALPFGK port."
        ::= { tnAlpfgkPortInfoEntry 1 }

--------------------------------------------------------------------------------
-- 4DPA2 Optical Port Info Scalars
--------------------------------------------------------------------------------
    tn4dpa2PortInfoAttributeTotal OBJECT-TYPE
        SYNTAX         Integer32
        MAX-ACCESS     read-only
        STATUS         current
        DESCRIPTION    ""
        ::= { tnOpticalPortInfo 88 }

--------------------------------------------------------------------------------
-- 4DPA2 Optical Port Info Table
--------------------------------------------------------------------------------
    tn4dpa2PortInfoTable OBJECT-TYPE
        SYNTAX         SEQUENCE OF Tn4dpa2PortInfoEntry
        MAX-ACCESS     not-accessible
        STATUS         current
        DESCRIPTION    "The ports on a 4DPA2 optical card."
        ::= { tnOpticalPortInfo 89 }

    tn4dpa2PortInfoEntry OBJECT-TYPE
        SYNTAX         Tn4dpa2PortInfoEntry
        MAX-ACCESS     not-accessible
        STATUS         current
        DESCRIPTION    ""
        INDEX { ifIndex }
        ::= { tn4dpa2PortInfoTable 1 }

    Tn4dpa2PortInfoEntry ::=
        SEQUENCE {
            tn4dpa2PortInfoFunction INTEGER
        }

    tn4dpa2PortInfoFunction OBJECT-TYPE
        SYNTAX         INTEGER {
                         network(1),
                         client(2)
                       }
        MAX-ACCESS     read-only
        STATUS         current
        DESCRIPTION    "Indicates the functional type of this 4DPA2 port."
        ::= { tn4dpa2PortInfoEntry 1 }

--------------------------------------------------------------------------------
-- 43STA1P Optical Port Info Scalars
--------------------------------------------------------------------------------
    tn43sta1pPortInfoAttributeTotal OBJECT-TYPE
        SYNTAX         Integer32
        MAX-ACCESS     read-only
        STATUS         current
        DESCRIPTION    ""
        ::= { tnOpticalPortInfo 90 }

--------------------------------------------------------------------------------
-- 43STA1P Optical Port Info Table
--------------------------------------------------------------------------------
    tn43sta1pPortInfoTable OBJECT-TYPE
        SYNTAX         SEQUENCE OF Tn43sta1pPortInfoEntry
        MAX-ACCESS     not-accessible
        STATUS         current
        DESCRIPTION    "The ports on a 43STA1P optical card."
        ::= { tnOpticalPortInfo 91 }

    tn43sta1pPortInfoEntry OBJECT-TYPE
        SYNTAX         Tn43sta1pPortInfoEntry
        MAX-ACCESS     not-accessible
        STATUS         current
        DESCRIPTION    ""
        INDEX { ifIndex }
        ::= { tn43sta1pPortInfoTable 1 }

    Tn43sta1pPortInfoEntry ::=
        SEQUENCE {
            tn43sta1pPortInfoFunction INTEGER
        }

    tn43sta1pPortInfoFunction OBJECT-TYPE
        SYNTAX         INTEGER {
                         network(1),
                         client(2)
                       }
        MAX-ACCESS     read-only
        STATUS         current
        DESCRIPTION    "Indicates the functional type of this 43STA1P port."
        ::= { tn43sta1pPortInfoEntry 1 }

--------------------------------------------------------------------------------
-- 43STX4P Optical Port Info Scalars
--------------------------------------------------------------------------------
    tn43stx4pPortInfoAttributeTotal OBJECT-TYPE
        SYNTAX         Integer32
        MAX-ACCESS     read-only
        STATUS         current
        DESCRIPTION    ""
        ::= { tnOpticalPortInfo 92 }

--------------------------------------------------------------------------------
-- 43STX4P Optical Port Info Table
--------------------------------------------------------------------------------
    tn43stx4pPortInfoTable OBJECT-TYPE
        SYNTAX         SEQUENCE OF Tn43stx4pPortInfoEntry
        MAX-ACCESS     not-accessible
        STATUS         current
        DESCRIPTION    "The ports on a 43STX4P optical card."
        ::= { tnOpticalPortInfo 93 }

    tn43stx4pPortInfoEntry OBJECT-TYPE
        SYNTAX         Tn43stx4pPortInfoEntry
        MAX-ACCESS     not-accessible
        STATUS         current
        DESCRIPTION    ""
        INDEX { ifIndex }
        ::= { tn43stx4pPortInfoTable 1 }

    Tn43stx4pPortInfoEntry ::=
        SEQUENCE {
            tn43stx4pPortInfoFunction INTEGER
        }

    tn43stx4pPortInfoFunction OBJECT-TYPE
        SYNTAX         INTEGER {
                         network(1),
                         client(2)
                       }
        MAX-ACCESS     read-only
        STATUS         current
        DESCRIPTION    "Indicates the functional type of this 43STX4P port."
        ::= { tn43stx4pPortInfoEntry 1 }

--------------------------------------------------------------------------------
-- RSMON Egress Port Info Table
--------------------------------------------------------------------------------
    tnRsmonEgrPortInfoTable OBJECT-TYPE
        SYNTAX         SEQUENCE OF TnRsmonEgrPortInfoEntry
        MAX-ACCESS     not-accessible
        STATUS         current
        DESCRIPTION    "Common attributes against RSMON Egress supported ports."
        ::= { tnOpticalPortInfo 96 }

    tnRsmonEgrPortInfoEntry OBJECT-TYPE
        SYNTAX         TnRsmonEgrPortInfoEntry
        MAX-ACCESS     not-accessible
        STATUS         current
        DESCRIPTION    ""
        INDEX { ifIndex }
        ::= { tnRsmonEgrPortInfoTable 1 }

    TnRsmonEgrPortInfoEntry ::=
        SEQUENCE {
            tnRsmonEgrPortIncomingTti  OCTET STRING,
            tnRsmonEgrPortTtiStatus    AluWdmTtiStatus
        }

    tnRsmonEgrPortIncomingTti OBJECT-TYPE
        SYNTAX         OCTET STRING
        MAX-ACCESS     read-only
        STATUS         current
        DESCRIPTION    "RSMON incoming TTI."
        DEFVAL         { "" }
        ::= { tnRsmonEgrPortInfoEntry 1 }

    tnRsmonEgrPortTtiStatus OBJECT-TYPE
        SYNTAX         AluWdmTtiStatus
        MAX-ACCESS     read-only
        STATUS         current
        DESCRIPTION    "RSMON TTI status."
        DEFVAL         { unspecified }
        ::= { tnRsmonEgrPortInfoEntry 2 }

--------------------------------------------------------------------------------
-- A2325A Optical Port Info Scalars
--------------------------------------------------------------------------------
    tnA2325aPortInfoAttributeTotal OBJECT-TYPE
        SYNTAX         Integer32
        MAX-ACCESS     read-only
        STATUS         current
        DESCRIPTION    ""
        ::= { tnOpticalPortInfo 97 }

--------------------------------------------------------------------------------
-- A2325A Optical Port Info Table
--------------------------------------------------------------------------------
    tnA2325aPortInfoTable OBJECT-TYPE
        SYNTAX         SEQUENCE OF TnA2325aPortInfoEntry
        MAX-ACCESS     not-accessible
        STATUS         current
        DESCRIPTION    "The ports on an A2325A optical card."
        ::= { tnOpticalPortInfo 98 }

    tnA2325aPortInfoEntry OBJECT-TYPE
        SYNTAX         TnA2325aPortInfoEntry
        MAX-ACCESS     not-accessible
        STATUS         current
        DESCRIPTION    ""
        INDEX { ifIndex }
        ::= { tnA2325aPortInfoTable 1 }

    TnA2325aPortInfoEntry ::=
        SEQUENCE {
            tnA2325aPortInfoFunction INTEGER
        }

    tnA2325aPortInfoFunction OBJECT-TYPE
        SYNTAX         INTEGER {
                         line(1),
                         signal(2),
                         dcm(3),
                         inv(4),
                         osc(5)
                       }
        MAX-ACCESS     read-only
        STATUS         current
        DESCRIPTION    "Indicates the functional type of this A2325A port."
        ::= { tnA2325aPortInfoEntry 1 }

--------------------------------------------------------------------------------
-- 11QPA4 Optical Port Info Scalars
--------------------------------------------------------------------------------
    tn11qpa4PortInfoAttributeTotal OBJECT-TYPE
        SYNTAX         Integer32
        MAX-ACCESS     read-only
        STATUS         current
        DESCRIPTION    ""
        ::= { tnOpticalPortInfo 99 }

--------------------------------------------------------------------------------
-- 11QPA4 Optical Port Info Table
--------------------------------------------------------------------------------
    tn11qpa4PortInfoTable OBJECT-TYPE
        SYNTAX         SEQUENCE OF Tn11qpa4PortInfoEntry
        MAX-ACCESS     not-accessible
        STATUS         current
        DESCRIPTION    "The ports on a 11QPA4 optical card."
        ::= { tnOpticalPortInfo 100 }

    tn11qpa4PortInfoEntry OBJECT-TYPE
        SYNTAX         Tn11qpa4PortInfoEntry
        MAX-ACCESS     not-accessible
        STATUS         current
        DESCRIPTION    ""
        INDEX { ifIndex }
        ::= { tn11qpa4PortInfoTable 1 }

    Tn11qpa4PortInfoEntry ::=
        SEQUENCE {
            tn11qpa4PortInfoFunction INTEGER
        }

    tn11qpa4PortInfoFunction OBJECT-TYPE
        SYNTAX         INTEGER {
                         network(1),
                         client(2),
                         evoa(3)
                       }
        MAX-ACCESS     read-only
        STATUS         current
        DESCRIPTION    "Indicates the functional type of this 11QPA4 port."
        ::= { tn11qpa4PortInfoEntry 1 }

--------------------------------------------------------------------------------
-- 112SCX10 Optical Port Info Scalars
--------------------------------------------------------------------------------
    tn112scx10PortInfoAttributeTotal OBJECT-TYPE
        SYNTAX         Integer32
        MAX-ACCESS     read-only
        STATUS         current
        DESCRIPTION    ""
        ::= { tnOpticalPortInfo 101 }

--------------------------------------------------------------------------------
-- 112SCX10 Optical Port Info Table
--------------------------------------------------------------------------------
    tn112scx10PortInfoTable OBJECT-TYPE
        SYNTAX         SEQUENCE OF Tn112scx10PortInfoEntry
        MAX-ACCESS     not-accessible
        STATUS         current
        DESCRIPTION    "The ports on a 112SCX10 optical card."
        ::= { tnOpticalPortInfo 102 }

    tn112scx10PortInfoEntry OBJECT-TYPE
        SYNTAX         Tn112scx10PortInfoEntry
        MAX-ACCESS     not-accessible
        STATUS         current
        DESCRIPTION    ""
        INDEX { ifIndex }
        ::= { tn112scx10PortInfoTable 1 }

    Tn112scx10PortInfoEntry ::=
        SEQUENCE {
            tn112scx10PortInfoFunction INTEGER
        }

    tn112scx10PortInfoFunction OBJECT-TYPE
        SYNTAX         INTEGER {
                         network(1),
                         client(2)
                       }
        MAX-ACCESS     read-only
        STATUS         current
        DESCRIPTION    "Indicates the functional type of this 112SCX10 port."
        ::= { tn112scx10PortInfoEntry 1 }

--------------------------------------------------------------------------------
-- 112SCA1 Optical Port Info Scalars
--------------------------------------------------------------------------------
    tn112sca1PortInfoAttributeTotal OBJECT-TYPE
        SYNTAX         Integer32
        MAX-ACCESS     read-only
        STATUS         current
        DESCRIPTION    ""
        ::= { tnOpticalPortInfo 103 }

--------------------------------------------------------------------------------
-- 112SCA1 Optical Port Info Table
--------------------------------------------------------------------------------
    tn112sca1PortInfoTable OBJECT-TYPE
        SYNTAX         SEQUENCE OF Tn112sca1PortInfoEntry
        MAX-ACCESS     not-accessible
        STATUS         current
        DESCRIPTION    "The ports on a 112SCA1 optical card."
        ::= { tnOpticalPortInfo 104 }

    tn112sca1PortInfoEntry OBJECT-TYPE
        SYNTAX         Tn112sca1PortInfoEntry
        MAX-ACCESS     not-accessible
        STATUS         current
        DESCRIPTION    ""
        INDEX { ifIndex }
        ::= { tn112sca1PortInfoTable 1 }

    Tn112sca1PortInfoEntry ::=
        SEQUENCE {
            tn112sca1PortInfoFunction INTEGER
        }

    tn112sca1PortInfoFunction OBJECT-TYPE
        SYNTAX         INTEGER {
                         network(1),
                         client(2)
                       }
        MAX-ACCESS     read-only
        STATUS         current
        DESCRIPTION    "Indicates the functional type of this 112SCA1 port."
        ::= { tn112sca1PortInfoEntry 1 }

--------------------------------------------------------------------------------
-- DWDM Common OTU4/ODU4 Line Port Info Table
--------------------------------------------------------------------------------
    tnDwdmCmnOtu4Odu4LinePortInfoTable OBJECT-TYPE
        SYNTAX         SEQUENCE OF TnDwdmCmnOtu4Odu4LinePortInfoEntry
        MAX-ACCESS     not-accessible
        STATUS         current
        DESCRIPTION    "Common attributes against DWDM line ports."
        ::= { tnOpticalPortInfo 105 }

    tnDwdmCmnOtu4Odu4LinePortInfoEntry OBJECT-TYPE
        SYNTAX         TnDwdmCmnOtu4Odu4LinePortInfoEntry
        MAX-ACCESS     not-accessible
        STATUS         current
        DESCRIPTION    ""
        INDEX { ifIndex }
        ::= { tnDwdmCmnOtu4Odu4LinePortInfoTable 1 }

    TnDwdmCmnOtu4Odu4LinePortInfoEntry ::=
        SEQUENCE {
            tnDwdmCmnLinePortOtu4IncomingTti             OCTET STRING,
            tnDwdmCmnLinePortOtu4TtiStatus               AluWdmTtiStatus,
            tnDwdmCmnLinePortOdu4IncomingTti             OCTET STRING,
            tnDwdmCmnLinePortOdu4TtiStatus               AluWdmTtiStatus,
            tnDwdmCmnLinePortOtu4PreFec                  Counter64,
            tnDwdmCmnLinePortOtu4PostFec                 Counter64,
            tnDwdmCmnLinePortOdu4DMInfoCurrentStatus     AluWdmDMInfoCurrentStatus,
            tnDwdmCmnLinePortOdu4DMInfoCurrentValue      Unsigned32
        }

    tnDwdmCmnLinePortOtu4IncomingTti OBJECT-TYPE
        SYNTAX         OCTET STRING
        MAX-ACCESS     read-only
        STATUS         current
        DESCRIPTION    "OTU4 incoming TTI."
        DEFVAL         { "" }
        ::= { tnDwdmCmnOtu4Odu4LinePortInfoEntry 1 }

    tnDwdmCmnLinePortOtu4TtiStatus OBJECT-TYPE
        SYNTAX         AluWdmTtiStatus
        MAX-ACCESS     read-only
        STATUS         current
        DESCRIPTION    "OTU4 TTI status."
        DEFVAL         { unspecified }
        ::= { tnDwdmCmnOtu4Odu4LinePortInfoEntry 2 }

    tnDwdmCmnLinePortOdu4IncomingTti OBJECT-TYPE
        SYNTAX         OCTET STRING
        MAX-ACCESS     read-only
        STATUS         current
        DESCRIPTION    "ODU4 incoming TTI."
        DEFVAL         { "" }
        ::= { tnDwdmCmnOtu4Odu4LinePortInfoEntry 3 }

    tnDwdmCmnLinePortOdu4TtiStatus OBJECT-TYPE
        SYNTAX         AluWdmTtiStatus
        MAX-ACCESS     read-only
        STATUS         current
        DESCRIPTION    "ODU4 TTI status."
        DEFVAL         { unspecified }
        ::= { tnDwdmCmnOtu4Odu4LinePortInfoEntry 4 }

    tnDwdmCmnLinePortOtu4PreFec OBJECT-TYPE
        SYNTAX         Counter64
        MAX-ACCESS     read-only
        STATUS         current
        DESCRIPTION    "Real time error bit rate of pre-FEC (Forward
                        Error Correction).

                        Current configurable range: 0 to 4000."
        ::= { tnDwdmCmnOtu4Odu4LinePortInfoEntry 5 }

    tnDwdmCmnLinePortOtu4PostFec OBJECT-TYPE
        SYNTAX         Counter64
        MAX-ACCESS     read-only
        STATUS         current
        DESCRIPTION    "Real time error bit rate of post-FEC (Forward
                        Error Correction).

                        Current configurable range: 0 to 4000."
        ::= { tnDwdmCmnOtu4Odu4LinePortInfoEntry 6 }

    tnDwdmCmnLinePortOdu4DMInfoCurrentStatus OBJECT-TYPE
        SYNTAX         AluWdmDMInfoCurrentStatus
        MAX-ACCESS     read-only
        STATUS         current
        DESCRIPTION    "Indicates whether this DM test is valid."
        DEFVAL         { invalid }
        ::= { tnDwdmCmnOtu4Odu4LinePortInfoEntry 7 }

    tnDwdmCmnLinePortOdu4DMInfoCurrentValue OBJECT-TYPE
        SYNTAX         Unsigned32
        MAX-ACCESS     read-only
        STATUS         current
        DESCRIPTION    "Reports the DM value in 10**(-7) seconds in the
                        current Interval."
        DEFVAL         { 0 }
        ::= { tnDwdmCmnOtu4Odu4LinePortInfoEntry 8 }

--------------------------------------------------------------------------------
-- DWDM Common OTU4/ODU4 Client Port Info Table
--------------------------------------------------------------------------------
    tnDwdmCmnOtu4Odu4ClientPortInfoTable OBJECT-TYPE
        SYNTAX         SEQUENCE OF TnDwdmCmnOtu4Odu4ClientPortInfoEntry
        MAX-ACCESS     not-accessible
        STATUS         current
        DESCRIPTION    "Common attributes against DWDM client ports."
        ::= { tnOpticalPortInfo 106 }

    tnDwdmCmnOtu4Odu4ClientPortInfoEntry OBJECT-TYPE
        SYNTAX         TnDwdmCmnOtu4Odu4ClientPortInfoEntry
        MAX-ACCESS     not-accessible
        STATUS         current
        DESCRIPTION    ""
        INDEX { ifIndex }
        ::= { tnDwdmCmnOtu4Odu4ClientPortInfoTable 1 }

    TnDwdmCmnOtu4Odu4ClientPortInfoEntry ::=
        SEQUENCE {
            tnDwdmCmnClientPortOtu4IncomingTti  OCTET STRING,
            tnDwdmCmnClientPortOtu4TtiStatus    AluWdmTtiStatus,
            tnDwdmCmnClientPortOdu4IncomingTti  OCTET STRING,
            tnDwdmCmnClientPortOdu4TtiStatus    AluWdmTtiStatus,
            tnDwdmCmnClientPortOtu4PreFec       Counter64,
            tnDwdmCmnClientPortOtu4PostFec      Counter64
        }

    tnDwdmCmnClientPortOtu4IncomingTti OBJECT-TYPE
        SYNTAX         OCTET STRING
        MAX-ACCESS     read-only
        STATUS         current
        DESCRIPTION    "OTU4 incoming TTI."
        DEFVAL         { "" }
        ::= { tnDwdmCmnOtu4Odu4ClientPortInfoEntry 1 }

    tnDwdmCmnClientPortOtu4TtiStatus OBJECT-TYPE
        SYNTAX         AluWdmTtiStatus
        MAX-ACCESS     read-only
        STATUS         current
        DESCRIPTION    "OTU4 TTI status."
        DEFVAL         { unspecified }
        ::= { tnDwdmCmnOtu4Odu4ClientPortInfoEntry 2 }

    tnDwdmCmnClientPortOdu4IncomingTti OBJECT-TYPE
        SYNTAX         OCTET STRING
        MAX-ACCESS     read-only
        STATUS         current
        DESCRIPTION    "ODU4 incoming TTI."
        DEFVAL         { "" }
        ::= { tnDwdmCmnOtu4Odu4ClientPortInfoEntry 3 }

    tnDwdmCmnClientPortOdu4TtiStatus OBJECT-TYPE
        SYNTAX         AluWdmTtiStatus
        MAX-ACCESS     read-only
        STATUS         current
        DESCRIPTION    "ODU4 TTI status."
        DEFVAL         { unspecified }
        ::= { tnDwdmCmnOtu4Odu4ClientPortInfoEntry 4 }

    tnDwdmCmnClientPortOtu4PreFec OBJECT-TYPE
        SYNTAX         Counter64
        MAX-ACCESS     read-only
        STATUS         current
        DESCRIPTION    "Real time error bit rate of pre-FEC (Forward
                        Error Correction).

                        Current configurable range: 0 to 4000."
        ::= { tnDwdmCmnOtu4Odu4ClientPortInfoEntry 5 }

    tnDwdmCmnClientPortOtu4PostFec OBJECT-TYPE
        SYNTAX         Counter64
        MAX-ACCESS     read-only
        STATUS         current
        DESCRIPTION    "Real time error bit rate of post-FEC (Forward
                        Error Correction).

                        Current configurable range: 0 to 4000."
        ::= { tnDwdmCmnOtu4Odu4ClientPortInfoEntry 6 }

--------------------------------------------------------------------------------
-- ALPFGT Optical Port Info Scalars
--------------------------------------------------------------------------------
    tnAlpfgtPortInfoAttributeTotal OBJECT-TYPE
        SYNTAX         Integer32
        MAX-ACCESS     read-only
        STATUS         current
        DESCRIPTION    ""
        ::= { tnOpticalPortInfo 107 }

--------------------------------------------------------------------------------
-- ALPFGT Optical Port Info Table
--------------------------------------------------------------------------------
    tnAlpfgtPortInfoTable OBJECT-TYPE
        SYNTAX         SEQUENCE OF TnAlpfgtPortInfoEntry
        MAX-ACCESS     not-accessible
        STATUS         current
        DESCRIPTION    "The ports on an ALPFGT optical card."
        ::= { tnOpticalPortInfo 108 }

    tnAlpfgtPortInfoEntry OBJECT-TYPE
        SYNTAX         TnAlpfgtPortInfoEntry
        MAX-ACCESS     not-accessible
        STATUS         current
        DESCRIPTION    ""
        INDEX { ifIndex }
        ::= { tnAlpfgtPortInfoTable 1 }

    TnAlpfgtPortInfoEntry ::=
        SEQUENCE {
            tnAlpfgtPortInfoFunction  INTEGER
        }

    tnAlpfgtPortInfoFunction OBJECT-TYPE
        SYNTAX         INTEGER {
                         line(1),
                         signal(2),
                         inv(3),
                         osc(4),
                         oscSfp(5)
                       }
        MAX-ACCESS     read-only
        STATUS         current
        DESCRIPTION    "Indicates the functional type of this ALPFGT port."
        ::= { tnAlpfgtPortInfoEntry 1 }

--------------------------------------------------------------------------------
-- OSCT Optical Port Info Scalars
--------------------------------------------------------------------------------
    tnOsctPortInfoAttributeTotal OBJECT-TYPE
        SYNTAX         Integer32
        MAX-ACCESS     read-only
        STATUS         current
        DESCRIPTION    ""
        ::= { tnOpticalPortInfo 109 }

--------------------------------------------------------------------------------
-- OSCT Optical Port Info Table
--------------------------------------------------------------------------------
    tnOsctPortInfoTable OBJECT-TYPE
        SYNTAX         SEQUENCE OF TnOsctPortInfoEntry
        MAX-ACCESS     not-accessible
        STATUS         current
        DESCRIPTION    "The ports on an OSCT optical card."
        ::= { tnOpticalPortInfo 110 }

    tnOsctPortInfoEntry OBJECT-TYPE
        SYNTAX         TnOsctPortInfoEntry
        MAX-ACCESS     not-accessible
        STATUS         current
        DESCRIPTION    ""
        INDEX { ifIndex }
        ::= { tnOsctPortInfoTable 1 }

    TnOsctPortInfoEntry ::=
        SEQUENCE {
            tnOsctPortInfoFunction     INTEGER
        }

    tnOsctPortInfoFunction OBJECT-TYPE
        SYNTAX         INTEGER {
                         signal(1),
                         line(2),
                         inv(3),
                         osc(4),
                         oscSfp(5)
                       }
        MAX-ACCESS     read-only
        STATUS         current
        DESCRIPTION    "Indicates the functional type of this OSCT port."
        ::= { tnOsctPortInfoEntry 1 }

--------------------------------------------------------------------------------
-- WTOCM Optical Port Info Scalars
--------------------------------------------------------------------------------
    tnWtocmPortInfoAttributeTotal OBJECT-TYPE
        SYNTAX         Integer32
        MAX-ACCESS     read-only
        STATUS         current
        DESCRIPTION    ""
        ::= { tnOpticalPortInfo 111 }

--------------------------------------------------------------------------------
-- WTOCM Optical Port Info Table
--------------------------------------------------------------------------------
    tnWtocmPortInfoTable OBJECT-TYPE
        SYNTAX         SEQUENCE OF TnWtocmPortInfoEntry
        MAX-ACCESS     not-accessible
        STATUS         current
        DESCRIPTION    "The ports on a WTOCM optical card."
        ::= { tnOpticalPortInfo 112 }

    tnWtocmPortInfoEntry OBJECT-TYPE
        SYNTAX         TnWtocmPortInfoEntry
        MAX-ACCESS     not-accessible
        STATUS         current
        DESCRIPTION    ""
        INDEX { ifIndex }
        ::= { tnWtocmPortInfoTable 1 }

    TnWtocmPortInfoEntry ::=
        SEQUENCE {
            tnWtocmPortInfoFunction            INTEGER,
            tnWtocmPortInfoPower               Integer32,
            tnWtocmPortInfoPowerMonitoredPort  Integer32
        }

    tnWtocmPortInfoFunction OBJECT-TYPE
        SYNTAX         INTEGER {
                         detect(1)
                       }
        MAX-ACCESS     read-only
        STATUS         current
        DESCRIPTION    "Indicates the functional type of this WTOCM port."
        ::= { tnWtocmPortInfoEntry 1 }

    tnWtocmPortInfoPower OBJECT-TYPE
        SYNTAX         Integer32
        UNITS          "mBm"
        MAX-ACCESS     read-only
        STATUS         current
        DESCRIPTION    "The total power into the WTOCM IN port."
        DEFVAL         { -9900 }
        ::= { tnWtocmPortInfoEntry 2 }

    tnWtocmPortInfoPowerMonitoredPort OBJECT-TYPE
        SYNTAX         Integer32
        UNITS          "mBm"
        MAX-ACCESS     read-only
        STATUS         current
        DESCRIPTION    "The total power out of associated monitored port."
        DEFVAL         { -9900 }
        ::= { tnWtocmPortInfoEntry 3 }

--------------------------------------------------------------------------------
-- WR2-88 Optical Port Info Scalars
--------------------------------------------------------------------------------
    tnWr2c88PortInfoAttributeTotal OBJECT-TYPE
        SYNTAX         Integer32
        MAX-ACCESS     read-only
        STATUS         current
        DESCRIPTION    ""
        ::= { tnOpticalPortInfo 113 }

--------------------------------------------------------------------------------
-- WR2-88 Optical Port Info Table
--------------------------------------------------------------------------------
    tnWr2c88PortInfoTable OBJECT-TYPE
        SYNTAX         SEQUENCE OF TnWr2c88PortInfoEntry
        MAX-ACCESS     not-accessible
        STATUS         current
        DESCRIPTION    "The ports on a WR2-88 optical card."
        ::= { tnOpticalPortInfo 114 }

    tnWr2c88PortInfoEntry OBJECT-TYPE
        SYNTAX         TnWr2c88PortInfoEntry
        MAX-ACCESS     not-accessible
        STATUS         current
        DESCRIPTION    ""
        INDEX { ifIndex }
        ::= { tnWr2c88PortInfoTable 1 }

    TnWr2c88PortInfoEntry ::=
        SEQUENCE {
            tnWr2c88PortInfoFunction            INTEGER,
            tnWr2c88PortRelativeAttenuationMin  Unsigned32,
            tnWr2c88PortAverageAttenuationOut   Unsigned32
        }

    tnWr2c88PortInfoFunction OBJECT-TYPE
        SYNTAX         INTEGER {
                         signal(1),
                         thru(2),
                         dropOut(3),
                         addIn(4),
                         inv(5)
                       }
        MAX-ACCESS     read-only
        STATUS         current
        DESCRIPTION    "Indicates the functional type of this WR2-88 port."
        ::= { tnWr2c88PortInfoEntry 1 }

    tnWr2c88PortRelativeAttenuationMin OBJECT-TYPE
        SYNTAX         Unsigned32
        UNITS          "mB"
        MAX-ACCESS     read-only
        STATUS         current
        DESCRIPTION    "The following description applies to the Thru
                        port of the WR2-88 card:

                        The minimum attenuation on the blocker across
                        all of the channels."
        DEFVAL         { 0 }
        ::= { tnWr2c88PortInfoEntry 2 }

    tnWr2c88PortAverageAttenuationOut OBJECT-TYPE
        SYNTAX         Unsigned32
        UNITS          "mB"
        MAX-ACCESS     read-only
        STATUS         current
        DESCRIPTION    "The following description applies to the Thru
                        port of the WR2-88 card:

                        The average attenuation on the blocker across
                        all of the channels."
        ::= { tnWr2c88PortInfoEntry 3 }

--------------------------------------------------------------------------------
-- AM2017B Optical Port Info Scalars
--------------------------------------------------------------------------------
    tnAm2017bPortInfoAttributeTotal OBJECT-TYPE
        SYNTAX         Integer32
        MAX-ACCESS     read-only
        STATUS         current
        DESCRIPTION    ""
        ::= { tnOpticalPortInfo 115 }

--------------------------------------------------------------------------------
-- AM2017B Optical Port Info Table
--------------------------------------------------------------------------------
    tnAm2017bPortInfoTable OBJECT-TYPE
        SYNTAX         SEQUENCE OF TnAm2017bPortInfoEntry
        MAX-ACCESS     not-accessible
        STATUS         current
        DESCRIPTION    "The ports on an AM2017B optical card."
        ::= { tnOpticalPortInfo 116 }

    tnAm2017bPortInfoEntry OBJECT-TYPE
        SYNTAX         TnAm2017bPortInfoEntry
        MAX-ACCESS     not-accessible
        STATUS         current
        DESCRIPTION    ""
        INDEX { ifIndex }
        ::= { tnAm2017bPortInfoTable 1 }

    TnAm2017bPortInfoEntry ::=
        SEQUENCE {
            tnAm2017bPortInfoFunction INTEGER
        }

    tnAm2017bPortInfoFunction OBJECT-TYPE
        SYNTAX         INTEGER {
                         line(1),
                         signal(2),
                         dcm(3),
                         inv(4),
                         osc(5)
                       }
        MAX-ACCESS     read-only
        STATUS         current
        DESCRIPTION    "Indicates the functional type of this AM2017B port."
        ::= { tnAm2017bPortInfoEntry 1 }

--------------------------------------------------------------------------------
-- AM2325B Optical Port Info Scalars
--------------------------------------------------------------------------------
    tnAm2325bPortInfoAttributeTotal OBJECT-TYPE
        SYNTAX         Integer32
        MAX-ACCESS     read-only
        STATUS         current
        DESCRIPTION    ""
        ::= { tnOpticalPortInfo 117 }

--------------------------------------------------------------------------------
-- AM2325B Optical Port Info Table
--------------------------------------------------------------------------------
    tnAm2325bPortInfoTable OBJECT-TYPE
        SYNTAX         SEQUENCE OF TnAm2325bPortInfoEntry
        MAX-ACCESS     not-accessible
        STATUS         current
        DESCRIPTION    "The ports on an AM2325B optical card."
        ::= { tnOpticalPortInfo 118 }

    tnAm2325bPortInfoEntry OBJECT-TYPE
        SYNTAX         TnAm2325bPortInfoEntry
        MAX-ACCESS     not-accessible
        STATUS         current
        DESCRIPTION    ""
        INDEX { ifIndex }
        ::= { tnAm2325bPortInfoTable 1 }

    TnAm2325bPortInfoEntry ::=
        SEQUENCE {
            tnAm2325bPortInfoFunction INTEGER
        }

    tnAm2325bPortInfoFunction OBJECT-TYPE
        SYNTAX         INTEGER {
                         line(1),
                         signal(2),
                         dcm(3),
                         inv(4),
                         osc(5)
                       }
        MAX-ACCESS     read-only
        STATUS         current
        DESCRIPTION    "Indicates the functional type of this AM2325B port."
        ::= { tnAm2325bPortInfoEntry 1 }

--------------------------------------------------------------------------------
-- 1DPP21 Optical Port Info Scalars
--------------------------------------------------------------------------------
    tn1dpp21PortInfoAttributeTotal OBJECT-TYPE
        SYNTAX         Integer32
        MAX-ACCESS     read-only
        STATUS         current
        DESCRIPTION    ""
        ::= { tnOpticalPortInfo 119 }

--------------------------------------------------------------------------------
-- 1DPP21 Optical Port Info Table
--------------------------------------------------------------------------------
    tn1dpp21PortInfoTable OBJECT-TYPE
        SYNTAX         SEQUENCE OF Tn1dpp21PortInfoEntry
        MAX-ACCESS     not-accessible
        STATUS         current
        DESCRIPTION    "The ports on a 1DPP21 optical card."
        ::= { tnOpticalPortInfo 120 }

    tn1dpp21PortInfoEntry OBJECT-TYPE
        SYNTAX         Tn1dpp21PortInfoEntry
        MAX-ACCESS     not-accessible
        STATUS         current
        DESCRIPTION    ""
        INDEX { ifIndex }
        ::= { tn1dpp21PortInfoTable 1 }

    Tn1dpp21PortInfoEntry ::=
        SEQUENCE {
            tn1dpp21PortInfoFunction                 INTEGER,
            tn1dpp21PortClockSourceIncomingQLStatus  Unsigned32,
            tn1dpp21PortClockSourceIncomingQL        Unsigned32
        }

    tn1dpp21PortInfoFunction OBJECT-TYPE
        SYNTAX         INTEGER {
                         network(1),
                         client(2)
                       }
        MAX-ACCESS     read-only
        STATUS         current
        DESCRIPTION    "Indicates the functional type of this 1DPP21 port."
        ::= { tn1dpp21PortInfoEntry 1 }

    tn1dpp21PortClockSourceIncomingQLStatus OBJECT-TYPE
        SYNTAX         Unsigned32
        MAX-ACCESS     read-only
        STATUS         current
        DESCRIPTION    "This object indicates the current status of
                        incoming QL on that port.
                          0: Valid
                          1: Invalid
                          2: Not Supported
                          3: Not Applicable

                        It's only applicable to the timing port with
                        SSM capabilities."
        DEFVAL         { 3 }
        ::= { tn1dpp21PortInfoEntry 2 }

    tn1dpp21PortClockSourceIncomingQL OBJECT-TYPE
        SYNTAX         Unsigned32
        MAX-ACCESS     read-only
        STATUS         current
        DESCRIPTION    "This object indicates the current value of
                        incoming QL on that port.
                          0:  Quality Unknown
                          1:  PRC
                          2:  SSU_A
                          3:  SSU_B
                          4:  EEC Option 1
                          5:  DNU
                          11: PRS
                          12: STU
                          13: ST2
                          14: TNC
                          15: ST3E
                          16: ST3
                          17: SMC
                          18: ST4
                          19: DUS
                          20: PNO
                          30: Unstable
                          31: Not applicable

                        It's only applicable to the timing port
                        with SSM capabilities."
        ::= { tn1dpp21PortInfoEntry 3 }

--------------------------------------------------------------------------------
-- E1 T1 Port Info Table
--------------------------------------------------------------------------------
--    obsolete
--    tnE1T1PortInfoTable OBJECT-TYPE ::= { tnOpticalPortInfo 121 }

--------------------------------------------------------------------------------
-- MVAC Optical Port Info Scalars
--------------------------------------------------------------------------------
    tnMvacPortInfoAttributeTotal OBJECT-TYPE
        SYNTAX         Integer32
        MAX-ACCESS     read-only
        STATUS         current
        DESCRIPTION    ""
        ::= { tnOpticalPortInfo 122 }

--------------------------------------------------------------------------------
-- MVAC Optical Port Info Table
--------------------------------------------------------------------------------
    tnMvacPortInfoTable OBJECT-TYPE
        SYNTAX         SEQUENCE OF TnMvacPortInfoEntry
        MAX-ACCESS     not-accessible
        STATUS         current
        DESCRIPTION    "The ports on a MVAC optical card."
        ::= { tnOpticalPortInfo 123 }

    tnMvacPortInfoEntry OBJECT-TYPE
        SYNTAX         TnMvacPortInfoEntry
        MAX-ACCESS     not-accessible
        STATUS         current
        DESCRIPTION    ""
        INDEX { ifIndex }
        ::= { tnMvacPortInfoTable 1 }

    TnMvacPortInfoEntry ::=
        SEQUENCE {
            tnMvacPortInfoFunction INTEGER
        }

    tnMvacPortInfoFunction OBJECT-TYPE
        SYNTAX         INTEGER {
                         general(1)
                       }
        MAX-ACCESS     read-only
        STATUS         current
        DESCRIPTION    "Indicates the functional type of this MVAC port."
        ::= { tnMvacPortInfoEntry 1 }

--------------------------------------------------------------------------------
-- 43SCX4 Optical Port Info Scalars
--------------------------------------------------------------------------------
    tn43scx4PortInfoAttributeTotal OBJECT-TYPE
        SYNTAX         Integer32
        MAX-ACCESS     read-only
        STATUS         current
        DESCRIPTION    ""
        ::= { tnOpticalPortInfo 126 }

--------------------------------------------------------------------------------
-- 43SCX4 Optical Port Info Table
--------------------------------------------------------------------------------
    tn43scx4PortInfoTable OBJECT-TYPE
        SYNTAX         SEQUENCE OF Tn43scx4PortInfoEntry
        MAX-ACCESS     not-accessible
        STATUS         current
        DESCRIPTION    "The ports on a 43SCX4 optical card."
        ::= { tnOpticalPortInfo 127 }

    tn43scx4PortInfoEntry OBJECT-TYPE
        SYNTAX         Tn43scx4PortInfoEntry
        MAX-ACCESS     not-accessible
        STATUS         current
        DESCRIPTION    ""
        INDEX { ifIndex }
        ::= { tn43scx4PortInfoTable 1 }

    Tn43scx4PortInfoEntry ::=
        SEQUENCE {
            tn43scx4PortInfoFunction INTEGER
        }

    tn43scx4PortInfoFunction OBJECT-TYPE
        SYNTAX         INTEGER {
                         network(1),
                         client(2)
                       }
        MAX-ACCESS     read-only
        STATUS         current
        DESCRIPTION    "Indicates the functional type of this 43SCX4 port."
        ::= { tn43scx4PortInfoEntry 1 }

--------------------------------------------------------------------------------
-- RA2P Optical Port Info Scalars
--------------------------------------------------------------------------------
    tnRa2pPortInfoAttributeTotal OBJECT-TYPE
        SYNTAX         Integer32
        MAX-ACCESS     read-only
        STATUS         current
        DESCRIPTION    ""
        ::= { tnOpticalPortInfo 128 }

--------------------------------------------------------------------------------
-- RA2P Optical Port Info Table
--------------------------------------------------------------------------------
    tnRa2pPortInfoTable OBJECT-TYPE
        SYNTAX         SEQUENCE OF TnRa2pPortInfoEntry
        MAX-ACCESS     not-accessible
        STATUS         current
        DESCRIPTION    "The ports on a RA2P optical card."
        ::= { tnOpticalPortInfo 129 }

    tnRa2pPortInfoEntry OBJECT-TYPE
        SYNTAX         TnRa2pPortInfoEntry
        MAX-ACCESS     not-accessible
        STATUS         current
        DESCRIPTION    ""
        INDEX { ifIndex }
        ::= { tnRa2pPortInfoTable 1 }

    TnRa2pPortInfoEntry ::=
        SEQUENCE {
            tnRa2pPortInfoFunction INTEGER
        }

    tnRa2pPortInfoFunction OBJECT-TYPE
        SYNTAX         INTEGER {
                         lineIn(1),
                         lineOut(2)
                       }
        MAX-ACCESS     read-only
        STATUS         current
        DESCRIPTION    "Indicates the functional type of this RA2P port."
        ::= { tnRa2pPortInfoEntry 1 }

--------------------------------------------------------------------------------
-- AM2318A Optical Port Info Scalars
--------------------------------------------------------------------------------
    tnAm2318aPortInfoAttributeTotal OBJECT-TYPE
        SYNTAX         Integer32
        MAX-ACCESS     read-only
        STATUS         current
        DESCRIPTION    ""
        ::= { tnOpticalPortInfo 130 }

--------------------------------------------------------------------------------
-- AM2318A Optical Port Info Table
--------------------------------------------------------------------------------
    tnAm2318aPortInfoTable OBJECT-TYPE
        SYNTAX         SEQUENCE OF TnAm2318aPortInfoEntry
        MAX-ACCESS     not-accessible
        STATUS         current
        DESCRIPTION    "The ports on an AM2318A optical card."
        ::= { tnOpticalPortInfo 131 }

    tnAm2318aPortInfoEntry OBJECT-TYPE
        SYNTAX         TnAm2318aPortInfoEntry
        MAX-ACCESS     not-accessible
        STATUS         current
        DESCRIPTION    ""
        INDEX { ifIndex }
        ::= { tnAm2318aPortInfoTable 1 }

    TnAm2318aPortInfoEntry ::=
        SEQUENCE {
            tnAm2318aPortInfoFunction INTEGER
        }

    tnAm2318aPortInfoFunction OBJECT-TYPE
        SYNTAX         INTEGER {
                         lineIn(1),
                         inv(2),
                         osc(3),
                         lineOut(4),
                         oscSfp(5),
                         det(6)
                       }
        MAX-ACCESS     read-only
        STATUS         current
        DESCRIPTION    "Indicates the functional type of this AM2318A port."
        ::= { tnAm2318aPortInfoEntry 1 }

--------------------------------------------------------------------------------
-- AM2125A Optical Port Info Scalars
--------------------------------------------------------------------------------
    tnAm2125aPortInfoAttributeTotal OBJECT-TYPE
        SYNTAX         Integer32
        MAX-ACCESS     read-only
        STATUS         current
        DESCRIPTION    ""
        ::= { tnOpticalPortInfo 132 }

--------------------------------------------------------------------------------
-- AM2125A Optical Port Info Table
--------------------------------------------------------------------------------
    tnAm2125aPortInfoTable OBJECT-TYPE
        SYNTAX         SEQUENCE OF TnAm2125aPortInfoEntry
        MAX-ACCESS     not-accessible
        STATUS         current
        DESCRIPTION    "The ports on an AM2125A optical card."
        ::= { tnOpticalPortInfo 133 }

    tnAm2125aPortInfoEntry OBJECT-TYPE
        SYNTAX         TnAm2125aPortInfoEntry
        MAX-ACCESS     not-accessible
        STATUS         current
        DESCRIPTION    ""
        INDEX { ifIndex }
        ::= { tnAm2125aPortInfoTable 1 }

    TnAm2125aPortInfoEntry ::=
        SEQUENCE {
            tnAm2125aPortInfoFunction INTEGER
        }

    tnAm2125aPortInfoFunction OBJECT-TYPE
        SYNTAX         INTEGER {
                         lineIn(1),
                         inv(2),
                         dcm(3),
                         lineOut(4),
                         oscSfp(5),
                         det(6),
                         osc(7)
                       }
        MAX-ACCESS     read-only
        STATUS         current
        DESCRIPTION    "Indicates the functional type of this AM2125A port."
        ::= { tnAm2125aPortInfoEntry 1 }

--------------------------------------------------------------------------------
-- WR8-88A Optical Port Info Scalars
--------------------------------------------------------------------------------
    tnWr8c88aPortInfoAttributeTotal OBJECT-TYPE
        SYNTAX         Integer32
        MAX-ACCESS     read-only
        STATUS         current
        DESCRIPTION    ""
        ::= { tnOpticalPortInfo 134 }

--------------------------------------------------------------------------------
-- WR8-88A Optical Port Info Table
--------------------------------------------------------------------------------
    tnWr8c88aPortInfoTable OBJECT-TYPE
        SYNTAX         SEQUENCE OF TnWr8c88aPortInfoEntry
        MAX-ACCESS     not-accessible
        STATUS         current
        DESCRIPTION    "The ports on a WR8-88A optical card."
        ::= { tnOpticalPortInfo 135 }

    tnWr8c88aPortInfoEntry OBJECT-TYPE
        SYNTAX         TnWr8c88aPortInfoEntry
        MAX-ACCESS     not-accessible
        STATUS         current
        DESCRIPTION    ""
        INDEX { ifIndex }
        ::= { tnWr8c88aPortInfoTable 1 }

    TnWr8c88aPortInfoEntry ::=
        SEQUENCE {
            tnWr8c88aPortInfoFunction     INTEGER
        }

    tnWr8c88aPortInfoFunction OBJECT-TYPE
        SYNTAX         INTEGER {
                         signal(1),
                         thru(2),
                         dropOut(3),
                         addIn(4),
--                       obsolete
--                         test(5),
                         meshOut(5),
                         inv(6)
                       }
        MAX-ACCESS     read-only
        STATUS         current
        DESCRIPTION    "Indicates the functional type of this WR8-88A port."
        ::= { tnWr8c88aPortInfoEntry 1 }

--------------------------------------------------------------------------------
-- 11DPE12E Optical Port Info Scalars
--------------------------------------------------------------------------------
    tn11dpe12ePortInfoAttributeTotal OBJECT-TYPE
        SYNTAX         Integer32
        MAX-ACCESS     read-only
        STATUS         current
        DESCRIPTION    ""
        ::= { tnOpticalPortInfo 136 }

--------------------------------------------------------------------------------
-- 11DPE12E Optical Port Info Table
--------------------------------------------------------------------------------
    tn11dpe12ePortInfoTable OBJECT-TYPE
        SYNTAX         SEQUENCE OF Tn11dpe12ePortInfoEntry
        MAX-ACCESS     not-accessible
        STATUS         current
        DESCRIPTION    "The ports on a 11DPE12E optical card."
        ::= { tnOpticalPortInfo 137 }

    tn11dpe12ePortInfoEntry OBJECT-TYPE
        SYNTAX         Tn11dpe12ePortInfoEntry
        MAX-ACCESS     not-accessible
        STATUS         current
        DESCRIPTION    ""
        INDEX { ifIndex }
        ::= { tn11dpe12ePortInfoTable 1 }

    Tn11dpe12ePortInfoEntry ::=
        SEQUENCE {
            tn11dpe12ePortInfoFunction           INTEGER,
            tn11dpe12ePortTotalVTS               Unsigned32,
            tn11dpe12ePortIngAvailableBandwidth  Unsigned32,
            tn11dpe12ePortEgrAvailableBandwidth  Unsigned32
        }

    tn11dpe12ePortInfoFunction OBJECT-TYPE
        SYNTAX         INTEGER {
                         network(1),
                         client(2),
                         evoa(3),
                         backplane(4)
                       }
        MAX-ACCESS     read-only
        STATUS         current
        DESCRIPTION    "Indicates the functional type of this 11DPE12E port."
        ::= { tn11dpe12ePortInfoEntry 1 }

    tn11dpe12ePortTotalVTS OBJECT-TYPE
        SYNTAX         Unsigned32
        MAX-ACCESS     read-only
        STATUS         current
        DESCRIPTION    "Total VTS for 11DPE12E ports."
        DEFVAL         { 0 }
        ::= { tn11dpe12ePortInfoEntry 2 }

    tn11dpe12ePortIngAvailableBandwidth OBJECT-TYPE
        SYNTAX         Unsigned32
        MAX-ACCESS     read-only
        STATUS         current
        DESCRIPTION    "Available bandwidth for ingress 11DPE12E ports."
        ::= { tn11dpe12ePortInfoEntry 3 }

    tn11dpe12ePortEgrAvailableBandwidth OBJECT-TYPE
        SYNTAX         Unsigned32
        MAX-ACCESS     read-only
        STATUS         current
        DESCRIPTION    "Available bandwidth for egress 11DPE12E ports."
        ::= { tn11dpe12ePortInfoEntry 4 }

--------------------------------------------------------------------------------
-- 112SX10L Optical Port Info Scalars
--------------------------------------------------------------------------------
    tn112sx10lPortInfoAttributeTotal OBJECT-TYPE
        SYNTAX         Integer32
        MAX-ACCESS     read-only
        STATUS         current
        DESCRIPTION    ""
        ::= { tnOpticalPortInfo 138 }

--------------------------------------------------------------------------------
-- 112SX10L Optical Port Info Table
--------------------------------------------------------------------------------
    tn112sx10lPortInfoTable OBJECT-TYPE
        SYNTAX         SEQUENCE OF Tn112sx10lPortInfoEntry
        MAX-ACCESS     not-accessible
        STATUS         current
        DESCRIPTION    "The ports on a 112SX10L optical card."
        ::= { tnOpticalPortInfo 139 }

    tn112sx10lPortInfoEntry OBJECT-TYPE
        SYNTAX         Tn112sx10lPortInfoEntry
        MAX-ACCESS     not-accessible
        STATUS         current
        DESCRIPTION    ""
        INDEX { ifIndex }
        ::= { tn112sx10lPortInfoTable 1 }

    Tn112sx10lPortInfoEntry ::=
        SEQUENCE {
            tn112sx10lPortInfoFunction INTEGER
        }

    tn112sx10lPortInfoFunction OBJECT-TYPE
        SYNTAX         INTEGER {
                         network(1),
                         client(2)
                       }
        MAX-ACCESS     read-only
        STATUS         current
        DESCRIPTION    "Indicates the functional type of this 112SX10L port."
        ::= { tn112sx10lPortInfoEntry 1 }

--------------------------------------------------------------------------------
-- 112SA1L Optical Port Info Scalars
--------------------------------------------------------------------------------
    tn112sa1lPortInfoAttributeTotal OBJECT-TYPE
        SYNTAX         Integer32
        MAX-ACCESS     read-only
        STATUS         current
        DESCRIPTION    ""
        ::= { tnOpticalPortInfo 140 }

--------------------------------------------------------------------------------
-- 112SA1L Optical Port Info Table
--------------------------------------------------------------------------------
    tn112sa1lPortInfoTable OBJECT-TYPE
        SYNTAX         SEQUENCE OF Tn112sa1lPortInfoEntry
        MAX-ACCESS     not-accessible
        STATUS         current
        DESCRIPTION    "The ports on a 112SA1L optical card."
        ::= { tnOpticalPortInfo 141 }

    tn112sa1lPortInfoEntry OBJECT-TYPE
        SYNTAX         Tn112sa1lPortInfoEntry
        MAX-ACCESS     not-accessible
        STATUS         current
        DESCRIPTION    ""
        INDEX { ifIndex }
        ::= { tn112sa1lPortInfoTable 1 }

    Tn112sa1lPortInfoEntry ::=
        SEQUENCE {
            tn112sa1lPortInfoFunction INTEGER
        }

    tn112sa1lPortInfoFunction OBJECT-TYPE
        SYNTAX         INTEGER {
                         network(1),
                         client(2)
                       }
        MAX-ACCESS     read-only
        STATUS         current
        DESCRIPTION    "Indicates the functional type of this 112SA1L port."
        ::= { tn112sa1lPortInfoEntry 1 }

--------------------------------------------------------------------------------
-- 11DPM12 Optical Port Info Scalars
--------------------------------------------------------------------------------
    tn11dpm12PortInfoAttributeTotal OBJECT-TYPE
        SYNTAX         Integer32
        MAX-ACCESS     read-only
        STATUS         current
        DESCRIPTION    ""
        ::= { tnOpticalPortInfo 142 }

--------------------------------------------------------------------------------
-- 11DPGM12 Optical Port Info Table
--------------------------------------------------------------------------------
    tn11dpm12PortInfoTable OBJECT-TYPE
        SYNTAX         SEQUENCE OF Tn11dpm12PortInfoEntry
        MAX-ACCESS     not-accessible
        STATUS         current
        DESCRIPTION    "The ports on a 11DPM12 optical card."
        ::= { tnOpticalPortInfo 143 }

    tn11dpm12PortInfoEntry OBJECT-TYPE
        SYNTAX         Tn11dpm12PortInfoEntry
        MAX-ACCESS     not-accessible
        STATUS         current
        DESCRIPTION    ""
        INDEX { ifIndex }
        ::= { tn11dpm12PortInfoTable 1 }

    Tn11dpm12PortInfoEntry ::=
        SEQUENCE {
            tn11dpm12PortInfoFunction     INTEGER
        }

    tn11dpm12PortInfoFunction OBJECT-TYPE
        SYNTAX         INTEGER {
                         network(1),
                         client(2),
                         evoa(3)
                       }
        MAX-ACCESS     read-only
        STATUS         current
        DESCRIPTION    "Indicates the functional type of this 11DPM12 port."
        ::= { tn11dpm12PortInfoEntry 1 }

--------------------------------------------------------------------------------
-- Raman Optical Port Info Table
--------------------------------------------------------------------------------
    tnRamanPortInfoTable OBJECT-TYPE
        SYNTAX         SEQUENCE OF TnRamanPortInfoEntry
        MAX-ACCESS     not-accessible
        STATUS         current
        DESCRIPTION    "The ports on an Raman optical card."
        ::= { tnOpticalPortInfo 144 }

    tnRamanPortInfoEntry OBJECT-TYPE
        SYNTAX         TnRamanPortInfoEntry
        MAX-ACCESS     not-accessible
        STATUS         current
        DESCRIPTION    ""
        INDEX { ifIndex }
        ::= { tnRamanPortInfoTable 1 }

    TnRamanPortInfoEntry ::=
        SEQUENCE {
            tnRamanPortTotalPowerIn       Integer32,
            tnRamanPortTotalPowerOut      Integer32,
            tnRamanPortSignalPowerOut     Integer32,
            tnRamanPortAsePowerOut        Integer32,
            tnRamanPortGain               Integer32,
            tnRamanPortPump1Power         Integer32,
            tnRamanPortPump2Power         Integer32,
            tnRamanPortPump3Power         Integer32,
            tnRamanPortPump4Power         Integer32
         }

    tnRamanPortTotalPowerIn OBJECT-TYPE
        SYNTAX         Integer32
        UNITS          "mBm"
        MAX-ACCESS     read-only
        STATUS         current
        DESCRIPTION    "The total power into the Raman LINEIN port, with
                        -9900 means no measured power.

                        Current range:
                        A4PSWG     :  -9900, -4000 to 2500
                        Other Cards:  -9900, -3600 to 1600."
        ::= { tnRamanPortInfoEntry 1 }

    tnRamanPortTotalPowerOut OBJECT-TYPE
        SYNTAX         Integer32
        UNITS          "mBm"
        MAX-ACCESS     read-only
        STATUS         current
        DESCRIPTION    "The total power out of the Raman LINEOUT port,
                        with -9900 means no measured power.

                        Current range:
                        A4PSWG     : -9900, -4300 to 2500
                        Other Cards: -9900, -3800 to 1800."
        ::= { tnRamanPortInfoEntry 2 }

    tnRamanPortSignalPowerOut OBJECT-TYPE
        SYNTAX         Integer32
        UNITS          "mBm"
        MAX-ACCESS     read-only
        STATUS         current
        DESCRIPTION    "The signal power out of the Raman LINEOUT port,
                        with -9900 means no measured power.

                        Current range:
                        A4PSWG     : -9900, -4300 to 2500
                        Other Cards: -9900, -3800 to 1800."
        ::= { tnRamanPortInfoEntry 3 }

    tnRamanPortAsePowerOut OBJECT-TYPE
        SYNTAX         Integer32
        UNITS          "mBm"
        MAX-ACCESS     read-only
        STATUS         current
        DESCRIPTION    "The ASE noise power out of the Raman LINEOUT
                        port, with -9900 means no measured power.

                        Current range: -9900, -3000 to 1000."
        ::= { tnRamanPortInfoEntry 4 }

    tnRamanPortGain OBJECT-TYPE
        SYNTAX         Integer32
        UNITS          "mB"
        MAX-ACCESS     read-only
        STATUS         current
        DESCRIPTION    "The current operating gain.

                        Current range: 0 to 2500."
        ::= { tnRamanPortInfoEntry 5 }

    tnRamanPortPump1Power OBJECT-TYPE
        SYNTAX         Integer32
        UNITS          "mW"
        MAX-ACCESS     read-only
        STATUS         current
        DESCRIPTION    "The pump 1 power for LINEIN.

                        Current range: 0 to 400."
        DEFVAL         { 0 }
        ::= { tnRamanPortInfoEntry 6 }

    tnRamanPortPump2Power OBJECT-TYPE
        SYNTAX         Integer32
        UNITS          "mW"
        MAX-ACCESS     read-only
        STATUS         current
        DESCRIPTION    "The pump 2 power for LINEIN.

                        Current range: 0 to 400."
        DEFVAL         { 0 }
        ::= { tnRamanPortInfoEntry 7 }

    tnRamanPortPump3Power OBJECT-TYPE
        SYNTAX         Integer32
        UNITS          "mW"
        MAX-ACCESS     read-only
        STATUS         current
        DESCRIPTION    "The pump 3 power for LINEIN.

                        Current range: 0 to 400."
        ::= { tnRamanPortInfoEntry 8 }

    tnRamanPortPump4Power OBJECT-TYPE
        SYNTAX         Integer32
        UNITS          "mW"
        MAX-ACCESS     read-only
        STATUS         current
        DESCRIPTION    "The pump 4 power for LINEIN.

                        Current range: 0 to 400."
        ::= { tnRamanPortInfoEntry 9 }



--------------------------------------------------------------------------------
-- MESH4 Optical Port Info Scalars
--------------------------------------------------------------------------------
    tnMesh4PortInfoAttributeTotal OBJECT-TYPE
        SYNTAX         Integer32
        MAX-ACCESS     read-only
        STATUS         current
        DESCRIPTION    ""
        ::= { tnOpticalPortInfo 145 }

--------------------------------------------------------------------------------
-- MESH4 Optical Port Info Table
--------------------------------------------------------------------------------
    tnMesh4PortInfoTable OBJECT-TYPE
        SYNTAX         SEQUENCE OF TnMesh4PortInfoEntry
        MAX-ACCESS     not-accessible
        STATUS         current
        DESCRIPTION    "The ports on a MESH4 card."
        ::= { tnOpticalPortInfo 146 }

    tnMesh4PortInfoEntry OBJECT-TYPE
        SYNTAX         TnMesh4PortInfoEntry
        MAX-ACCESS     not-accessible
        STATUS         current
        DESCRIPTION    ""
        INDEX { ifIndex }
        ::= { tnMesh4PortInfoTable 1 }

    TnMesh4PortInfoEntry ::=
        SEQUENCE {
            tnMesh4PortInfoFunction   INTEGER
         }

    tnMesh4PortInfoFunction OBJECT-TYPE
        SYNTAX         INTEGER {
                         sigIn(1),
                         sigOut(2)
                       }
        MAX-ACCESS     read-only
        STATUS         current
        DESCRIPTION    "Indicates the functional type of this MESH4 port."
        ::= { tnMesh4PortInfoEntry 1 }

--------------------------------------------------------------------------------
-- Tandem Connection Monitoring (TCM) Optical Port Info Scalars
--------------------------------------------------------------------------------
--    obsolete
--    tnTcmPortInfoAttributeTotal OBJECT-TYPE ::= { tnOpticalPortInfo 147 }

--------------------------------------------------------------------------------
-- Tandem Connection Monitoring (TCM) Optical Port Info Table
--------------------------------------------------------------------------------
--    obsolete
--    tnTcmPortInfoTable OBJECT-TYPE OBJECT-TYPE ::= { tnOpticalPortInfo 148 }

--------------------------------------------------------------------------------
-- 43SCA1 Optical Port Info Scalars
--------------------------------------------------------------------------------
    tn43sca1PortInfoAttributeTotal OBJECT-TYPE
        SYNTAX         Integer32
        MAX-ACCESS     read-only
        STATUS         current
        DESCRIPTION    ""
        ::= { tnOpticalPortInfo 149 }

--------------------------------------------------------------------------------
-- 43SCA1 Optical Port Info Table
--------------------------------------------------------------------------------
    tn43sca1PortInfoTable OBJECT-TYPE
        SYNTAX         SEQUENCE OF Tn43sca1PortInfoEntry
        MAX-ACCESS     not-accessible
        STATUS         current
        DESCRIPTION    "The ports on a 43SCA1 optical card."
        ::= { tnOpticalPortInfo 150 }

    tn43sca1PortInfoEntry OBJECT-TYPE
        SYNTAX         Tn43sca1PortInfoEntry
        MAX-ACCESS     not-accessible
        STATUS         current
        DESCRIPTION    ""
        INDEX { ifIndex }
        ::= { tn43sca1PortInfoTable 1 }

    Tn43sca1PortInfoEntry ::=
        SEQUENCE {
            tn43sca1PortInfoFunction INTEGER
        }

    tn43sca1PortInfoFunction OBJECT-TYPE
        SYNTAX         INTEGER {
                         network(1),
                         client(2)
                       }
        MAX-ACCESS     read-only
        STATUS         current
        DESCRIPTION    "Indicates the functional type of this 43SCA1 port."
        ::= { tn43sca1PortInfoEntry 1 }

--------------------------------------------------------------------------------
-- 43SCX4L Optical Port Info Scalars
--------------------------------------------------------------------------------
    tn43scx4lPortInfoAttributeTotal OBJECT-TYPE
        SYNTAX         Integer32
        MAX-ACCESS     read-only
        STATUS         current
        DESCRIPTION    ""
        ::= { tnOpticalPortInfo 151 }

--------------------------------------------------------------------------------
-- 43SCX4L Optical Port Info Table
--------------------------------------------------------------------------------
    tn43scx4lPortInfoTable OBJECT-TYPE
        SYNTAX         SEQUENCE OF Tn43scx4lPortInfoEntry
        MAX-ACCESS     not-accessible
        STATUS         current
        DESCRIPTION    "The ports on a 43SCX4L optical card."
        ::= { tnOpticalPortInfo 152 }

    tn43scx4lPortInfoEntry OBJECT-TYPE
        SYNTAX         Tn43scx4lPortInfoEntry
        MAX-ACCESS     not-accessible
        STATUS         current
        DESCRIPTION    ""
        INDEX { ifIndex }
        ::= { tn43scx4lPortInfoTable 1 }

    Tn43scx4lPortInfoEntry ::=
        SEQUENCE {
            tn43scx4lPortInfoFunction INTEGER
        }

    tn43scx4lPortInfoFunction OBJECT-TYPE
        SYNTAX         INTEGER {
                         network(1),
                         client(2)
                       }
        MAX-ACCESS     read-only
        STATUS         current
        DESCRIPTION    "Indicates the functional type of this 43SCX4L port."
        ::= { tn43scx4lPortInfoEntry 1 }

--------------------------------------------------------------------------------
-- AM2125B Optical Port Info Scalars
--------------------------------------------------------------------------------
    tnAm2125bPortInfoAttributeTotal OBJECT-TYPE
        SYNTAX         Integer32
        MAX-ACCESS     read-only
        STATUS         current
        DESCRIPTION    ""
        ::= { tnOpticalPortInfo 153 }

--------------------------------------------------------------------------------
-- AM2125B Optical Port Info Table
--------------------------------------------------------------------------------
    tnAm2125bPortInfoTable OBJECT-TYPE
        SYNTAX         SEQUENCE OF TnAm2125bPortInfoEntry
        MAX-ACCESS     not-accessible
        STATUS         current
        DESCRIPTION    "The ports on an AM2125B optical card."
        ::= { tnOpticalPortInfo 154 }

    tnAm2125bPortInfoEntry OBJECT-TYPE
        SYNTAX         TnAm2125bPortInfoEntry
        MAX-ACCESS     not-accessible
        STATUS         current
        DESCRIPTION    ""
        INDEX { ifIndex }
        ::= { tnAm2125bPortInfoTable 1 }

    TnAm2125bPortInfoEntry ::=
        SEQUENCE {
            tnAm2125bPortInfoFunction INTEGER
        }

    tnAm2125bPortInfoFunction OBJECT-TYPE
        SYNTAX         INTEGER {
                         lineIn(1),
                         inv(2),
                         dcm(3),
                         lineOut(4),
                         oscSfp(5),
                         det(6),
                         osc(7)
                       }
        MAX-ACCESS     read-only
        STATUS         current
        DESCRIPTION    "Indicates the functional type of this AM2125B port."
        ::= { tnAm2125bPortInfoEntry 1 }

--------------------------------------------------------------------------------
-- 112SNX10 Optical Port Info Scalars
--------------------------------------------------------------------------------
    tn112snx10PortInfoAttributeTotal OBJECT-TYPE
        SYNTAX         Integer32
        MAX-ACCESS     read-only
        STATUS         current
        DESCRIPTION    ""
        ::= { tnOpticalPortInfo 155 }

--------------------------------------------------------------------------------
-- 112SNX10 Optical Port Info Table
--------------------------------------------------------------------------------
    tn112snx10PortInfoTable OBJECT-TYPE
        SYNTAX         SEQUENCE OF Tn112snx10PortInfoEntry
        MAX-ACCESS     not-accessible
        STATUS         current
        DESCRIPTION    "The ports on a 112SNX10 optical card."
        ::= { tnOpticalPortInfo 156 }

    tn112snx10PortInfoEntry OBJECT-TYPE
        SYNTAX         Tn112snx10PortInfoEntry
        MAX-ACCESS     not-accessible
        STATUS         current
        DESCRIPTION    ""
        INDEX { ifIndex }
        ::= { tn112snx10PortInfoTable 1 }

    Tn112snx10PortInfoEntry ::=
        SEQUENCE {
            tn112snx10PortInfoFunction INTEGER
        }

    tn112snx10PortInfoFunction OBJECT-TYPE
        SYNTAX         INTEGER {
                         network(1),
                         client(2)
                       }
        MAX-ACCESS     read-only
        STATUS         current
        DESCRIPTION    "Indicates the functional type of this 112SNX10 port."
        ::= { tn112snx10PortInfoEntry 1 }

--------------------------------------------------------------------------------
-- 112SNA1 Optical Port Info Scalars
--------------------------------------------------------------------------------
    tn112sna1PortInfoAttributeTotal OBJECT-TYPE
        SYNTAX         Integer32
        MAX-ACCESS     read-only
        STATUS         current
        DESCRIPTION    ""
        ::= { tnOpticalPortInfo 157 }

--------------------------------------------------------------------------------
-- 112SNA1 Optical Port Info Table
--------------------------------------------------------------------------------
    tn112sna1PortInfoTable OBJECT-TYPE
        SYNTAX         SEQUENCE OF Tn112sna1PortInfoEntry
        MAX-ACCESS     not-accessible
        STATUS         current
        DESCRIPTION    "The ports on a 112SNA1 optical card."
        ::= { tnOpticalPortInfo 158 }

    tn112sna1PortInfoEntry OBJECT-TYPE
        SYNTAX         Tn112sna1PortInfoEntry
        MAX-ACCESS     not-accessible
        STATUS         current
        DESCRIPTION    ""
        INDEX { ifIndex }
        ::= { tn112sna1PortInfoTable 1 }

    Tn112sna1PortInfoEntry ::=
        SEQUENCE {
            tn112sna1PortInfoFunction INTEGER
        }

    tn112sna1PortInfoFunction OBJECT-TYPE
        SYNTAX         INTEGER {
                         network(1),
                         client(2)
                       }
        MAX-ACCESS     read-only
        STATUS         current
        DESCRIPTION    "Indicates the functional type of this 112SNA1 port."
        ::= { tn112sna1PortInfoEntry 1 }

--------------------------------------------------------------------------------
-- 11QTA4 Optical Port Info Scalars
--------------------------------------------------------------------------------
--    obsolete
--    tn11qta4PortInfoAttributeTotal OBJECT-TYPE ::= { tnOpticalPortInfo 159 }

--------------------------------------------------------------------------------
-- 11QTA4 Optical Port Info Table
--------------------------------------------------------------------------------
--    obsolete
--    tn11qta4PortInfoTable OBJECT-TYPE ::= { tnOpticalPortInfo 160 }

--------------------------------------------------------------------------------
-- 1DPP24M Optical Port Info Scalars
--------------------------------------------------------------------------------
    tn1dpp24mPortInfoAttributeTotal OBJECT-TYPE
        SYNTAX         Integer32
        MAX-ACCESS     read-only
        STATUS         current
        DESCRIPTION    ""
        ::= { tnOpticalPortInfo 161 }

--------------------------------------------------------------------------------
-- 1DPP24M Optical Port Info Table
--------------------------------------------------------------------------------
    tn1dpp24mPortInfoTable OBJECT-TYPE
        SYNTAX         SEQUENCE OF Tn1dpp24mPortInfoEntry
        MAX-ACCESS     not-accessible
        STATUS         current
        DESCRIPTION    "The ports on a 1DPP24M optical card."
        ::= { tnOpticalPortInfo 162 }

    tn1dpp24mPortInfoEntry OBJECT-TYPE
        SYNTAX         Tn1dpp24mPortInfoEntry
        MAX-ACCESS     not-accessible
        STATUS         current
        DESCRIPTION    ""
        INDEX { ifIndex }
        ::= { tn1dpp24mPortInfoTable 1 }

    Tn1dpp24mPortInfoEntry ::=
        SEQUENCE {
            tn1dpp24mPortInfoFunction                 INTEGER
--            obsolete
--            tn1dpp24mPortClockSourceIncomingQLStatus  Unsigned32,
--            tn1dpp24mPortClockSourceIncomingQL        Unsigned32
        }

    tn1dpp24mPortInfoFunction OBJECT-TYPE
        SYNTAX         INTEGER {
                         network(1),
                         client(2)
                       }
        MAX-ACCESS     read-only
        STATUS         current
        DESCRIPTION    "Indicates the functional type of this 1DPP24M port."
        ::= { tn1dpp24mPortInfoEntry 1 }

--    obsolete
--    tn1dpp24mPortClockSourceIncomingQLStatus OBJECT-TYPE ::= { tn1dpp24mPortInfoEntry 2 }
--    tn1dpp24mPortClockSourceIncomingQL OBJECT-TYPE ::= { tn1dpp24mPortInfoEntry 3 }

--------------------------------------------------------------------------------
-- DWDM Common OTU3/ODU3 Client Port Info Table
--------------------------------------------------------------------------------
    tnDwdmCmnOtu3Odu3ClientPortInfoTable OBJECT-TYPE
        SYNTAX         SEQUENCE OF TnDwdmCmnOtu3Odu3ClientPortInfoEntry
        MAX-ACCESS     not-accessible
        STATUS         current
        DESCRIPTION    "Common attributes against DWDM client ports."
        ::= { tnOpticalPortInfo 163 }

    tnDwdmCmnOtu3Odu3ClientPortInfoEntry OBJECT-TYPE
        SYNTAX         TnDwdmCmnOtu3Odu3ClientPortInfoEntry
        MAX-ACCESS     not-accessible
        STATUS         current
        DESCRIPTION    ""
        INDEX { ifIndex }
        ::= { tnDwdmCmnOtu3Odu3ClientPortInfoTable 1 }

    TnDwdmCmnOtu3Odu3ClientPortInfoEntry ::=
        SEQUENCE {
            tnDwdmCmnClientPortOtu3IncomingTti  OCTET STRING,
            tnDwdmCmnClientPortOtu3TtiStatus    AluWdmTtiStatus,
            tnDwdmCmnClientPortOdu3IncomingTti  OCTET STRING,
            tnDwdmCmnClientPortOdu3TtiStatus    AluWdmTtiStatus,
            tnDwdmCmnClientPortOtu3PreFec       Counter64,
            tnDwdmCmnClientPortOtu3PostFec      Counter64
        }

    tnDwdmCmnClientPortOtu3IncomingTti OBJECT-TYPE
        SYNTAX         OCTET STRING
        MAX-ACCESS     read-only
        STATUS         current
        DESCRIPTION    "OTU3 incoming TTI."
        DEFVAL         { "" }
        ::= { tnDwdmCmnOtu3Odu3ClientPortInfoEntry 1 }

    tnDwdmCmnClientPortOtu3TtiStatus OBJECT-TYPE
        SYNTAX         AluWdmTtiStatus
        MAX-ACCESS     read-only
        STATUS         current
        DESCRIPTION    "OTU3 TTI status."
        DEFVAL         { unspecified }
        ::= { tnDwdmCmnOtu3Odu3ClientPortInfoEntry 2 }

    tnDwdmCmnClientPortOdu3IncomingTti OBJECT-TYPE
        SYNTAX         OCTET STRING
        MAX-ACCESS     read-only
        STATUS         current
        DESCRIPTION    "ODU3 incoming TTI."
        DEFVAL         { "" }
        ::= { tnDwdmCmnOtu3Odu3ClientPortInfoEntry 3 }

    tnDwdmCmnClientPortOdu3TtiStatus OBJECT-TYPE
        SYNTAX         AluWdmTtiStatus
        MAX-ACCESS     read-only
        STATUS         current
        DESCRIPTION    "ODU3 TTI status."
        DEFVAL         { unspecified }
        ::= { tnDwdmCmnOtu3Odu3ClientPortInfoEntry 4 }

    tnDwdmCmnClientPortOtu3PreFec OBJECT-TYPE
        SYNTAX         Counter64
        MAX-ACCESS     read-only
        STATUS         current
        DESCRIPTION    "Real time error bit rate of pre-FEC (Forward
                        Error Correction).

                        Current configurable range: 0 to 4000."
        ::= { tnDwdmCmnOtu3Odu3ClientPortInfoEntry 5 }

    tnDwdmCmnClientPortOtu3PostFec OBJECT-TYPE
        SYNTAX         Counter64
        MAX-ACCESS     read-only
        STATUS         current
        DESCRIPTION    "Real time error bit rate of post-FEC (Forward
                        Error Correction).

                        Current configurable range: 0 to 4000."
        ::= { tnDwdmCmnOtu3Odu3ClientPortInfoEntry 6 }

--------------------------------------------------------------------------------
-- UL43SCUP Optical Port Info Scalars
--------------------------------------------------------------------------------
    tnul43scupPortInfoAttributeTotal OBJECT-TYPE
        SYNTAX         Integer32
        MAX-ACCESS     read-only
        STATUS         current
        DESCRIPTION    ""
        ::= { tnOpticalPortInfo 164 }

--------------------------------------------------------------------------------
-- UL43SCUP Optical Port Info Table
--------------------------------------------------------------------------------
    tnul43scupPortInfoTable OBJECT-TYPE
        SYNTAX         SEQUENCE OF Tnul43scupPortInfoEntry
        MAX-ACCESS     not-accessible
        STATUS         current
        DESCRIPTION    "The ports on a UL43SCUP optical card."
        ::= { tnOpticalPortInfo 165 }

    tnul43scupPortInfoEntry OBJECT-TYPE
        SYNTAX         Tnul43scupPortInfoEntry
        MAX-ACCESS     not-accessible
        STATUS         current
        DESCRIPTION    ""
        INDEX { ifIndex }
        ::= { tnul43scupPortInfoTable 1 }

    Tnul43scupPortInfoEntry ::=
        SEQUENCE {
            tnul43scupPortInfoFunction  INTEGER
        }

    tnul43scupPortInfoFunction OBJECT-TYPE
        SYNTAX         INTEGER {
                         network(1)
                       }
        MAX-ACCESS     read-only
        STATUS         current
        DESCRIPTION    "Indicates the functional type of this UL43SCUP port."
        ::= { tnul43scupPortInfoEntry 1 }

--------------------------------------------------------------------------------
-- UL11QCUP Optical Port Info Scalars
--------------------------------------------------------------------------------
    tnul11qcupPortInfoAttributeTotal OBJECT-TYPE
        SYNTAX         Integer32
        MAX-ACCESS     read-only
        STATUS         current
        DESCRIPTION    ""
        ::= { tnOpticalPortInfo 166 }

--------------------------------------------------------------------------------
-- UL11QCUP Optical Port Info Table
--------------------------------------------------------------------------------
    tnul11qcupPortInfoTable OBJECT-TYPE
        SYNTAX         SEQUENCE OF Tnul11qcupPortInfoEntry
        MAX-ACCESS     not-accessible
        STATUS         current
        DESCRIPTION    "The ports on a UL11QCUP optical card."
        ::= { tnOpticalPortInfo 167 }

    tnul11qcupPortInfoEntry OBJECT-TYPE
        SYNTAX         Tnul11qcupPortInfoEntry
        MAX-ACCESS     not-accessible
        STATUS         current
        DESCRIPTION    ""
        INDEX { ifIndex }
        ::= { tnul11qcupPortInfoTable 1 }

    Tnul11qcupPortInfoEntry ::=
        SEQUENCE {
            tnul11qcupPortInfoFunction     INTEGER
        }

    tnul11qcupPortInfoFunction OBJECT-TYPE
        SYNTAX         INTEGER {
                         network(1)
                       }
        MAX-ACCESS     read-only
        STATUS         current
        DESCRIPTION    "Indicates the functional type of this UL11QCUP port."
        ::= { tnul11qcupPortInfoEntry 1 }

--------------------------------------------------------------------------------
-- 11QPEN4 Optical Port Info Scalars
--------------------------------------------------------------------------------
    tn11qpen4PortInfoAttributeTotal OBJECT-TYPE
        SYNTAX         Integer32
        MAX-ACCESS     read-only
        STATUS         current
        DESCRIPTION    ""
        ::= { tnOpticalPortInfo 168 }

--------------------------------------------------------------------------------
-- 11QPEN4 Optical Port Info Table
--------------------------------------------------------------------------------
    tn11qpen4PortInfoTable OBJECT-TYPE
        SYNTAX         SEQUENCE OF Tn11qpen4PortInfoEntry
        MAX-ACCESS     not-accessible
        STATUS         current
        DESCRIPTION    "The ports on a 11QPEN4 optical card."
        ::= { tnOpticalPortInfo 169 }

    tn11qpen4PortInfoEntry OBJECT-TYPE
        SYNTAX         Tn11qpen4PortInfoEntry
        MAX-ACCESS     not-accessible
        STATUS         current
        DESCRIPTION    ""
        INDEX { ifIndex }
        ::= { tn11qpen4PortInfoTable 1 }

    Tn11qpen4PortInfoEntry ::=
        SEQUENCE {
            tn11qpen4PortInfoFunction                  INTEGER,
            tn11qpen4PortInfoEncryptionCurrentKeyInfo  SnmpAdminString,
            tn11qpen4PortInfoEncryptionNextKeyInfo     SnmpAdminString
        }

    tn11qpen4PortInfoFunction OBJECT-TYPE
        SYNTAX         INTEGER {
                         network(1),
                         client(2),
                         evoa(3)
                       }
        MAX-ACCESS     read-only
        STATUS         current
        DESCRIPTION    "Indicates the functional type of this 11QPEN4 port."
        ::= { tn11qpen4PortInfoEntry 1 }

    tn11qpen4PortInfoEncryptionCurrentKeyInfo OBJECT-TYPE
        SYNTAX         SnmpAdminString (SIZE(0..256))
        MAX-ACCESS     read-only
        STATUS         current
        DESCRIPTION    "Non-cryptographic information identifying the
                        current key."
        DEFVAL         { "" }
        ::= { tn11qpen4PortInfoEntry 2 }

    tn11qpen4PortInfoEncryptionNextKeyInfo OBJECT-TYPE
        SYNTAX         SnmpAdminString (SIZE(0..256))
        MAX-ACCESS     read-only
        STATUS         current
        DESCRIPTION    "Non-cryptographic information identifying the
                        standby key."
        DEFVAL         { "" }
        ::= { tn11qpen4PortInfoEntry 3 }

--------------------------------------------------------------------------------
-- 43SCX4E Optical Port Info Scalars
--------------------------------------------------------------------------------
    tn43scx4ePortInfoAttributeTotal OBJECT-TYPE
        SYNTAX         Integer32
        MAX-ACCESS     read-only
        STATUS         current
        DESCRIPTION    ""
        ::= { tnOpticalPortInfo 170 }

--------------------------------------------------------------------------------
-- 43SCX4E Optical Port Info Table
--------------------------------------------------------------------------------
    tn43scx4ePortInfoTable OBJECT-TYPE
        SYNTAX         SEQUENCE OF Tn43scx4ePortInfoEntry
        MAX-ACCESS     not-accessible
        STATUS         current
        DESCRIPTION    "The ports on a 43SCX4E optical card."
        ::= { tnOpticalPortInfo 171 }

    tn43scx4ePortInfoEntry OBJECT-TYPE
        SYNTAX         Tn43scx4ePortInfoEntry
        MAX-ACCESS     not-accessible
        STATUS         current
        DESCRIPTION    ""
        INDEX { ifIndex }
        ::= { tn43scx4ePortInfoTable 1 }

    Tn43scx4ePortInfoEntry ::=
        SEQUENCE {
            tn43scx4ePortInfoFunction INTEGER
        }

    tn43scx4ePortInfoFunction OBJECT-TYPE
        SYNTAX         INTEGER {
                         network(1),
                         client(2)
                       }
        MAX-ACCESS     read-only
        STATUS         current
        DESCRIPTION    "Indicates the functional type of this 43SCX4E port."
        ::= { tn43scx4ePortInfoEntry 1 }

--------------------------------------------------------------------------------
-- WSS Attenuation Optical Port Info Scalars
--------------------------------------------------------------------------------
    tnWssAttenPortInfoAttributeTotal OBJECT-TYPE
        SYNTAX         Integer32
        MAX-ACCESS     read-only
        STATUS         current
        DESCRIPTION    ""
        ::= { tnOpticalPortInfo 172 }

--------------------------------------------------------------------------------
-- WSS Attenuation Port Info Table
--------------------------------------------------------------------------------
    tnWssAttenPortInfoTable OBJECT-TYPE
        SYNTAX         SEQUENCE OF TnWssAttenPortInfoEntry
        MAX-ACCESS     not-accessible
        STATUS         current
        DESCRIPTION    "Through this table, a network operator may read
                        the WSS attenuation."
        ::= { tnOpticalPortInfo 173 }

    tnWssAttenPortInfoEntry OBJECT-TYPE
        SYNTAX         TnWssAttenPortInfoEntry
        MAX-ACCESS     not-accessible
        STATUS         current
        DESCRIPTION    ""
        INDEX { ifIndex,
                tnDirection,
                tnChannel }
        ::= { tnWssAttenPortInfoTable 1 }

    TnWssAttenPortInfoEntry ::=
        SEQUENCE {
            tnWssAttenPortInfoWssCurrentRelativeAtten  Unsigned32,
            tnWssAttenPortInfoApplicability            INTEGER
        }

    tnWssAttenPortInfoWssCurrentRelativeAtten OBJECT-TYPE
        SYNTAX         Unsigned32
        UNITS          "mB"
        MAX-ACCESS     read-only
        STATUS         current
        DESCRIPTION    "The attenuation, expressed in units of mB, is
                        associated with the WSS channel attenuation.
                        This is the current relative attenuation.

                        Current range: 0 to 1500."
        ::= { tnWssAttenPortInfoEntry 1 }

    tnWssAttenPortInfoApplicability OBJECT-TYPE
        SYNTAX         INTEGER {
                         notApplicable(1),
                         applicableAndAvailable(2)
                       }
        MAX-ACCESS     read-only
        STATUS         current
        DESCRIPTION    "Values include:

                        notApplicable - no XC is configured for this
                          channel.
                        applicableAndAvailable - XC is configured for
                          this channel."
        ::= { tnWssAttenPortInfoEntry 2 }

--------------------------------------------------------------------------------
-- 43SCGE1 Optical Port Info Scalars
--------------------------------------------------------------------------------
    tn43scge1PortInfoAttributeTotal OBJECT-TYPE
        SYNTAX         Integer32
        MAX-ACCESS     read-only
        STATUS         current
        DESCRIPTION    ""
        ::= { tnOpticalPortInfo 174 }

--------------------------------------------------------------------------------
-- 43SCGE1 Optical Port Info Table
--------------------------------------------------------------------------------
    tn43scge1PortInfoTable OBJECT-TYPE
        SYNTAX         SEQUENCE OF Tn43scge1PortInfoEntry
        MAX-ACCESS     not-accessible
        STATUS         current
        DESCRIPTION    "The ports on a 43SCGE1 optical card."
        ::= { tnOpticalPortInfo 175 }

    tn43scge1PortInfoEntry OBJECT-TYPE
        SYNTAX         Tn43scge1PortInfoEntry
        MAX-ACCESS     not-accessible
        STATUS         current
        DESCRIPTION    ""
        INDEX { ifIndex }
        ::= { tn43scge1PortInfoTable 1 }

    Tn43scge1PortInfoEntry ::=
        SEQUENCE {
            tn43scge1PortInfoFunction INTEGER
        }

    tn43scge1PortInfoFunction OBJECT-TYPE
        SYNTAX         INTEGER {
                         network(1),
                         client(2)
                       }
        MAX-ACCESS     read-only
        STATUS         current
        DESCRIPTION    "Indicates the functional type of this 43SCGE1 port."
        ::= { tn43scge1PortInfoEntry 1 }

--------------------------------------------------------------------------------
-- 11QPE24 Optical Port Info Scalars
--------------------------------------------------------------------------------
    tn11qpe24PortInfoAttributeTotal OBJECT-TYPE
        SYNTAX         Integer32
        MAX-ACCESS     read-only
        STATUS         current
        DESCRIPTION    ""
        ::= { tnOpticalPortInfo 176 }

--------------------------------------------------------------------------------
-- 11QPE24 Optical Port Info Table
--------------------------------------------------------------------------------
    tn11qpe24PortInfoTable OBJECT-TYPE
        SYNTAX         SEQUENCE OF Tn11qpe24PortInfoEntry
        MAX-ACCESS     not-accessible
        STATUS         current
        DESCRIPTION    "The ports on a 11QPE24 optical card."
        ::= { tnOpticalPortInfo 177 }

    tn11qpe24PortInfoEntry OBJECT-TYPE
        SYNTAX         Tn11qpe24PortInfoEntry
        MAX-ACCESS     not-accessible
        STATUS         current
        DESCRIPTION    ""
        INDEX { ifIndex }
        ::= { tn11qpe24PortInfoTable 1 }

    Tn11qpe24PortInfoEntry ::=
        SEQUENCE {
            tn11qpe24PortInfoFunction INTEGER
        }

    tn11qpe24PortInfoFunction OBJECT-TYPE
        SYNTAX         INTEGER {
                         network(1),
                         client(2),
                         evoa(3)
                       }
        MAX-ACCESS     read-only
        STATUS         current
        DESCRIPTION    "Indicates the functional type of this 11QPE24 port."
        ::= { tn11qpe24PortInfoEntry 1 }

--------------------------------------------------------------------------------
-- 11STAR1A Optical Port Info Scalars
--------------------------------------------------------------------------------
    tn11star1aPortInfoAttributeTotal OBJECT-TYPE
        SYNTAX         Integer32
        MAX-ACCESS     read-only
        STATUS         current
        DESCRIPTION    ""
        ::= { tnOpticalPortInfo 178 }

--------------------------------------------------------------------------------
-- 11STAR1A Optical Port Info Table
--------------------------------------------------------------------------------
    tn11star1aPortInfoTable OBJECT-TYPE
        SYNTAX         SEQUENCE OF Tn11star1aPortInfoEntry
        MAX-ACCESS     not-accessible
        STATUS         current
        DESCRIPTION    "The ports on a 11STAR1A optical card."
        ::= { tnOpticalPortInfo 179 }

    tn11star1aPortInfoEntry OBJECT-TYPE
        SYNTAX         Tn11star1aPortInfoEntry
        MAX-ACCESS     not-accessible
        STATUS         current
        DESCRIPTION    ""
        INDEX { ifIndex }
        ::= { tn11star1aPortInfoTable 1 }

    Tn11star1aPortInfoEntry ::=
        SEQUENCE {
            tn11star1aPortInfoFunction INTEGER
        }

    tn11star1aPortInfoFunction OBJECT-TYPE
        SYNTAX         INTEGER {
                         network(1),
                         client(2)
                       }
        MAX-ACCESS     read-only
        STATUS         current
        DESCRIPTION    "Indicates the functional type of this 11STAR1A port."
        ::= { tn11star1aPortInfoEntry 1 }

--------------------------------------------------------------------------------
-- MVAC8B Optical Port Info Scalars
--------------------------------------------------------------------------------
    tnMvac8bPortInfoAttributeTotal OBJECT-TYPE
        SYNTAX         Integer32
        MAX-ACCESS     read-only
        STATUS         current
        DESCRIPTION    ""
        ::= { tnOpticalPortInfo 180 }

--------------------------------------------------------------------------------
-- MVAC8B Optical Port Info Table
--------------------------------------------------------------------------------
    tnMvac8bPortInfoTable OBJECT-TYPE
        SYNTAX         SEQUENCE OF TnMvac8bPortInfoEntry
        MAX-ACCESS     not-accessible
        STATUS         current
        DESCRIPTION    "The ports on a MVAC8B optical card."
        ::= { tnOpticalPortInfo 181 }

    tnMvac8bPortInfoEntry OBJECT-TYPE
        SYNTAX         TnMvac8bPortInfoEntry
        MAX-ACCESS     not-accessible
        STATUS         current
        DESCRIPTION    ""
        INDEX { ifIndex }
        ::= { tnMvac8bPortInfoTable 1 }

    TnMvac8bPortInfoEntry ::=
        SEQUENCE {
            tnMvac8bPortInfoFunction INTEGER
        }

    tnMvac8bPortInfoFunction OBJECT-TYPE
        SYNTAX         INTEGER {
                         network(1),
                         client(2)
                       }
        MAX-ACCESS     read-only
        STATUS         current
        DESCRIPTION    "Indicates the functional type of this MVAC8B port."
        ::= { tnMvac8bPortInfoEntry 1 }

--------------------------------------------------------------------------------
-- WR8-88AF Optical Port Info Scalars
--------------------------------------------------------------------------------
    tnWr8c88afPortInfoAttributeTotal OBJECT-TYPE
        SYNTAX         Integer32
        MAX-ACCESS     read-only
        STATUS         current
        DESCRIPTION    ""
        ::= { tnOpticalPortInfo 182 }

--------------------------------------------------------------------------------
-- WR8-88AF Optical Port Info Table
--------------------------------------------------------------------------------
    tnWr8c88afPortInfoTable OBJECT-TYPE
        SYNTAX         SEQUENCE OF TnWr8c88afPortInfoEntry
        MAX-ACCESS     not-accessible
        STATUS         current
        DESCRIPTION    "The ports on a WR8-88AF optical card."
        ::= { tnOpticalPortInfo 183 }

    tnWr8c88afPortInfoEntry OBJECT-TYPE
        SYNTAX         TnWr8c88afPortInfoEntry
        MAX-ACCESS     not-accessible
        STATUS         current
        DESCRIPTION    ""
        INDEX { ifIndex }
        ::= { tnWr8c88afPortInfoTable 1 }

    TnWr8c88afPortInfoEntry ::=
        SEQUENCE {
            tnWr8c88afPortInfoFunction     INTEGER
        }

    tnWr8c88afPortInfoFunction OBJECT-TYPE
        SYNTAX         INTEGER {
                         signal(1),
                         thru(2),
                         dropOut(3),
                         addIn(4),
                         meshOut(5),
                         inv(6)
                       }
        MAX-ACCESS     read-only
        STATUS         current
        DESCRIPTION    "Indicates the functional type of this WR8-88AF port."
        ::= { tnWr8c88afPortInfoEntry 1 }

--------------------------------------------------------------------------------
-- 10AN10G Optical Port Info Scalars
--------------------------------------------------------------------------------
    tncl10an10gPortInfoAttributeTotal OBJECT-TYPE
        SYNTAX         Integer32
        MAX-ACCESS     read-only
        STATUS         current
        DESCRIPTION    ""
        ::= { tnOpticalPortInfo 184 }

--------------------------------------------------------------------------------
-- 10AN10G Optical Port Info Table
--------------------------------------------------------------------------------
    tncl10an10gPortInfoTable OBJECT-TYPE
        SYNTAX         SEQUENCE OF Tncl10an10gPortInfoEntry
        MAX-ACCESS     not-accessible
        STATUS         current
        DESCRIPTION    "The ports on a 10AN10G optical card."
        ::= { tnOpticalPortInfo 185 }

    tncl10an10gPortInfoEntry OBJECT-TYPE
        SYNTAX         Tncl10an10gPortInfoEntry
        MAX-ACCESS     not-accessible
        STATUS         current
        DESCRIPTION    ""
        INDEX { ifIndex }
        ::= { tncl10an10gPortInfoTable 1 }

    Tncl10an10gPortInfoEntry ::=
        SEQUENCE {
            tncl10an10gPortInfoFunction INTEGER
        }

    tncl10an10gPortInfoFunction OBJECT-TYPE
        SYNTAX         INTEGER {
                         network(1),
                         client(2)
                       }
        MAX-ACCESS     read-only
        STATUS         current
        DESCRIPTION    "Indicates the functional type of this 10AN10G port."
        ::= { tncl10an10gPortInfoEntry 1 }

--------------------------------------------------------------------------------
-- 24ANM Optical Port Info Scalars
--------------------------------------------------------------------------------
    tncl24anmPortInfoAttributeTotal OBJECT-TYPE
        SYNTAX         Integer32
        MAX-ACCESS     read-only
        STATUS         current
        DESCRIPTION    ""
        ::= { tnOpticalPortInfo 186 }

--------------------------------------------------------------------------------
-- 24ANM Optical Port Info Table
--------------------------------------------------------------------------------
    tncl24anmPortInfoTable OBJECT-TYPE
        SYNTAX         SEQUENCE OF Tncl24anmPortInfoEntry
        MAX-ACCESS     not-accessible
        STATUS         current
        DESCRIPTION    "The ports on a 24ANM optical card."
        ::= { tnOpticalPortInfo 187 }

    tncl24anmPortInfoEntry OBJECT-TYPE
        SYNTAX         Tncl24anmPortInfoEntry
        MAX-ACCESS     not-accessible
        STATUS         current
        DESCRIPTION    ""
        INDEX { ifIndex }
        ::= { tncl24anmPortInfoTable 1 }

    Tncl24anmPortInfoEntry ::=
        SEQUENCE {
            tncl24anmPortInfoFunction INTEGER
        }

    tncl24anmPortInfoFunction OBJECT-TYPE
        SYNTAX         INTEGER {
                         network(1),
                         client(2)
                       }
        MAX-ACCESS     read-only
        STATUS         current
        DESCRIPTION    "Indicates the functional type of this 24ANM port."
        ::= { tncl24anmPortInfoEntry 1 }

--------------------------------------------------------------------------------
-- OPSB Optical Port Info Scalars
--------------------------------------------------------------------------------
    tnOpsbPortInfoAttributeTotal OBJECT-TYPE
        SYNTAX         Integer32
        MAX-ACCESS     read-only
        STATUS         current
        DESCRIPTION    ""
        ::= { tnOpticalPortInfo 188 }

--------------------------------------------------------------------------------
-- OPSB Optical Port Info Table
--------------------------------------------------------------------------------
    tnOpsbPortInfoTable OBJECT-TYPE
        SYNTAX         SEQUENCE OF TnOpsbPortInfoEntry
        MAX-ACCESS     not-accessible
        STATUS         current
        DESCRIPTION    "The ports on an OPSB optical card."
        ::= { tnOpticalPortInfo 189 }

    tnOpsbPortInfoEntry OBJECT-TYPE
        SYNTAX         TnOpsbPortInfoEntry
        MAX-ACCESS     not-accessible
        STATUS         current
        DESCRIPTION    ""
        INDEX { ifIndex }
        ::= { tnOpsbPortInfoTable 1 }

    TnOpsbPortInfoEntry ::=
        SEQUENCE {
            tnOpsbPortInfoFunction     INTEGER
        }

    tnOpsbPortInfoFunction OBJECT-TYPE
        SYNTAX         INTEGER {
                         signal(1),
                         workingProtected(2)
                       }
        MAX-ACCESS     read-only
        STATUS         current
        DESCRIPTION    "Indicates the functional type of this OPSB port."
        ::= { tnOpsbPortInfoEntry 1 }

--------------------------------------------------------------------------------
-- OPS Optical Port Info Scalars
--------------------------------------------------------------------------------
    tnOpsPortInfoAttributeTotal OBJECT-TYPE
        SYNTAX         Integer32
        MAX-ACCESS     read-only
        STATUS         current
        DESCRIPTION    ""
        ::= { tnOpticalPortInfo 190 }

--------------------------------------------------------------------------------
-- OPS Optical Port Info Table
--------------------------------------------------------------------------------
    tnOpsPortInfoTable OBJECT-TYPE
        SYNTAX         SEQUENCE OF TnOpsPortInfoEntry
        MAX-ACCESS     not-accessible
        STATUS         current
        DESCRIPTION    "The attributes for an OPS optical card."
        ::= { tnOpticalPortInfo 191 }

    tnOpsPortInfoEntry OBJECT-TYPE
        SYNTAX         TnOpsPortInfoEntry
        MAX-ACCESS     not-accessible
        STATUS         current
        DESCRIPTION    ""
        INDEX { ifIndex }
        ::= { tnOpsPortInfoTable 1 }

    TnOpsPortInfoEntry ::=
        SEQUENCE {
            tnOpsPortInfoReceivedPower                  Integer32,
            tnOpsPortInfoPresentTransmitAttenuation     Integer32
        }

    tnOpsPortInfoReceivedPower OBJECT-TYPE
        SYNTAX         Integer32
        UNITS          "mBm"
        MAX-ACCESS     read-only
        STATUS         current
        DESCRIPTION    "The received power in mBm.  This is accessible
                        from ports 2 and 3 (working or protected)
                        exclusively."
        ::= { tnOpsPortInfoEntry 1 }

    tnOpsPortInfoPresentTransmitAttenuation OBJECT-TYPE
        SYNTAX         Integer32
        UNITS          "mB"
        MAX-ACCESS     read-only
        STATUS         current
        DESCRIPTION    "The present attenuation of the attenuator -
                        applies to the network ports of the OPS
                        optical card with attenuators."
        ::= { tnOpsPortInfoEntry 2 }

--------------------------------------------------------------------------------
-- 11DPE12A Optical Port Info Scalars
--------------------------------------------------------------------------------
    tn11dpe12aPortInfoAttributeTotal OBJECT-TYPE
        SYNTAX         Integer32
        MAX-ACCESS     read-only
        STATUS         current
        DESCRIPTION    ""
        ::= { tnOpticalPortInfo 192 }

--------------------------------------------------------------------------------
-- 11DPE12A Optical Port Info Table
--------------------------------------------------------------------------------
    tn11dpe12aPortInfoTable OBJECT-TYPE
        SYNTAX         SEQUENCE OF Tn11dpe12aPortInfoEntry
        MAX-ACCESS     not-accessible
        STATUS         current
        DESCRIPTION    "The ports on a 11DPE12A optical card."
        ::= { tnOpticalPortInfo 193 }

    tn11dpe12aPortInfoEntry OBJECT-TYPE
        SYNTAX         Tn11dpe12aPortInfoEntry
        MAX-ACCESS     not-accessible
        STATUS         current
        DESCRIPTION    ""
        INDEX { ifIndex }
        ::= { tn11dpe12aPortInfoTable 1 }

    Tn11dpe12aPortInfoEntry ::=
        SEQUENCE {
            tn11dpe12aPortInfoFunction               INTEGER,
            tn11dpe12aPortInfoTotalVTS               Unsigned32,
            tn11dpe12aPortInfoIngAvailableBandwidth  Unsigned32,
            tn11dpe12aPortInfoEgrAvailableBandwidth  Unsigned32
        }

    tn11dpe12aPortInfoFunction OBJECT-TYPE
        SYNTAX         INTEGER {
                         network(1),
                         client(2),
                         evoa(3),
                         backplane(4),
                         tod(5)
                       }
        MAX-ACCESS     read-only
        STATUS         current
        DESCRIPTION    "Indicates the functional type of this 11DPE12A port."
        ::= { tn11dpe12aPortInfoEntry 1 }

    tn11dpe12aPortInfoTotalVTS OBJECT-TYPE
        SYNTAX         Unsigned32
        MAX-ACCESS     read-only
        STATUS         current
        DESCRIPTION    "Total VTS for 11dpe12a ports."
        ::= { tn11dpe12aPortInfoEntry 2 }

    tn11dpe12aPortInfoIngAvailableBandwidth OBJECT-TYPE
        SYNTAX         Unsigned32
        MAX-ACCESS     read-only
        STATUS         current
        DESCRIPTION    "Available bandwidth for ingress 11DPE12A ports."
        ::= { tn11dpe12aPortInfoEntry 3 }

    tn11dpe12aPortInfoEgrAvailableBandwidth OBJECT-TYPE
        SYNTAX         Unsigned32
        MAX-ACCESS     read-only
        STATUS         current
        DESCRIPTION    "Available bandwidth for egress 11DPE12A ports."
        ::= { tn11dpe12aPortInfoEntry 4 }

--------------------------------------------------------------------------------
-- UL130SCUP Optical Port Info Scalars
--------------------------------------------------------------------------------
    tnul130scupPortInfoAttributeTotal OBJECT-TYPE
        SYNTAX         Integer32
        MAX-ACCESS     read-only
        STATUS         current
        DESCRIPTION    ""
        ::= { tnOpticalPortInfo 194 }

--------------------------------------------------------------------------------
-- UL130SCUP Optical Port Info Table
--------------------------------------------------------------------------------
    tnul130scupPortInfoTable OBJECT-TYPE
        SYNTAX         SEQUENCE OF Tnul130scupPortInfoEntry
        MAX-ACCESS     not-accessible
        STATUS         current
        DESCRIPTION    "The ports on a UL130SCUP optical card."
        ::= { tnOpticalPortInfo 195 }

    tnul130scupPortInfoEntry OBJECT-TYPE
        SYNTAX         Tnul130scupPortInfoEntry
        MAX-ACCESS     not-accessible
        STATUS         current
        DESCRIPTION    ""
        INDEX { ifIndex }
        ::= { tnul130scupPortInfoTable 1 }

    Tnul130scupPortInfoEntry ::=
        SEQUENCE {
            tnul130scupPortInfoFunction  INTEGER
        }

    tnul130scupPortInfoFunction OBJECT-TYPE
        SYNTAX         INTEGER {
                         network(1)
                       }
        MAX-ACCESS     read-only
        STATUS         current
        DESCRIPTION    "Indicates the functional type of this UL130SCUP port."
        ::= { tnul130scupPortInfoEntry 1 }

--------------------------------------------------------------------------------
-- 130SCX10 Optical Port Info Scalars
--------------------------------------------------------------------------------
    tn130scx10PortInfoAttributeTotal OBJECT-TYPE
        SYNTAX         Integer32
        MAX-ACCESS     read-only
        STATUS         current
        DESCRIPTION    ""
        ::= { tnOpticalPortInfo 196 }

--------------------------------------------------------------------------------
-- 130SCX10 Optical Port Info Table
--------------------------------------------------------------------------------
    tn130scx10PortInfoTable OBJECT-TYPE
        SYNTAX         SEQUENCE OF Tn130scx10PortInfoEntry
        MAX-ACCESS     not-accessible
        STATUS         current
        DESCRIPTION    "The ports on a 130SCX10 optical card."
        ::= { tnOpticalPortInfo 197 }

    tn130scx10PortInfoEntry OBJECT-TYPE
        SYNTAX         Tn130scx10PortInfoEntry
        MAX-ACCESS     not-accessible
        STATUS         current
        DESCRIPTION    ""
        INDEX { ifIndex }
        ::= { tn130scx10PortInfoTable 1 }

    Tn130scx10PortInfoEntry ::=
        SEQUENCE {
            tn130scx10PortInfoFunction  INTEGER
        }

    tn130scx10PortInfoFunction OBJECT-TYPE
        SYNTAX         INTEGER {
                         network(1),
                         client(2)
                       }
        MAX-ACCESS     read-only
        STATUS         current
        DESCRIPTION    "Indicates the functional type of this 130SCX10 port."
        ::= { tn130scx10PortInfoEntry 1 }

--------------------------------------------------------------------------------
-- A2P2125 Optical Port Info Scalars
--------------------------------------------------------------------------------
    tnA2p2125PortInfoAttributeTotal OBJECT-TYPE
        SYNTAX         Integer32
        MAX-ACCESS     read-only
        STATUS         current
        DESCRIPTION    ""
        ::= { tnOpticalPortInfo 198 }

--------------------------------------------------------------------------------
-- A2P2125 Optical Port Info Table
--------------------------------------------------------------------------------
    tnA2p2125PortInfoTable OBJECT-TYPE
        SYNTAX         SEQUENCE OF TnA2p2125PortInfoEntry
        MAX-ACCESS     not-accessible
        STATUS         current
        DESCRIPTION    "The ports on a A2P2125 optical card."
        ::= { tnOpticalPortInfo 199 }

    tnA2p2125PortInfoEntry OBJECT-TYPE
        SYNTAX         TnA2p2125PortInfoEntry
        MAX-ACCESS     not-accessible
        STATUS         current
        DESCRIPTION    ""
        INDEX { ifIndex }
        ::= { tnA2p2125PortInfoTable 1 }

    TnA2p2125PortInfoEntry ::=
        SEQUENCE {
            tnA2p2125PortInfoFunction  INTEGER
        }

    tnA2p2125PortInfoFunction OBJECT-TYPE
        SYNTAX         INTEGER {
                         lineIn(1),
                         inv(2),
                         dcm(3),
                         lineOut(4),
                         oscSfp(5),
                         osc(6)
                       }
        MAX-ACCESS     read-only
        STATUS         current
        DESCRIPTION    "Indicates the functional type of this A2P2125 port."
        ::= { tnA2p2125PortInfoEntry 1 }

--------------------------------------------------------------------------------
-- 4QPA8 Optical Port Info Scalars
--------------------------------------------------------------------------------
    tn4qpa8PortInfoAttributeTotal OBJECT-TYPE
        SYNTAX         Integer32
        MAX-ACCESS     read-only
        STATUS         current
        DESCRIPTION    ""
        ::= { tnOpticalPortInfo 200 }

--------------------------------------------------------------------------------
-- 4QPA8 Optical Port Info Table
--------------------------------------------------------------------------------
    tn4qpa8PortInfoTable OBJECT-TYPE
        SYNTAX         SEQUENCE OF Tn4qpa8PortInfoEntry
        MAX-ACCESS     not-accessible
        STATUS         current
        DESCRIPTION    "The ports on a 4QPA8 optical card."
        ::= { tnOpticalPortInfo 201 }

    tn4qpa8PortInfoEntry OBJECT-TYPE
        SYNTAX         Tn4qpa8PortInfoEntry
        MAX-ACCESS     not-accessible
        STATUS         current
        DESCRIPTION    ""
        INDEX { ifIndex }
        ::= { tn4qpa8PortInfoTable 1 }

    Tn4qpa8PortInfoEntry ::=
        SEQUENCE {
            tn4qpa8PortInfoFunction INTEGER
        }

    tn4qpa8PortInfoFunction OBJECT-TYPE
        SYNTAX         INTEGER {
                         network(1),
                         client(2),
                         evoa(3)
                       }
        MAX-ACCESS     read-only
        STATUS         current
        DESCRIPTION    "Indicates the functional type of this 4QPA8 port."
        ::= { tn4qpa8PortInfoEntry 1 }

--------------------------------------------------------------------------------
-- 112PDM11 Optical Port Info Scalars
--------------------------------------------------------------------------------
    tnOt112pdm11PortInfoAttributeTotal OBJECT-TYPE
        SYNTAX         Integer32
        MAX-ACCESS     read-only
        STATUS         current
        DESCRIPTION    ""
        ::= { tnOpticalPortInfo 202 }

--------------------------------------------------------------------------------
-- 112PDM11 Optical Port Info Table
--------------------------------------------------------------------------------
    tnOt112pdm11PortInfoTable OBJECT-TYPE
        SYNTAX         SEQUENCE OF TnOt112pdm11PortInfoEntry
        MAX-ACCESS     not-accessible
        STATUS         current
        DESCRIPTION    "The ports on a 112PDM11 optical card."
        ::= { tnOpticalPortInfo 203 }

    tnOt112pdm11PortInfoEntry OBJECT-TYPE
        SYNTAX         TnOt112pdm11PortInfoEntry
        MAX-ACCESS     not-accessible
        STATUS         current
        DESCRIPTION    ""
        INDEX { ifIndex }
        ::= { tnOt112pdm11PortInfoTable 1 }

    TnOt112pdm11PortInfoEntry ::=
        SEQUENCE {
            tnOt112pdm11PortInfoFunction INTEGER
        }

    tnOt112pdm11PortInfoFunction OBJECT-TYPE
        SYNTAX         INTEGER {
                         network(1),
                         client(2)
                       }
        MAX-ACCESS     read-only
        STATUS         current
        DESCRIPTION    "Indicates the functional type of this 112PDM11 port."
        ::= { tnOt112pdm11PortInfoEntry 1 }

--------------------------------------------------------------------------------
-- WTOCMA Optical Port Info Scalars
--------------------------------------------------------------------------------
    tnWtocmaPortInfoAttributeTotal OBJECT-TYPE
        SYNTAX         Integer32
        MAX-ACCESS     read-only
        STATUS         current
        DESCRIPTION    ""
        ::= { tnOpticalPortInfo 204 }

--------------------------------------------------------------------------------
-- WTOCMA Optical Port Info Table
--------------------------------------------------------------------------------
    tnWtocmaPortInfoTable OBJECT-TYPE
        SYNTAX         SEQUENCE OF TnWtocmaPortInfoEntry
        MAX-ACCESS     not-accessible
        STATUS         current
        DESCRIPTION    "The ports on a WTOCMA optical card."
        ::= { tnOpticalPortInfo 205 }

    tnWtocmaPortInfoEntry OBJECT-TYPE
        SYNTAX         TnWtocmaPortInfoEntry
        MAX-ACCESS     not-accessible
        STATUS         current
        DESCRIPTION    ""
        INDEX { ifIndex }
        ::= { tnWtocmaPortInfoTable 1 }

    TnWtocmaPortInfoEntry ::=
        SEQUENCE {
            tnWtocmaPortInfoFunction            INTEGER,
            tnWtocmaPortInfoPower               Integer32,
            tnWtocmaPortInfoPowerMonitoredPort  Integer32
        }

    tnWtocmaPortInfoFunction OBJECT-TYPE
        SYNTAX         INTEGER {
                         detect(1)
                       }
        MAX-ACCESS     read-only
        STATUS         current
        DESCRIPTION    "Indicates the functional type of this WTOCMA port."
        ::= { tnWtocmaPortInfoEntry 1 }

    tnWtocmaPortInfoPower OBJECT-TYPE
        SYNTAX         Integer32
        UNITS          "mBm"
        MAX-ACCESS     read-only
        STATUS         current
        DESCRIPTION    "The total power into the WTOCMA IN port."
        DEFVAL         { -9900 }
        ::= { tnWtocmaPortInfoEntry 2 }

    tnWtocmaPortInfoPowerMonitoredPort OBJECT-TYPE
        SYNTAX         Integer32
        UNITS          "mBm"
        MAX-ACCESS     read-only
        STATUS         current
        DESCRIPTION    "The total power out of the associated monitored
                        port."
        DEFVAL         { -9900 }
        ::= { tnWtocmaPortInfoEntry 3 }

--------------------------------------------------------------------------------
-- PTPCTL Optical Port Info Scalars
--------------------------------------------------------------------------------
    tnPtpctlPortInfoAttributeTotal OBJECT-TYPE
        SYNTAX         Integer32
        MAX-ACCESS     read-only
        STATUS         current
        DESCRIPTION    ""
        ::= { tnOpticalPortInfo 206 }

--------------------------------------------------------------------------------
-- PTPCTL Optical Port Info Table
--------------------------------------------------------------------------------
    tnPtpctlPortInfoTable OBJECT-TYPE
        SYNTAX         SEQUENCE OF TnPtpctlPortInfoEntry
        MAX-ACCESS     not-accessible
        STATUS         current
        DESCRIPTION    "The ports on a PTPCTL optical card."
        ::= { tnOpticalPortInfo 207 }

    tnPtpctlPortInfoEntry OBJECT-TYPE
        SYNTAX         TnPtpctlPortInfoEntry
        MAX-ACCESS     not-accessible
        STATUS         current
        DESCRIPTION    ""
        INDEX { ifIndex }
        ::= { tnPtpctlPortInfoTable 1 }

    TnPtpctlPortInfoEntry ::=
        SEQUENCE {
            tnPtpctlPortInfoFunction  INTEGER
        }

    tnPtpctlPortInfoFunction OBJECT-TYPE
        SYNTAX         INTEGER {
                         tp(1),
                         bits(2),
                         tod(3)
                       }
        MAX-ACCESS     read-only
        STATUS         current
        DESCRIPTION    "Indicates the functional type of this PTPCTL port."
        ::= { tnPtpctlPortInfoEntry 1 }

--------------------------------------------------------------------------------
-- PTPIO Optical Port Info Scalars
--------------------------------------------------------------------------------
    tnPtpioPortInfoAttributeTotal OBJECT-TYPE
        SYNTAX         Integer32
        MAX-ACCESS     read-only
        STATUS         current
        DESCRIPTION    ""
        ::= { tnOpticalPortInfo 208 }

--------------------------------------------------------------------------------
-- PTPIO Optical Port Info Table
--------------------------------------------------------------------------------
    tnPtpioPortInfoTable OBJECT-TYPE
        SYNTAX         SEQUENCE OF TnPtpioPortInfoEntry
        MAX-ACCESS     not-accessible
        STATUS         current
        DESCRIPTION    "The ports on a PTPIO optical card."
        ::= { tnOpticalPortInfo 209 }

    tnPtpioPortInfoEntry OBJECT-TYPE
        SYNTAX         TnPtpioPortInfoEntry
        MAX-ACCESS     not-accessible
        STATUS         current
        DESCRIPTION    ""
        INDEX { ifIndex }
        ::= { tnPtpioPortInfoTable 1 }

    TnPtpioPortInfoEntry ::=
        SEQUENCE {
            tnPtpioPortInfoFunction  INTEGER
        }

    tnPtpioPortInfoFunction OBJECT-TYPE
        SYNTAX         INTEGER {
                         tp(1),
                         line(2),
                         sig(3),
                         itp(4)
                       }
        MAX-ACCESS     read-only
        STATUS         current
        DESCRIPTION    "Indicates the functional type of this PTPIO port."
        ::= { tnPtpioPortInfoEntry 1 }

--------------------------------------------------------------------------------
-- 24ET1GB Optical Port Info Scalars
--------------------------------------------------------------------------------
    tnIo24et1gbPortInfoAttributeTotal OBJECT-TYPE
        SYNTAX         Integer32
        MAX-ACCESS     read-only
        STATUS         current
        DESCRIPTION    ""
        ::= { tnOpticalPortInfo 210 }

--------------------------------------------------------------------------------
-- 24ET1GB Optical Port Info Table
--------------------------------------------------------------------------------
    tnIo24et1gbPortInfoTable OBJECT-TYPE
        SYNTAX         SEQUENCE OF TnIo24et1gbPortInfoEntry
        MAX-ACCESS     not-accessible
        STATUS         current
        DESCRIPTION    "The ports on a 24ET1GB optical card."
        ::= { tnOpticalPortInfo 211 }

    tnIo24et1gbPortInfoEntry OBJECT-TYPE
        SYNTAX         TnIo24et1gbPortInfoEntry
        MAX-ACCESS     not-accessible
        STATUS         current
        DESCRIPTION    ""
        INDEX { ifIndex }
        ::= { tnIo24et1gbPortInfoTable 1 }

    TnIo24et1gbPortInfoEntry ::=
        SEQUENCE {
            tnIo24et1gbPortInfoFunction INTEGER
        }

    tnIo24et1gbPortInfoFunction OBJECT-TYPE
        SYNTAX         INTEGER {
                         network(1),
                         client(2)
                       }
        MAX-ACCESS     read-only
        STATUS         current
        DESCRIPTION    "Indicates the functional type of this 24ET1GB port."
        ::= { tnIo24et1gbPortInfoEntry 1 }

--------------------------------------------------------------------------------
-- 4AN10G Optical Port Info Scalars
--------------------------------------------------------------------------------
    tnIo4an10gPortInfoAttributeTotal OBJECT-TYPE
        SYNTAX         Integer32
        MAX-ACCESS     read-only
        STATUS         current
        DESCRIPTION    ""
        ::= { tnOpticalPortInfo 212 }

--------------------------------------------------------------------------------
-- 4AN10G Optical Port Info Table
--------------------------------------------------------------------------------
    tnIo4an10gPortInfoTable OBJECT-TYPE
        SYNTAX         SEQUENCE OF TnIo4an10gPortInfoEntry
        MAX-ACCESS     not-accessible
        STATUS         current
        DESCRIPTION    "The ports on a 4AN10G optical card."
        ::= { tnOpticalPortInfo 213 }

    tnIo4an10gPortInfoEntry OBJECT-TYPE
        SYNTAX         TnIo4an10gPortInfoEntry
        MAX-ACCESS     not-accessible
        STATUS         current
        DESCRIPTION    ""
        INDEX { ifIndex }
        ::= { tnIo4an10gPortInfoTable 1 }

    TnIo4an10gPortInfoEntry ::=
        SEQUENCE {
            tnIo4an10gPortInfoFunction INTEGER
        }

    tnIo4an10gPortInfoFunction OBJECT-TYPE
        SYNTAX         INTEGER {
                         network(1),
                         client(2)
                       }
        MAX-ACCESS     read-only
        STATUS         current
        DESCRIPTION    "Indicates the functional type of this 4AN10G port."
        ::= { tnIo4an10gPortInfoEntry 1 }

--------------------------------------------------------------------------------
-- 8ET1GB Optical Port Info Scalars
--------------------------------------------------------------------------------
    tnIo8et1gbPortInfoAttributeTotal OBJECT-TYPE
        SYNTAX         Integer32
        MAX-ACCESS     read-only
        STATUS         current
        DESCRIPTION    ""
        ::= { tnOpticalPortInfo 214 }

--------------------------------------------------------------------------------
-- 8ET1GB Optical Port Info Table
--------------------------------------------------------------------------------
    tnIo8et1gbPortInfoTable OBJECT-TYPE
        SYNTAX         SEQUENCE OF TnIo8et1gbPortInfoEntry
        MAX-ACCESS     not-accessible
        STATUS         current
        DESCRIPTION    "The ports on a 8ET1GB optical card."
        ::= { tnOpticalPortInfo 215 }

    tnIo8et1gbPortInfoEntry OBJECT-TYPE
        SYNTAX         TnIo8et1gbPortInfoEntry
        MAX-ACCESS     not-accessible
        STATUS         current
        DESCRIPTION    ""
        INDEX { ifIndex }
        ::= { tnIo8et1gbPortInfoTable 1 }

    TnIo8et1gbPortInfoEntry ::=
        SEQUENCE {
            tnIo8et1gbPortInfoFunction INTEGER
        }

    tnIo8et1gbPortInfoFunction OBJECT-TYPE
        SYNTAX         INTEGER {
                         network(1),
                         client(2)
                       }
        MAX-ACCESS     read-only
        STATUS         current
        DESCRIPTION    "Indicates the functional type of this 8ET1GB port."
        ::= { tnIo8et1gbPortInfoEntry 1 }

--------------------------------------------------------------------------------
-- 10ET10G Optical Port Info Scalars
--------------------------------------------------------------------------------
    tnIo10et10gPortInfoAttributeTotal OBJECT-TYPE
        SYNTAX         Integer32
        MAX-ACCESS     read-only
        STATUS         current
        DESCRIPTION    ""
        ::= { tnOpticalPortInfo 216 }

--------------------------------------------------------------------------------
-- 10ET10G Optical Port Info Table
--------------------------------------------------------------------------------
    tnIo10et10gPortInfoTable OBJECT-TYPE
        SYNTAX         SEQUENCE OF TnIo10et10gPortInfoEntry
        MAX-ACCESS     not-accessible
        STATUS         current
        DESCRIPTION    "The ports on a 10ET10G optical card."
        ::= { tnOpticalPortInfo 217 }

    tnIo10et10gPortInfoEntry OBJECT-TYPE
        SYNTAX         TnIo10et10gPortInfoEntry
        MAX-ACCESS     not-accessible
        STATUS         current
        DESCRIPTION    ""
        INDEX { ifIndex }
        ::= { tnIo10et10gPortInfoTable 1 }

    TnIo10et10gPortInfoEntry ::=
        SEQUENCE {
            tnIo10et10gPortInfoFunction INTEGER
        }

    tnIo10et10gPortInfoFunction OBJECT-TYPE
        SYNTAX         INTEGER {
                         network(1),
                         client(2)
                       }
        MAX-ACCESS     read-only
        STATUS         current
        DESCRIPTION    "Indicates the functional type of this 10ET10G port."
        ::= { tnIo10et10gPortInfoEntry 1 }

--------------------------------------------------------------------------------
-- UL11QCUPC Optical Port Info Scalars
--------------------------------------------------------------------------------
    tnUl11qcupcPortInfoAttributeTotal OBJECT-TYPE
        SYNTAX         Integer32
        MAX-ACCESS     read-only
        STATUS         current
        DESCRIPTION    ""
        ::= { tnOpticalPortInfo 218 }

--------------------------------------------------------------------------------
-- UL11QCUPC Optical Port Info Table
--------------------------------------------------------------------------------
    tnUl11qcupcPortInfoTable OBJECT-TYPE
        SYNTAX         SEQUENCE OF TnUl11qcupcPortInfoEntry
        MAX-ACCESS     not-accessible
        STATUS         current
        DESCRIPTION    "The ports on a UL11QCUPC optical card."
        ::= { tnOpticalPortInfo 219 }

    tnUl11qcupcPortInfoEntry OBJECT-TYPE
        SYNTAX         TnUl11qcupcPortInfoEntry
        MAX-ACCESS     not-accessible
        STATUS         current
        DESCRIPTION    ""
        INDEX { ifIndex }
        ::= { tnUl11qcupcPortInfoTable 1 }

    TnUl11qcupcPortInfoEntry ::=
        SEQUENCE {
            tnUl11qcupcPortInfoFunction INTEGER
        }

    tnUl11qcupcPortInfoFunction OBJECT-TYPE
        SYNTAX         INTEGER {
                         network(1),
                         evoa(2)
                       }
        MAX-ACCESS     read-only
        STATUS         current
        DESCRIPTION    "Indicates the functional type of this UL11QCUPC port."
        ::= { tnUl11qcupcPortInfoEntry 1 }

--------------------------------------------------------------------------------
-- 520SCX4 Optical Port Info Scalars
--------------------------------------------------------------------------------
    tnOt520scx4PortInfoAttributeTotal OBJECT-TYPE
        SYNTAX         Integer32
        MAX-ACCESS     read-only
        STATUS         current
        DESCRIPTION    ""
        ::= { tnOpticalPortInfo 220 }

--------------------------------------------------------------------------------
-- 520SCX4 Optical Port Info Table
--------------------------------------------------------------------------------
    tnOt520scx4PortInfoTable OBJECT-TYPE
        SYNTAX         SEQUENCE OF TnOt520scx4PortInfoEntry
        MAX-ACCESS     not-accessible
        STATUS         current
        DESCRIPTION    "The ports on a 520SCX4 optical card."
        ::= { tnOpticalPortInfo 221 }

    tnOt520scx4PortInfoEntry OBJECT-TYPE
        SYNTAX         TnOt520scx4PortInfoEntry
        MAX-ACCESS     not-accessible
        STATUS         current
        DESCRIPTION    ""
        INDEX { ifIndex }
        ::= { tnOt520scx4PortInfoTable 1 }

    TnOt520scx4PortInfoEntry ::=
        SEQUENCE {
            tnOt520scx4PortInfoFunction INTEGER
        }

    tnOt520scx4PortInfoFunction OBJECT-TYPE
        SYNTAX         INTEGER {
                         network(1),
                         client(2)
                       }
        MAX-ACCESS     read-only
        STATUS         current
        DESCRIPTION    "Indicates the functional type of this 520SCX4 port."
        ::= { tnOt520scx4PortInfoEntry 1 }

--------------------------------------------------------------------------------
-- Skew Info Table
--------------------------------------------------------------------------------
    tnSkewInfoTable OBJECT-TYPE
        SYNTAX         SEQUENCE OF TnSkewInfoEntry
        MAX-ACCESS     not-accessible
        STATUS         current
        DESCRIPTION    "."
        ::= { tnOpticalPortInfo 222 }

    tnSkewInfoEntry OBJECT-TYPE
        SYNTAX         TnSkewInfoEntry
        MAX-ACCESS     not-accessible
        STATUS         current
        DESCRIPTION    ""
        INDEX { ifIndex }
        ::= { tnSkewInfoTable 1 }

    TnSkewInfoEntry ::=
        SEQUENCE {
            tnSkewInfoString     OCTET STRING
         }

    tnSkewInfoString OBJECT-TYPE
        SYNTAX         OCTET STRING (SIZE(0..256))
        MAX-ACCESS     read-only
        STATUS         current
        DESCRIPTION    "The relative skew between the 20 logical lanes
                        on OTU4.  The string contains the skew for each
                        logical lane separated by spaces.

                        UNIT: ns"
        ::= { tnSkewInfoEntry 1 }

--------------------------------------------------------------------------------
-- Power Filter Port Info Scalars
--------------------------------------------------------------------------------
    tnPowerFilterPortInfoAttributeTotal OBJECT-TYPE
        SYNTAX         Integer32
        MAX-ACCESS     read-only
        STATUS         current
        DESCRIPTION    ""
        ::= { tnOpticalPortInfo 223 }

--------------------------------------------------------------------------------
-- Power Filter Port Info Table
--------------------------------------------------------------------------------
    tnPowerFilterPortInfoTable OBJECT-TYPE
        SYNTAX         SEQUENCE OF TnPowerFilterPortInfoEntry
        MAX-ACCESS     not-accessible
        STATUS         current
        DESCRIPTION    "The ports on a PowerFilter optical card."
        ::= { tnOpticalPortInfo 224 }

    tnPowerFilterPortInfoEntry OBJECT-TYPE
        SYNTAX         TnPowerFilterPortInfoEntry
        MAX-ACCESS     not-accessible
        STATUS         current
        DESCRIPTION    ""
        INDEX { ifIndex }
        ::= { tnPowerFilterPortInfoTable 1 }

    TnPowerFilterPortInfoEntry ::=
        SEQUENCE {
            tnPowerFilterPortInfoFunction INTEGER
        }

    tnPowerFilterPortInfoFunction OBJECT-TYPE
        SYNTAX         INTEGER {
                         oneTru(1)
                       }
        MAX-ACCESS     read-only
        STATUS         current
        DESCRIPTION    "Indicates the functional type of this PowerFilter port."
        ::= { tnPowerFilterPortInfoEntry 1 }

--------------------------------------------------------------------------------
-- 11OPE8 Optical Port Info Scalars
--------------------------------------------------------------------------------
    tn11ope8PortInfoAttributeTotal OBJECT-TYPE
        SYNTAX         Integer32
        MAX-ACCESS     read-only
        STATUS         current
        DESCRIPTION    ""
        ::= { tnOpticalPortInfo 225 }

--------------------------------------------------------------------------------
-- 11OPE8 Optical Port Info Table
--------------------------------------------------------------------------------
    tn11ope8PortInfoTable OBJECT-TYPE
        SYNTAX         SEQUENCE OF Tn11ope8PortInfoEntry
        MAX-ACCESS     not-accessible
        STATUS         current
        DESCRIPTION    "The ports on a 11OPE8 optical card."
        ::= { tnOpticalPortInfo 226 }

    tn11ope8PortInfoEntry OBJECT-TYPE
        SYNTAX         Tn11ope8PortInfoEntry
        MAX-ACCESS     not-accessible
        STATUS         current
        DESCRIPTION    ""
        INDEX { ifIndex }
        ::= { tn11ope8PortInfoTable 1 }

    Tn11ope8PortInfoEntry ::=
        SEQUENCE {
            tn11ope8PortInfoFunction INTEGER
        }

    tn11ope8PortInfoFunction OBJECT-TYPE
        SYNTAX         INTEGER {
                         network(1),
                         client(2),
                         evoa(3),
                         backplane(4),
                         tod(5)
                       }
        MAX-ACCESS     read-only
        STATUS         current
        DESCRIPTION    "Indicates the functional type of this 11OPE8 port."
        ::= { tn11ope8PortInfoEntry 1 }

--------------------------------------------------------------------------------
-- 11QCE12X Optical Port Info Scalars
--------------------------------------------------------------------------------
    tn11qce12xPortInfoAttributeTotal OBJECT-TYPE
        SYNTAX         Integer32
        MAX-ACCESS     read-only
        STATUS         current
        DESCRIPTION    ""
        ::= { tnOpticalPortInfo 227 }

--------------------------------------------------------------------------------
-- 11QCE12X Optical Port Info Table
--------------------------------------------------------------------------------
    tn11qce12xPortInfoTable OBJECT-TYPE
        SYNTAX         SEQUENCE OF Tn11qce12xPortInfoEntry
        MAX-ACCESS     not-accessible
        STATUS         current
        DESCRIPTION    "The ports on a 11QCE12X optical card."
        ::= { tnOpticalPortInfo 228 }

    tn11qce12xPortInfoEntry OBJECT-TYPE
        SYNTAX         Tn11qce12xPortInfoEntry
        MAX-ACCESS     not-accessible
        STATUS         current
        DESCRIPTION    ""
        INDEX { ifIndex }
        ::= { tn11qce12xPortInfoTable 1 }

    Tn11qce12xPortInfoEntry ::=
        SEQUENCE {
            tn11qce12xPortInfoFunction INTEGER
        }

    tn11qce12xPortInfoFunction OBJECT-TYPE
        SYNTAX         INTEGER {
                         network(1),
                         client(2),
                         evoa(3),
                         backplane(4),
                         tod(5)
                       }
        MAX-ACCESS     read-only
        STATUS         current
        DESCRIPTION    "Indicates the functional type of this 11QCE12X port."
        ::= { tn11qce12xPortInfoEntry 1 }

--------------------------------------------------------------------------------
-- AM2625A Optical Port Info Scalars
--------------------------------------------------------------------------------
    tnAm2625aPortInfoAttributeTotal OBJECT-TYPE
        SYNTAX         Integer32
        MAX-ACCESS     read-only
        STATUS         current
        DESCRIPTION    ""
        ::= { tnOpticalPortInfo 229 }

--------------------------------------------------------------------------------
-- AM2625A Optical Port Info Table
--------------------------------------------------------------------------------
    tnAm2625aPortInfoTable OBJECT-TYPE
        SYNTAX         SEQUENCE OF TnAm2625aPortInfoEntry
        MAX-ACCESS     not-accessible
        STATUS         current
        DESCRIPTION    "The ports on an AM2625A optical card."
        ::= { tnOpticalPortInfo 230 }

    tnAm2625aPortInfoEntry OBJECT-TYPE
        SYNTAX         TnAm2625aPortInfoEntry
        MAX-ACCESS     not-accessible
        STATUS         current
        DESCRIPTION    ""
        INDEX { ifIndex }
        ::= { tnAm2625aPortInfoTable 1 }

    TnAm2625aPortInfoEntry ::=
        SEQUENCE {
            tnAm2625aPortInfoFunction INTEGER
        }

    tnAm2625aPortInfoFunction OBJECT-TYPE
        SYNTAX         INTEGER {
                         lineIn(1),
                         inv(2),
                         dcm(3),
                         lineOut(4),
                         oscSfp(5),
                         det(6),
                         osc(7)
                       }
        MAX-ACCESS     read-only
        STATUS         current
        DESCRIPTION    "Indicates the functional type of this AM2625A port."
        ::= { tnAm2625aPortInfoEntry 1 }

--------------------------------------------------------------------------------
-- AM2032A Optical Port Info Scalars
--------------------------------------------------------------------------------
    tnAm2032aPortInfoAttributeTotal OBJECT-TYPE
        SYNTAX         Integer32
        MAX-ACCESS     read-only
        STATUS         current
        DESCRIPTION    ""
        ::= { tnOpticalPortInfo 231 }

--------------------------------------------------------------------------------
-- AM2032A Optical Port Info Table
--------------------------------------------------------------------------------
    tnAm2032aPortInfoTable OBJECT-TYPE
        SYNTAX         SEQUENCE OF TnAm2032aPortInfoEntry
        MAX-ACCESS     not-accessible
        STATUS         current
        DESCRIPTION    "The ports on an AM2032A optical card."
        ::= { tnOpticalPortInfo 232 }

    tnAm2032aPortInfoEntry OBJECT-TYPE
        SYNTAX         TnAm2032aPortInfoEntry
        MAX-ACCESS     not-accessible
        STATUS         current
        DESCRIPTION    ""
        INDEX { ifIndex }
        ::= { tnAm2032aPortInfoTable 1 }

    TnAm2032aPortInfoEntry ::=
        SEQUENCE {
            tnAm2032aPortInfoFunction INTEGER
        }

    tnAm2032aPortInfoFunction OBJECT-TYPE
        SYNTAX         INTEGER {
                         lineIn(1),
                         inv(2),
                         dcm(3),
                         lineOut(4),
                         oscSfp(5),
                         det(6),
                         osc(7)
                       }
        MAX-ACCESS     read-only
        STATUS         current
        DESCRIPTION    "Indicates the functional type of this AM2032A port."
        ::= { tnAm2032aPortInfoEntry 1 }

--------------------------------------------------------------------------------
-- OT260SCX2 Optical Port Info Scalars
--------------------------------------------------------------------------------
    tnOt260scx2PortInfoAttributeTotal OBJECT-TYPE
        SYNTAX         Integer32
        MAX-ACCESS     read-only
        STATUS         current
        DESCRIPTION    ""
        ::= { tnOpticalPortInfo 233 }

--------------------------------------------------------------------------------
-- OT260SCX2 Optical Port Info Table
--------------------------------------------------------------------------------
    tnOt260scx2PortInfoTable OBJECT-TYPE
        SYNTAX         SEQUENCE OF TnOt260scx2PortInfoEntry
        MAX-ACCESS     not-accessible
        STATUS         current
        DESCRIPTION    "The ports on a OT260SCX2 optical card."
        ::= { tnOpticalPortInfo 234 }

    tnOt260scx2PortInfoEntry OBJECT-TYPE
        SYNTAX         TnOt260scx2PortInfoEntry
        MAX-ACCESS     not-accessible
        STATUS         current
        DESCRIPTION    ""
        INDEX { ifIndex }
        ::= { tnOt260scx2PortInfoTable 1 }

    TnOt260scx2PortInfoEntry ::=
        SEQUENCE {
            tnOt260scx2PortInfoFunction INTEGER
        }

    tnOt260scx2PortInfoFunction OBJECT-TYPE
        SYNTAX         INTEGER {
                         network(1),
                         client(2)
                       }
        MAX-ACCESS     read-only
        STATUS         current
        DESCRIPTION    "Indicates the functional type of this OT260SCX2 port."
        ::= { tnOt260scx2PortInfoEntry 1 }

--------------------------------------------------------------------------------
-- OT130SNX10 Optical Port Info Scalars
--------------------------------------------------------------------------------
    tnOt130snx10PortInfoAttributeTotal OBJECT-TYPE
        SYNTAX         Integer32
        MAX-ACCESS     read-only
        STATUS         current
        DESCRIPTION    ""
        ::= { tnOpticalPortInfo 235 }

--------------------------------------------------------------------------------
-- OT130SNX10 Optical Port Info Table
--------------------------------------------------------------------------------
    tnOt130snx10PortInfoTable OBJECT-TYPE
        SYNTAX         SEQUENCE OF TnOt130snx10PortInfoEntry
        MAX-ACCESS     not-accessible
        STATUS         current
        DESCRIPTION    "The ports on a OT130SNX10 optical card."
        ::= { tnOpticalPortInfo 236 }

    tnOt130snx10PortInfoEntry OBJECT-TYPE
        SYNTAX         TnOt130snx10PortInfoEntry
        MAX-ACCESS     not-accessible
        STATUS         current
        DESCRIPTION    ""
        INDEX { ifIndex }
        ::= { tnOt130snx10PortInfoTable 1 }

    TnOt130snx10PortInfoEntry ::=
        SEQUENCE {
            tnOt130snx10PortInfoFunction  INTEGER
        }

    tnOt130snx10PortInfoFunction OBJECT-TYPE
        SYNTAX         INTEGER {
                         network(1),
                         client(2)
                       }
        MAX-ACCESS     read-only
        STATUS         current
        DESCRIPTION    "Indicates the functional type of this OT130SNX10 port."
        ::= { tnOt130snx10PortInfoEntry 1 }

--------------------------------------------------------------------------------
-- IO24ANMB Optical Port Info Scalars
--------------------------------------------------------------------------------
    tnIo24anmbPortInfoAttributeTotal OBJECT-TYPE
        SYNTAX         Integer32
        MAX-ACCESS     read-only
        STATUS         current
        DESCRIPTION    ""
        ::= { tnOpticalPortInfo 237 }

--------------------------------------------------------------------------------
-- IO24ANMB Optical Port Info Table
--------------------------------------------------------------------------------
    tnIo24anmbPortInfoTable OBJECT-TYPE
        SYNTAX         SEQUENCE OF TnIo24anmbPortInfoEntry
        MAX-ACCESS     not-accessible
        STATUS         current
        DESCRIPTION    "The ports on a IO24ANMB optical card."
        ::= { tnOpticalPortInfo 238 }

    tnIo24anmbPortInfoEntry OBJECT-TYPE
        SYNTAX         TnIo24anmbPortInfoEntry
        MAX-ACCESS     not-accessible
        STATUS         current
        DESCRIPTION    ""
        INDEX { ifIndex }
        ::= { tnIo24anmbPortInfoTable 1 }

    TnIo24anmbPortInfoEntry ::=
        SEQUENCE {
            tnIo24anmbPortInfoFunction INTEGER
        }

    tnIo24anmbPortInfoFunction OBJECT-TYPE
        SYNTAX         INTEGER {
                         client(1)
                       }
        MAX-ACCESS     read-only
        STATUS         current
        DESCRIPTION    "Indicates the functional type of this IO24ANMB port."
        ::= { tnIo24anmbPortInfoEntry 1 }

--------------------------------------------------------------------------------
-- OT11DPM8 Optical Port Info Scalars
--------------------------------------------------------------------------------
    tnOt11dpm8PortInfoAttributeTotal OBJECT-TYPE
        SYNTAX         Integer32
        MAX-ACCESS     read-only
        STATUS         current
        DESCRIPTION    ""
        ::= { tnOpticalPortInfo 239 }

--------------------------------------------------------------------------------
-- OT11DPM8 Optical Port Info Table
--------------------------------------------------------------------------------
    tnOt11dpm8PortInfoTable OBJECT-TYPE
        SYNTAX         SEQUENCE OF TnOt11dpm8PortInfoEntry
        MAX-ACCESS     not-accessible
        STATUS         current
        DESCRIPTION    "The ports on a OT11DPM8 optical card."
        ::= { tnOpticalPortInfo 240 }

    tnOt11dpm8PortInfoEntry OBJECT-TYPE
        SYNTAX         TnOt11dpm8PortInfoEntry
        MAX-ACCESS     not-accessible
        STATUS         current
        DESCRIPTION    ""
        INDEX { ifIndex }
        ::= { tnOt11dpm8PortInfoTable 1 }

    TnOt11dpm8PortInfoEntry ::=
        SEQUENCE {
            tnOt11dpm8PortInfoFunction INTEGER
        }

    tnOt11dpm8PortInfoFunction OBJECT-TYPE
        SYNTAX         INTEGER {
                         network(1),
                         client(2),
                         evoa(3)
                       }
        MAX-ACCESS     read-only
        STATUS         current
        DESCRIPTION    "Indicates the functional type of this OT11DPM8 port."
        ::= { tnOt11dpm8PortInfoEntry 1 }

--------------------------------------------------------------------------------
-- OT11DPM4M Optical Port Info Scalars
--------------------------------------------------------------------------------
    tnOt11dpm4mPortInfoAttributeTotal OBJECT-TYPE
        SYNTAX         Integer32
        MAX-ACCESS     read-only
        STATUS         current
        DESCRIPTION    ""
        ::= { tnOpticalPortInfo 241 }

--------------------------------------------------------------------------------
-- OT11DPM4M Optical Port Info Table
--------------------------------------------------------------------------------
    tnOt11dpm4mPortInfoTable OBJECT-TYPE
        SYNTAX         SEQUENCE OF TnOt11dpm4mPortInfoEntry
        MAX-ACCESS     not-accessible
        STATUS         current
        DESCRIPTION    "The ports on a OT11DPM4M optical card."
        ::= { tnOpticalPortInfo 242 }

    tnOt11dpm4mPortInfoEntry OBJECT-TYPE
        SYNTAX         TnOt11dpm4mPortInfoEntry
        MAX-ACCESS     not-accessible
        STATUS         current
        DESCRIPTION    ""
        INDEX { ifIndex }
        ::= { tnOt11dpm4mPortInfoTable 1 }

    TnOt11dpm4mPortInfoEntry ::=
        SEQUENCE {
            tnOt11dpm4mPortInfoFunction INTEGER
        }

    tnOt11dpm4mPortInfoFunction OBJECT-TYPE
        SYNTAX         INTEGER {
                         network(1),
                         client(2)
                       }
        MAX-ACCESS     read-only
        STATUS         current
        DESCRIPTION    "Indicates the functional type of this OT11DPM4M port."
        ::= { tnOt11dpm4mPortInfoEntry 1 }

--------------------------------------------------------------------------------
-- UL130SCUPB Optical Port Info Scalars
--------------------------------------------------------------------------------
    tnUl130scupbPortInfoAttributeTotal OBJECT-TYPE
        SYNTAX         Integer32
        MAX-ACCESS     read-only
        STATUS         current
        DESCRIPTION    ""
        ::= { tnOpticalPortInfo 243 }

--------------------------------------------------------------------------------
-- UL130SCUPB Optical Port Info Table
--------------------------------------------------------------------------------
    tnUl130scupbPortInfoTable OBJECT-TYPE
        SYNTAX         SEQUENCE OF TnUl130scupbPortInfoEntry
        MAX-ACCESS     not-accessible
        STATUS         current
        DESCRIPTION    "The ports on a UL130SCUPB optical card."
        ::= { tnOpticalPortInfo 244 }

    tnUl130scupbPortInfoEntry OBJECT-TYPE
        SYNTAX         TnUl130scupbPortInfoEntry
        MAX-ACCESS     not-accessible
        STATUS         current
        DESCRIPTION    ""
        INDEX { ifIndex }
        ::= { tnUl130scupbPortInfoTable 1 }

    TnUl130scupbPortInfoEntry ::=
        SEQUENCE {
            tnUl130scupbPortInfoFunction  INTEGER
        }

    tnUl130scupbPortInfoFunction OBJECT-TYPE
        SYNTAX         INTEGER {
                         network(1)
                       }
        MAX-ACCESS     read-only
        STATUS         current
        DESCRIPTION    "Indicates the functional type of this UL130SCUPB port."
        ::= { tnUl130scupbPortInfoEntry 1 }

--------------------------------------------------------------------------------
-- OT112SDX11 Optical Port Info Scalars
--------------------------------------------------------------------------------
    tnOt112sdx11PortInfoAttributeTotal OBJECT-TYPE
        SYNTAX         Integer32
        MAX-ACCESS     read-only
        STATUS         current
        DESCRIPTION    ""
        ::= { tnOpticalPortInfo 245 }

--------------------------------------------------------------------------------
-- OT112SDX11 Optical Port Info Table
--------------------------------------------------------------------------------
    tnOt112sdx11PortInfoTable OBJECT-TYPE
        SYNTAX         SEQUENCE OF TnOt112sdx11PortInfoEntry
        MAX-ACCESS     not-accessible
        STATUS         current
        DESCRIPTION    "The ports on a OT112SDX11 optical card."
        ::= { tnOpticalPortInfo 246 }

    tnOt112sdx11PortInfoEntry OBJECT-TYPE
        SYNTAX         TnOt112sdx11PortInfoEntry
        MAX-ACCESS     not-accessible
        STATUS         current
        DESCRIPTION    ""
        INDEX { ifIndex }
        ::= { tnOt112sdx11PortInfoTable 1 }

    TnOt112sdx11PortInfoEntry ::=
        SEQUENCE {
            tnOt112sdx11PortInfoFunction  INTEGER,
            tnOt112sdx11PortInfoAggrRate  INTEGER
        }

    tnOt112sdx11PortInfoFunction OBJECT-TYPE
        SYNTAX         INTEGER {
                         network(1),
                         client(2)
                       }
        MAX-ACCESS     read-only
        STATUS         current
        DESCRIPTION    "Indicates the functional type of this OT112SDX11 port."
        ::= { tnOt112sdx11PortInfoEntry 1 }

    tnOt112sdx11PortInfoAggrRate OBJECT-TYPE
        SYNTAX         INTEGER {
                         elan40Gb(1),
                         elan100Gb(2)
                       }
        MAX-ACCESS     read-only
        STATUS         current
        DESCRIPTION    "Indicates the Aggregation Ethernet signal rate
                        attached on the first lane of 112SDX11 client
                        ports."
        ::= { tnOt112sdx11PortInfoEntry 2 }

--------------------------------------------------------------------------------
-- AA2DONW Optical Port Info Scalars
--------------------------------------------------------------------------------
    tnAa2donwPortInfoAttributeTotal OBJECT-TYPE
        SYNTAX         Integer32
        MAX-ACCESS     read-only
        STATUS         current
        DESCRIPTION    ""
        ::= { tnOpticalPortInfo 247 }

--------------------------------------------------------------------------------
-- AA2DONW Optical Port Info Table
--------------------------------------------------------------------------------
    tnAa2donwPortInfoTable OBJECT-TYPE
        SYNTAX         SEQUENCE OF TnAa2donwPortInfoEntry
        MAX-ACCESS     not-accessible
        STATUS         current
        DESCRIPTION    "The ports on an AA2DONW optical card."
        ::= { tnOpticalPortInfo 248 }

    tnAa2donwPortInfoEntry OBJECT-TYPE
        SYNTAX         TnAa2donwPortInfoEntry
        MAX-ACCESS     not-accessible
        STATUS         current
        DESCRIPTION    ""
        INDEX { ifIndex }
        ::= { tnAa2donwPortInfoTable 1 }

    TnAa2donwPortInfoEntry ::=
        SEQUENCE {
            tnAa2donwPortInfoFunction  INTEGER
        }

    tnAa2donwPortInfoFunction OBJECT-TYPE
        SYNTAX         INTEGER {
                         line(1),
                         signal(2),
                         inv(3),
                         osc(4),
                         oscSfp(5)
                       }
        MAX-ACCESS     read-only
        STATUS         current
        DESCRIPTION    "Indicates the functional type of this AA2DONW port."
        ::= { tnAa2donwPortInfoEntry 1 }

--------------------------------------------------------------------------------
-- 130SCA1 Optical Port Info Scalars
--------------------------------------------------------------------------------
    tnOt130sca1PortInfoAttributeTotal OBJECT-TYPE
        SYNTAX         Integer32
        MAX-ACCESS     read-only
        STATUS         current
        DESCRIPTION    ""
        ::= { tnOpticalPortInfo 249 }

--------------------------------------------------------------------------------
-- 130SCA1 Optical Port Info Table
--------------------------------------------------------------------------------
    tnOt130sca1PortInfoTable OBJECT-TYPE
        SYNTAX         SEQUENCE OF TnOt130sca1PortInfoEntry
        MAX-ACCESS     not-accessible
        STATUS         current
        DESCRIPTION    "The ports on a 130SCA1 optical card."
        ::= { tnOpticalPortInfo 250 }

    tnOt130sca1PortInfoEntry OBJECT-TYPE
        SYNTAX         TnOt130sca1PortInfoEntry
        MAX-ACCESS     not-accessible
        STATUS         current
        DESCRIPTION    ""
        INDEX { ifIndex }
        ::= { tnOt130sca1PortInfoTable 1 }

    TnOt130sca1PortInfoEntry ::=
        SEQUENCE {
            tnOt130sca1PortInfoFunction INTEGER
        }

    tnOt130sca1PortInfoFunction OBJECT-TYPE
        SYNTAX         INTEGER {
                         network(1),
                         client(2)
                       }
        MAX-ACCESS     read-only
        STATUS         current
        DESCRIPTION    "Indicates the functional type of this 130SCA1 port."
        ::= { tnOt130sca1PortInfoEntry 1 }

--------------------------------------------------------------------------------
-- 10AN10GB Optical Port Info Scalars
--------------------------------------------------------------------------------
    tnIo10an10gbPortInfoAttributeTotal OBJECT-TYPE
        SYNTAX         Integer32
        MAX-ACCESS     read-only
        STATUS         current
        DESCRIPTION    ""
        ::= { tnOpticalPortInfo 251 }

--------------------------------------------------------------------------------
-- 10AN10GB Optical Port Info Table
--------------------------------------------------------------------------------
    tnIo10an10gbPortInfoTable OBJECT-TYPE
        SYNTAX         SEQUENCE OF TnIo10an10gbPortInfoEntry
        MAX-ACCESS     not-accessible
        STATUS         current
        DESCRIPTION    "The ports on a 10AN10GB optical card."
        ::= { tnOpticalPortInfo 252 }

    tnIo10an10gbPortInfoEntry OBJECT-TYPE
        SYNTAX         TnIo10an10gbPortInfoEntry
        MAX-ACCESS     not-accessible
        STATUS         current
        DESCRIPTION    ""
        INDEX { ifIndex }
        ::= { tnIo10an10gbPortInfoTable 1 }

    TnIo10an10gbPortInfoEntry ::=
        SEQUENCE {
            tnIo10an10gbPortInfoFunction INTEGER
        }

    tnIo10an10gbPortInfoFunction OBJECT-TYPE
        SYNTAX         INTEGER {
                         network(1),
                         client(2)
                       }
        MAX-ACCESS     read-only
        STATUS         current
        DESCRIPTION    "Indicates the functional type of this 10AN10GB port."
        ::= { tnIo10an10gbPortInfoEntry 1 }

--------------------------------------------------------------------------------
-- 10ET10GB Optical Port Info Scalars
--------------------------------------------------------------------------------
    tnIo10et10gbPortInfoAttributeTotal OBJECT-TYPE
        SYNTAX         Integer32
        MAX-ACCESS     read-only
        STATUS         current
        DESCRIPTION    ""
        ::= { tnOpticalPortInfo 253 }

--------------------------------------------------------------------------------
-- 10ET10GB Optical Port Info Table
--------------------------------------------------------------------------------
    tnIo10et10gbPortInfoTable OBJECT-TYPE
        SYNTAX         SEQUENCE OF TnIo10et10gbPortInfoEntry
        MAX-ACCESS     not-accessible
        STATUS         current
        DESCRIPTION    "The ports on a 10ET10GB optical card."
        ::= { tnOpticalPortInfo 254 }

    tnIo10et10gbPortInfoEntry OBJECT-TYPE
        SYNTAX         TnIo10et10gbPortInfoEntry
        MAX-ACCESS     not-accessible
        STATUS         current
        DESCRIPTION    ""
        INDEX { ifIndex }
        ::= { tnIo10et10gbPortInfoTable 1 }

    TnIo10et10gbPortInfoEntry ::=
        SEQUENCE {
            tnIo10et10gbPortInfoFunction INTEGER
        }

    tnIo10et10gbPortInfoFunction OBJECT-TYPE
        SYNTAX         INTEGER {
                         network(1),
                         client(2)
                       }
        MAX-ACCESS     read-only
        STATUS         current
        DESCRIPTION    "Indicates the functional type of this 10ET10GB port."
        ::= { tnIo10et10gbPortInfoEntry 1 }

--------------------------------------------------------------------------------
-- WR20-TF Optical Port Info Scalars
--------------------------------------------------------------------------------
    tnWr20tfPortInfoAttributeTotal OBJECT-TYPE
        SYNTAX         Integer32
        MAX-ACCESS     read-only
        STATUS         current
        DESCRIPTION    ""
        ::= { tnOpticalPortInfo 255 }

--------------------------------------------------------------------------------
-- WR20-TF Optical Port Info Table
--------------------------------------------------------------------------------
    tnWr20tfPortInfoTable OBJECT-TYPE
        SYNTAX         SEQUENCE OF TnWr20tfPortInfoEntry
        MAX-ACCESS     not-accessible
        STATUS         current
        DESCRIPTION    "The ports on a WR20-TF optical card."
        ::= { tnOpticalPortInfo 256 }

    tnWr20tfPortInfoEntry OBJECT-TYPE
        SYNTAX         TnWr20tfPortInfoEntry
        MAX-ACCESS     not-accessible
        STATUS         current
        DESCRIPTION    ""
        INDEX { ifIndex }
        ::= { tnWr20tfPortInfoTable 1 }

    TnWr20tfPortInfoEntry ::=
        SEQUENCE {
            tnWr20tfPortInfoFunction INTEGER
        }

    tnWr20tfPortInfoFunction OBJECT-TYPE
        SYNTAX         INTEGER {
                         signal(1),
                         adt(2),
                         ad(3),
                         inv(4)
                       }
        MAX-ACCESS     read-only
        STATUS         current
        DESCRIPTION    "Indicates the functional type of this WR20-TF port."
        ::= { tnWr20tfPortInfoEntry 1 }

--------------------------------------------------------------------------------
-- WSS Optical Port Info Scalars
--------------------------------------------------------------------------------
    tnWssPortInfoAttributeTotal OBJECT-TYPE
        SYNTAX         Integer32
        MAX-ACCESS     read-only
        STATUS         current
        DESCRIPTION    ""
        ::= { tnOpticalPortInfo 257 }

--------------------------------------------------------------------------------
-- WSS Optical Port Info Table
--------------------------------------------------------------------------------
    tnWssPortInfoTable OBJECT-TYPE
        SYNTAX         SEQUENCE OF TnWssPortInfoEntry
        MAX-ACCESS     not-accessible
        STATUS         current
        DESCRIPTION    "The ports on a WSS optical card."
        ::= { tnOpticalPortInfo 258 }

    tnWssPortInfoEntry OBJECT-TYPE
        SYNTAX         TnWssPortInfoEntry
        MAX-ACCESS     not-accessible
        STATUS         current
        DESCRIPTION    ""
        INDEX { ifIndex }
        ::= { tnWssPortInfoTable 1 }

    TnWssPortInfoEntry ::=
        SEQUENCE {
            tnWssPortInfoRelativeAttenuationMinIn       Unsigned32,
            tnWssPortInfoRelativeAttenuationMinOut      Unsigned32,
            tnWssPortInfoRelativeAverageAttenuationIn   Unsigned32,
            tnWssPortInfoRelativeAverageAttenuationOut  Unsigned32,
            tnWssPortInfoLossFromInToCommon             Integer32,
            tnWssPortInfoCurrentLossFromInToCommon      Integer32
        }

    tnWssPortInfoRelativeAttenuationMinIn OBJECT-TYPE
        SYNTAX         Unsigned32
        UNITS          "mB"
        MAX-ACCESS     read-only
        STATUS         current
        DESCRIPTION    "WR20-TF: The minimum attenuation on the WSS for
                                 the channels on the ADT or AD In port
                                 to SIG Out path.

                        Current range: 0 to 1500."
        DEFVAL         { 0 }
        ::= { tnWssPortInfoEntry 1 }

    tnWssPortInfoRelativeAttenuationMinOut OBJECT-TYPE
        SYNTAX         Unsigned32
        UNITS          "mB"
        MAX-ACCESS     read-only
        STATUS         current
        DESCRIPTION    "WR20-TF: The minimum attenuation on the WSS for
                                 the channels on the Sig In to ADT or AD
                                 Out port path.

                        Current range: 0 to 1500."
        DEFVAL         { 0 }
        ::= { tnWssPortInfoEntry 2 }

    tnWssPortInfoRelativeAverageAttenuationIn OBJECT-TYPE
        SYNTAX         Unsigned32
        UNITS          "mB"
        MAX-ACCESS     read-only
        STATUS         current
        DESCRIPTION    "WR20-TF: The average attenuation on the WSS for
                                 the channels on the ADT or AD In port
                                 to SIG Out path.

                        Current range: 0 to 1500."
        ::= { tnWssPortInfoEntry 3 }

    tnWssPortInfoRelativeAverageAttenuationOut OBJECT-TYPE
        SYNTAX         Unsigned32
        UNITS          "mB"
        MAX-ACCESS     read-only
        STATUS         current
        DESCRIPTION    "WR20-TF: The average attenuation on the WSS for
                                 the channels on the Sig In to ADT or
                                 AD Out port path.

                        Current range: 0 to 1500."
        ::= { tnWssPortInfoEntry 4 }

    tnWssPortInfoLossFromInToCommon OBJECT-TYPE
        SYNTAX         Integer32
        UNITS          "mB"
        MAX-ACCESS     read-only
        STATUS         current
        DESCRIPTION    "The measured loss during commissioning from input
                        port to SIG Out

                        Current range: -9900 to 9900."
        DEFVAL         { -9900 }
        ::= { tnWssPortInfoEntry 5 }

    tnWssPortInfoCurrentLossFromInToCommon OBJECT-TYPE
        SYNTAX         Integer32
        UNITS          "mB"
        MAX-ACCESS     read-only
        STATUS         current
        DESCRIPTION    "The most recent measured loss from input port
                        to SIG Out.

                        Current range: -9900 to 9900."
        DEFVAL         { -9900 }
        ::= { tnWssPortInfoEntry 6 }

--------------------------------------------------------------------------------
-- WTOCMF Optical Port Info Scalars
--------------------------------------------------------------------------------
    tnWtocmfPortInfoAttributeTotal OBJECT-TYPE
        SYNTAX         Integer32
        MAX-ACCESS     read-only
        STATUS         current
        DESCRIPTION    ""
        ::= { tnOpticalPortInfo 259 }

--------------------------------------------------------------------------------
-- WTOCMF Optical Port Info Table
--------------------------------------------------------------------------------
    tnWtocmfPortInfoTable OBJECT-TYPE
        SYNTAX         SEQUENCE OF TnWtocmfPortInfoEntry
        MAX-ACCESS     not-accessible
        STATUS         current
        DESCRIPTION    "The ports on a WTOCMF optical card."
        ::= { tnOpticalPortInfo 260 }

    tnWtocmfPortInfoEntry OBJECT-TYPE
        SYNTAX         TnWtocmfPortInfoEntry
        MAX-ACCESS     not-accessible
        STATUS         current
        DESCRIPTION    ""
        INDEX { ifIndex }
        ::= { tnWtocmfPortInfoTable 1 }

    TnWtocmfPortInfoEntry ::=
        SEQUENCE {
            tnWtocmfPortInfoFunction  INTEGER
        }

    tnWtocmfPortInfoFunction OBJECT-TYPE
        SYNTAX         INTEGER {
                         detect(1)
                       }
        MAX-ACCESS     read-only
        STATUS         current
        DESCRIPTION    "Indicates the functional type of this WTOCMF port."
        ::= { tnWtocmfPortInfoEntry 1 }

--------------------------------------------------------------------------------
-- ASWG Optical Port Info Scalars
--------------------------------------------------------------------------------
    tnAswgPortInfoAttributeTotal OBJECT-TYPE
        SYNTAX         Integer32
        MAX-ACCESS     read-only
        STATUS         current
        DESCRIPTION    ""
        ::= { tnOpticalPortInfo 261 }

--------------------------------------------------------------------------------
-- ASWG Optical Port Info Table
--------------------------------------------------------------------------------
    tnAswgPortInfoTable OBJECT-TYPE
        SYNTAX         SEQUENCE OF TnAswgPortInfoEntry
        MAX-ACCESS     not-accessible
        STATUS         current
        DESCRIPTION    "The ports on a ASWG optical card."
        ::= { tnOpticalPortInfo 262 }

    tnAswgPortInfoEntry OBJECT-TYPE
        SYNTAX         TnAswgPortInfoEntry
        MAX-ACCESS     not-accessible
        STATUS         current
        DESCRIPTION    ""
        INDEX { ifIndex }
        ::= { tnAswgPortInfoTable 1 }

    TnAswgPortInfoEntry ::=
        SEQUENCE {
            tnAswgPortInfoFunction  INTEGER
        }

    tnAswgPortInfoFunction OBJECT-TYPE
        SYNTAX         INTEGER {
                         lineIn(1),
                         otdrRx(2),
                         otdrTx(3),
                         lineOut(4),
                         oscSfp(5),
                         osc(6)
                       }
        MAX-ACCESS     read-only
        STATUS         current
        DESCRIPTION    "Indicates the functional type of this ASWG port."
        ::= { tnAswgPortInfoEntry 1 }

--------------------------------------------------------------------------------
-- A4PSWG Optical Port Info Scalars
--------------------------------------------------------------------------------
    tnA4pswgPortInfoAttributeTotal OBJECT-TYPE
        SYNTAX         Integer32
        MAX-ACCESS     read-only
        STATUS         current
        DESCRIPTION    ""
        ::= { tnOpticalPortInfo 263 }

--------------------------------------------------------------------------------
-- A4PSWG Optical Port Info Table
--------------------------------------------------------------------------------
    tnA4pswgPortInfoTable OBJECT-TYPE
        SYNTAX         SEQUENCE OF TnA4pswgPortInfoEntry
        MAX-ACCESS     not-accessible
        STATUS         current
        DESCRIPTION    "The ports on a A4PSWG optical card."
        ::= { tnOpticalPortInfo 264 }

    tnA4pswgPortInfoEntry OBJECT-TYPE
        SYNTAX         TnA4pswgPortInfoEntry
        MAX-ACCESS     not-accessible
        STATUS         current
        DESCRIPTION    ""
        INDEX { ifIndex }
        ::= { tnA4pswgPortInfoTable 1 }

    TnA4pswgPortInfoEntry ::=
        SEQUENCE {
            tnA4pswgPortInfoFunction  INTEGER
        }

    tnA4pswgPortInfoFunction OBJECT-TYPE
        SYNTAX         INTEGER {
                         lineIn(1),
                         otdrRx(2),
                         otdrTx(3),
                         lineOut(4),
                         oscSfp(5),
                         osc(6)
                       }
        MAX-ACCESS     read-only
        STATUS         current
        DESCRIPTION    "Indicates the functional type of this A4PSWG port."
        ::= { tnA4pswgPortInfoEntry 1 }

--------------------------------------------------------------------------------
-- OTDR(Optical Time Domain Reflectometer) Optical Port Info Scalars
--------------------------------------------------------------------------------
    tnOtdrPortInfoAttributeTotal OBJECT-TYPE
        SYNTAX         Integer32
        MAX-ACCESS     read-only
        STATUS         current
        DESCRIPTION    ""
        ::= { tnOpticalPortInfo 265 }

--------------------------------------------------------------------------------
-- OTDR(Optical Time Domain Reflectometer) Optical Port Info Table
--------------------------------------------------------------------------------
    tnOtdrPortInfoTable OBJECT-TYPE
        SYNTAX         SEQUENCE OF TnOtdrPortInfoEntry
        MAX-ACCESS     not-accessible
        STATUS         current
        DESCRIPTION    "The ports on an OTDR optical card."
        ::= { tnOpticalPortInfo 266 }

    tnOtdrPortInfoEntry OBJECT-TYPE
        SYNTAX         TnOtdrPortInfoEntry
        MAX-ACCESS     not-accessible
        STATUS         current
        DESCRIPTION    ""
        INDEX { ifIndex }
        ::= { tnOtdrPortInfoTable 1 }

    TnOtdrPortInfoEntry ::=
        SEQUENCE {
            tnOtdrPortInfoFunction INTEGER
        }

    tnOtdrPortInfoFunction OBJECT-TYPE
        SYNTAX         INTEGER {
                         px(1)
                       }
        MAX-ACCESS     read-only
        STATUS         current
        DESCRIPTION    "Indicates the functional type of this OTDR port."
        ::= { tnOtdrPortInfoEntry 1 }

--------------------------------------------------------------------------------
-- WR20-TFM Optical Port Info Scalars
--------------------------------------------------------------------------------
    tnWr20tfmPortInfoAttributeTotal OBJECT-TYPE
        SYNTAX         Integer32
        MAX-ACCESS     read-only
        STATUS         current
        DESCRIPTION    ""
        ::= { tnOpticalPortInfo 267 }

--------------------------------------------------------------------------------
-- WR20-TFM Optical Port Info Table
--------------------------------------------------------------------------------
    tnWr20tfmPortInfoTable OBJECT-TYPE
        SYNTAX         SEQUENCE OF TnWr20tfmPortInfoEntry
        MAX-ACCESS     not-accessible
        STATUS         current
        DESCRIPTION    "The ports on an WR20-TFM optical card."
        ::= { tnOpticalPortInfo 268 }

    tnWr20tfmPortInfoEntry OBJECT-TYPE
        SYNTAX         TnWr20tfmPortInfoEntry
        MAX-ACCESS     not-accessible
        STATUS         current
        DESCRIPTION    ""
        INDEX { ifIndex }
        ::= { tnWr20tfmPortInfoTable 1 }

    TnWr20tfmPortInfoEntry ::=
        SEQUENCE {
            tnWr20tfmPortInfoFunction      INTEGER,
            tnWr20tfmPortInfoTestingActive TruthValue
        }

    tnWr20tfmPortInfoFunction OBJECT-TYPE
        SYNTAX         INTEGER {
                         signal(1),
                         adt(2),
                         ad(3),
                         inv(4),
                         mpoDropOut(5),
                         mpoAddIn(6)
                       }
        MAX-ACCESS     read-only
        STATUS         current
        DESCRIPTION    "Indicates the functional type of this WR20-TFM port."
        ::= { tnWr20tfmPortInfoEntry 1 }

    tnWr20tfmPortInfoTestingActive OBJECT-TYPE
        SYNTAX         TruthValue
        MAX-ACCESS     read-only
        STATUS         current
        DESCRIPTION    "Node sets to true when testing in progress
                        on port (logic)."
        DEFVAL         { false } 
        ::= { tnWr20tfmPortInfoEntry 2 }

--------------------------------------------------------------------------------
-- AAR-8A Optical Port Info Scalars
--------------------------------------------------------------------------------
    tnAar8aPortInfoAttributeTotal OBJECT-TYPE
        SYNTAX         Integer32
        MAX-ACCESS     read-only
        STATUS         current
        DESCRIPTION    ""
        ::= { tnOpticalPortInfo 269 }

--------------------------------------------------------------------------------
-- AAR-8A Optical Port Info Table
--------------------------------------------------------------------------------
    tnAar8aPortInfoTable OBJECT-TYPE
        SYNTAX         SEQUENCE OF TnAar8aPortInfoEntry
        MAX-ACCESS     not-accessible
        STATUS         current
        DESCRIPTION    "The ports on an AAR-8A optical card."
        ::= { tnOpticalPortInfo 270 }

    tnAar8aPortInfoEntry OBJECT-TYPE
        SYNTAX         TnAar8aPortInfoEntry
        MAX-ACCESS     not-accessible
        STATUS         current
        DESCRIPTION    ""
        INDEX { ifIndex }
        ::= { tnAar8aPortInfoTable 1 }

    TnAar8aPortInfoEntry ::=
        SEQUENCE {
            tnAar8aPortInfoFunction   INTEGER
        }

    tnAar8aPortInfoFunction OBJECT-TYPE
        SYNTAX         INTEGER {
                         ampIn(1),
                         ampOut(2),
                         mpoFsm(3),
                         mpoMcs(4)
                       }
        MAX-ACCESS     read-only
        STATUS         current
        DESCRIPTION    "Indicates the functional type of this AAR-8A port."
        ::= { tnAar8aPortInfoEntry 1 }

--------------------------------------------------------------------------------
-- MCS8-16 Optical Port Info Scalars
--------------------------------------------------------------------------------
    tnMcs8x16PortInfoAttributeTotal OBJECT-TYPE
        SYNTAX         Integer32
        MAX-ACCESS     read-only
        STATUS         current
        DESCRIPTION    ""
        ::= { tnOpticalPortInfo 271 }

--------------------------------------------------------------------------------
-- MCS8-16 Optical Port Info Table
--------------------------------------------------------------------------------
    tnMcs8x16PortInfoTable OBJECT-TYPE
        SYNTAX         SEQUENCE OF TnMcs8x16PortInfoEntry
        MAX-ACCESS     not-accessible
        STATUS         current
        DESCRIPTION    "The ports on an MCS8-16 optical card."
        ::= { tnOpticalPortInfo 272 }

    tnMcs8x16PortInfoEntry OBJECT-TYPE
        SYNTAX         TnMcs8x16PortInfoEntry
        MAX-ACCESS     not-accessible
        STATUS         current
        DESCRIPTION    ""
        INDEX { ifIndex }
        ::= { tnMcs8x16PortInfoTable 1 }

    TnMcs8x16PortInfoEntry ::=
        SEQUENCE {
            tnMcs8x16PortInfoFunction                  INTEGER,
            tnMcs8x16PortInfoAddInsertionLossToSig1    Unsigned32,
            tnMcs8x16PortInfoAddInsertionLossToSig2    Unsigned32,
            tnMcs8x16PortInfoAddInsertionLossToSig3    Unsigned32,
            tnMcs8x16PortInfoAddInsertionLossToSig4    Unsigned32,
            tnMcs8x16PortInfoAddInsertionLossToSig5    Unsigned32,
            tnMcs8x16PortInfoAddInsertionLossToSig6    Unsigned32,
            tnMcs8x16PortInfoAddInsertionLossToSig7    Unsigned32,
            tnMcs8x16PortInfoAddInsertionLossToSig8    Unsigned32,
            tnMcs8x16PortInfoDropInsertionLossFromSig1 Unsigned32,
            tnMcs8x16PortInfoDropInsertionLossFromSig2 Unsigned32,
            tnMcs8x16PortInfoDropInsertionLossFromSig3 Unsigned32,
            tnMcs8x16PortInfoDropInsertionLossFromSig4 Unsigned32,
            tnMcs8x16PortInfoDropInsertionLossFromSig5 Unsigned32,
            tnMcs8x16PortInfoDropInsertionLossFromSig6 Unsigned32,
            tnMcs8x16PortInfoDropInsertionLossFromSig7 Unsigned32,
            tnMcs8x16PortInfoDropInsertionLossFromSig8 Unsigned32
        }

    tnMcs8x16PortInfoFunction OBJECT-TYPE
        SYNTAX         INTEGER {
                         signal(1),
                         ad(2),
                         mpoAar(3)
                       }
        MAX-ACCESS     read-only
        STATUS         current
        DESCRIPTION    "Indicates the functional type of this
                        MCS8-16 port."
        ::= { tnMcs8x16PortInfoEntry 1 }

    tnMcs8x16PortInfoAddInsertionLossToSig1 OBJECT-TYPE
        SYNTAX         Unsigned32
        UNITS          "mB"
        MAX-ACCESS     read-only
        STATUS         current
        DESCRIPTION    "Insertion loss to port SIG1 when disposed
                        to this path.  Add direction.

                        Current range: 0 to 2000."
        DEFVAL         { 1600 }
        ::= { tnMcs8x16PortInfoEntry 2 }

    tnMcs8x16PortInfoAddInsertionLossToSig2 OBJECT-TYPE
        SYNTAX         Unsigned32
        UNITS          "mB"
        MAX-ACCESS     read-only
        STATUS         current
        DESCRIPTION    "Insertion loss to port SIG2 when disposed
                        to this path.  Add direction.

                        Current range: 0 to 2000."
        DEFVAL         { 1600 }
        ::= { tnMcs8x16PortInfoEntry 3 }

    tnMcs8x16PortInfoAddInsertionLossToSig3 OBJECT-TYPE
        SYNTAX         Unsigned32
        UNITS          "mB"
        MAX-ACCESS     read-only
        STATUS         current
        DESCRIPTION    "Insertion loss to port SIG3 when disposed
                        to this path.  Add direction.  Applies to
                        NxM MCS where N>=3.

                        Current range: 0 to 2000."
        DEFVAL         { 1600 }
        ::= { tnMcs8x16PortInfoEntry 4 }

    tnMcs8x16PortInfoAddInsertionLossToSig4 OBJECT-TYPE
        SYNTAX         Unsigned32
        UNITS          "mB"
        MAX-ACCESS     read-only
        STATUS         current
        DESCRIPTION    "Insertion loss to port SIG4 when disposed
                        to this path. Add direction.  Applies to
                        NxM MCS where N>=4.

                        Current range: 0 to 2000."
        DEFVAL         { 1600 }
        ::= { tnMcs8x16PortInfoEntry 5 }

    tnMcs8x16PortInfoAddInsertionLossToSig5 OBJECT-TYPE
        SYNTAX         Unsigned32
        UNITS          "mB"
        MAX-ACCESS     read-only
        STATUS         current
        DESCRIPTION    "Insertion loss to port SIG5 when disposed
                        to this path.  Add direction.  Applies to
                        NxM MCS where N>=5.

                        Current range: 0 to 2000."
        DEFVAL         { 1600 }
        ::= { tnMcs8x16PortInfoEntry 6 }

    tnMcs8x16PortInfoAddInsertionLossToSig6 OBJECT-TYPE
        SYNTAX         Unsigned32
        UNITS          "mB"
        MAX-ACCESS     read-only
        STATUS         current
        DESCRIPTION    "Insertion loss to port SIG6 when disposed
                        to this path.  Add direction.  Applies to
                        NxM MCS where N>=6.

                        Current range: 0 to 2000."
        DEFVAL         { 1600 }
        ::= { tnMcs8x16PortInfoEntry 7 }

    tnMcs8x16PortInfoAddInsertionLossToSig7 OBJECT-TYPE
        SYNTAX         Unsigned32
        UNITS          "mB"
        MAX-ACCESS     read-only
        STATUS         current
        DESCRIPTION    "Insertion loss to port SIG7 when disposed
                        to this path.  Add direction.  Applies to
                        NxM MCS where N>=7.

                        Current range: 0 to 2000."
        DEFVAL         { 1600 }
        ::= { tnMcs8x16PortInfoEntry 8 }

    tnMcs8x16PortInfoAddInsertionLossToSig8 OBJECT-TYPE
        SYNTAX         Unsigned32
        UNITS          "mB"
        MAX-ACCESS     read-only
        STATUS         current
        DESCRIPTION    "Insertion loss to port SIG8 when disposed
                        to this path.  Add direction.  Applies to
                        NxM MCS where N>=8.

                        Current range: 0 to 2000."
        DEFVAL         { 1600 }
        ::= { tnMcs8x16PortInfoEntry 9 }

    tnMcs8x16PortInfoDropInsertionLossFromSig1 OBJECT-TYPE
        SYNTAX         Unsigned32
        UNITS          "mB"
        MAX-ACCESS     read-only
        STATUS         current
        DESCRIPTION    "Insertion loss from port SIG1 when disposed
                        to this path.  Drop direction.

                        Current range: 0 to 2000."
        DEFVAL         { 1600 }
        ::= { tnMcs8x16PortInfoEntry 10 }

    tnMcs8x16PortInfoDropInsertionLossFromSig2 OBJECT-TYPE
        SYNTAX         Unsigned32
        UNITS          "mB"
        MAX-ACCESS     read-only
        STATUS         current
        DESCRIPTION    "Insertion loss from port SIG2 when disposed
                        to this path.  Drop direction.

                        Current range: 0 to 2000."
        DEFVAL         { 1600 }
        ::= { tnMcs8x16PortInfoEntry 11 }

    tnMcs8x16PortInfoDropInsertionLossFromSig3 OBJECT-TYPE
        SYNTAX         Unsigned32
        UNITS          "mB"
        MAX-ACCESS     read-only
        STATUS         current
        DESCRIPTION    "Insertion loss from port SIG3 when disposed
                        to this path.  Drop direction.

                        Current range: 0 to 2000."
        DEFVAL         { 1600 }
        ::= { tnMcs8x16PortInfoEntry 12 }

    tnMcs8x16PortInfoDropInsertionLossFromSig4 OBJECT-TYPE
        SYNTAX         Unsigned32
        UNITS          "mB"
        MAX-ACCESS     read-only
        STATUS         current
        DESCRIPTION    "Insertion loss from port SIG4 when disposed
                        to this path.  Drop direction.

                        Current range: 0 to 2000."
        DEFVAL         { 1600 }
        ::= { tnMcs8x16PortInfoEntry 13 }

    tnMcs8x16PortInfoDropInsertionLossFromSig5 OBJECT-TYPE
        SYNTAX         Unsigned32
        UNITS          "mB"
        MAX-ACCESS     read-only
        STATUS         current
        DESCRIPTION    "Insertion loss from port SIG5 when disposed
                        to this path.  Drop direction.

                        Current range: 0 to 2000."
        DEFVAL         { 1600 }
        ::= { tnMcs8x16PortInfoEntry 14 }

    tnMcs8x16PortInfoDropInsertionLossFromSig6 OBJECT-TYPE
        SYNTAX         Unsigned32
        UNITS          "mB"
        MAX-ACCESS     read-only
        STATUS         current
        DESCRIPTION    "Insertion loss from port SIG6 when disposed
                        to this path.  Drop direction.

                        Current range: 0 to 2000."
        DEFVAL         { 1600 }
        ::= { tnMcs8x16PortInfoEntry 15 }

    tnMcs8x16PortInfoDropInsertionLossFromSig7 OBJECT-TYPE
        SYNTAX         Unsigned32
        UNITS          "mB"
        MAX-ACCESS     read-only
        STATUS         current
        DESCRIPTION    "Insertion loss from port SIG7 when disposed
                        to this path.  Drop direction.

                        Current range: 0 to 2000."
        DEFVAL         { 1600 }
        ::= { tnMcs8x16PortInfoEntry 16 }

    tnMcs8x16PortInfoDropInsertionLossFromSig8 OBJECT-TYPE
        SYNTAX         Unsigned32
        UNITS          "mB"
        MAX-ACCESS     read-only
        STATUS         current
        DESCRIPTION    "Insertion loss from port SIG8 when disposed
                        to this path.  Drop direction.

                        Current range: 0 to 2000."
        DEFVAL         { 1600 }
        ::= { tnMcs8x16PortInfoEntry 17 }

--------------------------------------------------------------------------------
-- MSH8-FSM Optical Port Info Scalars
--------------------------------------------------------------------------------
    tnMsh8fsmPortInfoAttributeTotal OBJECT-TYPE
        SYNTAX         Integer32
        MAX-ACCESS     read-only
        STATUS         current
        DESCRIPTION    ""
        ::= { tnOpticalPortInfo 273 }

--------------------------------------------------------------------------------
-- MSH8-FSM Optical Port Info Table
--------------------------------------------------------------------------------
    tnMsh8fsmPortInfoTable OBJECT-TYPE
        SYNTAX         SEQUENCE OF TnMsh8fsmPortInfoEntry
        MAX-ACCESS     not-accessible
        STATUS         current
        DESCRIPTION    "The ports on an MSH8-FSM optical card."
        ::= { tnOpticalPortInfo 274 }

    tnMsh8fsmPortInfoEntry OBJECT-TYPE
        SYNTAX         TnMsh8fsmPortInfoEntry
        MAX-ACCESS     not-accessible
        STATUS         current
        DESCRIPTION    ""
        INDEX { ifIndex }
        ::= { tnMsh8fsmPortInfoTable 1 }

    TnMsh8fsmPortInfoEntry ::=
        SEQUENCE {
            tnMsh8fsmPortInfoFunction   INTEGER
        }

    tnMsh8fsmPortInfoFunction OBJECT-TYPE
        SYNTAX         INTEGER {
                         mpoWssDropIn(1),
                         mpoWssAddOut(2),
                         mpoWssAd(3),
                         expIn(4),
                         expOut(5)
                       }
        MAX-ACCESS     read-only
        STATUS         current
        DESCRIPTION    "Indicates the functional type of this MSH8-FSM port."
        ::= { tnMsh8fsmPortInfoEntry 1 }

--------------------------------------------------------------------------------
-- Multi Cast Switch Port Info Scalars
--------------------------------------------------------------------------------
    tnMcsPortInfoAttributeTotal OBJECT-TYPE
        SYNTAX         Integer32
        MAX-ACCESS     read-only
        STATUS         current
        DESCRIPTION    ""
        ::= { tnOpticalPortInfo 275 }
--------------------------------------------------------------------------------
-- Multi Cast Switch Port Info Table
--------------------------------------------------------------------------------
    tnMcsPortInfoTable OBJECT-TYPE
        SYNTAX         SEQUENCE OF TnMcsPortInfoEntry
        MAX-ACCESS     not-accessible
        STATUS         current
        DESCRIPTION    "Current disposition AD attributes"
        ::= { tnOpticalPortInfo 276 }

    tnMcsPortInfoEntry OBJECT-TYPE
        SYNTAX         TnMcsPortInfoEntry
        MAX-ACCESS     not-accessible
        STATUS         current
        DESCRIPTION    ""
        INDEX { ifIndex }
        ::= { tnMcsPortInfoTable 1 }

    TnMcsPortInfoEntry ::=
        SEQUENCE {
            tnMcsPortInfoCurrentAddDisposition   INTEGER,
            tnMcsPortInfoCurrentDropDisposition  INTEGER,
            tnMcsPortInfoTestingActive           TruthValue
        }

    tnMcsPortInfoCurrentAddDisposition OBJECT-TYPE
        SYNTAX         INTEGER {
                         blocked(1),
                         sig1(2),
                         sig2(3),
                         sig3(4),
                         sig4(5),
                         sig5(6),
                         sig6(7),
                         sig7(8),
                         sig8(9)
                       }
        MAX-ACCESS     read-only
        STATUS         current
        DESCRIPTION    "The current disposition of the port
                        in the AD to SIG direction."
        DEFVAL         { blocked }
        ::= { tnMcsPortInfoEntry 1 }

    tnMcsPortInfoCurrentDropDisposition OBJECT-TYPE
        SYNTAX         INTEGER {
                         blocked(1),
                         sig1(2),
                         sig2(3),
                         sig3(4),
                         sig4(5),
                         sig5(6),
                         sig6(7),
                         sig7(8),
                         sig8(9)
                       }
        MAX-ACCESS     read-only
        STATUS         current
        DESCRIPTION    "The current disposition of the port
                        in the SIG to AD direction."
        DEFVAL         { blocked }
        ::= { tnMcsPortInfoEntry 2 }

    tnMcsPortInfoTestingActive OBJECT-TYPE
        SYNTAX         TruthValue
        MAX-ACCESS     read-only
        STATUS         current
        DESCRIPTION    "Node sets to true when testing in progress
                        on port (logic)."
        DEFVAL         { false }
        ::= { tnMcsPortInfoEntry 3 }

--------------------------------------------------------------------------------
-- Multi Cast Switch Port Channel Info Scalars
--------------------------------------------------------------------------------
    tnMcsPortChannelInfoAttributeTotal OBJECT-TYPE
        SYNTAX         Integer32
        MAX-ACCESS     read-only
        STATUS         current
        DESCRIPTION    ""
        ::= { tnOpticalPortInfo 277 }
--------------------------------------------------------------------------------
-- Multi Cast Switch Port Channel Info Table
--------------------------------------------------------------------------------
    tnMcsPortChannelInfoTable OBJECT-TYPE
        SYNTAX         SEQUENCE OF TnMcsPortChannelInfoEntry
        MAX-ACCESS     not-accessible
        STATUS         current
        DESCRIPTION    "Current disposition AD attributes."
        ::= { tnOpticalPortInfo 278 }

    tnMcsPortChannelInfoEntry OBJECT-TYPE
        SYNTAX         TnMcsPortChannelInfoEntry
        MAX-ACCESS     not-accessible
        STATUS         current
        DESCRIPTION    ""
        INDEX { ifIndex,
                tnChannel }
        ::= { tnMcsPortChannelInfoTable 1 }

    TnMcsPortChannelInfoEntry ::=
        SEQUENCE {
            tnMcsPortChannelInfoCurrentRoutingAdd INTEGER,
            tnMcsPortChannelInfoCurrentRoutingDrop INTEGER
        }

    tnMcsPortChannelInfoCurrentRoutingAdd OBJECT-TYPE
        SYNTAX         INTEGER {
                         notProvisioned(1),
                         ad1In(2),
                         ad2In(3),
                         ad3In(4),
                         ad4In(5),
                         ad5In(6),
                         ad6In(7),
                         ad7In(8),
                         ad8In(9),
                         ad9In(10),
                         ad10In(11),
                         ad11In(12),
                         ad12In(13),
                         ad13In(14),
                         ad14In(15),
                         ad15In(16),
                         ad16In(17)
                       }
        MAX-ACCESS     read-only
        STATUS         current
        DESCRIPTION    "The current routing of a channel from
                        AD port to SIG.  Value notProvisioned
                        means the channel is not cros-connected
                        at this port."
        DEFVAL         { notProvisioned }
        ::= { tnMcsPortChannelInfoEntry 1 }

    tnMcsPortChannelInfoCurrentRoutingDrop OBJECT-TYPE
        SYNTAX         INTEGER {
                         notProvisioned(1),
                         ad1Out(2),
                         ad2Out(3),
                         ad3Out(4),
                         ad4Out(5),
                         ad5Out(6),
                         ad6Out(7),
                         ad7Out(8),
                         ad8Out(9),
                         ad9Out(10),
                         ad10Out(11),
                         ad11Out(12),
                         ad12Out(13),
                         ad13Out(14),
                         ad14Out(15),
                         ad15Out(16),
                         ad16Out(17)
                       }
        MAX-ACCESS     read-only
        STATUS         current
        DESCRIPTION    "The current routing of a channel from
                        SIG to AD port.  Value notProvisioned
                        means the channel is not cros-connected
                        at this port."
        DEFVAL         { notProvisioned }
        ::= { tnMcsPortChannelInfoEntry 2 }

--------------------------------------------------------------------------------
-- Amplifier ARray (AAR) Optical Port Info Scalars
--------------------------------------------------------------------------------
    tnAarPortInfoAttributeTotal OBJECT-TYPE
        SYNTAX         Integer32
        MAX-ACCESS     read-only
        STATUS         current
        DESCRIPTION    ""
        ::= { tnOpticalPortInfo 279 }

--------------------------------------------------------------------------------
-- Amplifier ARray (AAR) Optical Port Info Table
--------------------------------------------------------------------------------
    tnAarPortInfoTable OBJECT-TYPE
        SYNTAX         SEQUENCE OF TnAarPortInfoEntry
        MAX-ACCESS     not-accessible
        STATUS         current
        DESCRIPTION    "The optical amplifier array attributes."
        ::= { tnOpticalPortInfo 280 }

    tnAarPortInfoEntry OBJECT-TYPE
        SYNTAX         TnAarPortInfoEntry
        MAX-ACCESS     not-accessible
        STATUS         current
        DESCRIPTION    ""
        INDEX { ifIndex }
        ::= { tnAarPortInfoTable 1 }

    TnAarPortInfoEntry ::=
        SEQUENCE {
            tnAarPortInfoTotalPowerIn          Integer32,
            tnAarPortInfoLosThreshold          Integer32,
            tnAarPortInfoLosThresholdTolerance Unsigned32,
            tnAarPortInfoLosMode               INTEGER,
            tnAarPortInfoTotalPowerOut         Integer32,
            tnAarPortInfoSignalPowerOut        Integer32,
            tnAarPortInfoOAPumpBiasCurrent     Integer32,
            tnAarPortInfoOAPumpTemperature     Integer32,
            tnAarPortInfoTestingActive         TruthValue 
        }

    tnAarPortInfoTotalPowerIn OBJECT-TYPE
        SYNTAX         Integer32
        UNITS          "mBm"
        MAX-ACCESS     read-only
        STATUS         current
        DESCRIPTION    "The total input power.

                        Current range: -9900, read from module."
        DEFVAL         { -9900 }
        ::= { tnAarPortInfoEntry 1 }

    tnAarPortInfoLosThreshold OBJECT-TYPE
        SYNTAX         Integer32
        UNITS          "mBm"
        MAX-ACCESS     read-only
        STATUS         current
        DESCRIPTION    "The threshold for going into
                        LOS shutdown.

                        Current range: -2700 to 0."
        DEFVAL         { -2500 }
        ::= { tnAarPortInfoEntry 2 }

    tnAarPortInfoLosThresholdTolerance OBJECT-TYPE
        SYNTAX         Unsigned32
        UNITS          "mB"
        MAX-ACCESS     read-only
        STATUS         current
        DESCRIPTION    "The tolerance for clearing LOS
                        shutdown,above the set threshold.

                        Current range: 0 to 1000."
        DEFVAL         { 100 }
        ::= { tnAarPortInfoEntry 3 }

    tnAarPortInfoLosMode OBJECT-TYPE
        SYNTAX         INTEGER {
                         losA(1),
                         losN(2)
                       }
        MAX-ACCESS     read-only
        STATUS         current
        DESCRIPTION    "The LOS mode of the amplifier.
                        LOS A: Amplifier pumps become idle
                               under loss of input signal.
                        LOS N: Amplifier pumps remain enabled
                               under loss of input signal."
        DEFVAL         { losA }
        ::= { tnAarPortInfoEntry 4 }

    tnAarPortInfoTotalPowerOut OBJECT-TYPE
        SYNTAX         Integer32
        UNITS          "mBm"
        MAX-ACCESS     read-only
        STATUS         current
        DESCRIPTION    "The total output power."
        DEFVAL         { -9900 }
        ::= { tnAarPortInfoEntry 5 }

    tnAarPortInfoSignalPowerOut OBJECT-TYPE
        SYNTAX         Integer32
        UNITS          "mBm"
        MAX-ACCESS     read-only
        STATUS         current
        DESCRIPTION    "The signal output power, total power
                        less added ASE."
        DEFVAL         { -9900 }
        ::= { tnAarPortInfoEntry 6 }

    tnAarPortInfoOAPumpBiasCurrent OBJECT-TYPE
        SYNTAX         Integer32
        UNITS          "mA"
        MAX-ACCESS     read-only
        STATUS         current
        DESCRIPTION    "The pump laser bias current."
        ::= { tnAarPortInfoEntry 7 }

    tnAarPortInfoOAPumpTemperature OBJECT-TYPE
        SYNTAX         Integer32
        UNITS          "Celcius"
        MAX-ACCESS     read-only
        STATUS         current
        DESCRIPTION    "The pump temperature."
        ::= { tnAarPortInfoEntry 8 }

    tnAarPortInfoTestingActive OBJECT-TYPE
        SYNTAX         TruthValue
        MAX-ACCESS     read-only
        STATUS         current
        DESCRIPTION    "Node sets to true when testing in progress
                        on port (logic)."
        DEFVAL         { false }
        ::= { tnAarPortInfoEntry 9 }



--------------------------------------------------------------------------------
-- WR20-TFM  Port Channel Info Scalars
--------------------------------------------------------------------------------
    tnWr20tfmPortChannelInfoAttributeTotal OBJECT-TYPE
        SYNTAX         Integer32
        MAX-ACCESS     read-only
        STATUS         current
        DESCRIPTION    ""
        ::= { tnOpticalPortInfo 281 }

--------------------------------------------------------------------------------
-- WR20-TFM  Port Channel Info Table
--------------------------------------------------------------------------------
    tnWr20tfmPortChannelInfoTable OBJECT-TYPE
        SYNTAX         SEQUENCE OF TnWr20tfmPortChannelInfoEntry
        MAX-ACCESS     not-accessible
        STATUS         current
        DESCRIPTION    "The current channel disposition in add/drop
                        direction on WR20-TFM optical card."
        ::= { tnOpticalPortInfo 282 }

    tnWr20tfmPortChannelInfoEntry OBJECT-TYPE
        SYNTAX         TnWr20tfmPortChannelInfoEntry
        MAX-ACCESS     not-accessible
        STATUS         current
        DESCRIPTION    ""
        INDEX { ifIndex,
                tnChannel }
        ::= { tnWr20tfmPortChannelInfoTable 1 }

    TnWr20tfmPortChannelInfoEntry ::=
        SEQUENCE {
            tnWr20tfmPortChannelInfoDropDisposition AluWdmWRChannelCurrentAddDropDisposition,
            tnWr20tfmPortChannelInfoAddDisposition  AluWdmWRChannelCurrentAddDropDisposition
        }

    tnWr20tfmPortChannelInfoDropDisposition OBJECT-TYPE
        SYNTAX         AluWdmWRChannelCurrentAddDropDisposition
        MAX-ACCESS     read-only
        STATUS         current
        DESCRIPTION    "The current channel disposition in the
                        drop direction."
        DEFVAL         { blocked }
        ::= { tnWr20tfmPortChannelInfoEntry 1 }

    tnWr20tfmPortChannelInfoAddDisposition OBJECT-TYPE
        SYNTAX         AluWdmWRChannelCurrentAddDropDisposition
        MAX-ACCESS     read-only
        STATUS         current
        DESCRIPTION    "The current channel disposition in the
                        add direction."
        DEFVAL         { blocked }
        ::= { tnWr20tfmPortChannelInfoEntry 2 }

--------------------------------------------------------------------------------
-- MPO Port Info Scalars
--------------------------------------------------------------------------------
    tnMpoPortInfoAttributeTotal OBJECT-TYPE
        SYNTAX         Integer32
        MAX-ACCESS     read-only
        STATUS         current
        DESCRIPTION    ""
        ::= { tnOpticalPortInfo 283 }

--------------------------------------------------------------------------------
-- MPO Port Info Table
--------------------------------------------------------------------------------
    tnMpoPortInfoTable OBJECT-TYPE
        SYNTAX         SEQUENCE OF TnMpoPortInfoEntry
        MAX-ACCESS     not-accessible
        STATUS         current
        DESCRIPTION    "MPO Port Direction of Signals"
        ::= { tnOpticalPortInfo 284 }

    tnMpoPortInfoEntry OBJECT-TYPE
        SYNTAX         TnMpoPortInfoEntry
        MAX-ACCESS     not-accessible
        STATUS         current
        DESCRIPTION    ""
        INDEX { ifIndex }
        ::= { tnMpoPortInfoTable 1 }

    TnMpoPortInfoEntry ::=
        SEQUENCE {
            tnMpoPortInfoSignalDirection INTEGER
        }

    tnMpoPortInfoSignalDirection OBJECT-TYPE
        SYNTAX         INTEGER {
                         in(1),
                         out(2),
                         bi(3)
                       }
        MAX-ACCESS     read-only
        STATUS         current
        DESCRIPTION    "Indicates if the multi-fiber connector carries
                        signals in, out, or bidirectionally at the port.
                        In: signals are received by the port at all
                            used positions.
                        Out: signals are sent from the port at all
                            used positions.
                        Bi: signals are carried in both directions;
                            some positions in, some positions out."
        ::= { tnMpoPortInfoEntry 1 }


--------------------------------------------------------------------------------
-- MPO Port Multi Position Info Scalars
--------------------------------------------------------------------------------
    tnMpoPortMultiPositionInfoAttributeTotal OBJECT-TYPE
        SYNTAX         Integer32
        MAX-ACCESS     read-only
        STATUS         current
        DESCRIPTION    ""
        ::= { tnOpticalPortInfo 285 }

--------------------------------------------------------------------------------
-- MPO Port Multi Position Info Table
--------------------------------------------------------------------------------
    tnMpoPortMultiPositionInfoTable OBJECT-TYPE
        SYNTAX         SEQUENCE OF TnMpoPortMultiPositionInfoEntry
        MAX-ACCESS     not-accessible
        STATUS         current
        DESCRIPTION    "MPO Port Direction of Signals"
        ::= { tnOpticalPortInfo 286 }

    tnMpoPortMultiPositionInfoEntry OBJECT-TYPE
        SYNTAX         TnMpoPortMultiPositionInfoEntry
        MAX-ACCESS     not-accessible
        STATUS         current
        DESCRIPTION    ""
        INDEX { ifIndex,
                tnPosition }
        ::= { tnMpoPortMultiPositionInfoTable 1 }

    TnMpoPortMultiPositionInfoEntry ::=
        SEQUENCE {
            tnPosition                                        INTEGER,
            tnMpoPortMultiPositionInfoUnderlyingPortUsage     INTEGER,
            tnMpoPortMultiPositionInfoUnderlyingPortIfIndex   InterfaceIndex,
            tnMpoPortMultiPositionInfoUnderlyingPortDirection INTEGER
        }

    tnPosition         OBJECT-TYPE
        SYNTAX         INTEGER {
                         position1(1),
                         position2(2),
                         position3(3),
                         position4(4),
                         position5(5),
                         position6(6),
                         position7(7),
                         position8(8),
                         position9(9),
                         position10(10),
                         position11(11),
                         position12(12)
                       }
        MAX-ACCESS     not-accessible
        STATUS         current
        DESCRIPTION    "The position on the multi-fiber connector."
        ::= { tnMpoPortMultiPositionInfoEntry 1 }

    tnMpoPortMultiPositionInfoUnderlyingPortUsage OBJECT-TYPE
        SYNTAX         INTEGER {
                         used(1),
                         notUsed(2),
                         none(3)
                       }
        MAX-ACCESS     read-only
        STATUS         current
        DESCRIPTION    "The usage of the position on the multi-fiber
                        connector.
                        used: Indicates the position is used by an
                              underlying logical port.
                        notUsed: Indicates the position is not used on
                                  the connector.
                        none: Indicates there are no underlying ports
                              for this multi- fiber connector."
        ::= { tnMpoPortMultiPositionInfoEntry 2 }

    tnMpoPortMultiPositionInfoUnderlyingPortIfIndex OBJECT-TYPE
        SYNTAX         InterfaceIndex
        MAX-ACCESS     read-only
        STATUS         current
        DESCRIPTION    "The logical pack port underlying at the position
                        given in INDEX.
                        Use tnMpoPortMultiPositionInfoUnderlyingPortUsage
                        to determine if a value is expected."
        ::= { tnMpoPortMultiPositionInfoEntry 3 }

    tnMpoPortMultiPositionInfoUnderlyingPortDirection OBJECT-TYPE
        SYNTAX         INTEGER {
                         in(1),
                         out(2),
                         notApplicable(3)
                       }
        MAX-ACCESS     read-only
        STATUS         current
        DESCRIPTION    "The direction (in/out) of the logical pack port
                        underling at the position given in INDEX.

                        in:            Signal direction is into the port.
                        out:           Signal direction is from the port.
                        notApplicable: The port is not used, or there is
                                       no underlying logical port for
                                       this multi-fiber connector."
        ::= { tnMpoPortMultiPositionInfoEntry 4 }

--------------------------------------------------------------------------------
-- 4AN100G Optical Port Info Scalars
--------------------------------------------------------------------------------
    tnIo4an100gPortInfoAttributeTotal OBJECT-TYPE
        SYNTAX         Integer32
        MAX-ACCESS     read-only
        STATUS         current
        DESCRIPTION    ""
        ::= { tnOpticalPortInfo 287 }

--------------------------------------------------------------------------------
-- 4AN100G Optical Port Info Table
--------------------------------------------------------------------------------
    tnIo4an100gPortInfoTable OBJECT-TYPE
        SYNTAX         SEQUENCE OF TnIo4an100gPortInfoEntry
        MAX-ACCESS     not-accessible
        STATUS         current
        DESCRIPTION    "The ports on a 4AN100G optical card."
        ::= { tnOpticalPortInfo 288 }

    tnIo4an100gPortInfoEntry OBJECT-TYPE
        SYNTAX         TnIo4an100gPortInfoEntry
        MAX-ACCESS     not-accessible
        STATUS         current
        DESCRIPTION    ""
        INDEX { ifIndex }
        ::= { tnIo4an100gPortInfoTable 1 }

    TnIo4an100gPortInfoEntry ::=
        SEQUENCE {
            tnIo4an100gPortInfoFunction  INTEGER
        }

    tnIo4an100gPortInfoFunction OBJECT-TYPE
        SYNTAX         INTEGER {
                         client(1)
                       }
        MAX-ACCESS     read-only
        STATUS         current
        DESCRIPTION    "Indicates the functional type of this 4AN100G port."
        ::= { tnIo4an100gPortInfoEntry 1 }

--------------------------------------------------------------------------------
-- 30AN10G Optical Port Info Scalars
--------------------------------------------------------------------------------
    tnIo30an10gPortInfoAttributeTotal OBJECT-TYPE
        SYNTAX         Integer32
        MAX-ACCESS     read-only
        STATUS         current
        DESCRIPTION    ""
        ::= { tnOpticalPortInfo 289 }

--------------------------------------------------------------------------------
-- 30AN10G Optical Port Info Table
--------------------------------------------------------------------------------
    tnIo30an10gPortInfoTable OBJECT-TYPE
        SYNTAX         SEQUENCE OF TnIo30an10gPortInfoEntry
        MAX-ACCESS     not-accessible
        STATUS         current
        DESCRIPTION    "The ports on a 30AN10G optical card."
        ::= { tnOpticalPortInfo 290 }

    tnIo30an10gPortInfoEntry OBJECT-TYPE
        SYNTAX         TnIo30an10gPortInfoEntry
        MAX-ACCESS     not-accessible
        STATUS         current
        DESCRIPTION    ""
        INDEX { ifIndex }
        ::= { tnIo30an10gPortInfoTable 1 }

    TnIo30an10gPortInfoEntry ::=
        SEQUENCE {
            tnIo30an10gPortInfoFunction  INTEGER
        }

    tnIo30an10gPortInfoFunction OBJECT-TYPE
        SYNTAX         INTEGER {
                         client(1)
                       }
        MAX-ACCESS     read-only
        STATUS         current
        DESCRIPTION    "Indicates the functional type of this 30AN10G port."
        ::= { tnIo30an10gPortInfoEntry 1 }

--------------------------------------------------------------------------------
-- 30AN300 Optical Port Info Scalars
--------------------------------------------------------------------------------
    tnIo30an300PortInfoAttributeTotal OBJECT-TYPE
        SYNTAX         Integer32
        MAX-ACCESS     read-only
        STATUS         current
        DESCRIPTION    ""
        ::= { tnOpticalPortInfo 291 }

--------------------------------------------------------------------------------
-- 30AN10G Optical Port Info Table
--------------------------------------------------------------------------------
    tnIo30an300PortInfoTable OBJECT-TYPE
        SYNTAX         SEQUENCE OF TnIo30an300PortInfoEntry
        MAX-ACCESS     not-accessible
        STATUS         current
        DESCRIPTION    "The ports on a 30AN300 optical card."
        ::= { tnOpticalPortInfo 292 }

    tnIo30an300PortInfoEntry OBJECT-TYPE
        SYNTAX         TnIo30an300PortInfoEntry
        MAX-ACCESS     not-accessible
        STATUS         current
        DESCRIPTION    ""
        INDEX { ifIndex }
        ::= { tnIo30an300PortInfoTable 1 }

    TnIo30an300PortInfoEntry ::=
        SEQUENCE {
            tnIo30an300PortInfoFunction  INTEGER
        }

    tnIo30an300PortInfoFunction OBJECT-TYPE
        SYNTAX         INTEGER {
                         client(1)
                       }
        MAX-ACCESS     read-only
        STATUS         current
        DESCRIPTION    "Indicates the functional type of this 30AN300 port."
        ::= { tnIo30an300PortInfoEntry 1 }

--------------------------------------------------------------------------------
-- 4AN400 Optical Port Info Scalars
--------------------------------------------------------------------------------
    tnIo4an400PortInfoAttributeTotal OBJECT-TYPE
        SYNTAX         Integer32
        MAX-ACCESS     read-only
        STATUS         current
        DESCRIPTION    ""
        ::= { tnOpticalPortInfo 293 }

--------------------------------------------------------------------------------
-- 4AN400 Optical Port Info Table
--------------------------------------------------------------------------------
    tnIo4an400PortInfoTable OBJECT-TYPE
        SYNTAX         SEQUENCE OF TnIo4an400PortInfoEntry
        MAX-ACCESS     not-accessible
        STATUS         current
        DESCRIPTION    "The ports on a 4AN400 optical card."
        ::= { tnOpticalPortInfo 294 }

    tnIo4an400PortInfoEntry OBJECT-TYPE
        SYNTAX         TnIo4an400PortInfoEntry
        MAX-ACCESS     not-accessible
        STATUS         current
        DESCRIPTION    ""
        INDEX { ifIndex }
        ::= { tnIo4an400PortInfoTable 1 }

    TnIo4an400PortInfoEntry ::=
        SEQUENCE {
            tnIo4an400PortInfoFunction  INTEGER
        }

    tnIo4an400PortInfoFunction OBJECT-TYPE
        SYNTAX         INTEGER {
                         client(1)
                       }
        MAX-ACCESS     read-only
        STATUS         current
        DESCRIPTION    "Indicates the functional type of this 4AN400 port."
        ::= { tnIo4an400PortInfoEntry 1 }

--------------------------------------------------------------------------------
-- 12P120 Optical Port Info Scalars
--------------------------------------------------------------------------------
    tn12p120PortInfoAttributeTotal OBJECT-TYPE
        SYNTAX         Integer32
        MAX-ACCESS     read-only
        STATUS         current
        DESCRIPTION    ""
        ::= { tnOpticalPortInfo 295 }

--------------------------------------------------------------------------------
-- 12P120 Optical Port Info Table
--------------------------------------------------------------------------------
    tn12p120PortInfoTable OBJECT-TYPE
        SYNTAX         SEQUENCE OF Tn12p120PortInfoEntry
        MAX-ACCESS     not-accessible
        STATUS         current
        DESCRIPTION    "The ports on a 12P120 optical card."
        ::= { tnOpticalPortInfo 296 }

    tn12p120PortInfoEntry OBJECT-TYPE
        SYNTAX         Tn12p120PortInfoEntry
        MAX-ACCESS     not-accessible
        STATUS         current
        DESCRIPTION    ""
        INDEX { ifIndex }
        ::= { tn12p120PortInfoTable 1 }

    Tn12p120PortInfoEntry ::=
        SEQUENCE {
            tn12p120PortInfoFunction  INTEGER
        }

    tn12p120PortInfoFunction OBJECT-TYPE
        SYNTAX         INTEGER {
                         network(1),
                         client(2),
                         evoa(3),
                         backplane(4)
                       }
        MAX-ACCESS     read-only
        STATUS         current
        DESCRIPTION    "Indicates the functional type of this 12P120 port."
        ::= { tn12p120PortInfoEntry 1 }

--------------------------------------------------------------------------------
-- 20P200 Optical Port Info Scalars
--------------------------------------------------------------------------------
    tn20p200PortInfoAttributeTotal OBJECT-TYPE
        SYNTAX         Integer32
        MAX-ACCESS     read-only
        STATUS         current
        DESCRIPTION    ""
        ::= { tnOpticalPortInfo 297 }

--------------------------------------------------------------------------------
-- 20P200 Optical Port Info Table
--------------------------------------------------------------------------------
    tn20p200PortInfoTable OBJECT-TYPE
        SYNTAX         SEQUENCE OF Tn20p200PortInfoEntry
        MAX-ACCESS     not-accessible
        STATUS         current
        DESCRIPTION    "The ports on a 20P200 optical card."
        ::= { tnOpticalPortInfo 298 }

    tn20p200PortInfoEntry OBJECT-TYPE
        SYNTAX         Tn20p200PortInfoEntry
        MAX-ACCESS     not-accessible
        STATUS         current
        DESCRIPTION    ""
        INDEX { ifIndex }
        ::= { tn20p200PortInfoTable 1 }

    Tn20p200PortInfoEntry ::=
        SEQUENCE {
            tn20p200PortInfoFunction  INTEGER
        }

    tn20p200PortInfoFunction OBJECT-TYPE
        SYNTAX         INTEGER {
                         network(1),
                         client(2),
                         backplane(3)
                       }
        MAX-ACCESS     read-only
        STATUS         current
        DESCRIPTION    "Indicates the functional type of this 20P200 port."
        ::= { tn20p200PortInfoEntry 1 }

--------------------------------------------------------------------------------
-- 1UD200 Optical Port Info Scalars
--------------------------------------------------------------------------------
    tn1ud200PortInfoAttributeTotal OBJECT-TYPE
        SYNTAX         Integer32
        MAX-ACCESS     read-only
        STATUS         current
        DESCRIPTION    ""
        ::= { tnOpticalPortInfo 299 }

--------------------------------------------------------------------------------
-- 1UD200 Optical Port Info Table
--------------------------------------------------------------------------------
    tn1ud200PortInfoTable OBJECT-TYPE
        SYNTAX         SEQUENCE OF Tn1ud200PortInfoEntry
        MAX-ACCESS     not-accessible
        STATUS         current
        DESCRIPTION    "The ports on a 1UD200 optical card."
        ::= { tnOpticalPortInfo 300 }

    tn1ud200PortInfoEntry OBJECT-TYPE
        SYNTAX         Tn1ud200PortInfoEntry
        MAX-ACCESS     not-accessible
        STATUS         current
        DESCRIPTION    ""
        INDEX { ifIndex }
        ::= { tn1ud200PortInfoTable 1 }

    Tn1ud200PortInfoEntry ::=
        SEQUENCE {
            tn1ud200PortInfoFunction  INTEGER
        }

    tn1ud200PortInfoFunction OBJECT-TYPE
        SYNTAX         INTEGER {
                         network(1),
                         backplane(2)
                       }
        MAX-ACCESS     read-only
        STATUS         current
        DESCRIPTION    "Indicates the functional type of this 1UD200 port."
        ::= { tn1ud200PortInfoEntry 1 }

--------------------------------------------------------------------------------
-- OT130SNQ10 Optical Port Info Scalars
--------------------------------------------------------------------------------
    tnOt130snq10PortInfoAttributeTotal OBJECT-TYPE
        SYNTAX         Integer32
        MAX-ACCESS     read-only
        STATUS         current
        DESCRIPTION    ""
        ::= { tnOpticalPortInfo 301 }

--------------------------------------------------------------------------------
-- OT130SNQ10 Optical Port Info Table
--------------------------------------------------------------------------------
    tnOt130snq10PortInfoTable OBJECT-TYPE
        SYNTAX         SEQUENCE OF TnOt130snq10PortInfoEntry
        MAX-ACCESS     not-accessible
        STATUS         current
        DESCRIPTION    "The ports on a OT130SNQ10 optical card."
        ::= { tnOpticalPortInfo 302 }

    tnOt130snq10PortInfoEntry OBJECT-TYPE
        SYNTAX         TnOt130snq10PortInfoEntry
        MAX-ACCESS     not-accessible
        STATUS         current
        DESCRIPTION    ""
        INDEX { ifIndex }
        ::= { tnOt130snq10PortInfoTable 1 }

    TnOt130snq10PortInfoEntry ::=
        SEQUENCE {
            tnOt130snq10PortInfoFunction  INTEGER
        }

    tnOt130snq10PortInfoFunction OBJECT-TYPE
        SYNTAX         INTEGER {
                         network(1),
                         client(2)
                       }
        MAX-ACCESS     read-only
        STATUS         current
        DESCRIPTION    "Indicates the functional type of this OT130SNQ10 port."
        ::= { tnOt130snq10PortInfoEntry 1 }
--------------------------------------------------------------------------------
-- IROADMV Optical Port Info Scalars
--------------------------------------------------------------------------------
    tnIroadmvPortInfoAttributeTotal OBJECT-TYPE
        SYNTAX         Integer32
        MAX-ACCESS     read-only
        STATUS         current
        DESCRIPTION    ""
        ::= { tnOpticalPortInfo 303 }

--------------------------------------------------------------------------------
-- IROADMV Optical Port Info Table
--------------------------------------------------------------------------------
    tnIroadmvPortInfoTable OBJECT-TYPE
        SYNTAX         SEQUENCE OF TnIroadmvPortInfoEntry
        MAX-ACCESS     not-accessible
        STATUS         current
        DESCRIPTION    "The ports on a IROADMV optical card."
        ::= { tnOpticalPortInfo 304 }

    tnIroadmvPortInfoEntry OBJECT-TYPE
        SYNTAX         TnIroadmvPortInfoEntry
        MAX-ACCESS     not-accessible
        STATUS         current
        DESCRIPTION    ""
        INDEX { ifIndex }
        ::= { tnIroadmvPortInfoTable 1 }

    TnIroadmvPortInfoEntry ::=
        SEQUENCE {
            tnIroadmvPortInfoFunction  INTEGER
        }

    tnIroadmvPortInfoFunction OBJECT-TYPE
        SYNTAX         INTEGER {
                         lineIn(1),
                         inv(2),
                         osc(3),
                         lineOut(4),
                         oscSfp(5),
                         adt(6),
                         dcm(7)
                       }
        MAX-ACCESS     read-only
        STATUS         current
        DESCRIPTION    "Indicates the functional type of this IROADMV port."
        ::= { tnIroadmvPortInfoEntry 1 }

--------------------------------------------------------------------------------
-- IROADMF Optical Port Info Scalars
--------------------------------------------------------------------------------
    tnIroadmfPortInfoAttributeTotal OBJECT-TYPE
        SYNTAX         Integer32
        MAX-ACCESS     read-only
        STATUS         current
        DESCRIPTION    ""
        ::= { tnOpticalPortInfo 305 }

--------------------------------------------------------------------------------
-- IROADMF Optical Port Info Table
--------------------------------------------------------------------------------
    tnIroadmfPortInfoTable OBJECT-TYPE
        SYNTAX         SEQUENCE OF TnIroadmfPortInfoEntry
        MAX-ACCESS     not-accessible
        STATUS         current
        DESCRIPTION    "The ports on a IROADMF optical card."
        ::= { tnOpticalPortInfo 306 }

    tnIroadmfPortInfoEntry OBJECT-TYPE
        SYNTAX         TnIroadmfPortInfoEntry
        MAX-ACCESS     not-accessible
        STATUS         current
        DESCRIPTION    ""
        INDEX { ifIndex }
        ::= { tnIroadmfPortInfoTable 1 }

    TnIroadmfPortInfoEntry ::=
        SEQUENCE {
            tnIroadmfPortInfoFunction  INTEGER
        }

    tnIroadmfPortInfoFunction OBJECT-TYPE
        SYNTAX         INTEGER {
                         lineIn(1),
                         inv(2),
                         osc(3),
                         lineOut(4),
                         oscSfp(5),
                         adt(6)
                       }
        MAX-ACCESS     read-only
        STATUS         current
        DESCRIPTION    "Indicates the functional type of this IROADMF port."
        ::= { tnIroadmfPortInfoEntry 1 }

--------------------------------------------------------------------------------
-- IROADM Optical Port Info Scalars
--------------------------------------------------------------------------------
    tnIroadmPortInfoAttributeTotal OBJECT-TYPE
        SYNTAX         Integer32
        MAX-ACCESS     read-only
        STATUS         current
        DESCRIPTION    "Total no of attributes in 
                        tnIroadmPortInfoTable."
        ::= { tnOpticalPortInfo 307 }

--------------------------------------------------------------------------------
-- IROADM Optical Port Info Table
--------------------------------------------------------------------------------
    tnIroadmPortInfoTable OBJECT-TYPE
        SYNTAX         SEQUENCE OF TnIroadmPortInfoEntry
        MAX-ACCESS     not-accessible
        STATUS         current
        DESCRIPTION    "Attributes related to IROADM optical cards."
        ::= { tnOpticalPortInfo 308 }

    tnIroadmPortInfoEntry OBJECT-TYPE
        SYNTAX         TnIroadmPortInfoEntry
        MAX-ACCESS     not-accessible
        STATUS         current
        DESCRIPTION    ""
        INDEX { ifIndex }
        ::= { tnIroadmPortInfoTable 1 }

    TnIroadmPortInfoEntry ::=
        SEQUENCE {
            tnIroadmPortInfoIngressOaPowerIn           Integer32,
            tnIroadmPortInfoIngressOaPowerOut          Integer32,
            tnIroadmPortInfoEgressOaPowerIn            Integer32,
            tnIroadmPortInfoEgressOaPowerOut           Integer32,
            tnIroadmPortInfoIngressOaSignalPowerOut    Integer32,
            tnIroadmPortInfoEgressOaSignalPowerOut     Integer32,
            tnIroadmPortInfoIngressOaInputToOutputGain Unsigned32,
            tnIroadmPortInfoEgressOaInputToOutputGain  Integer32,
            tnIroadmPortInfoEgressOaMaxFlatGain        Integer32,
            tnIroadmPortInfoIngressOaMaxFlatGain       Integer32,
            tnIroadmPortInfoActualTilt                 Integer32,
            tnIroadmPortInfoDCMInPower                 Integer32,
            tnIroadmPortInfoDCMOutPower                Integer32,
            tnIroadmPortInfoPowerSpanRepairMargin      Unsigned32,
            tnIroadmPortInfoEnable                     Integer32,
            tnIroadmPortInfoGainTilt                   Integer32
   
        }

    tnIroadmPortInfoIngressOaPowerIn OBJECT-TYPE
        SYNTAX         Integer32
        UNITS          "mBm"
        MAX-ACCESS     read-only
        STATUS         current
        DESCRIPTION    ""
        ::= { tnIroadmPortInfoEntry 1 }

    tnIroadmPortInfoIngressOaPowerOut OBJECT-TYPE
        SYNTAX         Integer32
        UNITS          "mBm"
        MAX-ACCESS     read-only
        STATUS         current
        DESCRIPTION    ""
        ::= { tnIroadmPortInfoEntry 2 }

    tnIroadmPortInfoEgressOaPowerIn OBJECT-TYPE
        SYNTAX         Integer32
        UNITS          "mBm"
        MAX-ACCESS     read-only
        STATUS         current
        DESCRIPTION    ""
        ::= { tnIroadmPortInfoEntry 3 }

    tnIroadmPortInfoEgressOaPowerOut OBJECT-TYPE
        SYNTAX         Integer32
        UNITS          "mBm"
        MAX-ACCESS     read-only
        STATUS         current
        DESCRIPTION    ""
        ::= { tnIroadmPortInfoEntry 4 }

    tnIroadmPortInfoIngressOaSignalPowerOut OBJECT-TYPE
        SYNTAX         Integer32
        UNITS          "mBm"
        MAX-ACCESS     read-only
        STATUS         current
        DESCRIPTION    ""
        ::= { tnIroadmPortInfoEntry 5 }

    tnIroadmPortInfoEgressOaSignalPowerOut OBJECT-TYPE
        SYNTAX         Integer32
        UNITS          "mBm"
        MAX-ACCESS     read-only
        STATUS         current
        DESCRIPTION    ""
        ::= { tnIroadmPortInfoEntry 6 }

    tnIroadmPortInfoIngressOaInputToOutputGain OBJECT-TYPE
        SYNTAX         Unsigned32
        UNITS          "mB"
        MAX-ACCESS     read-only
        STATUS         current
        DESCRIPTION    "Current range:

                       Iroadmv: 1500 to 3100.
                       Iroadmf: 1300 to 1900."
        ::= { tnIroadmPortInfoEntry 7 }

    tnIroadmPortInfoEgressOaInputToOutputGain OBJECT-TYPE
        SYNTAX         Integer32
        UNITS          "mB"
        MAX-ACCESS     read-only
        STATUS         current
        DESCRIPTION    "Current range:

                       Iroadmv: -300 to 2500.
                       Iroadmf: -300 to 2100."
        ::= { tnIroadmPortInfoEntry 8 }

    tnIroadmPortInfoEgressOaMaxFlatGain OBJECT-TYPE
        SYNTAX         Integer32
        UNITS          "mB"
        MAX-ACCESS     read-only
        STATUS         current
        DESCRIPTION    "Default value:
 
                       Iroadmv:2000
                       Iroadmf:1800."
        ::= { tnIroadmPortInfoEntry 9 }

    tnIroadmPortInfoIngressOaMaxFlatGain OBJECT-TYPE
        SYNTAX         Integer32
        UNITS          "mB"
        MAX-ACCESS     read-only
        STATUS         current
        DESCRIPTION    "Default value:

                       Iroadmv:2500
                       Iroadmf:1600."
        ::= { tnIroadmPortInfoEntry 10 }

    tnIroadmPortInfoActualTilt OBJECT-TYPE
        SYNTAX         Integer32
        UNITS          "mBm"
        MAX-ACCESS     read-only
        STATUS         current
        DESCRIPTION    "Current Range:
                        
                        -1000 to 500."
        ::= { tnIroadmPortInfoEntry 11 }

    tnIroadmPortInfoDCMInPower OBJECT-TYPE
        SYNTAX         Integer32
        UNITS          "mBm"
        MAX-ACCESS     read-only
        STATUS         current
        DESCRIPTION    ""
        ::= { tnIroadmPortInfoEntry 12 }

    tnIroadmPortInfoDCMOutPower OBJECT-TYPE
        SYNTAX         Integer32
        UNITS          "mBm"
        MAX-ACCESS     read-only
        STATUS         current
        DESCRIPTION    ""
        ::= { tnIroadmPortInfoEntry 13 }

    tnIroadmPortInfoPowerSpanRepairMargin OBJECT-TYPE
        SYNTAX         Unsigned32
        UNITS          "mB"
        MAX-ACCESS     read-only
        STATUS         current
        DESCRIPTION    "Current range:
                        
                        1500 to 3100."
        DEFVAL         { 2500 }
        ::= { tnIroadmPortInfoEntry 14 }

    tnIroadmPortInfoEnable OBJECT-TYPE
        SYNTAX         Integer32
        MAX-ACCESS     read-only
        STATUS         current
        DESCRIPTION    ""
        ::= { tnIroadmPortInfoEntry 15 }

    tnIroadmPortInfoGainTilt OBJECT-TYPE
        SYNTAX         Integer32
        UNITS          "mB"
        MAX-ACCESS     read-only
        STATUS         current
        DESCRIPTION    "Current  range: "
        DEFVAL         { 0 }
        ::= { tnIroadmPortInfoEntry 16 }

--------------------------------------------------------------------------------
-- IROADM Optical Port Channel Info Scalars
--------------------------------------------------------------------------------
    tnIroadmPortChannelInfoAttributeTotal OBJECT-TYPE
        SYNTAX         Integer32
        MAX-ACCESS     read-only
        STATUS         current
        DESCRIPTION    "Total no of attributes in
                        tnIroadmPortChannelInfoTable."
        ::= { tnOpticalPortInfo 309 }

--------------------------------------------------------------------------------
-- IROADM Optical Port Channel Info Table
--------------------------------------------------------------------------------
    tnIroadmPortChannelInfoTable OBJECT-TYPE
        SYNTAX         SEQUENCE OF TnIroadmPortChannelInfoEntry
        MAX-ACCESS     not-accessible
        STATUS         current
        DESCRIPTION    ""
        ::= { tnOpticalPortInfo 310 }

    tnIroadmPortChannelInfoEntry OBJECT-TYPE
        SYNTAX         TnIroadmPortChannelInfoEntry
        MAX-ACCESS     not-accessible
        STATUS         current
        DESCRIPTION    ""
        INDEX { ifIndex,
                tnChannel }
        ::= { tnIroadmPortChannelInfoTable 1 }

    TnIroadmPortChannelInfoEntry ::=
        SEQUENCE {
            tnIroadmPortChannelInfoAddDisposition INTEGER
        }

    tnIroadmPortChannelInfoAddDisposition OBJECT-TYPE
        SYNTAX         INTEGER {
                         adt1(1),
                         adt2(2),
                         adt3(3),
                         adt4(4),
                         blocked(5)
                       }
        MAX-ACCESS     read-only
        STATUS         current
        DESCRIPTION    ""
        DEFVAL         { blocked }
        ::= { tnIroadmPortChannelInfoEntry 1 }

--------------------------------------------------------------------------------
-- WSS REFERENCE LD Info Scalars
--------------------------------------------------------------------------------
    tnWssRefLdInfoAttributeTotal OBJECT-TYPE
        SYNTAX         Integer32
        MAX-ACCESS     read-only
        STATUS         current
        DESCRIPTION    "Total no of attributes present in
                        tnWssRefLdInfoTable."
        ::= { tnOpticalPortInfo 311 }

--------------------------------------------------------------------------------
-- WSS REFERENCE LD Info Table
--------------------------------------------------------------------------------
    tnWssRefLdInfoTable OBJECT-TYPE
        SYNTAX         SEQUENCE OF TnWssRefLdInfoEntry
        MAX-ACCESS     not-accessible
        STATUS         current
        DESCRIPTION    "Through this table, a network operator may
                        read the reference port for WSS control."
        ::= { tnOpticalPortInfo 312 }

    tnWssRefLdInfoEntry OBJECT-TYPE
        SYNTAX         TnWssRefLdInfoEntry
        MAX-ACCESS     not-accessible
        STATUS         current
        DESCRIPTION    ""
        INDEX { ifIndex,
                tnChannel }
        ::= { tnWssRefLdInfoTable 1 }

    TnWssRefLdInfoEntry ::=
        SEQUENCE {
            tnWssRefLdInfoIfIndex        InterfaceIndexOrZero,
            tnWssRefLdInfoApplicability  INTEGER
        }


    tnWssRefLdInfoIfIndex OBJECT-TYPE
        SYNTAX         InterfaceIndexOrZero
        MAX-ACCESS     read-only
        STATUS         current
        DESCRIPTION    "Show the shelf, slot, and port of the LD card
                        that is providing the reference point for WSS
                        adjustments at the SIG port of the WR card. 
                        Applies only to cards at level 0 in the
                        configuration."
        ::= { tnWssRefLdInfoEntry 1 }

    tnWssRefLdInfoApplicability OBJECT-TYPE
        SYNTAX         INTEGER {
                         notApplicable(1),
                         applicableAndAvailable(2)
                       }
        MAX-ACCESS     read-only
        STATUS         current
        DESCRIPTION    "Values include:
                        notApplicable - no XC is configured for this
                          channel.
                        applicableAndAvailable - XC is configured for
                          this channel."
        ::= { tnWssRefLdInfoEntry 2 }

--------------------------------------------------------------------------------
-- MON-OCM Optical Port Config Scalars
--------------------------------------------------------------------------------
    tnMonOcmPortInfoAttributeTotal OBJECT-TYPE
        SYNTAX         Integer32
        MAX-ACCESS     read-only
        STATUS         current
        DESCRIPTION    "Total no of attributes in tnMonOcmPortInfoTable."
        ::= { tnOpticalPortInfo 313 }

--------------------------------------------------------------------------------
-- MON-OCM Optical Port Config Table
--------------------------------------------------------------------------------
    tnMonOcmPortInfoTable OBJECT-TYPE
        SYNTAX         SEQUENCE OF TnMonOcmPortInfoEntry
        MAX-ACCESS     not-accessible
        STATUS         current
        DESCRIPTION    "The ports on a MON-OCM card."
        ::= { tnOpticalPortInfo 314 }

    tnMonOcmPortInfoEntry OBJECT-TYPE
        SYNTAX         TnMonOcmPortInfoEntry
        MAX-ACCESS     not-accessible
        STATUS         current
        DESCRIPTION    ""
        INDEX { ifIndex }
        ::= { tnMonOcmPortInfoTable 1 }

    TnMonOcmPortInfoEntry ::=
        SEQUENCE {
            tnMonOcmPortInfoFunction  INTEGER
        }

    tnMonOcmPortInfoFunction OBJECT-TYPE
        SYNTAX         INTEGER {
                         output(1),
                         input(2),
                         monitor(3)
                       }
        MAX-ACCESS     read-only
        STATUS         current
        DESCRIPTION    "Indicates the functional type of this MON-OCM port."
        ::= { tnMonOcmPortInfoEntry 1 }

--------------------------------------------------------------------------------
-- Ul2uc400 Optical Port Info Scalars
--------------------------------------------------------------------------------
    tnUl2uc400PortInfoAttributeTotal OBJECT-TYPE
        SYNTAX         Integer32
        MAX-ACCESS     read-only
        STATUS         current
        DESCRIPTION    "Total no of attributes in  tnUl2uc400PortInfoTable"
        ::= { tnOpticalPortInfo 315 }

--------------------------------------------------------------------------------
-- Ul2uc400 Optical Port Info Table
--------------------------------------------------------------------------------
    tnUl2uc400PortInfoTable OBJECT-TYPE
        SYNTAX         SEQUENCE OF TnUl2uc400PortInfoEntry
        MAX-ACCESS     not-accessible
        STATUS         current
        DESCRIPTION    "The ports on a Ul2uc400 optical card."
        ::= { tnOpticalPortInfo 316 }

    tnUl2uc400PortInfoEntry OBJECT-TYPE
        SYNTAX         TnUl2uc400PortInfoEntry
        MAX-ACCESS     not-accessible
        STATUS         current
        DESCRIPTION    ""
        INDEX { ifIndex }
        ::= { tnUl2uc400PortInfoTable 1 }

    TnUl2uc400PortInfoEntry ::=
        SEQUENCE {
            tnUl2uc400PortInfoFunction  INTEGER
        }

    tnUl2uc400PortInfoFunction OBJECT-TYPE
        SYNTAX         INTEGER {
                         network(1)
                       }
        MAX-ACCESS     read-only
        STATUS         current
        DESCRIPTION    "Indicates the functional type of this Ul2uc400 port."
        ::= { tnUl2uc400PortInfoEntry 1 }


--------------------------------------------------------------------------------
-- Ul4uc400 Optical Port Info Scalars
--------------------------------------------------------------------------------
    tnUl4uc400PortInfoAttributeTotal OBJECT-TYPE
        SYNTAX         Integer32
        MAX-ACCESS     read-only
        STATUS         current
        DESCRIPTION    "Total no of attributes in tnUl4uc400PortInfoTable."
        ::= { tnOpticalPortInfo 317 }

--------------------------------------------------------------------------------
-- Ul4uc400 Optical Port Info Table
--------------------------------------------------------------------------------
    tnUl4uc400PortInfoTable OBJECT-TYPE
        SYNTAX         SEQUENCE OF TnUl4uc400PortInfoEntry
        MAX-ACCESS     not-accessible
        STATUS         current
        DESCRIPTION    "The ports on a Ul4uc400 optical card."
        ::= { tnOpticalPortInfo 318 }

    tnUl4uc400PortInfoEntry OBJECT-TYPE
        SYNTAX         TnUl4uc400PortInfoEntry
        MAX-ACCESS     not-accessible
        STATUS         current
        DESCRIPTION    ""
        INDEX { ifIndex }
        ::= { tnUl4uc400PortInfoTable 1 }

    TnUl4uc400PortInfoEntry ::=
        SEQUENCE {
            tnUl4uc400PortInfoFunction  INTEGER
        }

    tnUl4uc400PortInfoFunction OBJECT-TYPE
        SYNTAX         INTEGER {
                         network(1)
                       }
        MAX-ACCESS     read-only
        STATUS         current
        DESCRIPTION    "Indicates the functional type of this Ul4uc400 port."
        ::= { tnUl4uc400PortInfoEntry 1 }

--------------------------------------------------------------------------------
-- Ul20uc200 Optical Port Info Scalars
--------------------------------------------------------------------------------
    tnUl20uc200PortInfoAttributeTotal OBJECT-TYPE
        SYNTAX         Integer32
        MAX-ACCESS     read-only
        STATUS         current
        DESCRIPTION    "Total no of attributes in tnUl20uc200PortInfoTable."
        ::= { tnOpticalPortInfo 319 }

--------------------------------------------------------------------------------
-- Ul20uc200 Optical Port Info Table
--------------------------------------------------------------------------------
    tnUl20uc200PortInfoTable OBJECT-TYPE
        SYNTAX         SEQUENCE OF TnUl20uc200PortInfoEntry
        MAX-ACCESS     not-accessible
        STATUS         current
        DESCRIPTION    "The ports on a Ul20uc200 optical card."
        ::= { tnOpticalPortInfo 320 }

    tnUl20uc200PortInfoEntry OBJECT-TYPE
        SYNTAX         TnUl20uc200PortInfoEntry
        MAX-ACCESS     not-accessible
        STATUS         current
        DESCRIPTION    ""
        INDEX { ifIndex }
        ::= { tnUl20uc200PortInfoTable 1 }

    TnUl20uc200PortInfoEntry ::=
        SEQUENCE {
            tnUl20uc200PortInfoFunction  INTEGER
        }

    tnUl20uc200PortInfoFunction OBJECT-TYPE
        SYNTAX         INTEGER {
                         network(1)
                       }
        MAX-ACCESS     read-only
        STATUS         current
        DESCRIPTION    "Indicates the functional type of this Ul20uc200 port."
        ::= { tnUl20uc200PortInfoEntry 1 }

--------------------------------------------------------------------------------
-- D5X500 Optical Port Info Scalars
--------------------------------------------------------------------------------
    tnD5x500PortInfoAttributeTotal OBJECT-TYPE
        SYNTAX         Integer32
        MAX-ACCESS     read-only
        STATUS         current
        DESCRIPTION    ""
        ::= { tnOpticalPortInfo 321 }

--------------------------------------------------------------------------------
-- D5X500 Optical Port Info Table
--------------------------------------------------------------------------------
    tnD5x500PortInfoTable OBJECT-TYPE
        SYNTAX         SEQUENCE OF TnD5x500PortInfoEntry
        MAX-ACCESS     not-accessible
        STATUS         current
        DESCRIPTION    "The ports on a D5X500 optical card."
        ::= { tnOpticalPortInfo 322 }

    tnD5x500PortInfoEntry OBJECT-TYPE
        SYNTAX         TnD5x500PortInfoEntry
        MAX-ACCESS     not-accessible
        STATUS         current
        DESCRIPTION    ""
        INDEX { ifIndex }
        ::= { tnD5x500PortInfoTable 1 }

    TnD5x500PortInfoEntry ::=
        SEQUENCE {
            tnD5x500PortInfoFunction INTEGER
        }

    tnD5x500PortInfoFunction OBJECT-TYPE
        SYNTAX         INTEGER {
                         network(1),
                         client(2),
                         backplane(3)
                       }
        MAX-ACCESS     read-only
        STATUS         current
        DESCRIPTION    "Indicates the functional type of this D5X500 port."
        ::= { tnD5x500PortInfoEntry 1 }

--------------------------------------------------------------------------------
-- OtS11M100 Optical Port Info Scalars
--------------------------------------------------------------------------------
    tnOtS11M100PortInfoAttributeTotal OBJECT-TYPE
        SYNTAX         Integer32
        MAX-ACCESS     read-only
        STATUS         current
        DESCRIPTION    ""
        ::= { tnOpticalPortInfo 323 }

--------------------------------------------------------------------------------
-- OtS11M100 Optical Port Info Table
--------------------------------------------------------------------------------
    tnOtS11M100PortInfoTable OBJECT-TYPE
        SYNTAX         SEQUENCE OF TnOtS11M100PortInfoEntry
        MAX-ACCESS     not-accessible
        STATUS         current
        DESCRIPTION    "The ports on a OtS11M100 optical card."
        ::= { tnOpticalPortInfo 324 }

    tnOtS11M100PortInfoEntry OBJECT-TYPE
        SYNTAX         TnOtS11M100PortInfoEntry
        MAX-ACCESS     not-accessible
        STATUS         current
        DESCRIPTION    ""
        INDEX { ifIndex }
        ::= { tnOtS11M100PortInfoTable 1 }

    TnOtS11M100PortInfoEntry ::=
        SEQUENCE {
            tnOtS11M100PortInfoFunction  INTEGER
        }

    tnOtS11M100PortInfoFunction OBJECT-TYPE
        SYNTAX         INTEGER {
                         network(1),
                         client(2)
                       }
        MAX-ACCESS     read-only
        STATUS         current
        DESCRIPTION    "Indicates the functional type of this OtS11M100 port."
        ::= { tnOtS11M100PortInfoEntry 1 }

--------------------------------------------------------------------------------
-- MON-OTDR(MON-Optical Time Domain Reflectometer) Optical Port Info Scalars
--------------------------------------------------------------------------------
    tnMonOtdrPortInfoAttributeTotal OBJECT-TYPE
        SYNTAX         Integer32
        MAX-ACCESS     read-only
        STATUS         current
        DESCRIPTION    ""
        ::= { tnOpticalPortInfo 325 }

--------------------------------------------------------------------------------
-- MON-OTDR(Optical Time Domain Reflectometer) Optical Port Info Table
--------------------------------------------------------------------------------
    tnMonOtdrPortInfoTable OBJECT-TYPE
        SYNTAX         SEQUENCE OF TnMonOtdrPortInfoEntry
        MAX-ACCESS     not-accessible
        STATUS         current
        DESCRIPTION    "The ports on an MON-OTDR optical card."
        ::= { tnOpticalPortInfo 326 }

    tnMonOtdrPortInfoEntry OBJECT-TYPE
        SYNTAX         TnMonOtdrPortInfoEntry
        MAX-ACCESS     not-accessible
        STATUS         current
        DESCRIPTION    ""
        INDEX { ifIndex }
        ::= { tnMonOtdrPortInfoTable 1 }

    TnMonOtdrPortInfoEntry ::=
        SEQUENCE {
            tnMonOtdrPortInfoFunction INTEGER
        }

    tnMonOtdrPortInfoFunction OBJECT-TYPE
        SYNTAX         INTEGER {
                         lineIn(1),
                         otdrRx(2),
                         otdrTx(3),
                         lineOut(4),
                         sigIn(5),
                         sigOut(6)
                       }
        MAX-ACCESS     read-only
        STATUS         current
        DESCRIPTION    "Indicates the functional type of this MON-OTDR port."
        ::= { tnMonOtdrPortInfoEntry 1 }

--------------------------------------------------------------------------------
-- PSS96 Power Filter Port Info Scalars
--------------------------------------------------------------------------------
    tnPSS96PowerFilterPortInfoAttributeTotal OBJECT-TYPE
        SYNTAX         Integer32
        MAX-ACCESS     read-only
        STATUS         current
        DESCRIPTION    ""
        ::= { tnOpticalPortInfo 327 }

--------------------------------------------------------------------------------
-- PSS96Power Filter Port Info Table
--------------------------------------------------------------------------------
    tnPSS96PowerFilterPortInfoTable OBJECT-TYPE
        SYNTAX         SEQUENCE OF TnPSS96PowerFilterPortInfoEntry
        MAX-ACCESS     not-accessible
        STATUS         current
        DESCRIPTION    "The ports on a PSS96PowerFilter optical card."
        ::= { tnOpticalPortInfo 328 }

    tnPSS96PowerFilterPortInfoEntry OBJECT-TYPE
        SYNTAX         TnPSS96PowerFilterPortInfoEntry
        MAX-ACCESS     not-accessible
        STATUS         current
        DESCRIPTION    ""
        INDEX { ifIndex }
        ::= { tnPSS96PowerFilterPortInfoTable 1 }

    TnPSS96PowerFilterPortInfoEntry ::=
        SEQUENCE {
            tnPSS96PowerFilterPortInfoFunction INTEGER
        }

    tnPSS96PowerFilterPortInfoFunction OBJECT-TYPE
        SYNTAX         INTEGER {
                         powerFilterPort1(1),
                         powerFilterPort2(2),
                         powerFilterPort3(3)             
                       }
        MAX-ACCESS     read-only
        STATUS         current
        DESCRIPTION    "Indicates the functional type of this PSS96PowerFilter port."
        ::= { tnPSS96PowerFilterPortInfoEntry 1 }

--------------------------------------------------------------------------------
-- 12CE120 Optical Port Info Scalars
--------------------------------------------------------------------------------
     tn12ce120PortInfoAttributeTotal OBJECT-TYPE
         SYNTAX         Integer32
         MAX-ACCESS     read-only
         STATUS         current
         DESCRIPTION    ""
         ::= { tnOpticalPortInfo 329}

--------------------------------------------------------------------------------
-- 12CE120 Optical Port Info Table
--------------------------------------------------------------------------------
     tn12ce120PortInfoTable OBJECT-TYPE
         SYNTAX         SEQUENCE OF Tn12ce120PortInfoEntry
         MAX-ACCESS     not-accessible
         STATUS         current
         DESCRIPTION    "The ports on a 12CE120 optical card."
         ::= { tnOpticalPortInfo 330}

     tn12ce120PortInfoEntry OBJECT-TYPE
         SYNTAX         Tn12ce120PortInfoEntry
         MAX-ACCESS     not-accessible
         STATUS         current
         DESCRIPTION    ""
         INDEX { ifIndex }
         ::= { tn12ce120PortInfoTable 1 }

     Tn12ce120PortInfoEntry ::=
         SEQUENCE {
             tn12ce120PortInfoFunction INTEGER
         }

     tn12ce120PortInfoFunction OBJECT-TYPE
         SYNTAX         INTEGER {
                          network(1),
                          backplane(2),
                          tod(3)
                         }
         MAX-ACCESS     read-only
         STATUS         current
         DESCRIPTION    "Indicates the functional type of this 12CE120 port."
         ::= { tn12ce120PortInfoEntry 1 }

--------------------------------------------------------------------------------
-- 1CE100 Optical Port Info Scalars
--------------------------------------------------------------------------------
     tn1ce100PortInfoAttributeTotal OBJECT-TYPE
         SYNTAX         Integer32
         MAX-ACCESS     read-only
         STATUS         current
         DESCRIPTION    ""
         ::= { tnOpticalPortInfo 331}

--------------------------------------------------------------------------------
 -- 1CE100 Optical Port Info Table
--------------------------------------------------------------------------------
     tn1ce100PortInfoTable OBJECT-TYPE
         SYNTAX         SEQUENCE OF Tn1ce100PortInfoEntry
         MAX-ACCESS     not-accessible
         STATUS         current
         DESCRIPTION    "The ports on a 1CE100 optical card."
         ::= { tnOpticalPortInfo 332}

     tn1ce100PortInfoEntry OBJECT-TYPE
         SYNTAX         Tn1ce100PortInfoEntry
         MAX-ACCESS     not-accessible
         STATUS         current
         DESCRIPTION    ""
         INDEX { ifIndex }
         ::= { tn1ce100PortInfoTable 1 }

     Tn1ce100PortInfoEntry ::=
         SEQUENCE {
             tn1ce100PortInfoFunction INTEGER
         }

     tn1ce100PortInfoFunction OBJECT-TYPE
         SYNTAX         INTEGER {
                          client(1),
                          backplane(2),
                          tod(3)
                         }
         MAX-ACCESS     read-only
         STATUS         current
         DESCRIPTION    "Indicates the functional type of this 1CE100 port."
         ::= { tn1ce100PortInfoEntry 1 }

--------------------------------------------------------------------------------
-- LCI1000 Optical Port Info Scalars
--------------------------------------------------------------------------------
    tnLcI1000PortInfoAttributeTotal OBJECT-TYPE
        SYNTAX         Integer32 
        MAX-ACCESS     read-only 
        STATUS         current
        DESCRIPTION    ""
        ::= { tnOpticalPortInfo 333 }

--------------------------------------------------------------------------------
-- LCI1000 Optical Port Info Table
--------------------------------------------------------------------------------
    tnLcI1000PortInfoTable OBJECT-TYPE
        SYNTAX         SEQUENCE OF TnLcI1000PortInfoEntry
        MAX-ACCESS     not-accessible
        STATUS         current
        DESCRIPTION    "The ports on a LcI1000 optical card."
        ::= { tnOpticalPortInfo 334 }
 
    tnLcI1000PortInfoEntry  OBJECT-TYPE
        SYNTAX         TnLcI1000PortInfoEntry 
        MAX-ACCESS     not-accessible
        STATUS         current
        DESCRIPTION    ""
        INDEX { ifIndex }
        ::= { tnLcI1000PortInfoTable 1 }
 
    TnLcI1000PortInfoEntry ::= SEQUENCE {
        tnLcI1000PortInfoFunction INTEGER
    }

    tnLcI1000PortInfoFunction OBJECT-TYPE
        SYNTAX         INTEGER{
                         network(1),
                         client(2)
                       }
        MAX-ACCESS     read-only 
        STATUS         current
        DESCRIPTION    "Indicates the functional type of
                        this LcI1000 port."
        ::= { tnLcI1000PortInfoEntry 1 }

--------------------------------------------------------------------------------
--------------------------------------------------------------------------------
-- Optical Port Line Card Configuration
--------------------------------------------------------------------------------
--    obsolete
--    tnBbaHgPortLcConfigAttributeTotal OBJECT-TYPE ::= { tnOpticalPortLcConfig 1 }
--    tnBbaHgPortLcConfigTable OBJECT-TYPE ::= { tnOpticalPortLcConfig 2 }
--    tnBbaLgPortLcConfigAttributeTotal OBJECT-TYPE ::= { tnOpticalPortLcConfig 3 }
--    tnBbaLgPortLcConfigTable OBJECT-TYPE ::= { tnOpticalPortLcConfig 4 }

--------------------------------------------------------------------------------
-- Conformance Group Definitions
--------------------------------------------------------------------------------

--------------------------------------------------------------------------------
-- Obsoleted OIDs
--------------------------------------------------------------------------------
--    tnOpticalPortScalarsGroup OBJECT-GROUP ::= { tnOpticalPortGroups 1 }
--    tnOC48SwsPortScalarsGroup OBJECT-GROUP ::= { tnOpticalPortGroups 2 }
--    tnSimpleOpticsPortScalarsGroup OBJECT-GROUP ::= { tnOpticalPortGroups 3 }
--    tnOC48SwsUserNwPortScalarsGroup OBJECT-GROUP ::= { tnOpticalPortGroups 4 }
--    tnOC48SwsUserNwPortGroup OBJECT-GROUP ::= { tnOpticalPortGroups 5 }
--    tnBandFilterPortScalarsGroup OBJECT-GROUP ::= { tnOpticalPortGroups 6 }
--    tnBandFilterPortGroup OBJECT-GROUP ::= { tnOpticalPortGroups 7 }
--    tnOscPortScalarsGroup OBJECT-GROUP ::= { tnOpticalPortGroups 8 }
--    tnOscPortGroup OBJECT-GROUP ::= { tnOpticalPortGroups 9 }
--    tnChannelFilterPortScalarsGroup OBJECT-GROUP ::= { tnOpticalPortGroups 10 }
--    tnChannelFilterPortGroup OBJECT-GROUP ::= { tnOpticalPortGroups 11 }
--    tnBbaLinePortScalarsGroup OBJECT-GROUP ::= { tnOpticalPortGroups 12 }
--    tnBbaLinePortGroup OBJECT-GROUP ::= { tnOpticalPortGroups 13 }
--    tnPpsPortScalarsGroup OBJECT-GROUP ::= { tnOpticalPortGroups 14 }
--    tnPpsPortGroup OBJECT-GROUP ::= { tnOpticalPortGroups 15 }
--    tnOC192SwsUserNwPortScalarsGroup OBJECT-GROUP ::= { tnOpticalPortGroups 16 }
--    tnOC192SwsUserNwPortGroup OBJECT-GROUP ::= { tnOpticalPortGroups 17 }
--    tn2x1GEoSWSPortScalarsGroup OBJECT-GROUP ::= { tnOpticalPortGroups 18 }
--    tn2x1GEoSWSPortGroup OBJECT-GROUP ::= { tnOpticalPortGroups 19 }
--    tnSonetPortScalarsGroup OBJECT-GROUP ::= { tnOpticalPortGroups 20 }
--    tnSonetPortGroup OBJECT-GROUP ::= { tnOpticalPortGroups 21 }

    tnOpticalPortGroup OBJECT-GROUP
        OBJECTS {
            tnOpticalPortInsertionLoss
        }
        STATUS         current
        DESCRIPTION    ""
        ::= { tnOpticalPortGroups 22 }

--------------------------------------------------------------------------------
-- Obsoleted OIDs
--------------------------------------------------------------------------------
--    tnRoadmPortScalarsGroup OBJECT-GROUP ::= { tnOpticalPortGroups 23 }
--    tnRoadmPortGroup OBJECT-GROUP ::= { tnOpticalPortGroups 24 }
--    tnWaveKeyPortScalarsGroup OBJECT-GROUP ::= { tnOpticalPortGroups 25 }

    tnWaveKeyPortGroup OBJECT-GROUP
        OBJECTS {
            tnWaveKeyPortUnexpectedWKThreshIngress,
            tnWaveKeyPortUnexpectedWKThreshEgress,
            tnWaveKeyPortUnexpectedWKThreshAutoModeIngress,
            tnWaveKeyPortUnexpectedWKThreshAutoModeEgress,
            tnWaveKeyPortUnexpectedWKThreshDeltaIngress,
            tnWaveKeyPortUnexpectedWKThreshDeltaEgress,
            tnWaveKeyPortPresentUnexpectedWKThreshIngress,
            tnWaveKeyPortPresentUnexpectedWKThreshEgress,
            tnWaveKeyPortSupportedDirections,
            tnWaveKeyPortUnexpectedWKThreshAutoMaxOffsetIn,
            tnWaveKeyPortUnexpectedWKThreshAutoMaxOffsetOut,
            tnWaveKeyPortCommonEgressPower,
            tnWaveKeyPortCommonIngressPower,
            tnWaveKeyPortDefaultPowerDeviationIn,
            tnWaveKeyPortDefaultPowerDeviationOut
        }
        STATUS         current
        DESCRIPTION    ""
        ::= { tnOpticalPortGroups 26 }

--------------------------------------------------------------------------------
-- Obsoleted OIDs
--------------------------------------------------------------------------------
--    tn10GELANPortScalarsGroup OBJECT-GROUP ::= { tnOpticalPortGroups 27 }
--    tn10GELANPortGroup OBJECT-GROUP ::= { tnOpticalPortGroups 28 }

    tnOpticalFiberGroup OBJECT-GROUP
        OBJECTS {
            tnOpticalFiberFixedLoss,
            tnOpticalFiberLength,
            tnOpticalFiberLossRating,
            tnOpticalFiberDispersionRating
        }
        STATUS         current
        DESCRIPTION    ""
        ::= { tnOpticalPortGroups 29 }

--------------------------------------------------------------------------------
-- Obsoleted OIDs
--------------------------------------------------------------------------------
--    tnChannelAddDropPortScalarsGroup OBJECT-GROUP ::= { tnOpticalPortGroups 30 }
--    tnChannelAddDropPortGroup OBJECT-GROUP ::= { tnOpticalPortGroups 31 }
--    tnQuadOC48MuxPortScalarsGroup OBJECT-GROUP ::= { tnOpticalPortGroups 32 }
--    tnQuadOC48MuxPortGroup OBJECT-GROUP ::= { tnOpticalPortGroups 33 }
--    tnBbaLowGainPortScalarsGroup OBJECT-GROUP ::= { tnOpticalPortGroups 34 }
--    tnBbaLowGainPortGroup OBJECT-GROUP ::= { tnOpticalPortGroups 35 }

    tnLoopbackPortGroup OBJECT-GROUP
        OBJECTS {
            tnLoopbackPortDLEB,
            tnLoopbackPortLLEB,
            tnLoopbackPortTSEB
        }
        STATUS         current
        DESCRIPTION    ""
        ::= { tnOpticalPortGroups 36 }

--------------------------------------------------------------------------------
-- Obsoleted OIDs
--------------------------------------------------------------------------------
--    tnDcmPortScalarsGroup OBJECT-GROUP ::= { tnOpticalPortGroups 37 }
--    tnDcmPortGroup OBJECT-GROUP ::= { tnOpticalPortGroups 38 }

    tnInsertionLossPortGroup OBJECT-GROUP
        OBJECTS {
            tnInsertionLossPortEgress,
            tnInsertionLossPortIngress
        }
        STATUS         current
        DESCRIPTION    ""
        ::= { tnOpticalPortGroups 39 }

--------------------------------------------------------------------------------
-- Obsoleted OIDs
--------------------------------------------------------------------------------
--    tnQuadOC3or12MuxPortScalarsGroup OBJECT-GROUP ::= { tnOpticalPortGroups 40 }
--    tnQuadOC3or12MuxPortGroup OBJECT-GROUP ::= { tnOpticalPortGroups 41 }
--    tnDecaGigEMuxPortScalarsGroup OBJECT-GROUP ::= { tnOpticalPortGroups 42 }
--    tnDecaGigEMuxPortGroup OBJECT-GROUP ::= { tnOpticalPortGroups 43 }

    tnProtectionGroupPortGroup OBJECT-GROUP
        OBJECTS {
            tnProtectionGroupId
        }
        STATUS         current
        DESCRIPTION    ""
        ::= { tnOpticalPortGroups 44 }

    tnDTVPortGroup OBJECT-GROUP
        OBJECTS {
            tnDTVPortControl,
            tnDTVPortValueAmplitude,
            tnDTVPortValuePhase
        }
        STATUS         current
        DESCRIPTION    ""
        ::= { tnOpticalPortGroups 45 }

    tnPortInventoryGroup OBJECT-GROUP
        OBJECTS {
            tnPortInventoryCLEI,
            tnPortInventoryCompanyID,
            tnPortInventoryDate,
            tnPortInventoryExtraData,
            tnPortInventoryFactoryID,
            tnPortInventoryManufacturingPartNumber,
            tnPortInventoryMnemonic,
            tnPortInventorySerialNumber,
            tnPortInventorySWPartNumber
        }
        STATUS         current
        DESCRIPTION    ""
        ::= { tnOpticalPortGroups 46 }

    tnPortOtdrScanGroup OBJECT-GROUP
        OBJECTS {
            tnPortOtdrScanConnAddress,
            tnPortOtdrScanDescription,
            tnPortOtdrScanFileName,
            tnPortOtdrScanProfileId,
            tnPortOtdrScanAvgTime,
            tnPortOtdrScanPulseLength,
            tnPortOtdrScanRange,
            tnPortOtdrScanResolution,
            tnPortOtdrScanWaveLength,
            tnPortOtdrScanControl,
            tnPortOtdrScanStatus,
            tnPortOtdrScanResult,
            tnPortOtdrScanTimeRemaining,
            tnPortOtdrScanLastSuccessfulTimeStamp
        }
        STATUS         current
        DESCRIPTION    ""
        ::= { tnOpticalPortGroups 47 }

    tnFlexgridOtsInfoGroup OBJECT-GROUP
        OBJECTS {
            tnFlexgridOtsInfoLineGranularityMHz
        }
        STATUS         current
        DESCRIPTION    ""
        ::= { tnOpticalPortGroups 48 }

--------------------------------------------------------------------------------
-- Conformance Port Config Group Definitions
--------------------------------------------------------------------------------
    tnSdhPortConfigScalarsGroup OBJECT-GROUP
        OBJECTS {
            tnSdhPortConfigAttributeTotal
        }
        STATUS         current
        DESCRIPTION    ""
        ::= { tnOpticalPortConfigGroups 1 }

    tnSdhPortConfigGroup OBJECT-GROUP
        OBJECTS {
            tnSdhPortRxSignalDegradeThreshold,
            tnSdhPortRxSignalFailThreshold,
            tnSdhPortExpectedRxSectionTrace,
            tnSdhPortTxSectionTrace,
            tnSdhPortRxTIMSEnabled,
            tnSdhPortRxSectionTraceMode,
            tnSdhPortTxSectionTraceMode,
            tnSdhPortTxSynchStatusMessageDUS
        }
        STATUS         current
        DESCRIPTION    ""
        ::= { tnOpticalPortConfigGroups 2 }

--    obsolete
--    tnOC48STM16PortConfigScalarsGroup OBJECT-GROUP ::= { tnOpticalPortConfigGroups 3 }
--    tnOC48STM16PortConfigGroup OBJECT-GROUP ::= { tnOpticalPortConfigGroups 4 }
--    tnOC192STM64PortConfigScalarsGroup OBJECT-GROUP ::= { tnOpticalPortConfigGroups 5 }
--    tnOC192STM64PortConfigGroup OBJECT-GROUP ::= { tnOpticalPortConfigGroups 6 }
--    tnQuadOC48STM16MuxPortConfigScalarsGroup OBJECT-GROUP ::= { tnOpticalPortConfigGroups 7 }
--    tnQuadOC48STM16MuxPortConfigGroup OBJECT-GROUP ::= { tnOpticalPortConfigGroups 8 }
--    tnQuadOC3or12STM1or4MuxPortConfigScalarsGroup OBJECT-GROUP ::= { tnOpticalPortConfigGroups 9 }
--    tnQuadOC3or12STM1or4MuxPortConfigGroup OBJECT-GROUP ::= { tnOpticalPortConfigGroups 10 }
--    tnBandFilterPortConfigScalarsGroup OBJECT-GROUP ::= { tnOpticalPortConfigGroups 11 }
--    tnBandFilterPortConfigGroup OBJECT-GROUP ::= { tnOpticalPortConfigGroups 12 }

    tnOscPortConfigScalarsGroup OBJECT-GROUP
        OBJECTS {
            tnOscPortConfigAttributeTotal
        }
        STATUS         current
        DESCRIPTION    ""
        ::= { tnOpticalPortConfigGroups 13 }

    tnOscPortConfigGroup OBJECT-GROUP
        OBJECTS {
            tnOscPortConfigFunction
--            obsolete
--            tnOscPortPhyDeviceReset
        }
        STATUS         current
        DESCRIPTION    ""
        ::= { tnOpticalPortConfigGroups 14 }

--    obsolete
--    tnChFilterPortConfigScalarsGroup OBJECT-GROUP ::= { tnOpticalPortConfigGroups 15 }
--    tnChFilterPortConfigGroup OBJECT-GROUP ::= { tnOpticalPortConfigGroups 16 }
--    tnChAddDropPortConfigScalarsGroup OBJECT-GROUP ::= { tnOpticalPortConfigGroups 17 }
--    tnChAddDropPortConfigGroup OBJECT-GROUP ::= { tnOpticalPortConfigGroups 18 }
--    tnBbaHgPortConfigScalarsGroup OBJECT-GROUP ::= { tnOpticalPortConfigGroups 19 }
--    tnBbaHgPortConfigGroup OBJECT-GROUP ::= { tnOpticalPortConfigGroups 20 }
--    tnBbaLgPortConfigScalarsGroup OBJECT-GROUP ::= { tnOpticalPortConfigGroups 21 }
--    tnBbaLgPortConfigGroup OBJECT-GROUP ::= { tnOpticalPortConfigGroups 22 }
--    tnPpsPortConfigScalarsGroup OBJECT-GROUP ::= { tnOpticalPortConfigGroups 23 }
--    tnPpsPortConfigGroup OBJECT-GROUP ::= { tnOpticalPortConfigGroups 24 }
--    tnDualGigEMuxPortConfigScalarsGroup OBJECT-GROUP ::= { tnOpticalPortConfigGroups 25 }
--    tnDualGigEMuxPortConfigGroup OBJECT-GROUP ::= { tnOpticalPortConfigGroups 26 }
--    tnRoadmPortConfigScalarsGroup OBJECT-GROUP ::= { tnOpticalPortConfigGroups 27 }
--    tnRoadmPortConfigGroup OBJECT-GROUP ::= { tnOpticalPortConfigGroups 28 }
--    tn10GigELANPortConfigScalarsGroup OBJECT-GROUP ::= { tnOpticalPortConfigGroups 29 }
--    tn10GigELANPortConfigGroup OBJECT-GROUP ::= { tnOpticalPortConfigGroups 30 }

    tnDcmPortConfigScalarsGroup OBJECT-GROUP
        OBJECTS {
            tnDcmPortConfigAttributeTotal
        }
        STATUS         current
        DESCRIPTION    ""
        ::= { tnOpticalPortConfigGroups 31 }

    tnDcmPortConfigGroup OBJECT-GROUP
        OBJECTS {
            tnDcmPortConfigFunction
        }
        STATUS         current
        DESCRIPTION    ""
        ::= { tnOpticalPortConfigGroups 32 }

--    obsolete
--    tnDecaGigEMuxPortConfigScalarsGroup OBJECT-GROUP ::= { tnOpticalPortConfigGroups 33 }
--    tnDecaGigEMuxPortConfigGroup OBJECT-GROUP ::= { tnOpticalPortConfigGroups 34 }

    tnSonetPortConfigScalarsGroup OBJECT-GROUP
        OBJECTS {
            tnSonetPortConfigAttributeTotal
        }
        STATUS         current
        DESCRIPTION    ""
        ::= { tnOpticalPortConfigGroups 35 }

    tnSonetPortConfigGroup OBJECT-GROUP
        OBJECTS {
            tnSonetPortRxSignalDegradeThreshold,
            tnSonetPortRxSignalFailThreshold,
            tnSonetPortExpectedRxSectionTrace,
            tnSonetPortTxSectionTrace,
            tnSonetPortRxTIMSEnabled,
            tnSonetPortRxSectionTraceMode,
            tnSonetPortTxSectionTraceMode,
            tnSonetPortTxSynchStatusMessageDUS
        }
        STATUS         current
        DESCRIPTION    ""
        ::= { tnOpticalPortConfigGroups 36 }

--    obsolete
--    tnExternalDcuPortConfigScalarsGroup OBJECT-GROUP ::= { tnOpticalPortConfigGroups 37 }
--    tnExternalDcuPortConfigGroup OBJECT-GROUP ::= { tnOpticalPortConfigGroups 38 }

    tnDigitalWrapperPortConfigScalarsGroup OBJECT-GROUP
        OBJECTS {
            tnDigitalWrapperPortConfigAttributeTotal
        }
        STATUS         current
        DESCRIPTION    ""
        ::= { tnOpticalPortConfigGroups 39 }

    tnDigitalWrapperPortConfigGroup OBJECT-GROUP
        OBJECTS {
            tnDwPortRxRSBERSDThresh,
            tnDwPortRxRSBERSFThresh,
            tnDwPortDwMode,
            tnDwPortPMTTIEnabled,
            tnDwPortPTIEnabled
        }
        STATUS         current
        DESCRIPTION    ""
        ::= { tnOpticalPortConfigGroups 40 }

    tnNetworkPortConfigScalarsGroup OBJECT-GROUP
        OBJECTS {
            tnNetworkPortConfigAttributeTotal
        }
        STATUS         current
        DESCRIPTION    ""
        ::= { tnOpticalPortConfigGroups 41 }

    tnNetworkPortConfigGroup OBJECT-GROUP
        OBJECTS {
--            obsolete
--            tnNwPortOchStatusRx,
--            tnNwPortOchStatusTx,
            tnNwPortProgrammedChannel,
            tnNwPortChannelRx,
            tnNwPortChannelSpacing
        }
        STATUS         current
        DESCRIPTION    ""
        ::= { tnOpticalPortConfigGroups 42 }

--    obsolete
--    tnMsaHgPortConfigScalarsGroup OBJECT-GROUP ::= { tnOpticalPortConfigGroups 43 }
--    tnMsaHgPortConfigGroup OBJECT-GROUP ::= { tnOpticalPortConfigGroups 44 }
--    tnCmd42PortConfigScalarsGroup OBJECT-GROUP ::= { tnOpticalPortConfigGroups 45 }
--    tnCmd42PortConfigGroup OBJECT-GROUP ::= { tnOpticalPortConfigGroups 46 }
--    tnWssX9PortConfigScalarsGroup OBJECT-GROUP ::= { tnOpticalPortConfigGroups 47 }
--    tnWssX9PortConfigGroup OBJECT-GROUP ::= { tnOpticalPortConfigGroups 48 }

    tnSfpPortConfigScalarsGroup OBJECT-GROUP
        OBJECTS {
            tnSfpPortConfigAttributeTotal
        }
        STATUS         current
        DESCRIPTION    ""
        ::= { tnOpticalPortConfigGroups 49 }

    tnSfpPortConfigGroup OBJECT-GROUP
        OBJECTS {
            tnSfpPortType
        }
        STATUS         current
        DESCRIPTION    ""
        ::= { tnOpticalPortConfigGroups 50 }

--    obsolete
--    tn1xMR2dot5GPortConfigScalarsGroup OBJECT-GROUP ::= { tnOpticalPortConfigGroups 51 }
--    tn1xMR2dot5GPortConfigGroup OBJECT-GROUP ::= { tnOpticalPortConfigGroups 52 }

    tnOpsaPortConfigScalarsGroup OBJECT-GROUP
        OBJECTS {
            tnOpsaPortConfigAttributeTotal
        }
        STATUS         current
        DESCRIPTION    ""
        ::= { tnOpticalPortConfigGroups 53 }

    tnOpsaPortConfigGroup OBJECT-GROUP
        OBJECTS {
            tnOpsaPortConfigFunction
--            obsolete
--            tnOpsaPortSwitchingThreshold,     
--            tnOpsaPortSwitchingThresholdTolerance, 
--            tnOpsaPortTransmitAttenuation,  
--            tnOpsaPortSwitchingThreshCalcControl 
        }
        STATUS         current
        DESCRIPTION    ""
        ::= { tnOpticalPortConfigGroups 54 }

    tn11stmm10PortConfigScalarsGroup OBJECT-GROUP
        OBJECTS {
            tn11stmm10PortConfigAttributeTotal
        }
        STATUS         current
        DESCRIPTION    ""
        ::= { tnOpticalPortConfigGroups 55 }

    tn11stmm10PortConfigGroup OBJECT-GROUP
        OBJECTS {
            tn11stmm10PortConfigFunction
        }
        STATUS         current
        DESCRIPTION    ""
        ::= { tnOpticalPortConfigGroups 56 }

    tn11star1PortConfigScalarsGroup OBJECT-GROUP
        OBJECTS {
            tn11star1PortConfigAttributeTotal
        }
        STATUS         current
        DESCRIPTION    ""
        ::= { tnOpticalPortConfigGroups 57 }

    tn11star1PortConfigGroup OBJECT-GROUP
        OBJECTS {
            tn11star1PortConfigFunction
        }
        STATUS         current
        DESCRIPTION    ""
        ::= { tnOpticalPortConfigGroups 58 }

    tnAhphgPortConfigScalarsGroup OBJECT-GROUP
        OBJECTS {
            tnAhphgPortConfigAttributeTotal
        }
        STATUS         current
        DESCRIPTION    ""
        ::= { tnOpticalPortConfigGroups 59 }

    tnAhphgPortConfigGroup OBJECT-GROUP
        OBJECTS {
            tnAhphgPortConfigFunction
        }
        STATUS         current
        DESCRIPTION    ""
        ::= { tnOpticalPortConfigGroups 60 }

    tnAlphgPortConfigScalarsGroup OBJECT-GROUP
        OBJECTS {
            tnAlphgPortConfigAttributeTotal
        }
        STATUS         current
        DESCRIPTION    ""
        ::= { tnOpticalPortConfigGroups 61 }

    tnAlphgPortConfigGroup OBJECT-GROUP
        OBJECTS {
            tnAlphgPortConfigFunction
        }
        STATUS         current
        DESCRIPTION    ""
        ::= { tnOpticalPortConfigGroups 62 }

    tnCwr8PortConfigScalarsGroup OBJECT-GROUP
        OBJECTS {
            tnCwr8PortConfigAttributeTotal
        }
        STATUS         current
        DESCRIPTION    ""
        ::= { tnOpticalPortConfigGroups 63 }

    tnCwr8PortConfigGroup OBJECT-GROUP
        OBJECTS {
            tnCwr8PortConfigFunction,
--            obsolete
--            tnCwr8PortBlockerAging,
            tnCwr8PortDropTargetPower
        }
        STATUS         current
        DESCRIPTION    ""
        ::= { tnOpticalPortConfigGroups 64 }

    tn11stge12PortConfigScalarsGroup OBJECT-GROUP
        OBJECTS {
            tn11stge12PortConfigAttributeTotal
        }
        STATUS         current
        DESCRIPTION    ""
        ::= { tnOpticalPortConfigGroups 65 }

    tn11stge12PortConfigGroup OBJECT-GROUP
        OBJECTS {
            tn11stge12PortConfigFunction
        }
        STATUS         current
        DESCRIPTION    ""
        ::= { tnOpticalPortConfigGroups 66 }

    tn11dpge12PortConfigScalarsGroup OBJECT-GROUP
        OBJECTS {
            tn11dpge12PortConfigAttributeTotal
        }
        STATUS         current
        DESCRIPTION    ""
        ::= { tnOpticalPortConfigGroups 67 }

    tn11dpge12PortConfigGroup OBJECT-GROUP
        OBJECTS {
            tn11dpge12PortConfigFunction
        }
        STATUS         current
        DESCRIPTION    ""
        ::= { tnOpticalPortConfigGroups 68 }

    tnSfd44PortConfigScalarsGroup OBJECT-GROUP
        OBJECTS {
            tnSfd44PortConfigAttributeTotal
        }
        STATUS         current
        DESCRIPTION    ""
        ::= { tnOpticalPortConfigGroups 69 }

    tnSfd44PortConfigGroup OBJECT-GROUP
        OBJECTS {
            tnSfd44PortConfigFunction
        }
        STATUS         current
        DESCRIPTION    ""
        ::= { tnOpticalPortConfigGroups 70 }

    tnDwdmCmnPortConfigGroup OBJECT-GROUP
        OBJECTS {
            tnDwdmCmnPortXfpType,
            tnDwdmCmnPortAlmProfName,
            tnDwdmCmnPortMgracd
        }
        STATUS         current
        DESCRIPTION    ""
        ::= { tnOpticalPortConfigGroups 71 }

    tnDwdmCmnLinePortConfigGroup OBJECT-GROUP
        OBJECTS {
--          obsolete
--            tnDwdmCmnLinePortLoopType,
            tnDwdmCmnLinePortTransmissionMode,
            tnDwdmCmnLinePortOchOtu2FecMode,
            tnDwdmCmnLinePortOchOtu2Rate,
            tnDwdmCmnLinePortOtu2TransmittedTti,
            tnDwdmCmnLinePortOtu2ExpectedTti,
            tnDwdmCmnLinePortOtu2TimConsequenceAction,
            tnDwdmCmnLinePortOtu2TimDetectionMode,
            tnDwdmCmnLinePortOdu2PayloadType,
            tnDwdmCmnLinePortOdu2OchSignalDefConsequenceAction,
            tnDwdmCmnLinePortOdu2PlmConsequenceAction,
            tnDwdmCmnLinePortOdu2MappingMode,
            tnDwdmCmnLinePortOdu2TpMode,
            tnDwdmCmnLinePortOdu2TransmittedTti,
            tnDwdmCmnLinePortOdu2ExpectedTti,
            tnDwdmCmnLinePortOdu2TimConsequenceAction,
            tnDwdmCmnLinePortOdu2TimDetectionMode,
            tnDwdmCmnLinePortCrossRegPartner,
            tnDwdmCmnLinePortBroadcastFrom,
            tnDwdmCmnLinePortRegenResponse,
            tnDwdmCmnLinePortOtu2holdofftimer,  -- deprecated
            tnDwdmCmnLinePortDemandName,
            tnDwdmCmnLinePortApsEnable,
            tnDwdmCmnLinePortHoldOffTimer,
            tnDwdmCmnLinePortDMConfigCMEPMode,
            tnDwdmCmnLinePortDMConfigEnable,
            tnDwdmCmnLinePortCluster,
            tnDwdmCmnLinePortDegInterval,
            tnDwdmCmnLinePortDegThreshold,
            tnDwdmCmnLinePorttxShape,
            tnDwdmCmnLinePortCdPreComp,
            tnDwdmCmnLinePortPhasenCode
        }
        STATUS         current
        DESCRIPTION    ""
        ::= { tnOpticalPortConfigGroups 72 }

    tnDwdmCmnClientPortConfigGroup OBJECT-GROUP
        OBJECTS {
--            obsolete
--            tnDwdmCmnClientPortLoopType,
            tnDwdmCmnClientPortLosProp,
            tnDwdmCmnClientPortTs1,
            tnDwdmCmnClientPortTs2,
            tnDwdmCmnClientPortOchOtu2FecMode,
            tnDwdmCmnClientPortOchOtu2Rate,
            tnDwdmCmnClientPortOtu2TransmittedTti,
            tnDwdmCmnClientPortOtu2ExpectedTti,
            tnDwdmCmnClientPortOtu2TimConsequenceAction,
            tnDwdmCmnClientPortOtu2TimDetectionMode,
            tnDwdmCmnClientPortOdu2TransmittedTti,
            tnDwdmCmnClientPortOdu2ExpectedTti,
            tnDwdmCmnClientPortOdu2TimDetectionMode,
            tnDwdmCmnClientPortProtectionTs1,
            tnDwdmCmnClientPortProtectionTs2,
            tnDwdmCmnClientPortTsMap,
            tnDwdmCmnClientPortContainer,
            tnDwdmCmnClientPortCSF,
            tnDwdmCmnClientPortSSF,
            tnDwdmCmnClientPortScramMode,
            tnDwdmCmnClientPortDegInterval,
            tnDwdmCmnClientPortDegThreshold,
            tnDwdmCmnClientPortHoldOffTimer
        }
        STATUS         current
        DESCRIPTION    ""
        ::= { tnOpticalPortConfigGroups 73 }

    tnRsmonIngrPortConfigGroup OBJECT-GROUP
        OBJECTS {
            tnRsmonIngrPortTransmittedTti,
            tnRsmonIngrPortExpectedTti,
            tnRsmonIngrPortTimod,
            tnRsmonIngrPortTimDetection,
            tnRsmonIngrPortTimConsequenceAction,
--            obsolete
--            tnRsmonIngrPortTimDetectionMode,
            tnRsmonIngrPortSigMode
        }
        STATUS         current
        DESCRIPTION    ""
        ::= { tnOpticalPortConfigGroups 74 }

    tnMsmonPortConfigGroup OBJECT-GROUP
        OBJECTS {
            tnMsmonPortMappingMode,
            tnMsmonPortExcThLevel,
            tnMsmonPortDegThLevel
        }
        STATUS         current
        DESCRIPTION    ""
        ::= { tnOpticalPortConfigGroups 75 }

    tnOscSfpPortConfigGroup OBJECT-GROUP
        OBJECTS {
--            obsolete
--            tnOscSfpPortType,
            tnOscSfpTemperature,
            tnOscMtu,
            tnOscMtuNeg
        }
        STATUS         current
        DESCRIPTION    ""
        ::= { tnOpticalPortConfigGroups 76 }

    tnDwdmGpPhyPortConfigGroup OBJECT-GROUP
        OBJECTS {
            tnDwdmGpPhyPortPacketIfType,
            tnDwdmGpPhyPortErroredFrameDrop,
            tnDwdmGpPhyPortAutoNegotiation,
            tnDwdmGpPhyPortPacketFcMode,
            tnDwdmGpPhyPortGfpcrc
        }
        STATUS         current
        DESCRIPTION    ""
        ::= { tnOpticalPortConfigGroups 77 }

--    obsolete
--    tnGccPortConfigGroup OBJECT-GROUP ::= { tnOpticalPortConfigGroups 78 }

    tnSvacPortConfigGroup OBJECT-GROUP
        OBJECTS {
            tnSvacPortConfigFunction
        }
        STATUS         current
        DESCRIPTION    ""
        ::= { tnOpticalPortConfigGroups 79 }

    tnSfdPortConfigGroup OBJECT-GROUP
        OBJECTS {
            tnSfd5aPortConfigFunction,
            tnSfd5bPortConfigFunction,
            tnSfd5cPortConfigFunction,
            tnSfd5dPortConfigFunction,
            tnSfd5ePortConfigFunction,
            tnSfd5fPortConfigFunction,
            tnSfd5gPortConfigFunction,
            tnSfd5hPortConfigFunction,
            tnSfd10aPortConfigFunction,
            tnSfd10bPortConfigFunction,
            tnSfd10cPortConfigFunction,
            tnSfd10dPortConfigFunction,
            tnSfd8aPortConfigFunction,
            tnSfd8bPortConfigFunction,
            tnSfd8cPortConfigFunction,
            tnSfd8dPortConfigFunction,
            tnSfd4aPortConfigFunction,
            tnSfd4bPortConfigFunction,
            tnSfd4cPortConfigFunction,
            tnSfd4dPortConfigFunction,
            tnSfd4ePortConfigFunction,
            tnSfd4fPortConfigFunction,
            tnSfd4gPortConfigFunction,
            tnSfd4hPortConfigFunction,
            tnSfd2aPortConfigFunction,
            tnSfd2bPortConfigFunction,
            tnSfd2cPortConfigFunction,
            tnSfd2dPortConfigFunction,
            tnSfd2ePortConfigFunction,
            tnSfd2fPortConfigFunction,
            tnSfd2gPortConfigFunction,
            tnSfd2hPortConfigFunction,
            tnSfd2iPortConfigFunction,
            tnSfd2lPortConfigFunction,
            tnSfd2mPortConfigFunction,
            tnSfd2nPortConfigFunction,
            tnSfd2oPortConfigFunction,
            tnSfd2pPortConfigFunction,
            tnSfd2qPortConfigFunction,
            tnSfd2rPortConfigFunction,
            tnVwmSfd8aPortConfigFunction,
            tnVwmSfd8bPortConfigFunction,
            tnVwmSfd8cPortConfigFunction,
            tnVwmSfd8dPortConfigFunction

        }
        STATUS         current
        DESCRIPTION    ""
        ::= { tnOpticalPortConfigGroups 80 }

    tnSfcPortConfigGroup OBJECT-GROUP
        OBJECTS {
            tnSfc2aPortConfigFunction,
            tnSfc2bPortConfigFunction,
            tnSfc2cPortConfigFunction,
            tnSfc2dPortConfigFunction,
            tnSfc4aPortConfigFunction,
            tnSfc4bPortConfigFunction,
            tnSfc8PortConfigFunction,
            tnSfc1aPortConfigFunction,
            tnSfc1bPortConfigFunction,
            tnSfc1cPortConfigFunction,
            tnSfc1dPortConfigFunction,
            tnSfc1ePortConfigFunction,
            tnSfc1fPortConfigFunction,
            tnSfc1gPortConfigFunction,
            tnSfc1hPortConfigFunction,
            tnVwmSfc8PortConfigFunction
        }
        STATUS         current
        DESCRIPTION    ""
        ::= { tnOpticalPortConfigGroups 81 }

    tnVtsPortConfigGroup OBJECT-GROUP
        OBJECTS {
            tnVtsPortVts1Source,
            tnVtsPortVts2Source,
            tnVtsPortVts3Source,
            tnVtsPortVts4Source,
            tnVtsPortVts5Source,
            tnVtsPortVts6Source,
            tnVtsPortVts7Source,
            tnVtsPortVts8Source,
            tnVtsPortVts9Source,
            tnVtsPortVts10Source
        }
        STATUS         current
        DESCRIPTION    ""
        ::= { tnOpticalPortConfigGroups 82 }

    tnOmdPortConfigGroup OBJECT-GROUP
        OBJECTS {
            tnOmdPortLosThreshold,
            tnOmdPortLosThresholdTolerance,
            tnOmdPortLosOutThreshold,
            tnOmdPortLosOutThresholdTolerance
        }
        STATUS         current
        DESCRIPTION    ""
        ::= { tnOpticalPortConfigGroups 83 }

    tn4dpa4PortConfigScalarsGroup OBJECT-GROUP
        OBJECTS {
            tn4dpa4PortConfigAttributeTotal
        }
        STATUS         current
        DESCRIPTION    ""
        ::= { tnOpticalPortConfigGroups 84 }

    tn4dpa4PortConfigGroup OBJECT-GROUP
        OBJECTS {
            tn4dpa4PortConfigFunction
        }
        STATUS         current
        DESCRIPTION    ""
        ::= { tnOpticalPortConfigGroups 85 }

    tnCwr8c88PortConfigScalarsGroup OBJECT-GROUP
        OBJECTS {
            tnCwr8c88PortConfigAttributeTotal
        }
        STATUS         current
        DESCRIPTION    ""
        ::= { tnOpticalPortConfigGroups 86 }

    tnCwr8c88PortConfigGroup OBJECT-GROUP
        OBJECTS {
            tnCwr8c88PortConfigFunction,
--            obsolete
--            tnCwr8c88PortBlockerAging,
            tnCwr8c88PortDropTargetPower
        }
        STATUS         current
        DESCRIPTION    ""
        ::= { tnOpticalPortConfigGroups 87 }

    tnSfd44bPortConfigScalarsGroup OBJECT-GROUP
        OBJECTS {
            tnSfd44bPortConfigAttributeTotal
        }
        STATUS         current
        DESCRIPTION    ""
        ::= { tnOpticalPortConfigGroups 88 }

    tnSfd44bPortConfigGroup OBJECT-GROUP
        OBJECTS {
            tnSfd44bPortConfigFunction
        }
        STATUS         current
        DESCRIPTION    ""
        ::= { tnOpticalPortConfigGroups 89 }

    tnItlbPortConfigScalarsGroup OBJECT-GROUP
        OBJECTS {
            tnItlbPortConfigAttributeTotal
        }
        STATUS         current
        DESCRIPTION    ""
        ::= { tnOpticalPortConfigGroups 90 }

    tnItlbPortConfigGroup OBJECT-GROUP
        OBJECTS {
            tnItlbPortConfigFunction
        }
        STATUS         current
        DESCRIPTION    ""
        ::= { tnOpticalPortConfigGroups 91 }

    tnAhplgPortConfigScalarsGroup OBJECT-GROUP
        OBJECTS {
            tnAhplgPortConfigAttributeTotal
        }
        STATUS         current
        DESCRIPTION    ""
        ::= { tnOpticalPortConfigGroups 92 }

    tnAhplgPortConfigGroup OBJECT-GROUP
        OBJECTS {
            tnAhplgPortConfigFunction
        }
        STATUS         current
        DESCRIPTION    ""
        ::= { tnOpticalPortConfigGroups 93 }

    tnDwdmCmnOtu1Odu1LinePortConfigGroup OBJECT-GROUP
        OBJECTS {
            tnDwdmCmnLinePortOchOtu1FecMode,
            tnDwdmCmnLinePortOchOtu1Rate,
            tnDwdmCmnLinePortOtu1TransmittedTti,
            tnDwdmCmnLinePortOtu1ExpectedTti,
            tnDwdmCmnLinePortOtu1TimConsequenceAction,
            tnDwdmCmnLinePortOtu1TimDetectionMode,
            tnDwdmCmnLinePortOdu1PayloadType,
            tnDwdmCmnLinePortOdu1OchSignalDefConsequenceAction,
            tnDwdmCmnLinePortOdu1PlmConsequenceAction,
            tnDwdmCmnLinePortOdu1MappingMode,
            tnDwdmCmnLinePortOdu1TpMode,
            tnDwdmCmnLinePortOdu1TransmittedTti,
            tnDwdmCmnLinePortOdu1ExpectedTti,
            tnDwdmCmnLinePortOdu1TimConsequenceAction,
            tnDwdmCmnLinePortOdu1TimDetectionMode,
            tnDwdmCmnLinePortOdu1Interworking
        }
        STATUS         current
        DESCRIPTION    ""
        ::= { tnOpticalPortConfigGroups 94 }

    tnDwdmCmnOtu1Odu1ClientPortConfigGroup OBJECT-GROUP
        OBJECTS {
            tnDwdmCmnClientPortOchOtu1FecMode,
            tnDwdmCmnClientPortOchOtu1Rate,
            tnDwdmCmnClientPortOtu1TransmittedTti,
            tnDwdmCmnClientPortOtu1ExpectedTti,
            tnDwdmCmnClientPortOtu1TimConsequenceAction,
            tnDwdmCmnClientPortOtu1TimDetectionMode,
            tnDwdmCmnClientPortOdu1TransmittedTti,
            tnDwdmCmnClientPortOdu1ExpectedTti,
            tnDwdmCmnClientPortOdu1TimDetectionMode
        }
        STATUS         current
        DESCRIPTION    ""
        ::= { tnOpticalPortConfigGroups 95 }

    tn43stx4PortConfigScalarsGroup OBJECT-GROUP
        OBJECTS {
            tn43stx4PortConfigAttributeTotal
        }
        STATUS         current
        DESCRIPTION    ""
        ::= { tnOpticalPortConfigGroups 96 }

    tn43stx4PortConfigGroup OBJECT-GROUP
        OBJECTS {
            tn43stx4PortConfigFunction
        }
        STATUS         current
        DESCRIPTION    ""
        ::= { tnOpticalPortConfigGroups 97 }

    tnDwdmCmnOtu3Odu3LinePortConfigGroup OBJECT-GROUP
        OBJECTS {
            tnDwdmCmnLinePortOchOtu3FecMode,
            tnDwdmCmnLinePortOtu3TransmittedTti,
            tnDwdmCmnLinePortOtu3ExpectedTti,
            tnDwdmCmnLinePortOtu3TimConsequenceAction,
            tnDwdmCmnLinePortOtu3TimDetectionMode,
            tnDwdmCmnLinePortOdu3PayloadType,
            tnDwdmCmnLinePortOdu3PlmConsequenceAction,
            tnDwdmCmnLinePortOdu3TransmittedTti,
            tnDwdmCmnLinePortOdu3ExpectedTti,
            tnDwdmCmnLinePortOdu3TimConsequenceAction,
            tnDwdmCmnLinePortOdu3TimDetectionMode,
            tnDwdmCmnLinePortOdu3MappingMode,
            tnDwdmCmnLinePortOchOtu3Rate,
            tnDwdmCmnLinePortOdu3Interworking
        }
        STATUS         current
        DESCRIPTION    ""
        ::= { tnOpticalPortConfigGroups 98 }

    tnAlpfgkPortConfigScalarsGroup OBJECT-GROUP
        OBJECTS {
            tnAlpfgkPortConfigAttributeTotal
        }
        STATUS         current
        DESCRIPTION    ""
        ::= { tnOpticalPortConfigGroups 99 }

    tnAlpfgkPortConfigGroup OBJECT-GROUP
        OBJECTS {
            tnAlpfgkPortConfigFunction
        }
        STATUS         current
        DESCRIPTION    ""
        ::= { tnOpticalPortConfigGroups 100 }

    tn4dpa2PortConfigScalarsGroup OBJECT-GROUP
        OBJECTS {
            tn4dpa2PortConfigAttributeTotal
        }
        STATUS         current
        DESCRIPTION    ""
        ::= { tnOpticalPortConfigGroups 101 }

    tn4dpa2PortConfigGroup OBJECT-GROUP
        OBJECTS {
            tn4dpa2PortConfigFunction
        }
        STATUS         current
        DESCRIPTION    ""
        ::= { tnOpticalPortConfigGroups 102 }

    tn43sta1pPortConfigScalarsGroup OBJECT-GROUP
        OBJECTS {
            tn43sta1pPortConfigAttributeTotal
        }
        STATUS         current
        DESCRIPTION    ""
        ::= { tnOpticalPortConfigGroups 103 }

    tn43sta1pPortConfigGroup OBJECT-GROUP
        OBJECTS {
            tn43sta1pPortConfigFunction
        }
        STATUS         current
        DESCRIPTION    ""
        ::= { tnOpticalPortConfigGroups 104 }

    tn43stx4pPortConfigScalarsGroup OBJECT-GROUP
        OBJECTS {
            tn43stx4pPortConfigAttributeTotal
        }
        STATUS         current
        DESCRIPTION    ""
        ::= { tnOpticalPortConfigGroups 105 }

    tn43stx4pPortConfigGroup OBJECT-GROUP
        OBJECTS {
            tn43stx4pPortConfigFunction
        }
        STATUS         current
        DESCRIPTION    ""
        ::= { tnOpticalPortConfigGroups 106 }

    tnA2325aPortConfigScalarsGroup OBJECT-GROUP
        OBJECTS {
            tnA2325aPortConfigAttributeTotal
        }
        STATUS         current
        DESCRIPTION    ""
        ::= { tnOpticalPortConfigGroups 109 }

    tnA2325aPortConfigGroup OBJECT-GROUP
        OBJECTS {
            tnA2325aPortConfigFunction
        }
        STATUS         current
        DESCRIPTION    ""
        ::= { tnOpticalPortConfigGroups 110 }

    tnSfd40PortConfigScalarsGroup OBJECT-GROUP
        OBJECTS {
            tnSfd40PortConfigAttributeTotal
        }
        STATUS         current
        DESCRIPTION    ""
        ::= { tnOpticalPortConfigGroups 111 }

    tnSfd40PortConfigGroup OBJECT-GROUP
        OBJECTS {
            tnSfd40PortConfigFunction
        }
        STATUS         current
        DESCRIPTION    ""
        ::= { tnOpticalPortConfigGroups 112 }

    tnSfd40bPortConfigScalarsGroup OBJECT-GROUP
        OBJECTS {
            tnSfd40bPortConfigAttributeTotal
        }
        STATUS         current
        DESCRIPTION    ""
        ::= { tnOpticalPortConfigGroups 113 }

    tnSfd40bPortConfigGroup OBJECT-GROUP
        OBJECTS {
            tnSfd40bPortConfigFunction
        }
        STATUS         current
        DESCRIPTION    ""
        ::= { tnOpticalPortConfigGroups 114 }

    tn11qpa4PortConfigScalarsGroup OBJECT-GROUP
        OBJECTS {
            tn11qpa4PortConfigAttributeTotal
        }
        STATUS         current
        DESCRIPTION    ""
        ::= { tnOpticalPortConfigGroups 115 }

    tn11qpa4PortConfigGroup OBJECT-GROUP
        OBJECTS {
            tn11qpa4PortConfigFunction
        }
        STATUS         current
        DESCRIPTION    ""
        ::= { tnOpticalPortConfigGroups 116 }

    tn112scx10PortConfigScalarsGroup OBJECT-GROUP
        OBJECTS {
            tn112scx10PortConfigAttributeTotal
        }
        STATUS         current
        DESCRIPTION    ""
        ::= { tnOpticalPortConfigGroups 117 }

    tn112scx10PortConfigGroup OBJECT-GROUP
        OBJECTS {
            tn112scx10PortConfigFunction
        }
        STATUS         current
        DESCRIPTION    ""
        ::= { tnOpticalPortConfigGroups 118 }

    tn112sca1PortConfigScalarsGroup OBJECT-GROUP
        OBJECTS {
            tn112sca1PortConfigAttributeTotal
        }
        STATUS         current
        DESCRIPTION    ""
        ::= { tnOpticalPortConfigGroups 119 }

    tn112sca1PortConfigGroup OBJECT-GROUP
        OBJECTS {
            tn112sca1PortConfigFunction
        }
        STATUS         current
        DESCRIPTION    ""
        ::= { tnOpticalPortConfigGroups 120 }

    tnDwdmCmnOtu4Odu4LinePortConfigGroup OBJECT-GROUP
        OBJECTS {
            tnDwdmCmnLinePortOchOtu4FecMode,
            tnDwdmCmnLinePortOchOtu4Rate,
            tnDwdmCmnLinePortOtu4TransmittedTti,
            tnDwdmCmnLinePortOtu4ExpectedTti,
            tnDwdmCmnLinePortOtu4TimConsequenceAction,
            tnDwdmCmnLinePortOtu4TimDetectionMode,
            tnDwdmCmnLinePortOdu4PayloadType,
            tnDwdmCmnLinePortOdu4PlmConsequenceAction,
            tnDwdmCmnLinePortOdu4TransmittedTti,
            tnDwdmCmnLinePortOdu4ExpectedTti,
            tnDwdmCmnLinePortOdu4TimConsequenceAction,
            tnDwdmCmnLinePortOdu4TimDetectionMode,
            tnDwdmCmnLinePortOtu4RegenResponse,
            tnDwdmCmnLinePortOdu4Interworking,
            tnDwdmCmnLinePortOtu4holdofftimer,  -- deprecated
            tnDwdmCmnLinePortOdu4112GInterworking,
            tnDwdmCmnLinePortOdu4DMConfigCMEPMode,
            tnDwdmCmnLinePortOdu4DMConfigEnable,
            tnDwdmCmnLinePortOdu4CndRes,
            tnDwdmCmnLinePortOdu4Encoding
        }
        STATUS         current
        DESCRIPTION    ""
        ::= { tnOpticalPortConfigGroups 121 }

    tnDwdmCmnOtu4Odu4ClientPortConfigGroup OBJECT-GROUP
        OBJECTS {
            tnDwdmCmnClientPortOchOtu4FecMode,
            tnDwdmCmnClientPortOchOtu4Rate,
            tnDwdmCmnClientPortOtu4TransmittedTti,
            tnDwdmCmnClientPortOtu4ExpectedTti,
            tnDwdmCmnClientPortOtu4TimConsequenceAction,
            tnDwdmCmnClientPortOtu4TimDetectionMode,
            tnDwdmCmnClientPortOdu4TransmittedTti,
            tnDwdmCmnClientPortOdu4ExpectedTti,
            tnDwdmCmnClientPortOdu4TimDetectionMode
--            obsolete
--            tnDwdmCmnClientPortOdu4IncomingTti,
--            tnDwdmCmnClientPortOdu4TtiStatus
        }
        STATUS         current
        DESCRIPTION    ""
        ::= { tnOpticalPortConfigGroups 122 }

    tnRsmonEgrPortConfigGroup OBJECT-GROUP
        OBJECTS {
            tnRsmonEgrPortTimod,
            tnRsmonEgrPortSigMode,
            tnRsmonEgrPortTransmittedTti,
            tnRsmonEgrPortExpectedTti,
            tnRsmonEgrPortTimDetection,
            tnRsmonEgrPortTimConsequenceAction
        }
        STATUS         current
        DESCRIPTION    ""
        ::= { tnOpticalPortConfigGroups 123 }

    tnDwdmCbrArPortConfigGroup OBJECT-GROUP
        OBJECTS {
            tnDwdmCbrArPortHdsdiRate
        }
        STATUS         current
        DESCRIPTION    ""
        ::= { tnOpticalPortConfigGroups 124 }

    tnAlpfgtPortConfigScalarsGroup OBJECT-GROUP
        OBJECTS {
            tnAlpfgtPortConfigAttributeTotal
        }
        STATUS         current
        DESCRIPTION    ""
        ::= { tnOpticalPortConfigGroups 125 }

    tnAlpfgtPortConfigGroup OBJECT-GROUP
        OBJECTS {
            tnAlpfgtPortConfigFunction
        }
        STATUS         current
        DESCRIPTION    ""
        ::= { tnOpticalPortConfigGroups 126 }

    tnOsctPortConfigScalarsGroup OBJECT-GROUP
        OBJECTS {
            tnOsctPortConfigAttributeTotal
        }
        STATUS         current
        DESCRIPTION    ""
        ::= { tnOpticalPortConfigGroups 127 }

    tnOsctPortConfigGroup OBJECT-GROUP
        OBJECTS {
            tnOsctPortConfigFunction
        }
        STATUS         current
        DESCRIPTION    ""
        ::= { tnOpticalPortConfigGroups 128 }

    tnWtocmPortConfigScalarsGroup OBJECT-GROUP
        OBJECTS {
            tnWtocmPortConfigAttributeTotal
        }
        STATUS         current
        DESCRIPTION    ""
        ::= { tnOpticalPortConfigGroups 129 }

    tnWtocmPortConfigGroup OBJECT-GROUP
        OBJECTS {
            tnWtocmPortConfigFunction
        }
        STATUS         current
        DESCRIPTION    ""
        ::= { tnOpticalPortConfigGroups 130 }

    tnWr2c88PortConfigScalarsGroup OBJECT-GROUP
        OBJECTS {
            tnWr2c88PortConfigAttributeTotal
        }
        STATUS         current
        DESCRIPTION    ""
        ::= { tnOpticalPortConfigGroups 131 }

    tnWr2c88PortConfigGroup OBJECT-GROUP
        OBJECTS {
            tnWr2c88PortConfigFunction
--            obsolete
--            tnWr2c88PortBlockerAging
        }
        STATUS         current
        DESCRIPTION    ""
        ::= { tnOpticalPortConfigGroups 132 }

    tnAm2017bPortConfigScalarsGroup OBJECT-GROUP
        OBJECTS {
            tnAm2017bPortConfigAttributeTotal
        }
        STATUS         current
        DESCRIPTION    ""
        ::= { tnOpticalPortConfigGroups 133 }

    tnAm2017bPortConfigGroup OBJECT-GROUP
        OBJECTS {
            tnAm2017bPortConfigFunction
        }
        STATUS         current
        DESCRIPTION    ""
        ::= { tnOpticalPortConfigGroups 134 }

    tnAm2325bPortConfigScalarsGroup OBJECT-GROUP
        OBJECTS {
            tnAm2325bPortConfigAttributeTotal
        }
        STATUS         current
        DESCRIPTION    ""
        ::= { tnOpticalPortConfigGroups 135 }

    tnAm2325bPortConfigGroup OBJECT-GROUP
        OBJECTS {
            tnAm2325bPortConfigFunction
        }
        STATUS         current
        DESCRIPTION    ""
        ::= { tnOpticalPortConfigGroups 136 }

    tn1dpp21PortConfigScalarsGroup OBJECT-GROUP
        OBJECTS {
            tn1dpp21PortConfigAttributeTotal
        }
        STATUS         current
        DESCRIPTION    ""
        ::= { tnOpticalPortConfigGroups 137 }

    tn1dpp21PortConfigGroup OBJECT-GROUP
        OBJECTS {
            tn1dpp21PortConfigFunction
        }
        STATUS         current
        DESCRIPTION    ""
        ::= { tnOpticalPortConfigGroups 138 }

    tnE1T1PortConfigGroup OBJECT-GROUP
        OBJECTS {
            tnE1T1MappingMode,
            tnE1T1Format,
            tnE1T1ClientEgressTimingMode,
            tnE1T1PortConfigImpedance
        }
        STATUS         current
        DESCRIPTION    ""
        ::= { tnOpticalPortConfigGroups 139 }

    tnMvacPortConfigScalarsGroup OBJECT-GROUP
        OBJECTS {
            tnMvacPortConfigAttributeTotal
        }
        STATUS         current
        DESCRIPTION    ""
        ::= { tnOpticalPortConfigGroups 140 }

    tnMvacPortConfigGroup OBJECT-GROUP
        OBJECTS {
            tnMvacPortConfigFunction,
            tnMvacPortConfigVoaMode,
            tnMvacPortConfigAttenuationModeAtten,
            tnMvacPortConfigConnToPort
        }
        STATUS         current
        DESCRIPTION    ""
        ::= { tnOpticalPortConfigGroups 141 }

    tn43scx4PortConfigScalarsGroup OBJECT-GROUP
        OBJECTS {
            tn43scx4PortConfigAttributeTotal
        }
        STATUS         current
        DESCRIPTION    ""
        ::= { tnOpticalPortConfigGroups 144 }

    tn43scx4PortConfigGroup OBJECT-GROUP
        OBJECTS {
            tn43scx4PortConfigFunction
        }
        STATUS         current
        DESCRIPTION    ""
        ::= { tnOpticalPortConfigGroups 145 }

    tnRa2pPortConfigScalarsGroup OBJECT-GROUP
        OBJECTS {
            tnRa2pPortConfigAttributeTotal
        }
        STATUS         current
        DESCRIPTION    ""
        ::= { tnOpticalPortConfigGroups 146 }

    tnRa2pPortConfigGroup OBJECT-GROUP
        OBJECTS {
            tnRa2pPortConfigFunction
        }
        STATUS         current
        DESCRIPTION    ""
        ::= { tnOpticalPortConfigGroups 147 }

    tnAm2318aPortConfigScalarsGroup OBJECT-GROUP
        OBJECTS {
            tnAm2318aPortConfigAttributeTotal
        }
        STATUS         current
        DESCRIPTION    ""
        ::= { tnOpticalPortConfigGroups 148 }

    tnAm2318aPortConfigGroup OBJECT-GROUP
        OBJECTS {
            tnAm2318aPortConfigFunction
        }
        STATUS         current
        DESCRIPTION    ""
        ::= { tnOpticalPortConfigGroups 149 }

    tnAm2125aPortConfigScalarsGroup OBJECT-GROUP
        OBJECTS {
            tnAm2125aPortConfigAttributeTotal
        }
        STATUS         current
        DESCRIPTION    ""
        ::= { tnOpticalPortConfigGroups 150 }

    tnAm2125aPortConfigGroup OBJECT-GROUP
        OBJECTS {
            tnAm2125aPortConfigFunction
        }
        STATUS         current
        DESCRIPTION    ""
        ::= { tnOpticalPortConfigGroups 151 }

    tnItluPortConfigScalarsGroup OBJECT-GROUP
        OBJECTS {
            tnItluPortConfigAttributeTotal
        }
        STATUS         current
        DESCRIPTION    ""
        ::= { tnOpticalPortConfigGroups 152 }

    tnItluPortConfigGroup OBJECT-GROUP
        OBJECTS {
            tnItluPortConfigFunction
        }
        STATUS         current
        DESCRIPTION    ""
        ::= { tnOpticalPortConfigGroups 153 }

    tnWr8c88aPortConfigScalarsGroup OBJECT-GROUP
        OBJECTS {
            tnWr8c88aPortConfigAttributeTotal
        }
        STATUS         current
        DESCRIPTION    ""
        ::= { tnOpticalPortConfigGroups 154 }

    tnWr8c88aPortConfigGroup OBJECT-GROUP
        OBJECTS {
            tnWr8c88aPortConfigFunction
        }
        STATUS         current
        DESCRIPTION    ""
        ::= { tnOpticalPortConfigGroups 155 }

    tn11dpe12ePortConfigScalarsGroup OBJECT-GROUP
        OBJECTS {
            tn11dpe12ePortConfigAttributeTotal
        }
        STATUS         current
        DESCRIPTION    ""
        ::= { tnOpticalPortConfigGroups 156 }

    tn11dpe12ePortConfigGroup OBJECT-GROUP
        OBJECTS {
            tn11dpe12ePortConfigFunction,
            tn11dpe12ePortQinQModeTPID,
            tn11dpe12ePortQinQModePVID
        }
        STATUS         current
        DESCRIPTION    ""
        ::= { tnOpticalPortConfigGroups 157 }

    tn112sx10lPortConfigScalarsGroup OBJECT-GROUP
        OBJECTS {
            tn112sx10lPortConfigAttributeTotal
        }
        STATUS         current
        DESCRIPTION    ""
        ::= { tnOpticalPortConfigGroups 158 }

    tn112sx10lPortConfigGroup OBJECT-GROUP
        OBJECTS {
            tn112sx10lPortConfigFunction
        }
        STATUS         current
        DESCRIPTION    ""
        ::= { tnOpticalPortConfigGroups 159 }

    tn112sa1lPortConfigScalarsGroup OBJECT-GROUP
        OBJECTS {
            tn112sa1lPortConfigAttributeTotal
        }
        STATUS         current
        DESCRIPTION    ""
        ::= { tnOpticalPortConfigGroups 160 }

    tn112sa1lPortConfigGroup OBJECT-GROUP
        OBJECTS {
            tn112sa1lPortConfigFunction
        }
        STATUS         current
        DESCRIPTION    ""
        ::= { tnOpticalPortConfigGroups 161 }

    tn11dpm12PortConfigScalarsGroup OBJECT-GROUP
        OBJECTS {
            tn11dpm12PortConfigAttributeTotal
        }
        STATUS         current
        DESCRIPTION    ""
        ::= { tnOpticalPortConfigGroups 162 }

    tn11dpm12PortConfigGroup OBJECT-GROUP
        OBJECTS {
            tn11dpm12PortConfigFunction
        }
        STATUS         current
        DESCRIPTION    ""
        ::= { tnOpticalPortConfigGroups 163 }

--    obsolete
--    tnWr8c88aAttenPortConfigGroup OBJECT-GROUP ::= { tnOpticalPortConfigGroups 164 }

    tnRamanPortConfigGroup OBJECT-GROUP
        OBJECTS {
            tnRamanPortFiberType,
            tnRamanPortGMinExpected,
            tnRamanPortGMaxExpected,
            tnRamanPortTiltTarget,
            tnRamanPortOperatingMode,
            tnRamanPortAgcTargetGain,
            tnRamanPortAprMode
        }
        STATUS         current
        DESCRIPTION    ""
        ::= { tnOpticalPortConfigGroups 165 }

    tnMesh4PortConfigScalarsGroup OBJECT-GROUP
        OBJECTS {
            tnMesh4PortConfigAttributeTotal
        }
        STATUS         current
        DESCRIPTION    ""
        ::= { tnOpticalPortConfigGroups 166 }

    tnMesh4PortConfigGroup OBJECT-GROUP
        OBJECTS {
            tnMesh4PortConfigFunction
        }
        STATUS         current
        DESCRIPTION    ""
        ::= { tnOpticalPortConfigGroups 167 }

--    obsolete
--    tnTcmPortConfigScalarsGroup OBJECT-GROUP OBJECT-TYPE ::= { tnOpticalPortConfigGroups 168 }
--    tnTcmPortConfigGroup OBJECT-GROUP OBJECT-TYPE ::= { tnOpticalPortConfigGroups 169 }

    tn43sca1PortConfigScalarsGroup OBJECT-GROUP
        OBJECTS {
            tn43sca1PortConfigAttributeTotal
        }
        STATUS         current
        DESCRIPTION    ""
        ::= { tnOpticalPortConfigGroups 170 }

    tn43sca1PortConfigGroup OBJECT-GROUP
        OBJECTS {
            tn43sca1PortConfigFunction
        }
        STATUS         current
        DESCRIPTION    ""
        ::= { tnOpticalPortConfigGroups 171 }

    tn43scx4lPortConfigScalarsGroup OBJECT-GROUP
        OBJECTS {
            tn43scx4lPortConfigAttributeTotal
        }
        STATUS         current
        DESCRIPTION    ""
        ::= { tnOpticalPortConfigGroups 172 }

    tn43scx4lPortConfigGroup OBJECT-GROUP
        OBJECTS {
            tn43scx4lPortConfigFunction
        }
        STATUS         current
        DESCRIPTION    ""
        ::= { tnOpticalPortConfigGroups 173 }

    tnAm2125bPortConfigScalarsGroup OBJECT-GROUP
        OBJECTS {
            tnAm2125bPortConfigAttributeTotal
        }
        STATUS         current
        DESCRIPTION    ""
        ::= { tnOpticalPortConfigGroups 174 }

    tnAm2125bPortConfigGroup OBJECT-GROUP
        OBJECTS {
            tnAm2125bPortConfigFunction
        }
        STATUS         current
        DESCRIPTION    ""
        ::= { tnOpticalPortConfigGroups 175 }

    tn112snx10PortConfigScalarsGroup OBJECT-GROUP
        OBJECTS {
            tn112snx10PortConfigAttributeTotal
        }
        STATUS         current
        DESCRIPTION    ""
        ::= { tnOpticalPortConfigGroups 176 }

    tn112snx10PortConfigGroup OBJECT-GROUP
        OBJECTS {
            tn112snx10PortConfigFunction
        }
        STATUS         current
        DESCRIPTION    ""
        ::= { tnOpticalPortConfigGroups 177 }

    tn112sna1PortConfigScalarsGroup OBJECT-GROUP
        OBJECTS {
            tn112sna1PortConfigAttributeTotal
        }
        STATUS         current
        DESCRIPTION    ""
        ::= { tnOpticalPortConfigGroups 178 }

    tn112sna1PortConfigGroup OBJECT-GROUP
        OBJECTS {
            tn112sna1PortConfigFunction
        }
        STATUS         current
        DESCRIPTION    ""
        ::= { tnOpticalPortConfigGroups 179 }

--    obsolete
--    tn11qta4PortConfigScalarsGroup OBJECT-GROUP ::= { tnOpticalPortConfigGroups 180 }
--    tn11qta4PortConfigGroup OBJECT-GROUP ::= { tnOpticalPortConfigGroups 181 }

    tn1dpp24mPortConfigScalarsGroup OBJECT-GROUP
        OBJECTS {
            tn1dpp24mPortConfigAttributeTotal
        }
        STATUS         current
        DESCRIPTION    ""
        ::= { tnOpticalPortConfigGroups 182 }

    tn1dpp24mPortConfigGroup OBJECT-GROUP
        OBJECTS {
            tn1dpp24mPortConfigFunction
        }
        STATUS         current
        DESCRIPTION    ""
        ::= { tnOpticalPortConfigGroups 183 }

    tnDwdmCmnOtu3Odu3ClientPortConfigGroup OBJECT-GROUP
        OBJECTS {
            tnDwdmCmnClientPortOchOtu3FecMode,
            tnDwdmCmnClientPortOchOtu3Rate,
            tnDwdmCmnClientPortOtu3TransmittedTti,
            tnDwdmCmnClientPortOtu3ExpectedTti,
            tnDwdmCmnClientPortOtu3TimConsequenceAction,
            tnDwdmCmnClientPortOtu3TimDetectionMode,
            tnDwdmCmnClientPortOdu3TransmittedTti,
            tnDwdmCmnClientPortOdu3ExpectedTti,
            tnDwdmCmnClientPortOdu3TimDetectionMode
        }
        STATUS         current
        DESCRIPTION    ""
        ::= { tnOpticalPortConfigGroups 184 }

    tnul43scupPortConfigScalarsGroup OBJECT-GROUP
        OBJECTS {
            tnul43scupPortConfigAttributeTotal
        }
        STATUS         current
        DESCRIPTION    ""
        ::= { tnOpticalPortConfigGroups 185 }

    tnul43scupPortConfigGroup OBJECT-GROUP
        OBJECTS {
            tnul43scupPortConfigFunction
        }
        STATUS         current
        DESCRIPTION    ""
        ::= { tnOpticalPortConfigGroups 186 }

    tnul11qcupPortConfigScalarsGroup OBJECT-GROUP
        OBJECTS {
            tnul11qcupPortConfigAttributeTotal
        }
        STATUS         current
        DESCRIPTION    ""
        ::= { tnOpticalPortConfigGroups 187 }

    tnul11qcupPortConfigGroup OBJECT-GROUP
        OBJECTS {
            tnul11qcupPortConfigFunction
        }
        STATUS         current
        DESCRIPTION    ""
        ::= { tnOpticalPortConfigGroups 188 }

    tn11qpen4PortConfigScalarsGroup OBJECT-GROUP
        OBJECTS {
            tn11qpen4PortConfigAttributeTotal
        }
        STATUS         current
        DESCRIPTION    ""
        ::= { tnOpticalPortConfigGroups 189 }

    tn11qpen4PortConfigGroup OBJECT-GROUP
        OBJECTS {
            tn11qpen4PortConfigFunction,
            tn11qpen4PortConfigEncryptionOperateKeySwitch,
            tn11qpen4PortConfigEncryptionState,
            tn11qpen4PortConfigEncryptionNextKey,
            tn11qpen4PortConfigEncryptionWKAT
        }
        STATUS         current
        DESCRIPTION    ""
        ::= { tnOpticalPortConfigGroups 190 }

    tn43scx4ePortConfigScalarsGroup OBJECT-GROUP
        OBJECTS {
            tn43scx4ePortConfigAttributeTotal
        }
        STATUS         current
        DESCRIPTION    ""
        ::= { tnOpticalPortConfigGroups 191 }

    tn43scx4ePortConfigGroup OBJECT-GROUP
        OBJECTS {
            tn43scx4ePortConfigFunction
        }
        STATUS         current
        DESCRIPTION    ""
        ::= { tnOpticalPortConfigGroups 192 }

    tn43scge1PortConfigScalarsGroup OBJECT-GROUP
        OBJECTS {
            tn43scge1PortConfigAttributeTotal
        }
        STATUS         current
        DESCRIPTION    ""
        ::= { tnOpticalPortConfigGroups 193 }

    tn43scge1PortConfigGroup OBJECT-GROUP
        OBJECTS {
            tn43scge1PortConfigFunction
        }
        STATUS         current
        DESCRIPTION    ""
        ::= { tnOpticalPortConfigGroups 194 }

    tn11qpe24PortConfigScalarsGroup OBJECT-GROUP
        OBJECTS {
            tn11qpe24PortConfigAttributeTotal
        }
        STATUS         current
        DESCRIPTION    ""
        ::= { tnOpticalPortConfigGroups 195 }

    tn11qpe24PortConfigGroup OBJECT-GROUP
        OBJECTS {
            tn11qpe24PortConfigFunction
        }
        STATUS         current
        DESCRIPTION    ""
        ::= { tnOpticalPortConfigGroups 196 }

    tn11star1aPortConfigScalarsGroup OBJECT-GROUP
        OBJECTS {
            tn11star1aPortConfigAttributeTotal
        }
        STATUS         current
        DESCRIPTION    ""
        ::= { tnOpticalPortConfigGroups 197 }

    tn11star1aPortConfigGroup OBJECT-GROUP
        OBJECTS {
            tn11star1aPortConfigFunction
        }
        STATUS         current
        DESCRIPTION    ""
        ::= { tnOpticalPortConfigGroups 198 }

    tnMvac8bPortConfigScalarsGroup OBJECT-GROUP
        OBJECTS {
            tnMvac8bPortConfigAttributeTotal
        }
        STATUS         current
        DESCRIPTION    ""
        ::= { tnOpticalPortConfigGroups 199 }

    tnMvac8bPortConfigGroup OBJECT-GROUP
        OBJECTS {
            tnMvac8bPortConfigFunction
        }
        STATUS         current
        DESCRIPTION    ""
        ::= { tnOpticalPortConfigGroups 200 }

    tnWssAttenPortConfigScalarsGroup OBJECT-GROUP
        OBJECTS {
            tnWssAttenPortConfigAttributeTotal
        }
        STATUS         current
        DESCRIPTION    ""
        ::= { tnOpticalPortConfigGroups 201 }

    tnWssAttenPortConfigGroup OBJECT-GROUP
        OBJECTS {
            tnWssAttenPortConfigWssAtten
        }
        STATUS         current
        DESCRIPTION    ""
        ::= { tnOpticalPortConfigGroups 202 }

    tnWr8c88afPortConfigScalarsGroup OBJECT-GROUP
        OBJECTS {
            tnWr8c88afPortConfigAttributeTotal
        }
        STATUS         current
        DESCRIPTION    ""
        ::= { tnOpticalPortConfigGroups 203 }

    tnWr8c88afPortConfigGroup OBJECT-GROUP
        OBJECTS {
            tnWr8c88afPortConfigFunction
        }
        STATUS         current
        DESCRIPTION    ""
        ::= { tnOpticalPortConfigGroups 204 }

    tncl10an10gPortConfigScalarsGroup OBJECT-GROUP
        OBJECTS {
            tncl10an10gPortConfigAttributeTotal
        }
        STATUS         current
        DESCRIPTION    ""
        ::= { tnOpticalPortConfigGroups 205 }

    tncl10an10gPortConfigGroup OBJECT-GROUP
        OBJECTS {
            tncl10an10gPortConfigFunction
        }
        STATUS         current
        DESCRIPTION    ""
        ::= { tnOpticalPortConfigGroups 206 }

    tncl24anmPortConfigScalarsGroup OBJECT-GROUP
        OBJECTS {
            tncl24anmPortConfigAttributeTotal
        }
        STATUS         current
        DESCRIPTION    ""
        ::= { tnOpticalPortConfigGroups 207 }

    tncl24anmPortConfigGroup OBJECT-GROUP
        OBJECTS {
            tncl24anmPortConfigFunction
        }
        STATUS         current
        DESCRIPTION    ""
        ::= { tnOpticalPortConfigGroups 208 }

    tnOpsbPortConfigScalarsGroup OBJECT-GROUP
        OBJECTS {
            tnOpsbPortConfigAttributeTotal
        }
        STATUS         current
        DESCRIPTION    ""
        ::= { tnOpticalPortConfigGroups 209 }

    tnOpsbPortConfigGroup OBJECT-GROUP
        OBJECTS {
            tnOpsbPortConfigFunction
        }
        STATUS         current
        DESCRIPTION    ""
        ::= { tnOpticalPortConfigGroups 210 }

    tnOpsPortConfigScalarsGroup OBJECT-GROUP
        OBJECTS {
            tnOpsPortConfigAttributeTotal
        }
        STATUS         current
        DESCRIPTION    ""
        ::= { tnOpticalPortConfigGroups 211 }

    tnOpsPortConfigGroup OBJECT-GROUP
        OBJECTS {
            tnOpsPortConfigSwitchingThreshold,
            tnOpsPortConfigSwitchingThresholdTolerance,
            tnOpsPortConfigTransmitAttenuation,
            tnOpsPortConfigSwitchingThreshCalcControl
        }
        STATUS         current
        DESCRIPTION    ""
        ::= { tnOpticalPortConfigGroups 212 }

    tn11dpe12aPortConfigScalarsGroup OBJECT-GROUP
        OBJECTS {
            tn11dpe12aPortConfigAttributeTotal
        }
        STATUS         current
        DESCRIPTION    ""
        ::= { tnOpticalPortConfigGroups 213 }

    tn11dpe12aPortConfigGroup OBJECT-GROUP
        OBJECTS {
            tn11dpe12aPortConfigFunction,
            tn11dpe12aPortConfigQinQModeTPID,
            tn11dpe12aPortConfigQinQModePVID,
            tn11dpe12aPortConfigLPTConsequenceAction,
            tn11dpe12aPortConfigMtu,
            tn11dpe12aPortConfigPortRole,
            tn11dpe12aPortConfigPtpTrans,
            tn11dpe12aPortConfigCompatibilityMode,
            tn11dpe12aPortConfigFlowControl
        }
        STATUS         current
        DESCRIPTION    ""
        ::= { tnOpticalPortConfigGroups 214 }

    tnul130scupPortConfigScalarsGroup OBJECT-GROUP
        OBJECTS {
            tnul130scupPortConfigAttributeTotal
        }
        STATUS         current
        DESCRIPTION    ""
        ::= { tnOpticalPortConfigGroups 215 }

    tnul130scupPortConfigGroup OBJECT-GROUP
        OBJECTS {
            tnul130scupPortConfigFunction
        }
        STATUS         current
        DESCRIPTION    ""
        ::= { tnOpticalPortConfigGroups 216 }

    tn130scx10PortConfigScalarsGroup OBJECT-GROUP
        OBJECTS {
            tn130scx10PortConfigAttributeTotal
        }
        STATUS         current
        DESCRIPTION    ""
        ::= { tnOpticalPortConfigGroups 217 }

    tn130scx10PortConfigGroup OBJECT-GROUP
        OBJECTS {
            tn130scx10PortConfigFunction
        }
        STATUS         current
        DESCRIPTION    ""
        ::= { tnOpticalPortConfigGroups 218 }

    tnA2p2125PortConfigScalarsGroup OBJECT-GROUP
        OBJECTS {
            tnA2p2125PortConfigAttributeTotal
        }
        STATUS         current
        DESCRIPTION    ""
        ::= { tnOpticalPortConfigGroups 219 }

    tnA2p2125PortConfigGroup OBJECT-GROUP
        OBJECTS {
            tnA2p2125PortConfigFunction
        }
        STATUS         current
        DESCRIPTION    ""
        ::= { tnOpticalPortConfigGroups 220 }

    tn4qpa8PortConfigScalarsGroup OBJECT-GROUP
        OBJECTS {
            tn4qpa8PortConfigAttributeTotal
        }
        STATUS         current
        DESCRIPTION    ""
        ::= { tnOpticalPortConfigGroups 221 }

    tn4qpa8PortConfigGroup OBJECT-GROUP
        OBJECTS {
            tn4qpa8PortConfigFunction,
            tn4qpa8PortConfigTtpPresent
        }
        STATUS         current
        DESCRIPTION    ""
        ::= { tnOpticalPortConfigGroups 222 }

    tnOt112pdm11PortConfigScalarsGroup OBJECT-GROUP
        OBJECTS {
            tnOt112pdm11PortConfigAttributeTotal
        }
        STATUS         current
        DESCRIPTION    ""
        ::= { tnOpticalPortConfigGroups 223 }

    tnOt112pdm11PortConfigGroup OBJECT-GROUP
        OBJECTS {
            tnOt112pdm11PortConfigFunction
        }
        STATUS         current
        DESCRIPTION    ""
        ::= { tnOpticalPortConfigGroups 224 }

    tnWtocmaPortConfigScalarsGroup OBJECT-GROUP
        OBJECTS {
            tnWtocmaPortConfigAttributeTotal
        }
        STATUS         current
        DESCRIPTION    ""
        ::= { tnOpticalPortConfigGroups 225 }

    tnWtocmaPortConfigGroup OBJECT-GROUP
        OBJECTS {
            tnWtocmaPortConfigFunction,
            tnWtocmaPortConfigOsnrMeasure,
            tnWtocmaPortConfigOsnrClear
        }
        STATUS         current
        DESCRIPTION    ""
        ::= { tnOpticalPortConfigGroups 226 }

    tnPtpctlPortConfigScalarsGroup OBJECT-GROUP
        OBJECTS {
            tnPtpctlPortConfigAttributeTotal
        }
        STATUS         current
        DESCRIPTION    ""
        ::= { tnOpticalPortConfigGroups 227 }

    tnPtpctlPortConfigGroup OBJECT-GROUP
        OBJECTS {
            tnPtpctlPortConfigFunction
        }
        STATUS         current
        DESCRIPTION    ""
        ::= { tnOpticalPortConfigGroups 228 }

    tnPtpioPortConfigScalarsGroup OBJECT-GROUP
        OBJECTS {
            tnPtpioPortConfigAttributeTotal
        }
        STATUS         current
        DESCRIPTION    ""
        ::= { tnOpticalPortConfigGroups 229 }

    tnPtpioPortConfigGroup OBJECT-GROUP
        OBJECTS {
            tnPtpioPortConfigFunction,
            tnPtpioPortConfigSigPortConnFromPort,
            tnPtpioPortConfigSigPortConnToPort
        }
        STATUS         current
        DESCRIPTION    ""
        ::= { tnOpticalPortConfigGroups 230 }

    tnIo24et1gbPortConfigScalarsGroup OBJECT-GROUP
        OBJECTS {
            tnIo24et1gbPortConfigAttributeTotal
        }
        STATUS         current
        DESCRIPTION    ""
        ::= { tnOpticalPortConfigGroups 231 }

    tnIo24et1gbPortConfigGroup OBJECT-GROUP
        OBJECTS {
            tnIo24et1gbPortConfigFunction
        }
        STATUS         current
        DESCRIPTION    ""
        ::= { tnOpticalPortConfigGroups 232 }

    tnDwdmIoPortConfigScalarsGroup OBJECT-GROUP
        OBJECTS {
            tnDwdmIoPortConfigAttributeTotal
        }
        STATUS         current
        DESCRIPTION    ""
        ::= { tnOpticalPortConfigGroups 233 }

    tnDwdmIoPortConfigGroup OBJECT-GROUP
        OBJECTS {
            tnDwdmIoPortRole
        }
        STATUS         current
        DESCRIPTION    ""
        ::= { tnOpticalPortConfigGroups 234 }

    tnIo4an10gPortConfigScalarsGroup OBJECT-GROUP
        OBJECTS {
            tnIo4an10gPortConfigAttributeTotal
        }
        STATUS         current
        DESCRIPTION    ""
        ::= { tnOpticalPortConfigGroups 235 }

    tnIo4an10gPortConfigGroup OBJECT-GROUP
        OBJECTS {
            tnIo4an10gPortConfigFunction
        }
        STATUS         current
        DESCRIPTION    ""
        ::= { tnOpticalPortConfigGroups 236 }

    tnIo8et1gbPortConfigScalarsGroup OBJECT-GROUP
        OBJECTS {
            tnIo8et1gbPortConfigAttributeTotal
        }
        STATUS         current
        DESCRIPTION    ""
        ::= { tnOpticalPortConfigGroups 237 }

    tnIo8et1gbPortConfigGroup OBJECT-GROUP
        OBJECTS {
            tnIo8et1gbPortConfigFunction
        }
        STATUS         current
        DESCRIPTION    ""
        ::= { tnOpticalPortConfigGroups 238 }

    tnIo10et10gPortConfigScalarsGroup OBJECT-GROUP
        OBJECTS {
            tnIo10et10gPortConfigAttributeTotal
        }
        STATUS         current
        DESCRIPTION    ""
        ::= { tnOpticalPortConfigGroups 239 }

    tnIo10et10gPortConfigGroup OBJECT-GROUP
        OBJECTS {
            tnIo10et10gPortConfigFunction
        }
        STATUS         current
        DESCRIPTION    ""
        ::= { tnOpticalPortConfigGroups 240 }

    tnUl11qcupcPortConfigScalarsGroup OBJECT-GROUP
        OBJECTS {
            tnUl11qcupcPortConfigAttributeTotal
        }
        STATUS         current
        DESCRIPTION    ""
        ::= { tnOpticalPortConfigGroups 241 }

    tnUl11qcupcPortConfigGroup OBJECT-GROUP
        OBJECTS {
            tnUl11qcupcPortConfigFunction
        }
        STATUS         current
        DESCRIPTION    ""
        ::= { tnOpticalPortConfigGroups 242 }

    tnOt520scx4PortConfigScalarsGroup OBJECT-GROUP
        OBJECTS {
            tnOt520scx4PortConfigAttributeTotal
        }
        STATUS         current
        DESCRIPTION    ""
        ::= { tnOpticalPortConfigGroups 243 }

    tnOt520scx4PortConfigGroup OBJECT-GROUP
        OBJECTS {
            tnOt520scx4PortConfigFunction
        }
        STATUS         current
        DESCRIPTION    ""
        ::= { tnOpticalPortConfigGroups 244 }

    tnWssAprPortConfigScalarsGroup OBJECT-GROUP
        OBJECTS {
            tnWssAprPortConfigAttributeTotal
        }
        STATUS         current
        DESCRIPTION    ""
        ::= { tnOpticalPortConfigGroups 245 }

    tnWssAprPortConfigGroup OBJECT-GROUP
        OBJECTS {
            tnWssAprPortConfigAprHoldOffTime
        }
        STATUS         current
        DESCRIPTION    ""
        ::= { tnOpticalPortConfigGroups 246 }

    tnPowerFilterPortConfigScalarsGroup OBJECT-GROUP
        OBJECTS {
            tnPowerFilterPortConfigAttributeTotal
        }
        STATUS         current
        DESCRIPTION    ""
        ::= { tnOpticalPortConfigGroups 247 }

    tnPowerFilterPortConfigGroup OBJECT-GROUP
        OBJECTS {
            tnPowerFilterPortConfigFunction
        }
        STATUS         current
        DESCRIPTION    ""
        ::= { tnOpticalPortConfigGroups 248 }

    tn11ope8PortConfigScalarsGroup OBJECT-GROUP
        OBJECTS {
            tn11ope8PortConfigAttributeTotal
        }
        STATUS         current
        DESCRIPTION    ""
        ::= { tnOpticalPortConfigGroups 249 }

    tn11ope8PortConfigGroup OBJECT-GROUP
        OBJECTS {
            tn11ope8PortConfigFunction
        }
        STATUS         current
        DESCRIPTION    ""
        ::= { tnOpticalPortConfigGroups 250 }

    tn11qce12xPortConfigScalarsGroup OBJECT-GROUP
        OBJECTS {
            tn11qce12xPortConfigAttributeTotal
        }
        STATUS         current
        DESCRIPTION    ""
        ::= { tnOpticalPortConfigGroups 251 }

    tn11qce12xPortConfigGroup OBJECT-GROUP
        OBJECTS {
            tn11qce12xPortConfigFunction
        }
        STATUS         current
        DESCRIPTION    ""
        ::= { tnOpticalPortConfigGroups 252 }

    tnAm2625aPortConfigScalarsGroup OBJECT-GROUP
        OBJECTS {
            tnAm2625aPortConfigAttributeTotal
        }
        STATUS         current
        DESCRIPTION    ""
        ::= { tnOpticalPortConfigGroups 253 }

    tnAm2625aPortConfigGroup OBJECT-GROUP
        OBJECTS {
            tnAm2625aPortConfigFunction
        }
        STATUS         current
        DESCRIPTION    ""
        ::= { tnOpticalPortConfigGroups 254 }

    tnAm2032aPortConfigScalarsGroup OBJECT-GROUP
        OBJECTS {
            tnAm2032aPortConfigAttributeTotal
        }
        STATUS         current
        DESCRIPTION    ""
        ::= { tnOpticalPortConfigGroups 255 }

    tnAm2032aPortConfigGroup OBJECT-GROUP
        OBJECTS {
            tnAm2032aPortConfigFunction
        }
        STATUS         current
        DESCRIPTION    ""
        ::= { tnOpticalPortConfigGroups 256 }

    tnOt260scx2PortConfigScalarsGroup OBJECT-GROUP
        OBJECTS {
            tnOt260scx2PortConfigAttributeTotal
        }
        STATUS         current
        DESCRIPTION    ""
        ::= { tnOpticalPortConfigGroups 257 }

    tnOt260scx2PortConfigGroup OBJECT-GROUP
        OBJECTS {
            tnOt260scx2PortConfigFunction
        }
        STATUS         current
        DESCRIPTION    ""
        ::= { tnOpticalPortConfigGroups 258 }

    tnOt130snx10PortConfigScalarsGroup OBJECT-GROUP
        OBJECTS {
            tnOt130snx10PortConfigAttributeTotal
        }
        STATUS         current
        DESCRIPTION    ""
        ::= { tnOpticalPortConfigGroups 259 }

    tnOt130snx10PortConfigGroup OBJECT-GROUP
        OBJECTS {
            tnOt130snx10PortConfigFunction
        }
        STATUS         current
        DESCRIPTION    ""
        ::= { tnOpticalPortConfigGroups 260 }

    tnIo24anmbPortConfigScalarsGroup OBJECT-GROUP
        OBJECTS {
            tnIo24anmbPortConfigAttributeTotal
        }
        STATUS         current
        DESCRIPTION    ""
        ::= { tnOpticalPortConfigGroups 261 }

    tnIo24anmbPortConfigGroup OBJECT-GROUP
        OBJECTS {
            tnIo24anmbPortConfigFunction
        }
        STATUS         current
        DESCRIPTION    ""
        ::= { tnOpticalPortConfigGroups 262 }

    tnOt11dpm8PortConfigScalarsGroup OBJECT-GROUP
        OBJECTS {
            tnOt11dpm8PortConfigAttributeTotal
        }
        STATUS         current
        DESCRIPTION    ""
        ::= { tnOpticalPortConfigGroups 263 }

    tnOt11dpm8PortConfigGroup OBJECT-GROUP
        OBJECTS {
            tnOt11dpm8PortConfigFunction
        }
        STATUS         current
        DESCRIPTION    ""
        ::= { tnOpticalPortConfigGroups 264 }

    tnOt11dpm4mPortConfigScalarsGroup OBJECT-GROUP
        OBJECTS {
            tnOt11dpm4mPortConfigAttributeTotal
        }
        STATUS         current
        DESCRIPTION    ""
        ::= { tnOpticalPortConfigGroups 265 }

    tnOt11dpm4mPortConfigGroup OBJECT-GROUP
        OBJECTS {
            tnOt11dpm4mPortConfigFunction
        }
        STATUS         current
        DESCRIPTION    ""
        ::= { tnOpticalPortConfigGroups 266 }

    tnUl130scupbPortConfigScalarsGroup OBJECT-GROUP
        OBJECTS {
            tnUl130scupbPortConfigAttributeTotal
        }
        STATUS         current
        DESCRIPTION    ""
        ::= { tnOpticalPortConfigGroups 267 }

    tnUl130scupbPortConfigGroup OBJECT-GROUP
        OBJECTS {
            tnUl130scupbPortConfigFunction
        }
        STATUS         current
        DESCRIPTION    ""
        ::= { tnOpticalPortConfigGroups 268 }

    tnOt112sdx11PortConfigScalarsGroup OBJECT-GROUP
        OBJECTS {
            tnOt112sdx11PortConfigAttributeTotal
        }
        STATUS         current
        DESCRIPTION    ""
        ::= { tnOpticalPortConfigGroups 269 }

    tnOt112sdx11PortConfigGroup OBJECT-GROUP
        OBJECTS {
            tnOt112sdx11PortConfigFunction,
            tnOt112sdx11PortConfigLinkGroupId,
            tnOt112sdx11ProgrammedNwOutputPower
        }
        STATUS         current
        DESCRIPTION    ""
        ::= { tnOpticalPortConfigGroups 270 }

    tnAa2donwPortConfigScalarsGroup OBJECT-GROUP
        OBJECTS {
            tnAa2donwPortConfigAttributeTotal
        }
        STATUS         current
        DESCRIPTION    ""
        ::= { tnOpticalPortConfigGroups 271 }

    tnAa2donwPortConfigGroup OBJECT-GROUP
        OBJECTS {
            tnAa2donwPortConfigFunction
        }
        STATUS         current
        DESCRIPTION    ""
        ::= { tnOpticalPortConfigGroups 272 }

    tnOt130sca1PortConfigScalarsGroup OBJECT-GROUP
        OBJECTS {
            tnOt130sca1PortConfigAttributeTotal
        }
        STATUS         current
        DESCRIPTION    ""
        ::= { tnOpticalPortConfigGroups 273 }

    tnOt130sca1PortConfigGroup OBJECT-GROUP
        OBJECTS {
            tnOt130sca1PortConfigFunction
        }
        STATUS         current
        DESCRIPTION    ""
        ::= { tnOpticalPortConfigGroups 274 }

    tnIo10an10gbPortConfigScalarsGroup OBJECT-GROUP
        OBJECTS {
            tnIo10an10gbPortConfigAttributeTotal
        }
        STATUS         current
        DESCRIPTION    ""
        ::= { tnOpticalPortConfigGroups 275 }

    tnIo10an10gbPortConfigGroup OBJECT-GROUP
        OBJECTS {
            tnIo10an10gbPortConfigFunction
        }
        STATUS         current
        DESCRIPTION    ""
        ::= { tnOpticalPortConfigGroups 276 }

    tnIo10et10gbPortConfigScalarsGroup OBJECT-GROUP
        OBJECTS {
            tnIo10et10gbPortConfigAttributeTotal
        }
        STATUS         current
        DESCRIPTION    ""
        ::= { tnOpticalPortConfigGroups 277 }

    tnIo10et10gbPortConfigGroup OBJECT-GROUP
        OBJECTS {
            tnIo10et10gbPortConfigFunction
        }
        STATUS         current
        DESCRIPTION    ""
        ::= { tnOpticalPortConfigGroups 278 }

    tnPsc1x6PortConfigScalarsGroup OBJECT-GROUP
        OBJECTS {
            tnPsc1x6PortConfigAttributeTotal
        }
        STATUS         current
        DESCRIPTION    ""
        ::= { tnOpticalPortConfigGroups 279 }

    tnPsc1x6PortConfigGroup OBJECT-GROUP
        OBJECTS {
            tnPsc1x6PortConfigFunction
        }
        STATUS         current
        DESCRIPTION    ""
        ::= { tnOpticalPortConfigGroups 280 }

    tnWr20tfPortConfigScalarsGroup OBJECT-GROUP
        OBJECTS {
            tnWr20tfPortConfigAttributeTotal
        }
        STATUS         current
        DESCRIPTION    ""
        ::= { tnOpticalPortConfigGroups 281 }

    tnWr20tfPortConfigGroup OBJECT-GROUP
        OBJECTS {
            tnWr20tfPortConfigFunction,
            tnWr20tfPortConfigDropInitTargetPower,
            tnWr20tfPortConfigExpressTargetPower,
            tnWr20tfPortConfigDropMaxTargetPower,
            tnWr20tfPortConfigDropMinTargetPower
        }
        STATUS         current
        DESCRIPTION    ""
        ::= { tnOpticalPortConfigGroups 282 }

    tnWtocmfPortConfigScalarsGroup OBJECT-GROUP
        OBJECTS {
            tnWtocmfPortConfigAttributeTotal
        }
        STATUS         current
        DESCRIPTION    ""
        ::= { tnOpticalPortConfigGroups 283 }

    tnWtocmfPortConfigGroup OBJECT-GROUP
        OBJECTS {
            tnWtocmfPortConfigFunction
        }
        STATUS         current
        DESCRIPTION    ""
        ::= { tnOpticalPortConfigGroups 284 }

    tnAswgPortConfigScalarsGroup OBJECT-GROUP
        OBJECTS {
            tnAswgPortConfigAttributeTotal
        }
        STATUS         current
        DESCRIPTION    ""
        ::= { tnOpticalPortConfigGroups 285 }

    tnAswgPortConfigGroup OBJECT-GROUP
        OBJECTS {
            tnAswgPortConfigFunction
        }
        STATUS         current
        DESCRIPTION    ""
        ::= { tnOpticalPortConfigGroups 286 }

    tnA4pswgPortConfigScalarsGroup OBJECT-GROUP
        OBJECTS {
            tnA4pswgPortConfigAttributeTotal
        }
        STATUS         current
        DESCRIPTION    ""
        ::= { tnOpticalPortConfigGroups 287 }

    tnA4pswgPortConfigGroup OBJECT-GROUP
        OBJECTS {
            tnA4pswgPortConfigFunction
        }
        STATUS         current
        DESCRIPTION    ""
        ::= { tnOpticalPortConfigGroups 288 }

    tnOtdrPortConfigScalarsGroup OBJECT-GROUP
        OBJECTS {
            tnOtdrPortConfigAttributeTotal
        }
        STATUS         current
        DESCRIPTION    ""
        ::= { tnOpticalPortConfigGroups 289 }

    tnOtdrPortConfigGroup OBJECT-GROUP
        OBJECTS {
            tnOtdrPortConfigFunction,
            tnOtdrPortConfigConnAddress
        }
        STATUS         current
        DESCRIPTION    ""
        ::= { tnOpticalPortConfigGroups 290 }

    tnWr20tfmPortConfigScalarsGroup OBJECT-GROUP
        OBJECTS {
            tnWr20tfmPortConfigAttributeTotal
        }
        STATUS         current
        DESCRIPTION    ""
        ::= { tnOpticalPortConfigGroups 291 }

    tnWr20tfmPortConfigGroup OBJECT-GROUP
        OBJECTS {
            tnWr20tfmPortConfigFunction,
            tnWr20tfmPortConfigDropInitTargetPower,
            tnWr20tfmPortConfigExpressTargetPower,
            tnWr20tfmPortConfigDropMaxTargetPower,
            tnWr20tfmPortConfigDropMinTargetPower,
--          obsolete
--          tnWr20tfmPortConfigExecuteForcedDropDisposition,
            tnWr20tfmPortConfigEndForcedDropDisposition,
--          obsolete
--          tnWr20tfmPortConfigExecuteForcedAddDisposition,
            tnWr20tfmPortConfigEndForcedAddDisposition,
            tnWr20tfmPortConfigForceAllchannelsDropDisposition,
            tnWr20tfmPortConfigForceAllchannelsAddDisposition
        }
        STATUS         current
        DESCRIPTION    ""
        ::= { tnOpticalPortConfigGroups 292 }

    tnAar8aPortConfigScalarsGroup OBJECT-GROUP
        OBJECTS {
            tnAar8aPortConfigAttributeTotal
        }
        STATUS         current
        DESCRIPTION    ""
        ::= { tnOpticalPortConfigGroups 293 }

    tnAar8aPortConfigGroup OBJECT-GROUP
        OBJECTS {
            tnAar8aPortConfigFunction
        }
        STATUS         current
        DESCRIPTION    ""
        ::= { tnOpticalPortConfigGroups 294 }

    tnMcs8x16PortConfigScalarsGroup OBJECT-GROUP
        OBJECTS {
            tnMcs8x16PortConfigAttributeTotal
        }
        STATUS         current
        DESCRIPTION    ""
        ::= { tnOpticalPortConfigGroups 295 }

    tnMcs8x16PortConfigGroup OBJECT-GROUP
        OBJECTS {
            tnMcs8x16PortConfigFunction
        }
        STATUS         current
        DESCRIPTION    ""
        ::= { tnOpticalPortConfigGroups 296 }

    tnMsh8fsmPortConfigScalarsGroup OBJECT-GROUP
        OBJECTS {
            tnMsh8fsmPortConfigAttributeTotal
        }
        STATUS         current
        DESCRIPTION    ""
        ::= { tnOpticalPortConfigGroups 297 }

    tnMsh8fsmPortConfigGroup OBJECT-GROUP
        OBJECTS {
            tnMsh8fsmPortConfigFunction
        }
        STATUS         current
        DESCRIPTION    ""
        ::= { tnOpticalPortConfigGroups 298 }

    tnMcsPortConfigScalarsGroup OBJECT-GROUP
        OBJECTS {
           tnMcsPortConfigAttributeTotal
        }
        STATUS         current
        DESCRIPTION    ""
        ::= { tnOpticalPortConfigGroups 299 }

    tnMcsPortConfigGroup OBJECT-GROUP
        OBJECTS {
           tnMcsPortConfigTargetForDispositionForce,
           tnMcsPortConfigExecuteForceDispositionToTarget
        }
        STATUS         current
        DESCRIPTION    ""
        ::= { tnOpticalPortConfigGroups 300 }

    tnAarPortConfigScalarsGroup OBJECT-GROUP
        OBJECTS {
            tnAarPortConfigAttributeTotal
        }
        STATUS         current
        DESCRIPTION    ""
        ::= { tnOpticalPortConfigGroups 301 }

    tnAarPortConfigGroup OBJECT-GROUP
        OBJECTS {
            tnAarPortConfigOperatingMode,
            tnAarPortConfigPowerGainTarget,
            tnAarPortConfigSignalPowerTarget
        }
        STATUS         current
        DESCRIPTION    ""
        ::= { tnOpticalPortConfigGroups 302 }

    tnWr20tfmPortChannelConfigScalarsGroup OBJECT-GROUP
        OBJECTS {
            tnWr20tfmPortChannelConfigAttributeTotal
        }
        STATUS         current
        DESCRIPTION    ""
        ::= { tnOpticalPortConfigGroups 303 }

    tnWr20tfmPortChannelConfigGroup OBJECT-GROUP
        OBJECTS {
            tnWr20tfmPortChannelConfigTargetForcedDropDisposition,
            tnWr20tfmPortChannelConfigTargetForcedAddDisposition
        }
        STATUS         current
        DESCRIPTION    ""
        ::= { tnOpticalPortConfigGroups 304 }

    tnMpoPortConfigScalarsGroup OBJECT-GROUP
        OBJECTS {
            tnMpoPortConfigAttributeTotal
        }
        STATUS         current
        DESCRIPTION    ""
        ::= { tnOpticalPortConfigGroups 305 }

    tnMpoPortChannelConfigGroup OBJECT-GROUP
        OBJECTS {
            tnMpoPortConfigFarEndIfIndex,
            tnMpoPortConfigFarEndType,
            tnMpoPortConfigDescription
        }
        STATUS         current
        DESCRIPTION    ""
        ::= { tnOpticalPortConfigGroups 306 }

    tnIo4an100gPortConfigScalarsGroup OBJECT-GROUP
        OBJECTS {
            tnIo4an100gPortConfigAttributeTotal
        }
        STATUS         current
        DESCRIPTION    ""
        ::= { tnOpticalPortConfigGroups 307 }

    tnIo4an100gPortConfigGroup OBJECT-GROUP
        OBJECTS {
            tnIo4an100gPortConfigFunction
        }
        STATUS         current
        DESCRIPTION    ""
        ::= { tnOpticalPortConfigGroups 308 }

    tnIo30an10gPortConfigScalarsGroup OBJECT-GROUP
        OBJECTS {
            tnIo30an10gPortConfigAttributeTotal
        }
        STATUS         current
        DESCRIPTION    ""
        ::= { tnOpticalPortConfigGroups 309 }

    tnIo30an10gPortConfigGroup OBJECT-GROUP
        OBJECTS {
            tnIo30an10gPortConfigFunction
        }
        STATUS         current
        DESCRIPTION    ""
        ::= { tnOpticalPortConfigGroups 310 }

    tnIo30an300PortConfigScalarsGroup OBJECT-GROUP
        OBJECTS {
            tnIo30an300PortConfigAttributeTotal
        }
        STATUS         current
        DESCRIPTION    ""
        ::= { tnOpticalPortConfigGroups 311 }

    tnIo30an300PortConfigGroup OBJECT-GROUP
        OBJECTS {
            tnIo30an300PortConfigFunction
        }
        STATUS         current
        DESCRIPTION    ""
        ::= { tnOpticalPortConfigGroups 312 }

    tnIo4an400PortConfigScalarsGroup OBJECT-GROUP
        OBJECTS {
            tnIo4an400PortConfigAttributeTotal
        }
        STATUS         current
        DESCRIPTION    ""
        ::= { tnOpticalPortConfigGroups 313 }

    tnIo4an400PortConfigGroup OBJECT-GROUP
        OBJECTS {
            tnIo4an400PortConfigFunction
        }
        STATUS         current
        DESCRIPTION    ""
        ::= { tnOpticalPortConfigGroups 314 }

    tn12p120PortConfigScalarsGroup OBJECT-GROUP
        OBJECTS {
            tn12p120PortConfigAttributeTotal
        }
        STATUS         current
        DESCRIPTION    ""
        ::= { tnOpticalPortConfigGroups 315 }

    tn12p120PortConfigGroup OBJECT-GROUP
        OBJECTS {
            tn12p120PortConfigFunction
        }
        STATUS         current
        DESCRIPTION    ""
        ::= { tnOpticalPortConfigGroups 316 }

    tn20p200PortConfigScalarsGroup OBJECT-GROUP
        OBJECTS {
            tn20p200PortConfigAttributeTotal
        }
        STATUS         current
        DESCRIPTION    ""
        ::= { tnOpticalPortConfigGroups 317 }

    tn20p200PortConfigGroup OBJECT-GROUP
        OBJECTS {
            tn20p200PortConfigFunction
        }
        STATUS         current
        DESCRIPTION    ""
        ::= { tnOpticalPortConfigGroups 318 }

    tn1ud200PortConfigScalarsGroup OBJECT-GROUP
        OBJECTS {
            tn1ud200PortConfigAttributeTotal
        }
        STATUS         current
        DESCRIPTION    ""
        ::= { tnOpticalPortConfigGroups 319 }

    tn1ud200PortConfigGroup OBJECT-GROUP
        OBJECTS {
            tn1ud200PortConfigFunction
        }
        STATUS         current
        DESCRIPTION    ""
        ::= { tnOpticalPortConfigGroups 320 }

   tnOt130snq10PortConfigScalarsGroup OBJECT-GROUP
        OBJECTS {
            tnOt130snq10PortConfigAttributeTotal
        }
        STATUS         current
        DESCRIPTION    ""
        ::= { tnOpticalPortConfigGroups 321 }

    tnOt130snq10PortConfigGroup OBJECT-GROUP
        OBJECTS {
            tnOt130snq10PortConfigFunction
        }
        STATUS         current
        DESCRIPTION    ""
        ::= { tnOpticalPortConfigGroups 322 }

   tnIroadmvPortConfigScalarsGroup OBJECT-GROUP
        OBJECTS {
            tnIroadmvPortConfigAttributeTotal
        }
        STATUS         current
        DESCRIPTION    ""
        ::= { tnOpticalPortConfigGroups 323 }

    tnIroadmvPortConfigGroup OBJECT-GROUP
        OBJECTS {
            tnIroadmvPortConfigFunction
        }
        STATUS         current
        DESCRIPTION    ""
        ::= { tnOpticalPortConfigGroups 324 }

   tnIroadmfPortConfigScalarsGroup OBJECT-GROUP
        OBJECTS {
            tnIroadmfPortConfigAttributeTotal
        }
        STATUS         current
        DESCRIPTION    ""
        ::= { tnOpticalPortConfigGroups 325 }

    tnIroadmfPortConfigGroup OBJECT-GROUP
        OBJECTS {
            tnIroadmfPortConfigFunction
        }
        STATUS         current
        DESCRIPTION    ""
        ::= { tnOpticalPortConfigGroups 326 }

   tnIroadmPortConfigScalarsGroup OBJECT-GROUP
        OBJECTS {
            tnIroadmPortConfigAttributeTotal
        }
        STATUS         current
        DESCRIPTION    ""
        ::= { tnOpticalPortConfigGroups 327 }

    tnIroadmPortConfigGroup OBJECT-GROUP
        OBJECTS {
            tnIroadmPortConfigPowerGain,
            tnIroadmPortConfigPowerGainBackoff,
            tnIroadmPortConfigTargetTilt,
            tnIroadmPortConfigVoaSet,
            tnIroadmPortConfigNominalSpanLossOut,
            tnIroadmPortConfigFiberTypeOut,
            tnIroadmPortConfigFiberLengthKm,
            tnIroadmPortConfigAddMinChannelPower,
            tnIroadmPortConfigEgressOaRippleToRemove,
            tnIroadmPortConfigExpressMinChannelPower,
            tnIroadmPortConfigIngressOaGainMin,
            tnIroadmPortConfigIngressOaGainMax,
            tnIroadmPortConfigTargetPpcOut,
            tnIroadmPortConfigIngressOaTargetPpcOut,
            tnIroadmPortConfigIngressOaTargetPpcAdj,
            tnIroadmPortConfigSignalFailThreshold,
            tnIroadmPortConfigSignalDegradeThreshold,
            tnIroadmPortConfigAprDisable
        }
        STATUS         current
        DESCRIPTION    ""
        ::= { tnOpticalPortConfigGroups 328 }

     tnMonOcmPortConfigScalarsGroup OBJECT-GROUP
        OBJECTS {
            tnMonOcmPortConfigAttributeTotal
        }
        STATUS         current
        DESCRIPTION    ""
        ::= { tnOpticalPortConfigGroups 329 }

    tnMonOcmPortConfigGroup OBJECT-GROUP
        OBJECTS {
            tnMonOcmPortConfigFunction
        }
        STATUS         current
        DESCRIPTION    ""
        ::= { tnOpticalPortConfigGroups 330 }

     tnUl2uc400PortConfigScalarsGroup OBJECT-GROUP
        OBJECTS {
            tnUl2uc400PortConfigAttributeTotal
        }
        STATUS         current
        DESCRIPTION    ""
        ::= { tnOpticalPortConfigGroups 331 }

    tnUl2uc400PortConfigGroup OBJECT-GROUP
        OBJECTS {
            tnUl2uc400PortConfigFunction
        }
        STATUS         current
        DESCRIPTION    ""
        ::= { tnOpticalPortConfigGroups 332 }

    tnUl4uc400PortConfigScalarsGroup OBJECT-GROUP
        OBJECTS {
            tnUl4uc400PortConfigAttributeTotal
        }
        STATUS         current
        DESCRIPTION    ""
        ::= { tnOpticalPortConfigGroups 333 }

    tnUl4uc400PortConfigGroup OBJECT-GROUP
        OBJECTS {
            tnUl4uc400PortConfigFunction
        }
        STATUS         current
        DESCRIPTION    ""
        ::= { tnOpticalPortConfigGroups 334 }

    tnUl20uc200PortConfigScalarsGroup OBJECT-GROUP
        OBJECTS {
            tnUl20uc200PortConfigAttributeTotal
        }
        STATUS         current
        DESCRIPTION    ""
        ::= { tnOpticalPortConfigGroups 335 }

    tnUl20uc200PortConfigGroup OBJECT-GROUP
        OBJECTS {
            tnUl20uc200PortConfigFunction
        }
        STATUS         current
        DESCRIPTION    ""
        ::= { tnOpticalPortConfigGroups 336 }

    tnD5x500PortConfigScalarsGroup OBJECT-GROUP
        OBJECTS {
            tnD5x500PortConfigAttributeTotal
        }
        STATUS         current
        DESCRIPTION    ""
        ::= { tnOpticalPortConfigGroups 337 }

    tnD5x500PortConfigGroup OBJECT-GROUP
        OBJECTS {
            tnD5x500PortConfigFunction
        }
        STATUS         current
        DESCRIPTION    ""
        ::= { tnOpticalPortConfigGroups 338 }

    tnOtS11M100PortConfigScalarsGroup OBJECT-GROUP
        OBJECTS {
            tnOtS11M100PortConfigAttributeTotal
        }
        STATUS         current
        DESCRIPTION    ""
        ::= { tnOpticalPortConfigGroups 339 }

    tnOtS11M100PortConfigGroup OBJECT-GROUP
        OBJECTS {
            tnOtS11M100PortConfigFunction
        }
        STATUS         current
        DESCRIPTION    ""
        ::= { tnOpticalPortConfigGroups 340 }

    tnMonOtdrPortConfigScalarsGroup OBJECT-GROUP
        OBJECTS {
            tnMonOtdrPortConfigAttributeTotal
        }
        STATUS         current
        DESCRIPTION    ""
        ::= { tnOpticalPortConfigGroups 341 }

    tnMonOtdrPortConfigGroup OBJECT-GROUP
        OBJECTS {
            tnMonOtdrPortConfigFunction,
            tnMonOtdrPortConfigConnAddress
        }
        STATUS         current
        DESCRIPTION    ""
        ::= { tnOpticalPortConfigGroups 342 }

    tnPSS96PowerFilterPortConfigScalarsGroup OBJECT-GROUP
        OBJECTS {
            tnPSS96PowerFilterPortConfigAttributeTotal
        }
        STATUS         current
        DESCRIPTION    ""
        ::= { tnOpticalPortConfigGroups 343 }

    tnPSS96PowerFilterPortConfigGroup OBJECT-GROUP
        OBJECTS {
            tnPSS96PowerFilterPortConfigFunction,
            tnPSS96ExpectedAmps
        }
        STATUS         current
        DESCRIPTION    ""
        ::= { tnOpticalPortConfigGroups 344 }

     tn12ce120PortConfigScalarsGroup OBJECT-GROUP
         OBJECTS {
             tn12ce120PortConfigAttributeTotal
         }
         STATUS         current
         DESCRIPTION    ""
         ::= { tnOpticalPortConfigGroups 345 }

     tn12ce120PortConfigGroup OBJECT-GROUP
         OBJECTS {
             tn12ce120PortConfigFunction
         }
         STATUS         current
         DESCRIPTION    ""
         ::= { tnOpticalPortConfigGroups 346 }

     tn1ce100PortConfigScalarsGroup OBJECT-GROUP
         OBJECTS {
             tn1ce100PortConfigAttributeTotal
         }
         STATUS         current
         DESCRIPTION    ""
         ::= { tnOpticalPortConfigGroups 347 }

     tn1ce100PortConfigGroup OBJECT-GROUP
         OBJECTS {
             tn1ce100PortConfigFunction
         }
                 STATUS         current
         DESCRIPTION    ""
         ::= { tnOpticalPortConfigGroups 348 }

    tnLcI1000PortConfigScalarsGroup  OBJECT-GROUP
        OBJECTS {
            tnLcI1000PortConfigAttributeTotal
        }
        STATUS         current
        DESCRIPTION    ""
        ::= { tnOpticalPortConfigGroups 349 }

    tnLcI1000PortConfigGroup  OBJECT-GROUP
        OBJECTS {
            tnLcI1000PortConfigFunction
        }
        STATUS         current
        DESCRIPTION    ""
        ::= { tnOpticalPortConfigGroups 350 }

--------------------------------------------------------------------------------
-- Conformance Port Info Group Definitions
--------------------------------------------------------------------------------
    tnSdhPortInfoScalarsGroup OBJECT-GROUP
        OBJECTS {
            tnSdhPortInfoAttributeTotal
        }
        STATUS         current
        DESCRIPTION    ""
        ::= { tnOpticalPortInfoGroups 1 }

    tnSdhPortInfoGroup OBJECT-GROUP
        OBJECTS {
            tnSdhPortRxSectionTrace,
--            obsolete
--            tnSdhPortTxSynchStatusMessage,
            tnSdhPortTiming,
--            obsolete
--            tnSdhPortRxSynchStatusMessage,
            tnSdhPortRxSectionTraceValid,
            tnSdhPortTxSynchronizeStatusMessage,
            tnSdhPortRxSynchronizeStatusMessage
        }
        STATUS         current
        DESCRIPTION    ""
        ::= { tnOpticalPortInfoGroups 2 }

--    obsolete
--    tnOC48STM16PortInfoScalarsGroup OBJECT-GROUP ::= { tnOpticalPortInfoGroups 3 }
--    tnOC48STM16PortInfoGroup OBJECT-GROUP ::= { tnOpticalPortInfoGroups 4 }
--    tnOC192STM64PortInfoScalarsGroup OBJECT-GROUP ::= { tnOpticalPortInfoGroups 5 }
--    tnOC192STM64PortInfoGroup OBJECT-GROUP ::= { tnOpticalPortInfoGroups 6 }
--    tnQuadOC48STM16MuxPortInfoScalarsGroup OBJECT-GROUP ::= { tnOpticalPortInfoGroups 7 }
--    tnQuadOC48STM16MuxPortInfoGroup OBJECT-GROUP ::= { tnOpticalPortInfoGroups 8 }
--    tnQuadOC3or12STM1or4MuxPortInfoScalarsGroup OBJECT-GROUP ::= { tnOpticalPortInfoGroups 9 }
--    tnQuadOC3or12STM1or4MuxPortInfoGroup OBJECT-GROUP ::= { tnOpticalPortInfoGroups 10 }
--    tnBandFilterPortInfoScalarsGroup OBJECT-GROUP ::= { tnOpticalPortInfoGroups 11 }
--    tnBandFilterPortInfoGroup OBJECT-GROUP ::= { tnOpticalPortInfoGroups 12 }

    tnOscPortInfoScalarsGroup OBJECT-GROUP
        OBJECTS {
            tnOscPortInfoAttributeTotal
        }
        STATUS         current
        DESCRIPTION    ""
        ::= { tnOpticalPortInfoGroups 13 }

    tnOscPortInfoGroup OBJECT-GROUP
        OBJECTS {
            tnOscPortInfoFunction,
            tnOscPortTotalNwPowerIn,
            tnOscPortTotalNwPowerOut,
            tnOscPortPhyDeviceLinkStatus,
            tnOscPortPhyDeviceIdNo,
            tnOscPortPhyDeviceMfgModelNo,
            tnOscPortPhyDeviceMfgRevNo
        }
        STATUS         current
        DESCRIPTION    ""
        ::= { tnOpticalPortInfoGroups 14 }

--    obsolete
--    tnChFilterPortInfoScalarsGroup OBJECT-GROUP ::= { tnOpticalPortInfoGroups 15 }
--    tnChFilterPortInfoGroup OBJECT-GROUP ::= { tnOpticalPortInfoGroups 16 }
--    tnChAddDropPortInfoScalarsGroup OBJECT-GROUP ::= { tnOpticalPortInfoGroups 17 }
--    tnChAddDropPortInfoGroup OBJECT-GROUP ::= { tnOpticalPortInfoGroups 18 }
--    tnBbaHgPortInfoScalarsGroup OBJECT-GROUP ::= { tnOpticalPortInfoGroups 19 }
--    tnBbaHgPortInfoGroup OBJECT-GROUP ::= { tnOpticalPortInfoGroups 20 }
--    tnBbaLgPortInfoScalarsGroup OBJECT-GROUP ::= { tnOpticalPortInfoGroups 21 }
--    tnBbaLgPortInfoGroup OBJECT-GROUP ::= { tnOpticalPortInfoGroups 22 }
--    tnPpsPortInfoScalarsGroup OBJECT-GROUP ::= { tnOpticalPortInfoGroups 23 }
--    tnPpsPortInfoGroup OBJECT-GROUP ::= { tnOpticalPortInfoGroups 24 }
--    tnDualGigEMuxPortInfoScalarsGroup OBJECT-GROUP ::= { tnOpticalPortInfoGroups 25 }
--    tnDualGigEMuxPortInfoGroup OBJECT-GROUP ::= { tnOpticalPortInfoGroups 26 }
--    tnRoadmPortInfoScalarsGroup OBJECT-GROUP ::= { tnOpticalPortInfoGroups 27 }
--    tnRoadmPortInfoGroup OBJECT-GROUP ::= { tnOpticalPortInfoGroups 28 }
--    tn10GigELANPortInfoScalarsGroup OBJECT-GROUP ::= { tnOpticalPortInfoGroups 29 }
--    tn10GigELANPortInfoGroup OBJECT-GROUP ::= { tnOpticalPortInfoGroups 30 }

    tnDcmPortInfoScalarsGroup OBJECT-GROUP
        OBJECTS {
            tnDcmPortInfoAttributeTotal
        }
        STATUS         current
        DESCRIPTION    ""
        ::= { tnOpticalPortInfoGroups 31 }

    tnDcmPortInfoGroup OBJECT-GROUP
        OBJECTS {
            tnDcmPortInfoFunction
        }
        STATUS         current
        DESCRIPTION    ""
        ::= { tnOpticalPortInfoGroups 32 }

--    obsolete
--    tnDecaGigEMuxPortInfoScalarsGroup OBJECT-GROUP ::= { tnOpticalPortInfoGroups 33 }
--    tnDecaGigEMuxPortInfoGroup OBJECT-GROUP ::= { tnOpticalPortInfoGroups 34 }

    tnSonetPortInfoScalarsGroup OBJECT-GROUP
        OBJECTS {
            tnSonetPortInfoAttributeTotal
        }
        STATUS         current
        DESCRIPTION    ""
        ::= { tnOpticalPortInfoGroups 35 }

    tnSonetPortInfoGroup OBJECT-GROUP
        OBJECTS {
            tnSonetPortRxSectionTrace,
            tnSonetPortTxSynchStatusMessage,
            tnSonetPortTiming,
            tnSonetPortRxSynchStatusMessage,
            tnSonetPortRxSectionTraceValid
        }
        STATUS         current
        DESCRIPTION    ""
        ::= { tnOpticalPortInfoGroups 36 }

--    obsolete
--    tnExternalDcuPortInfoScalarsGroup OBJECT-GROUP ::= { tnOpticalPortInfoGroups 37 }
--    tnExternalDcuPortInfoGroup OBJECT-GROUP ::= { tnOpticalPortInfoGroups 38 }

    tnDigitalWrapperPortInfoScalarsGroup OBJECT-GROUP
        OBJECTS {
            tnDigitalWrapperPortInfoAttributeTotal
        }
        STATUS         current
        DESCRIPTION    ""
        ::= { tnOpticalPortInfoGroups 39 }

    tnDigitalWrapperPortInfoGroup OBJECT-GROUP
        OBJECTS {
            tnDwPortRxPMTTI,
            tnDwPortRxPMExpectedTTI,
            tnDwPortTxPMTTI
        }
        STATUS         current
        DESCRIPTION    ""
        ::= { tnOpticalPortInfoGroups 40 }

--    obsolete
--    tnMsaHgPortInfoScalarsGroup OBJECT-GROUP ::= { tnOpticalPortInfoGroups 41 }
--    tnMsaHgPortInfoGroup OBJECT-GROUP ::= { tnOpticalPortInfoGroups 42 }
--    tnWssX9PortInfoScalarsGroup OBJECT-GROUP ::= { tnOpticalPortInfoGroups 43 }
--    tnWssX9PortInfoGroup OBJECT-GROUP ::= { tnOpticalPortInfoGroups 44 }

    tnSfpPortInfoScalarsGroup OBJECT-GROUP
        OBJECTS {
            tnSfpPortInfoAttributeTotal
        }
        STATUS         current
        DESCRIPTION    ""
        ::= { tnOpticalPortInfoGroups 45 }

    tnSfpPortInfoGroup OBJECT-GROUP
        OBJECTS {
            tnSfpPortModulePresentType,
            tnSfpPortModuleVendorSerNo,
            tnSfpPortModuleState,
            tnSfpPortModuleVendor,
            tnSfpPortTxDisable,
            tnSfpPortWavelength,
            tnSfpPortModuleType,
            tnSfpPortCLEI,
            tnSfpPortUnitPartNum,
            tnSfpPortSWPartNum,
            tnSfpPortFactoryID,
            tnSfpPortDate,
            tnSfpPortExtraData,
            tnSfpPortMaximumCaseTemperature,
            tnSfpPortInterchangeabilityMarking,
            tnSfpPortAcronymCode
        }
        STATUS         current
        DESCRIPTION    ""
        ::= { tnOpticalPortInfoGroups 46 }

--    obsolete
--    tn1xMR2dot5GPortInfoScalarsGroup OBJECT-GROUP ::= { tnOpticalPortInfoGroups 47 }
--    tn1xMR2dot5GPortInfoGroup OBJECT-GROUP ::= { tnOpticalPortInfoGroups 48 }

    tnNetworkPortInfoScalarsGroup OBJECT-GROUP
        OBJECTS {
            tnNetworkPortInfoAttributeTotal
        }
        STATUS         current
        DESCRIPTION    ""
        ::= { tnOpticalPortInfoGroups 49 }

    tnNetworkPortInfoGroup OBJECT-GROUP
        OBJECTS {
            tnNwPortOchRxStatus,
            tnNwPortOchTxStatus,
            tnNwPortPresentChannel
        }
        STATUS         current
        DESCRIPTION    ""
        ::= { tnOpticalPortInfoGroups 50 }

    tnOpsaPortInfoScalarsGroup OBJECT-GROUP
        OBJECTS {
            tnOpsaPortInfoAttributeTotal
        }
        STATUS         current
        DESCRIPTION    ""
        ::= { tnOpticalPortInfoGroups 51 }

    tnOpsaPortInfoGroup OBJECT-GROUP
        OBJECTS {
            tnOpsaPortInfoFunction,
            tnOpsaPortReceivedPower,              -- deprecated
            tnOpsaPortPresentTransmitAttenuation  -- deprecated
        }
        STATUS         current
        DESCRIPTION    ""
        ::= { tnOpticalPortInfoGroups 52 }

    tn11stmm10PortInfoScalarsGroup OBJECT-GROUP
        OBJECTS {
            tn11stmm10PortInfoAttributeTotal
        }
        STATUS         current
        DESCRIPTION    ""
        ::= { tnOpticalPortInfoGroups 53 }

    tn11stmm10PortInfoGroup OBJECT-GROUP
        OBJECTS {
            tn11stmm10PortInfoFunction
        }
        STATUS         current
        DESCRIPTION    ""
        ::= { tnOpticalPortInfoGroups 54 }

    tn11star1PortInfoScalarsGroup OBJECT-GROUP
        OBJECTS {
            tn11star1PortInfoAttributeTotal
        }
        STATUS         current
        DESCRIPTION    ""
        ::= { tnOpticalPortInfoGroups 55 }

    tn11star1PortInfoGroup OBJECT-GROUP
        OBJECTS {
            tn11star1PortInfoFunction
        }
        STATUS         current
        DESCRIPTION    ""
        ::= { tnOpticalPortInfoGroups 56 }

    tnAhphgPortInfoScalarsGroup OBJECT-GROUP
        OBJECTS {
            tnAhphgPortInfoAttributeTotal
        }
        STATUS         current
        DESCRIPTION    ""
        ::= { tnOpticalPortInfoGroups 57 }

    tnAhphgPortInfoGroup OBJECT-GROUP
        OBJECTS {
            tnAhphgPortInfoFunction
        }
        STATUS         current
        DESCRIPTION    ""
        ::= { tnOpticalPortInfoGroups 58 }

    tnAlphgPortInfoScalarsGroup OBJECT-GROUP
        OBJECTS {
            tnAlphgPortInfoAttributeTotal
        }
        STATUS         current
        DESCRIPTION    ""
        ::= { tnOpticalPortInfoGroups 59 }

    tnAlphgPortInfoGroup OBJECT-GROUP
        OBJECTS {
            tnAlphgPortInfoFunction
        }
        STATUS         current
        DESCRIPTION    ""
        ::= { tnOpticalPortInfoGroups 60 }

    tnCwr8PortInfoScalarsGroup OBJECT-GROUP
        OBJECTS {
            tnCwr8PortInfoAttributeTotal
        }
        STATUS         current
        DESCRIPTION    ""
        ::= { tnOpticalPortInfoGroups 61 }

    tnCwr8PortInfoGroup OBJECT-GROUP
        OBJECTS {
            tnCwr8PortInfoFunction,
--            obsolete
--            tnCwr8PortTotalNwPowerIn,
--            tnCwr8PortTotalNwPowerOut,
            tnCwr8PortRelativeAttenuationMin,
            tnCwr8PortAverageAttenuationOut
        }
        STATUS         current
        DESCRIPTION    ""
        ::= { tnOpticalPortInfoGroups 62 }

    tn11stge12PortInfoScalarsGroup OBJECT-GROUP
        OBJECTS {
            tn11stge12PortInfoAttributeTotal
        }
        STATUS         current
        DESCRIPTION    ""
        ::= { tnOpticalPortInfoGroups 63 }

    tn11stge12PortInfoGroup OBJECT-GROUP
        OBJECTS {
            tn11stge12PortInfoFunction
        }
        STATUS         current
        DESCRIPTION    ""
        ::= { tnOpticalPortInfoGroups 64 }

    tn11dpge12PortInfoScalarsGroup OBJECT-GROUP
        OBJECTS {
            tn11dpge12PortInfoAttributeTotal
        }
        STATUS         current
        DESCRIPTION    ""
        ::= { tnOpticalPortInfoGroups 65 }

    tn11dpge12PortInfoGroup OBJECT-GROUP
        OBJECTS {
            tn11dpge12PortInfoFunction,
            tn11dpge12PortAvailableBandwidth,
            tn11dpge12PortTotalVTS,
            tn11dpge12PortIngAvailableBandwidth,
            tn11dpge12PortEgrAvailableBandwidth
        }
        STATUS         current
        DESCRIPTION    ""
        ::= { tnOpticalPortInfoGroups 66 }

--    obsolete
--    tnDwdmGpPhyPortInfoGroup OBJECT-GROUP ::= { tnOpticalPortInfoGroups 67 }

    tnDwdmCmnLinePortInfoGroup OBJECT-GROUP
        OBJECTS {
            tnDwdmCmnLinePortOtu2IncomingTti,
            tnDwdmCmnLinePortOtu2TtiStatus,
            tnDwdmCmnLinePortOdu2IncomingTti,
            tnDwdmCmnLinePortOdu2TtiStatus,
--            obsolete
--            tnDwdmCmnLinePortAvailableBandwidth,
            tnDwdmCmnLinePortOtu2PreFec,
            tnDwdmCmnLinePortOtu2PostFec,
            tnDwdmCmnLinePortOdu2IncFwFTFLTypeID,
            tnDwdmCmnLinePortOdu2IncFwFTFLOperID,
            tnDwdmCmnLinePortOdu2IncBwFTFLTypeID,
            tnDwdmCmnLinePortOdu2IncBwFTFLOperID,
            tnDwdmCmnLinePortOdu2IncResRow2,
            tnDwdmCmnLinePortOdu2IncResRow4,
            tnDwdmCmnLinePortOdu2IncExp,
            tnDwdmCmnLinePortOtu2IncRes,
            tnDwdmCmnLinePortDMInfoCurrentStatus,
            tnDwdmCmnLinePortDMInfoCurrentValue
        }
        STATUS         current
        DESCRIPTION    ""
        ::= { tnOpticalPortInfoGroups 68 }

    tnDwdmCmnClientPortInfoGroup OBJECT-GROUP
        OBJECTS {
            tnDwdmCmnClientPortOtu2IncomingTti,
            tnDwdmCmnClientPortOtu2TtiStatus,
            tnDwdmCmnClientPortOdu2IncomingTti,
            tnDwdmCmnClientPortOdu2TtiStatus,
--            obsolete
--            tnDwdmCmnClientPortAvailableBandwidth,
            tnDwdmCmnClientPortBroadcastPortMap,
            tnDwdmCmnClientPortOtu2PreFec,
            tnDwdmCmnClientPortOtu2PostFec,
            tnDwdmCmnClientPortOdu2IncFwFTFLTypeID,
            tnDwdmCmnClientPortOdu2IncFwFTFLOperID,
            tnDwdmCmnClientPortOdu2IncBwFTFLTypeID,
            tnDwdmCmnClientPortOdu2IncBwFTFLOperID,
            tnDwdmCmnClientPortOdu2IncResRow2,
            tnDwdmCmnClientPortOdu2IncResRow4,
            tnDwdmCmnClientPortOdu2IncExp,
            tnDwdmCmnClientPortOtu2IncRes
        }
        STATUS         current
        DESCRIPTION    ""
        ::= { tnOpticalPortInfoGroups 69 }

    tnRsmonIngrPortInfoGroup OBJECT-GROUP
        OBJECTS {
            tnRsmonIngrPortIncomingTti,
            tnRsmonIngrPortTtiStatus
        }
        STATUS         current
        DESCRIPTION    ""
        ::= { tnOpticalPortInfoGroups 70 }

    tnOtPortInfoGroup OBJECT-GROUP
        OBJECTS {
            tnOtPortRxPower,
            tnOtPortTxPower,
            tnOtPortBias,
            tnOtPortTemperature,
            tnOtPortTxPowerLaser,
            tnOtPortRxLanePowers,
            tnOtPortTxLanePowers,
            tnOtPortRxLaneBslPowers,
            tnOtPortTxLaneBslPowers
        }
        STATUS         current
        DESCRIPTION    ""
        ::= { tnOpticalPortInfoGroups 71 }

    tnWaveKeyPortInfoGroup OBJECT-GROUP
        OBJECTS {
            tnWaveKeyPortNwPowerIn,
            tnWaveKeyPortNwPowerOut,
--            obsolete
--            tnWavekeyPortWTDecoderUsageStatusIn,
--            tnWavekeyPortWTDecoderUsageStatusOut,
            tnWaveKeyPortWTDecoderMeasurementTypeIn,
            tnWaveKeyPortWTDecoderMeasurementTypeOut
        }
        STATUS         current
        DESCRIPTION    ""
        ::= { tnOpticalPortInfoGroups 72 }

    tnOmdPortInfoGroup OBJECT-GROUP
        OBJECTS {
            tnOmdPortReceivedPower,
            tnOmdPortTransmittedPower
        }
        STATUS         current
        DESCRIPTION    ""
        ::= { tnOpticalPortInfoGroups 73 }

    tn4dpa4PortInfoScalarsGroup OBJECT-GROUP
        OBJECTS {
            tn4dpa4PortInfoAttributeTotal
        }
        STATUS         current
        DESCRIPTION    ""
        ::= { tnOpticalPortInfoGroups 74 }

    tn4dpa4PortInfoGroup OBJECT-GROUP
        OBJECTS {
            tn4dpa4PortInfoFunction
        }
        STATUS         current
        DESCRIPTION    ""
        ::= { tnOpticalPortInfoGroups 75 }

    tnCwr8c88PortInfoScalarsGroup OBJECT-GROUP
        OBJECTS {
            tnCwr8c88PortInfoAttributeTotal
        }
        STATUS         current
        DESCRIPTION    ""
        ::= { tnOpticalPortInfoGroups 76 }

    tnCwr8c88PortInfoGroup OBJECT-GROUP
        OBJECTS {
            tnCwr8c88PortInfoFunction,
            tnCwr8c88PortRelativeAttenuationMin,
            tnCwr8c88PortAverageAttenuationOut
        }
        STATUS         current
        DESCRIPTION    ""
        ::= { tnOpticalPortInfoGroups 77 }

    tnAhplgPortInfoScalarsGroup OBJECT-GROUP
        OBJECTS {
            tnAhplgPortInfoAttributeTotal
        }
        STATUS         current
        DESCRIPTION    ""
        ::= { tnOpticalPortInfoGroups 78 }

    tnAhplgPortInfoGroup OBJECT-GROUP
        OBJECTS {
            tnAhplgPortInfoFunction
        }
        STATUS         current
        DESCRIPTION    ""
        ::= { tnOpticalPortInfoGroups 79 }

    tnTimeSlotLinePortInfoGroup OBJECT-GROUP
        OBJECTS {
            tnTimeSlotLinePortFarEndIfType,
            tnTimeSlotLinePortFarEndInterfaceIndex,
            tnTimeSlotLinePortNearEndIfType,
            tnTimeSlotLinePortNearEndInterfaceIndex
        }
        STATUS         current
        DESCRIPTION    ""
        ::= { tnOpticalPortInfoGroups 80 }

    tnDwdmCmnOtu1Odu1LinePortInfoGroup OBJECT-GROUP
        OBJECTS {
            tnDwdmCmnLinePortOtu1IncomingTti,
            tnDwdmCmnLinePortOtu1TtiStatus,
            tnDwdmCmnLinePortOdu1IncomingTti,
            tnDwdmCmnLinePortOdu1TtiStatus
        }
        STATUS         current
        DESCRIPTION    ""
        ::= { tnOpticalPortInfoGroups 81 }

    tnDwdmCmnOtu1Odu1ClientPortInfoGroup OBJECT-GROUP
        OBJECTS {
            tnDwdmCmnClientPortOtu1IncomingTti,
            tnDwdmCmnClientPortOtu1TtiStatus,
            tnDwdmCmnClientPortOdu1IncomingTti,
            tnDwdmCmnClientPortOdu1TtiStatus,
            tnDwdmCmnClientPortOtu1PreFec,
            tnDwdmCmnClientPortOtu1PostFec
        }
        STATUS         current
        DESCRIPTION    ""
        ::= { tnOpticalPortInfoGroups 82 }

    tn43stx4PortInfoScalarsGroup OBJECT-GROUP
        OBJECTS {
            tn43stx4PortInfoAttributeTotal
        }
        STATUS         current
        DESCRIPTION    ""
        ::= { tnOpticalPortInfoGroups 83 }

    tn43stx4PortInfoGroup OBJECT-GROUP
        OBJECTS {
            tn43stx4PortInfoFunction
        }
        STATUS         current
        DESCRIPTION    ""
        ::= { tnOpticalPortInfoGroups 84 }

    tnDwdmCmnOtu3Odu3LinePortInfoGroup OBJECT-GROUP
        OBJECTS {
            tnDwdmCmnLinePortOtu3IncomingTti,
            tnDwdmCmnLinePortOtu3TtiStatus,
            tnDwdmCmnLinePortOdu3IncomingTti,
            tnDwdmCmnLinePortOdu3TtiStatus,
            tnDwdmCmnLinePortOtu3PreFec,
            tnDwdmCmnLinePortOtu3PostFec,
            tnDwdmCmnLinePortOdu3IncFwFTFLTypeID,
            tnDwdmCmnLinePortOdu3IncFwFTFLOperID,
            tnDwdmCmnLinePortOdu3IncBwFTFLTypeID,
            tnDwdmCmnLinePortOdu3IncBwFTFLOperID,
            tnDwdmCmnLinePortOdu3IncResRow2,
            tnDwdmCmnLinePortOdu3IncResRow4,
            tnDwdmCmnLinePortOdu3IncExp,
            tnDwdmCmnLinePortOtu3IncRes
        }
        STATUS         current
        DESCRIPTION    ""
        ::= { tnOpticalPortInfoGroups 85 }

    tnAlpfgkPortInfoScalarsGroup OBJECT-GROUP
        OBJECTS {
            tnAlpfgkPortInfoAttributeTotal
        }
        STATUS         current
        DESCRIPTION    ""
        ::= { tnOpticalPortInfoGroups 86 }

    tnAlpfgkPortInfoGroup OBJECT-GROUP
        OBJECTS {
            tnAlpfgkPortInfoFunction
        }
        STATUS         current
        DESCRIPTION    ""
        ::= { tnOpticalPortInfoGroups 87 }

    tn4dpa2PortInfoScalarsGroup OBJECT-GROUP
        OBJECTS {
            tn4dpa2PortInfoAttributeTotal
        }
        STATUS         current
        DESCRIPTION    ""
        ::= { tnOpticalPortInfoGroups 88 }

    tn4dpa2PortInfoGroup OBJECT-GROUP
        OBJECTS {
            tn4dpa2PortInfoFunction
        }
        STATUS         current
        DESCRIPTION    ""
        ::= { tnOpticalPortInfoGroups 89 }

    tn43sta1pPortInfoScalarsGroup OBJECT-GROUP
        OBJECTS {
            tn43sta1pPortInfoAttributeTotal
        }
        STATUS         current
        DESCRIPTION    ""
        ::= { tnOpticalPortInfoGroups 90 }

    tn43sta1pPortInfoGroup OBJECT-GROUP
        OBJECTS {
            tn43sta1pPortInfoFunction
        }
        STATUS         current
        DESCRIPTION    ""
        ::= { tnOpticalPortInfoGroups 91 }

    tn43stx4pPortInfoScalarsGroup OBJECT-GROUP
        OBJECTS {
            tn43stx4pPortInfoAttributeTotal
        }
        STATUS         current
        DESCRIPTION    ""
        ::= { tnOpticalPortInfoGroups 92 }

    tn43stx4pPortInfoGroup OBJECT-GROUP
        OBJECTS {
            tn43stx4pPortInfoFunction
        }
        STATUS         current
        DESCRIPTION    ""
        ::= { tnOpticalPortInfoGroups 93 }

    tnRsmonEgrPortInfoGroup OBJECT-GROUP
        OBJECTS {
            tnRsmonEgrPortIncomingTti,
            tnRsmonEgrPortTtiStatus
        }
        STATUS         current
        DESCRIPTION    ""
        ::= { tnOpticalPortInfoGroups 96 }

    tnA2325aPortInfoScalarsGroup OBJECT-GROUP
        OBJECTS {
            tnA2325aPortInfoAttributeTotal
        }
        STATUS         current
        DESCRIPTION    ""
        ::= { tnOpticalPortInfoGroups 97 }

    tnA2325aPortInfoGroup OBJECT-GROUP
        OBJECTS {
            tnA2325aPortInfoFunction
        }
        STATUS         current
        DESCRIPTION    ""
        ::= { tnOpticalPortInfoGroups 98 }

    tn11qpa4PortInfoScalarsGroup OBJECT-GROUP
        OBJECTS {
            tn11qpa4PortInfoAttributeTotal
        }
        STATUS         current
        DESCRIPTION    ""
        ::= { tnOpticalPortInfoGroups 99 }

    tn11qpa4PortInfoGroup OBJECT-GROUP
        OBJECTS {
            tn11qpa4PortInfoFunction
        }
        STATUS         current
        DESCRIPTION    ""
        ::= { tnOpticalPortInfoGroups 100 }

    tn112scx10PortInfoScalarsGroup OBJECT-GROUP
        OBJECTS {
            tn112scx10PortInfoAttributeTotal
        }
        STATUS         current
        DESCRIPTION    ""
        ::= { tnOpticalPortInfoGroups 101 }

    tn112scx10PortInfoGroup OBJECT-GROUP
        OBJECTS {
            tn112scx10PortInfoFunction
        }
        STATUS         current
        DESCRIPTION    ""
        ::= { tnOpticalPortInfoGroups 102 }

    tn112sca1PortInfoScalarsGroup OBJECT-GROUP
        OBJECTS {
            tn112sca1PortInfoAttributeTotal
        }
        STATUS         current
        DESCRIPTION    ""
        ::= { tnOpticalPortInfoGroups 103 }

    tn112sca1PortInfoGroup OBJECT-GROUP
        OBJECTS {
            tn112sca1PortInfoFunction
        }
        STATUS         current
        DESCRIPTION    ""
        ::= { tnOpticalPortInfoGroups 104 }

    tnDwdmCmnOtu4Odu4LinePortInfoGroup OBJECT-GROUP
        OBJECTS {
            tnDwdmCmnLinePortOtu4IncomingTti,
            tnDwdmCmnLinePortOtu4TtiStatus,
            tnDwdmCmnLinePortOdu4IncomingTti,
            tnDwdmCmnLinePortOdu4TtiStatus,
            tnDwdmCmnLinePortOtu4PreFec,
            tnDwdmCmnLinePortOtu4PostFec,
            tnDwdmCmnLinePortOdu4DMInfoCurrentStatus,
            tnDwdmCmnLinePortOdu4DMInfoCurrentValue
        }
        STATUS         current
        DESCRIPTION    ""
        ::= { tnOpticalPortInfoGroups 105 }

    tnDwdmCmnOtu4Odu4ClientPortInfoGroup OBJECT-GROUP
        OBJECTS {
            tnDwdmCmnClientPortOtu4IncomingTti,
            tnDwdmCmnClientPortOtu4TtiStatus,
            tnDwdmCmnClientPortOdu4IncomingTti,
            tnDwdmCmnClientPortOdu4TtiStatus,
            tnDwdmCmnClientPortOtu1PreFec,
            tnDwdmCmnClientPortOtu1PostFec
        }
        STATUS         current
        DESCRIPTION    ""
        ::= { tnOpticalPortInfoGroups 106 }

    tnAlpfgtPortInfoScalarsGroup OBJECT-GROUP
        OBJECTS {
            tnAlpfgtPortInfoAttributeTotal
        }
        STATUS         current
        DESCRIPTION    ""
        ::= { tnOpticalPortInfoGroups 107 }

    tnAlpfgtPortInfoGroup OBJECT-GROUP
        OBJECTS {
            tnAlpfgtPortInfoFunction
        }
        STATUS         current
        DESCRIPTION    ""
        ::= { tnOpticalPortInfoGroups 108 }

    tnOsctPortInfoScalarsGroup OBJECT-GROUP
        OBJECTS {
            tnOsctPortInfoAttributeTotal
        }
        STATUS         current
        DESCRIPTION    ""
        ::= { tnOpticalPortInfoGroups 109 }

    tnOsctPortInfoGroup OBJECT-GROUP
        OBJECTS {
            tnOsctPortInfoFunction
        }
        STATUS         current
        DESCRIPTION    ""
        ::= { tnOpticalPortInfoGroups 110 }

    tnWtocmPortInfoScalarsGroup OBJECT-GROUP
        OBJECTS {
            tnWtocmPortInfoAttributeTotal
        }
        STATUS         current
        DESCRIPTION    ""
        ::= { tnOpticalPortInfoGroups 111 }

    tnWtocmPortInfoGroup OBJECT-GROUP
        OBJECTS {
            tnWtocmPortInfoFunction,
            tnWtocmPortInfoPower,
            tnWtocmPortInfoPowerMonitoredPort
        }
        STATUS         current
        DESCRIPTION    ""
        ::= { tnOpticalPortInfoGroups 112 }

    tnWr2c88PortInfoScalarsGroup OBJECT-GROUP
        OBJECTS {
            tnWr2c88PortInfoAttributeTotal
        }
        STATUS         current
        DESCRIPTION    ""
        ::= { tnOpticalPortInfoGroups 113 }

    tnWr2c88PortInfoGroup OBJECT-GROUP
        OBJECTS {
            tnWr2c88PortInfoFunction,
            tnWr2c88PortRelativeAttenuationMin,
            tnWr2c88PortAverageAttenuationOut
        }
        STATUS         current
        DESCRIPTION    ""
        ::= { tnOpticalPortInfoGroups 114 }

    tnAm2017bPortInfoScalarsGroup OBJECT-GROUP
        OBJECTS {
            tnAm2017bPortInfoAttributeTotal
        }
        STATUS         current
        DESCRIPTION    ""
        ::= { tnOpticalPortInfoGroups 115 }

    tnAm2017bPortInfoGroup OBJECT-GROUP
        OBJECTS {
            tnAm2017bPortInfoFunction
        }
        STATUS         current
        DESCRIPTION    ""
        ::= { tnOpticalPortInfoGroups 116 }


    tnAm2325bPortInfoScalarsGroup OBJECT-GROUP
        OBJECTS {
            tnAm2325bPortInfoAttributeTotal
        }
        STATUS         current
        DESCRIPTION    ""
        ::= { tnOpticalPortInfoGroups 117 }

    tnAm2325bPortInfoGroup OBJECT-GROUP
        OBJECTS {
            tnAm2325bPortInfoFunction
        }
        STATUS         current
        DESCRIPTION    ""
        ::= { tnOpticalPortInfoGroups 118 }

    tn1dpp21PortInfoScalarsGroup OBJECT-GROUP
        OBJECTS {
            tn1dpp21PortInfoAttributeTotal
        }
        STATUS         current
        DESCRIPTION    ""
        ::= { tnOpticalPortInfoGroups 119 }

    tn1dpp21PortInfoGroup OBJECT-GROUP
        OBJECTS {
            tn1dpp21PortInfoFunction,
            tn1dpp21PortClockSourceIncomingQLStatus,
            tn1dpp21PortClockSourceIncomingQL
        }
        STATUS         current
        DESCRIPTION    ""
        ::= { tnOpticalPortInfoGroups 120 }

--    obsolete
--    tnE1T1PortInfoGroup OBJECT-GROUP ::= { tnOpticalPortInfoGroups 121 }

    tnMvacPortInfoScalarsGroup OBJECT-GROUP
        OBJECTS {
            tnMvacPortInfoAttributeTotal
        }
        STATUS         current
        DESCRIPTION    ""
        ::= { tnOpticalPortInfoGroups 122 }

    tnMvacPortInfoGroup OBJECT-GROUP
        OBJECTS {
            tnMvacPortInfoFunction
        }
        STATUS         current
        DESCRIPTION    ""
        ::= { tnOpticalPortInfoGroups 123 }

    tn43scx4PortInfoScalarsGroup OBJECT-GROUP
        OBJECTS {
            tn43scx4PortInfoAttributeTotal
        }
        STATUS         current
        DESCRIPTION    ""
        ::= { tnOpticalPortInfoGroups 126 }

    tn43scx4PortInfoGroup OBJECT-GROUP
        OBJECTS {
            tn43scx4PortInfoFunction
        }
        STATUS         current
        DESCRIPTION    ""
        ::= { tnOpticalPortInfoGroups 127 }

    tnRa2pPortInfoScalarsGroup OBJECT-GROUP
        OBJECTS {
            tnRa2pPortInfoAttributeTotal
        }
        STATUS         current
        DESCRIPTION    ""
        ::= { tnOpticalPortInfoGroups 128 }

    tnRa2pPortInfoGroup OBJECT-GROUP
        OBJECTS {
            tnRa2pPortInfoFunction
        }
        STATUS         current
        DESCRIPTION    ""
        ::= { tnOpticalPortInfoGroups 129 }

    tnAm2318aPortInfoScalarsGroup OBJECT-GROUP
        OBJECTS {
            tnAm2318aPortInfoAttributeTotal
        }
        STATUS         current
        DESCRIPTION    ""
        ::= { tnOpticalPortInfoGroups 130 }

    tnAm2318aPortInfoGroup OBJECT-GROUP
        OBJECTS {
            tnAm2318aPortInfoFunction
        }
        STATUS         current
        DESCRIPTION    ""
        ::= { tnOpticalPortInfoGroups 131 }

    tnAm2125aPortInfoScalarsGroup OBJECT-GROUP
        OBJECTS {
            tnAm2125aPortInfoAttributeTotal
        }
        STATUS         current
        DESCRIPTION    ""
        ::= { tnOpticalPortInfoGroups 132 }

    tnAm2125aPortInfoGroup OBJECT-GROUP
        OBJECTS {
            tnAm2125aPortInfoFunction
        }
        STATUS         current
        DESCRIPTION    ""
        ::= { tnOpticalPortInfoGroups 133 }

    tnWr8c88aPortInfoScalarsGroup OBJECT-GROUP
        OBJECTS {
            tnWr8c88aPortInfoAttributeTotal
        }
        STATUS         current
        DESCRIPTION    ""
        ::= { tnOpticalPortInfoGroups 134 }

    tnWr8c88aPortInfoGroup OBJECT-GROUP
        OBJECTS {
            tnWr8c88aPortInfoFunction
        }
        STATUS         current
        DESCRIPTION    ""
        ::= { tnOpticalPortInfoGroups 135 }

    tn11dpe12ePortInfoScalarsGroup OBJECT-GROUP
        OBJECTS {
            tn11dpe12ePortInfoAttributeTotal
        }
        STATUS         current
        DESCRIPTION    ""
        ::= { tnOpticalPortInfoGroups 136 }

    tn11dpe12ePortInfoGroup OBJECT-GROUP
        OBJECTS {
            tn11dpe12ePortInfoFunction,
            tn11dpe12ePortTotalVTS,
            tn11dpe12ePortIngAvailableBandwidth,
            tn11dpe12ePortEgrAvailableBandwidth
        }
        STATUS         current
        DESCRIPTION    ""
        ::= { tnOpticalPortInfoGroups 137 }

    tn112sx10lPortInfoScalarsGroup OBJECT-GROUP
        OBJECTS {
            tn112sx10lPortInfoAttributeTotal
        }
        STATUS         current
        DESCRIPTION    ""
        ::= { tnOpticalPortInfoGroups 138 }

    tn112sx10lPortInfoGroup OBJECT-GROUP
        OBJECTS {
            tn112sx10lPortInfoFunction
        }
        STATUS         current
        DESCRIPTION    ""
        ::= { tnOpticalPortInfoGroups 139 }

    tn112sa1lPortInfoScalarsGroup OBJECT-GROUP
        OBJECTS {
            tn112sa1lPortInfoAttributeTotal
        }
        STATUS         current
        DESCRIPTION    ""
        ::= { tnOpticalPortInfoGroups 140 }

    tn112sa1lPortInfoGroup OBJECT-GROUP
        OBJECTS {
            tn112sa1lPortInfoFunction
        }
        STATUS         current
        DESCRIPTION    ""
        ::= { tnOpticalPortInfoGroups 141 }

    tn11dpm12PortInfoScalarsGroup OBJECT-GROUP
        OBJECTS {
            tn11dpm12PortInfoAttributeTotal
        }
        STATUS         current
        DESCRIPTION    ""
        ::= { tnOpticalPortInfoGroups 142 }

    tn11dpm12PortInfoGroup OBJECT-GROUP
        OBJECTS {
            tn11dpm12PortInfoFunction
        }
        STATUS         current
        DESCRIPTION    ""
        ::= { tnOpticalPortInfoGroups 143 }

    tnRamanPortInfoGroup OBJECT-GROUP
        OBJECTS {
            tnRamanPortTotalPowerIn,
            tnRamanPortTotalPowerOut,
            tnRamanPortSignalPowerOut,
            tnRamanPortAsePowerOut,
            tnRamanPortGain,
            tnRamanPortPump1Power,
            tnRamanPortPump2Power,
            tnRamanPortPump3Power,
            tnRamanPortPump4Power
        }
        STATUS         current
        DESCRIPTION    ""
        ::= { tnOpticalPortInfoGroups 144 }

    tnMesh4PortInfoScalarsGroup OBJECT-GROUP
        OBJECTS {
            tnMesh4PortInfoAttributeTotal
        }
        STATUS         current
        DESCRIPTION    ""
        ::= { tnOpticalPortInfoGroups 145 }

    tnMesh4PortInfoGroup OBJECT-GROUP
        OBJECTS {
            tnMesh4PortInfoFunction
        }
        STATUS         current
        DESCRIPTION    ""
        ::= { tnOpticalPortInfoGroups 146 }

--    obsolete
--    tnTcmPortInfoScalarsGroup OBJECT-GROUP ::= { tnOpticalPortInfoGroups 147 }
--    tnTcmPortInfoGroup OBJECT-GROUP ::= { tnOpticalPortInfoGroups 148 }

    tn43sca1PortInfoScalarsGroup OBJECT-GROUP
        OBJECTS {
            tn43sca1PortInfoAttributeTotal
        }
        STATUS         current
        DESCRIPTION    ""
        ::= { tnOpticalPortInfoGroups 149 }

    tn43sca1PortInfoGroup OBJECT-GROUP
        OBJECTS {
            tn43sca1PortInfoFunction
        }
        STATUS         current
        DESCRIPTION    ""
        ::= { tnOpticalPortInfoGroups 150 }

    tn43scx4lPortInfoScalarsGroup OBJECT-GROUP
        OBJECTS {
            tn43scx4lPortInfoAttributeTotal
        }
        STATUS         current
        DESCRIPTION    ""
        ::= { tnOpticalPortInfoGroups 151 }

    tn43scx4lPortInfoGroup OBJECT-GROUP
        OBJECTS {
            tn43scx4lPortInfoFunction
        }
        STATUS         current
        DESCRIPTION    ""
        ::= { tnOpticalPortInfoGroups 152 }

    tnAm2125bPortInfoScalarsGroup OBJECT-GROUP
        OBJECTS {
            tnAm2125bPortInfoAttributeTotal
        }
        STATUS         current
        DESCRIPTION    ""
        ::= { tnOpticalPortInfoGroups 153 }

    tnAm2125bPortInfoGroup OBJECT-GROUP
        OBJECTS {
            tnAm2125bPortInfoFunction
        }
        STATUS         current
        DESCRIPTION    ""
        ::= { tnOpticalPortInfoGroups 154 }

    tn112snx10PortInfoScalarsGroup OBJECT-GROUP
        OBJECTS {
            tn112snx10PortInfoAttributeTotal
        }
        STATUS         current
        DESCRIPTION    ""
        ::= { tnOpticalPortInfoGroups 155 }

    tn112snx10PortInfoGroup OBJECT-GROUP
        OBJECTS {
            tn112snx10PortInfoFunction
        }
        STATUS         current
        DESCRIPTION    ""
        ::= { tnOpticalPortInfoGroups 156 }

    tn112sna1PortInfoScalarsGroup OBJECT-GROUP
        OBJECTS {
            tn112sna1PortInfoAttributeTotal
        }
        STATUS         current
        DESCRIPTION    ""
        ::= { tnOpticalPortInfoGroups 157 }

    tn112sna1PortInfoGroup OBJECT-GROUP
        OBJECTS {
            tn112sna1PortInfoFunction
        }
        STATUS         current
        DESCRIPTION    ""
        ::= { tnOpticalPortInfoGroups 158 }

--    obsolete
--    tn11qta4PortInfoScalarsGroup OBJECT-GROUP ::= { tnOpticalPortInfoGroups 159 }
--    tn11qta4PortInfoGroup OBJECT-GROUP ::= { tnOpticalPortInfoGroups 160 }

    tn1dpp24mPortInfoScalarsGroup OBJECT-GROUP
        OBJECTS {
            tn1dpp24mPortInfoAttributeTotal
        }
        STATUS         current
        DESCRIPTION    ""
        ::= { tnOpticalPortInfoGroups 161 }

    tn1dpp24mPortInfoGroup OBJECT-GROUP
        OBJECTS {
            tn1dpp24mPortInfoFunction
--            obsolete
--            tn1dpp24mPortClockSourceIncomingQLStatus,
--            tn1dpp24mPortClockSourceIncomingQL
        }
        STATUS         current
        DESCRIPTION    ""
        ::= { tnOpticalPortInfoGroups 162 }

    tnDwdmCmnOtu3Odu3ClientPortInfoGroup OBJECT-GROUP
        OBJECTS {
            tnDwdmCmnClientPortOtu3IncomingTti,
            tnDwdmCmnClientPortOtu3TtiStatus,
            tnDwdmCmnClientPortOdu3IncomingTti,
            tnDwdmCmnClientPortOdu3TtiStatus,
            tnDwdmCmnClientPortOtu1PreFec,
            tnDwdmCmnClientPortOtu1PostFec
        }
        STATUS         current
        DESCRIPTION    ""
        ::= { tnOpticalPortInfoGroups 163 }

    tnul43scupPortInfoScalarsGroup OBJECT-GROUP
        OBJECTS {
            tnul43scupPortInfoAttributeTotal
        }
        STATUS         current
        DESCRIPTION    ""
        ::= { tnOpticalPortInfoGroups 164 }

    tnul43scupPortInfoGroup OBJECT-GROUP
        OBJECTS {
            tnul43scupPortInfoFunction
        }
        STATUS         current
        DESCRIPTION    ""
        ::= { tnOpticalPortInfoGroups 165 }

    tnul11qcupPortInfoScalarsGroup OBJECT-GROUP
        OBJECTS {
            tnul11qcupPortInfoAttributeTotal
        }
        STATUS         current
        DESCRIPTION    ""
        ::= { tnOpticalPortInfoGroups 166 }

    tnul11qcupPortInfoGroup OBJECT-GROUP
        OBJECTS {
            tnul11qcupPortInfoFunction
        }
        STATUS         current
        DESCRIPTION    ""
        ::= { tnOpticalPortInfoGroups 167 }

    tn11qpen4PortInfoScalarsGroup OBJECT-GROUP
        OBJECTS {
            tn11qpen4PortInfoAttributeTotal
        }
        STATUS         current
        DESCRIPTION    ""
        ::= { tnOpticalPortInfoGroups 168 }

    tn11qpen4PortInfoGroup OBJECT-GROUP
        OBJECTS {
            tn11qpen4PortInfoFunction,
            tn11qpen4PortInfoEncryptionCurrentKeyInfo,
            tn11qpen4PortInfoEncryptionNextKeyInfo
        }
        STATUS         current
        DESCRIPTION    ""
        ::= { tnOpticalPortInfoGroups 169 }

    tn43scx4ePortInfoScalarsGroup OBJECT-GROUP
        OBJECTS {
            tn43scx4ePortInfoAttributeTotal
        }
        STATUS         current
        DESCRIPTION    ""
        ::= { tnOpticalPortInfoGroups 170 }

    tn43scx4ePortInfoGroup OBJECT-GROUP
        OBJECTS {
            tn43scx4ePortInfoFunction
        }
        STATUS         current
        DESCRIPTION    ""
        ::= { tnOpticalPortInfoGroups 171 }

    tnWssAttenPortInfoScalarsGroup OBJECT-GROUP
        OBJECTS {
            tnWssAttenPortInfoAttributeTotal
        }
        STATUS         current
        DESCRIPTION    ""
        ::= { tnOpticalPortInfoGroups 172 }

    tnWssAttenPortInfoGroup OBJECT-GROUP
        OBJECTS {
            tnWssAttenPortInfoWssCurrentRelativeAtten,
            tnWssAttenPortInfoApplicability
        }
        STATUS         current
        DESCRIPTION    ""
        ::= { tnOpticalPortInfoGroups 173 }

    tn43scge1PortInfoScalarsGroup OBJECT-GROUP
        OBJECTS {
            tn43scge1PortInfoAttributeTotal
        }
        STATUS         current
        DESCRIPTION    ""
        ::= { tnOpticalPortInfoGroups 174 }

    tn43scge1PortInfoGroup OBJECT-GROUP
        OBJECTS {
            tn43scge1PortInfoFunction
        }
        STATUS         current
        DESCRIPTION    ""
        ::= { tnOpticalPortInfoGroups 175 }

    tn11qpe24PortInfoScalarsGroup OBJECT-GROUP
        OBJECTS {
            tn11qpe24PortInfoAttributeTotal
        }
        STATUS         current
        DESCRIPTION    ""
        ::= { tnOpticalPortInfoGroups 176 }

    tn11qpe24PortInfoGroup OBJECT-GROUP
        OBJECTS {
            tn11qpe24PortInfoFunction
        }
        STATUS         current
        DESCRIPTION    ""
        ::= { tnOpticalPortInfoGroups 177 }

    tn11star1aPortInfoScalarsGroup OBJECT-GROUP
        OBJECTS {
            tn11star1aPortInfoAttributeTotal
        }
        STATUS         current
        DESCRIPTION    ""
        ::= { tnOpticalPortInfoGroups 178 }

    tn11star1aPortInfoGroup OBJECT-GROUP
        OBJECTS {
            tn11star1aPortInfoFunction
        }
        STATUS         current
        DESCRIPTION    ""
        ::= { tnOpticalPortInfoGroups 179 }

    tnMvac8bPortInfoScalarsGroup OBJECT-GROUP
        OBJECTS {
            tnMvac8bPortInfoAttributeTotal
        }
        STATUS         current
        DESCRIPTION    ""
        ::= { tnOpticalPortInfoGroups 180 }

    tnMvac8bPortInfoGroup OBJECT-GROUP
        OBJECTS {
            tnMvac8bPortInfoFunction
        }
        STATUS         current
        DESCRIPTION    ""
        ::= { tnOpticalPortInfoGroups 181 }

    tnWr8c88afPortInfoScalarsGroup OBJECT-GROUP
        OBJECTS {
            tnWr8c88afPortInfoAttributeTotal
        }
        STATUS         current
        DESCRIPTION    ""
        ::= { tnOpticalPortInfoGroups 182 }

    tnWr8c88afPortInfoGroup OBJECT-GROUP
        OBJECTS {
            tnWr8c88afPortInfoFunction
        }
        STATUS         current
        DESCRIPTION    ""
        ::= { tnOpticalPortInfoGroups 183 }

    tncl10an10gPortInfoScalarsGroup OBJECT-GROUP
        OBJECTS {
            tncl10an10gPortInfoAttributeTotal
        }
        STATUS         current
        DESCRIPTION    ""
        ::= { tnOpticalPortInfoGroups 184 }

    tncl10an10gPortInfoGroup OBJECT-GROUP
        OBJECTS {
            tncl10an10gPortInfoFunction
        }
        STATUS         current
        DESCRIPTION    ""
        ::= { tnOpticalPortInfoGroups 185 }

    tncl24anmPortInfoScalarsGroup OBJECT-GROUP
        OBJECTS {
            tncl24anmPortInfoAttributeTotal
        }
        STATUS         current
        DESCRIPTION    ""
        ::= { tnOpticalPortInfoGroups 186 }

    tncl24anmPortInfoGroup OBJECT-GROUP
        OBJECTS {
            tncl24anmPortInfoFunction
        }
        STATUS         current
        DESCRIPTION    ""
        ::= { tnOpticalPortInfoGroups 187 }

    tnOpsbPortInfoScalarsGroup OBJECT-GROUP
        OBJECTS {
            tnOpsbPortInfoAttributeTotal
        }
        STATUS         current
        DESCRIPTION    ""
        ::= { tnOpticalPortInfoGroups 188 }

    tnOpsbPortInfoGroup OBJECT-GROUP
        OBJECTS {
            tnOpsbPortInfoFunction
        }
        STATUS         current
        DESCRIPTION    ""
        ::= { tnOpticalPortInfoGroups 189 }

    tnOpsPortInfoScalarsGroup OBJECT-GROUP
        OBJECTS {
            tnOpsPortInfoAttributeTotal
        }
        STATUS         current
        DESCRIPTION    ""
        ::= { tnOpticalPortInfoGroups 190 }

    tnOpsPortInfoGroup OBJECT-GROUP
        OBJECTS {
            tnOpsPortInfoReceivedPower,
            tnOpsPortInfoPresentTransmitAttenuation
        }
        STATUS         current
        DESCRIPTION    ""
        ::= { tnOpticalPortInfoGroups 191 }

    tn11dpe12aPortInfoScalarsGroup OBJECT-GROUP
        OBJECTS {
            tn11dpe12aPortInfoAttributeTotal
        }
        STATUS         current
        DESCRIPTION    ""
        ::= { tnOpticalPortInfoGroups 192 }

    tn11dpe12aPortInfoGroup OBJECT-GROUP
        OBJECTS {
            tn11dpe12aPortInfoFunction,
            tn11dpe12aPortInfoTotalVTS,
            tn11dpe12aPortInfoIngAvailableBandwidth,
            tn11dpe12aPortInfoEgrAvailableBandwidth
        }
        STATUS         current
        DESCRIPTION    ""
        ::= { tnOpticalPortInfoGroups 193 }

    tnul130scupPortInfoScalarsGroup OBJECT-GROUP
        OBJECTS {
            tnul130scupPortInfoAttributeTotal
        }
        STATUS         current
        DESCRIPTION    ""
        ::= { tnOpticalPortInfoGroups 194 }

    tnul130scupPortInfoGroup OBJECT-GROUP
        OBJECTS {
            tnul130scupPortInfoFunction
        }
        STATUS         current
        DESCRIPTION    ""
        ::= { tnOpticalPortInfoGroups 195 }

    tn130scx10PortInfoScalarsGroup OBJECT-GROUP
        OBJECTS {
            tn130scx10PortInfoAttributeTotal
        }
        STATUS         current
        DESCRIPTION    ""
        ::= { tnOpticalPortInfoGroups 196 }

    tn130scx10PortInfoGroup OBJECT-GROUP
        OBJECTS {
            tn130scx10PortInfoFunction
        }
        STATUS         current
        DESCRIPTION    ""
        ::= { tnOpticalPortInfoGroups 197 }

    tnA2p2125PortInfoScalarsGroup OBJECT-GROUP
        OBJECTS {
            tnA2p2125PortInfoAttributeTotal
        }
        STATUS         current
        DESCRIPTION    ""
        ::= { tnOpticalPortInfoGroups 198 }

    tnA2p2125PortInfoGroup OBJECT-GROUP
        OBJECTS {
            tnA2p2125PortInfoFunction
        }
        STATUS         current
        DESCRIPTION    ""
        ::= { tnOpticalPortInfoGroups 199 }

    tn4qpa8PortInfoScalarsGroup OBJECT-GROUP
        OBJECTS {
            tn4qpa8PortInfoAttributeTotal
        }
        STATUS         current
        DESCRIPTION    ""
        ::= { tnOpticalPortInfoGroups 200 }

    tn4qpa8PortInfoGroup OBJECT-GROUP
        OBJECTS {
            tn4qpa8PortInfoFunction
        }
        STATUS         current
        DESCRIPTION    ""
        ::= { tnOpticalPortInfoGroups 201 }

    tnOt112pdm11PortInfoScalarsGroup OBJECT-GROUP
        OBJECTS {
            tnOt112pdm11PortInfoAttributeTotal
        }
        STATUS         current
        DESCRIPTION    ""
        ::= { tnOpticalPortInfoGroups 202 }

    tnOt112pdm11PortInfoGroup OBJECT-GROUP
        OBJECTS {
            tnOt112pdm11PortInfoFunction
        }
        STATUS         current
        DESCRIPTION    ""
        ::= { tnOpticalPortInfoGroups 203 }

    tnWtocmaPortInfoScalarsGroup OBJECT-GROUP
        OBJECTS {
            tnWtocmaPortInfoAttributeTotal
        }
        STATUS         current
        DESCRIPTION    ""
        ::= { tnOpticalPortInfoGroups 204 }

    tnWtocmaPortInfoGroup OBJECT-GROUP
        OBJECTS {
            tnWtocmaPortInfoFunction,
            tnWtocmaPortInfoPower,
            tnWtocmaPortInfoPowerMonitoredPort
        }
        STATUS         current
        DESCRIPTION    ""
        ::= { tnOpticalPortInfoGroups 205 }

    tnPtpctlPortInfoScalarsGroup OBJECT-GROUP
        OBJECTS {
            tnPtpctlPortInfoAttributeTotal
        }
        STATUS         current
        DESCRIPTION    ""
        ::= { tnOpticalPortInfoGroups 206 }

    tnPtpctlPortInfoGroup OBJECT-GROUP
        OBJECTS {
            tnPtpctlPortInfoFunction
        }
        STATUS         current
        DESCRIPTION    ""
        ::= { tnOpticalPortInfoGroups 207 }

    tnPtpioPortInfoScalarsGroup OBJECT-GROUP
        OBJECTS {
            tnPtpioPortInfoAttributeTotal
        }
        STATUS         current
        DESCRIPTION    ""
        ::= { tnOpticalPortInfoGroups 208 }

    tnPtpioPortInfoGroup OBJECT-GROUP
        OBJECTS {
            tnPtpioPortInfoFunction
        }
        STATUS         current
        DESCRIPTION    ""
        ::= { tnOpticalPortInfoGroups 209 }

    tnIo24et1gbPortInfoScalarsGroup OBJECT-GROUP
        OBJECTS {
            tnIo24et1gbPortInfoAttributeTotal
        }
        STATUS         current
        DESCRIPTION    ""
        ::= { tnOpticalPortInfoGroups 210 }

    tnIo24et1gbPortInfoGroup OBJECT-GROUP
        OBJECTS {
            tnIo24et1gbPortInfoFunction
        }
        STATUS         current
        DESCRIPTION    ""
        ::= { tnOpticalPortInfoGroups 211 }

    tnIo4an10gPortInfoScalarsGroup OBJECT-GROUP
        OBJECTS {
            tnIo4an10gPortInfoAttributeTotal
        }
        STATUS         current
        DESCRIPTION    ""
        ::= { tnOpticalPortInfoGroups 212 }

    tnIo4an10gPortInfoGroup OBJECT-GROUP
        OBJECTS {
            tnIo4an10gPortInfoFunction
        }
        STATUS         current
        DESCRIPTION    ""
        ::= { tnOpticalPortInfoGroups 213 }

    tnIo8et1gbPortInfoScalarsGroup OBJECT-GROUP
        OBJECTS {
            tnIo8et1gbPortInfoAttributeTotal
        }
        STATUS         current
        DESCRIPTION    ""
        ::= { tnOpticalPortInfoGroups 214 }

    tnIo8et1gbPortInfoGroup OBJECT-GROUP
        OBJECTS {
            tnIo8et1gbPortInfoFunction
        }
        STATUS         current
        DESCRIPTION    ""
        ::= { tnOpticalPortInfoGroups 215 }

    tnIo10et10gPortInfoScalarsGroup OBJECT-GROUP
        OBJECTS {
            tnIo10et10gPortInfoAttributeTotal
        }
        STATUS         current
        DESCRIPTION    ""
        ::= { tnOpticalPortInfoGroups 216 }

    tnIo10et10gPortInfoGroup OBJECT-GROUP
        OBJECTS {
            tnIo10et10gPortInfoFunction
        }
        STATUS         current
        DESCRIPTION    ""
        ::= { tnOpticalPortInfoGroups 217 }

    tnUl11qcupcPortInfoScalarsGroup OBJECT-GROUP
        OBJECTS {
            tnUl11qcupcPortInfoAttributeTotal
        }
        STATUS         current
        DESCRIPTION    ""
        ::= { tnOpticalPortInfoGroups 218 }

    tnUl11qcupcPortInfoGroup OBJECT-GROUP
        OBJECTS {
            tnUl11qcupcPortInfoFunction
        }
        STATUS         current
        DESCRIPTION    ""
        ::= { tnOpticalPortInfoGroups 219 }

    tnOt520scx4PortInfoScalarsGroup OBJECT-GROUP
        OBJECTS {
            tnOt520scx4PortInfoAttributeTotal
        }
        STATUS         current
        DESCRIPTION    ""
        ::= { tnOpticalPortInfoGroups 220 }

    tnOt520scx4PortInfoGroup OBJECT-GROUP
        OBJECTS {
            tnOt520scx4PortInfoFunction
        }
        STATUS         current
        DESCRIPTION    ""
        ::= { tnOpticalPortInfoGroups 221 }

    tnSkewInfoGroup OBJECT-GROUP
        OBJECTS {
            tnSkewInfoString
        }
        STATUS         current
        DESCRIPTION    ""
        ::= { tnOpticalPortInfoGroups 222 }

    tnPowerFilterPortInfoScalarsGroup OBJECT-GROUP
        OBJECTS {
            tnPowerFilterPortInfoAttributeTotal
        }
        STATUS         current
        DESCRIPTION    ""
        ::= { tnOpticalPortInfoGroups 223 }

    tnPowerFilterPortInfoGroup OBJECT-GROUP
        OBJECTS {
            tnPowerFilterPortInfoFunction
        }
        STATUS         current
        DESCRIPTION    ""
        ::= { tnOpticalPortInfoGroups 224 }

    tn11ope8PortInfoScalarsGroup OBJECT-GROUP
        OBJECTS {
            tn11ope8PortInfoAttributeTotal
        }
        STATUS         current
        DESCRIPTION    ""
        ::= { tnOpticalPortInfoGroups 225 }

    tn11ope8PortInfoGroup OBJECT-GROUP
        OBJECTS {
            tn11ope8PortInfoFunction
        }
        STATUS         current
        DESCRIPTION    ""
        ::= { tnOpticalPortInfoGroups 226 }

    tn11qce12xPortInfoScalarsGroup OBJECT-GROUP
        OBJECTS {
            tn11qce12xPortInfoAttributeTotal
        }
        STATUS         current
        DESCRIPTION    ""
        ::= { tnOpticalPortInfoGroups 227 }

    tn11qce12xPortInfoGroup OBJECT-GROUP
        OBJECTS {
            tn11qce12xPortInfoFunction
        }
        STATUS         current
        DESCRIPTION    ""
        ::= { tnOpticalPortInfoGroups 228 }

    tnAm2625aPortInfoScalarsGroup OBJECT-GROUP
        OBJECTS {
            tnAm2625aPortInfoAttributeTotal
        }
        STATUS         current
        DESCRIPTION    ""
        ::= { tnOpticalPortInfoGroups 229 }

    tnAm2625aPortInfoGroup OBJECT-GROUP
        OBJECTS {
            tnAm2625aPortInfoFunction
        }
        STATUS         current
        DESCRIPTION    ""
        ::= { tnOpticalPortInfoGroups 230 }

    tnAm2032aPortInfoScalarsGroup OBJECT-GROUP
        OBJECTS {
            tnAm2032aPortInfoAttributeTotal
        }
        STATUS         current
        DESCRIPTION    ""
        ::= { tnOpticalPortInfoGroups 231 }

    tnAm2032aPortInfoGroup OBJECT-GROUP
        OBJECTS {
            tnAm2032aPortInfoFunction
        }
        STATUS         current
        DESCRIPTION    ""
        ::= { tnOpticalPortInfoGroups 232 }

    tnOt260scx2PortInfoScalarsGroup OBJECT-GROUP
        OBJECTS {
            tnOt260scx2PortInfoAttributeTotal
        }
        STATUS         current
        DESCRIPTION    ""
        ::= { tnOpticalPortInfoGroups 233 }

    tnOt260scx2PortInfoGroup OBJECT-GROUP
        OBJECTS {
            tnOt260scx2PortInfoFunction
        }
        STATUS         current
        DESCRIPTION    ""
        ::= { tnOpticalPortInfoGroups 234 }

    tnOt130snx10PortInfoScalarsGroup OBJECT-GROUP
        OBJECTS {
            tnOt130snx10PortInfoAttributeTotal
        }
        STATUS         current
        DESCRIPTION    ""
        ::= { tnOpticalPortInfoGroups 235 }

    tnOt130snx10PortInfoGroup OBJECT-GROUP
        OBJECTS {
            tnOt130snx10PortInfoFunction
        }
        STATUS         current
        DESCRIPTION    ""
        ::= { tnOpticalPortInfoGroups 236 }

    tnIo24anmbPortInfoScalarsGroup OBJECT-GROUP
        OBJECTS {
            tnIo24anmbPortInfoAttributeTotal
        }
        STATUS         current
        DESCRIPTION    ""
        ::= { tnOpticalPortInfoGroups 237 }

    tnIo24anmbPortInfoGroup OBJECT-GROUP
        OBJECTS {
            tnIo24anmbPortInfoFunction
        }
        STATUS         current
        DESCRIPTION    ""
        ::= { tnOpticalPortInfoGroups 238 }

    tnOt11dpm8PortInfoScalarsGroup OBJECT-GROUP
        OBJECTS {
            tnOt11dpm8PortInfoAttributeTotal
        }
        STATUS         current
        DESCRIPTION    ""
        ::= { tnOpticalPortInfoGroups 239 }

    tnOt11dpm8PortInfoGroup OBJECT-GROUP
        OBJECTS {
            tnOt11dpm8PortInfoFunction
        }
        STATUS         current
        DESCRIPTION    ""
        ::= { tnOpticalPortInfoGroups 240 }

    tnOt11dpm4mPortInfoScalarsGroup OBJECT-GROUP
        OBJECTS {
            tnOt11dpm4mPortInfoAttributeTotal
        }
        STATUS         current
        DESCRIPTION    ""
        ::= { tnOpticalPortInfoGroups 241 }

    tnOt11dpm4mPortInfoGroup OBJECT-GROUP
        OBJECTS {
            tnOt11dpm4mPortInfoFunction
        }
        STATUS         current
        DESCRIPTION    ""
        ::= { tnOpticalPortInfoGroups 242 }

    tnUl130scupbPortInfoScalarsGroup OBJECT-GROUP
        OBJECTS {
            tnUl130scupbPortInfoAttributeTotal
        }
        STATUS         current
        DESCRIPTION    ""
        ::= { tnOpticalPortInfoGroups 243 }

    tnUl130scupbPortInfoGroup OBJECT-GROUP
        OBJECTS {
            tnUl130scupbPortInfoFunction
        }
        STATUS         current
        DESCRIPTION    ""
        ::= { tnOpticalPortInfoGroups 244 }

    tnOt112sdx11PortInfoScalarsGroup OBJECT-GROUP
        OBJECTS {
            tnOt112sdx11PortInfoAttributeTotal
        }
        STATUS         current
        DESCRIPTION    ""
        ::= { tnOpticalPortInfoGroups 245 }

    tnOt112sdx11PortInfoGroup OBJECT-GROUP
        OBJECTS {
            tnOt112sdx11PortInfoFunction,
            tnOt112sdx11PortInfoAggrRate
        }
        STATUS         current
        DESCRIPTION    ""
        ::= { tnOpticalPortInfoGroups 246 }

    tnAa2donwPortInfoScalarsGroup OBJECT-GROUP
        OBJECTS {
            tnAa2donwPortInfoAttributeTotal
        }
        STATUS         current
        DESCRIPTION    ""
        ::= { tnOpticalPortInfoGroups 247 }

    tnAa2donwPortInfoGroup OBJECT-GROUP
        OBJECTS {
            tnAa2donwPortInfoFunction
        }
        STATUS         current
        DESCRIPTION    ""
        ::= { tnOpticalPortInfoGroups 248 }

    tnOt130sca1PortInfoScalarsGroup OBJECT-GROUP
        OBJECTS {
            tnOt130sca1PortInfoAttributeTotal
        }
        STATUS         current
        DESCRIPTION    ""
        ::= { tnOpticalPortInfoGroups 249 }

    tnOt130sca1PortInfoGroup OBJECT-GROUP
        OBJECTS {
            tnOt130sca1PortInfoFunction
        }
        STATUS         current
        DESCRIPTION    ""
        ::= { tnOpticalPortInfoGroups 250 }

    tnIo10an10gbPortInfoScalarsGroup OBJECT-GROUP
        OBJECTS {
            tnIo10an10gbPortInfoAttributeTotal
        }
        STATUS         current
        DESCRIPTION    ""
        ::= { tnOpticalPortInfoGroups 251 }

    tnIo10an10gbPortInfoGroup OBJECT-GROUP
        OBJECTS {
            tnIo10an10gbPortInfoFunction
        }
        STATUS         current
        DESCRIPTION    ""
        ::= { tnOpticalPortInfoGroups 252 }

    tnIo10et10gbPortInfoScalarsGroup OBJECT-GROUP
        OBJECTS {
            tnIo10et10gbPortInfoAttributeTotal
        }
        STATUS         current
        DESCRIPTION    ""
        ::= { tnOpticalPortInfoGroups 253 }

    tnIo10et10gbPortInfoGroup OBJECT-GROUP
        OBJECTS {
            tnIo10et10gbPortInfoFunction
        }
        STATUS         current
        DESCRIPTION    ""
        ::= { tnOpticalPortInfoGroups 254 }

    tnWr20tfPortInfoScalarsGroup OBJECT-GROUP
        OBJECTS {
            tnWr20tfPortInfoAttributeTotal
        }
        STATUS         current
        DESCRIPTION    ""
        ::= { tnOpticalPortInfoGroups 255 }

    tnWr20tfPortInfoGroup OBJECT-GROUP
        OBJECTS {
            tnWr20tfPortInfoFunction
        }
        STATUS         current
        DESCRIPTION    ""
        ::= { tnOpticalPortInfoGroups 256 }

    tnWssPortInfoScalarsGroup OBJECT-GROUP
        OBJECTS {
            tnWssPortInfoAttributeTotal
        }
        STATUS         current
        DESCRIPTION    ""
        ::= { tnOpticalPortInfoGroups 257 }

    tnWssPortInfoGroup OBJECT-GROUP
        OBJECTS {
            tnWssPortInfoRelativeAttenuationMinIn,
            tnWssPortInfoRelativeAttenuationMinOut,
            tnWssPortInfoRelativeAverageAttenuationIn,
            tnWssPortInfoRelativeAverageAttenuationOut,
            tnWssPortInfoLossFromInToCommon,
            tnWssPortInfoCurrentLossFromInToCommon
        }
        STATUS         current
        DESCRIPTION    ""
        ::= { tnOpticalPortInfoGroups 258 }

    tnWtocmfPortInfoScalarsGroup OBJECT-GROUP
        OBJECTS {
            tnWtocmfPortInfoAttributeTotal
        }
        STATUS         current
        DESCRIPTION    ""
        ::= { tnOpticalPortInfoGroups 259 }

    tnWtocmfPortInfoGroup OBJECT-GROUP
        OBJECTS {
            tnWtocmfPortInfoFunction
        }
        STATUS         current
        DESCRIPTION    ""
        ::= { tnOpticalPortInfoGroups 260 }

    tnAswgPortInfoScalarsGroup OBJECT-GROUP
        OBJECTS {
            tnAswgPortInfoAttributeTotal
        }
        STATUS         current
        DESCRIPTION    ""
        ::= { tnOpticalPortInfoGroups 261 }

    tnAswgPortInfoGroup OBJECT-GROUP
        OBJECTS {
            tnAswgPortInfoFunction
        }
        STATUS         current
        DESCRIPTION    ""
        ::= { tnOpticalPortInfoGroups 262 }

    tnA4pswgPortInfoScalarsGroup OBJECT-GROUP
        OBJECTS {
            tnA4pswgPortInfoAttributeTotal
        }
        STATUS         current
        DESCRIPTION    ""
        ::= { tnOpticalPortInfoGroups 263 }

    tnA4pswgPortInfoGroup OBJECT-GROUP
        OBJECTS {
            tnA4pswgPortInfoFunction
        }
        STATUS         current
        DESCRIPTION    ""
        ::= { tnOpticalPortInfoGroups 264 }

    tnOtdrPortInfoScalarsGroup OBJECT-GROUP
        OBJECTS {
            tnOtdrPortInfoAttributeTotal
        }
        STATUS         current
        DESCRIPTION    ""
        ::= { tnOpticalPortInfoGroups 265 }

    tnOtdrPortInfoGroup OBJECT-GROUP
        OBJECTS {
            tnOtdrPortInfoFunction
        }
        STATUS         current
        DESCRIPTION    ""
        ::= { tnOpticalPortInfoGroups 266 }

    tnWr20tfmPortInfoScalarsGroup OBJECT-GROUP
        OBJECTS {
            tnWr20tfmPortInfoAttributeTotal
        }
        STATUS         current
        DESCRIPTION    ""
        ::= { tnOpticalPortInfoGroups 267 }

    tnWr20tfmPortInfoGroup OBJECT-GROUP
        OBJECTS {
            tnWr20tfmPortInfoFunction,
            tnWr20tfmPortInfoTestingActive
        }
        STATUS         current
        DESCRIPTION    ""
        ::= { tnOpticalPortInfoGroups 268 }

    tnAar8aPortInfoScalarsGroup OBJECT-GROUP
        OBJECTS {
            tnAar8aPortInfoAttributeTotal
        }
        STATUS         current
        DESCRIPTION    ""
        ::= { tnOpticalPortInfoGroups 269 }

    tnAar8aPortInfoGroup OBJECT-GROUP
        OBJECTS {
            tnAar8aPortInfoFunction
        }
        STATUS         current
        DESCRIPTION    ""
        ::= { tnOpticalPortInfoGroups 270 }

    tnMcs8x16PortInfoScalarsGroup OBJECT-GROUP
        OBJECTS {
            tnMcs8x16PortInfoAttributeTotal
        }
        STATUS         current
        DESCRIPTION    ""
        ::= { tnOpticalPortInfoGroups 271 }

    tnMcs8x16PortInfoGroup OBJECT-GROUP
        OBJECTS {
            tnMcs8x16PortInfoFunction,
            tnMcs8x16PortInfoAddInsertionLossToSig1,
            tnMcs8x16PortInfoAddInsertionLossToSig2,
            tnMcs8x16PortInfoAddInsertionLossToSig3,
            tnMcs8x16PortInfoAddInsertionLossToSig4,
            tnMcs8x16PortInfoAddInsertionLossToSig5,
            tnMcs8x16PortInfoAddInsertionLossToSig6,
            tnMcs8x16PortInfoAddInsertionLossToSig7,
            tnMcs8x16PortInfoAddInsertionLossToSig8,
            tnMcs8x16PortInfoDropInsertionLossFromSig1,
            tnMcs8x16PortInfoDropInsertionLossFromSig2,
            tnMcs8x16PortInfoDropInsertionLossFromSig3,
            tnMcs8x16PortInfoDropInsertionLossFromSig4,
            tnMcs8x16PortInfoDropInsertionLossFromSig5,
            tnMcs8x16PortInfoDropInsertionLossFromSig6,
            tnMcs8x16PortInfoDropInsertionLossFromSig7,
            tnMcs8x16PortInfoDropInsertionLossFromSig8
        }
        STATUS         current
        DESCRIPTION    ""
        ::= { tnOpticalPortInfoGroups 272 }

    tnMsh8fsmPortInfoScalarsGroup OBJECT-GROUP
        OBJECTS {
            tnMsh8fsmPortInfoAttributeTotal
        }
        STATUS         current
        DESCRIPTION    ""
        ::= { tnOpticalPortInfoGroups 273 }

    tnMsh8fsmPortInfoGroup OBJECT-GROUP
        OBJECTS {
            tnMsh8fsmPortInfoFunction
        }
        STATUS         current
        DESCRIPTION    ""
        ::= { tnOpticalPortInfoGroups 274 }

    tnMcsPortInfoScalarsGroup OBJECT-GROUP
        OBJECTS {
            tnMcsPortInfoAttributeTotal
        }
        STATUS         current
        DESCRIPTION    ""
        ::= { tnOpticalPortInfoGroups 275 }

    tnMcsPortInfoGroup OBJECT-GROUP
        OBJECTS {
           tnMcsPortInfoCurrentAddDisposition,
           tnMcsPortInfoCurrentDropDisposition,
           tnMcsPortInfoTestingActive
        }
        STATUS         current
        DESCRIPTION    ""
        ::= { tnOpticalPortInfoGroups 276 }

    tnMcsPortChannelInfoScalarsGroup OBJECT-GROUP
        OBJECTS {
            tnMcsPortChannelInfoAttributeTotal
        }
        STATUS         current
        DESCRIPTION    ""
        ::= { tnOpticalPortInfoGroups 277 }

    tnMcsPortChannelInfoGroup OBJECT-GROUP
        OBJECTS {
           tnMcsPortChannelInfoCurrentRoutingAdd,
           tnMcsPortChannelInfoCurrentRoutingDrop
        }
        STATUS         current
        DESCRIPTION    ""
        ::= { tnOpticalPortInfoGroups 278 }

    tnAarPortInfoScalarsGroup OBJECT-GROUP
        OBJECTS {
            tnAarPortInfoAttributeTotal
        }
        STATUS         current
        DESCRIPTION    ""
        ::= { tnOpticalPortInfoGroups 279 }

    tnAarPortInfoGroup OBJECT-GROUP
        OBJECTS {
            tnAarPortInfoTotalPowerIn,
            tnAarPortInfoLosThreshold,
            tnAarPortInfoLosThresholdTolerance,
            tnAarPortInfoLosMode,
            tnAarPortInfoTotalPowerOut,
            tnAarPortInfoSignalPowerOut,
            tnAarPortInfoOAPumpBiasCurrent,
            tnAarPortInfoOAPumpTemperature,
            tnAarPortInfoTestingActive
        }
        STATUS         current
        DESCRIPTION    ""
        ::= { tnOpticalPortInfoGroups 280 }

    tnWr20tfmPortChannelInfoScalarsGroup OBJECT-GROUP
        OBJECTS {
            tnWr20tfmPortChannelInfoAttributeTotal
        }
        STATUS         current
        DESCRIPTION    ""
        ::= { tnOpticalPortInfoGroups 281 }

    tnWr20tfmPortChannelInfoGroup OBJECT-GROUP
        OBJECTS {
            tnWr20tfmPortChannelInfoDropDisposition,
            tnWr20tfmPortChannelInfoAddDisposition
        }
        STATUS         current
        DESCRIPTION    ""
        ::= { tnOpticalPortInfoGroups 282 }

    tnMpoPortInfoScalarsGroup OBJECT-GROUP
        OBJECTS {
            tnMpoPortInfoAttributeTotal
        }
        STATUS         current
        DESCRIPTION    ""
        ::= { tnOpticalPortInfoGroups 283 }

    tnMpoPortInfoGroup OBJECT-GROUP
        OBJECTS {
            tnMpoPortInfoSignalDirection
        }
        STATUS         current
        DESCRIPTION    ""
        ::= { tnOpticalPortInfoGroups 284 }

    tnMpoPortMultiPositionScalarsGroup OBJECT-GROUP
        OBJECTS {
            tnMpoPortMultiPositionInfoAttributeTotal
        }
        STATUS         current
        DESCRIPTION    ""
        ::= { tnOpticalPortInfoGroups 285 }

    tnMpoPortMultiPositionInfoGroup OBJECT-GROUP
        OBJECTS {
            tnMpoPortMultiPositionInfoUnderlyingPortUsage,
            tnMpoPortMultiPositionInfoUnderlyingPortIfIndex,
            tnMpoPortMultiPositionInfoUnderlyingPortDirection
        }
        STATUS         current
        DESCRIPTION    ""
        ::= { tnOpticalPortInfoGroups 286 }
 
    tnIo4an100gPortInfoScalarsGroup OBJECT-GROUP
        OBJECTS {
            tnIo4an100gPortInfoAttributeTotal
        }
        STATUS         current
        DESCRIPTION    ""
        ::= { tnOpticalPortInfoGroups 287 }

    tnIo4an100gPortInfoGroup OBJECT-GROUP
        OBJECTS {
            tnIo4an100gPortInfoFunction
        }
        STATUS         current
        DESCRIPTION    ""
        ::= { tnOpticalPortInfoGroups 288 }

    tnIo30an10gPortInfoScalarsGroup OBJECT-GROUP
        OBJECTS {
            tnIo30an10gPortInfoAttributeTotal
        }
        STATUS         current
        DESCRIPTION    ""
        ::= { tnOpticalPortInfoGroups 289 }

    tnIo30an10gPortInfoGroup OBJECT-GROUP
        OBJECTS {
            tnIo30an10gPortInfoFunction
        }
        STATUS         current
        DESCRIPTION    ""
        ::= { tnOpticalPortInfoGroups 290 }

    tnIo30an300PortInfoScalarsGroup OBJECT-GROUP
        OBJECTS {
            tnIo30an300PortInfoAttributeTotal
        }
        STATUS         current
        DESCRIPTION    ""
        ::= { tnOpticalPortInfoGroups 291 }

    tnIo30an300PortInfoGroup OBJECT-GROUP
        OBJECTS {
            tnIo30an300PortInfoFunction
        }
        STATUS         current
        DESCRIPTION    ""
        ::= { tnOpticalPortInfoGroups 292 }

    tnIo4an400PortInfoScalarsGroup OBJECT-GROUP
        OBJECTS {
            tnIo4an400PortInfoAttributeTotal
        }
        STATUS         current
        DESCRIPTION    ""
        ::= { tnOpticalPortInfoGroups 293 }

    tnIo4an400PortInfoGroup OBJECT-GROUP
        OBJECTS {
            tnIo4an400PortInfoFunction
        }
        STATUS         current
        DESCRIPTION    ""
        ::= { tnOpticalPortInfoGroups 294 }

    tn12p120PortInfoScalarsGroup OBJECT-GROUP
        OBJECTS {
            tn12p120PortInfoAttributeTotal
        }
        STATUS         current
        DESCRIPTION    ""
        ::= { tnOpticalPortInfoGroups 295 }

    tn12p120PortInfoGroup OBJECT-GROUP
        OBJECTS {
            tn12p120PortInfoFunction
        }
        STATUS         current
        DESCRIPTION    ""
        ::= { tnOpticalPortInfoGroups 296 }

    tn20p200PortInfoScalarsGroup OBJECT-GROUP
        OBJECTS {
            tn20p200PortInfoAttributeTotal
        }
        STATUS         current
        DESCRIPTION    ""
        ::= { tnOpticalPortInfoGroups 297 }

    tn20p200PortInfoGroup OBJECT-GROUP
        OBJECTS {
            tn20p200PortInfoFunction
        }
        STATUS         current
        DESCRIPTION    ""
        ::= { tnOpticalPortInfoGroups 298 }

    tn1ud200PortInfoScalarsGroup OBJECT-GROUP
        OBJECTS {
            tn1ud200PortInfoAttributeTotal
        }
        STATUS         current
        DESCRIPTION    ""
        ::= { tnOpticalPortInfoGroups 299 }

    tn1ud200PortInfoGroup OBJECT-GROUP
        OBJECTS {
            tn1ud200PortInfoFunction
        }
        STATUS         current
        DESCRIPTION    ""
        ::= { tnOpticalPortInfoGroups 300 }

    tnOt130snq10PortInfoScalarsGroup OBJECT-GROUP
        OBJECTS {
            tnOt130snq10PortInfoAttributeTotal
        }
        STATUS         current
        DESCRIPTION    ""
        ::= { tnOpticalPortInfoGroups 301 }

    tnOt130snq10PortInfoGroup OBJECT-GROUP
        OBJECTS {
            tnOt130snq10PortInfoFunction
        }
        STATUS         current
        DESCRIPTION    ""
        ::= { tnOpticalPortInfoGroups 302 }

   tnIroadmvPortInfoScalarsGroup OBJECT-GROUP
        OBJECTS {
            tnIroadmvPortInfoAttributeTotal
        }
        STATUS         current
        DESCRIPTION    ""
        ::= { tnOpticalPortInfoGroups 303 }

    tnIroadmvPortInfoGroup OBJECT-GROUP
        OBJECTS {
            tnIroadmvPortInfoFunction
        }
        STATUS         current
        DESCRIPTION    ""
        ::= { tnOpticalPortInfoGroups 304 }

   tnIroadmfPortInfoScalarsGroup OBJECT-GROUP
        OBJECTS {
            tnIroadmfPortInfoAttributeTotal
        }
        STATUS         current
        DESCRIPTION    ""
        ::= { tnOpticalPortInfoGroups 305 }

    tnIroadmfPortInfoGroup OBJECT-GROUP
        OBJECTS {
            tnIroadmfPortInfoFunction
        }
        STATUS         current
        DESCRIPTION    ""
        ::= { tnOpticalPortInfoGroups 306 }

   tnIroadmPortInfoScalarsGroup OBJECT-GROUP
        OBJECTS {
            tnIroadmPortInfoAttributeTotal
        }
        STATUS         current
        DESCRIPTION    ""
        ::= { tnOpticalPortInfoGroups 307 }

    tnIroadmPortInfoGroup OBJECT-GROUP
        OBJECTS {
            tnIroadmPortInfoIngressOaPowerIn,
            tnIroadmPortInfoIngressOaPowerOut,
            tnIroadmPortInfoEgressOaPowerIn,
            tnIroadmPortInfoEgressOaPowerOut,
            tnIroadmPortInfoIngressOaSignalPowerOut,
            tnIroadmPortInfoEgressOaSignalPowerOut,
            tnIroadmPortInfoIngressOaInputToOutputGain,
            tnIroadmPortInfoEgressOaInputToOutputGain,
            tnIroadmPortInfoEgressOaMaxFlatGain,
            tnIroadmPortInfoIngressOaMaxFlatGain,
            tnIroadmPortInfoActualTilt,
            tnIroadmPortInfoDCMInPower,
            tnIroadmPortInfoDCMOutPower,
            tnIroadmPortInfoPowerSpanRepairMargin,
            tnIroadmPortInfoEnable,
            tnIroadmPortInfoGainTilt
        }
        STATUS         current
        DESCRIPTION    ""
        ::= { tnOpticalPortInfoGroups 308 }
   
    tnIroadmPortChannelInfoScalarsGroup OBJECT-GROUP
        OBJECTS {
            tnIroadmPortChannelInfoAttributeTotal
        }
        STATUS         current
        DESCRIPTION    ""
        ::= { tnOpticalPortInfoGroups 309 }

    tnIroadmPortChannelInfoGroup OBJECT-GROUP
        OBJECTS {
            tnIroadmPortChannelInfoAddDisposition
        }
        STATUS         current
        DESCRIPTION    ""
        ::= { tnOpticalPortInfoGroups 310 }
   
    tnWssRefLdInfoScalarsGroup OBJECT-GROUP
        OBJECTS {
            tnWssRefLdInfoAttributeTotal
        }
        STATUS         current
        DESCRIPTION    ""
        ::= { tnOpticalPortInfoGroups 311 }

    tnWssRefLdInfoGroup OBJECT-GROUP
        OBJECTS {
            tnWssRefLdInfoIfIndex,
            tnWssRefLdInfoApplicability
        }
        STATUS         current
        DESCRIPTION    ""
        ::= { tnOpticalPortInfoGroups 312 }

   tnMonOcmPortInfoScalarsGroup OBJECT-GROUP
        OBJECTS {
            tnMonOcmPortInfoAttributeTotal
        }
        STATUS         current
        DESCRIPTION    ""
        ::= { tnOpticalPortInfoGroups 313 }

    tnMonOcmPortInfoGroup OBJECT-GROUP
        OBJECTS {
            tnMonOcmPortInfoFunction
        }
        STATUS         current
        DESCRIPTION    ""
        ::= { tnOpticalPortInfoGroups 314 }

     tnUl2uc400PortInfoScalarsGroup OBJECT-GROUP
        OBJECTS {
            tnUl2uc400PortInfoAttributeTotal
        }
        STATUS         current
        DESCRIPTION    ""
        ::= { tnOpticalPortInfoGroups 315 }

    tnUl2uc400PortInfoGroup OBJECT-GROUP
        OBJECTS {
            tnUl2uc400PortInfoFunction
        }
        STATUS         current
        DESCRIPTION    ""
        ::= { tnOpticalPortInfoGroups 316 }

    tnUl4uc400PortInfoScalarsGroup OBJECT-GROUP
        OBJECTS {
            tnUl4uc400PortInfoAttributeTotal
        }
        STATUS         current
        DESCRIPTION    ""
        ::= { tnOpticalPortInfoGroups 317 }

    tnUl4uc400PortInfoGroup OBJECT-GROUP
        OBJECTS {
            tnUl4uc400PortInfoFunction
        }
        STATUS         current
        DESCRIPTION    ""
        ::= { tnOpticalPortInfoGroups 318 }

    tnUl20uc200PortInfoScalarsGroup OBJECT-GROUP
        OBJECTS {
            tnUl20uc200PortInfoAttributeTotal
        }
        STATUS         current
        DESCRIPTION    ""
        ::= { tnOpticalPortInfoGroups 319 }

    tnUl20uc200PortInfoGroup OBJECT-GROUP
        OBJECTS {
            tnUl20uc200PortInfoFunction
        }
        STATUS         current
        DESCRIPTION    ""
        ::= { tnOpticalPortInfoGroups 320 }

    tnD5x500PortInfoScalarsGroup OBJECT-GROUP
        OBJECTS {
            tnD5x500PortInfoAttributeTotal
        }
        STATUS         current
        DESCRIPTION    ""
        ::= { tnOpticalPortInfoGroups 321 }

    tnD5x500PortInfoGroup OBJECT-GROUP
        OBJECTS {
            tnD5x500PortInfoFunction
        }
        STATUS         current
        DESCRIPTION    ""
        ::= { tnOpticalPortInfoGroups 322 }

    tnOtS11M100PortInfoScalarsGroup OBJECT-GROUP
        OBJECTS {
            tnOtS11M100PortInfoAttributeTotal
        }
        STATUS         current
        DESCRIPTION    ""
        ::= { tnOpticalPortInfoGroups 323 }

    tnOtS11M100PortInfoGroup OBJECT-GROUP
        OBJECTS {
            tnOtS11M100PortInfoFunction
        }
        STATUS         current
        DESCRIPTION    ""
        ::= { tnOpticalPortInfoGroups 324 }

    tnMonOtdrPortInfoScalarsGroup OBJECT-GROUP
        OBJECTS {
            tnMonOtdrPortInfoAttributeTotal
        }
        STATUS         current
        DESCRIPTION    ""
        ::= { tnOpticalPortInfoGroups 325 }

    tnMonOtdrPortInfoGroup OBJECT-GROUP
        OBJECTS {
            tnMonOtdrPortInfoFunction
        }
        STATUS         current
        DESCRIPTION    ""
        ::= { tnOpticalPortInfoGroups 326 }

    tnPSS96PowerFilterPortInfoScalarsGroup OBJECT-GROUP
        OBJECTS {
            tnPSS96PowerFilterPortInfoAttributeTotal
        }
        STATUS         current
        DESCRIPTION    ""
        ::= { tnOpticalPortInfoGroups 327 }

    tnPSS96PowerFilterPortInfoGroup OBJECT-GROUP
        OBJECTS {
            tnPSS96PowerFilterPortInfoFunction
        }
        STATUS         current
        DESCRIPTION    ""
        ::= { tnOpticalPortInfoGroups 328 }

      tn12ce120PortInfoScalarsGroup OBJECT-GROUP
         OBJECTS {
             tn12ce120PortInfoAttributeTotal
         }
         STATUS         current
         DESCRIPTION    ""
         ::= { tnOpticalPortInfoGroups 329 }

     tn12ce120PortInfoGroup OBJECT-GROUP
         OBJECTS {
             tn12ce120PortInfoFunction
         }
         STATUS         current
         DESCRIPTION    ""
         ::= { tnOpticalPortInfoGroups 330 }

     tn1ce100PortInfoScalarsGroup OBJECT-GROUP
         OBJECTS {
             tn1ce100PortInfoAttributeTotal
         }
         STATUS         current
         DESCRIPTION    ""
         ::= { tnOpticalPortInfoGroups 331 }

     tn1ce100PortInfoGroup OBJECT-GROUP
         OBJECTS {
             tn1ce100PortInfoFunction
         }
         STATUS         current
         DESCRIPTION    ""
         ::= { tnOpticalPortInfoGroups 332 }

    tnLcI1000PortInfoScalarsGroup  OBJECT-GROUP
        OBJECTS {
            tnLcI1000PortInfoAttributeTotal
        }
        STATUS         current
        DESCRIPTION    ""
        ::= { tnOpticalPortInfoGroups 333 }

    tnLcI1000PortInfoGroup  OBJECT-GROUP
        OBJECTS {
            tnLcI1000PortInfoFunction
        }
        STATUS         current
        DESCRIPTION    ""
        ::= { tnOpticalPortInfoGroups 334 }

--------------------------------------------------------------------------------
-- Conformance Port Line Card Config Group Definitions
--------------------------------------------------------------------------------
--    obsolete
--    tnBbaHgPortLcConfigScalarsGroup OBJECT-GROUP ::= { tnOpticalPortLcConfigGroups 1 }
--    tnBbaHgPortLcConfigGroup OBJECT-GROUP ::= { tnOpticalPortLcConfigGroups 2 }
--    tnBbaLgPortLcConfigScalarsGroup OBJECT-GROUP ::= { tnOpticalPortLcConfigGroups 3 }
--    tnBbaLgPortLcConfigGroup OBJECT-GROUP ::= { tnOpticalPortLcConfigGroups 4 }

--------------------------------------------------------------------------------
-- Compliance Statements (mandatory)
--------------------------------------------------------------------------------
    tnOpticalPortCompliance MODULE-COMPLIANCE
        STATUS         current
        DESCRIPTION    ""
        MODULE
        MANDATORY-GROUPS {
--            obsolete
--            tnOpticalPortScalarsGroup,
--            tnOC48SwsPortScalarsGroup,
--            tnSimpleOpticsPortScalarsGroup,
--            tnOC48SwsUserNwPortScalarsGroup,
--            tnOC48SwsUserNwPortGroup,
--            tnBandFilterPortScalarsGroup,
--            tnBandFilterPortGroup,
--            tnOscPortScalarsGroup,
--            tnOscPortGroup,
--            tnChannelFilterPortScalarsGroup,
--            tnChannelFilterPortGroup,
--            tnBbaLinePortScalarsGroup,
--            tnBbaLinePortGroup,
--            tnPpsPortScalarsGroup,
--            tnPpsPortGroup,
--            tnOC192SwsUserNwPortScalarsGroup,
--            tnOC192SwsUserNwPortGroup,
--            tn2x1GEoSWSPortScalarsGroup,
--            tn2x1GEoSWSPortGroup,
--            tnSonetPortScalarsGroup,
--            tnSonetPortGroup,
            tnOpticalPortGroup,
--            obsolete
--            tnRoadmPortScalarsGroup,
--            tnRoadmPortGroup,
--            tnWaveKeyPortScalarsGroup,
            tnWaveKeyPortGroup,
--            obsolete
--            tn10GELANPortScalarsGroup,
--            tn10GELANPortGroup,
            tnOpticalFiberGroup,
--            obsolete
--            tnChannelAddDropPortScalarsGroup,
--            tnChannelAddDropPortGroup,
--            tnQuadOC48MuxPortScalarsGroup,
--            tnQuadOC48MuxPortGroup,
--            tnBbaLowGainPortScalarsGroup,
--            tnBbaLowGainPortGroup,
            tnLoopbackPortGroup,
--            obsolete
--            tnDcmPortScalarsGroup,
--            tnDcmPortGroup,
            tnInsertionLossPortGroup,
--            obsolete
--            tnQuadOC3or12MuxPortScalarsGroup,
--            tnQuadOC3or12MuxPortGroup,
--            tnDecaGigEMuxPortScalarsGroup,
--            tnDecaGigEMuxPortGroup,
            tnProtectionGroupPortGroup,
            tnDTVPortGroup,
            tnPortInventoryGroup,
            tnPortOtdrScanGroup,
            tnFlexgridOtsInfoGroup
        }
        ::= { tnOpticalPortCompliances 1 }

--------------------------------------------------------------------------------
-- Compliance Port Config Statements (mandatory)
--------------------------------------------------------------------------------
    tnOpticalPortConfigCompliance MODULE-COMPLIANCE
        STATUS         current
        DESCRIPTION    ""
        MODULE
        MANDATORY-GROUPS {
            tnSdhPortConfigScalarsGroup,
            tnSdhPortConfigGroup,
--            obsolete
--            tnOC48STM16PortConfigScalarsGroup,
--            tnOC48STM16PortConfigGroup,
--            tnOC192STM64PortConfigScalarsGroup,
--            tnOC192STM64PortConfigGroup,
--            tnQuadOC48STM16MuxPortConfigScalarsGroup,
--            tnQuadOC48STM16MuxPortConfigGroup,
--            tnQuadOC3or12STM1or4MuxPortConfigScalarsGroup,
--            tnQuadOC3or12STM1or4MuxPortConfigGroup,
--            tnBandFilterPortConfigScalarsGroup,
--            tnBandFilterPortConfigGroup,
            tnOscPortConfigScalarsGroup,
            tnOscPortConfigGroup,
--            obsolete
--            tnChFilterPortConfigScalarsGroup,
--            tnChFilterPortConfigGroup,
--            tnChAddDropPortConfigScalarsGroup,
--            tnChAddDropPortConfigGroup,
--            tnBbaHgPortConfigScalarsGroup,
--            tnBbaHgPortConfigGroup,
--            tnBbaLgPortConfigScalarsGroup,
--            tnBbaLgPortConfigGroup,
--            tnPpsPortConfigScalarsGroup,
--            tnPpsPortConfigGroup,
--            tnDualGigEMuxPortConfigScalarsGroup,
--            tnDualGigEMuxPortConfigGroup,
--            tnRoadmPortConfigScalarsGroup,
--            tnRoadmPortConfigGroup,
--            tn10GigELANPortConfigScalarsGroup,
--            tn10GigELANPortConfigGroup,
            tnDcmPortConfigScalarsGroup,
            tnDcmPortConfigGroup,
--            obsolete
--            tnDecaGigEMuxPortConfigScalarsGroup,
--            tnDecaGigEMuxPortConfigGroup,
            tnSonetPortConfigScalarsGroup,
            tnSonetPortConfigGroup,
--            obsolete
--            tnExternalDcuPortConfigScalarsGroup,
--            tnExternalDcuPortConfigGroup,
            tnDigitalWrapperPortConfigScalarsGroup,
            tnDigitalWrapperPortConfigGroup,
            tnNetworkPortConfigScalarsGroup,
            tnNetworkPortConfigGroup,
--            obsolete
--            tnMsaHgPortConfigScalarsGroup,
--            tnMsaHgPortConfigGroup,
--            tnCmd42PortConfigScalarsGroup,
--            tnCmd42PortConfigGroup,
--            tnWssX9PortConfigScalarsGroup,
--            tnWssX9PortConfigGroup,
            tnSfpPortConfigScalarsGroup,
            tnSfpPortConfigGroup,
--            obsolete
--            tn1xMR2dot5GPortConfigScalarsGroup,
--            tn1xMR2dot5GPortConfigGroup,
            tnOpsaPortConfigScalarsGroup,
            tnOpsaPortConfigGroup,
            tn11stmm10PortConfigScalarsGroup,
            tn11stmm10PortConfigGroup,
            tn11star1PortConfigScalarsGroup,
            tn11star1PortConfigGroup,
            tnAhphgPortConfigScalarsGroup,
            tnAhphgPortConfigGroup,
            tnAlphgPortConfigScalarsGroup,
            tnAlphgPortConfigGroup,
            tnCwr8PortConfigScalarsGroup,
            tnCwr8PortConfigGroup,
            tn11stge12PortConfigScalarsGroup,
            tn11stge12PortConfigGroup,
            tn11dpge12PortConfigScalarsGroup,
            tn11dpge12PortConfigGroup,
            tnSfd44PortConfigScalarsGroup,
            tnSfd44PortConfigGroup,
            tnDwdmCmnPortConfigGroup,
            tnDwdmCmnLinePortConfigGroup,
            tnDwdmCmnClientPortConfigGroup,
            tnRsmonIngrPortConfigGroup,
            tnMsmonPortConfigGroup,
            tnOscSfpPortConfigGroup,
            tnDwdmGpPhyPortConfigGroup,
--            obsolete
--            tnGccPortConfigGroup,
            tnSvacPortConfigGroup,
            tnSfdPortConfigGroup,
            tnSfcPortConfigGroup,
            tnVtsPortConfigGroup,
            tnOmdPortConfigGroup,
            tn4dpa4PortConfigScalarsGroup,
            tn4dpa4PortConfigGroup,
            tnCwr8c88PortConfigScalarsGroup,
            tnCwr8c88PortConfigGroup,
            tnSfd44bPortConfigScalarsGroup,
            tnSfd44bPortConfigGroup,
            tnItlbPortConfigScalarsGroup,
            tnItlbPortConfigGroup,
            tnAhplgPortConfigScalarsGroup,
            tnAhplgPortConfigGroup,
            tnDwdmCmnOtu1Odu1LinePortConfigGroup,
            tnDwdmCmnOtu1Odu1ClientPortConfigGroup,
            tn43stx4PortConfigScalarsGroup,
            tn43stx4PortConfigGroup,
            tnDwdmCmnOtu3Odu3LinePortConfigGroup,
            tnAlpfgkPortConfigScalarsGroup,
            tnAlpfgkPortConfigGroup,
            tn4dpa2PortConfigScalarsGroup,
            tn4dpa2PortConfigGroup,
            tn43sta1pPortConfigScalarsGroup,
            tn43sta1pPortConfigGroup,
            tn43stx4pPortConfigScalarsGroup,
            tn43stx4pPortConfigGroup,
            tnA2325aPortConfigScalarsGroup,
            tnA2325aPortConfigGroup,
            tnSfd40PortConfigScalarsGroup,
            tnSfd40PortConfigGroup,
            tnSfd40bPortConfigScalarsGroup,
            tnSfd40bPortConfigGroup,
            tn11qpa4PortConfigScalarsGroup,
            tn11qpa4PortConfigGroup,
            tn112scx10PortConfigScalarsGroup,
            tn112scx10PortConfigGroup,
            tn112sca1PortConfigScalarsGroup,
            tn112sca1PortConfigGroup,
            tnDwdmCmnOtu4Odu4LinePortConfigGroup,
            tnDwdmCmnOtu4Odu4ClientPortConfigGroup,
            tnRsmonEgrPortConfigGroup,
            tnDwdmCbrArPortConfigGroup,
            tnAlpfgtPortConfigScalarsGroup,
            tnAlpfgtPortConfigGroup,
            tnOsctPortConfigScalarsGroup,
            tnOsctPortConfigGroup,
            tnWtocmPortConfigScalarsGroup,
            tnWtocmPortConfigGroup,
            tnWr2c88PortConfigScalarsGroup,
            tnWr2c88PortConfigGroup,
            tnAm2017bPortConfigScalarsGroup,
            tnAm2325bPortConfigGroup,
            tn1dpp21PortConfigScalarsGroup,
            tn1dpp21PortConfigGroup,
            tnE1T1PortConfigGroup,
            tnMvacPortConfigScalarsGroup,
            tnMvacPortConfigGroup,
            tn43scx4PortConfigScalarsGroup,
            tn43scx4PortConfigGroup,
            tnRa2pPortConfigScalarsGroup,
            tnRa2pPortConfigGroup,
            tnAm2318aPortConfigScalarsGroup,
            tnAm2318aPortConfigGroup,
            tnAm2125aPortConfigScalarsGroup,
            tnAm2125aPortConfigGroup,
            tnItluPortConfigScalarsGroup,
            tnItluPortConfigGroup,
            tnWr8c88aPortConfigScalarsGroup,
            tnWr8c88aPortConfigGroup,
            tn11dpe12ePortConfigScalarsGroup,
            tn11dpe12ePortConfigGroup,
            tn112sx10lPortConfigScalarsGroup,
            tn112sx10lPortConfigGroup,
            tn112sa1lPortConfigScalarsGroup,
            tn112sa1lPortConfigGroup,
            tn11dpm12PortConfigScalarsGroup,
            tn11dpm12PortConfigGroup,
--            obsolete
--            tnWr8c88aAttenPortConfigGroup,
            tnRamanPortConfigGroup,
            tnMesh4PortConfigScalarsGroup,
            tnMesh4PortConfigGroup,
--            obsolete
--            tnTcmPortConfigScalarsGroup,
--            tnTcmPortConfigGroup,
            tn43sca1PortConfigScalarsGroup,
            tn43sca1PortConfigGroup,
            tn43scx4lPortConfigScalarsGroup,
            tn43scx4lPortConfigGroup,
            tnAm2125bPortConfigScalarsGroup,
            tnAm2125bPortConfigGroup,
            tn112snx10PortConfigScalarsGroup,
            tn112snx10PortConfigGroup,
            tn112sna1PortConfigScalarsGroup,
            tn112sna1PortConfigGroup,
--            obsolete
--            tn11qta4PortConfigScalarsGroup,
--            tn11qta4PortConfigGroup,
            tn1dpp24mPortConfigScalarsGroup,
            tn1dpp24mPortConfigGroup,
            tnul43scupPortConfigScalarsGroup,
            tnul43scupPortConfigGroup,
            tnul11qcupPortConfigScalarsGroup,
            tnul11qcupPortConfigGroup,
            tnDwdmCmnOtu3Odu3ClientPortConfigGroup,
            tn11qpen4PortConfigScalarsGroup,
            tn11qpen4PortConfigGroup,
            tn43scx4ePortConfigScalarsGroup,
            tn43scx4ePortConfigGroup,
            tn43scge1PortConfigScalarsGroup,
            tn43scge1PortConfigGroup,
            tn11qpe24PortConfigScalarsGroup,
            tn11qpe24PortConfigGroup,
            tn11star1aPortConfigScalarsGroup,
            tn11star1aPortConfigGroup,
            tnMvac8bPortConfigScalarsGroup,
            tnMvac8bPortConfigGroup,
            tnWssAttenPortConfigScalarsGroup,
            tnWssAttenPortConfigGroup,
            tnWr8c88afPortConfigScalarsGroup,
            tnWr8c88afPortConfigGroup,
            tncl10an10gPortConfigScalarsGroup,
            tncl10an10gPortConfigGroup,
            tncl24anmPortConfigScalarsGroup,
            tncl24anmPortConfigGroup,
            tnOpsbPortConfigScalarsGroup,
            tnOpsbPortConfigGroup,
            tnOpsPortConfigScalarsGroup,
            tnOpsPortConfigGroup,
            tn11dpe12aPortConfigScalarsGroup,
            tn11dpe12aPortConfigGroup,
            tnul130scupPortConfigScalarsGroup,
            tnul130scupPortConfigGroup,
            tn130scx10PortConfigScalarsGroup,
            tn130scx10PortConfigGroup,
            tnA2p2125PortConfigScalarsGroup,
            tnA2p2125PortConfigGroup,
            tn4qpa8PortConfigScalarsGroup,
            tn4qpa8PortConfigGroup,
            tnOt112pdm11PortConfigScalarsGroup,
            tnOt112pdm11PortConfigGroup,
            tnWtocmaPortConfigScalarsGroup,
            tnWtocmaPortConfigGroup,
            tnPtpctlPortConfigScalarsGroup,
            tnPtpctlPortConfigGroup,
            tnPtpioPortConfigScalarsGroup,
            tnPtpioPortConfigGroup,
            tnIo24et1gbPortConfigScalarsGroup,
            tnIo24et1gbPortConfigGroup,
            tnDwdmIoPortConfigScalarsGroup,
            tnDwdmIoPortConfigGroup,
            tnIo4an10gPortConfigScalarsGroup,
            tnIo4an10gPortConfigGroup,
            tnIo8et1gbPortConfigScalarsGroup,
            tnIo8et1gbPortConfigGroup,
            tnIo10et10gPortConfigScalarsGroup,
            tnIo10et10gPortConfigGroup,
            tnUl11qcupcPortConfigScalarsGroup,
            tnUl11qcupcPortConfigGroup,
            tnOt520scx4PortConfigScalarsGroup,
            tnOt520scx4PortConfigGroup,
            tnWssAprPortConfigScalarsGroup,
            tnWssAprPortConfigGroup,
            tnPowerFilterPortConfigScalarsGroup,
            tnPowerFilterPortConfigGroup,
            tn11ope8PortConfigScalarsGroup,
            tn11ope8PortConfigGroup,
            tn11qce12xPortConfigScalarsGroup,
            tn11qce12xPortConfigGroup,
            tnAm2625aPortConfigScalarsGroup,
            tnAm2625aPortConfigGroup,
            tnAm2032aPortConfigScalarsGroup,
            tnAm2032aPortConfigGroup,
            tnOt260scx2PortConfigScalarsGroup,
            tnOt260scx2PortConfigGroup,
            tnOt130snx10PortConfigScalarsGroup,
            tnOt130snx10PortConfigGroup,
            tnIo24anmbPortConfigScalarsGroup,
            tnIo24anmbPortConfigGroup,
            tnOt11dpm8PortConfigScalarsGroup,
            tnOt11dpm8PortConfigGroup,
            tnOt11dpm4mPortConfigScalarsGroup,
            tnOt11dpm4mPortConfigGroup,
            tnUl130scupbPortConfigScalarsGroup,
            tnUl130scupbPortConfigGroup,
            tnOt112sdx11PortConfigScalarsGroup,
            tnOt112sdx11PortConfigGroup,
            tnAa2donwPortConfigScalarsGroup,
            tnAa2donwPortConfigGroup,
            tnOt130sca1PortConfigScalarsGroup,
            tnOt130sca1PortConfigGroup,
            tnIo10an10gbPortConfigScalarsGroup,
            tnIo10an10gbPortConfigGroup,
            tnIo10et10gbPortConfigScalarsGroup,
            tnIo10et10gbPortConfigGroup,
            tnPsc1x6PortConfigScalarsGroup,
            tnPsc1x6PortConfigGroup,
            tnWr20tfPortConfigScalarsGroup,
            tnWr20tfPortConfigGroup,
            tnWtocmfPortConfigScalarsGroup,
            tnWtocmfPortConfigGroup,
            tnAswgPortConfigScalarsGroup,
            tnAswgPortConfigGroup,
            tnA4pswgPortConfigScalarsGroup,
            tnA4pswgPortConfigGroup,
            tnOtdrPortConfigScalarsGroup,
            tnOtdrPortConfigGroup,
            tnWr20tfmPortConfigScalarsGroup,
            tnWr20tfmPortConfigGroup,
            tnAar8aPortConfigScalarsGroup,
            tnAar8aPortConfigGroup,
            tnMcs8x16PortConfigScalarsGroup,
            tnMcs8x16PortConfigGroup,
            tnMsh8fsmPortConfigScalarsGroup,
            tnMsh8fsmPortConfigGroup,
            tnMcsPortConfigScalarsGroup,
            tnMcsPortConfigGroup,
            tnAarPortConfigScalarsGroup,
            tnAarPortConfigGroup,
            tnWr20tfmPortChannelConfigScalarsGroup,
            tnWr20tfmPortChannelConfigGroup,
            tnMpoPortConfigScalarsGroup,
            tnMpoPortConfigGroup,
            tnIo4an100gPortConfigScalarsGroup,
            tnIo4an100gPortConfigGroup,
            tnIo30an10gPortConfigScalarsGroup,
            tnIo30an10gPortConfigGroup,
            tnIo30an300PortConfigScalarsGroup,
            tnIo30an300PortConfigGroup,
            tnIo4an400PortConfigScalarsGroup,
            tnIo4an400PortConfigGroup,
            tn12p120PortConfigScalarsGroup,
            tn12p120PortConfigGroup,
            tn20p200PortConfigScalarsGroup,
            tn20p200PortConfigGroup,
            tn1ud200PortConfigScalarsGroup,
            tn1ud200PortConfigGroup,
            tnOt130snq10PortConfigScalarsGroup,
            tnOt130snq10PortConfigGroup,
            tnIroadmvPortConfigScalarsGroup,
            tnIroadmvPortConfigGroup,
            tnIroadmfPortConfigScalarsGroup,
            tnIroadmfPortConfigGroup,
            tnIroadmPortConfigScalarsGroup,
            tnIroadmPortConfigGroup,
            tnMonOcmPortConfigScalarsGroup,
            tnMonOcmPortConfigGroup,
            tnUl2uc400PortConfigScalarsGroup,
            tnUl2uc400PortConfigGroup,
            tnUl4uc400PortConfigScalarsGroup,
            tnUl4uc400PortConfigGroup,
            tnUl20uc200PortConfigScalarsGroup,
            tnUl20uc200PortConfigGroup,
            tnD5x500PortConfigScalarsGroup,
            tnD5x500PortConfigGroup,
            tnOtS11M100PortConfigScalarsGroup,
            tnOtS11M100PortConfigGroup,
            tnMonOtdrPortConfigScalarsGroup,
            tnMonOtdrPortConfigGroup,
            tnPSS96PowerFilterPortConfigScalarsGroup,
            tnPSS96PowerFilterPortConfigGroup,
            tn12ce120PortConfigScalarsGroup,
            tn12ce120PortConfigGroup,
            tn1ce100PortConfigScalarsGroup,
            tn1ce100PortConfigGroup,
            tnLcI1000PortConfigScalarsGroup,
            tnLcI1000PortConfigGroup
        }
        ::= { tnOpticalPortConfigCompliances 1 }

--------------------------------------------------------------------------------
-- Compliance Port Info Statements (mandatory)
--------------------------------------------------------------------------------
    tnOpticalPortInfoCompliance MODULE-COMPLIANCE
        STATUS         current
        DESCRIPTION    ""
        MODULE
        MANDATORY-GROUPS {
            tnSdhPortInfoScalarsGroup,
            tnSdhPortInfoGroup,
--            obsolete
--            tnOC48STM16PortInfoScalarsGroup,
--            tnOC48STM16PortInfoGroup,
--            tnOC192STM64PortInfoScalarsGroup,
--            tnOC192STM64PortInfoGroup,
--            tnQuadOC48STM16MuxPortInfoScalarsGroup,
--            tnQuadOC48STM16MuxPortInfoGroup,
--            tnQuadOC3or12STM1or4MuxPortInfoScalarsGroup,
--            tnQuadOC3or12STM1or4MuxPortInfoGroup,
--            tnBandFilterPortInfoScalarsGroup,
--            tnBandFilterPortInfoGroup,
            tnOscPortInfoScalarsGroup,
            tnOscPortInfoGroup,
--            obsolete
--            tnChFilterPortInfoScalarsGroup,
--            tnChFilterPortInfoGroup,
--            tnChAddDropPortInfoScalarsGroup,
--            tnChAddDropPortInfoGroup,
--            tnBbaHgPortInfoScalarsGroup,
--            tnBbaHgPortInfoGroup,
--            tnBbaLgPortInfoScalarsGroup,
--            tnBbaLgPortInfoGroup,
--            tnPpsPortInfoScalarsGroup,
--            tnPpsPortInfoGroup,
--            tnDualGigEMuxPortInfoScalarsGroup,
--            tnDualGigEMuxPortInfoGroup,
--            tnRoadmPortInfoScalarsGroup,
--            tnRoadmPortInfoGroup,
--            tn10GigELANPortInfoScalarsGroup,
--            tn10GigELANPortInfoGroup,
            tnDcmPortInfoGroup,
            tnDcmPortInfoScalarsGroup,
--            obsolete
--            tnDecaGigEMuxPortInfoScalarsGroup,
--            tnDecaGigEMuxPortInfoGroup,
            tnSonetPortInfoScalarsGroup,
            tnSonetPortInfoGroup,
--            obsolete
--            tnExternalDcuPortInfoScalarsGroup,
--            tnExternalDcuPortInfoGroup,
            tnDigitalWrapperPortInfoScalarsGroup,
            tnDigitalWrapperPortInfoGroup,
--            obsolete
--            tnMsaHgPortInfoScalarsGroup,
--            tnMsaHgPortInfoGroup,
--            tnWssX9PortInfoScalarsGroup,
--            tnWssX9PortInfoGroup,
            tnSfpPortInfoScalarsGroup,
            tnSfpPortInfoGroup,
--            obsolete
--            tn1xMR2dot5GPortInfoScalarsGroup,
--            tn1xMR2dot5GPortInfoGroup,
            tnNetworkPortInfoScalarsGroup,
            tnNetworkPortInfoGroup,
            tnOpsaPortInfoScalarsGroup,
            tnOpsaPortInfoGroup,
            tn11stmm10PortInfoScalarsGroup,
            tn11stmm10PortInfoGroup,
            tn11star1PortInfoScalarsGroup,
            tn11star1PortInfoGroup,
            tnAhphgPortInfoScalarsGroup,
            tnAhphgPortInfoGroup,
            tnAlphgPortInfoScalarsGroup,
            tnAlphgPortInfoGroup,
            tnCwr8PortInfoScalarsGroup,
            tnCwr8PortInfoGroup,
            tn11stge12PortInfoScalarsGroup,
            tn11stge12PortInfoGroup,
            tn11dpge12PortInfoScalarsGroup,
            tn11dpge12PortInfoGroup,
--            obsolete
--            tnDwdmGpPhyPortInfoGroup,
            tnDwdmCmnLinePortInfoGroup,
            tnDwdmCmnClientPortInfoGroup,
            tnRsmonIngrPortInfoGroup,
            tnOtPortInfoGroup,
            tnWaveKeyPortInfoGroup,
            tnOmdPortInfoGroup,
            tn4dpa4PortInfoScalarsGroup,
            tn4dpa4PortInfoGroup,
            tnCwr8c88PortInfoScalarsGroup,
            tnCwr8c88PortInfoGroup,
            tnAhplgPortInfoScalarsGroup,
            tnAhplgPortInfoGroup,
            tnTimeSlotLinePortInfoGroup,
            tnDwdmCmnOtu1Odu1LinePortInfoGroup,
            tnDwdmCmnOtu1Odu1ClientPortInfoGroup,
            tn43stx4PortInfoScalarsGroup,
            tn43stx4PortInfoGroup,
            tnDwdmCmnOtu3Odu3LinePortInfoGroup,
            tnAlpfgkPortInfoScalarsGroup,
            tnAlpfgkPortInfoGroup,
            tn4dpa2PortInfoScalarsGroup,
            tn4dpa2PortInfoGroup,
            tn43sta1pPortInfoScalarsGroup,
            tn43sta1pPortInfoGroup,
            tn43stx4pPortInfoScalarsGroup,
            tn43stx4pPortInfoGroup,
            tnRsmonEgrPortInfoGroup,
            tnA2325aPortInfoScalarsGroup,
            tnA2325aPortInfoGroup,
            tn11qpa4PortInfoScalarsGroup,
            tn11qpa4PortInfoGroup,
            tn112scx10PortInfoScalarsGroup,
            tn112scx10PortInfoGroup,
            tn112sca1PortInfoScalarsGroup,
            tn112sca1PortInfoGroup,
            tnDwdmCmnOtu4Odu4LinePortInfoGroup,
            tnDwdmCmnOtu4Odu4ClientPortInfoGroup,
            tnAlpfgtPortInfoScalarsGroup,
            tnAlpfgtPortInfoGroup,
            tnOsctPortInfoScalarsGroup,
            tnOsctPortInfoGroup,
            tnWtocmPortInfoScalarsGroup,
            tnWtocmPortInfoGroup,
            tnWr2c88PortInfoScalarsGroup,
            tnWr2c88PortInfoGroup,
            tnAm2017bPortInfoScalarsGroup,
            tnAm2325bPortInfoGroup,
            tn1dpp21PortInfoScalarsGroup,
            tn1dpp21PortInfoGroup,
--            obsolete
--            tnE1T1PortInfoGroup,
            tnMvacPortInfoScalarsGroup,
            tnMvacPortInfoGroup,
            tn43scx4PortInfoScalarsGroup,
            tn43scx4PortInfoGroup,
            tnRa2pPortInfoScalarsGroup,
            tnRa2pPortInfoGroup,
            tnAm2318aPortInfoScalarsGroup,
            tnAm2318aPortInfoGroup,
            tnAm2125aPortInfoScalarsGroup,
            tnAm2125aPortInfoGroup,
            tnWr8c88aPortInfoScalarsGroup,
            tnWr8c88aPortInfoGroup,
            tn11dpe12ePortInfoScalarsGroup,
            tn11dpe12ePortInfoGroup,
            tn112sx10lPortInfoScalarsGroup,
            tn112sx10lPortInfoGroup,
            tn112sa1lPortInfoScalarsGroup,
            tn112sa1lPortInfoGroup,
            tn11dpm12PortInfoScalarsGroup,
            tn11dpm12PortInfoGroup,
            tnRamanPortInfoGroup,
            tnMesh4PortInfoScalarsGroup,
            tnMesh4PortInfoGroup,
--            obsolete
--            tnTcmPortInfoScalarsGroup,
--            tnTcmPortInfoGroup,
            tn43sca1PortInfoScalarsGroup,
            tn43sca1PortInfoGroup,
            tn43scx4lPortInfoScalarsGroup,
            tn43scx4lPortInfoGroup,
            tnAm2125bPortInfoScalarsGroup,
            tnAm2125bPortInfoGroup,
            tn112snx10PortInfoScalarsGroup,
            tn112snx10PortInfoGroup,
            tn112sna1PortInfoScalarsGroup,
            tn112sna1PortInfoGroup,
--            obsolete
--            tn11qta4PortInfoScalarsGroup,
--            tn11qta4PortInfoGroup,
            tn1dpp24mPortInfoScalarsGroup,
            tn1dpp24mPortInfoGroup,
            tnul43scupPortInfoScalarsGroup,
            tnul43scupPortInfoGroup,
            tnul11qcupPortInfoScalarsGroup,
            tnul11qcupPortInfoGroup,
            tnDwdmCmnOtu3Odu3ClientPortInfoGroup,
            tn11qpen4PortInfoScalarsGroup,
            tn11qpen4PortInfoGroup,
            tn43scx4ePortInfoScalarsGroup,
            tn43scx4ePortInfoGroup,
            tnWssAttenPortInfoScalarsGroup,
            tnWssAttenPortInfoGroup,
            tn43scge1PortInfoScalarsGroup,
            tn43scge1PortInfoGroup,
            tn11qpe24PortInfoScalarsGroup,
            tn11qpe24PortInfoGroup,
            tn11star1aPortInfoScalarsGroup,
            tn11star1aPortInfoGroup,
            tnMvac8bPortInfoScalarsGroup,
            tnMvac8bPortInfoGroup,
            tnWr8c88afPortInfoScalarsGroup,
            tnWr8c88afPortInfoGroup,
            tncl10an10gPortInfoScalarsGroup,
            tncl10an10gPortInfoGroup,
            tncl24anmPortInfoScalarsGroup,
            tncl24anmPortInfoGroup,
            tnOpsbPortInfoScalarsGroup,
            tnOpsbPortInfoGroup,
            tnOpsPortInfoScalarsGroup,
            tnOpsPortInfoGroup,
            tn11dpe12aPortInfoScalarsGroup,
            tn11dpe12aPortInfoGroup,
            tnul130scupPortInfoScalarsGroup,
            tnul130scupPortInfoGroup,
            tn130scx10PortInfoScalarsGroup,
            tn130scx10PortInfoGroup,
            tnA2p2125PortInfoScalarsGroup,
            tnA2p2125PortInfoGroup,
            tn4qpa8PortInfoScalarsGroup,
            tn4qpa8PortInfoGroup,
            tnOt112pdm11PortInfoScalarsGroup,
            tnOt112pdm11PortInfoGroup,
            tnWtocmaPortInfoScalarsGroup,
            tnWtocmaPortInfoGroup,
            tnPtpctlPortInfoScalarsGroup,
            tnPtpctlPortInfoGroup,
            tnPtpioPortInfoScalarsGroup,
            tnPtpioPortInfoGroup,
            tnIo24et1gbPortInfoScalarsGroup,
            tnIo24et1gbPortInfoGroup,
            tnIo4an10gPortInfoScalarsGroup,
            tnIo4an10gPortInfoGroup,
            tnIo8et1gbPortInfoScalarsGroup,
            tnIo8et1gbPortInfoGroup,
            tnIo10et10gPortInfoScalarsGroup,
            tnIo10et10gPortInfoGroup,
            tnUl11qcupcPortInfoScalarsGroup,
            tnUl11qcupcPortInfoGroup,
            tnOt520scx4PortInfoScalarsGroup,
            tnOt520scx4PortInfoGroup,
            tnSkewInfoGroup,
            tnPowerFilterPortInfoScalarsGroup,
            tnPowerFilterPortInfoGroup,
            tn11ope8PortInfoScalarsGroup,
            tn11ope8PortInfoGroup,
            tn11qce12xPortInfoScalarsGroup,
            tn11qce12xPortInfoGroup,
            tnAm2625aPortInfoScalarsGroup,
            tnAm2625aPortInfoGroup,
            tnAm2032aPortInfoScalarsGroup,
            tnAm2032aPortInfoGroup,
            tnOt260scx2PortInfoScalarsGroup,
            tnOt260scx2PortInfoGroup,
            tnOt130snx10PortInfoScalarsGroup,
            tnOt130snx10PortInfoGroup,
            tnIo24anmbPortInfoScalarsGroup,
            tnIo24anmbPortInfoGroup,
            tnOt11dpm8PortInfoScalarsGroup,
            tnOt11dpm8PortInfoGroup,
            tnOt11dpm4mPortInfoScalarsGroup,
            tnOt11dpm4mPortInfoGroup,
            tnUl130scupbPortInfoScalarsGroup,
            tnUl130scupbPortInfoGroup,
            tnOt112sdx11PortInfoScalarsGroup,
            tnOt112sdx11PortInfoGroup,
            tnAa2donwPortInfoScalarsGroup,
            tnAa2donwPortInfoGroup,
            tnOt130sca1PortInfoScalarsGroup,
            tnOt130sca1PortInfoGroup,
            tnIo10an10gbPortInfoScalarsGroup,
            tnIo10an10gbPortInfoGroup,
            tnIo10et10gbPortInfoScalarsGroup,
            tnIo10et10gbPortInfoGroup,
            tnWr20tfPortInfoScalarsGroup,
            tnWr20tfPortInfoGroup,
            tnWssPortInfoScalarsGroup,
            tnWssPortInfoGroup,
            tnWtocmfPortInfoScalarsGroup,
            tnWtocmfPortInfoGroup,
            tnAswgPortInfoScalarsGroup,
            tnAswgPortInfoGroup,
            tnA4pswgPortInfoScalarsGroup,
            tnA4pswgPortInfoGroup,
            tnOtdrPortInfoScalarsGroup,
            tnOtdrPortInfoGroup,
            tnWr20tfmPortInfoScalarsGroup,
            tnWr20tfmPortInfoGroup,
            tnAar8aPortInfoScalarsGroup,
            tnAar8aPortInfoGroup,
            tnMcs8x16PortInfoScalarsGroup,
            tnMcs8x16PortInfoGroup,
            tnMsh8fsmPortInfoScalarsGroup,
            tnMsh8fsmPortInfoGroup,
            tnMcsPortInfoScalarsGroup,
            tnMcsPortInfoGroup,
            tnMcsPortChannelInfoScalarsGroup,
            tnMcsPortChannelInfoGroup,
            tnAarPortInfoScalarsGroup,
            tnAarPortInfoGroup,
            tnWr20tfmPortChannelInfoScalarsGroup,
            tnWr20tfmPortChannelInfoGroup,
            tnMpoPortInfoScalarsGroup,
            tnMpoPortInfoGroup,
            tnMpoPortMultiPositionInfoScalarsGroup,
            tnMpoPortMultiPositionInfoGroup,
            tnIo4an100gPortInfoScalarsGroup,
            tnIo4an100gPortInfoGroup,
            tnIo30an10gPortInfoScalarsGroup,
            tnIo30an10gPortInfoGroup,
            tnIo30an300PortInfoScalarsGroup,
            tnIo30an300PortInfoGroup,
            tnIo4an400PortInfoScalarsGroup,
            tnIo4an400PortInfoGroup,
            tn12p120PortInfoScalarsGroup,
            tn12p120PortInfoGroup,
            tn20p200PortInfoScalarsGroup,
            tn20p200PortInfoGroup,
            tn1ud200PortInfoScalarsGroup,
            tn1ud200PortInfoGroup,
            tnOt130snq10PortInfoScalarsGroup,
            tnOt130snq10PortInfoGroup,
            tnIroadmvPortInfoScalarsGroup,
            tnIroadmvPortInfoGroup,
            tnIroadmfPortInfoScalarsGroup,
            tnIroadmfPortInfoGroup,
            tnIroadmPortInfoScalarsGroup,
            tnIroadmPortInfoGroup,
            tnIroadmPortChannelInfoScalarsGroup,
            tnIroadmPortChannelInfoGroup,
            tnWssRefLdInfoScalarsGroup,
            tnWssRefLdInfoGroup,
            tnMonOcmPortInfoScalarsGroup,
            tnMonOcmPortInfoGroup,
            tnUl2uc400PortInfoScalarsGroup,
            tnUl2uc400PortInfoGroup,
            tnUl4uc400PortInfoScalarsGroup,
            tnUl4uc400PortInfoGroup,
            tnUl20uc200PortInfoScalarsGroup,
            tnUl20uc200PortInfoGroup,
            tnD5x500PortInfoScalarsGroup,
            tnD5x500PortInfoGroup,
            tnOtS11M100PortInfoScalarsGroup,
            tnOtS11M100PortInfoGroup,
            tnMonOtdrPortInfoScalarsGroup,
            tnMonOtdrPortInfoGroup,
            tnPSS96PowerFilterPortInfoScalarsGroup,
            tnPSS96PowerFilterPortInfoGroup,
            tn12ce120InfoScalarsGroup,
            tn12ce120PortInfoGroup,
            tn1ce100InfoScalarsGroup,
            tn1ce100PortInfoGroup,
            tnLcI1000PortInfoScalarsGroup,
            tnLcI1000PortInfoGroup 
        }
        ::= { tnOpticalPortInfoCompliances 1 }

--------------------------------------------------------------------------------
-- Compliance Port Line Card Config Statements (mandatory)
--------------------------------------------------------------------------------
--    obsolete
--    tnOpticalPortLcConfigCompliance MODULE-COMPLIANCE ::= { tnOpticalPortLcConfigCompliances 1 }

END -- DEFINITION OF TROPIC-OPTICALPORT-MIB
