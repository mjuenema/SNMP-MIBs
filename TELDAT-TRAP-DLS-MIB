-- file automatically created


TELDAT-TRAP-DLS-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


dlsTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the DLS event subsystem."
    REVISION "201401200930Z"
    DESCRIPTION "Initial implementation"
        ::= { telEventTraps 116 }


dlsEventsGroup	OBJECT IDENTIFIER	::= { dlsTrapsMIB 1 }

dlsNotifications	OBJECT IDENTIFIER	::= { dlsTrapsMIB 2 }
dlsNotificationsPrefix	OBJECT IDENTIFIER	::= { dlsNotifications 0 }

dlsEventObjects1 OBJECT-IDENTITY
    STATUS current
    DESCRIPTION
        "Event DLS.1
        As a result of DLS requesting an OPEN to a particular destination
        specified by the ip address, TCPIM tries to find the corresponding
        tcp configuration entry in the RAM list. If not found, it prints
        this message."
    ::= { dlsEventsGroup 1 }

dls1_ip_address OBJECT-TYPE
    SYNTAX IpAddress
    MAX-ACCESS accessible-for-notify
    STATUS current
    DESCRIPTION
        "Parameter 'ip_address' in event DLS.1"
    ::= { dlsEventObjects1 1 }

dlsEventObjects2 OBJECT-IDENTITY
    STATUS current
    DESCRIPTION
        "Event DLS.2
        As a result of DLS requesting an OPEN to a particular destination
        specified by the ip address, TCPIM opens a connection to the
        destination."
    ::= { dlsEventsGroup 2 }

dls2_ip_address OBJECT-TYPE
    SYNTAX IpAddress
    MAX-ACCESS accessible-for-notify
    STATUS current
    DESCRIPTION
        "Parameter 'ip_address' in event DLS.2"
    ::= { dlsEventObjects2 1 }

dlsEventObjects3 OBJECT-IDENTITY
    STATUS current
    DESCRIPTION
        "Event DLS.3
        Our read tcp connection has been opened via an illegal neighbor
        (i.e., someone we do not know about). As a result, we reject
        the connection, and thereby close it."
    ::= { dlsEventsGroup 3 }

dls3_ip_address OBJECT-TYPE
    SYNTAX IpAddress
    MAX-ACCESS accessible-for-notify
    STATUS current
    DESCRIPTION
        "Parameter 'ip_address' in event DLS.3"
    ::= { dlsEventObjects3 1 }

dlsEventObjects4 OBJECT-IDENTITY
    STATUS current
    DESCRIPTION
        "Event DLS.4
        DLS has requested we open a connection to the destination ip address.
        However, a connection already exists (or is in the pending state)."
    ::= { dlsEventsGroup 4 }

dls4_ip_address OBJECT-TYPE
    SYNTAX IpAddress
    MAX-ACCESS accessible-for-notify
    STATUS current
    DESCRIPTION
        "Parameter 'ip_address' in event DLS.4"
    ::= { dlsEventObjects4 1 }

dlsEventObjects5 OBJECT-IDENTITY
    STATUS current
    DESCRIPTION
        "Event DLS.5
        As a result of DLS requesting an OPEN to a particular destination
        specified by the ip address, TCPIM opens a connection to the
        destination."
    ::= { dlsEventsGroup 5 }

dls5_ip_address OBJECT-TYPE
    SYNTAX IpAddress
    MAX-ACCESS accessible-for-notify
    STATUS current
    DESCRIPTION
        "Parameter 'ip_address' in event DLS.5"
    ::= { dlsEventObjects5 1 }

dlsEventObjects6 OBJECT-IDENTITY
    STATUS current
    DESCRIPTION
        "Event DLS.6
        DLS is requesting a transport connection to be closed - however, it
        cannot be closed because there is no established connection to
        that neighbor."
    ::= { dlsEventsGroup 6 }

dls6_ip_address OBJECT-TYPE
    SYNTAX IpAddress
    MAX-ACCESS accessible-for-notify
    STATUS current
    DESCRIPTION
        "Parameter 'ip_address' in event DLS.6"
    ::= { dlsEventObjects6 1 }

dlsEventObjects7 OBJECT-IDENTITY
    STATUS current
    DESCRIPTION
        "Event DLS.7
        The other side has opened our read port, and as a result, we
        open our write port to the other side."
    ::= { dlsEventsGroup 7 }

dls7_ip_address OBJECT-TYPE
    SYNTAX IpAddress
    MAX-ACCESS accessible-for-notify
    STATUS current
    DESCRIPTION
        "Parameter 'ip_address' in event DLS.7"
    ::= { dlsEventObjects7 1 }

dlsEventObjects10 OBJECT-IDENTITY
    STATUS current
    DESCRIPTION
        "Event DLS.10
        As a result of DLS configured for local conversion, we must establish
        two transport connections to ourselves."
    ::= { dlsEventsGroup 10 }

dls10_ip_address OBJECT-TYPE
    SYNTAX IpAddress
    MAX-ACCESS accessible-for-notify
    STATUS current
    DESCRIPTION
        "Parameter 'ip_address' in event DLS.10"
    ::= { dlsEventObjects10 1 }

dlsEventObjects11 OBJECT-IDENTITY
    STATUS current
    DESCRIPTION
        "Event DLS.11
        As a result of DLS requesting an OPEN to ourself (due to local
        conversion), specified by the ip address, TCPIM tries to find the
        corresponding tcp configuration entry in the RAM list. If not found,
        it prints this message."
    ::= { dlsEventsGroup 11 }

dls11_ip_address OBJECT-TYPE
    SYNTAX IpAddress
    MAX-ACCESS accessible-for-notify
    STATUS current
    DESCRIPTION
        "Parameter 'ip_address' in event DLS.11"
    ::= { dlsEventObjects11 1 }

dlsEventObjects12 OBJECT-IDENTITY
    STATUS current
    DESCRIPTION
        "Event DLS.12
        As a result of DLS configured for local conversion, we must establish
        two transport connections to ourselves."
    ::= { dlsEventsGroup 12 }

dls12_ip_address OBJECT-TYPE
    SYNTAX IpAddress
    MAX-ACCESS accessible-for-notify
    STATUS current
    DESCRIPTION
        "Parameter 'ip_address' in event DLS.12"
    ::= { dlsEventObjects12 1 }

dlsEventObjects16 OBJECT-IDENTITY
    STATUS current
    DESCRIPTION
        "Event DLS.16
        A DLSw group packet was sent."
    ::= { dlsEventsGroup 16 }

dls16_type OBJECT-TYPE
    SYNTAX Integer32
    MAX-ACCESS accessible-for-notify
    STATUS current
    DESCRIPTION
        "Parameter 'type' in event DLS.16"
    ::= { dlsEventObjects16 1 }

dls16_group OBJECT-TYPE
    SYNTAX Integer32
    MAX-ACCESS accessible-for-notify
    STATUS current
    DESCRIPTION
        "Parameter 'group' in event DLS.16"
    ::= { dlsEventObjects16 2 }

dls16_role OBJECT-TYPE
    SYNTAX Integer32
    MAX-ACCESS accessible-for-notify
    STATUS current
    DESCRIPTION
        "Parameter 'role' in event DLS.16"
    ::= { dlsEventObjects16 3 }

dls16_destination OBJECT-TYPE
    SYNTAX IpAddress
    MAX-ACCESS accessible-for-notify
    STATUS current
    DESCRIPTION
        "Parameter 'destination' in event DLS.16"
    ::= { dlsEventObjects16 4 }

dlsEventObjects18 OBJECT-IDENTITY
    STATUS current
    DESCRIPTION
        "Event DLS.18
        A DLSw group packet was received."
    ::= { dlsEventsGroup 18 }

dls18_type OBJECT-TYPE
    SYNTAX Integer32
    MAX-ACCESS accessible-for-notify
    STATUS current
    DESCRIPTION
        "Parameter 'type' in event DLS.18"
    ::= { dlsEventObjects18 1 }

dls18_group OBJECT-TYPE
    SYNTAX Integer32
    MAX-ACCESS accessible-for-notify
    STATUS current
    DESCRIPTION
        "Parameter 'group' in event DLS.18"
    ::= { dlsEventObjects18 2 }

dls18_role OBJECT-TYPE
    SYNTAX Integer32
    MAX-ACCESS accessible-for-notify
    STATUS current
    DESCRIPTION
        "Parameter 'role' in event DLS.18"
    ::= { dlsEventObjects18 3 }

dls18_source OBJECT-TYPE
    SYNTAX IpAddress
    MAX-ACCESS accessible-for-notify
    STATUS current
    DESCRIPTION
        "Parameter 'source' in event DLS.18"
    ::= { dlsEventObjects18 4 }

dlsEventObjects19 OBJECT-IDENTITY
    STATUS current
    DESCRIPTION
        "Event DLS.19
        A DLSw group packet was received with either a bad version #, type,
        priority, or domain id."
    ::= { dlsEventsGroup 19 }

dls19_version OBJECT-TYPE
    SYNTAX Integer32
    MAX-ACCESS accessible-for-notify
    STATUS current
    DESCRIPTION
        "Parameter 'version' in event DLS.19"
    ::= { dlsEventObjects19 1 }

dls19_type OBJECT-TYPE
    SYNTAX Integer32
    MAX-ACCESS accessible-for-notify
    STATUS current
    DESCRIPTION
        "Parameter 'type' in event DLS.19"
    ::= { dlsEventObjects19 2 }

dls19_priority OBJECT-TYPE
    SYNTAX Integer32
    MAX-ACCESS accessible-for-notify
    STATUS current
    DESCRIPTION
        "Parameter 'priority' in event DLS.19"
    ::= { dlsEventObjects19 3 }

dls19_domain OBJECT-TYPE
    SYNTAX Integer32
    MAX-ACCESS accessible-for-notify
    STATUS current
    DESCRIPTION
        "Parameter 'domain' in event DLS.19"
    ::= { dlsEventObjects19 4 }

dlsEventObjects20 OBJECT-IDENTITY
    STATUS current
    DESCRIPTION
        "Event DLS.20
        A group packet was received for a group that was dynamically deleted."
    ::= { dlsEventsGroup 20 }

dls20_group OBJECT-TYPE
    SYNTAX Integer32
    MAX-ACCESS accessible-for-notify
    STATUS current
    DESCRIPTION
        "Parameter 'group' in event DLS.20"
    ::= { dlsEventObjects20 1 }

dlsEventObjects21 OBJECT-IDENTITY
    STATUS current
    DESCRIPTION
        "Event DLS.21
        A group packet was received but the roles were mismatched. The only
        valid role matches are Client/Server and Peer/Peer."
    ::= { dlsEventsGroup 21 }

dls21_group OBJECT-TYPE
    SYNTAX Integer32
    MAX-ACCESS accessible-for-notify
    STATUS current
    DESCRIPTION
        "Parameter 'group' in event DLS.21"
    ::= { dlsEventObjects21 1 }

dls21_role OBJECT-TYPE
    SYNTAX Integer32
    MAX-ACCESS accessible-for-notify
    STATUS current
    DESCRIPTION
        "Parameter 'role' in event DLS.21"
    ::= { dlsEventObjects21 2 }

dlsEventObjects22 OBJECT-IDENTITY
    STATUS current
    DESCRIPTION
        "Event DLS.22
        A group match has been found and we are initiating a connect."
    ::= { dlsEventsGroup 22 }

dls22_address OBJECT-TYPE
    SYNTAX IpAddress
    MAX-ACCESS accessible-for-notify
    STATUS current
    DESCRIPTION
        "Parameter 'address' in event DLS.22"
    ::= { dlsEventObjects22 1 }

dls22_group OBJECT-TYPE
    SYNTAX Integer32
    MAX-ACCESS accessible-for-notify
    STATUS current
    DESCRIPTION
        "Parameter 'group' in event DLS.22"
    ::= { dlsEventObjects22 2 }

dlsEventObjects23 OBJECT-IDENTITY
    STATUS current
    DESCRIPTION
        "Event DLS.23
        A group match has been found but we are not initiating a connection
        because a static IP connection to the partner has been deleted."
    ::= { dlsEventsGroup 23 }

dls23_address OBJECT-TYPE
    SYNTAX IpAddress
    MAX-ACCESS accessible-for-notify
    STATUS current
    DESCRIPTION
        "Parameter 'address' in event DLS.23"
    ::= { dlsEventObjects23 1 }

dls23_group OBJECT-TYPE
    SYNTAX Integer32
    MAX-ACCESS accessible-for-notify
    STATUS current
    DESCRIPTION
        "Parameter 'group' in event DLS.23"
    ::= { dlsEventObjects23 2 }

dlsEventObjects24 OBJECT-IDENTITY
    STATUS current
    DESCRIPTION
        "Event DLS.24
        A group match has been found but we are not initiating a connection
        because a static IP connection to the partner already exists."
    ::= { dlsEventsGroup 24 }

dls24_address OBJECT-TYPE
    SYNTAX IpAddress
    MAX-ACCESS accessible-for-notify
    STATUS current
    DESCRIPTION
        "Parameter 'address' in event DLS.24"
    ::= { dlsEventObjects24 1 }

dls24_group OBJECT-TYPE
    SYNTAX Integer32
    MAX-ACCESS accessible-for-notify
    STATUS current
    DESCRIPTION
        "Parameter 'group' in event DLS.24"
    ::= { dlsEventObjects24 2 }

dlsEventObjects27 OBJECT-IDENTITY
    STATUS current
    DESCRIPTION
        "Event DLS.27
        The maximum number of sdlc link stations has been exceeded since all
        available source SAPs have been allocated. The link station was not
        opened."
    ::= { dlsEventsGroup 27 }

dls27_station OBJECT-TYPE
    SYNTAX Integer32
    MAX-ACCESS accessible-for-notify
    STATUS current
    DESCRIPTION
        "Parameter 'station' in event DLS.27"
    ::= { dlsEventObjects27 1 }

dls27_interface OBJECT-TYPE
    SYNTAX Integer32
    MAX-ACCESS accessible-for-notify
    STATUS current
    DESCRIPTION
        "Parameter 'interface' in event DLS.27"
    ::= { dlsEventObjects27 2 }

dlsEventObjects28 OBJECT-IDENTITY
    STATUS current
    DESCRIPTION
        "Event DLS.28
        There was not enough memory available to initialize an SDLC link."
    ::= { dlsEventsGroup 28 }

dls28_interface OBJECT-TYPE
    SYNTAX DisplayString
    MAX-ACCESS accessible-for-notify
    STATUS current
    DESCRIPTION
        "Parameter 'interface' in event DLS.28"
    ::= { dlsEventObjects28 1 }

dlsEventObjects29 OBJECT-IDENTITY
    STATUS current
    DESCRIPTION
        "Event DLS.29
        The sdlc open station function returned an unexpected return code."
    ::= { dlsEventsGroup 29 }

dls29_rtn_code OBJECT-TYPE
    SYNTAX Integer32
    MAX-ACCESS accessible-for-notify
    STATUS current
    DESCRIPTION
        "Parameter 'rtn_code' in event DLS.29"
    ::= { dlsEventObjects29 1 }

dls29_interface OBJECT-TYPE
    SYNTAX DisplayString
    MAX-ACCESS accessible-for-notify
    STATUS current
    DESCRIPTION
        "Parameter 'interface' in event DLS.29"
    ::= { dlsEventObjects29 2 }

dlsEventObjects30 OBJECT-IDENTITY
    STATUS current
    DESCRIPTION
        "Event DLS.30
        The sdlc link control block was not found for the SDLC link being
        deleted."
    ::= { dlsEventsGroup 30 }

dls30_interface OBJECT-TYPE
    SYNTAX DisplayString
    MAX-ACCESS accessible-for-notify
    STATUS current
    DESCRIPTION
        "Parameter 'interface' in event DLS.30"
    ::= { dlsEventObjects30 1 }

dlsEventObjects31 OBJECT-IDENTITY
    STATUS current
    DESCRIPTION
        "Event DLS.31
        The sdlc station for the network interface has been successfully closed."
    ::= { dlsEventsGroup 31 }

dls31_interface OBJECT-TYPE
    SYNTAX DisplayString
    MAX-ACCESS accessible-for-notify
    STATUS current
    DESCRIPTION
        "Parameter 'interface' in event DLS.31"
    ::= { dlsEventObjects31 1 }

dlsEventObjects32 OBJECT-IDENTITY
    STATUS current
    DESCRIPTION
        "Event DLS.32
        The sdlc close station function returned an unexpected return code."
    ::= { dlsEventsGroup 32 }

dls32_rtn_code OBJECT-TYPE
    SYNTAX Integer32
    MAX-ACCESS accessible-for-notify
    STATUS current
    DESCRIPTION
        "Parameter 'rtn_code' in event DLS.32"
    ::= { dlsEventObjects32 1 }

dls32_interface OBJECT-TYPE
    SYNTAX DisplayString
    MAX-ACCESS accessible-for-notify
    STATUS current
    DESCRIPTION
        "Parameter 'interface' in event DLS.32"
    ::= { dlsEventObjects32 2 }

dlsEventObjects33 OBJECT-IDENTITY
    STATUS current
    DESCRIPTION
        "Event DLS.33
        The sdlc link control block was not found for the SDLC link station
        being initialized."
    ::= { dlsEventsGroup 33 }

dls33_interface OBJECT-TYPE
    SYNTAX DisplayString
    MAX-ACCESS accessible-for-notify
    STATUS current
    DESCRIPTION
        "Parameter 'interface' in event DLS.33"
    ::= { dlsEventObjects33 1 }

dlsEventObjects34 OBJECT-IDENTITY
    STATUS current
    DESCRIPTION
        "Event DLS.34
        There was not enough memory available to initialize an SDLC link station."
    ::= { dlsEventsGroup 34 }

dls34_interface OBJECT-TYPE
    SYNTAX DisplayString
    MAX-ACCESS accessible-for-notify
    STATUS current
    DESCRIPTION
        "Parameter 'interface' in event DLS.34"
    ::= { dlsEventObjects34 1 }

dlsEventObjects35 OBJECT-IDENTITY
    STATUS current
    DESCRIPTION
        "Event DLS.35
        The sdlc link station for the link address has been successfully opened
        on the network interface."
    ::= { dlsEventsGroup 35 }

dls35_link_address OBJECT-TYPE
    SYNTAX Integer32
    MAX-ACCESS accessible-for-notify
    STATUS current
    DESCRIPTION
        "Parameter 'link_address' in event DLS.35"
    ::= { dlsEventObjects35 1 }

dls35_interface OBJECT-TYPE
    SYNTAX DisplayString
    MAX-ACCESS accessible-for-notify
    STATUS current
    DESCRIPTION
        "Parameter 'interface' in event DLS.35"
    ::= { dlsEventObjects35 2 }

dlsEventObjects36 OBJECT-IDENTITY
    STATUS current
    DESCRIPTION
        "Event DLS.36
        The specified sdlc link station could not be opened because it is a
        duplicate of one already opened."
    ::= { dlsEventsGroup 36 }

dls36_link_address OBJECT-TYPE
    SYNTAX Integer32
    MAX-ACCESS accessible-for-notify
    STATUS current
    DESCRIPTION
        "Parameter 'link_address' in event DLS.36"
    ::= { dlsEventObjects36 1 }

dls36_interface OBJECT-TYPE
    SYNTAX DisplayString
    MAX-ACCESS accessible-for-notify
    STATUS current
    DESCRIPTION
        "Parameter 'interface' in event DLS.36"
    ::= { dlsEventObjects36 2 }

dlsEventObjects37 OBJECT-IDENTITY
    STATUS current
    DESCRIPTION
        "Event DLS.37
        The sdlc open link station function returned an unexpected return code."
    ::= { dlsEventsGroup 37 }

dls37_rtn_code OBJECT-TYPE
    SYNTAX Integer32
    MAX-ACCESS accessible-for-notify
    STATUS current
    DESCRIPTION
        "Parameter 'rtn_code' in event DLS.37"
    ::= { dlsEventObjects37 1 }

dls37_interface OBJECT-TYPE
    SYNTAX DisplayString
    MAX-ACCESS accessible-for-notify
    STATUS current
    DESCRIPTION
        "Parameter 'interface' in event DLS.37"
    ::= { dlsEventObjects37 2 }

dlsEventObjects38 OBJECT-IDENTITY
    STATUS current
    DESCRIPTION
        "Event DLS.38
        The sdlc link station for the address and network interface specified
        has been successfully closed."
    ::= { dlsEventsGroup 38 }

dls38_link_address OBJECT-TYPE
    SYNTAX Integer32
    MAX-ACCESS accessible-for-notify
    STATUS current
    DESCRIPTION
        "Parameter 'link_address' in event DLS.38"
    ::= { dlsEventObjects38 1 }

dls38_interface OBJECT-TYPE
    SYNTAX DisplayString
    MAX-ACCESS accessible-for-notify
    STATUS current
    DESCRIPTION
        "Parameter 'interface' in event DLS.38"
    ::= { dlsEventObjects38 2 }

dlsEventObjects39 OBJECT-IDENTITY
    STATUS current
    DESCRIPTION
        "Event DLS.39
        A net up indication has been received for an sdlc link station."
    ::= { dlsEventsGroup 39 }

dls39_link_address OBJECT-TYPE
    SYNTAX Integer32
    MAX-ACCESS accessible-for-notify
    STATUS current
    DESCRIPTION
        "Parameter 'link_address' in event DLS.39"
    ::= { dlsEventObjects39 1 }

dls39_interface OBJECT-TYPE
    SYNTAX DisplayString
    MAX-ACCESS accessible-for-notify
    STATUS current
    DESCRIPTION
        "Parameter 'interface' in event DLS.39"
    ::= { dlsEventObjects39 2 }

dlsEventObjects40 OBJECT-IDENTITY
    STATUS current
    DESCRIPTION
        "Event DLS.40
        A net down indication has been received for an sdlc link station."
    ::= { dlsEventsGroup 40 }

dls40_link_address OBJECT-TYPE
    SYNTAX Integer32
    MAX-ACCESS accessible-for-notify
    STATUS current
    DESCRIPTION
        "Parameter 'link_address' in event DLS.40"
    ::= { dlsEventObjects40 1 }

dls40_interface OBJECT-TYPE
    SYNTAX DisplayString
    MAX-ACCESS accessible-for-notify
    STATUS current
    DESCRIPTION
        "Parameter 'interface' in event DLS.40"
    ::= { dlsEventObjects40 2 }

dlsEventObjects41 OBJECT-IDENTITY
    STATUS current
    DESCRIPTION
        "Event DLS.41
        A net up indication has been received for an sdlc link station on
        an interface that is not down."
    ::= { dlsEventsGroup 41 }

dls41_link_address OBJECT-TYPE
    SYNTAX Integer32
    MAX-ACCESS accessible-for-notify
    STATUS current
    DESCRIPTION
        "Parameter 'link_address' in event DLS.41"
    ::= { dlsEventObjects41 1 }

dls41_interface OBJECT-TYPE
    SYNTAX DisplayString
    MAX-ACCESS accessible-for-notify
    STATUS current
    DESCRIPTION
        "Parameter 'interface' in event DLS.41"
    ::= { dlsEventObjects41 2 }

dlsEventObjects42 OBJECT-IDENTITY
    STATUS current
    DESCRIPTION
        "Event DLS.42
        The sdlc link station specified is transitioning to resolve
        pending state."
    ::= { dlsEventsGroup 42 }

dls42_link_address OBJECT-TYPE
    SYNTAX Integer32
    MAX-ACCESS accessible-for-notify
    STATUS current
    DESCRIPTION
        "Parameter 'link_address' in event DLS.42"
    ::= { dlsEventObjects42 1 }

dls42_interface OBJECT-TYPE
    SYNTAX DisplayString
    MAX-ACCESS accessible-for-notify
    STATUS current
    DESCRIPTION
        "Parameter 'interface' in event DLS.42"
    ::= { dlsEventObjects42 2 }

dlsEventObjects43 OBJECT-IDENTITY
    STATUS current
    DESCRIPTION
        "Event DLS.43
        An unexpected test response was received from the sdlc link station
        specified."
    ::= { dlsEventsGroup 43 }

dls43_link_address OBJECT-TYPE
    SYNTAX Integer32
    MAX-ACCESS accessible-for-notify
    STATUS current
    DESCRIPTION
        "Parameter 'link_address' in event DLS.43"
    ::= { dlsEventObjects43 1 }

dls43_interface OBJECT-TYPE
    SYNTAX DisplayString
    MAX-ACCESS accessible-for-notify
    STATUS current
    DESCRIPTION
        "Parameter 'interface' in event DLS.43"
    ::= { dlsEventObjects43 2 }

dlsEventObjects44 OBJECT-IDENTITY
    STATUS current
    DESCRIPTION
        "Event DLS.44
        An unexpected XID type was received for a PU type 2 device from
        the sdlc link station specified."
    ::= { dlsEventsGroup 44 }

dls44_link_address OBJECT-TYPE
    SYNTAX Integer32
    MAX-ACCESS accessible-for-notify
    STATUS current
    DESCRIPTION
        "Parameter 'link_address' in event DLS.44"
    ::= { dlsEventObjects44 1 }

dls44_interface OBJECT-TYPE
    SYNTAX DisplayString
    MAX-ACCESS accessible-for-notify
    STATUS current
    DESCRIPTION
        "Parameter 'interface' in event DLS.44"
    ::= { dlsEventObjects44 2 }

dlsEventObjects45 OBJECT-IDENTITY
    STATUS current
    DESCRIPTION
        "Event DLS.45
        An invalid length XID-0 was received from the sdlc link station
        specified."
    ::= { dlsEventsGroup 45 }

dls45_link_address OBJECT-TYPE
    SYNTAX Integer32
    MAX-ACCESS accessible-for-notify
    STATUS current
    DESCRIPTION
        "Parameter 'link_address' in event DLS.45"
    ::= { dlsEventObjects45 1 }

dls45_interface OBJECT-TYPE
    SYNTAX DisplayString
    MAX-ACCESS accessible-for-notify
    STATUS current
    DESCRIPTION
        "Parameter 'interface' in event DLS.45"
    ::= { dlsEventObjects45 2 }

dlsEventObjects46 OBJECT-IDENTITY
    STATUS current
    DESCRIPTION
        "Event DLS.46
        An indication that a secondary SDLC link station sent a SNRM was
        received from the sdlc link station specified."
    ::= { dlsEventsGroup 46 }

dls46_link_address OBJECT-TYPE
    SYNTAX Integer32
    MAX-ACCESS accessible-for-notify
    STATUS current
    DESCRIPTION
        "Parameter 'link_address' in event DLS.46"
    ::= { dlsEventObjects46 1 }

dls46_interface OBJECT-TYPE
    SYNTAX DisplayString
    MAX-ACCESS accessible-for-notify
    STATUS current
    DESCRIPTION
        "Parameter 'interface' in event DLS.46"
    ::= { dlsEventObjects46 2 }

dlsEventObjects47 OBJECT-IDENTITY
    STATUS current
    DESCRIPTION
        "Event DLS.47
        The sdlc link station specified is transitioning to contacted state."
    ::= { dlsEventsGroup 47 }

dls47_link_address OBJECT-TYPE
    SYNTAX Integer32
    MAX-ACCESS accessible-for-notify
    STATUS current
    DESCRIPTION
        "Parameter 'link_address' in event DLS.47"
    ::= { dlsEventObjects47 1 }

dls47_interface OBJECT-TYPE
    SYNTAX DisplayString
    MAX-ACCESS accessible-for-notify
    STATUS current
    DESCRIPTION
        "Parameter 'interface' in event DLS.47"
    ::= { dlsEventObjects47 2 }

dlsEventObjects48 OBJECT-IDENTITY
    STATUS current
    DESCRIPTION
        "Event DLS.48
        An unexpected connect confirm was received from the sdlc link station
        specified."
    ::= { dlsEventsGroup 48 }

dls48_link_address OBJECT-TYPE
    SYNTAX Integer32
    MAX-ACCESS accessible-for-notify
    STATUS current
    DESCRIPTION
        "Parameter 'link_address' in event DLS.48"
    ::= { dlsEventObjects48 1 }

dls48_interface OBJECT-TYPE
    SYNTAX DisplayString
    MAX-ACCESS accessible-for-notify
    STATUS current
    DESCRIPTION
        "Parameter 'interface' in event DLS.48"
    ::= { dlsEventObjects48 2 }

dlsEventObjects49 OBJECT-IDENTITY
    STATUS current
    DESCRIPTION
        "Event DLS.49
        A disconnect indication was received from the SDLC link station
        specified."
    ::= { dlsEventsGroup 49 }

dls49_link_address OBJECT-TYPE
    SYNTAX Integer32
    MAX-ACCESS accessible-for-notify
    STATUS current
    DESCRIPTION
        "Parameter 'link_address' in event DLS.49"
    ::= { dlsEventObjects49 1 }

dls49_interface OBJECT-TYPE
    SYNTAX DisplayString
    MAX-ACCESS accessible-for-notify
    STATUS current
    DESCRIPTION
        "Parameter 'interface' in event DLS.49"
    ::= { dlsEventObjects49 2 }

dlsEventObjects50 OBJECT-IDENTITY
    STATUS current
    DESCRIPTION
        "Event DLS.50
        The disconnect sequence for the SDLC link station specified is complete."
    ::= { dlsEventsGroup 50 }

dls50_link_address OBJECT-TYPE
    SYNTAX Integer32
    MAX-ACCESS accessible-for-notify
    STATUS current
    DESCRIPTION
        "Parameter 'link_address' in event DLS.50"
    ::= { dlsEventObjects50 1 }

dls50_interface OBJECT-TYPE
    SYNTAX DisplayString
    MAX-ACCESS accessible-for-notify
    STATUS current
    DESCRIPTION
        "Parameter 'interface' in event DLS.50"
    ::= { dlsEventObjects50 2 }

dlsEventObjects51 OBJECT-IDENTITY
    STATUS current
    DESCRIPTION
        "Event DLS.51
        An unexpected disconnect indication was received from
        the sdlc link station specified."
    ::= { dlsEventsGroup 51 }

dls51_state OBJECT-TYPE
    SYNTAX Integer32
    MAX-ACCESS accessible-for-notify
    STATUS current
    DESCRIPTION
        "Parameter 'state' in event DLS.51"
    ::= { dlsEventObjects51 1 }

dls51_link_address OBJECT-TYPE
    SYNTAX Integer32
    MAX-ACCESS accessible-for-notify
    STATUS current
    DESCRIPTION
        "Parameter 'link_address' in event DLS.51"
    ::= { dlsEventObjects51 2 }

dls51_interface OBJECT-TYPE
    SYNTAX DisplayString
    MAX-ACCESS accessible-for-notify
    STATUS current
    DESCRIPTION
        "Parameter 'interface' in event DLS.51"
    ::= { dlsEventObjects51 3 }

dlsEventObjects52 OBJECT-IDENTITY
    STATUS current
    DESCRIPTION
        "Event DLS.52
        A disconnect confirm was received for the SDLC link station specified."
    ::= { dlsEventsGroup 52 }

dls52_link_address OBJECT-TYPE
    SYNTAX Integer32
    MAX-ACCESS accessible-for-notify
    STATUS current
    DESCRIPTION
        "Parameter 'link_address' in event DLS.52"
    ::= { dlsEventObjects52 1 }

dls52_interface OBJECT-TYPE
    SYNTAX DisplayString
    MAX-ACCESS accessible-for-notify
    STATUS current
    DESCRIPTION
        "Parameter 'interface' in event DLS.52"
    ::= { dlsEventObjects52 2 }

dlsEventObjects53 OBJECT-IDENTITY
    STATUS current
    DESCRIPTION
        "Event DLS.53
        An unexpected disconnect confirm was received from the sdlc link station
        specified."
    ::= { dlsEventsGroup 53 }

dls53_state OBJECT-TYPE
    SYNTAX Integer32
    MAX-ACCESS accessible-for-notify
    STATUS current
    DESCRIPTION
        "Parameter 'state' in event DLS.53"
    ::= { dlsEventObjects53 1 }

dls53_link_address OBJECT-TYPE
    SYNTAX Integer32
    MAX-ACCESS accessible-for-notify
    STATUS current
    DESCRIPTION
        "Parameter 'link_address' in event DLS.53"
    ::= { dlsEventObjects53 2 }

dls53_interface OBJECT-TYPE
    SYNTAX DisplayString
    MAX-ACCESS accessible-for-notify
    STATUS current
    DESCRIPTION
        "Parameter 'interface' in event DLS.53"
    ::= { dlsEventObjects53 3 }

dlsEventObjects54 OBJECT-IDENTITY
    STATUS current
    DESCRIPTION
        "Event DLS.54
        An unexpected resolve_r event was received for the sdlc link station
        specified."
    ::= { dlsEventsGroup 54 }

dls54_state OBJECT-TYPE
    SYNTAX Integer32
    MAX-ACCESS accessible-for-notify
    STATUS current
    DESCRIPTION
        "Parameter 'state' in event DLS.54"
    ::= { dlsEventObjects54 1 }

dls54_link_address OBJECT-TYPE
    SYNTAX Integer32
    MAX-ACCESS accessible-for-notify
    STATUS current
    DESCRIPTION
        "Parameter 'link_address' in event DLS.54"
    ::= { dlsEventObjects54 2 }

dls54_interface OBJECT-TYPE
    SYNTAX DisplayString
    MAX-ACCESS accessible-for-notify
    STATUS current
    DESCRIPTION
        "Parameter 'interface' in event DLS.54"
    ::= { dlsEventObjects54 3 }

dlsEventObjects55 OBJECT-IDENTITY
    STATUS current
    DESCRIPTION
        "Event DLS.55
        The sdlc link station specified is transitioning to connected state."
    ::= { dlsEventsGroup 55 }

dls55_link_address OBJECT-TYPE
    SYNTAX Integer32
    MAX-ACCESS accessible-for-notify
    STATUS current
    DESCRIPTION
        "Parameter 'link_address' in event DLS.55"
    ::= { dlsEventObjects55 1 }

dls55_interface OBJECT-TYPE
    SYNTAX DisplayString
    MAX-ACCESS accessible-for-notify
    STATUS current
    DESCRIPTION
        "Parameter 'interface' in event DLS.55"
    ::= { dlsEventObjects55 2 }

dlsEventObjects56 OBJECT-IDENTITY
    STATUS current
    DESCRIPTION
        "Event DLS.56
        The sdlc connect request function returned an unexpected return code."
    ::= { dlsEventsGroup 56 }

dls56_rtn_code OBJECT-TYPE
    SYNTAX Integer32
    MAX-ACCESS accessible-for-notify
    STATUS current
    DESCRIPTION
        "Parameter 'rtn_code' in event DLS.56"
    ::= { dlsEventObjects56 1 }

dls56_link_address OBJECT-TYPE
    SYNTAX Integer32
    MAX-ACCESS accessible-for-notify
    STATUS current
    DESCRIPTION
        "Parameter 'link_address' in event DLS.56"
    ::= { dlsEventObjects56 2 }

dls56_interface OBJECT-TYPE
    SYNTAX DisplayString
    MAX-ACCESS accessible-for-notify
    STATUS current
    DESCRIPTION
        "Parameter 'interface' in event DLS.56"
    ::= { dlsEventObjects56 3 }

dlsEventObjects57 OBJECT-IDENTITY
    STATUS current
    DESCRIPTION
        "Event DLS.57
        An unexpected xid event was received for the sdlc link station
        specified."
    ::= { dlsEventsGroup 57 }

dls57_state OBJECT-TYPE
    SYNTAX Integer32
    MAX-ACCESS accessible-for-notify
    STATUS current
    DESCRIPTION
        "Parameter 'state' in event DLS.57"
    ::= { dlsEventObjects57 1 }

dls57_link_address OBJECT-TYPE
    SYNTAX Integer32
    MAX-ACCESS accessible-for-notify
    STATUS current
    DESCRIPTION
        "Parameter 'link_address' in event DLS.57"
    ::= { dlsEventObjects57 2 }

dls57_interface OBJECT-TYPE
    SYNTAX DisplayString
    MAX-ACCESS accessible-for-notify
    STATUS current
    DESCRIPTION
        "Parameter 'interface' in event DLS.57"
    ::= { dlsEventObjects57 3 }

dlsEventObjects58 OBJECT-IDENTITY
    STATUS current
    DESCRIPTION
        "Event DLS.58
        An unexpected XID-3 was received from DLS for a PU type 2 device for
        the sdlc link station specified."
    ::= { dlsEventsGroup 58 }

dls58_link_address OBJECT-TYPE
    SYNTAX Integer32
    MAX-ACCESS accessible-for-notify
    STATUS current
    DESCRIPTION
        "Parameter 'link_address' in event DLS.58"
    ::= { dlsEventObjects58 1 }

dls58_interface OBJECT-TYPE
    SYNTAX DisplayString
    MAX-ACCESS accessible-for-notify
    STATUS current
    DESCRIPTION
        "Parameter 'interface' in event DLS.58"
    ::= { dlsEventObjects58 2 }

dlsEventObjects59 OBJECT-IDENTITY
    STATUS current
    DESCRIPTION
        "Event DLS.59
        An unexpected DLC_CONTACT event was received from DLS for
        the sdlc link station specified."
    ::= { dlsEventsGroup 59 }

dls59_state OBJECT-TYPE
    SYNTAX Integer32
    MAX-ACCESS accessible-for-notify
    STATUS current
    DESCRIPTION
        "Parameter 'state' in event DLS.59"
    ::= { dlsEventObjects59 1 }

dls59_link_address OBJECT-TYPE
    SYNTAX Integer32
    MAX-ACCESS accessible-for-notify
    STATUS current
    DESCRIPTION
        "Parameter 'link_address' in event DLS.59"
    ::= { dlsEventObjects59 2 }

dls59_interface OBJECT-TYPE
    SYNTAX DisplayString
    MAX-ACCESS accessible-for-notify
    STATUS current
    DESCRIPTION
        "Parameter 'interface' in event DLS.59"
    ::= { dlsEventObjects59 3 }

dlsEventObjects60 OBJECT-IDENTITY
    STATUS current
    DESCRIPTION
        "Event DLS.60
        An unexpected DLC_INFO event was received from DLS for
        the sdlc link station specified."
    ::= { dlsEventsGroup 60 }

dls60_state OBJECT-TYPE
    SYNTAX Integer32
    MAX-ACCESS accessible-for-notify
    STATUS current
    DESCRIPTION
        "Parameter 'state' in event DLS.60"
    ::= { dlsEventObjects60 1 }

dls60_link_address OBJECT-TYPE
    SYNTAX Integer32
    MAX-ACCESS accessible-for-notify
    STATUS current
    DESCRIPTION
        "Parameter 'link_address' in event DLS.60"
    ::= { dlsEventObjects60 2 }

dls60_interface OBJECT-TYPE
    SYNTAX DisplayString
    MAX-ACCESS accessible-for-notify
    STATUS current
    DESCRIPTION
        "Parameter 'interface' in event DLS.60"
    ::= { dlsEventObjects60 3 }

dlsEventObjects61 OBJECT-IDENTITY
    STATUS current
    DESCRIPTION
        "Event DLS.61
        An unexpected DLC_DGRM event was received from DLS for
        the sdlc link station specified."
    ::= { dlsEventsGroup 61 }

dls61_state OBJECT-TYPE
    SYNTAX Integer32
    MAX-ACCESS accessible-for-notify
    STATUS current
    DESCRIPTION
        "Parameter 'state' in event DLS.61"
    ::= { dlsEventObjects61 1 }

dls61_link_address OBJECT-TYPE
    SYNTAX Integer32
    MAX-ACCESS accessible-for-notify
    STATUS current
    DESCRIPTION
        "Parameter 'link_address' in event DLS.61"
    ::= { dlsEventObjects61 2 }

dls61_interface OBJECT-TYPE
    SYNTAX DisplayString
    MAX-ACCESS accessible-for-notify
    STATUS current
    DESCRIPTION
        "Parameter 'interface' in event DLS.61"
    ::= { dlsEventObjects61 3 }

dlsEventObjects62 OBJECT-IDENTITY
    STATUS current
    DESCRIPTION
        "Event DLS.62
        An unexpected I-frame was received from SDLC for the sdlc link station
        specified."
    ::= { dlsEventsGroup 62 }

dls62_state OBJECT-TYPE
    SYNTAX Integer32
    MAX-ACCESS accessible-for-notify
    STATUS current
    DESCRIPTION
        "Parameter 'state' in event DLS.62"
    ::= { dlsEventObjects62 1 }

dls62_link_address OBJECT-TYPE
    SYNTAX Integer32
    MAX-ACCESS accessible-for-notify
    STATUS current
    DESCRIPTION
        "Parameter 'link_address' in event DLS.62"
    ::= { dlsEventObjects62 2 }

dls62_interface OBJECT-TYPE
    SYNTAX DisplayString
    MAX-ACCESS accessible-for-notify
    STATUS current
    DESCRIPTION
        "Parameter 'interface' in event DLS.62"
    ::= { dlsEventObjects62 3 }

dlsEventObjects63 OBJECT-IDENTITY
    STATUS current
    DESCRIPTION
        "Event DLS.63
        An unexpected UI-frame was received from SDLC for the sdlc link station
        specified."
    ::= { dlsEventsGroup 63 }

dls63_state OBJECT-TYPE
    SYNTAX Integer32
    MAX-ACCESS accessible-for-notify
    STATUS current
    DESCRIPTION
        "Parameter 'state' in event DLS.63"
    ::= { dlsEventObjects63 1 }

dls63_link_address OBJECT-TYPE
    SYNTAX Integer32
    MAX-ACCESS accessible-for-notify
    STATUS current
    DESCRIPTION
        "Parameter 'link_address' in event DLS.63"
    ::= { dlsEventObjects63 2 }

dls63_interface OBJECT-TYPE
    SYNTAX DisplayString
    MAX-ACCESS accessible-for-notify
    STATUS current
    DESCRIPTION
        "Parameter 'interface' in event DLS.63"
    ::= { dlsEventObjects63 3 }

dlsEventObjects64 OBJECT-IDENTITY
    STATUS current
    DESCRIPTION
        "Event DLS.64
        A HALT_DL event was sent from DLS for the specified sdlc link station."
    ::= { dlsEventsGroup 64 }

dls64_link_address OBJECT-TYPE
    SYNTAX Integer32
    MAX-ACCESS accessible-for-notify
    STATUS current
    DESCRIPTION
        "Parameter 'link_address' in event DLS.64"
    ::= { dlsEventObjects64 1 }

dls64_interface OBJECT-TYPE
    SYNTAX DisplayString
    MAX-ACCESS accessible-for-notify
    STATUS current
    DESCRIPTION
        "Parameter 'interface' in event DLS.64"
    ::= { dlsEventObjects64 2 }

dlsEventObjects65 OBJECT-IDENTITY
    STATUS current
    DESCRIPTION
        "Event DLS.65
        The sdlc link station specified is transitioning
        to disconnect pending state."
    ::= { dlsEventsGroup 65 }

dls65_link_address OBJECT-TYPE
    SYNTAX Integer32
    MAX-ACCESS accessible-for-notify
    STATUS current
    DESCRIPTION
        "Parameter 'link_address' in event DLS.65"
    ::= { dlsEventObjects65 1 }

dls65_interface OBJECT-TYPE
    SYNTAX DisplayString
    MAX-ACCESS accessible-for-notify
    STATUS current
    DESCRIPTION
        "Parameter 'interface' in event DLS.65"
    ::= { dlsEventObjects65 2 }

dlsEventObjects66 OBJECT-IDENTITY
    STATUS current
    DESCRIPTION
        "Event DLS.66
        The sdlc disconnect request function returned an unexpected return code."
    ::= { dlsEventsGroup 66 }

dls66_rtn_code OBJECT-TYPE
    SYNTAX Integer32
    MAX-ACCESS accessible-for-notify
    STATUS current
    DESCRIPTION
        "Parameter 'rtn_code' in event DLS.66"
    ::= { dlsEventObjects66 1 }

dls66_link_address OBJECT-TYPE
    SYNTAX Integer32
    MAX-ACCESS accessible-for-notify
    STATUS current
    DESCRIPTION
        "Parameter 'link_address' in event DLS.66"
    ::= { dlsEventObjects66 2 }

dls66_interface OBJECT-TYPE
    SYNTAX DisplayString
    MAX-ACCESS accessible-for-notify
    STATUS current
    DESCRIPTION
        "Parameter 'interface' in event DLS.66"
    ::= { dlsEventObjects66 3 }

dlsEventObjects67 OBJECT-IDENTITY
    STATUS current
    DESCRIPTION
        "Event DLS.67
        The sdlc link station specified is transitioning to disconnect state."
    ::= { dlsEventsGroup 67 }

dls67_link_address OBJECT-TYPE
    SYNTAX Integer32
    MAX-ACCESS accessible-for-notify
    STATUS current
    DESCRIPTION
        "Parameter 'link_address' in event DLS.67"
    ::= { dlsEventObjects67 1 }

dls67_interface OBJECT-TYPE
    SYNTAX DisplayString
    MAX-ACCESS accessible-for-notify
    STATUS current
    DESCRIPTION
        "Parameter 'interface' in event DLS.67"
    ::= { dlsEventObjects67 2 }

dlsEventObjects68 OBJECT-IDENTITY
    STATUS current
    DESCRIPTION
        "Event DLS.68
        An unexpected DLC_HALT_DL event was received from DLS for
        the sdlc link station specified."
    ::= { dlsEventsGroup 68 }

dls68_state OBJECT-TYPE
    SYNTAX Integer32
    MAX-ACCESS accessible-for-notify
    STATUS current
    DESCRIPTION
        "Parameter 'state' in event DLS.68"
    ::= { dlsEventObjects68 1 }

dls68_link_address OBJECT-TYPE
    SYNTAX Integer32
    MAX-ACCESS accessible-for-notify
    STATUS current
    DESCRIPTION
        "Parameter 'link_address' in event DLS.68"
    ::= { dlsEventObjects68 2 }

dls68_interface OBJECT-TYPE
    SYNTAX DisplayString
    MAX-ACCESS accessible-for-notify
    STATUS current
    DESCRIPTION
        "Parameter 'interface' in event DLS.68"
    ::= { dlsEventObjects68 3 }

dlsEventObjects69 OBJECT-IDENTITY
    STATUS current
    DESCRIPTION
        "Event DLS.69
        The cleanup timer expired for the specified sdlc link station."
    ::= { dlsEventsGroup 69 }

dls69_link_address OBJECT-TYPE
    SYNTAX Integer32
    MAX-ACCESS accessible-for-notify
    STATUS current
    DESCRIPTION
        "Parameter 'link_address' in event DLS.69"
    ::= { dlsEventObjects69 1 }

dls69_interface OBJECT-TYPE
    SYNTAX DisplayString
    MAX-ACCESS accessible-for-notify
    STATUS current
    DESCRIPTION
        "Parameter 'interface' in event DLS.69"
    ::= { dlsEventObjects69 2 }

dlsEventObjects70 OBJECT-IDENTITY
    STATUS current
    DESCRIPTION
        "Event DLS.70
        The sdlc cleanup timer expired, but the sdlc link station is in an
        unexpected state."
    ::= { dlsEventsGroup 70 }

dls70_state OBJECT-TYPE
    SYNTAX Integer32
    MAX-ACCESS accessible-for-notify
    STATUS current
    DESCRIPTION
        "Parameter 'state' in event DLS.70"
    ::= { dlsEventObjects70 1 }

dls70_link_address OBJECT-TYPE
    SYNTAX Integer32
    MAX-ACCESS accessible-for-notify
    STATUS current
    DESCRIPTION
        "Parameter 'link_address' in event DLS.70"
    ::= { dlsEventObjects70 2 }

dls70_interface OBJECT-TYPE
    SYNTAX DisplayString
    MAX-ACCESS accessible-for-notify
    STATUS current
    DESCRIPTION
        "Parameter 'interface' in event DLS.70"
    ::= { dlsEventObjects70 3 }

dlsEventObjects71 OBJECT-IDENTITY
    STATUS current
    DESCRIPTION
        "Event DLS.71
        The buffer retry timer expired for the specified sdlc link station."
    ::= { dlsEventsGroup 71 }

dls71_link_address OBJECT-TYPE
    SYNTAX Integer32
    MAX-ACCESS accessible-for-notify
    STATUS current
    DESCRIPTION
        "Parameter 'link_address' in event DLS.71"
    ::= { dlsEventObjects71 1 }

dls71_interface OBJECT-TYPE
    SYNTAX DisplayString
    MAX-ACCESS accessible-for-notify
    STATUS current
    DESCRIPTION
        "Parameter 'interface' in event DLS.71"
    ::= { dlsEventObjects71 2 }

dlsEventObjects72 OBJECT-IDENTITY
    STATUS current
    DESCRIPTION
        "Event DLS.72
        The sdlc buffer retry timer expired, but the sdlc link station is in an
        unexpected state."
    ::= { dlsEventsGroup 72 }

dls72_state OBJECT-TYPE
    SYNTAX Integer32
    MAX-ACCESS accessible-for-notify
    STATUS current
    DESCRIPTION
        "Parameter 'state' in event DLS.72"
    ::= { dlsEventObjects72 1 }

dls72_link_address OBJECT-TYPE
    SYNTAX Integer32
    MAX-ACCESS accessible-for-notify
    STATUS current
    DESCRIPTION
        "Parameter 'link_address' in event DLS.72"
    ::= { dlsEventObjects72 2 }

dls72_interface OBJECT-TYPE
    SYNTAX DisplayString
    MAX-ACCESS accessible-for-notify
    STATUS current
    DESCRIPTION
        "Parameter 'interface' in event DLS.72"
    ::= { dlsEventObjects72 3 }

dlsEventObjects73 OBJECT-IDENTITY
    STATUS current
    DESCRIPTION
        "Event DLS.73
        The sdlc interface finite state machine was passed an unknown event."
    ::= { dlsEventsGroup 73 }

dls73_event OBJECT-TYPE
    SYNTAX Integer32
    MAX-ACCESS accessible-for-notify
    STATUS current
    DESCRIPTION
        "Parameter 'event' in event DLS.73"
    ::= { dlsEventObjects73 1 }

dls73_link_address OBJECT-TYPE
    SYNTAX Integer32
    MAX-ACCESS accessible-for-notify
    STATUS current
    DESCRIPTION
        "Parameter 'link_address' in event DLS.73"
    ::= { dlsEventObjects73 2 }

dls73_interface OBJECT-TYPE
    SYNTAX DisplayString
    MAX-ACCESS accessible-for-notify
    STATUS current
    DESCRIPTION
        "Parameter 'interface' in event DLS.73"
    ::= { dlsEventObjects73 3 }

dlsEventObjects74 OBJECT-IDENTITY
    STATUS current
    DESCRIPTION
        "Event DLS.74
        The sdlc link station specified is transitioning to disconnect state
        due to a net up indication."
    ::= { dlsEventsGroup 74 }

dls74_link_address OBJECT-TYPE
    SYNTAX Integer32
    MAX-ACCESS accessible-for-notify
    STATUS current
    DESCRIPTION
        "Parameter 'link_address' in event DLS.74"
    ::= { dlsEventObjects74 1 }

dls74_interface OBJECT-TYPE
    SYNTAX DisplayString
    MAX-ACCESS accessible-for-notify
    STATUS current
    DESCRIPTION
        "Parameter 'interface' in event DLS.74"
    ::= { dlsEventObjects74 2 }

dlsEventObjects75 OBJECT-IDENTITY
    STATUS current
    DESCRIPTION
        "Event DLS.75
        An unexpected XID type was received for a PU type 2.1 device from
        the sdlc link station specified."
    ::= { dlsEventsGroup 75 }

dls75_link_address OBJECT-TYPE
    SYNTAX Integer32
    MAX-ACCESS accessible-for-notify
    STATUS current
    DESCRIPTION
        "Parameter 'link_address' in event DLS.75"
    ::= { dlsEventObjects75 1 }

dls75_interface OBJECT-TYPE
    SYNTAX DisplayString
    MAX-ACCESS accessible-for-notify
    STATUS current
    DESCRIPTION
        "Parameter 'interface' in event DLS.75"
    ::= { dlsEventObjects75 2 }

dlsEventObjects76 OBJECT-IDENTITY
    STATUS current
    DESCRIPTION
        "Event DLS.76
        An unexpected XID-0 was received for a PU type 2.1 device from
        the sdlc link station specified."
    ::= { dlsEventsGroup 76 }

dls76_link_address OBJECT-TYPE
    SYNTAX Integer32
    MAX-ACCESS accessible-for-notify
    STATUS current
    DESCRIPTION
        "Parameter 'link_address' in event DLS.76"
    ::= { dlsEventObjects76 1 }

dls76_interface OBJECT-TYPE
    SYNTAX DisplayString
    MAX-ACCESS accessible-for-notify
    STATUS current
    DESCRIPTION
        "Parameter 'interface' in event DLS.76"
    ::= { dlsEventObjects76 2 }

dlsEventObjects77 OBJECT-IDENTITY
    STATUS current
    DESCRIPTION
        "Event DLS.77
        No buffer could be obtained for sending a test frame to
        an SDLC link station. The operation will be retried later."
    ::= { dlsEventsGroup 77 }

dls77_link_address OBJECT-TYPE
    SYNTAX Integer32
    MAX-ACCESS accessible-for-notify
    STATUS current
    DESCRIPTION
        "Parameter 'link_address' in event DLS.77"
    ::= { dlsEventObjects77 1 }

dls77_interface OBJECT-TYPE
    SYNTAX DisplayString
    MAX-ACCESS accessible-for-notify
    STATUS current
    DESCRIPTION
        "Parameter 'interface' in event DLS.77"
    ::= { dlsEventObjects77 2 }

dlsEventObjects78 OBJECT-IDENTITY
    STATUS current
    DESCRIPTION
        "Event DLS.78
        The sdlc test request function returned an unexpected return code."
    ::= { dlsEventsGroup 78 }

dls78_rtn_code OBJECT-TYPE
    SYNTAX Integer32
    MAX-ACCESS accessible-for-notify
    STATUS current
    DESCRIPTION
        "Parameter 'rtn_code' in event DLS.78"
    ::= { dlsEventObjects78 1 }

dls78_link_address OBJECT-TYPE
    SYNTAX Integer32
    MAX-ACCESS accessible-for-notify
    STATUS current
    DESCRIPTION
        "Parameter 'link_address' in event DLS.78"
    ::= { dlsEventObjects78 2 }

dls78_interface OBJECT-TYPE
    SYNTAX DisplayString
    MAX-ACCESS accessible-for-notify
    STATUS current
    DESCRIPTION
        "Parameter 'interface' in event DLS.78"
    ::= { dlsEventObjects78 3 }

dlsEventObjects79 OBJECT-IDENTITY
    STATUS current
    DESCRIPTION
        "Event DLS.79
        No buffer could be obtained for sending an xid0 frame to
        an SDLC link station. The operation will be retried later."
    ::= { dlsEventsGroup 79 }

dls79_link_address OBJECT-TYPE
    SYNTAX Integer32
    MAX-ACCESS accessible-for-notify
    STATUS current
    DESCRIPTION
        "Parameter 'link_address' in event DLS.79"
    ::= { dlsEventObjects79 1 }

dls79_interface OBJECT-TYPE
    SYNTAX DisplayString
    MAX-ACCESS accessible-for-notify
    STATUS current
    DESCRIPTION
        "Parameter 'interface' in event DLS.79"
    ::= { dlsEventObjects79 2 }

dlsEventObjects80 OBJECT-IDENTITY
    STATUS current
    DESCRIPTION
        "Event DLS.80
        No buffer could be obtained for sending a null xid frame to
        an SDLC link station. The operation will be retried later."
    ::= { dlsEventsGroup 80 }

dls80_link_address OBJECT-TYPE
    SYNTAX Integer32
    MAX-ACCESS accessible-for-notify
    STATUS current
    DESCRIPTION
        "Parameter 'link_address' in event DLS.80"
    ::= { dlsEventObjects80 1 }

dls80_interface OBJECT-TYPE
    SYNTAX DisplayString
    MAX-ACCESS accessible-for-notify
    STATUS current
    DESCRIPTION
        "Parameter 'interface' in event DLS.80"
    ::= { dlsEventObjects80 2 }

dlsEventObjects81 OBJECT-IDENTITY
    STATUS current
    DESCRIPTION
        "Event DLS.81
        The sdlc I frame request function returned an unexpected return code."
    ::= { dlsEventsGroup 81 }

dls81_rtn_code OBJECT-TYPE
    SYNTAX Integer32
    MAX-ACCESS accessible-for-notify
    STATUS current
    DESCRIPTION
        "Parameter 'rtn_code' in event DLS.81"
    ::= { dlsEventObjects81 1 }

dls81_link_address OBJECT-TYPE
    SYNTAX Integer32
    MAX-ACCESS accessible-for-notify
    STATUS current
    DESCRIPTION
        "Parameter 'link_address' in event DLS.81"
    ::= { dlsEventObjects81 2 }

dls81_interface OBJECT-TYPE
    SYNTAX DisplayString
    MAX-ACCESS accessible-for-notify
    STATUS current
    DESCRIPTION
        "Parameter 'interface' in event DLS.81"
    ::= { dlsEventObjects81 3 }

dlsEventObjects82 OBJECT-IDENTITY
    STATUS current
    DESCRIPTION
        "Event DLS.82
        The sdlc UI frame request function returned an unexpected return code."
    ::= { dlsEventsGroup 82 }

dls82_rtn_code OBJECT-TYPE
    SYNTAX Integer32
    MAX-ACCESS accessible-for-notify
    STATUS current
    DESCRIPTION
        "Parameter 'rtn_code' in event DLS.82"
    ::= { dlsEventObjects82 1 }

dls82_link_address OBJECT-TYPE
    SYNTAX Integer32
    MAX-ACCESS accessible-for-notify
    STATUS current
    DESCRIPTION
        "Parameter 'link_address' in event DLS.82"
    ::= { dlsEventObjects82 2 }

dls82_interface OBJECT-TYPE
    SYNTAX DisplayString
    MAX-ACCESS accessible-for-notify
    STATUS current
    DESCRIPTION
        "Parameter 'interface' in event DLS.82"
    ::= { dlsEventObjects82 3 }

dlsEventObjects83 OBJECT-IDENTITY
    STATUS current
    DESCRIPTION
        "Event DLS.83
        The sdlc force rnr request function returned an unexpected return code."
    ::= { dlsEventsGroup 83 }

dls83_rtn_code OBJECT-TYPE
    SYNTAX Integer32
    MAX-ACCESS accessible-for-notify
    STATUS current
    DESCRIPTION
        "Parameter 'rtn_code' in event DLS.83"
    ::= { dlsEventObjects83 1 }

dls83_link_address OBJECT-TYPE
    SYNTAX Integer32
    MAX-ACCESS accessible-for-notify
    STATUS current
    DESCRIPTION
        "Parameter 'link_address' in event DLS.83"
    ::= { dlsEventObjects83 2 }

dls83_interface OBJECT-TYPE
    SYNTAX DisplayString
    MAX-ACCESS accessible-for-notify
    STATUS current
    DESCRIPTION
        "Parameter 'interface' in event DLS.83"
    ::= { dlsEventObjects83 3 }

dlsEventObjects84 OBJECT-IDENTITY
    STATUS current
    DESCRIPTION
        "Event DLS.84
        No buffer could be obtained for copying a data buffer for queueing
        while congested. The existing buffer is queued."
    ::= { dlsEventsGroup 84 }

dls84_link_address OBJECT-TYPE
    SYNTAX Integer32
    MAX-ACCESS accessible-for-notify
    STATUS current
    DESCRIPTION
        "Parameter 'link_address' in event DLS.84"
    ::= { dlsEventObjects84 1 }

dls84_interface OBJECT-TYPE
    SYNTAX DisplayString
    MAX-ACCESS accessible-for-notify
    STATUS current
    DESCRIPTION
        "Parameter 'interface' in event DLS.84"
    ::= { dlsEventObjects84 2 }

dlsEventObjects86 OBJECT-IDENTITY
    STATUS current
    DESCRIPTION
        "Event DLS.86
        The specified SDLC connection was disconnected due to an error detected
        by the SDLC protocol."
    ::= { dlsEventsGroup 86 }

dls86_reason OBJECT-TYPE
    SYNTAX DisplayString
    MAX-ACCESS accessible-for-notify
    STATUS current
    DESCRIPTION
        "Parameter 'reason' in event DLS.86"
    ::= { dlsEventObjects86 1 }

dls86_link_address OBJECT-TYPE
    SYNTAX Integer32
    MAX-ACCESS accessible-for-notify
    STATUS current
    DESCRIPTION
        "Parameter 'link_address' in event DLS.86"
    ::= { dlsEventObjects86 2 }

dls86_interface OBJECT-TYPE
    SYNTAX DisplayString
    MAX-ACCESS accessible-for-notify
    STATUS current
    DESCRIPTION
        "Parameter 'interface' in event DLS.86"
    ::= { dlsEventObjects86 3 }

dlsEventObjects87 OBJECT-IDENTITY
    STATUS current
    DESCRIPTION
        "Event DLS.87
        The sdlc link station specified is transitioning to NULL_XID_PENDING
        state, meaning that it is awaiting a response to a NULL XID
        that was sent."
    ::= { dlsEventsGroup 87 }

dls87_link_address OBJECT-TYPE
    SYNTAX Integer32
    MAX-ACCESS accessible-for-notify
    STATUS current
    DESCRIPTION
        "Parameter 'link_address' in event DLS.87"
    ::= { dlsEventObjects87 1 }

dls87_interface OBJECT-TYPE
    SYNTAX DisplayString
    MAX-ACCESS accessible-for-notify
    STATUS current
    DESCRIPTION
        "Parameter 'interface' in event DLS.87"
    ::= { dlsEventObjects87 2 }

dlsEventObjects88 OBJECT-IDENTITY
    STATUS current
    DESCRIPTION
        "Event DLS.88
        The sdlc link station specified is transitioning to XID_0_PENDING state,
        meaning that it is awaiting a response to an XID-0 that was sent."
    ::= { dlsEventsGroup 88 }

dls88_link_address OBJECT-TYPE
    SYNTAX Integer32
    MAX-ACCESS accessible-for-notify
    STATUS current
    DESCRIPTION
        "Parameter 'link_address' in event DLS.88"
    ::= { dlsEventObjects88 1 }

dls88_interface OBJECT-TYPE
    SYNTAX DisplayString
    MAX-ACCESS accessible-for-notify
    STATUS current
    DESCRIPTION
        "Parameter 'interface' in event DLS.88"
    ::= { dlsEventObjects88 2 }

dlsEventObjects89 OBJECT-IDENTITY
    STATUS current
    DESCRIPTION
        "Event DLS.89
        TCP connection to the DLS neighbor went down. All the DLS sessions
        active on that TCP connection are brought down individually."
    ::= { dlsEventsGroup 89 }

dls89_address OBJECT-TYPE
    SYNTAX IpAddress
    MAX-ACCESS accessible-for-notify
    STATUS current
    DESCRIPTION
        "Parameter 'address' in event DLS.89"
    ::= { dlsEventObjects89 1 }

dls89_source_mac_address OBJECT-TYPE
    SYNTAX DisplayString
    MAX-ACCESS accessible-for-notify
    STATUS current
    DESCRIPTION
        "Parameter 'source_mac_address' in event DLS.89"
    ::= { dlsEventObjects89 2 }

dls89_dest_mac_address OBJECT-TYPE
    SYNTAX DisplayString
    MAX-ACCESS accessible-for-notify
    STATUS current
    DESCRIPTION
        "Parameter 'dest_mac_address' in event DLS.89"
    ::= { dlsEventObjects89 3 }

dls89_source_sap OBJECT-TYPE
    SYNTAX Integer32
    MAX-ACCESS accessible-for-notify
    STATUS current
    DESCRIPTION
        "Parameter 'source_sap' in event DLS.89"
    ::= { dlsEventObjects89 4 }

dls89_dest_sap OBJECT-TYPE
    SYNTAX Integer32
    MAX-ACCESS accessible-for-notify
    STATUS current
    DESCRIPTION
        "Parameter 'dest_sap' in event DLS.89"
    ::= { dlsEventObjects89 5 }

dlsEventObjects90 OBJECT-IDENTITY
    STATUS current
    DESCRIPTION
        "Event DLS.90
        DLS forwarder received a Switch to Switch Protocol message of over TCP."
    ::= { dlsEventsGroup 90 }

dls90_type OBJECT-TYPE
    SYNTAX DisplayString
    MAX-ACCESS accessible-for-notify
    STATUS current
    DESCRIPTION
        "Parameter 'type' in event DLS.90"
    ::= { dlsEventObjects90 1 }

dls90_ip_address OBJECT-TYPE
    SYNTAX IpAddress
    MAX-ACCESS accessible-for-notify
    STATUS current
    DESCRIPTION
        "Parameter 'ip_address' in event DLS.90"
    ::= { dlsEventObjects90 2 }

dls90_source_mac_address OBJECT-TYPE
    SYNTAX DisplayString
    MAX-ACCESS accessible-for-notify
    STATUS current
    DESCRIPTION
        "Parameter 'source_mac_address' in event DLS.90"
    ::= { dlsEventObjects90 3 }

dls90_dest_mac_address OBJECT-TYPE
    SYNTAX DisplayString
    MAX-ACCESS accessible-for-notify
    STATUS current
    DESCRIPTION
        "Parameter 'dest_mac_address' in event DLS.90"
    ::= { dlsEventObjects90 4 }

dls90_source_sap OBJECT-TYPE
    SYNTAX Integer32
    MAX-ACCESS accessible-for-notify
    STATUS current
    DESCRIPTION
        "Parameter 'source_sap' in event DLS.90"
    ::= { dlsEventObjects90 5 }

dls90_dest_sap OBJECT-TYPE
    SYNTAX Integer32
    MAX-ACCESS accessible-for-notify
    STATUS current
    DESCRIPTION
        "Parameter 'dest_sap' in event DLS.90"
    ::= { dlsEventObjects90 6 }

dlsEventObjects91 OBJECT-IDENTITY
    STATUS current
    DESCRIPTION
        "Event DLS.91
        TCP connection to a DLS Peer was previously congested. It has now
        become uncongested so that DLS can resume sending data over that
        connection."
    ::= { dlsEventsGroup 91 }

dls91_ip_address OBJECT-TYPE
    SYNTAX IpAddress
    MAX-ACCESS accessible-for-notify
    STATUS current
    DESCRIPTION
        "Parameter 'ip_address' in event DLS.91"
    ::= { dlsEventObjects91 1 }

dlsEventObjects92 OBJECT-IDENTITY
    STATUS current
    DESCRIPTION
        "Event DLS.92
        DLS forwarder received a DLC event from the underlying LINK which
        could be LLC or SDLC to either perform some service or as an
        acknowledgement to previously issued command."
    ::= { dlsEventsGroup 92 }

dls92_type OBJECT-TYPE
    SYNTAX DisplayString
    MAX-ACCESS accessible-for-notify
    STATUS current
    DESCRIPTION
        "Parameter 'type' in event DLS.92"
    ::= { dlsEventObjects92 1 }

dls92_source_mac_address OBJECT-TYPE
    SYNTAX DisplayString
    MAX-ACCESS accessible-for-notify
    STATUS current
    DESCRIPTION
        "Parameter 'source_mac_address' in event DLS.92"
    ::= { dlsEventObjects92 2 }

dls92_dest_mac_address OBJECT-TYPE
    SYNTAX DisplayString
    MAX-ACCESS accessible-for-notify
    STATUS current
    DESCRIPTION
        "Parameter 'dest_mac_address' in event DLS.92"
    ::= { dlsEventObjects92 3 }

dls92_source_sap OBJECT-TYPE
    SYNTAX Integer32
    MAX-ACCESS accessible-for-notify
    STATUS current
    DESCRIPTION
        "Parameter 'source_sap' in event DLS.92"
    ::= { dlsEventObjects92 4 }

dls92_dest_sap OBJECT-TYPE
    SYNTAX Integer32
    MAX-ACCESS accessible-for-notify
    STATUS current
    DESCRIPTION
        "Parameter 'dest_sap' in event DLS.92"
    ::= { dlsEventObjects92 5 }

dlsEventObjects93 OBJECT-IDENTITY
    STATUS current
    DESCRIPTION
        "Event DLS.93
        While processing an event, either an SSP message received over
        TCP or an event presented from underlying DLC, the associated
        DLS session is stepping into a new state."
    ::= { dlsEventsGroup 93 }

dls93_state OBJECT-TYPE
    SYNTAX DisplayString
    MAX-ACCESS accessible-for-notify
    STATUS current
    DESCRIPTION
        "Parameter 'state' in event DLS.93"
    ::= { dlsEventObjects93 1 }

dls93_source_mac_address OBJECT-TYPE
    SYNTAX DisplayString
    MAX-ACCESS accessible-for-notify
    STATUS current
    DESCRIPTION
        "Parameter 'source_mac_address' in event DLS.93"
    ::= { dlsEventObjects93 2 }

dls93_dest_mac_address OBJECT-TYPE
    SYNTAX DisplayString
    MAX-ACCESS accessible-for-notify
    STATUS current
    DESCRIPTION
        "Parameter 'dest_mac_address' in event DLS.93"
    ::= { dlsEventObjects93 3 }

dls93_source_sap OBJECT-TYPE
    SYNTAX Integer32
    MAX-ACCESS accessible-for-notify
    STATUS current
    DESCRIPTION
        "Parameter 'source_sap' in event DLS.93"
    ::= { dlsEventObjects93 4 }

dls93_dest_sap OBJECT-TYPE
    SYNTAX Integer32
    MAX-ACCESS accessible-for-notify
    STATUS current
    DESCRIPTION
        "Parameter 'dest_sap' in event DLS.93"
    ::= { dlsEventObjects93 5 }

dlsEventObjects94 OBJECT-IDENTITY
    STATUS current
    DESCRIPTION
        "Event DLS.94
        While processing an event, either an SSP message received over
        TCP or an event presented from underlying DLC, the DLS state
        machine discovered the event occurring in an unexpected state."
    ::= { dlsEventsGroup 94 }

dls94_state OBJECT-TYPE
    SYNTAX DisplayString
    MAX-ACCESS accessible-for-notify
    STATUS current
    DESCRIPTION
        "Parameter 'state' in event DLS.94"
    ::= { dlsEventObjects94 1 }

dls94_source_mac_address OBJECT-TYPE
    SYNTAX DisplayString
    MAX-ACCESS accessible-for-notify
    STATUS current
    DESCRIPTION
        "Parameter 'source_mac_address' in event DLS.94"
    ::= { dlsEventObjects94 2 }

dls94_dest_mac_address OBJECT-TYPE
    SYNTAX DisplayString
    MAX-ACCESS accessible-for-notify
    STATUS current
    DESCRIPTION
        "Parameter 'dest_mac_address' in event DLS.94"
    ::= { dlsEventObjects94 3 }

dls94_source_sap OBJECT-TYPE
    SYNTAX Integer32
    MAX-ACCESS accessible-for-notify
    STATUS current
    DESCRIPTION
        "Parameter 'source_sap' in event DLS.94"
    ::= { dlsEventObjects94 4 }

dls94_dest_sap OBJECT-TYPE
    SYNTAX Integer32
    MAX-ACCESS accessible-for-notify
    STATUS current
    DESCRIPTION
        "Parameter 'dest_sap' in event DLS.94"
    ::= { dlsEventObjects94 5 }

dlsEventObjects98 OBJECT-IDENTITY
    STATUS current
    DESCRIPTION
        "Event DLS.98
        The TEST command frame received from the underlying DATA LINK is
        being enqueued in the firewall queue. This is true for the case
        when there is already a CANUREACH SSP message dispatched and
        is awaiting for the ICANREACH response."
    ::= { dlsEventsGroup 98 }

dls98_source_mac_address OBJECT-TYPE
    SYNTAX DisplayString
    MAX-ACCESS accessible-for-notify
    STATUS current
    DESCRIPTION
        "Parameter 'source_mac_address' in event DLS.98"
    ::= { dlsEventObjects98 1 }

dls98_dest_mac_address OBJECT-TYPE
    SYNTAX DisplayString
    MAX-ACCESS accessible-for-notify
    STATUS current
    DESCRIPTION
        "Parameter 'dest_mac_address' in event DLS.98"
    ::= { dlsEventObjects98 2 }

dls98_source_sap OBJECT-TYPE
    SYNTAX Integer32
    MAX-ACCESS accessible-for-notify
    STATUS current
    DESCRIPTION
        "Parameter 'source_sap' in event DLS.98"
    ::= { dlsEventObjects98 3 }

dls98_dest_sap OBJECT-TYPE
    SYNTAX Integer32
    MAX-ACCESS accessible-for-notify
    STATUS current
    DESCRIPTION
        "Parameter 'dest_sap' in event DLS.98"
    ::= { dlsEventObjects98 4 }

dlsEventObjects99 OBJECT-IDENTITY
    STATUS current
    DESCRIPTION
        "Event DLS.99
        While processing TEST(c) for a given destination, DLS sends out
        a broadcast of CANUREACH to all DLS partner. If there is not a
        single TCP connection established between DLS partners, this
        operation will fail. In such event, DLS session is terminated."
    ::= { dlsEventsGroup 99 }

dls99_source_mac_address OBJECT-TYPE
    SYNTAX DisplayString
    MAX-ACCESS accessible-for-notify
    STATUS current
    DESCRIPTION
        "Parameter 'source_mac_address' in event DLS.99"
    ::= { dlsEventObjects99 1 }

dls99_dest_mac_address OBJECT-TYPE
    SYNTAX DisplayString
    MAX-ACCESS accessible-for-notify
    STATUS current
    DESCRIPTION
        "Parameter 'dest_mac_address' in event DLS.99"
    ::= { dlsEventObjects99 2 }

dls99_source_sap OBJECT-TYPE
    SYNTAX Integer32
    MAX-ACCESS accessible-for-notify
    STATUS current
    DESCRIPTION
        "Parameter 'source_sap' in event DLS.99"
    ::= { dlsEventObjects99 3 }

dls99_dest_sap OBJECT-TYPE
    SYNTAX Integer32
    MAX-ACCESS accessible-for-notify
    STATUS current
    DESCRIPTION
        "Parameter 'dest_sap' in event DLS.99"
    ::= { dlsEventObjects99 4 }

dlsEventObjects100 OBJECT-IDENTITY
    STATUS current
    DESCRIPTION
        "Event DLS.100
        While processing TEST(c) for a given destination, DLS sends out
        a CANUREACH to specific DLS partner(s) if it knows that
        destination station is connected to one of its LAN. If this
        operation fails, for some difficulty within TCP connection, this
        event is produced. This does not necessarily result in
        termination of the DLS session as there can be success
        sending to other DLS partner."
    ::= { dlsEventsGroup 100 }

dls100_ip_address OBJECT-TYPE
    SYNTAX IpAddress
    MAX-ACCESS accessible-for-notify
    STATUS current
    DESCRIPTION
        "Parameter 'ip_address' in event DLS.100"
    ::= { dlsEventObjects100 1 }

dls100_source_mac_address OBJECT-TYPE
    SYNTAX DisplayString
    MAX-ACCESS accessible-for-notify
    STATUS current
    DESCRIPTION
        "Parameter 'source_mac_address' in event DLS.100"
    ::= { dlsEventObjects100 2 }

dls100_dest_mac_address OBJECT-TYPE
    SYNTAX DisplayString
    MAX-ACCESS accessible-for-notify
    STATUS current
    DESCRIPTION
        "Parameter 'dest_mac_address' in event DLS.100"
    ::= { dlsEventObjects100 3 }

dls100_source_sap OBJECT-TYPE
    SYNTAX Integer32
    MAX-ACCESS accessible-for-notify
    STATUS current
    DESCRIPTION
        "Parameter 'source_sap' in event DLS.100"
    ::= { dlsEventObjects100 4 }

dls100_dest_sap OBJECT-TYPE
    SYNTAX Integer32
    MAX-ACCESS accessible-for-notify
    STATUS current
    DESCRIPTION
        "Parameter 'dest_sap' in event DLS.100"
    ::= { dlsEventObjects100 5 }

dlsEventObjects101 OBJECT-IDENTITY
    STATUS current
    DESCRIPTION
        "Event DLS.101
        While processing TEST(c) for a given destination, DLS sent out
        a CANUREACH to specific DLS partner(s) if it knows that
        destination station is connected to one of its LAN."
    ::= { dlsEventsGroup 101 }

dls101_ip_address OBJECT-TYPE
    SYNTAX IpAddress
    MAX-ACCESS accessible-for-notify
    STATUS current
    DESCRIPTION
        "Parameter 'ip_address' in event DLS.101"
    ::= { dlsEventObjects101 1 }

dls101_source_mac_address OBJECT-TYPE
    SYNTAX DisplayString
    MAX-ACCESS accessible-for-notify
    STATUS current
    DESCRIPTION
        "Parameter 'source_mac_address' in event DLS.101"
    ::= { dlsEventObjects101 2 }

dls101_dest_mac_address OBJECT-TYPE
    SYNTAX DisplayString
    MAX-ACCESS accessible-for-notify
    STATUS current
    DESCRIPTION
        "Parameter 'dest_mac_address' in event DLS.101"
    ::= { dlsEventObjects101 3 }

dls101_source_sap OBJECT-TYPE
    SYNTAX Integer32
    MAX-ACCESS accessible-for-notify
    STATUS current
    DESCRIPTION
        "Parameter 'source_sap' in event DLS.101"
    ::= { dlsEventObjects101 4 }

dls101_dest_sap OBJECT-TYPE
    SYNTAX Integer32
    MAX-ACCESS accessible-for-notify
    STATUS current
    DESCRIPTION
        "Parameter 'dest_sap' in event DLS.101"
    ::= { dlsEventObjects101 5 }

dlsEventObjects102 OBJECT-IDENTITY
    STATUS current
    DESCRIPTION
        "Event DLS.102
        While processing TEST(c) for a given destination, DLS sent out
        broadcast CANUREACH to all the DLS partner(s) it has TCP
        connection established with.
        Exploring phases: (0) Broadcast to all DLS partner(s).
        (1) Broadcast to priorized DLS partner(s).
        (2) Broadcast to no priorized DLS partner(s)."
    ::= { dlsEventsGroup 102 }

dls102_source_mac_address OBJECT-TYPE
    SYNTAX DisplayString
    MAX-ACCESS accessible-for-notify
    STATUS current
    DESCRIPTION
        "Parameter 'source_mac_address' in event DLS.102"
    ::= { dlsEventObjects102 1 }

dls102_dest_mac_address OBJECT-TYPE
    SYNTAX DisplayString
    MAX-ACCESS accessible-for-notify
    STATUS current
    DESCRIPTION
        "Parameter 'dest_mac_address' in event DLS.102"
    ::= { dlsEventObjects102 2 }

dls102_source_sap OBJECT-TYPE
    SYNTAX Integer32
    MAX-ACCESS accessible-for-notify
    STATUS current
    DESCRIPTION
        "Parameter 'source_sap' in event DLS.102"
    ::= { dlsEventObjects102 3 }

dls102_dest_sap OBJECT-TYPE
    SYNTAX Integer32
    MAX-ACCESS accessible-for-notify
    STATUS current
    DESCRIPTION
        "Parameter 'dest_sap' in event DLS.102"
    ::= { dlsEventObjects102 4 }

dls102_phase OBJECT-TYPE
    SYNTAX Integer32
    MAX-ACCESS accessible-for-notify
    STATUS current
    DESCRIPTION
        "Parameter 'phase' in event DLS.102"
    ::= { dlsEventObjects102 5 }

dlsEventObjects104 OBJECT-IDENTITY
    STATUS current
    DESCRIPTION
        "Event DLS.104
        DLS connection can get established without using the specific
        SAPs, for example, SAP 0 as DSAP or SSAP. However, when the
        specific SAPs are used, the same connection's SAPs are updated."
    ::= { dlsEventsGroup 104 }

dls104_source_mac_address OBJECT-TYPE
    SYNTAX DisplayString
    MAX-ACCESS accessible-for-notify
    STATUS current
    DESCRIPTION
        "Parameter 'source_mac_address' in event DLS.104"
    ::= { dlsEventObjects104 1 }

dls104_dest_mac_address OBJECT-TYPE
    SYNTAX DisplayString
    MAX-ACCESS accessible-for-notify
    STATUS current
    DESCRIPTION
        "Parameter 'dest_mac_address' in event DLS.104"
    ::= { dlsEventObjects104 2 }

dls104_source_sap OBJECT-TYPE
    SYNTAX Integer32
    MAX-ACCESS accessible-for-notify
    STATUS current
    DESCRIPTION
        "Parameter 'source_sap' in event DLS.104"
    ::= { dlsEventObjects104 3 }

dls104_dest_sap OBJECT-TYPE
    SYNTAX Integer32
    MAX-ACCESS accessible-for-notify
    STATUS current
    DESCRIPTION
        "Parameter 'dest_sap' in event DLS.104"
    ::= { dlsEventObjects104 4 }

dlsEventObjects106 OBJECT-IDENTITY
    STATUS current
    DESCRIPTION
        "Event DLS.106
        A CANUREACH SSP message we received over the TCP from a DLS Peer.
        However, none of the underlying data link layer, SDLC or LLC, could
        translate this to a TEST(c) frame."
    ::= { dlsEventsGroup 106 }

dls106_source_mac_address OBJECT-TYPE
    SYNTAX DisplayString
    MAX-ACCESS accessible-for-notify
    STATUS current
    DESCRIPTION
        "Parameter 'source_mac_address' in event DLS.106"
    ::= { dlsEventObjects106 1 }

dls106_dest_mac_address OBJECT-TYPE
    SYNTAX DisplayString
    MAX-ACCESS accessible-for-notify
    STATUS current
    DESCRIPTION
        "Parameter 'dest_mac_address' in event DLS.106"
    ::= { dlsEventObjects106 2 }

dls106_source_sap OBJECT-TYPE
    SYNTAX Integer32
    MAX-ACCESS accessible-for-notify
    STATUS current
    DESCRIPTION
        "Parameter 'source_sap' in event DLS.106"
    ::= { dlsEventObjects106 3 }

dls106_dest_sap OBJECT-TYPE
    SYNTAX Integer32
    MAX-ACCESS accessible-for-notify
    STATUS current
    DESCRIPTION
        "Parameter 'dest_sap' in event DLS.106"
    ::= { dlsEventObjects106 4 }

dlsEventObjects107 OBJECT-IDENTITY
    STATUS current
    DESCRIPTION
        "Event DLS.107
        DLS is learning New MAC and IP association from an SSP message
        received from the peer DLS. This typically occurs during CANUREACH
        or ICANREACH message receipt time."
    ::= { dlsEventsGroup 107 }

dls107_ip_address OBJECT-TYPE
    SYNTAX IpAddress
    MAX-ACCESS accessible-for-notify
    STATUS current
    DESCRIPTION
        "Parameter 'ip_address' in event DLS.107"
    ::= { dlsEventObjects107 1 }

dls107_mac_address OBJECT-TYPE
    SYNTAX DisplayString
    MAX-ACCESS accessible-for-notify
    STATUS current
    DESCRIPTION
        "Parameter 'mac_address' in event DLS.107"
    ::= { dlsEventObjects107 2 }

dlsEventObjects108 OBJECT-IDENTITY
    STATUS current
    DESCRIPTION
        "Event DLS.108
        DLS has received an unanticipated ICANREACH message. ICANREACH SSP
        message is usually expected only as a response to an CANUREACH SSP
        message sent earlier. The DLS state machine will not process this
        message. However, it still will go ahead and learn the IP address
        and MAC address association."
    ::= { dlsEventsGroup 108 }

dls108_ip_address OBJECT-TYPE
    SYNTAX IpAddress
    MAX-ACCESS accessible-for-notify
    STATUS current
    DESCRIPTION
        "Parameter 'ip_address' in event DLS.108"
    ::= { dlsEventObjects108 1 }

dls108_mac_address OBJECT-TYPE
    SYNTAX DisplayString
    MAX-ACCESS accessible-for-notify
    STATUS current
    DESCRIPTION
        "Parameter 'mac_address' in event DLS.108"
    ::= { dlsEventObjects108 2 }

dlsEventObjects109 OBJECT-IDENTITY
    STATUS current
    DESCRIPTION
        "Event DLS.109
        DLS has received a secondary ICANREACH message from other
        DLS peer(s) which also claims reachability to the MAC address
        via him(them). This is normal. The DLS state machine takes note
        of these DLS peers, But no further communication takes place."
    ::= { dlsEventsGroup 109 }

dls109_ip_address OBJECT-TYPE
    SYNTAX IpAddress
    MAX-ACCESS accessible-for-notify
    STATUS current
    DESCRIPTION
        "Parameter 'ip_address' in event DLS.109"
    ::= { dlsEventObjects109 1 }

dls109_mac_address OBJECT-TYPE
    SYNTAX DisplayString
    MAX-ACCESS accessible-for-notify
    STATUS current
    DESCRIPTION
        "Parameter 'mac_address' in event DLS.109"
    ::= { dlsEventObjects109 2 }

dlsEventObjects110 OBJECT-IDENTITY
    STATUS current
    DESCRIPTION
        "Event DLS.110
        DLS has received an ICANREACH message from one or more DLS
        peers. This has triggered sending of pending CANUREACH to the
        same destination MAC address. These messages were present in
        the firewall queue."
    ::= { dlsEventsGroup 110 }

dls110_mac_address OBJECT-TYPE
    SYNTAX DisplayString
    MAX-ACCESS accessible-for-notify
    STATUS current
    DESCRIPTION
        "Parameter 'mac_address' in event DLS.110"
    ::= { dlsEventObjects110 1 }

dlsEventObjects111 OBJECT-IDENTITY
    STATUS current
    DESCRIPTION
        "Event DLS.111
        DLS successfully sent out an SSP message over TCP to its DLS peer."
    ::= { dlsEventsGroup 111 }

dls111_message_type OBJECT-TYPE
    SYNTAX DisplayString
    MAX-ACCESS accessible-for-notify
    STATUS current
    DESCRIPTION
        "Parameter 'message_type' in event DLS.111"
    ::= { dlsEventObjects111 1 }

dls111_ip_address OBJECT-TYPE
    SYNTAX IpAddress
    MAX-ACCESS accessible-for-notify
    STATUS current
    DESCRIPTION
        "Parameter 'ip_address' in event DLS.111"
    ::= { dlsEventObjects111 2 }

dls111_source_mac_address OBJECT-TYPE
    SYNTAX DisplayString
    MAX-ACCESS accessible-for-notify
    STATUS current
    DESCRIPTION
        "Parameter 'source_mac_address' in event DLS.111"
    ::= { dlsEventObjects111 3 }

dls111_dest_mac_address OBJECT-TYPE
    SYNTAX DisplayString
    MAX-ACCESS accessible-for-notify
    STATUS current
    DESCRIPTION
        "Parameter 'dest_mac_address' in event DLS.111"
    ::= { dlsEventObjects111 4 }

dls111_source_sap OBJECT-TYPE
    SYNTAX Integer32
    MAX-ACCESS accessible-for-notify
    STATUS current
    DESCRIPTION
        "Parameter 'source_sap' in event DLS.111"
    ::= { dlsEventObjects111 5 }

dls111_dest_sap OBJECT-TYPE
    SYNTAX Integer32
    MAX-ACCESS accessible-for-notify
    STATUS current
    DESCRIPTION
        "Parameter 'dest_sap' in event DLS.111"
    ::= { dlsEventObjects111 6 }

dlsEventObjects112 OBJECT-IDENTITY
    STATUS current
    DESCRIPTION
        "Event DLS.112
        Due to some problems with TCP connection to its DLS peer, an
        SSP control message could not be sent out."
    ::= { dlsEventsGroup 112 }

dls112_message_type OBJECT-TYPE
    SYNTAX DisplayString
    MAX-ACCESS accessible-for-notify
    STATUS current
    DESCRIPTION
        "Parameter 'message_type' in event DLS.112"
    ::= { dlsEventObjects112 1 }

dls112_ip_address OBJECT-TYPE
    SYNTAX IpAddress
    MAX-ACCESS accessible-for-notify
    STATUS current
    DESCRIPTION
        "Parameter 'ip_address' in event DLS.112"
    ::= { dlsEventObjects112 2 }

dls112_source_mac_address OBJECT-TYPE
    SYNTAX DisplayString
    MAX-ACCESS accessible-for-notify
    STATUS current
    DESCRIPTION
        "Parameter 'source_mac_address' in event DLS.112"
    ::= { dlsEventObjects112 3 }

dls112_dest_mac_address OBJECT-TYPE
    SYNTAX DisplayString
    MAX-ACCESS accessible-for-notify
    STATUS current
    DESCRIPTION
        "Parameter 'dest_mac_address' in event DLS.112"
    ::= { dlsEventObjects112 4 }

dls112_source_sap OBJECT-TYPE
    SYNTAX Integer32
    MAX-ACCESS accessible-for-notify
    STATUS current
    DESCRIPTION
        "Parameter 'source_sap' in event DLS.112"
    ::= { dlsEventObjects112 5 }

dls112_dest_sap OBJECT-TYPE
    SYNTAX Integer32
    MAX-ACCESS accessible-for-notify
    STATUS current
    DESCRIPTION
        "Parameter 'dest_sap' in event DLS.112"
    ::= { dlsEventObjects112 6 }

dlsEventObjects113 OBJECT-IDENTITY
    STATUS current
    DESCRIPTION
        "Event DLS.113
        Due to some problems, SAP initialization with LLC failed."
    ::= { dlsEventsGroup 113 }

dls113_Sap OBJECT-TYPE
    SYNTAX Integer32
    MAX-ACCESS accessible-for-notify
    STATUS current
    DESCRIPTION
        "Parameter 'Sap' in event DLS.113"
    ::= { dlsEventObjects113 1 }

dlsEventObjects114 OBJECT-IDENTITY
    STATUS current
    DESCRIPTION
        "Event DLS.114
        LLC tunable parameters are out of range."
    ::= { dlsEventsGroup 114 }

dls114_Sap OBJECT-TYPE
    SYNTAX Integer32
    MAX-ACCESS accessible-for-notify
    STATUS current
    DESCRIPTION
        "Parameter 'Sap' in event DLS.114"
    ::= { dlsEventObjects114 1 }

dls114_reason OBJECT-TYPE
    SYNTAX Integer32
    MAX-ACCESS accessible-for-notify
    STATUS current
    DESCRIPTION
        "Parameter 'reason' in event DLS.114"
    ::= { dlsEventObjects114 2 }

dlsEventObjects115 OBJECT-IDENTITY
    STATUS current
    DESCRIPTION
        "Event DLS.115
        No memory available for the SAP control block."
    ::= { dlsEventsGroup 115 }

dls115_Sap OBJECT-TYPE
    SYNTAX Integer32
    MAX-ACCESS accessible-for-notify
    STATUS current
    DESCRIPTION
        "Parameter 'Sap' in event DLS.115"
    ::= { dlsEventObjects115 1 }

dlsEventObjects116 OBJECT-IDENTITY
    STATUS current
    DESCRIPTION
        "Event DLS.116
        Opening of SAP failed due to problems in the LLC.
        Reason code is indicative of the specific problem."
    ::= { dlsEventsGroup 116 }

dls116_Sap OBJECT-TYPE
    SYNTAX Integer32
    MAX-ACCESS accessible-for-notify
    STATUS current
    DESCRIPTION
        "Parameter 'Sap' in event DLS.116"
    ::= { dlsEventObjects116 1 }

dls116_reason OBJECT-TYPE
    SYNTAX Integer32
    MAX-ACCESS accessible-for-notify
    STATUS current
    DESCRIPTION
        "Parameter 'reason' in event DLS.116"
    ::= { dlsEventObjects116 2 }

dlsEventObjects117 OBJECT-IDENTITY
    STATUS current
    DESCRIPTION
        "Event DLS.117
        Closing SAP with the LLC."
    ::= { dlsEventsGroup 117 }

dls117_Sap OBJECT-TYPE
    SYNTAX Integer32
    MAX-ACCESS accessible-for-notify
    STATUS current
    DESCRIPTION
        "Parameter 'Sap' in event DLS.117"
    ::= { dlsEventObjects117 1 }

dlsEventObjects118 OBJECT-IDENTITY
    STATUS current
    DESCRIPTION
        "Event DLS.118
        Opening of station for LLC data link services failed because
        the SAP under which station to be opened is invalid."
    ::= { dlsEventsGroup 118 }

dls118_Destination OBJECT-TYPE
    SYNTAX DisplayString
    MAX-ACCESS accessible-for-notify
    STATUS current
    DESCRIPTION
        "Parameter 'Destination' in event DLS.118"
    ::= { dlsEventObjects118 1 }

dls118_Source OBJECT-TYPE
    SYNTAX DisplayString
    MAX-ACCESS accessible-for-notify
    STATUS current
    DESCRIPTION
        "Parameter 'Source' in event DLS.118"
    ::= { dlsEventObjects118 2 }

dls118_Dsap OBJECT-TYPE
    SYNTAX Integer32
    MAX-ACCESS accessible-for-notify
    STATUS current
    DESCRIPTION
        "Parameter 'Dsap' in event DLS.118"
    ::= { dlsEventObjects118 3 }

dls118_Ssap OBJECT-TYPE
    SYNTAX Integer32
    MAX-ACCESS accessible-for-notify
    STATUS current
    DESCRIPTION
        "Parameter 'Ssap' in event DLS.118"
    ::= { dlsEventObjects118 4 }

dlsEventObjects119 OBJECT-IDENTITY
    STATUS current
    DESCRIPTION
        "Event DLS.119
        Opening of station for LLC data link services failed because
        there is no memory available to create control block to manage
        the connection."
    ::= { dlsEventsGroup 119 }

dls119_Destination OBJECT-TYPE
    SYNTAX DisplayString
    MAX-ACCESS accessible-for-notify
    STATUS current
    DESCRIPTION
        "Parameter 'Destination' in event DLS.119"
    ::= { dlsEventObjects119 1 }

dls119_Source OBJECT-TYPE
    SYNTAX DisplayString
    MAX-ACCESS accessible-for-notify
    STATUS current
    DESCRIPTION
        "Parameter 'Source' in event DLS.119"
    ::= { dlsEventObjects119 2 }

dls119_Dsap OBJECT-TYPE
    SYNTAX Integer32
    MAX-ACCESS accessible-for-notify
    STATUS current
    DESCRIPTION
        "Parameter 'Dsap' in event DLS.119"
    ::= { dlsEventObjects119 3 }

dls119_Ssap OBJECT-TYPE
    SYNTAX Integer32
    MAX-ACCESS accessible-for-notify
    STATUS current
    DESCRIPTION
        "Parameter 'Ssap' in event DLS.119"
    ::= { dlsEventObjects119 4 }

dlsEventObjects120 OBJECT-IDENTITY
    STATUS current
    DESCRIPTION
        "Event DLS.120
        Opening of station for LLC data link services failed due to
        some problems within LLC. The reason code is indicative of
        the specific problem."
    ::= { dlsEventsGroup 120 }

dls120_Reason OBJECT-TYPE
    SYNTAX Integer32
    MAX-ACCESS accessible-for-notify
    STATUS current
    DESCRIPTION
        "Parameter 'Reason' in event DLS.120"
    ::= { dlsEventObjects120 1 }

dls120_Destination OBJECT-TYPE
    SYNTAX DisplayString
    MAX-ACCESS accessible-for-notify
    STATUS current
    DESCRIPTION
        "Parameter 'Destination' in event DLS.120"
    ::= { dlsEventObjects120 2 }

dls120_Source OBJECT-TYPE
    SYNTAX DisplayString
    MAX-ACCESS accessible-for-notify
    STATUS current
    DESCRIPTION
        "Parameter 'Source' in event DLS.120"
    ::= { dlsEventObjects120 3 }

dls120_Dsap OBJECT-TYPE
    SYNTAX Integer32
    MAX-ACCESS accessible-for-notify
    STATUS current
    DESCRIPTION
        "Parameter 'Dsap' in event DLS.120"
    ::= { dlsEventObjects120 4 }

dls120_Ssap OBJECT-TYPE
    SYNTAX Integer32
    MAX-ACCESS accessible-for-notify
    STATUS current
    DESCRIPTION
        "Parameter 'Ssap' in event DLS.120"
    ::= { dlsEventObjects120 5 }

dlsEventObjects121 OBJECT-IDENTITY
    STATUS current
    DESCRIPTION
        "Event DLS.121
        Opening of station for LLC data link services succeeded."
    ::= { dlsEventsGroup 121 }

dls121_Destination OBJECT-TYPE
    SYNTAX DisplayString
    MAX-ACCESS accessible-for-notify
    STATUS current
    DESCRIPTION
        "Parameter 'Destination' in event DLS.121"
    ::= { dlsEventObjects121 1 }

dls121_Source OBJECT-TYPE
    SYNTAX DisplayString
    MAX-ACCESS accessible-for-notify
    STATUS current
    DESCRIPTION
        "Parameter 'Source' in event DLS.121"
    ::= { dlsEventObjects121 2 }

dls121_Dsap OBJECT-TYPE
    SYNTAX Integer32
    MAX-ACCESS accessible-for-notify
    STATUS current
    DESCRIPTION
        "Parameter 'Dsap' in event DLS.121"
    ::= { dlsEventObjects121 3 }

dls121_Ssap OBJECT-TYPE
    SYNTAX Integer32
    MAX-ACCESS accessible-for-notify
    STATUS current
    DESCRIPTION
        "Parameter 'Ssap' in event DLS.121"
    ::= { dlsEventObjects121 4 }

dlsEventObjects123 OBJECT-IDENTITY
    STATUS current
    DESCRIPTION
        "Event DLS.123
        Exchange of station for LLC data link services succeeded.
        Exchange operation involves opening an already opened station
        for LLC services under a different SAP."
    ::= { dlsEventsGroup 123 }

dls123_Destination OBJECT-TYPE
    SYNTAX DisplayString
    MAX-ACCESS accessible-for-notify
    STATUS current
    DESCRIPTION
        "Parameter 'Destination' in event DLS.123"
    ::= { dlsEventObjects123 1 }

dls123_Source OBJECT-TYPE
    SYNTAX DisplayString
    MAX-ACCESS accessible-for-notify
    STATUS current
    DESCRIPTION
        "Parameter 'Source' in event DLS.123"
    ::= { dlsEventObjects123 2 }

dls123_Dsap OBJECT-TYPE
    SYNTAX Integer32
    MAX-ACCESS accessible-for-notify
    STATUS current
    DESCRIPTION
        "Parameter 'Dsap' in event DLS.123"
    ::= { dlsEventObjects123 3 }

dls123_Ssap OBJECT-TYPE
    SYNTAX Integer32
    MAX-ACCESS accessible-for-notify
    STATUS current
    DESCRIPTION
        "Parameter 'Ssap' in event DLS.123"
    ::= { dlsEventObjects123 4 }

dlsEventObjects124 OBJECT-IDENTITY
    STATUS current
    DESCRIPTION
        "Event DLS.124
        Closed station by force for LLC data link services."
    ::= { dlsEventsGroup 124 }

dls124_source_mac_address OBJECT-TYPE
    SYNTAX DisplayString
    MAX-ACCESS accessible-for-notify
    STATUS current
    DESCRIPTION
        "Parameter 'source_mac_address' in event DLS.124"
    ::= { dlsEventObjects124 1 }

dls124_dest_mac_address OBJECT-TYPE
    SYNTAX DisplayString
    MAX-ACCESS accessible-for-notify
    STATUS current
    DESCRIPTION
        "Parameter 'dest_mac_address' in event DLS.124"
    ::= { dlsEventObjects124 2 }

dls124_source_sap OBJECT-TYPE
    SYNTAX Integer32
    MAX-ACCESS accessible-for-notify
    STATUS current
    DESCRIPTION
        "Parameter 'source_sap' in event DLS.124"
    ::= { dlsEventObjects124 3 }

dls124_dest_sap OBJECT-TYPE
    SYNTAX Integer32
    MAX-ACCESS accessible-for-notify
    STATUS current
    DESCRIPTION
        "Parameter 'dest_sap' in event DLS.124"
    ::= { dlsEventObjects124 4 }

dlsEventObjects125 OBJECT-IDENTITY
    STATUS current
    DESCRIPTION
        "Event DLS.125
        Closed station quietly for LLC data link services."
    ::= { dlsEventsGroup 125 }

dls125_source_mac_address OBJECT-TYPE
    SYNTAX DisplayString
    MAX-ACCESS accessible-for-notify
    STATUS current
    DESCRIPTION
        "Parameter 'source_mac_address' in event DLS.125"
    ::= { dlsEventObjects125 1 }

dls125_dest_mac_address OBJECT-TYPE
    SYNTAX DisplayString
    MAX-ACCESS accessible-for-notify
    STATUS current
    DESCRIPTION
        "Parameter 'dest_mac_address' in event DLS.125"
    ::= { dlsEventObjects125 2 }

dls125_source_sap OBJECT-TYPE
    SYNTAX Integer32
    MAX-ACCESS accessible-for-notify
    STATUS current
    DESCRIPTION
        "Parameter 'source_sap' in event DLS.125"
    ::= { dlsEventObjects125 3 }

dls125_dest_sap OBJECT-TYPE
    SYNTAX Integer32
    MAX-ACCESS accessible-for-notify
    STATUS current
    DESCRIPTION
        "Parameter 'dest_sap' in event DLS.125"
    ::= { dlsEventObjects125 4 }

dlsEventObjects126 OBJECT-IDENTITY
    STATUS current
    DESCRIPTION
        "Event DLS.126
        LLC was unsuccessful in sending out a frame. The reason
        indicative of the specific problem."
    ::= { dlsEventsGroup 126 }

dls126_action OBJECT-TYPE
    SYNTAX DisplayString
    MAX-ACCESS accessible-for-notify
    STATUS current
    DESCRIPTION
        "Parameter 'action' in event DLS.126"
    ::= { dlsEventObjects126 1 }

dls126_reason OBJECT-TYPE
    SYNTAX Integer32
    MAX-ACCESS accessible-for-notify
    STATUS current
    DESCRIPTION
        "Parameter 'reason' in event DLS.126"
    ::= { dlsEventObjects126 2 }

dls126_source_mac_address OBJECT-TYPE
    SYNTAX DisplayString
    MAX-ACCESS accessible-for-notify
    STATUS current
    DESCRIPTION
        "Parameter 'source_mac_address' in event DLS.126"
    ::= { dlsEventObjects126 3 }

dls126_dest_mac_address OBJECT-TYPE
    SYNTAX DisplayString
    MAX-ACCESS accessible-for-notify
    STATUS current
    DESCRIPTION
        "Parameter 'dest_mac_address' in event DLS.126"
    ::= { dlsEventObjects126 4 }

dls126_source_sap OBJECT-TYPE
    SYNTAX Integer32
    MAX-ACCESS accessible-for-notify
    STATUS current
    DESCRIPTION
        "Parameter 'source_sap' in event DLS.126"
    ::= { dlsEventObjects126 5 }

dls126_dest_sap OBJECT-TYPE
    SYNTAX Integer32
    MAX-ACCESS accessible-for-notify
    STATUS current
    DESCRIPTION
        "Parameter 'dest_sap' in event DLS.126"
    ::= { dlsEventObjects126 6 }

dlsEventObjects127 OBJECT-IDENTITY
    STATUS current
    DESCRIPTION
        "Event DLS.127
        LLC became busy after sending out a frame. This busyness
        is an honor system and the frame submitted to LLC does
        get accepted for sending. However, DLS takes note of
        this condition and refrains from sending more frames."
    ::= { dlsEventsGroup 127 }

dls127_action OBJECT-TYPE
    SYNTAX DisplayString
    MAX-ACCESS accessible-for-notify
    STATUS current
    DESCRIPTION
        "Parameter 'action' in event DLS.127"
    ::= { dlsEventObjects127 1 }

dls127_source_mac_address OBJECT-TYPE
    SYNTAX DisplayString
    MAX-ACCESS accessible-for-notify
    STATUS current
    DESCRIPTION
        "Parameter 'source_mac_address' in event DLS.127"
    ::= { dlsEventObjects127 2 }

dls127_dest_mac_address OBJECT-TYPE
    SYNTAX DisplayString
    MAX-ACCESS accessible-for-notify
    STATUS current
    DESCRIPTION
        "Parameter 'dest_mac_address' in event DLS.127"
    ::= { dlsEventObjects127 3 }

dls127_source_sap OBJECT-TYPE
    SYNTAX Integer32
    MAX-ACCESS accessible-for-notify
    STATUS current
    DESCRIPTION
        "Parameter 'source_sap' in event DLS.127"
    ::= { dlsEventObjects127 4 }

dls127_dest_sap OBJECT-TYPE
    SYNTAX Integer32
    MAX-ACCESS accessible-for-notify
    STATUS current
    DESCRIPTION
        "Parameter 'dest_sap' in event DLS.127"
    ::= { dlsEventObjects127 5 }

dlsEventObjects128 OBJECT-IDENTITY
    STATUS current
    DESCRIPTION
        "Event DLS.128
        LLC is busy, frames received from TCP are being enqueued to
        the pending queue for that LLC session. When LLC exits busy
        condition, all the frames from the pending queue will be flushed."
    ::= { dlsEventsGroup 128 }

dls128_source_mac_address OBJECT-TYPE
    SYNTAX DisplayString
    MAX-ACCESS accessible-for-notify
    STATUS current
    DESCRIPTION
        "Parameter 'source_mac_address' in event DLS.128"
    ::= { dlsEventObjects128 1 }

dls128_dest_mac_address OBJECT-TYPE
    SYNTAX DisplayString
    MAX-ACCESS accessible-for-notify
    STATUS current
    DESCRIPTION
        "Parameter 'dest_mac_address' in event DLS.128"
    ::= { dlsEventObjects128 2 }

dls128_source_sap OBJECT-TYPE
    SYNTAX Integer32
    MAX-ACCESS accessible-for-notify
    STATUS current
    DESCRIPTION
        "Parameter 'source_sap' in event DLS.128"
    ::= { dlsEventObjects128 3 }

dls128_dest_sap OBJECT-TYPE
    SYNTAX Integer32
    MAX-ACCESS accessible-for-notify
    STATUS current
    DESCRIPTION
        "Parameter 'dest_sap' in event DLS.128"
    ::= { dlsEventObjects128 4 }

dlsEventObjects129 OBJECT-IDENTITY
    STATUS current
    DESCRIPTION
        "Event DLS.129
        A frame received from DLS cloud was successfully sent to an
        LLC end station."
    ::= { dlsEventsGroup 129 }

dls129_message_type OBJECT-TYPE
    SYNTAX DisplayString
    MAX-ACCESS accessible-for-notify
    STATUS current
    DESCRIPTION
        "Parameter 'message_type' in event DLS.129"
    ::= { dlsEventObjects129 1 }

dls129_source_mac_address OBJECT-TYPE
    SYNTAX DisplayString
    MAX-ACCESS accessible-for-notify
    STATUS current
    DESCRIPTION
        "Parameter 'source_mac_address' in event DLS.129"
    ::= { dlsEventObjects129 2 }

dls129_dest_mac_address OBJECT-TYPE
    SYNTAX DisplayString
    MAX-ACCESS accessible-for-notify
    STATUS current
    DESCRIPTION
        "Parameter 'dest_mac_address' in event DLS.129"
    ::= { dlsEventObjects129 3 }

dls129_source_sap OBJECT-TYPE
    SYNTAX Integer32
    MAX-ACCESS accessible-for-notify
    STATUS current
    DESCRIPTION
        "Parameter 'source_sap' in event DLS.129"
    ::= { dlsEventObjects129 4 }

dls129_dest_sap OBJECT-TYPE
    SYNTAX Integer32
    MAX-ACCESS accessible-for-notify
    STATUS current
    DESCRIPTION
        "Parameter 'dest_sap' in event DLS.129"
    ::= { dlsEventObjects129 5 }

dlsEventObjects130 OBJECT-IDENTITY
    STATUS current
    DESCRIPTION
        "Event DLS.130
        Frame was not processed by the DLS as the SAP, as well as
        the station was not opened for LLC data link services."
    ::= { dlsEventsGroup 130 }

dls130_source_mac_address OBJECT-TYPE
    SYNTAX DisplayString
    MAX-ACCESS accessible-for-notify
    STATUS current
    DESCRIPTION
        "Parameter 'source_mac_address' in event DLS.130"
    ::= { dlsEventObjects130 1 }

dls130_dest_mac_address OBJECT-TYPE
    SYNTAX DisplayString
    MAX-ACCESS accessible-for-notify
    STATUS current
    DESCRIPTION
        "Parameter 'dest_mac_address' in event DLS.130"
    ::= { dlsEventObjects130 2 }

dls130_source_sap OBJECT-TYPE
    SYNTAX Integer32
    MAX-ACCESS accessible-for-notify
    STATUS current
    DESCRIPTION
        "Parameter 'source_sap' in event DLS.130"
    ::= { dlsEventObjects130 3 }

dls130_dest_sap OBJECT-TYPE
    SYNTAX Integer32
    MAX-ACCESS accessible-for-notify
    STATUS current
    DESCRIPTION
        "Parameter 'dest_sap' in event DLS.130"
    ::= { dlsEventObjects130 4 }

dlsEventObjects131 OBJECT-IDENTITY
    STATUS current
    DESCRIPTION
        "Event DLS.131
        Frame was not processed by the DLS as the DSAP of the frame
        is not configured to be switched for the interface on which the frame
        was received."
    ::= { dlsEventsGroup 131 }

dls131_interface OBJECT-TYPE
    SYNTAX DisplayString
    MAX-ACCESS accessible-for-notify
    STATUS current
    DESCRIPTION
        "Parameter 'interface' in event DLS.131"
    ::= { dlsEventObjects131 1 }

dls131_source_mac_address OBJECT-TYPE
    SYNTAX DisplayString
    MAX-ACCESS accessible-for-notify
    STATUS current
    DESCRIPTION
        "Parameter 'source_mac_address' in event DLS.131"
    ::= { dlsEventObjects131 2 }

dls131_dest_mac_address OBJECT-TYPE
    SYNTAX DisplayString
    MAX-ACCESS accessible-for-notify
    STATUS current
    DESCRIPTION
        "Parameter 'dest_mac_address' in event DLS.131"
    ::= { dlsEventObjects131 3 }

dls131_source_sap OBJECT-TYPE
    SYNTAX Integer32
    MAX-ACCESS accessible-for-notify
    STATUS current
    DESCRIPTION
        "Parameter 'source_sap' in event DLS.131"
    ::= { dlsEventObjects131 4 }

dls131_dest_sap OBJECT-TYPE
    SYNTAX Integer32
    MAX-ACCESS accessible-for-notify
    STATUS current
    DESCRIPTION
        "Parameter 'dest_sap' in event DLS.131"
    ::= { dlsEventObjects131 5 }

dlsEventObjects132 OBJECT-IDENTITY
    STATUS current
    DESCRIPTION
        "Event DLS.132
        Frame was not processed by the DLS-LLC interface modules
        state machine as it could not be successfully relayed via
        DLS. This instance is normal for TEST command frame as DLS
        copies the frame and still refuses the frame so that it
        can also be sent via the bridge path."
    ::= { dlsEventsGroup 132 }

dls132_frame_type OBJECT-TYPE
    SYNTAX DisplayString
    MAX-ACCESS accessible-for-notify
    STATUS current
    DESCRIPTION
        "Parameter 'frame_type' in event DLS.132"
    ::= { dlsEventObjects132 1 }

dls132_source_mac_address OBJECT-TYPE
    SYNTAX DisplayString
    MAX-ACCESS accessible-for-notify
    STATUS current
    DESCRIPTION
        "Parameter 'source_mac_address' in event DLS.132"
    ::= { dlsEventObjects132 2 }

dls132_dest_mac_address OBJECT-TYPE
    SYNTAX DisplayString
    MAX-ACCESS accessible-for-notify
    STATUS current
    DESCRIPTION
        "Parameter 'dest_mac_address' in event DLS.132"
    ::= { dlsEventObjects132 3 }

dls132_source_sap OBJECT-TYPE
    SYNTAX Integer32
    MAX-ACCESS accessible-for-notify
    STATUS current
    DESCRIPTION
        "Parameter 'source_sap' in event DLS.132"
    ::= { dlsEventObjects132 4 }

dls132_dest_sap OBJECT-TYPE
    SYNTAX Integer32
    MAX-ACCESS accessible-for-notify
    STATUS current
    DESCRIPTION
        "Parameter 'dest_sap' in event DLS.132"
    ::= { dlsEventObjects132 5 }

dlsEventObjects133 OBJECT-IDENTITY
    STATUS current
    DESCRIPTION
        "Event DLS.133
        LLC event was not processed."
    ::= { dlsEventsGroup 133 }

dls133_eventtype OBJECT-TYPE
    SYNTAX DisplayString
    MAX-ACCESS accessible-for-notify
    STATUS current
    DESCRIPTION
        "Parameter 'eventtype' in event DLS.133"
    ::= { dlsEventObjects133 1 }

dls133_source_mac_address OBJECT-TYPE
    SYNTAX DisplayString
    MAX-ACCESS accessible-for-notify
    STATUS current
    DESCRIPTION
        "Parameter 'source_mac_address' in event DLS.133"
    ::= { dlsEventObjects133 2 }

dls133_dest_mac_address OBJECT-TYPE
    SYNTAX DisplayString
    MAX-ACCESS accessible-for-notify
    STATUS current
    DESCRIPTION
        "Parameter 'dest_mac_address' in event DLS.133"
    ::= { dlsEventObjects133 3 }

dls133_source_sap OBJECT-TYPE
    SYNTAX Integer32
    MAX-ACCESS accessible-for-notify
    STATUS current
    DESCRIPTION
        "Parameter 'source_sap' in event DLS.133"
    ::= { dlsEventObjects133 4 }

dls133_dest_sap OBJECT-TYPE
    SYNTAX Integer32
    MAX-ACCESS accessible-for-notify
    STATUS current
    DESCRIPTION
        "Parameter 'dest_sap' in event DLS.133"
    ::= { dlsEventObjects133 5 }

dlsEventObjects134 OBJECT-IDENTITY
    STATUS current
    DESCRIPTION
        "Event DLS.134
        An LLC event was not processed by the DLS as the handle
        by the LLC to DLS was bad."
    ::= { dlsEventsGroup 134 }

dls134_llcevent OBJECT-TYPE
    SYNTAX DisplayString
    MAX-ACCESS accessible-for-notify
    STATUS current
    DESCRIPTION
        "Parameter 'llcevent' in event DLS.134"
    ::= { dlsEventObjects134 1 }

dlsEventObjects135 OBJECT-IDENTITY
    STATUS current
    DESCRIPTION
        "Event DLS.135
        An unrecognizable LLC event occurred. This event is not processed."
    ::= { dlsEventsGroup 135 }

dls135_llcevent OBJECT-TYPE
    SYNTAX Integer32
    MAX-ACCESS accessible-for-notify
    STATUS current
    DESCRIPTION
        "Parameter 'llcevent' in event DLS.135"
    ::= { dlsEventObjects135 1 }

dls135_source_mac_address OBJECT-TYPE
    SYNTAX DisplayString
    MAX-ACCESS accessible-for-notify
    STATUS current
    DESCRIPTION
        "Parameter 'source_mac_address' in event DLS.135"
    ::= { dlsEventObjects135 2 }

dls135_dest_mac_address OBJECT-TYPE
    SYNTAX DisplayString
    MAX-ACCESS accessible-for-notify
    STATUS current
    DESCRIPTION
        "Parameter 'dest_mac_address' in event DLS.135"
    ::= { dlsEventObjects135 3 }

dls135_source_sap OBJECT-TYPE
    SYNTAX Integer32
    MAX-ACCESS accessible-for-notify
    STATUS current
    DESCRIPTION
        "Parameter 'source_sap' in event DLS.135"
    ::= { dlsEventObjects135 4 }

dls135_dest_sap OBJECT-TYPE
    SYNTAX Integer32
    MAX-ACCESS accessible-for-notify
    STATUS current
    DESCRIPTION
        "Parameter 'dest_sap' in event DLS.135"
    ::= { dlsEventObjects135 5 }

dlsEventObjects136 OBJECT-IDENTITY
    STATUS current
    DESCRIPTION
        "Event DLS.136
        An LLC request from DLS was not processed by the LLC interface
        module as the handle passed from DLS is bad."
    ::= { dlsEventsGroup 136 }

dls136_llcevent OBJECT-TYPE
    SYNTAX DisplayString
    MAX-ACCESS accessible-for-notify
    STATUS current
    DESCRIPTION
        "Parameter 'llcevent' in event DLS.136"
    ::= { dlsEventObjects136 1 }

dls136_source_mac_address OBJECT-TYPE
    SYNTAX DisplayString
    MAX-ACCESS accessible-for-notify
    STATUS current
    DESCRIPTION
        "Parameter 'source_mac_address' in event DLS.136"
    ::= { dlsEventObjects136 2 }

dls136_dest_mac_address OBJECT-TYPE
    SYNTAX DisplayString
    MAX-ACCESS accessible-for-notify
    STATUS current
    DESCRIPTION
        "Parameter 'dest_mac_address' in event DLS.136"
    ::= { dlsEventObjects136 3 }

dls136_source_sap OBJECT-TYPE
    SYNTAX Integer32
    MAX-ACCESS accessible-for-notify
    STATUS current
    DESCRIPTION
        "Parameter 'source_sap' in event DLS.136"
    ::= { dlsEventObjects136 4 }

dls136_dest_sap OBJECT-TYPE
    SYNTAX Integer32
    MAX-ACCESS accessible-for-notify
    STATUS current
    DESCRIPTION
        "Parameter 'dest_sap' in event DLS.136"
    ::= { dlsEventObjects136 5 }

dlsEventObjects137 OBJECT-IDENTITY
    STATUS current
    DESCRIPTION
        "Event DLS.137
        A START_DL request from DLS to LLC interface module was not
        honored as LLC portion of the DLS is not enabled. This is not
        an error. When a CANUREACH is received, DLS will issue START_DL
        request to data link service interface modules. If they are not
        configured to switch for the SAP or not configured at all, it
        is common to discard such request."
    ::= { dlsEventsGroup 137 }

dls137_source_mac_address OBJECT-TYPE
    SYNTAX DisplayString
    MAX-ACCESS accessible-for-notify
    STATUS current
    DESCRIPTION
        "Parameter 'source_mac_address' in event DLS.137"
    ::= { dlsEventObjects137 1 }

dls137_dest_mac_address OBJECT-TYPE
    SYNTAX DisplayString
    MAX-ACCESS accessible-for-notify
    STATUS current
    DESCRIPTION
        "Parameter 'dest_mac_address' in event DLS.137"
    ::= { dlsEventObjects137 2 }

dls137_source_sap OBJECT-TYPE
    SYNTAX Integer32
    MAX-ACCESS accessible-for-notify
    STATUS current
    DESCRIPTION
        "Parameter 'source_sap' in event DLS.137"
    ::= { dlsEventObjects137 3 }

dls137_dest_sap OBJECT-TYPE
    SYNTAX Integer32
    MAX-ACCESS accessible-for-notify
    STATUS current
    DESCRIPTION
        "Parameter 'dest_sap' in event DLS.137"
    ::= { dlsEventObjects137 4 }

dlsEventObjects138 OBJECT-IDENTITY
    STATUS current
    DESCRIPTION
        "Event DLS.138
        A START_DL request from DLS to LLC interface module was not
        honored as data link station could not be opened with LLC."
    ::= { dlsEventsGroup 138 }

dls138_source_mac_address OBJECT-TYPE
    SYNTAX DisplayString
    MAX-ACCESS accessible-for-notify
    STATUS current
    DESCRIPTION
        "Parameter 'source_mac_address' in event DLS.138"
    ::= { dlsEventObjects138 1 }

dls138_dest_mac_address OBJECT-TYPE
    SYNTAX DisplayString
    MAX-ACCESS accessible-for-notify
    STATUS current
    DESCRIPTION
        "Parameter 'dest_mac_address' in event DLS.138"
    ::= { dlsEventObjects138 2 }

dls138_source_sap OBJECT-TYPE
    SYNTAX Integer32
    MAX-ACCESS accessible-for-notify
    STATUS current
    DESCRIPTION
        "Parameter 'source_sap' in event DLS.138"
    ::= { dlsEventObjects138 3 }

dls138_dest_sap OBJECT-TYPE
    SYNTAX Integer32
    MAX-ACCESS accessible-for-notify
    STATUS current
    DESCRIPTION
        "Parameter 'dest_sap' in event DLS.138"
    ::= { dlsEventObjects138 4 }

dlsEventObjects139 OBJECT-IDENTITY
    STATUS current
    DESCRIPTION
        "Event DLS.139
        When the first XID is received, the real SAPs get resolved.
        During this time, data link station is opened with LLC and
        resources get exchanged from data link station opened with
        NULL SAP. This exchange operation has failed and therefore
        XID is not processed."
    ::= { dlsEventsGroup 139 }

dls139_source_mac_address OBJECT-TYPE
    SYNTAX DisplayString
    MAX-ACCESS accessible-for-notify
    STATUS current
    DESCRIPTION
        "Parameter 'source_mac_address' in event DLS.139"
    ::= { dlsEventObjects139 1 }

dls139_dest_mac_address OBJECT-TYPE
    SYNTAX DisplayString
    MAX-ACCESS accessible-for-notify
    STATUS current
    DESCRIPTION
        "Parameter 'dest_mac_address' in event DLS.139"
    ::= { dlsEventObjects139 2 }

dls139_source_sap OBJECT-TYPE
    SYNTAX Integer32
    MAX-ACCESS accessible-for-notify
    STATUS current
    DESCRIPTION
        "Parameter 'source_sap' in event DLS.139"
    ::= { dlsEventObjects139 3 }

dls139_dest_sap OBJECT-TYPE
    SYNTAX Integer32
    MAX-ACCESS accessible-for-notify
    STATUS current
    DESCRIPTION
        "Parameter 'dest_sap' in event DLS.139"
    ::= { dlsEventObjects139 4 }

dlsEventObjects140 OBJECT-IDENTITY
    STATUS current
    DESCRIPTION
        "Event DLS.140
        When the first XID is received, the real SAPs get resolved.
        During this time, DLS's interface module to LLC verifies the
        SAP for which XID is received. If SAP can not be found or
        can not be opened for some reason, XID processing is
        discontinued."
    ::= { dlsEventsGroup 140 }

dls140_source_mac_address OBJECT-TYPE
    SYNTAX DisplayString
    MAX-ACCESS accessible-for-notify
    STATUS current
    DESCRIPTION
        "Parameter 'source_mac_address' in event DLS.140"
    ::= { dlsEventObjects140 1 }

dls140_dest_mac_address OBJECT-TYPE
    SYNTAX DisplayString
    MAX-ACCESS accessible-for-notify
    STATUS current
    DESCRIPTION
        "Parameter 'dest_mac_address' in event DLS.140"
    ::= { dlsEventObjects140 2 }

dls140_source_sap OBJECT-TYPE
    SYNTAX Integer32
    MAX-ACCESS accessible-for-notify
    STATUS current
    DESCRIPTION
        "Parameter 'source_sap' in event DLS.140"
    ::= { dlsEventObjects140 3 }

dls140_dest_sap OBJECT-TYPE
    SYNTAX Integer32
    MAX-ACCESS accessible-for-notify
    STATUS current
    DESCRIPTION
        "Parameter 'dest_sap' in event DLS.140"
    ::= { dlsEventObjects140 4 }

dlsEventObjects141 OBJECT-IDENTITY
    STATUS current
    DESCRIPTION
        "Event DLS.141
        LLC interface module for the DLS received an event from either
        LLC or DLS."
    ::= { dlsEventsGroup 141 }

dls141_message_type OBJECT-TYPE
    SYNTAX DisplayString
    MAX-ACCESS accessible-for-notify
    STATUS current
    DESCRIPTION
        "Parameter 'message_type' in event DLS.141"
    ::= { dlsEventObjects141 1 }

dls141_source_mac_address OBJECT-TYPE
    SYNTAX DisplayString
    MAX-ACCESS accessible-for-notify
    STATUS current
    DESCRIPTION
        "Parameter 'source_mac_address' in event DLS.141"
    ::= { dlsEventObjects141 2 }

dls141_dest_mac_address OBJECT-TYPE
    SYNTAX DisplayString
    MAX-ACCESS accessible-for-notify
    STATUS current
    DESCRIPTION
        "Parameter 'dest_mac_address' in event DLS.141"
    ::= { dlsEventObjects141 3 }

dls141_source_sap OBJECT-TYPE
    SYNTAX Integer32
    MAX-ACCESS accessible-for-notify
    STATUS current
    DESCRIPTION
        "Parameter 'source_sap' in event DLS.141"
    ::= { dlsEventObjects141 4 }

dls141_dest_sap OBJECT-TYPE
    SYNTAX Integer32
    MAX-ACCESS accessible-for-notify
    STATUS current
    DESCRIPTION
        "Parameter 'dest_sap' in event DLS.141"
    ::= { dlsEventObjects141 5 }

dlsEventObjects142 OBJECT-IDENTITY
    STATUS current
    DESCRIPTION
        "Event DLS.142
        DLS interface to LLC received an event in the bad state."
    ::= { dlsEventsGroup 142 }

dls142_eventname OBJECT-TYPE
    SYNTAX DisplayString
    MAX-ACCESS accessible-for-notify
    STATUS current
    DESCRIPTION
        "Parameter 'eventname' in event DLS.142"
    ::= { dlsEventObjects142 1 }

dls142_statename OBJECT-TYPE
    SYNTAX DisplayString
    MAX-ACCESS accessible-for-notify
    STATUS current
    DESCRIPTION
        "Parameter 'statename' in event DLS.142"
    ::= { dlsEventObjects142 2 }

dls142_source_mac_address OBJECT-TYPE
    SYNTAX DisplayString
    MAX-ACCESS accessible-for-notify
    STATUS current
    DESCRIPTION
        "Parameter 'source_mac_address' in event DLS.142"
    ::= { dlsEventObjects142 3 }

dls142_dest_mac_address OBJECT-TYPE
    SYNTAX DisplayString
    MAX-ACCESS accessible-for-notify
    STATUS current
    DESCRIPTION
        "Parameter 'dest_mac_address' in event DLS.142"
    ::= { dlsEventObjects142 4 }

dls142_source_sap OBJECT-TYPE
    SYNTAX Integer32
    MAX-ACCESS accessible-for-notify
    STATUS current
    DESCRIPTION
        "Parameter 'source_sap' in event DLS.142"
    ::= { dlsEventObjects142 5 }

dls142_dest_sap OBJECT-TYPE
    SYNTAX Integer32
    MAX-ACCESS accessible-for-notify
    STATUS current
    DESCRIPTION
        "Parameter 'dest_sap' in event DLS.142"
    ::= { dlsEventObjects142 6 }

dlsEventObjects143 OBJECT-IDENTITY
    STATUS current
    DESCRIPTION
        "Event DLS.143
        LLC interface module for the DLS is changing state as a
        result of processing an event either from LLC or DLS."
    ::= { dlsEventsGroup 143 }

dls143_oldstate OBJECT-TYPE
    SYNTAX DisplayString
    MAX-ACCESS accessible-for-notify
    STATUS current
    DESCRIPTION
        "Parameter 'oldstate' in event DLS.143"
    ::= { dlsEventObjects143 1 }

dls143_newstate OBJECT-TYPE
    SYNTAX DisplayString
    MAX-ACCESS accessible-for-notify
    STATUS current
    DESCRIPTION
        "Parameter 'newstate' in event DLS.143"
    ::= { dlsEventObjects143 2 }

dls143_source_mac_address OBJECT-TYPE
    SYNTAX DisplayString
    MAX-ACCESS accessible-for-notify
    STATUS current
    DESCRIPTION
        "Parameter 'source_mac_address' in event DLS.143"
    ::= { dlsEventObjects143 3 }

dls143_dest_mac_address OBJECT-TYPE
    SYNTAX DisplayString
    MAX-ACCESS accessible-for-notify
    STATUS current
    DESCRIPTION
        "Parameter 'dest_mac_address' in event DLS.143"
    ::= { dlsEventObjects143 4 }

dls143_source_sap OBJECT-TYPE
    SYNTAX Integer32
    MAX-ACCESS accessible-for-notify
    STATUS current
    DESCRIPTION
        "Parameter 'source_sap' in event DLS.143"
    ::= { dlsEventObjects143 5 }

dls143_dest_sap OBJECT-TYPE
    SYNTAX Integer32
    MAX-ACCESS accessible-for-notify
    STATUS current
    DESCRIPTION
        "Parameter 'dest_sap' in event DLS.143"
    ::= { dlsEventObjects143 6 }

dlsEventObjects144 OBJECT-IDENTITY
    STATUS current
    DESCRIPTION
        "Event DLS.144
        In Multipath bridge environment, it is possible to receive
        multiple responses to the TEST command sent earlier. The
        LLC interface module discards such TEST responses."
    ::= { dlsEventsGroup 144 }

dls144_source_mac_address OBJECT-TYPE
    SYNTAX DisplayString
    MAX-ACCESS accessible-for-notify
    STATUS current
    DESCRIPTION
        "Parameter 'source_mac_address' in event DLS.144"
    ::= { dlsEventObjects144 1 }

dls144_dest_mac_address OBJECT-TYPE
    SYNTAX DisplayString
    MAX-ACCESS accessible-for-notify
    STATUS current
    DESCRIPTION
        "Parameter 'dest_mac_address' in event DLS.144"
    ::= { dlsEventObjects144 2 }

dls144_source_sap OBJECT-TYPE
    SYNTAX Integer32
    MAX-ACCESS accessible-for-notify
    STATUS current
    DESCRIPTION
        "Parameter 'source_sap' in event DLS.144"
    ::= { dlsEventObjects144 3 }

dls144_dest_sap OBJECT-TYPE
    SYNTAX Integer32
    MAX-ACCESS accessible-for-notify
    STATUS current
    DESCRIPTION
        "Parameter 'dest_sap' in event DLS.144"
    ::= { dlsEventObjects144 4 }

dlsEventObjects145 OBJECT-IDENTITY
    STATUS current
    DESCRIPTION
        "Event DLS.145
        When the first XID is received, the real SAPs get resolved.
        The LLC interface module DLS first tries to locate the
        SAP control block for NULL SAP so that it can search for
        an open data link connection within this SAP. The SAP
        control block to NULL SAP could not be found and hence this
        frame does not get processed."
    ::= { dlsEventsGroup 145 }

dls145_source_mac_address OBJECT-TYPE
    SYNTAX DisplayString
    MAX-ACCESS accessible-for-notify
    STATUS current
    DESCRIPTION
        "Parameter 'source_mac_address' in event DLS.145"
    ::= { dlsEventObjects145 1 }

dls145_dest_mac_address OBJECT-TYPE
    SYNTAX DisplayString
    MAX-ACCESS accessible-for-notify
    STATUS current
    DESCRIPTION
        "Parameter 'dest_mac_address' in event DLS.145"
    ::= { dlsEventObjects145 2 }

dls145_source_sap OBJECT-TYPE
    SYNTAX Integer32
    MAX-ACCESS accessible-for-notify
    STATUS current
    DESCRIPTION
        "Parameter 'source_sap' in event DLS.145"
    ::= { dlsEventObjects145 3 }

dls145_dest_sap OBJECT-TYPE
    SYNTAX Integer32
    MAX-ACCESS accessible-for-notify
    STATUS current
    DESCRIPTION
        "Parameter 'dest_sap' in event DLS.145"
    ::= { dlsEventObjects145 4 }

dlsEventObjects146 OBJECT-IDENTITY
    STATUS current
    DESCRIPTION
        "Event DLS.146
        When the first XID is received, the real SAPs get resolved.
        During this time, DLS's interface module to LLC opens a new
        data link connection on the real SAP. Wel, this operation
        failed."
    ::= { dlsEventsGroup 146 }

dls146_source_mac_address OBJECT-TYPE
    SYNTAX DisplayString
    MAX-ACCESS accessible-for-notify
    STATUS current
    DESCRIPTION
        "Parameter 'source_mac_address' in event DLS.146"
    ::= { dlsEventObjects146 1 }

dls146_dest_mac_address OBJECT-TYPE
    SYNTAX DisplayString
    MAX-ACCESS accessible-for-notify
    STATUS current
    DESCRIPTION
        "Parameter 'dest_mac_address' in event DLS.146"
    ::= { dlsEventObjects146 2 }

dls146_source_sap OBJECT-TYPE
    SYNTAX Integer32
    MAX-ACCESS accessible-for-notify
    STATUS current
    DESCRIPTION
        "Parameter 'source_sap' in event DLS.146"
    ::= { dlsEventObjects146 3 }

dls146_dest_sap OBJECT-TYPE
    SYNTAX Integer32
    MAX-ACCESS accessible-for-notify
    STATUS current
    DESCRIPTION
        "Parameter 'dest_sap' in event DLS.146"
    ::= { dlsEventObjects146 4 }

dlsEventObjects147 OBJECT-IDENTITY
    STATUS current
    DESCRIPTION
        "Event DLS.147
        When the first XID is received, the real SAPs get resolved.
        During this time, data link station is opened with LLC and
        resources gets exchanged from data link station opened with
        NULL SAP. This exchange operation has failed and therefore
        XID from LLC is not processed."
    ::= { dlsEventsGroup 147 }

dls147_source_mac_address OBJECT-TYPE
    SYNTAX DisplayString
    MAX-ACCESS accessible-for-notify
    STATUS current
    DESCRIPTION
        "Parameter 'source_mac_address' in event DLS.147"
    ::= { dlsEventObjects147 1 }

dls147_dest_mac_address OBJECT-TYPE
    SYNTAX DisplayString
    MAX-ACCESS accessible-for-notify
    STATUS current
    DESCRIPTION
        "Parameter 'dest_mac_address' in event DLS.147"
    ::= { dlsEventObjects147 2 }

dls147_source_sap OBJECT-TYPE
    SYNTAX Integer32
    MAX-ACCESS accessible-for-notify
    STATUS current
    DESCRIPTION
        "Parameter 'source_sap' in event DLS.147"
    ::= { dlsEventObjects147 3 }

dls147_dest_sap OBJECT-TYPE
    SYNTAX Integer32
    MAX-ACCESS accessible-for-notify
    STATUS current
    DESCRIPTION
        "Parameter 'dest_sap' in event DLS.147"
    ::= { dlsEventObjects147 4 }

dlsEventObjects148 OBJECT-IDENTITY
    STATUS current
    DESCRIPTION
        "Event DLS.148
        The data frames received from the LLC is being discarded by
        the LLC interface module as TCP connection is congested."
    ::= { dlsEventsGroup 148 }

dls148_frametype OBJECT-TYPE
    SYNTAX DisplayString
    MAX-ACCESS accessible-for-notify
    STATUS current
    DESCRIPTION
        "Parameter 'frametype' in event DLS.148"
    ::= { dlsEventObjects148 1 }

dls148_source_mac_address OBJECT-TYPE
    SYNTAX DisplayString
    MAX-ACCESS accessible-for-notify
    STATUS current
    DESCRIPTION
        "Parameter 'source_mac_address' in event DLS.148"
    ::= { dlsEventObjects148 2 }

dls148_dest_mac_address OBJECT-TYPE
    SYNTAX DisplayString
    MAX-ACCESS accessible-for-notify
    STATUS current
    DESCRIPTION
        "Parameter 'dest_mac_address' in event DLS.148"
    ::= { dlsEventObjects148 3 }

dls148_source_sap OBJECT-TYPE
    SYNTAX Integer32
    MAX-ACCESS accessible-for-notify
    STATUS current
    DESCRIPTION
        "Parameter 'source_sap' in event DLS.148"
    ::= { dlsEventObjects148 4 }

dls148_dest_sap OBJECT-TYPE
    SYNTAX Integer32
    MAX-ACCESS accessible-for-notify
    STATUS current
    DESCRIPTION
        "Parameter 'dest_sap' in event DLS.148"
    ::= { dlsEventObjects148 5 }

dlsEventObjects149 OBJECT-IDENTITY
    STATUS current
    DESCRIPTION
        "Event DLS.149
        LLC interface module for the DLS received an event from either
        LLC or DLS."
    ::= { dlsEventsGroup 149 }

dls149_event_type OBJECT-TYPE
    SYNTAX DisplayString
    MAX-ACCESS accessible-for-notify
    STATUS current
    DESCRIPTION
        "Parameter 'event_type' in event DLS.149"
    ::= { dlsEventObjects149 1 }

dls149_source_mac_address OBJECT-TYPE
    SYNTAX DisplayString
    MAX-ACCESS accessible-for-notify
    STATUS current
    DESCRIPTION
        "Parameter 'source_mac_address' in event DLS.149"
    ::= { dlsEventObjects149 2 }

dls149_dest_mac_address OBJECT-TYPE
    SYNTAX DisplayString
    MAX-ACCESS accessible-for-notify
    STATUS current
    DESCRIPTION
        "Parameter 'dest_mac_address' in event DLS.149"
    ::= { dlsEventObjects149 3 }

dls149_source_sap OBJECT-TYPE
    SYNTAX Integer32
    MAX-ACCESS accessible-for-notify
    STATUS current
    DESCRIPTION
        "Parameter 'source_sap' in event DLS.149"
    ::= { dlsEventObjects149 4 }

dls149_dest_sap OBJECT-TYPE
    SYNTAX Integer32
    MAX-ACCESS accessible-for-notify
    STATUS current
    DESCRIPTION
        "Parameter 'dest_sap' in event DLS.149"
    ::= { dlsEventObjects149 5 }

dlsEventObjects150 OBJECT-IDENTITY
    STATUS current
    DESCRIPTION
        "Event DLS.150
        DLS forwarder received a DLC event from the underlying LINK which
        could be LLC or SDLC to either perform some service or as an
        acknowledgement to previously issued command."
    ::= { dlsEventsGroup 150 }

dls150_event_type OBJECT-TYPE
    SYNTAX DisplayString
    MAX-ACCESS accessible-for-notify
    STATUS current
    DESCRIPTION
        "Parameter 'event_type' in event DLS.150"
    ::= { dlsEventObjects150 1 }

dls150_source_mac_address OBJECT-TYPE
    SYNTAX DisplayString
    MAX-ACCESS accessible-for-notify
    STATUS current
    DESCRIPTION
        "Parameter 'source_mac_address' in event DLS.150"
    ::= { dlsEventObjects150 2 }

dls150_dest_mac_address OBJECT-TYPE
    SYNTAX DisplayString
    MAX-ACCESS accessible-for-notify
    STATUS current
    DESCRIPTION
        "Parameter 'dest_mac_address' in event DLS.150"
    ::= { dlsEventObjects150 3 }

dls150_source_sap OBJECT-TYPE
    SYNTAX Integer32
    MAX-ACCESS accessible-for-notify
    STATUS current
    DESCRIPTION
        "Parameter 'source_sap' in event DLS.150"
    ::= { dlsEventObjects150 4 }

dls150_dest_sap OBJECT-TYPE
    SYNTAX Integer32
    MAX-ACCESS accessible-for-notify
    STATUS current
    DESCRIPTION
        "Parameter 'dest_sap' in event DLS.150"
    ::= { dlsEventObjects150 5 }

dlsEventObjects151 OBJECT-IDENTITY
    STATUS current
    DESCRIPTION
        "Event DLS.151
        DLS successfully sent out an SSP message over TCP to its DLS peer."
    ::= { dlsEventsGroup 151 }

dls151_message_type OBJECT-TYPE
    SYNTAX DisplayString
    MAX-ACCESS accessible-for-notify
    STATUS current
    DESCRIPTION
        "Parameter 'message_type' in event DLS.151"
    ::= { dlsEventObjects151 1 }

dls151_ip_address OBJECT-TYPE
    SYNTAX IpAddress
    MAX-ACCESS accessible-for-notify
    STATUS current
    DESCRIPTION
        "Parameter 'ip_address' in event DLS.151"
    ::= { dlsEventObjects151 2 }

dls151_source_mac_address OBJECT-TYPE
    SYNTAX DisplayString
    MAX-ACCESS accessible-for-notify
    STATUS current
    DESCRIPTION
        "Parameter 'source_mac_address' in event DLS.151"
    ::= { dlsEventObjects151 3 }

dls151_dest_mac_address OBJECT-TYPE
    SYNTAX DisplayString
    MAX-ACCESS accessible-for-notify
    STATUS current
    DESCRIPTION
        "Parameter 'dest_mac_address' in event DLS.151"
    ::= { dlsEventObjects151 4 }

dls151_source_sap OBJECT-TYPE
    SYNTAX Integer32
    MAX-ACCESS accessible-for-notify
    STATUS current
    DESCRIPTION
        "Parameter 'source_sap' in event DLS.151"
    ::= { dlsEventObjects151 5 }

dls151_dest_sap OBJECT-TYPE
    SYNTAX Integer32
    MAX-ACCESS accessible-for-notify
    STATUS current
    DESCRIPTION
        "Parameter 'dest_sap' in event DLS.151"
    ::= { dlsEventObjects151 6 }

dlsEventObjects152 OBJECT-IDENTITY
    STATUS current
    DESCRIPTION
        "Event DLS.152
        DLS forwarder received a Switch to Switch Protocol message of over TCP."
    ::= { dlsEventsGroup 152 }

dls152_message_type OBJECT-TYPE
    SYNTAX DisplayString
    MAX-ACCESS accessible-for-notify
    STATUS current
    DESCRIPTION
        "Parameter 'message_type' in event DLS.152"
    ::= { dlsEventObjects152 1 }

dls152_ip_address OBJECT-TYPE
    SYNTAX IpAddress
    MAX-ACCESS accessible-for-notify
    STATUS current
    DESCRIPTION
        "Parameter 'ip_address' in event DLS.152"
    ::= { dlsEventObjects152 2 }

dls152_source_mac_address OBJECT-TYPE
    SYNTAX DisplayString
    MAX-ACCESS accessible-for-notify
    STATUS current
    DESCRIPTION
        "Parameter 'source_mac_address' in event DLS.152"
    ::= { dlsEventObjects152 3 }

dls152_dest_mac_address OBJECT-TYPE
    SYNTAX DisplayString
    MAX-ACCESS accessible-for-notify
    STATUS current
    DESCRIPTION
        "Parameter 'dest_mac_address' in event DLS.152"
    ::= { dlsEventObjects152 4 }

dls152_source_sap OBJECT-TYPE
    SYNTAX Integer32
    MAX-ACCESS accessible-for-notify
    STATUS current
    DESCRIPTION
        "Parameter 'source_sap' in event DLS.152"
    ::= { dlsEventObjects152 5 }

dls152_dest_sap OBJECT-TYPE
    SYNTAX Integer32
    MAX-ACCESS accessible-for-notify
    STATUS current
    DESCRIPTION
        "Parameter 'dest_sap' in event DLS.152"
    ::= { dlsEventObjects152 6 }

dlsEventObjects153 OBJECT-IDENTITY
    STATUS current
    DESCRIPTION
        "Event DLS.153
        A frame received from DLS cloud was successfully sent to an
        LLC end station."
    ::= { dlsEventsGroup 153 }

dls153_frame_type OBJECT-TYPE
    SYNTAX DisplayString
    MAX-ACCESS accessible-for-notify
    STATUS current
    DESCRIPTION
        "Parameter 'frame_type' in event DLS.153"
    ::= { dlsEventObjects153 1 }

dls153_source_mac_address OBJECT-TYPE
    SYNTAX DisplayString
    MAX-ACCESS accessible-for-notify
    STATUS current
    DESCRIPTION
        "Parameter 'source_mac_address' in event DLS.153"
    ::= { dlsEventObjects153 2 }

dls153_dest_mac_address OBJECT-TYPE
    SYNTAX DisplayString
    MAX-ACCESS accessible-for-notify
    STATUS current
    DESCRIPTION
        "Parameter 'dest_mac_address' in event DLS.153"
    ::= { dlsEventObjects153 3 }

dls153_source_sap OBJECT-TYPE
    SYNTAX Integer32
    MAX-ACCESS accessible-for-notify
    STATUS current
    DESCRIPTION
        "Parameter 'source_sap' in event DLS.153"
    ::= { dlsEventObjects153 4 }

dls153_dest_sap OBJECT-TYPE
    SYNTAX Integer32
    MAX-ACCESS accessible-for-notify
    STATUS current
    DESCRIPTION
        "Parameter 'dest_sap' in event DLS.153"
    ::= { dlsEventObjects153 5 }

dlsEventObjects154 OBJECT-IDENTITY
    STATUS current
    DESCRIPTION
        "Event DLS.154
        A frame received from DLS cloud was not successfully sent -
        bridge port not up."
    ::= { dlsEventsGroup 154 }

dls154_frame_type OBJECT-TYPE
    SYNTAX DisplayString
    MAX-ACCESS accessible-for-notify
    STATUS current
    DESCRIPTION
        "Parameter 'frame_type' in event DLS.154"
    ::= { dlsEventObjects154 1 }

dls154_source_mac_address OBJECT-TYPE
    SYNTAX DisplayString
    MAX-ACCESS accessible-for-notify
    STATUS current
    DESCRIPTION
        "Parameter 'source_mac_address' in event DLS.154"
    ::= { dlsEventObjects154 2 }

dls154_dest_mac_address OBJECT-TYPE
    SYNTAX DisplayString
    MAX-ACCESS accessible-for-notify
    STATUS current
    DESCRIPTION
        "Parameter 'dest_mac_address' in event DLS.154"
    ::= { dlsEventObjects154 3 }

dls154_source_sap OBJECT-TYPE
    SYNTAX Integer32
    MAX-ACCESS accessible-for-notify
    STATUS current
    DESCRIPTION
        "Parameter 'source_sap' in event DLS.154"
    ::= { dlsEventObjects154 4 }

dls154_dest_sap OBJECT-TYPE
    SYNTAX Integer32
    MAX-ACCESS accessible-for-notify
    STATUS current
    DESCRIPTION
        "Parameter 'dest_sap' in event DLS.154"
    ::= { dlsEventObjects154 5 }

dlsEventObjects155 OBJECT-IDENTITY
    STATUS current
    DESCRIPTION
        "Event DLS.155
        Due to some problems with TCP connection to its DLS peer, an
        SSP control message could not be sent out."
    ::= { dlsEventsGroup 155 }

dls155_message_type OBJECT-TYPE
    SYNTAX DisplayString
    MAX-ACCESS accessible-for-notify
    STATUS current
    DESCRIPTION
        "Parameter 'message_type' in event DLS.155"
    ::= { dlsEventObjects155 1 }

dls155_ip_address OBJECT-TYPE
    SYNTAX IpAddress
    MAX-ACCESS accessible-for-notify
    STATUS current
    DESCRIPTION
        "Parameter 'ip_address' in event DLS.155"
    ::= { dlsEventObjects155 2 }

dls155_source_mac_address OBJECT-TYPE
    SYNTAX DisplayString
    MAX-ACCESS accessible-for-notify
    STATUS current
    DESCRIPTION
        "Parameter 'source_mac_address' in event DLS.155"
    ::= { dlsEventObjects155 3 }

dls155_dest_mac_address OBJECT-TYPE
    SYNTAX DisplayString
    MAX-ACCESS accessible-for-notify
    STATUS current
    DESCRIPTION
        "Parameter 'dest_mac_address' in event DLS.155"
    ::= { dlsEventObjects155 4 }

dls155_source_sap OBJECT-TYPE
    SYNTAX Integer32
    MAX-ACCESS accessible-for-notify
    STATUS current
    DESCRIPTION
        "Parameter 'source_sap' in event DLS.155"
    ::= { dlsEventObjects155 5 }

dls155_dest_sap OBJECT-TYPE
    SYNTAX Integer32
    MAX-ACCESS accessible-for-notify
    STATUS current
    DESCRIPTION
        "Parameter 'dest_sap' in event DLS.155"
    ::= { dlsEventObjects155 6 }

dlsEventObjects156 OBJECT-IDENTITY
    STATUS current
    DESCRIPTION
        "Event DLS.156
        A session pool has been created for a new DLS connection.
        This pool is used exclusively by this session for data transfer."
    ::= { dlsEventsGroup 156 }

dls156_count OBJECT-TYPE
    SYNTAX Integer32
    MAX-ACCESS accessible-for-notify
    STATUS current
    DESCRIPTION
        "Parameter 'count' in event DLS.156"
    ::= { dlsEventObjects156 1 }

dls156_source_mac_address OBJECT-TYPE
    SYNTAX DisplayString
    MAX-ACCESS accessible-for-notify
    STATUS current
    DESCRIPTION
        "Parameter 'source_mac_address' in event DLS.156"
    ::= { dlsEventObjects156 2 }

dls156_dest_mac_address OBJECT-TYPE
    SYNTAX DisplayString
    MAX-ACCESS accessible-for-notify
    STATUS current
    DESCRIPTION
        "Parameter 'dest_mac_address' in event DLS.156"
    ::= { dlsEventObjects156 3 }

dls156_source_sap OBJECT-TYPE
    SYNTAX Integer32
    MAX-ACCESS accessible-for-notify
    STATUS current
    DESCRIPTION
        "Parameter 'source_sap' in event DLS.156"
    ::= { dlsEventObjects156 4 }

dls156_dest_sap OBJECT-TYPE
    SYNTAX Integer32
    MAX-ACCESS accessible-for-notify
    STATUS current
    DESCRIPTION
        "Parameter 'dest_sap' in event DLS.156"
    ::= { dlsEventObjects156 5 }

dlsEventObjects157 OBJECT-IDENTITY
    STATUS current
    DESCRIPTION
        "Event DLS.157
        The global DLS memory pool has been created. This is used for
        SSP control messages and other non-data transfer related items."
    ::= { dlsEventsGroup 157 }

dls157_type OBJECT-TYPE
    SYNTAX DisplayString
    MAX-ACCESS accessible-for-notify
    STATUS current
    DESCRIPTION
        "Parameter 'type' in event DLS.157"
    ::= { dlsEventObjects157 1 }

dls157_count OBJECT-TYPE
    SYNTAX Integer32
    MAX-ACCESS accessible-for-notify
    STATUS current
    DESCRIPTION
        "Parameter 'count' in event DLS.157"
    ::= { dlsEventObjects157 2 }

dlsEventObjects158 OBJECT-IDENTITY
    STATUS current
    DESCRIPTION
        "Event DLS.158
        There is currently not enough memory available to support a
        new DLS session."
    ::= { dlsEventsGroup 158 }

dls158_count OBJECT-TYPE
    SYNTAX Integer32
    MAX-ACCESS accessible-for-notify
    STATUS current
    DESCRIPTION
        "Parameter 'count' in event DLS.158"
    ::= { dlsEventObjects158 1 }

dls158_source_mac_address OBJECT-TYPE
    SYNTAX DisplayString
    MAX-ACCESS accessible-for-notify
    STATUS current
    DESCRIPTION
        "Parameter 'source_mac_address' in event DLS.158"
    ::= { dlsEventObjects158 2 }

dls158_dest_mac_address OBJECT-TYPE
    SYNTAX DisplayString
    MAX-ACCESS accessible-for-notify
    STATUS current
    DESCRIPTION
        "Parameter 'dest_mac_address' in event DLS.158"
    ::= { dlsEventObjects158 3 }

dls158_source_sap OBJECT-TYPE
    SYNTAX Integer32
    MAX-ACCESS accessible-for-notify
    STATUS current
    DESCRIPTION
        "Parameter 'source_sap' in event DLS.158"
    ::= { dlsEventObjects158 4 }

dls158_dest_sap OBJECT-TYPE
    SYNTAX Integer32
    MAX-ACCESS accessible-for-notify
    STATUS current
    DESCRIPTION
        "Parameter 'dest_sap' in event DLS.158"
    ::= { dlsEventObjects158 5 }

dlsEventObjects159 OBJECT-IDENTITY
    STATUS current
    DESCRIPTION
        "Event DLS.159
        There is not enough memory available to support DLS. DLS has
        been disabled."
    ::= { dlsEventsGroup 159 }

dls159_type OBJECT-TYPE
    SYNTAX DisplayString
    MAX-ACCESS accessible-for-notify
    STATUS current
    DESCRIPTION
        "Parameter 'type' in event DLS.159"
    ::= { dlsEventObjects159 1 }

dls159_count OBJECT-TYPE
    SYNTAX Integer32
    MAX-ACCESS accessible-for-notify
    STATUS current
    DESCRIPTION
        "Parameter 'count' in event DLS.159"
    ::= { dlsEventObjects159 2 }

dlsEventObjects160 OBJECT-IDENTITY
    STATUS current
    DESCRIPTION
        "Event DLS.160
        The DLS session is congested due to either TCP backup, or the
        receipt of a DLS_ENTER_BUSY SSP message. If this happens too
        frequently, consider increasing the amount of memory allocated
        to each DLS session."
    ::= { dlsEventsGroup 160 }

dls160_flow_ctrl_type OBJECT-TYPE
    SYNTAX DisplayString
    MAX-ACCESS accessible-for-notify
    STATUS current
    DESCRIPTION
        "Parameter 'flow_ctrl_type' in event DLS.160"
    ::= { dlsEventObjects160 1 }

dls160_source_mac_address OBJECT-TYPE
    SYNTAX DisplayString
    MAX-ACCESS accessible-for-notify
    STATUS current
    DESCRIPTION
        "Parameter 'source_mac_address' in event DLS.160"
    ::= { dlsEventObjects160 2 }

dls160_dest_mac_address OBJECT-TYPE
    SYNTAX DisplayString
    MAX-ACCESS accessible-for-notify
    STATUS current
    DESCRIPTION
        "Parameter 'dest_mac_address' in event DLS.160"
    ::= { dlsEventObjects160 3 }

dls160_source_sap OBJECT-TYPE
    SYNTAX Integer32
    MAX-ACCESS accessible-for-notify
    STATUS current
    DESCRIPTION
        "Parameter 'source_sap' in event DLS.160"
    ::= { dlsEventObjects160 4 }

dls160_dest_sap OBJECT-TYPE
    SYNTAX Integer32
    MAX-ACCESS accessible-for-notify
    STATUS current
    DESCRIPTION
        "Parameter 'dest_sap' in event DLS.160"
    ::= { dlsEventObjects160 5 }

dlsEventObjects161 OBJECT-IDENTITY
    STATUS current
    DESCRIPTION
        "Event DLS.161
        The total amount of memory allocated by all currently active
        DLS sessions exceeded the amount pre-allocated by the user
        for DLS. As a result, the data links are temporarily being
        quiesced until some of the memory is freed up. If this happens too
        frequently, consider increasing the amount of memory allocated
        to DLSw."
    ::= { dlsEventsGroup 161 }

dls161_pool_type OBJECT-TYPE
    SYNTAX DisplayString
    MAX-ACCESS accessible-for-notify
    STATUS current
    DESCRIPTION
        "Parameter 'pool_type' in event DLS.161"
    ::= { dlsEventObjects161 1 }

dls161_pool_state OBJECT-TYPE
    SYNTAX Integer32
    MAX-ACCESS accessible-for-notify
    STATUS current
    DESCRIPTION
        "Parameter 'pool_state' in event DLS.161"
    ::= { dlsEventObjects161 2 }

dls161_memavail OBJECT-TYPE
    SYNTAX Integer32
    MAX-ACCESS accessible-for-notify
    STATUS current
    DESCRIPTION
        "Parameter 'memavail' in event DLS.161"
    ::= { dlsEventObjects161 3 }

dlsEventObjects162 OBJECT-IDENTITY
    STATUS current
    DESCRIPTION
        "Event DLS.162
        Sufficient memory has been freed up since the last time DLS
        was congested to allow the data links to receive data again."
    ::= { dlsEventsGroup 162 }

dls162_flow_ctrl_type OBJECT-TYPE
    SYNTAX DisplayString
    MAX-ACCESS accessible-for-notify
    STATUS current
    DESCRIPTION
        "Parameter 'flow_ctrl_type' in event DLS.162"
    ::= { dlsEventObjects162 1 }

dls162_source_mac_address OBJECT-TYPE
    SYNTAX DisplayString
    MAX-ACCESS accessible-for-notify
    STATUS current
    DESCRIPTION
        "Parameter 'source_mac_address' in event DLS.162"
    ::= { dlsEventObjects162 2 }

dls162_dest_mac_address OBJECT-TYPE
    SYNTAX DisplayString
    MAX-ACCESS accessible-for-notify
    STATUS current
    DESCRIPTION
        "Parameter 'dest_mac_address' in event DLS.162"
    ::= { dlsEventObjects162 3 }

dls162_source_sap OBJECT-TYPE
    SYNTAX Integer32
    MAX-ACCESS accessible-for-notify
    STATUS current
    DESCRIPTION
        "Parameter 'source_sap' in event DLS.162"
    ::= { dlsEventObjects162 4 }

dls162_dest_sap OBJECT-TYPE
    SYNTAX Integer32
    MAX-ACCESS accessible-for-notify
    STATUS current
    DESCRIPTION
        "Parameter 'dest_sap' in event DLS.162"
    ::= { dlsEventObjects162 5 }

dlsEventObjects163 OBJECT-IDENTITY
    STATUS current
    DESCRIPTION
        "Event DLS.163
        Sufficient memory has been freed up since the last time DLS
        was congested to allow the data links to receive data again."
    ::= { dlsEventsGroup 163 }

dls163_pool_type OBJECT-TYPE
    SYNTAX DisplayString
    MAX-ACCESS accessible-for-notify
    STATUS current
    DESCRIPTION
        "Parameter 'pool_type' in event DLS.163"
    ::= { dlsEventObjects163 1 }

dls163_pool_state OBJECT-TYPE
    SYNTAX Integer32
    MAX-ACCESS accessible-for-notify
    STATUS current
    DESCRIPTION
        "Parameter 'pool_state' in event DLS.163"
    ::= { dlsEventObjects163 2 }

dls163_memavail OBJECT-TYPE
    SYNTAX Integer32
    MAX-ACCESS accessible-for-notify
    STATUS current
    DESCRIPTION
        "Parameter 'memavail' in event DLS.163"
    ::= { dlsEventObjects163 3 }

dlsEventObjects164 OBJECT-IDENTITY
    STATUS current
    DESCRIPTION
        "Event DLS.164
        No buffer could be obtained for copying a data buffer for
        queueing while the transport is congested. The existing
        device buffer is queued."
    ::= { dlsEventsGroup 164 }

dls164_source_mac_address OBJECT-TYPE
    SYNTAX DisplayString
    MAX-ACCESS accessible-for-notify
    STATUS current
    DESCRIPTION
        "Parameter 'source_mac_address' in event DLS.164"
    ::= { dlsEventObjects164 1 }

dls164_dest_mac_address OBJECT-TYPE
    SYNTAX DisplayString
    MAX-ACCESS accessible-for-notify
    STATUS current
    DESCRIPTION
        "Parameter 'dest_mac_address' in event DLS.164"
    ::= { dlsEventObjects164 2 }

dls164_source_sap OBJECT-TYPE
    SYNTAX Integer32
    MAX-ACCESS accessible-for-notify
    STATUS current
    DESCRIPTION
        "Parameter 'source_sap' in event DLS.164"
    ::= { dlsEventObjects164 3 }

dls164_dest_sap OBJECT-TYPE
    SYNTAX Integer32
    MAX-ACCESS accessible-for-notify
    STATUS current
    DESCRIPTION
        "Parameter 'dest_sap' in event DLS.164"
    ::= { dlsEventObjects164 4 }

dlsEventObjects165 OBJECT-IDENTITY
    STATUS current
    DESCRIPTION
        "Event DLS.165
        All buffers have been returned to a DLSw session pool after
        the DLSw session has been closed. The pool may now be removed."
    ::= { dlsEventsGroup 165 }

dls165_source_mac_address OBJECT-TYPE
    SYNTAX DisplayString
    MAX-ACCESS accessible-for-notify
    STATUS current
    DESCRIPTION
        "Parameter 'source_mac_address' in event DLS.165"
    ::= { dlsEventObjects165 1 }

dls165_dest_mac_address OBJECT-TYPE
    SYNTAX DisplayString
    MAX-ACCESS accessible-for-notify
    STATUS current
    DESCRIPTION
        "Parameter 'dest_mac_address' in event DLS.165"
    ::= { dlsEventObjects165 2 }

dls165_source_sap OBJECT-TYPE
    SYNTAX Integer32
    MAX-ACCESS accessible-for-notify
    STATUS current
    DESCRIPTION
        "Parameter 'source_sap' in event DLS.165"
    ::= { dlsEventObjects165 3 }

dls165_dest_sap OBJECT-TYPE
    SYNTAX Integer32
    MAX-ACCESS accessible-for-notify
    STATUS current
    DESCRIPTION
        "Parameter 'dest_sap' in event DLS.165"
    ::= { dlsEventObjects165 4 }

dlsEventObjects166 OBJECT-IDENTITY
    STATUS current
    DESCRIPTION
        "Event DLS.166
        DLS forwarder received a Switch to Switch Protocol message of
        CANUREACH over TCP."
    ::= { dlsEventsGroup 166 }

dls166_ip_address OBJECT-TYPE
    SYNTAX IpAddress
    MAX-ACCESS accessible-for-notify
    STATUS current
    DESCRIPTION
        "Parameter 'ip_address' in event DLS.166"
    ::= { dlsEventObjects166 1 }

dls166_source_mac_address OBJECT-TYPE
    SYNTAX DisplayString
    MAX-ACCESS accessible-for-notify
    STATUS current
    DESCRIPTION
        "Parameter 'source_mac_address' in event DLS.166"
    ::= { dlsEventObjects166 2 }

dls166_dest_mac_address OBJECT-TYPE
    SYNTAX DisplayString
    MAX-ACCESS accessible-for-notify
    STATUS current
    DESCRIPTION
        "Parameter 'dest_mac_address' in event DLS.166"
    ::= { dlsEventObjects166 3 }

dls166_source_sap OBJECT-TYPE
    SYNTAX Integer32
    MAX-ACCESS accessible-for-notify
    STATUS current
    DESCRIPTION
        "Parameter 'source_sap' in event DLS.166"
    ::= { dlsEventObjects166 4 }

dls166_dest_sap OBJECT-TYPE
    SYNTAX Integer32
    MAX-ACCESS accessible-for-notify
    STATUS current
    DESCRIPTION
        "Parameter 'dest_sap' in event DLS.166"
    ::= { dlsEventObjects166 5 }

dlsEventObjects167 OBJECT-IDENTITY
    STATUS current
    DESCRIPTION
        "Event DLS.167
        DLS forwarder received a Switch to Switch Protocol message of
        ICANREACH over TCP."
    ::= { dlsEventsGroup 167 }

dls167_ip_address OBJECT-TYPE
    SYNTAX IpAddress
    MAX-ACCESS accessible-for-notify
    STATUS current
    DESCRIPTION
        "Parameter 'ip_address' in event DLS.167"
    ::= { dlsEventObjects167 1 }

dls167_source_mac_address OBJECT-TYPE
    SYNTAX DisplayString
    MAX-ACCESS accessible-for-notify
    STATUS current
    DESCRIPTION
        "Parameter 'source_mac_address' in event DLS.167"
    ::= { dlsEventObjects167 2 }

dls167_dest_mac_address OBJECT-TYPE
    SYNTAX DisplayString
    MAX-ACCESS accessible-for-notify
    STATUS current
    DESCRIPTION
        "Parameter 'dest_mac_address' in event DLS.167"
    ::= { dlsEventObjects167 3 }

dls167_source_sap OBJECT-TYPE
    SYNTAX Integer32
    MAX-ACCESS accessible-for-notify
    STATUS current
    DESCRIPTION
        "Parameter 'source_sap' in event DLS.167"
    ::= { dlsEventObjects167 4 }

dls167_dest_sap OBJECT-TYPE
    SYNTAX Integer32
    MAX-ACCESS accessible-for-notify
    STATUS current
    DESCRIPTION
        "Parameter 'dest_sap' in event DLS.167"
    ::= { dlsEventObjects167 5 }

dlsEventObjects168 OBJECT-IDENTITY
    STATUS current
    DESCRIPTION
        "Event DLS.168
        DLS forwarder received a Switch to Switch Protocol message of
        REACHACK over TCP."
    ::= { dlsEventsGroup 168 }

dls168_ip_address OBJECT-TYPE
    SYNTAX IpAddress
    MAX-ACCESS accessible-for-notify
    STATUS current
    DESCRIPTION
        "Parameter 'ip_address' in event DLS.168"
    ::= { dlsEventObjects168 1 }

dls168_source_mac_address OBJECT-TYPE
    SYNTAX DisplayString
    MAX-ACCESS accessible-for-notify
    STATUS current
    DESCRIPTION
        "Parameter 'source_mac_address' in event DLS.168"
    ::= { dlsEventObjects168 2 }

dls168_dest_mac_address OBJECT-TYPE
    SYNTAX DisplayString
    MAX-ACCESS accessible-for-notify
    STATUS current
    DESCRIPTION
        "Parameter 'dest_mac_address' in event DLS.168"
    ::= { dlsEventObjects168 3 }

dls168_source_sap OBJECT-TYPE
    SYNTAX Integer32
    MAX-ACCESS accessible-for-notify
    STATUS current
    DESCRIPTION
        "Parameter 'source_sap' in event DLS.168"
    ::= { dlsEventObjects168 4 }

dls168_dest_sap OBJECT-TYPE
    SYNTAX Integer32
    MAX-ACCESS accessible-for-notify
    STATUS current
    DESCRIPTION
        "Parameter 'dest_sap' in event DLS.168"
    ::= { dlsEventObjects168 5 }

dlsEventObjects169 OBJECT-IDENTITY
    STATUS current
    DESCRIPTION
        "Event DLS.169
        DLS forwarder received a Switch to Switch Protocol message of
        XIDFRAME over TCP."
    ::= { dlsEventsGroup 169 }

dls169_ip_address OBJECT-TYPE
    SYNTAX IpAddress
    MAX-ACCESS accessible-for-notify
    STATUS current
    DESCRIPTION
        "Parameter 'ip_address' in event DLS.169"
    ::= { dlsEventObjects169 1 }

dls169_source_mac_address OBJECT-TYPE
    SYNTAX DisplayString
    MAX-ACCESS accessible-for-notify
    STATUS current
    DESCRIPTION
        "Parameter 'source_mac_address' in event DLS.169"
    ::= { dlsEventObjects169 2 }

dls169_dest_mac_address OBJECT-TYPE
    SYNTAX DisplayString
    MAX-ACCESS accessible-for-notify
    STATUS current
    DESCRIPTION
        "Parameter 'dest_mac_address' in event DLS.169"
    ::= { dlsEventObjects169 3 }

dls169_source_sap OBJECT-TYPE
    SYNTAX Integer32
    MAX-ACCESS accessible-for-notify
    STATUS current
    DESCRIPTION
        "Parameter 'source_sap' in event DLS.169"
    ::= { dlsEventObjects169 4 }

dls169_dest_sap OBJECT-TYPE
    SYNTAX Integer32
    MAX-ACCESS accessible-for-notify
    STATUS current
    DESCRIPTION
        "Parameter 'dest_sap' in event DLS.169"
    ::= { dlsEventObjects169 5 }

dlsEventObjects170 OBJECT-IDENTITY
    STATUS current
    DESCRIPTION
        "Event DLS.170
        DLS forwarder received a Switch to Switch Protocol message of
        DGRMFRAME over TCP."
    ::= { dlsEventsGroup 170 }

dls170_ip_address OBJECT-TYPE
    SYNTAX IpAddress
    MAX-ACCESS accessible-for-notify
    STATUS current
    DESCRIPTION
        "Parameter 'ip_address' in event DLS.170"
    ::= { dlsEventObjects170 1 }

dls170_source_mac_address OBJECT-TYPE
    SYNTAX DisplayString
    MAX-ACCESS accessible-for-notify
    STATUS current
    DESCRIPTION
        "Parameter 'source_mac_address' in event DLS.170"
    ::= { dlsEventObjects170 2 }

dls170_dest_mac_address OBJECT-TYPE
    SYNTAX DisplayString
    MAX-ACCESS accessible-for-notify
    STATUS current
    DESCRIPTION
        "Parameter 'dest_mac_address' in event DLS.170"
    ::= { dlsEventObjects170 3 }

dls170_source_sap OBJECT-TYPE
    SYNTAX Integer32
    MAX-ACCESS accessible-for-notify
    STATUS current
    DESCRIPTION
        "Parameter 'source_sap' in event DLS.170"
    ::= { dlsEventObjects170 4 }

dls170_dest_sap OBJECT-TYPE
    SYNTAX Integer32
    MAX-ACCESS accessible-for-notify
    STATUS current
    DESCRIPTION
        "Parameter 'dest_sap' in event DLS.170"
    ::= { dlsEventObjects170 5 }

dlsEventObjects171 OBJECT-IDENTITY
    STATUS current
    DESCRIPTION
        "Event DLS.171
        DLS forwarder received a Switch to Switch Protocol message of
        CONTACT over TCP."
    ::= { dlsEventsGroup 171 }

dls171_ip_address OBJECT-TYPE
    SYNTAX IpAddress
    MAX-ACCESS accessible-for-notify
    STATUS current
    DESCRIPTION
        "Parameter 'ip_address' in event DLS.171"
    ::= { dlsEventObjects171 1 }

dls171_source_mac_address OBJECT-TYPE
    SYNTAX DisplayString
    MAX-ACCESS accessible-for-notify
    STATUS current
    DESCRIPTION
        "Parameter 'source_mac_address' in event DLS.171"
    ::= { dlsEventObjects171 2 }

dls171_dest_mac_address OBJECT-TYPE
    SYNTAX DisplayString
    MAX-ACCESS accessible-for-notify
    STATUS current
    DESCRIPTION
        "Parameter 'dest_mac_address' in event DLS.171"
    ::= { dlsEventObjects171 3 }

dls171_source_sap OBJECT-TYPE
    SYNTAX Integer32
    MAX-ACCESS accessible-for-notify
    STATUS current
    DESCRIPTION
        "Parameter 'source_sap' in event DLS.171"
    ::= { dlsEventObjects171 4 }

dls171_dest_sap OBJECT-TYPE
    SYNTAX Integer32
    MAX-ACCESS accessible-for-notify
    STATUS current
    DESCRIPTION
        "Parameter 'dest_sap' in event DLS.171"
    ::= { dlsEventObjects171 5 }

dlsEventObjects172 OBJECT-IDENTITY
    STATUS current
    DESCRIPTION
        "Event DLS.172
        DLS forwarder received a Switch to Switch Protocol message of
        CONTACTED over TCP."
    ::= { dlsEventsGroup 172 }

dls172_ip_address OBJECT-TYPE
    SYNTAX IpAddress
    MAX-ACCESS accessible-for-notify
    STATUS current
    DESCRIPTION
        "Parameter 'ip_address' in event DLS.172"
    ::= { dlsEventObjects172 1 }

dls172_source_mac_address OBJECT-TYPE
    SYNTAX DisplayString
    MAX-ACCESS accessible-for-notify
    STATUS current
    DESCRIPTION
        "Parameter 'source_mac_address' in event DLS.172"
    ::= { dlsEventObjects172 2 }

dls172_dest_mac_address OBJECT-TYPE
    SYNTAX DisplayString
    MAX-ACCESS accessible-for-notify
    STATUS current
    DESCRIPTION
        "Parameter 'dest_mac_address' in event DLS.172"
    ::= { dlsEventObjects172 3 }

dls172_source_sap OBJECT-TYPE
    SYNTAX Integer32
    MAX-ACCESS accessible-for-notify
    STATUS current
    DESCRIPTION
        "Parameter 'source_sap' in event DLS.172"
    ::= { dlsEventObjects172 4 }

dls172_dest_sap OBJECT-TYPE
    SYNTAX Integer32
    MAX-ACCESS accessible-for-notify
    STATUS current
    DESCRIPTION
        "Parameter 'dest_sap' in event DLS.172"
    ::= { dlsEventObjects172 5 }

dlsEventObjects173 OBJECT-IDENTITY
    STATUS current
    DESCRIPTION
        "Event DLS.173
        DLS forwarder received a Switch to Switch Protocol message of
        DATAFRAME over TCP."
    ::= { dlsEventsGroup 173 }

dls173_ip_address OBJECT-TYPE
    SYNTAX IpAddress
    MAX-ACCESS accessible-for-notify
    STATUS current
    DESCRIPTION
        "Parameter 'ip_address' in event DLS.173"
    ::= { dlsEventObjects173 1 }

dls173_source_mac_address OBJECT-TYPE
    SYNTAX DisplayString
    MAX-ACCESS accessible-for-notify
    STATUS current
    DESCRIPTION
        "Parameter 'source_mac_address' in event DLS.173"
    ::= { dlsEventObjects173 2 }

dls173_dest_mac_address OBJECT-TYPE
    SYNTAX DisplayString
    MAX-ACCESS accessible-for-notify
    STATUS current
    DESCRIPTION
        "Parameter 'dest_mac_address' in event DLS.173"
    ::= { dlsEventObjects173 3 }

dls173_source_sap OBJECT-TYPE
    SYNTAX Integer32
    MAX-ACCESS accessible-for-notify
    STATUS current
    DESCRIPTION
        "Parameter 'source_sap' in event DLS.173"
    ::= { dlsEventObjects173 4 }

dls173_dest_sap OBJECT-TYPE
    SYNTAX Integer32
    MAX-ACCESS accessible-for-notify
    STATUS current
    DESCRIPTION
        "Parameter 'dest_sap' in event DLS.173"
    ::= { dlsEventObjects173 5 }

dlsEventObjects174 OBJECT-IDENTITY
    STATUS current
    DESCRIPTION
        "Event DLS.174
        DLS forwarder received a Switch to Switch Protocol message of
        RESTART_DL over TCP."
    ::= { dlsEventsGroup 174 }

dls174_ip_address OBJECT-TYPE
    SYNTAX IpAddress
    MAX-ACCESS accessible-for-notify
    STATUS current
    DESCRIPTION
        "Parameter 'ip_address' in event DLS.174"
    ::= { dlsEventObjects174 1 }

dls174_source_mac_address OBJECT-TYPE
    SYNTAX DisplayString
    MAX-ACCESS accessible-for-notify
    STATUS current
    DESCRIPTION
        "Parameter 'source_mac_address' in event DLS.174"
    ::= { dlsEventObjects174 2 }

dls174_dest_mac_address OBJECT-TYPE
    SYNTAX DisplayString
    MAX-ACCESS accessible-for-notify
    STATUS current
    DESCRIPTION
        "Parameter 'dest_mac_address' in event DLS.174"
    ::= { dlsEventObjects174 3 }

dls174_source_sap OBJECT-TYPE
    SYNTAX Integer32
    MAX-ACCESS accessible-for-notify
    STATUS current
    DESCRIPTION
        "Parameter 'source_sap' in event DLS.174"
    ::= { dlsEventObjects174 4 }

dls174_dest_sap OBJECT-TYPE
    SYNTAX Integer32
    MAX-ACCESS accessible-for-notify
    STATUS current
    DESCRIPTION
        "Parameter 'dest_sap' in event DLS.174"
    ::= { dlsEventObjects174 5 }

dlsEventObjects175 OBJECT-IDENTITY
    STATUS current
    DESCRIPTION
        "Event DLS.175
        DLS forwarder received a Switch to Switch Protocol message of
        RESTARTED over TCP."
    ::= { dlsEventsGroup 175 }

dls175_ip_address OBJECT-TYPE
    SYNTAX IpAddress
    MAX-ACCESS accessible-for-notify
    STATUS current
    DESCRIPTION
        "Parameter 'ip_address' in event DLS.175"
    ::= { dlsEventObjects175 1 }

dls175_source_mac_address OBJECT-TYPE
    SYNTAX DisplayString
    MAX-ACCESS accessible-for-notify
    STATUS current
    DESCRIPTION
        "Parameter 'source_mac_address' in event DLS.175"
    ::= { dlsEventObjects175 2 }

dls175_dest_mac_address OBJECT-TYPE
    SYNTAX DisplayString
    MAX-ACCESS accessible-for-notify
    STATUS current
    DESCRIPTION
        "Parameter 'dest_mac_address' in event DLS.175"
    ::= { dlsEventObjects175 3 }

dls175_source_sap OBJECT-TYPE
    SYNTAX Integer32
    MAX-ACCESS accessible-for-notify
    STATUS current
    DESCRIPTION
        "Parameter 'source_sap' in event DLS.175"
    ::= { dlsEventObjects175 4 }

dls175_dest_sap OBJECT-TYPE
    SYNTAX Integer32
    MAX-ACCESS accessible-for-notify
    STATUS current
    DESCRIPTION
        "Parameter 'dest_sap' in event DLS.175"
    ::= { dlsEventObjects175 5 }

dlsEventObjects176 OBJECT-IDENTITY
    STATUS current
    DESCRIPTION
        "Event DLS.176
        DLS forwarder received a Switch to Switch Protocol message of
        HALT_DL over TCP."
    ::= { dlsEventsGroup 176 }

dls176_ip_address OBJECT-TYPE
    SYNTAX IpAddress
    MAX-ACCESS accessible-for-notify
    STATUS current
    DESCRIPTION
        "Parameter 'ip_address' in event DLS.176"
    ::= { dlsEventObjects176 1 }

dls176_source_mac_address OBJECT-TYPE
    SYNTAX DisplayString
    MAX-ACCESS accessible-for-notify
    STATUS current
    DESCRIPTION
        "Parameter 'source_mac_address' in event DLS.176"
    ::= { dlsEventObjects176 2 }

dls176_dest_mac_address OBJECT-TYPE
    SYNTAX DisplayString
    MAX-ACCESS accessible-for-notify
    STATUS current
    DESCRIPTION
        "Parameter 'dest_mac_address' in event DLS.176"
    ::= { dlsEventObjects176 3 }

dls176_source_sap OBJECT-TYPE
    SYNTAX Integer32
    MAX-ACCESS accessible-for-notify
    STATUS current
    DESCRIPTION
        "Parameter 'source_sap' in event DLS.176"
    ::= { dlsEventObjects176 4 }

dls176_dest_sap OBJECT-TYPE
    SYNTAX Integer32
    MAX-ACCESS accessible-for-notify
    STATUS current
    DESCRIPTION
        "Parameter 'dest_sap' in event DLS.176"
    ::= { dlsEventObjects176 5 }

dlsEventObjects177 OBJECT-IDENTITY
    STATUS current
    DESCRIPTION
        "Event DLS.177
        DLS forwarder received a Switch to Switch Protocol message of
        DL_HALTED over TCP."
    ::= { dlsEventsGroup 177 }

dls177_ip_address OBJECT-TYPE
    SYNTAX IpAddress
    MAX-ACCESS accessible-for-notify
    STATUS current
    DESCRIPTION
        "Parameter 'ip_address' in event DLS.177"
    ::= { dlsEventObjects177 1 }

dls177_source_mac_address OBJECT-TYPE
    SYNTAX DisplayString
    MAX-ACCESS accessible-for-notify
    STATUS current
    DESCRIPTION
        "Parameter 'source_mac_address' in event DLS.177"
    ::= { dlsEventObjects177 2 }

dls177_dest_mac_address OBJECT-TYPE
    SYNTAX DisplayString
    MAX-ACCESS accessible-for-notify
    STATUS current
    DESCRIPTION
        "Parameter 'dest_mac_address' in event DLS.177"
    ::= { dlsEventObjects177 3 }

dls177_source_sap OBJECT-TYPE
    SYNTAX Integer32
    MAX-ACCESS accessible-for-notify
    STATUS current
    DESCRIPTION
        "Parameter 'source_sap' in event DLS.177"
    ::= { dlsEventObjects177 4 }

dls177_dest_sap OBJECT-TYPE
    SYNTAX Integer32
    MAX-ACCESS accessible-for-notify
    STATUS current
    DESCRIPTION
        "Parameter 'dest_sap' in event DLS.177"
    ::= { dlsEventObjects177 5 }

dlsEventObjects178 OBJECT-IDENTITY
    STATUS current
    DESCRIPTION
        "Event DLS.178
        DLS forwarder received a Switch to Switch Protocol message of
        INFOFRAME over TCP."
    ::= { dlsEventsGroup 178 }

dls178_ip_address OBJECT-TYPE
    SYNTAX IpAddress
    MAX-ACCESS accessible-for-notify
    STATUS current
    DESCRIPTION
        "Parameter 'ip_address' in event DLS.178"
    ::= { dlsEventObjects178 1 }

dls178_source_mac_address OBJECT-TYPE
    SYNTAX DisplayString
    MAX-ACCESS accessible-for-notify
    STATUS current
    DESCRIPTION
        "Parameter 'source_mac_address' in event DLS.178"
    ::= { dlsEventObjects178 2 }

dls178_dest_mac_address OBJECT-TYPE
    SYNTAX DisplayString
    MAX-ACCESS accessible-for-notify
    STATUS current
    DESCRIPTION
        "Parameter 'dest_mac_address' in event DLS.178"
    ::= { dlsEventObjects178 3 }

dls178_source_sap OBJECT-TYPE
    SYNTAX Integer32
    MAX-ACCESS accessible-for-notify
    STATUS current
    DESCRIPTION
        "Parameter 'source_sap' in event DLS.178"
    ::= { dlsEventObjects178 4 }

dls178_dest_sap OBJECT-TYPE
    SYNTAX Integer32
    MAX-ACCESS accessible-for-notify
    STATUS current
    DESCRIPTION
        "Parameter 'dest_sap' in event DLS.178"
    ::= { dlsEventObjects178 5 }

dlsEventObjects179 OBJECT-IDENTITY
    STATUS current
    DESCRIPTION
        "Event DLS.179
        DLS forwarder received a Switch to Switch Protocol message of
        ENTER_BUSY over TCP."
    ::= { dlsEventsGroup 179 }

dls179_ip_address OBJECT-TYPE
    SYNTAX IpAddress
    MAX-ACCESS accessible-for-notify
    STATUS current
    DESCRIPTION
        "Parameter 'ip_address' in event DLS.179"
    ::= { dlsEventObjects179 1 }

dls179_source_mac_address OBJECT-TYPE
    SYNTAX DisplayString
    MAX-ACCESS accessible-for-notify
    STATUS current
    DESCRIPTION
        "Parameter 'source_mac_address' in event DLS.179"
    ::= { dlsEventObjects179 2 }

dls179_dest_mac_address OBJECT-TYPE
    SYNTAX DisplayString
    MAX-ACCESS accessible-for-notify
    STATUS current
    DESCRIPTION
        "Parameter 'dest_mac_address' in event DLS.179"
    ::= { dlsEventObjects179 3 }

dls179_source_sap OBJECT-TYPE
    SYNTAX Integer32
    MAX-ACCESS accessible-for-notify
    STATUS current
    DESCRIPTION
        "Parameter 'source_sap' in event DLS.179"
    ::= { dlsEventObjects179 4 }

dls179_dest_sap OBJECT-TYPE
    SYNTAX Integer32
    MAX-ACCESS accessible-for-notify
    STATUS current
    DESCRIPTION
        "Parameter 'dest_sap' in event DLS.179"
    ::= { dlsEventObjects179 5 }

dlsEventObjects180 OBJECT-IDENTITY
    STATUS current
    DESCRIPTION
        "Event DLS.180
        DLS forwarder received a Switch to Switch Protocol message of
        EXIT_BUSY over TCP."
    ::= { dlsEventsGroup 180 }

dls180_ip_address OBJECT-TYPE
    SYNTAX IpAddress
    MAX-ACCESS accessible-for-notify
    STATUS current
    DESCRIPTION
        "Parameter 'ip_address' in event DLS.180"
    ::= { dlsEventObjects180 1 }

dls180_source_mac_address OBJECT-TYPE
    SYNTAX DisplayString
    MAX-ACCESS accessible-for-notify
    STATUS current
    DESCRIPTION
        "Parameter 'source_mac_address' in event DLS.180"
    ::= { dlsEventObjects180 2 }

dls180_dest_mac_address OBJECT-TYPE
    SYNTAX DisplayString
    MAX-ACCESS accessible-for-notify
    STATUS current
    DESCRIPTION
        "Parameter 'dest_mac_address' in event DLS.180"
    ::= { dlsEventObjects180 3 }

dls180_source_sap OBJECT-TYPE
    SYNTAX Integer32
    MAX-ACCESS accessible-for-notify
    STATUS current
    DESCRIPTION
        "Parameter 'source_sap' in event DLS.180"
    ::= { dlsEventObjects180 4 }

dls180_dest_sap OBJECT-TYPE
    SYNTAX Integer32
    MAX-ACCESS accessible-for-notify
    STATUS current
    DESCRIPTION
        "Parameter 'dest_sap' in event DLS.180"
    ::= { dlsEventObjects180 5 }

dlsEventObjects181 OBJECT-IDENTITY
    STATUS current
    DESCRIPTION
        "Event DLS.181
        DLS forwarder received a Switch to Switch Protocol message of
        HALT_DL_NOACK over TCP."
    ::= { dlsEventsGroup 181 }

dls181_ip_address OBJECT-TYPE
    SYNTAX IpAddress
    MAX-ACCESS accessible-for-notify
    STATUS current
    DESCRIPTION
        "Parameter 'ip_address' in event DLS.181"
    ::= { dlsEventObjects181 1 }

dls181_source_mac_address OBJECT-TYPE
    SYNTAX DisplayString
    MAX-ACCESS accessible-for-notify
    STATUS current
    DESCRIPTION
        "Parameter 'source_mac_address' in event DLS.181"
    ::= { dlsEventObjects181 2 }

dls181_dest_mac_address OBJECT-TYPE
    SYNTAX DisplayString
    MAX-ACCESS accessible-for-notify
    STATUS current
    DESCRIPTION
        "Parameter 'dest_mac_address' in event DLS.181"
    ::= { dlsEventObjects181 3 }

dls181_source_sap OBJECT-TYPE
    SYNTAX Integer32
    MAX-ACCESS accessible-for-notify
    STATUS current
    DESCRIPTION
        "Parameter 'source_sap' in event DLS.181"
    ::= { dlsEventObjects181 4 }

dls181_dest_sap OBJECT-TYPE
    SYNTAX Integer32
    MAX-ACCESS accessible-for-notify
    STATUS current
    DESCRIPTION
        "Parameter 'dest_sap' in event DLS.181"
    ::= { dlsEventObjects181 5 }

dlsEventObjects182 OBJECT-IDENTITY
    STATUS current
    DESCRIPTION
        "Event DLS.182
        DLS forwarder received a Switch to Switch Protocol message of
        IAMOKAY over TCP."
    ::= { dlsEventsGroup 182 }

dls182_ip_address OBJECT-TYPE
    SYNTAX IpAddress
    MAX-ACCESS accessible-for-notify
    STATUS current
    DESCRIPTION
        "Parameter 'ip_address' in event DLS.182"
    ::= { dlsEventObjects182 1 }

dlsEventObjects183 OBJECT-IDENTITY
    STATUS current
    DESCRIPTION
        "Event DLS.183
        DLS forwarder received an unrecognized Switch to Switch Protocol
        message over TCP."
    ::= { dlsEventsGroup 183 }

dls183_ip_address OBJECT-TYPE
    SYNTAX IpAddress
    MAX-ACCESS accessible-for-notify
    STATUS current
    DESCRIPTION
        "Parameter 'ip_address' in event DLS.183"
    ::= { dlsEventObjects183 1 }

dls183_source_mac_address OBJECT-TYPE
    SYNTAX DisplayString
    MAX-ACCESS accessible-for-notify
    STATUS current
    DESCRIPTION
        "Parameter 'source_mac_address' in event DLS.183"
    ::= { dlsEventObjects183 2 }

dls183_dest_mac_address OBJECT-TYPE
    SYNTAX DisplayString
    MAX-ACCESS accessible-for-notify
    STATUS current
    DESCRIPTION
        "Parameter 'dest_mac_address' in event DLS.183"
    ::= { dlsEventObjects183 3 }

dls183_source_sap OBJECT-TYPE
    SYNTAX Integer32
    MAX-ACCESS accessible-for-notify
    STATUS current
    DESCRIPTION
        "Parameter 'source_sap' in event DLS.183"
    ::= { dlsEventObjects183 4 }

dls183_dest_sap OBJECT-TYPE
    SYNTAX Integer32
    MAX-ACCESS accessible-for-notify
    STATUS current
    DESCRIPTION
        "Parameter 'dest_sap' in event DLS.183"
    ::= { dlsEventObjects183 5 }

dlsEventObjects184 OBJECT-IDENTITY
    STATUS current
    DESCRIPTION
        "Event DLS.184
        DLS forwarder received a DLC_CONTACTED event from the underlying
        data link which could be LLC or SDLC."
    ::= { dlsEventsGroup 184 }

dls184_source_mac_address OBJECT-TYPE
    SYNTAX DisplayString
    MAX-ACCESS accessible-for-notify
    STATUS current
    DESCRIPTION
        "Parameter 'source_mac_address' in event DLS.184"
    ::= { dlsEventObjects184 1 }

dls184_dest_mac_address OBJECT-TYPE
    SYNTAX DisplayString
    MAX-ACCESS accessible-for-notify
    STATUS current
    DESCRIPTION
        "Parameter 'dest_mac_address' in event DLS.184"
    ::= { dlsEventObjects184 2 }

dls184_source_sap OBJECT-TYPE
    SYNTAX Integer32
    MAX-ACCESS accessible-for-notify
    STATUS current
    DESCRIPTION
        "Parameter 'source_sap' in event DLS.184"
    ::= { dlsEventObjects184 3 }

dls184_dest_sap OBJECT-TYPE
    SYNTAX Integer32
    MAX-ACCESS accessible-for-notify
    STATUS current
    DESCRIPTION
        "Parameter 'dest_sap' in event DLS.184"
    ::= { dlsEventObjects184 4 }

dlsEventObjects185 OBJECT-IDENTITY
    STATUS current
    DESCRIPTION
        "Event DLS.185
        DLS forwarder received a DLC_ERROR event from the underlying
        data link which could be LLC or SDLC."
    ::= { dlsEventsGroup 185 }

dls185_source_mac_address OBJECT-TYPE
    SYNTAX DisplayString
    MAX-ACCESS accessible-for-notify
    STATUS current
    DESCRIPTION
        "Parameter 'source_mac_address' in event DLS.185"
    ::= { dlsEventObjects185 1 }

dls185_dest_mac_address OBJECT-TYPE
    SYNTAX DisplayString
    MAX-ACCESS accessible-for-notify
    STATUS current
    DESCRIPTION
        "Parameter 'dest_mac_address' in event DLS.185"
    ::= { dlsEventObjects185 2 }

dls185_source_sap OBJECT-TYPE
    SYNTAX Integer32
    MAX-ACCESS accessible-for-notify
    STATUS current
    DESCRIPTION
        "Parameter 'source_sap' in event DLS.185"
    ::= { dlsEventObjects185 3 }

dls185_dest_sap OBJECT-TYPE
    SYNTAX Integer32
    MAX-ACCESS accessible-for-notify
    STATUS current
    DESCRIPTION
        "Parameter 'dest_sap' in event DLS.185"
    ::= { dlsEventObjects185 4 }

dlsEventObjects186 OBJECT-IDENTITY
    STATUS current
    DESCRIPTION
        "Event DLS.186
        DLS forwarder received a DLC_RESET event from the underlying
        data link which could be LLC or SDLC."
    ::= { dlsEventsGroup 186 }

dls186_source_mac_address OBJECT-TYPE
    SYNTAX DisplayString
    MAX-ACCESS accessible-for-notify
    STATUS current
    DESCRIPTION
        "Parameter 'source_mac_address' in event DLS.186"
    ::= { dlsEventObjects186 1 }

dls186_dest_mac_address OBJECT-TYPE
    SYNTAX DisplayString
    MAX-ACCESS accessible-for-notify
    STATUS current
    DESCRIPTION
        "Parameter 'dest_mac_address' in event DLS.186"
    ::= { dlsEventObjects186 2 }

dls186_source_sap OBJECT-TYPE
    SYNTAX Integer32
    MAX-ACCESS accessible-for-notify
    STATUS current
    DESCRIPTION
        "Parameter 'source_sap' in event DLS.186"
    ::= { dlsEventObjects186 3 }

dls186_dest_sap OBJECT-TYPE
    SYNTAX Integer32
    MAX-ACCESS accessible-for-notify
    STATUS current
    DESCRIPTION
        "Parameter 'dest_sap' in event DLS.186"
    ::= { dlsEventObjects186 4 }

dlsEventObjects187 OBJECT-IDENTITY
    STATUS current
    DESCRIPTION
        "Event DLS.187
        DLS forwarder received a DLC_DL_HALTED event from the underlying
        data link which could be LLC or SDLC."
    ::= { dlsEventsGroup 187 }

dls187_source_mac_address OBJECT-TYPE
    SYNTAX DisplayString
    MAX-ACCESS accessible-for-notify
    STATUS current
    DESCRIPTION
        "Parameter 'source_mac_address' in event DLS.187"
    ::= { dlsEventObjects187 1 }

dls187_dest_mac_address OBJECT-TYPE
    SYNTAX DisplayString
    MAX-ACCESS accessible-for-notify
    STATUS current
    DESCRIPTION
        "Parameter 'dest_mac_address' in event DLS.187"
    ::= { dlsEventObjects187 2 }

dls187_source_sap OBJECT-TYPE
    SYNTAX Integer32
    MAX-ACCESS accessible-for-notify
    STATUS current
    DESCRIPTION
        "Parameter 'source_sap' in event DLS.187"
    ::= { dlsEventObjects187 3 }

dls187_dest_sap OBJECT-TYPE
    SYNTAX Integer32
    MAX-ACCESS accessible-for-notify
    STATUS current
    DESCRIPTION
        "Parameter 'dest_sap' in event DLS.187"
    ::= { dlsEventObjects187 4 }

dlsEventObjects188 OBJECT-IDENTITY
    STATUS current
    DESCRIPTION
        "Event DLS.188
        DLS forwarder received a DLC_DL_ENTER_BUSY event from the underlying
        data link which could be LLC or SDLC."
    ::= { dlsEventsGroup 188 }

dls188_source_mac_address OBJECT-TYPE
    SYNTAX DisplayString
    MAX-ACCESS accessible-for-notify
    STATUS current
    DESCRIPTION
        "Parameter 'source_mac_address' in event DLS.188"
    ::= { dlsEventObjects188 1 }

dls188_dest_mac_address OBJECT-TYPE
    SYNTAX DisplayString
    MAX-ACCESS accessible-for-notify
    STATUS current
    DESCRIPTION
        "Parameter 'dest_mac_address' in event DLS.188"
    ::= { dlsEventObjects188 2 }

dls188_source_sap OBJECT-TYPE
    SYNTAX Integer32
    MAX-ACCESS accessible-for-notify
    STATUS current
    DESCRIPTION
        "Parameter 'source_sap' in event DLS.188"
    ::= { dlsEventObjects188 3 }

dls188_dest_sap OBJECT-TYPE
    SYNTAX Integer32
    MAX-ACCESS accessible-for-notify
    STATUS current
    DESCRIPTION
        "Parameter 'dest_sap' in event DLS.188"
    ::= { dlsEventObjects188 4 }

dlsEventObjects189 OBJECT-IDENTITY
    STATUS current
    DESCRIPTION
        "Event DLS.189
        DLS forwarder received a DLC_DL_EXIT_BUSY event from the underlying
        data link which could be LLC or SDLC."
    ::= { dlsEventsGroup 189 }

dls189_source_mac_address OBJECT-TYPE
    SYNTAX DisplayString
    MAX-ACCESS accessible-for-notify
    STATUS current
    DESCRIPTION
        "Parameter 'source_mac_address' in event DLS.189"
    ::= { dlsEventObjects189 1 }

dls189_dest_mac_address OBJECT-TYPE
    SYNTAX DisplayString
    MAX-ACCESS accessible-for-notify
    STATUS current
    DESCRIPTION
        "Parameter 'dest_mac_address' in event DLS.189"
    ::= { dlsEventObjects189 2 }

dls189_source_sap OBJECT-TYPE
    SYNTAX Integer32
    MAX-ACCESS accessible-for-notify
    STATUS current
    DESCRIPTION
        "Parameter 'source_sap' in event DLS.189"
    ::= { dlsEventObjects189 3 }

dls189_dest_sap OBJECT-TYPE
    SYNTAX Integer32
    MAX-ACCESS accessible-for-notify
    STATUS current
    DESCRIPTION
        "Parameter 'dest_sap' in event DLS.189"
    ::= { dlsEventObjects189 4 }

dlsEventObjects190 OBJECT-IDENTITY
    STATUS current
    DESCRIPTION
        "Event DLS.190
        DLS forwarder received a DLC_DL_STARTED event from the underlying
        data link which could be LLC or SDLC."
    ::= { dlsEventsGroup 190 }

dls190_source_mac_address OBJECT-TYPE
    SYNTAX DisplayString
    MAX-ACCESS accessible-for-notify
    STATUS current
    DESCRIPTION
        "Parameter 'source_mac_address' in event DLS.190"
    ::= { dlsEventObjects190 1 }

dls190_dest_mac_address OBJECT-TYPE
    SYNTAX DisplayString
    MAX-ACCESS accessible-for-notify
    STATUS current
    DESCRIPTION
        "Parameter 'dest_mac_address' in event DLS.190"
    ::= { dlsEventObjects190 2 }

dls190_source_sap OBJECT-TYPE
    SYNTAX Integer32
    MAX-ACCESS accessible-for-notify
    STATUS current
    DESCRIPTION
        "Parameter 'source_sap' in event DLS.190"
    ::= { dlsEventObjects190 3 }

dls190_dest_sap OBJECT-TYPE
    SYNTAX Integer32
    MAX-ACCESS accessible-for-notify
    STATUS current
    DESCRIPTION
        "Parameter 'dest_sap' in event DLS.190"
    ::= { dlsEventObjects190 4 }

dlsEventObjects191 OBJECT-IDENTITY
    STATUS current
    DESCRIPTION
        "Event DLS.191
        DLS forwarder received a DLC_RESOLVE_C event from the underlying
        data link which could be LLC or SDLC."
    ::= { dlsEventsGroup 191 }

dls191_source_mac_address OBJECT-TYPE
    SYNTAX DisplayString
    MAX-ACCESS accessible-for-notify
    STATUS current
    DESCRIPTION
        "Parameter 'source_mac_address' in event DLS.191"
    ::= { dlsEventObjects191 1 }

dls191_dest_mac_address OBJECT-TYPE
    SYNTAX DisplayString
    MAX-ACCESS accessible-for-notify
    STATUS current
    DESCRIPTION
        "Parameter 'dest_mac_address' in event DLS.191"
    ::= { dlsEventObjects191 2 }

dls191_source_sap OBJECT-TYPE
    SYNTAX Integer32
    MAX-ACCESS accessible-for-notify
    STATUS current
    DESCRIPTION
        "Parameter 'source_sap' in event DLS.191"
    ::= { dlsEventObjects191 3 }

dls191_dest_sap OBJECT-TYPE
    SYNTAX Integer32
    MAX-ACCESS accessible-for-notify
    STATUS current
    DESCRIPTION
        "Parameter 'dest_sap' in event DLS.191"
    ::= { dlsEventObjects191 4 }

dlsEventObjects192 OBJECT-IDENTITY
    STATUS current
    DESCRIPTION
        "Event DLS.192
        DLS forwarder received a DLC_INFO event from the underlying
        data link which could be LLC or SDLC."
    ::= { dlsEventsGroup 192 }

dls192_source_mac_address OBJECT-TYPE
    SYNTAX DisplayString
    MAX-ACCESS accessible-for-notify
    STATUS current
    DESCRIPTION
        "Parameter 'source_mac_address' in event DLS.192"
    ::= { dlsEventObjects192 1 }

dls192_dest_mac_address OBJECT-TYPE
    SYNTAX DisplayString
    MAX-ACCESS accessible-for-notify
    STATUS current
    DESCRIPTION
        "Parameter 'dest_mac_address' in event DLS.192"
    ::= { dlsEventObjects192 2 }

dls192_source_sap OBJECT-TYPE
    SYNTAX Integer32
    MAX-ACCESS accessible-for-notify
    STATUS current
    DESCRIPTION
        "Parameter 'source_sap' in event DLS.192"
    ::= { dlsEventObjects192 3 }

dls192_dest_sap OBJECT-TYPE
    SYNTAX Integer32
    MAX-ACCESS accessible-for-notify
    STATUS current
    DESCRIPTION
        "Parameter 'dest_sap' in event DLS.192"
    ::= { dlsEventObjects192 4 }

dlsEventObjects193 OBJECT-IDENTITY
    STATUS current
    DESCRIPTION
        "Event DLS.193
        DLS forwarder received a DLC_DGRM event from the underlying
        data link which could be LLC or SDLC."
    ::= { dlsEventsGroup 193 }

dls193_source_mac_address OBJECT-TYPE
    SYNTAX DisplayString
    MAX-ACCESS accessible-for-notify
    STATUS current
    DESCRIPTION
        "Parameter 'source_mac_address' in event DLS.193"
    ::= { dlsEventObjects193 1 }

dls193_dest_mac_address OBJECT-TYPE
    SYNTAX DisplayString
    MAX-ACCESS accessible-for-notify
    STATUS current
    DESCRIPTION
        "Parameter 'dest_mac_address' in event DLS.193"
    ::= { dlsEventObjects193 2 }

dls193_source_sap OBJECT-TYPE
    SYNTAX Integer32
    MAX-ACCESS accessible-for-notify
    STATUS current
    DESCRIPTION
        "Parameter 'source_sap' in event DLS.193"
    ::= { dlsEventObjects193 3 }

dls193_dest_sap OBJECT-TYPE
    SYNTAX Integer32
    MAX-ACCESS accessible-for-notify
    STATUS current
    DESCRIPTION
        "Parameter 'dest_sap' in event DLS.193"
    ::= { dlsEventObjects193 4 }

dlsEventObjects194 OBJECT-IDENTITY
    STATUS current
    DESCRIPTION
        "Event DLS.194
        DLS forwarder received a DLC_XID event from the underlying
        data link which could be LLC or SDLC."
    ::= { dlsEventsGroup 194 }

dls194_source_mac_address OBJECT-TYPE
    SYNTAX DisplayString
    MAX-ACCESS accessible-for-notify
    STATUS current
    DESCRIPTION
        "Parameter 'source_mac_address' in event DLS.194"
    ::= { dlsEventObjects194 1 }

dls194_dest_mac_address OBJECT-TYPE
    SYNTAX DisplayString
    MAX-ACCESS accessible-for-notify
    STATUS current
    DESCRIPTION
        "Parameter 'dest_mac_address' in event DLS.194"
    ::= { dlsEventObjects194 2 }

dls194_source_sap OBJECT-TYPE
    SYNTAX Integer32
    MAX-ACCESS accessible-for-notify
    STATUS current
    DESCRIPTION
        "Parameter 'source_sap' in event DLS.194"
    ::= { dlsEventObjects194 3 }

dls194_dest_sap OBJECT-TYPE
    SYNTAX Integer32
    MAX-ACCESS accessible-for-notify
    STATUS current
    DESCRIPTION
        "Parameter 'dest_sap' in event DLS.194"
    ::= { dlsEventObjects194 4 }

dlsEventObjects195 OBJECT-IDENTITY
    STATUS current
    DESCRIPTION
        "Event DLS.195
        DLS forwarder received a DLC_DATAFRAME event from the underlying
        data link which could be LLC or SDLC."
    ::= { dlsEventsGroup 195 }

dls195_source_mac_address OBJECT-TYPE
    SYNTAX DisplayString
    MAX-ACCESS accessible-for-notify
    STATUS current
    DESCRIPTION
        "Parameter 'source_mac_address' in event DLS.195"
    ::= { dlsEventObjects195 1 }

dls195_dest_mac_address OBJECT-TYPE
    SYNTAX DisplayString
    MAX-ACCESS accessible-for-notify
    STATUS current
    DESCRIPTION
        "Parameter 'dest_mac_address' in event DLS.195"
    ::= { dlsEventObjects195 2 }

dls195_source_sap OBJECT-TYPE
    SYNTAX Integer32
    MAX-ACCESS accessible-for-notify
    STATUS current
    DESCRIPTION
        "Parameter 'source_sap' in event DLS.195"
    ::= { dlsEventObjects195 3 }

dls195_dest_sap OBJECT-TYPE
    SYNTAX Integer32
    MAX-ACCESS accessible-for-notify
    STATUS current
    DESCRIPTION
        "Parameter 'dest_sap' in event DLS.195"
    ::= { dlsEventObjects195 4 }

dlsEventObjects196 OBJECT-IDENTITY
    STATUS current
    DESCRIPTION
        "Event DLS.196
        While processing an event, either an SSP message received over
        TCP or an event presented from underlying DLC, the associated
        DLS session is transitioning to DISCONNECTED state."
    ::= { dlsEventsGroup 196 }

dls196_source_mac_address OBJECT-TYPE
    SYNTAX DisplayString
    MAX-ACCESS accessible-for-notify
    STATUS current
    DESCRIPTION
        "Parameter 'source_mac_address' in event DLS.196"
    ::= { dlsEventObjects196 1 }

dls196_dest_mac_address OBJECT-TYPE
    SYNTAX DisplayString
    MAX-ACCESS accessible-for-notify
    STATUS current
    DESCRIPTION
        "Parameter 'dest_mac_address' in event DLS.196"
    ::= { dlsEventObjects196 2 }

dls196_source_sap OBJECT-TYPE
    SYNTAX Integer32
    MAX-ACCESS accessible-for-notify
    STATUS current
    DESCRIPTION
        "Parameter 'source_sap' in event DLS.196"
    ::= { dlsEventObjects196 3 }

dls196_dest_sap OBJECT-TYPE
    SYNTAX Integer32
    MAX-ACCESS accessible-for-notify
    STATUS current
    DESCRIPTION
        "Parameter 'dest_sap' in event DLS.196"
    ::= { dlsEventObjects196 4 }

dlsEventObjects197 OBJECT-IDENTITY
    STATUS current
    DESCRIPTION
        "Event DLS.197
        While processing an event, either an SSP message received over
        TCP or an event presented from underlying DLC, the associated
        DLS session is transitioning to CONNECT_PENDING state."
    ::= { dlsEventsGroup 197 }

dls197_source_mac_address OBJECT-TYPE
    SYNTAX DisplayString
    MAX-ACCESS accessible-for-notify
    STATUS current
    DESCRIPTION
        "Parameter 'source_mac_address' in event DLS.197"
    ::= { dlsEventObjects197 1 }

dls197_dest_mac_address OBJECT-TYPE
    SYNTAX DisplayString
    MAX-ACCESS accessible-for-notify
    STATUS current
    DESCRIPTION
        "Parameter 'dest_mac_address' in event DLS.197"
    ::= { dlsEventObjects197 2 }

dls197_source_sap OBJECT-TYPE
    SYNTAX Integer32
    MAX-ACCESS accessible-for-notify
    STATUS current
    DESCRIPTION
        "Parameter 'source_sap' in event DLS.197"
    ::= { dlsEventObjects197 3 }

dls197_dest_sap OBJECT-TYPE
    SYNTAX Integer32
    MAX-ACCESS accessible-for-notify
    STATUS current
    DESCRIPTION
        "Parameter 'dest_sap' in event DLS.197"
    ::= { dlsEventObjects197 4 }

dlsEventObjects198 OBJECT-IDENTITY
    STATUS current
    DESCRIPTION
        "Event DLS.198
        While processing an event, either an SSP message received over
        TCP or an event presented from underlying DLC, the associated
        DLS session is transitioning to CONNECTED state."
    ::= { dlsEventsGroup 198 }

dls198_source_mac_address OBJECT-TYPE
    SYNTAX DisplayString
    MAX-ACCESS accessible-for-notify
    STATUS current
    DESCRIPTION
        "Parameter 'source_mac_address' in event DLS.198"
    ::= { dlsEventObjects198 1 }

dls198_dest_mac_address OBJECT-TYPE
    SYNTAX DisplayString
    MAX-ACCESS accessible-for-notify
    STATUS current
    DESCRIPTION
        "Parameter 'dest_mac_address' in event DLS.198"
    ::= { dlsEventObjects198 2 }

dls198_source_sap OBJECT-TYPE
    SYNTAX Integer32
    MAX-ACCESS accessible-for-notify
    STATUS current
    DESCRIPTION
        "Parameter 'source_sap' in event DLS.198"
    ::= { dlsEventObjects198 3 }

dls198_dest_sap OBJECT-TYPE
    SYNTAX Integer32
    MAX-ACCESS accessible-for-notify
    STATUS current
    DESCRIPTION
        "Parameter 'dest_sap' in event DLS.198"
    ::= { dlsEventObjects198 4 }

dlsEventObjects199 OBJECT-IDENTITY
    STATUS current
    DESCRIPTION
        "Event DLS.199
        While processing an event, either an SSP message received over
        TCP or an event presented from underlying DLC, the associated
        DLS session is transitioning to DISCONNECT_PENDING state."
    ::= { dlsEventsGroup 199 }

dls199_source_mac_address OBJECT-TYPE
    SYNTAX DisplayString
    MAX-ACCESS accessible-for-notify
    STATUS current
    DESCRIPTION
        "Parameter 'source_mac_address' in event DLS.199"
    ::= { dlsEventObjects199 1 }

dls199_dest_mac_address OBJECT-TYPE
    SYNTAX DisplayString
    MAX-ACCESS accessible-for-notify
    STATUS current
    DESCRIPTION
        "Parameter 'dest_mac_address' in event DLS.199"
    ::= { dlsEventObjects199 2 }

dls199_source_sap OBJECT-TYPE
    SYNTAX Integer32
    MAX-ACCESS accessible-for-notify
    STATUS current
    DESCRIPTION
        "Parameter 'source_sap' in event DLS.199"
    ::= { dlsEventObjects199 3 }

dls199_dest_sap OBJECT-TYPE
    SYNTAX Integer32
    MAX-ACCESS accessible-for-notify
    STATUS current
    DESCRIPTION
        "Parameter 'dest_sap' in event DLS.199"
    ::= { dlsEventObjects199 4 }

dlsEventObjects200 OBJECT-IDENTITY
    STATUS current
    DESCRIPTION
        "Event DLS.200
        While processing an event, either an SSP message received over
        TCP or an event presented from underlying DLC, the associated
        DLS session is transitioning to CIRCUIT_ESTABLISHED state."
    ::= { dlsEventsGroup 200 }

dls200_source_mac_address OBJECT-TYPE
    SYNTAX DisplayString
    MAX-ACCESS accessible-for-notify
    STATUS current
    DESCRIPTION
        "Parameter 'source_mac_address' in event DLS.200"
    ::= { dlsEventObjects200 1 }

dls200_dest_mac_address OBJECT-TYPE
    SYNTAX DisplayString
    MAX-ACCESS accessible-for-notify
    STATUS current
    DESCRIPTION
        "Parameter 'dest_mac_address' in event DLS.200"
    ::= { dlsEventObjects200 2 }

dls200_source_sap OBJECT-TYPE
    SYNTAX Integer32
    MAX-ACCESS accessible-for-notify
    STATUS current
    DESCRIPTION
        "Parameter 'source_sap' in event DLS.200"
    ::= { dlsEventObjects200 3 }

dls200_dest_sap OBJECT-TYPE
    SYNTAX Integer32
    MAX-ACCESS accessible-for-notify
    STATUS current
    DESCRIPTION
        "Parameter 'dest_sap' in event DLS.200"
    ::= { dlsEventObjects200 4 }

dlsEventObjects201 OBJECT-IDENTITY
    STATUS current
    DESCRIPTION
        "Event DLS.201
        While processing an event, either an SSP message received over
        TCP or an event presented from underlying DLC, the associated
        DLS session is transitioning to CIRCUIT_PENDING state."
    ::= { dlsEventsGroup 201 }

dls201_source_mac_address OBJECT-TYPE
    SYNTAX DisplayString
    MAX-ACCESS accessible-for-notify
    STATUS current
    DESCRIPTION
        "Parameter 'source_mac_address' in event DLS.201"
    ::= { dlsEventObjects201 1 }

dls201_dest_mac_address OBJECT-TYPE
    SYNTAX DisplayString
    MAX-ACCESS accessible-for-notify
    STATUS current
    DESCRIPTION
        "Parameter 'dest_mac_address' in event DLS.201"
    ::= { dlsEventObjects201 2 }

dls201_source_sap OBJECT-TYPE
    SYNTAX Integer32
    MAX-ACCESS accessible-for-notify
    STATUS current
    DESCRIPTION
        "Parameter 'source_sap' in event DLS.201"
    ::= { dlsEventObjects201 3 }

dls201_dest_sap OBJECT-TYPE
    SYNTAX Integer32
    MAX-ACCESS accessible-for-notify
    STATUS current
    DESCRIPTION
        "Parameter 'dest_sap' in event DLS.201"
    ::= { dlsEventObjects201 4 }

dlsEventObjects202 OBJECT-IDENTITY
    STATUS current
    DESCRIPTION
        "Event DLS.202
        While processing an event, either an SSP message received over
        TCP or an event presented from underlying DLC, the associated
        DLS session is transitioning to CIRCUIT_RESTART state."
    ::= { dlsEventsGroup 202 }

dls202_source_mac_address OBJECT-TYPE
    SYNTAX DisplayString
    MAX-ACCESS accessible-for-notify
    STATUS current
    DESCRIPTION
        "Parameter 'source_mac_address' in event DLS.202"
    ::= { dlsEventObjects202 1 }

dls202_dest_mac_address OBJECT-TYPE
    SYNTAX DisplayString
    MAX-ACCESS accessible-for-notify
    STATUS current
    DESCRIPTION
        "Parameter 'dest_mac_address' in event DLS.202"
    ::= { dlsEventObjects202 2 }

dls202_source_sap OBJECT-TYPE
    SYNTAX Integer32
    MAX-ACCESS accessible-for-notify
    STATUS current
    DESCRIPTION
        "Parameter 'source_sap' in event DLS.202"
    ::= { dlsEventObjects202 3 }

dls202_dest_sap OBJECT-TYPE
    SYNTAX Integer32
    MAX-ACCESS accessible-for-notify
    STATUS current
    DESCRIPTION
        "Parameter 'dest_sap' in event DLS.202"
    ::= { dlsEventObjects202 4 }

dlsEventObjects203 OBJECT-IDENTITY
    STATUS current
    DESCRIPTION
        "Event DLS.203
        While processing an event, either an SSP message received over
        TCP or an event presented from underlying DLC, the associated
        DLS session is transitioning to RESOLVE_PENDING state."
    ::= { dlsEventsGroup 203 }

dls203_source_mac_address OBJECT-TYPE
    SYNTAX DisplayString
    MAX-ACCESS accessible-for-notify
    STATUS current
    DESCRIPTION
        "Parameter 'source_mac_address' in event DLS.203"
    ::= { dlsEventObjects203 1 }

dls203_dest_mac_address OBJECT-TYPE
    SYNTAX DisplayString
    MAX-ACCESS accessible-for-notify
    STATUS current
    DESCRIPTION
        "Parameter 'dest_mac_address' in event DLS.203"
    ::= { dlsEventObjects203 2 }

dls203_source_sap OBJECT-TYPE
    SYNTAX Integer32
    MAX-ACCESS accessible-for-notify
    STATUS current
    DESCRIPTION
        "Parameter 'source_sap' in event DLS.203"
    ::= { dlsEventObjects203 3 }

dls203_dest_sap OBJECT-TYPE
    SYNTAX Integer32
    MAX-ACCESS accessible-for-notify
    STATUS current
    DESCRIPTION
        "Parameter 'dest_sap' in event DLS.203"
    ::= { dlsEventObjects203 4 }

dlsEventObjects204 OBJECT-IDENTITY
    STATUS current
    DESCRIPTION
        "Event DLS.204
        While processing an event, either an SSP message received over
        TCP or an event presented from underlying DLC, the associated
        DLS session is transitioning to CONTACT_PENDING state."
    ::= { dlsEventsGroup 204 }

dls204_source_mac_address OBJECT-TYPE
    SYNTAX DisplayString
    MAX-ACCESS accessible-for-notify
    STATUS current
    DESCRIPTION
        "Parameter 'source_mac_address' in event DLS.204"
    ::= { dlsEventObjects204 1 }

dls204_dest_mac_address OBJECT-TYPE
    SYNTAX DisplayString
    MAX-ACCESS accessible-for-notify
    STATUS current
    DESCRIPTION
        "Parameter 'dest_mac_address' in event DLS.204"
    ::= { dlsEventObjects204 2 }

dls204_source_sap OBJECT-TYPE
    SYNTAX Integer32
    MAX-ACCESS accessible-for-notify
    STATUS current
    DESCRIPTION
        "Parameter 'source_sap' in event DLS.204"
    ::= { dlsEventObjects204 3 }

dls204_dest_sap OBJECT-TYPE
    SYNTAX Integer32
    MAX-ACCESS accessible-for-notify
    STATUS current
    DESCRIPTION
        "Parameter 'dest_sap' in event DLS.204"
    ::= { dlsEventObjects204 4 }

dlsEventObjects205 OBJECT-IDENTITY
    STATUS current
    DESCRIPTION
        "Event DLS.205
        While processing an event, either an SSP message received over
        TCP or an event presented from underlying DLC, the associated
        DLS session is transitioning to RESTART_PENDING state."
    ::= { dlsEventsGroup 205 }

dls205_source_mac_address OBJECT-TYPE
    SYNTAX DisplayString
    MAX-ACCESS accessible-for-notify
    STATUS current
    DESCRIPTION
        "Parameter 'source_mac_address' in event DLS.205"
    ::= { dlsEventObjects205 1 }

dls205_dest_mac_address OBJECT-TYPE
    SYNTAX DisplayString
    MAX-ACCESS accessible-for-notify
    STATUS current
    DESCRIPTION
        "Parameter 'dest_mac_address' in event DLS.205"
    ::= { dlsEventObjects205 2 }

dls205_source_sap OBJECT-TYPE
    SYNTAX Integer32
    MAX-ACCESS accessible-for-notify
    STATUS current
    DESCRIPTION
        "Parameter 'source_sap' in event DLS.205"
    ::= { dlsEventObjects205 3 }

dls205_dest_sap OBJECT-TYPE
    SYNTAX Integer32
    MAX-ACCESS accessible-for-notify
    STATUS current
    DESCRIPTION
        "Parameter 'dest_sap' in event DLS.205"
    ::= { dlsEventObjects205 4 }

dlsEventObjects206 OBJECT-IDENTITY
    STATUS current
    DESCRIPTION
        "Event DLS.206
        While processing an event, either an SSP message received over
        TCP or an event presented from underlying DLC, the associated
        DLS session is transitioning to HALT_PENDING state."
    ::= { dlsEventsGroup 206 }

dls206_source_mac_address OBJECT-TYPE
    SYNTAX DisplayString
    MAX-ACCESS accessible-for-notify
    STATUS current
    DESCRIPTION
        "Parameter 'source_mac_address' in event DLS.206"
    ::= { dlsEventObjects206 1 }

dls206_dest_mac_address OBJECT-TYPE
    SYNTAX DisplayString
    MAX-ACCESS accessible-for-notify
    STATUS current
    DESCRIPTION
        "Parameter 'dest_mac_address' in event DLS.206"
    ::= { dlsEventObjects206 2 }

dls206_source_sap OBJECT-TYPE
    SYNTAX Integer32
    MAX-ACCESS accessible-for-notify
    STATUS current
    DESCRIPTION
        "Parameter 'source_sap' in event DLS.206"
    ::= { dlsEventObjects206 3 }

dls206_dest_sap OBJECT-TYPE
    SYNTAX Integer32
    MAX-ACCESS accessible-for-notify
    STATUS current
    DESCRIPTION
        "Parameter 'dest_sap' in event DLS.206"
    ::= { dlsEventObjects206 4 }

dlsEventObjects207 OBJECT-IDENTITY
    STATUS current
    DESCRIPTION
        "Event DLS.207
        While processing a DLC_CONTACTED event, the DLS state
        machine discovered the event occurring in an unexpected state."
    ::= { dlsEventsGroup 207 }

dls207_state OBJECT-TYPE
    SYNTAX DisplayString
    MAX-ACCESS accessible-for-notify
    STATUS current
    DESCRIPTION
        "Parameter 'state' in event DLS.207"
    ::= { dlsEventObjects207 1 }

dls207_source_mac_address OBJECT-TYPE
    SYNTAX DisplayString
    MAX-ACCESS accessible-for-notify
    STATUS current
    DESCRIPTION
        "Parameter 'source_mac_address' in event DLS.207"
    ::= { dlsEventObjects207 2 }

dls207_dest_mac_address OBJECT-TYPE
    SYNTAX DisplayString
    MAX-ACCESS accessible-for-notify
    STATUS current
    DESCRIPTION
        "Parameter 'dest_mac_address' in event DLS.207"
    ::= { dlsEventObjects207 3 }

dls207_source_sap OBJECT-TYPE
    SYNTAX Integer32
    MAX-ACCESS accessible-for-notify
    STATUS current
    DESCRIPTION
        "Parameter 'source_sap' in event DLS.207"
    ::= { dlsEventObjects207 4 }

dls207_dest_sap OBJECT-TYPE
    SYNTAX Integer32
    MAX-ACCESS accessible-for-notify
    STATUS current
    DESCRIPTION
        "Parameter 'dest_sap' in event DLS.207"
    ::= { dlsEventObjects207 5 }

dlsEventObjects208 OBJECT-IDENTITY
    STATUS current
    DESCRIPTION
        "Event DLS.208
        While processing a DLC_DGRM event, the DLS state
        machine discovered the event occurring in an unexpected state."
    ::= { dlsEventsGroup 208 }

dls208_state OBJECT-TYPE
    SYNTAX DisplayString
    MAX-ACCESS accessible-for-notify
    STATUS current
    DESCRIPTION
        "Parameter 'state' in event DLS.208"
    ::= { dlsEventObjects208 1 }

dls208_source_mac_address OBJECT-TYPE
    SYNTAX DisplayString
    MAX-ACCESS accessible-for-notify
    STATUS current
    DESCRIPTION
        "Parameter 'source_mac_address' in event DLS.208"
    ::= { dlsEventObjects208 2 }

dls208_dest_mac_address OBJECT-TYPE
    SYNTAX DisplayString
    MAX-ACCESS accessible-for-notify
    STATUS current
    DESCRIPTION
        "Parameter 'dest_mac_address' in event DLS.208"
    ::= { dlsEventObjects208 3 }

dls208_source_sap OBJECT-TYPE
    SYNTAX Integer32
    MAX-ACCESS accessible-for-notify
    STATUS current
    DESCRIPTION
        "Parameter 'source_sap' in event DLS.208"
    ::= { dlsEventObjects208 4 }

dls208_dest_sap OBJECT-TYPE
    SYNTAX Integer32
    MAX-ACCESS accessible-for-notify
    STATUS current
    DESCRIPTION
        "Parameter 'dest_sap' in event DLS.208"
    ::= { dlsEventObjects208 5 }

dlsEventObjects209 OBJECT-IDENTITY
    STATUS current
    DESCRIPTION
        "Event DLS.209
        While processing a DLC_ERROR event, the DLS state
        machine discovered the event occurring in an unexpected state."
    ::= { dlsEventsGroup 209 }

dls209_state OBJECT-TYPE
    SYNTAX DisplayString
    MAX-ACCESS accessible-for-notify
    STATUS current
    DESCRIPTION
        "Parameter 'state' in event DLS.209"
    ::= { dlsEventObjects209 1 }

dls209_source_mac_address OBJECT-TYPE
    SYNTAX DisplayString
    MAX-ACCESS accessible-for-notify
    STATUS current
    DESCRIPTION
        "Parameter 'source_mac_address' in event DLS.209"
    ::= { dlsEventObjects209 2 }

dls209_dest_mac_address OBJECT-TYPE
    SYNTAX DisplayString
    MAX-ACCESS accessible-for-notify
    STATUS current
    DESCRIPTION
        "Parameter 'dest_mac_address' in event DLS.209"
    ::= { dlsEventObjects209 3 }

dls209_source_sap OBJECT-TYPE
    SYNTAX Integer32
    MAX-ACCESS accessible-for-notify
    STATUS current
    DESCRIPTION
        "Parameter 'source_sap' in event DLS.209"
    ::= { dlsEventObjects209 4 }

dls209_dest_sap OBJECT-TYPE
    SYNTAX Integer32
    MAX-ACCESS accessible-for-notify
    STATUS current
    DESCRIPTION
        "Parameter 'dest_sap' in event DLS.209"
    ::= { dlsEventObjects209 5 }

dlsEventObjects210 OBJECT-IDENTITY
    STATUS current
    DESCRIPTION
        "Event DLS.210
        While processing a DLC_INFO event, the DLS state
        machine discovered the event occurring in an unexpected state."
    ::= { dlsEventsGroup 210 }

dls210_state OBJECT-TYPE
    SYNTAX DisplayString
    MAX-ACCESS accessible-for-notify
    STATUS current
    DESCRIPTION
        "Parameter 'state' in event DLS.210"
    ::= { dlsEventObjects210 1 }

dls210_source_mac_address OBJECT-TYPE
    SYNTAX DisplayString
    MAX-ACCESS accessible-for-notify
    STATUS current
    DESCRIPTION
        "Parameter 'source_mac_address' in event DLS.210"
    ::= { dlsEventObjects210 2 }

dls210_dest_mac_address OBJECT-TYPE
    SYNTAX DisplayString
    MAX-ACCESS accessible-for-notify
    STATUS current
    DESCRIPTION
        "Parameter 'dest_mac_address' in event DLS.210"
    ::= { dlsEventObjects210 3 }

dls210_source_sap OBJECT-TYPE
    SYNTAX Integer32
    MAX-ACCESS accessible-for-notify
    STATUS current
    DESCRIPTION
        "Parameter 'source_sap' in event DLS.210"
    ::= { dlsEventObjects210 4 }

dls210_dest_sap OBJECT-TYPE
    SYNTAX Integer32
    MAX-ACCESS accessible-for-notify
    STATUS current
    DESCRIPTION
        "Parameter 'dest_sap' in event DLS.210"
    ::= { dlsEventObjects210 5 }

dlsEventObjects211 OBJECT-IDENTITY
    STATUS current
    DESCRIPTION
        "Event DLS.211
        While processing a DLC_DL_HALTED event, the DLS state
        machine discovered the event occurring in an unexpected state."
    ::= { dlsEventsGroup 211 }

dls211_state OBJECT-TYPE
    SYNTAX DisplayString
    MAX-ACCESS accessible-for-notify
    STATUS current
    DESCRIPTION
        "Parameter 'state' in event DLS.211"
    ::= { dlsEventObjects211 1 }

dls211_source_mac_address OBJECT-TYPE
    SYNTAX DisplayString
    MAX-ACCESS accessible-for-notify
    STATUS current
    DESCRIPTION
        "Parameter 'source_mac_address' in event DLS.211"
    ::= { dlsEventObjects211 2 }

dls211_dest_mac_address OBJECT-TYPE
    SYNTAX DisplayString
    MAX-ACCESS accessible-for-notify
    STATUS current
    DESCRIPTION
        "Parameter 'dest_mac_address' in event DLS.211"
    ::= { dlsEventObjects211 3 }

dls211_source_sap OBJECT-TYPE
    SYNTAX Integer32
    MAX-ACCESS accessible-for-notify
    STATUS current
    DESCRIPTION
        "Parameter 'source_sap' in event DLS.211"
    ::= { dlsEventObjects211 4 }

dls211_dest_sap OBJECT-TYPE
    SYNTAX Integer32
    MAX-ACCESS accessible-for-notify
    STATUS current
    DESCRIPTION
        "Parameter 'dest_sap' in event DLS.211"
    ::= { dlsEventObjects211 5 }

dlsEventObjects212 OBJECT-IDENTITY
    STATUS current
    DESCRIPTION
        "Event DLS.212
        While processing a DLC_DL_STARTED event, the DLS state
        machine discovered the event occurring in an unexpected state."
    ::= { dlsEventsGroup 212 }

dls212_state OBJECT-TYPE
    SYNTAX DisplayString
    MAX-ACCESS accessible-for-notify
    STATUS current
    DESCRIPTION
        "Parameter 'state' in event DLS.212"
    ::= { dlsEventObjects212 1 }

dls212_source_mac_address OBJECT-TYPE
    SYNTAX DisplayString
    MAX-ACCESS accessible-for-notify
    STATUS current
    DESCRIPTION
        "Parameter 'source_mac_address' in event DLS.212"
    ::= { dlsEventObjects212 2 }

dls212_dest_mac_address OBJECT-TYPE
    SYNTAX DisplayString
    MAX-ACCESS accessible-for-notify
    STATUS current
    DESCRIPTION
        "Parameter 'dest_mac_address' in event DLS.212"
    ::= { dlsEventObjects212 3 }

dls212_source_sap OBJECT-TYPE
    SYNTAX Integer32
    MAX-ACCESS accessible-for-notify
    STATUS current
    DESCRIPTION
        "Parameter 'source_sap' in event DLS.212"
    ::= { dlsEventObjects212 4 }

dls212_dest_sap OBJECT-TYPE
    SYNTAX Integer32
    MAX-ACCESS accessible-for-notify
    STATUS current
    DESCRIPTION
        "Parameter 'dest_sap' in event DLS.212"
    ::= { dlsEventObjects212 5 }

dlsEventObjects213 OBJECT-IDENTITY
    STATUS current
    DESCRIPTION
        "Event DLS.213
        While processing a DLC_RESET event, the DLS state
        machine discovered the event occurring in an unexpected state."
    ::= { dlsEventsGroup 213 }

dls213_state OBJECT-TYPE
    SYNTAX DisplayString
    MAX-ACCESS accessible-for-notify
    STATUS current
    DESCRIPTION
        "Parameter 'state' in event DLS.213"
    ::= { dlsEventObjects213 1 }

dls213_source_mac_address OBJECT-TYPE
    SYNTAX DisplayString
    MAX-ACCESS accessible-for-notify
    STATUS current
    DESCRIPTION
        "Parameter 'source_mac_address' in event DLS.213"
    ::= { dlsEventObjects213 2 }

dls213_dest_mac_address OBJECT-TYPE
    SYNTAX DisplayString
    MAX-ACCESS accessible-for-notify
    STATUS current
    DESCRIPTION
        "Parameter 'dest_mac_address' in event DLS.213"
    ::= { dlsEventObjects213 3 }

dls213_source_sap OBJECT-TYPE
    SYNTAX Integer32
    MAX-ACCESS accessible-for-notify
    STATUS current
    DESCRIPTION
        "Parameter 'source_sap' in event DLS.213"
    ::= { dlsEventObjects213 4 }

dls213_dest_sap OBJECT-TYPE
    SYNTAX Integer32
    MAX-ACCESS accessible-for-notify
    STATUS current
    DESCRIPTION
        "Parameter 'dest_sap' in event DLS.213"
    ::= { dlsEventObjects213 5 }

dlsEventObjects214 OBJECT-IDENTITY
    STATUS current
    DESCRIPTION
        "Event DLS.214
        While processing a DLC_RESOLVE_C event, the DLS state
        machine discovered the event occurring in an unexpected state."
    ::= { dlsEventsGroup 214 }

dls214_state OBJECT-TYPE
    SYNTAX DisplayString
    MAX-ACCESS accessible-for-notify
    STATUS current
    DESCRIPTION
        "Parameter 'state' in event DLS.214"
    ::= { dlsEventObjects214 1 }

dls214_source_mac_address OBJECT-TYPE
    SYNTAX DisplayString
    MAX-ACCESS accessible-for-notify
    STATUS current
    DESCRIPTION
        "Parameter 'source_mac_address' in event DLS.214"
    ::= { dlsEventObjects214 2 }

dls214_dest_mac_address OBJECT-TYPE
    SYNTAX DisplayString
    MAX-ACCESS accessible-for-notify
    STATUS current
    DESCRIPTION
        "Parameter 'dest_mac_address' in event DLS.214"
    ::= { dlsEventObjects214 3 }

dls214_source_sap OBJECT-TYPE
    SYNTAX Integer32
    MAX-ACCESS accessible-for-notify
    STATUS current
    DESCRIPTION
        "Parameter 'source_sap' in event DLS.214"
    ::= { dlsEventObjects214 4 }

dls214_dest_sap OBJECT-TYPE
    SYNTAX Integer32
    MAX-ACCESS accessible-for-notify
    STATUS current
    DESCRIPTION
        "Parameter 'dest_sap' in event DLS.214"
    ::= { dlsEventObjects214 5 }

dlsEventObjects215 OBJECT-IDENTITY
    STATUS current
    DESCRIPTION
        "Event DLS.215
        While processing a DLC_XID event, the DLS state
        machine discovered the event occurring in an unexpected state."
    ::= { dlsEventsGroup 215 }

dls215_state OBJECT-TYPE
    SYNTAX DisplayString
    MAX-ACCESS accessible-for-notify
    STATUS current
    DESCRIPTION
        "Parameter 'state' in event DLS.215"
    ::= { dlsEventObjects215 1 }

dls215_source_mac_address OBJECT-TYPE
    SYNTAX DisplayString
    MAX-ACCESS accessible-for-notify
    STATUS current
    DESCRIPTION
        "Parameter 'source_mac_address' in event DLS.215"
    ::= { dlsEventObjects215 2 }

dls215_dest_mac_address OBJECT-TYPE
    SYNTAX DisplayString
    MAX-ACCESS accessible-for-notify
    STATUS current
    DESCRIPTION
        "Parameter 'dest_mac_address' in event DLS.215"
    ::= { dlsEventObjects215 3 }

dls215_source_sap OBJECT-TYPE
    SYNTAX Integer32
    MAX-ACCESS accessible-for-notify
    STATUS current
    DESCRIPTION
        "Parameter 'source_sap' in event DLS.215"
    ::= { dlsEventObjects215 4 }

dls215_dest_sap OBJECT-TYPE
    SYNTAX Integer32
    MAX-ACCESS accessible-for-notify
    STATUS current
    DESCRIPTION
        "Parameter 'dest_sap' in event DLS.215"
    ::= { dlsEventObjects215 5 }

dlsEventObjects216 OBJECT-IDENTITY
    STATUS current
    DESCRIPTION
        "Event DLS.216
        While processing a CANUREACH event, the DLS state
        machine discovered the event occurring in an unexpected state."
    ::= { dlsEventsGroup 216 }

dls216_state OBJECT-TYPE
    SYNTAX DisplayString
    MAX-ACCESS accessible-for-notify
    STATUS current
    DESCRIPTION
        "Parameter 'state' in event DLS.216"
    ::= { dlsEventObjects216 1 }

dls216_source_mac_address OBJECT-TYPE
    SYNTAX DisplayString
    MAX-ACCESS accessible-for-notify
    STATUS current
    DESCRIPTION
        "Parameter 'source_mac_address' in event DLS.216"
    ::= { dlsEventObjects216 2 }

dls216_dest_mac_address OBJECT-TYPE
    SYNTAX DisplayString
    MAX-ACCESS accessible-for-notify
    STATUS current
    DESCRIPTION
        "Parameter 'dest_mac_address' in event DLS.216"
    ::= { dlsEventObjects216 3 }

dls216_source_sap OBJECT-TYPE
    SYNTAX Integer32
    MAX-ACCESS accessible-for-notify
    STATUS current
    DESCRIPTION
        "Parameter 'source_sap' in event DLS.216"
    ::= { dlsEventObjects216 4 }

dls216_dest_sap OBJECT-TYPE
    SYNTAX Integer32
    MAX-ACCESS accessible-for-notify
    STATUS current
    DESCRIPTION
        "Parameter 'dest_sap' in event DLS.216"
    ::= { dlsEventObjects216 5 }

dlsEventObjects217 OBJECT-IDENTITY
    STATUS current
    DESCRIPTION
        "Event DLS.217
        While processing a DGRMFRAME event, the DLS state
        machine discovered the event occurring in an unexpected state."
    ::= { dlsEventsGroup 217 }

dls217_state OBJECT-TYPE
    SYNTAX DisplayString
    MAX-ACCESS accessible-for-notify
    STATUS current
    DESCRIPTION
        "Parameter 'state' in event DLS.217"
    ::= { dlsEventObjects217 1 }

dls217_source_mac_address OBJECT-TYPE
    SYNTAX DisplayString
    MAX-ACCESS accessible-for-notify
    STATUS current
    DESCRIPTION
        "Parameter 'source_mac_address' in event DLS.217"
    ::= { dlsEventObjects217 2 }

dls217_dest_mac_address OBJECT-TYPE
    SYNTAX DisplayString
    MAX-ACCESS accessible-for-notify
    STATUS current
    DESCRIPTION
        "Parameter 'dest_mac_address' in event DLS.217"
    ::= { dlsEventObjects217 3 }

dls217_source_sap OBJECT-TYPE
    SYNTAX Integer32
    MAX-ACCESS accessible-for-notify
    STATUS current
    DESCRIPTION
        "Parameter 'source_sap' in event DLS.217"
    ::= { dlsEventObjects217 4 }

dls217_dest_sap OBJECT-TYPE
    SYNTAX Integer32
    MAX-ACCESS accessible-for-notify
    STATUS current
    DESCRIPTION
        "Parameter 'dest_sap' in event DLS.217"
    ::= { dlsEventObjects217 5 }

dlsEventObjects218 OBJECT-IDENTITY
    STATUS current
    DESCRIPTION
        "Event DLS.218
        While processing a XIDFRAME event, the DLS state
        machine discovered the event occurring in an unexpected state."
    ::= { dlsEventsGroup 218 }

dls218_state OBJECT-TYPE
    SYNTAX DisplayString
    MAX-ACCESS accessible-for-notify
    STATUS current
    DESCRIPTION
        "Parameter 'state' in event DLS.218"
    ::= { dlsEventObjects218 1 }

dls218_source_mac_address OBJECT-TYPE
    SYNTAX DisplayString
    MAX-ACCESS accessible-for-notify
    STATUS current
    DESCRIPTION
        "Parameter 'source_mac_address' in event DLS.218"
    ::= { dlsEventObjects218 2 }

dls218_dest_mac_address OBJECT-TYPE
    SYNTAX DisplayString
    MAX-ACCESS accessible-for-notify
    STATUS current
    DESCRIPTION
        "Parameter 'dest_mac_address' in event DLS.218"
    ::= { dlsEventObjects218 3 }

dls218_source_sap OBJECT-TYPE
    SYNTAX Integer32
    MAX-ACCESS accessible-for-notify
    STATUS current
    DESCRIPTION
        "Parameter 'source_sap' in event DLS.218"
    ::= { dlsEventObjects218 4 }

dls218_dest_sap OBJECT-TYPE
    SYNTAX Integer32
    MAX-ACCESS accessible-for-notify
    STATUS current
    DESCRIPTION
        "Parameter 'dest_sap' in event DLS.218"
    ::= { dlsEventObjects218 5 }

dlsEventObjects219 OBJECT-IDENTITY
    STATUS current
    DESCRIPTION
        "Event DLS.219
        While processing a DATAFRAME event, the DLS state
        machine discovered the event occurring in an unexpected state."
    ::= { dlsEventsGroup 219 }

dls219_state OBJECT-TYPE
    SYNTAX DisplayString
    MAX-ACCESS accessible-for-notify
    STATUS current
    DESCRIPTION
        "Parameter 'state' in event DLS.219"
    ::= { dlsEventObjects219 1 }

dls219_source_mac_address OBJECT-TYPE
    SYNTAX DisplayString
    MAX-ACCESS accessible-for-notify
    STATUS current
    DESCRIPTION
        "Parameter 'source_mac_address' in event DLS.219"
    ::= { dlsEventObjects219 2 }

dls219_dest_mac_address OBJECT-TYPE
    SYNTAX DisplayString
    MAX-ACCESS accessible-for-notify
    STATUS current
    DESCRIPTION
        "Parameter 'dest_mac_address' in event DLS.219"
    ::= { dlsEventObjects219 3 }

dls219_source_sap OBJECT-TYPE
    SYNTAX Integer32
    MAX-ACCESS accessible-for-notify
    STATUS current
    DESCRIPTION
        "Parameter 'source_sap' in event DLS.219"
    ::= { dlsEventObjects219 4 }

dls219_dest_sap OBJECT-TYPE
    SYNTAX Integer32
    MAX-ACCESS accessible-for-notify
    STATUS current
    DESCRIPTION
        "Parameter 'dest_sap' in event DLS.219"
    ::= { dlsEventObjects219 5 }

dlsEventObjects220 OBJECT-IDENTITY
    STATUS current
    DESCRIPTION
        "Event DLS.220
        While processing a CONTACT event, the DLS state
        machine discovered the event occurring in an unexpected state."
    ::= { dlsEventsGroup 220 }

dls220_state OBJECT-TYPE
    SYNTAX DisplayString
    MAX-ACCESS accessible-for-notify
    STATUS current
    DESCRIPTION
        "Parameter 'state' in event DLS.220"
    ::= { dlsEventObjects220 1 }

dls220_source_mac_address OBJECT-TYPE
    SYNTAX DisplayString
    MAX-ACCESS accessible-for-notify
    STATUS current
    DESCRIPTION
        "Parameter 'source_mac_address' in event DLS.220"
    ::= { dlsEventObjects220 2 }

dls220_dest_mac_address OBJECT-TYPE
    SYNTAX DisplayString
    MAX-ACCESS accessible-for-notify
    STATUS current
    DESCRIPTION
        "Parameter 'dest_mac_address' in event DLS.220"
    ::= { dlsEventObjects220 3 }

dls220_source_sap OBJECT-TYPE
    SYNTAX Integer32
    MAX-ACCESS accessible-for-notify
    STATUS current
    DESCRIPTION
        "Parameter 'source_sap' in event DLS.220"
    ::= { dlsEventObjects220 4 }

dls220_dest_sap OBJECT-TYPE
    SYNTAX Integer32
    MAX-ACCESS accessible-for-notify
    STATUS current
    DESCRIPTION
        "Parameter 'dest_sap' in event DLS.220"
    ::= { dlsEventObjects220 5 }

dlsEventObjects221 OBJECT-IDENTITY
    STATUS current
    DESCRIPTION
        "Event DLS.221
        While processing a CONTACTED event, the DLS state
        machine discovered the event occurring in an unexpected state."
    ::= { dlsEventsGroup 221 }

dls221_state OBJECT-TYPE
    SYNTAX DisplayString
    MAX-ACCESS accessible-for-notify
    STATUS current
    DESCRIPTION
        "Parameter 'state' in event DLS.221"
    ::= { dlsEventObjects221 1 }

dls221_source_mac_address OBJECT-TYPE
    SYNTAX DisplayString
    MAX-ACCESS accessible-for-notify
    STATUS current
    DESCRIPTION
        "Parameter 'source_mac_address' in event DLS.221"
    ::= { dlsEventObjects221 2 }

dls221_dest_mac_address OBJECT-TYPE
    SYNTAX DisplayString
    MAX-ACCESS accessible-for-notify
    STATUS current
    DESCRIPTION
        "Parameter 'dest_mac_address' in event DLS.221"
    ::= { dlsEventObjects221 3 }

dls221_source_sap OBJECT-TYPE
    SYNTAX Integer32
    MAX-ACCESS accessible-for-notify
    STATUS current
    DESCRIPTION
        "Parameter 'source_sap' in event DLS.221"
    ::= { dlsEventObjects221 4 }

dls221_dest_sap OBJECT-TYPE
    SYNTAX Integer32
    MAX-ACCESS accessible-for-notify
    STATUS current
    DESCRIPTION
        "Parameter 'dest_sap' in event DLS.221"
    ::= { dlsEventObjects221 5 }

dlsEventObjects222 OBJECT-IDENTITY
    STATUS current
    DESCRIPTION
        "Event DLS.222
        While processing a RESTART_DL event, the DLS state
        machine discovered the event occurring in an unexpected state."
    ::= { dlsEventsGroup 222 }

dls222_state OBJECT-TYPE
    SYNTAX DisplayString
    MAX-ACCESS accessible-for-notify
    STATUS current
    DESCRIPTION
        "Parameter 'state' in event DLS.222"
    ::= { dlsEventObjects222 1 }

dls222_source_mac_address OBJECT-TYPE
    SYNTAX DisplayString
    MAX-ACCESS accessible-for-notify
    STATUS current
    DESCRIPTION
        "Parameter 'source_mac_address' in event DLS.222"
    ::= { dlsEventObjects222 2 }

dls222_dest_mac_address OBJECT-TYPE
    SYNTAX DisplayString
    MAX-ACCESS accessible-for-notify
    STATUS current
    DESCRIPTION
        "Parameter 'dest_mac_address' in event DLS.222"
    ::= { dlsEventObjects222 3 }

dls222_source_sap OBJECT-TYPE
    SYNTAX Integer32
    MAX-ACCESS accessible-for-notify
    STATUS current
    DESCRIPTION
        "Parameter 'source_sap' in event DLS.222"
    ::= { dlsEventObjects222 4 }

dls222_dest_sap OBJECT-TYPE
    SYNTAX Integer32
    MAX-ACCESS accessible-for-notify
    STATUS current
    DESCRIPTION
        "Parameter 'dest_sap' in event DLS.222"
    ::= { dlsEventObjects222 5 }

dlsEventObjects223 OBJECT-IDENTITY
    STATUS current
    DESCRIPTION
        "Event DLS.223
        While processing a DL_RESTARTED event, the DLS state
        machine discovered the event occurring in an unexpected state."
    ::= { dlsEventsGroup 223 }

dls223_state OBJECT-TYPE
    SYNTAX DisplayString
    MAX-ACCESS accessible-for-notify
    STATUS current
    DESCRIPTION
        "Parameter 'state' in event DLS.223"
    ::= { dlsEventObjects223 1 }

dls223_source_mac_address OBJECT-TYPE
    SYNTAX DisplayString
    MAX-ACCESS accessible-for-notify
    STATUS current
    DESCRIPTION
        "Parameter 'source_mac_address' in event DLS.223"
    ::= { dlsEventObjects223 2 }

dls223_dest_mac_address OBJECT-TYPE
    SYNTAX DisplayString
    MAX-ACCESS accessible-for-notify
    STATUS current
    DESCRIPTION
        "Parameter 'dest_mac_address' in event DLS.223"
    ::= { dlsEventObjects223 3 }

dls223_source_sap OBJECT-TYPE
    SYNTAX Integer32
    MAX-ACCESS accessible-for-notify
    STATUS current
    DESCRIPTION
        "Parameter 'source_sap' in event DLS.223"
    ::= { dlsEventObjects223 4 }

dls223_dest_sap OBJECT-TYPE
    SYNTAX Integer32
    MAX-ACCESS accessible-for-notify
    STATUS current
    DESCRIPTION
        "Parameter 'dest_sap' in event DLS.223"
    ::= { dlsEventObjects223 5 }

dlsEventObjects224 OBJECT-IDENTITY
    STATUS current
    DESCRIPTION
        "Event DLS.224
        While processing an INFOFRAME event, the DLS state
        machine discovered the event occurring in an unexpected state."
    ::= { dlsEventsGroup 224 }

dls224_state OBJECT-TYPE
    SYNTAX DisplayString
    MAX-ACCESS accessible-for-notify
    STATUS current
    DESCRIPTION
        "Parameter 'state' in event DLS.224"
    ::= { dlsEventObjects224 1 }

dls224_source_mac_address OBJECT-TYPE
    SYNTAX DisplayString
    MAX-ACCESS accessible-for-notify
    STATUS current
    DESCRIPTION
        "Parameter 'source_mac_address' in event DLS.224"
    ::= { dlsEventObjects224 2 }

dls224_dest_mac_address OBJECT-TYPE
    SYNTAX DisplayString
    MAX-ACCESS accessible-for-notify
    STATUS current
    DESCRIPTION
        "Parameter 'dest_mac_address' in event DLS.224"
    ::= { dlsEventObjects224 3 }

dls224_source_sap OBJECT-TYPE
    SYNTAX Integer32
    MAX-ACCESS accessible-for-notify
    STATUS current
    DESCRIPTION
        "Parameter 'source_sap' in event DLS.224"
    ::= { dlsEventObjects224 4 }

dls224_dest_sap OBJECT-TYPE
    SYNTAX Integer32
    MAX-ACCESS accessible-for-notify
    STATUS current
    DESCRIPTION
        "Parameter 'dest_sap' in event DLS.224"
    ::= { dlsEventObjects224 5 }

dlsEventObjects225 OBJECT-IDENTITY
    STATUS current
    DESCRIPTION
        "Event DLS.225
        While processing a HALT_DL event, the DLS state
        machine discovered the event occurring in an unexpected state."
    ::= { dlsEventsGroup 225 }

dls225_state OBJECT-TYPE
    SYNTAX DisplayString
    MAX-ACCESS accessible-for-notify
    STATUS current
    DESCRIPTION
        "Parameter 'state' in event DLS.225"
    ::= { dlsEventObjects225 1 }

dls225_source_mac_address OBJECT-TYPE
    SYNTAX DisplayString
    MAX-ACCESS accessible-for-notify
    STATUS current
    DESCRIPTION
        "Parameter 'source_mac_address' in event DLS.225"
    ::= { dlsEventObjects225 2 }

dls225_dest_mac_address OBJECT-TYPE
    SYNTAX DisplayString
    MAX-ACCESS accessible-for-notify
    STATUS current
    DESCRIPTION
        "Parameter 'dest_mac_address' in event DLS.225"
    ::= { dlsEventObjects225 3 }

dls225_source_sap OBJECT-TYPE
    SYNTAX Integer32
    MAX-ACCESS accessible-for-notify
    STATUS current
    DESCRIPTION
        "Parameter 'source_sap' in event DLS.225"
    ::= { dlsEventObjects225 4 }

dls225_dest_sap OBJECT-TYPE
    SYNTAX Integer32
    MAX-ACCESS accessible-for-notify
    STATUS current
    DESCRIPTION
        "Parameter 'dest_sap' in event DLS.225"
    ::= { dlsEventObjects225 5 }

dlsEventObjects226 OBJECT-IDENTITY
    STATUS current
    DESCRIPTION
        "Event DLS.226
        While processing a HALT_DL_NOACK event, the DLS state
        machine discovered the event occurring in an unexpected state."
    ::= { dlsEventsGroup 226 }

dls226_state OBJECT-TYPE
    SYNTAX DisplayString
    MAX-ACCESS accessible-for-notify
    STATUS current
    DESCRIPTION
        "Parameter 'state' in event DLS.226"
    ::= { dlsEventObjects226 1 }

dls226_source_mac_address OBJECT-TYPE
    SYNTAX DisplayString
    MAX-ACCESS accessible-for-notify
    STATUS current
    DESCRIPTION
        "Parameter 'source_mac_address' in event DLS.226"
    ::= { dlsEventObjects226 2 }

dls226_dest_mac_address OBJECT-TYPE
    SYNTAX DisplayString
    MAX-ACCESS accessible-for-notify
    STATUS current
    DESCRIPTION
        "Parameter 'dest_mac_address' in event DLS.226"
    ::= { dlsEventObjects226 3 }

dls226_source_sap OBJECT-TYPE
    SYNTAX Integer32
    MAX-ACCESS accessible-for-notify
    STATUS current
    DESCRIPTION
        "Parameter 'source_sap' in event DLS.226"
    ::= { dlsEventObjects226 4 }

dls226_dest_sap OBJECT-TYPE
    SYNTAX Integer32
    MAX-ACCESS accessible-for-notify
    STATUS current
    DESCRIPTION
        "Parameter 'dest_sap' in event DLS.226"
    ::= { dlsEventObjects226 5 }

dlsEventObjects227 OBJECT-IDENTITY
    STATUS current
    DESCRIPTION
        "Event DLS.227
        While processing a DL_HALTED event, the DLS state
        machine discovered the event occurring in an unexpected state."
    ::= { dlsEventsGroup 227 }

dls227_state OBJECT-TYPE
    SYNTAX DisplayString
    MAX-ACCESS accessible-for-notify
    STATUS current
    DESCRIPTION
        "Parameter 'state' in event DLS.227"
    ::= { dlsEventObjects227 1 }

dls227_source_mac_address OBJECT-TYPE
    SYNTAX DisplayString
    MAX-ACCESS accessible-for-notify
    STATUS current
    DESCRIPTION
        "Parameter 'source_mac_address' in event DLS.227"
    ::= { dlsEventObjects227 2 }

dls227_dest_mac_address OBJECT-TYPE
    SYNTAX DisplayString
    MAX-ACCESS accessible-for-notify
    STATUS current
    DESCRIPTION
        "Parameter 'dest_mac_address' in event DLS.227"
    ::= { dlsEventObjects227 3 }

dls227_source_sap OBJECT-TYPE
    SYNTAX Integer32
    MAX-ACCESS accessible-for-notify
    STATUS current
    DESCRIPTION
        "Parameter 'source_sap' in event DLS.227"
    ::= { dlsEventObjects227 4 }

dls227_dest_sap OBJECT-TYPE
    SYNTAX Integer32
    MAX-ACCESS accessible-for-notify
    STATUS current
    DESCRIPTION
        "Parameter 'dest_sap' in event DLS.227"
    ::= { dlsEventObjects227 5 }

dlsEventObjects228 OBJECT-IDENTITY
    STATUS current
    DESCRIPTION
        "Event DLS.228
        While processing an ENTER_BUSY event, the DLS state
        machine discovered the event occurring in an unexpected state."
    ::= { dlsEventsGroup 228 }

dls228_state OBJECT-TYPE
    SYNTAX DisplayString
    MAX-ACCESS accessible-for-notify
    STATUS current
    DESCRIPTION
        "Parameter 'state' in event DLS.228"
    ::= { dlsEventObjects228 1 }

dls228_source_mac_address OBJECT-TYPE
    SYNTAX DisplayString
    MAX-ACCESS accessible-for-notify
    STATUS current
    DESCRIPTION
        "Parameter 'source_mac_address' in event DLS.228"
    ::= { dlsEventObjects228 2 }

dls228_dest_mac_address OBJECT-TYPE
    SYNTAX DisplayString
    MAX-ACCESS accessible-for-notify
    STATUS current
    DESCRIPTION
        "Parameter 'dest_mac_address' in event DLS.228"
    ::= { dlsEventObjects228 3 }

dls228_source_sap OBJECT-TYPE
    SYNTAX Integer32
    MAX-ACCESS accessible-for-notify
    STATUS current
    DESCRIPTION
        "Parameter 'source_sap' in event DLS.228"
    ::= { dlsEventObjects228 4 }

dls228_dest_sap OBJECT-TYPE
    SYNTAX Integer32
    MAX-ACCESS accessible-for-notify
    STATUS current
    DESCRIPTION
        "Parameter 'dest_sap' in event DLS.228"
    ::= { dlsEventObjects228 5 }

dlsEventObjects229 OBJECT-IDENTITY
    STATUS current
    DESCRIPTION
        "Event DLS.229
        While processing an EXIT_BUSY event, the DLS state
        machine discovered the event occurring in an unexpected state."
    ::= { dlsEventsGroup 229 }

dls229_state OBJECT-TYPE
    SYNTAX DisplayString
    MAX-ACCESS accessible-for-notify
    STATUS current
    DESCRIPTION
        "Parameter 'state' in event DLS.229"
    ::= { dlsEventObjects229 1 }

dls229_source_mac_address OBJECT-TYPE
    SYNTAX DisplayString
    MAX-ACCESS accessible-for-notify
    STATUS current
    DESCRIPTION
        "Parameter 'source_mac_address' in event DLS.229"
    ::= { dlsEventObjects229 2 }

dls229_dest_mac_address OBJECT-TYPE
    SYNTAX DisplayString
    MAX-ACCESS accessible-for-notify
    STATUS current
    DESCRIPTION
        "Parameter 'dest_mac_address' in event DLS.229"
    ::= { dlsEventObjects229 3 }

dls229_source_sap OBJECT-TYPE
    SYNTAX Integer32
    MAX-ACCESS accessible-for-notify
    STATUS current
    DESCRIPTION
        "Parameter 'source_sap' in event DLS.229"
    ::= { dlsEventObjects229 4 }

dls229_dest_sap OBJECT-TYPE
    SYNTAX Integer32
    MAX-ACCESS accessible-for-notify
    STATUS current
    DESCRIPTION
        "Parameter 'dest_sap' in event DLS.229"
    ::= { dlsEventObjects229 5 }

dlsEventObjects230 OBJECT-IDENTITY
    STATUS current
    DESCRIPTION
        "Event DLS.230
        While processing a REACHACK event, the DLS state
        machine discovered the event occurring in an unexpected state."
    ::= { dlsEventsGroup 230 }

dls230_state OBJECT-TYPE
    SYNTAX DisplayString
    MAX-ACCESS accessible-for-notify
    STATUS current
    DESCRIPTION
        "Parameter 'state' in event DLS.230"
    ::= { dlsEventObjects230 1 }

dls230_source_mac_address OBJECT-TYPE
    SYNTAX DisplayString
    MAX-ACCESS accessible-for-notify
    STATUS current
    DESCRIPTION
        "Parameter 'source_mac_address' in event DLS.230"
    ::= { dlsEventObjects230 2 }

dls230_dest_mac_address OBJECT-TYPE
    SYNTAX DisplayString
    MAX-ACCESS accessible-for-notify
    STATUS current
    DESCRIPTION
        "Parameter 'dest_mac_address' in event DLS.230"
    ::= { dlsEventObjects230 3 }

dls230_source_sap OBJECT-TYPE
    SYNTAX Integer32
    MAX-ACCESS accessible-for-notify
    STATUS current
    DESCRIPTION
        "Parameter 'source_sap' in event DLS.230"
    ::= { dlsEventObjects230 4 }

dls230_dest_sap OBJECT-TYPE
    SYNTAX Integer32
    MAX-ACCESS accessible-for-notify
    STATUS current
    DESCRIPTION
        "Parameter 'dest_sap' in event DLS.230"
    ::= { dlsEventObjects230 5 }

dlsEventObjects231 OBJECT-IDENTITY
    STATUS current
    DESCRIPTION
        "Event DLS.231
        DLS successfully sent out a CANUREACH SSP message over TCP to its
        DLS peer."
    ::= { dlsEventsGroup 231 }

dls231_ip_address OBJECT-TYPE
    SYNTAX IpAddress
    MAX-ACCESS accessible-for-notify
    STATUS current
    DESCRIPTION
        "Parameter 'ip_address' in event DLS.231"
    ::= { dlsEventObjects231 1 }

dls231_source_mac_address OBJECT-TYPE
    SYNTAX DisplayString
    MAX-ACCESS accessible-for-notify
    STATUS current
    DESCRIPTION
        "Parameter 'source_mac_address' in event DLS.231"
    ::= { dlsEventObjects231 2 }

dls231_dest_mac_address OBJECT-TYPE
    SYNTAX DisplayString
    MAX-ACCESS accessible-for-notify
    STATUS current
    DESCRIPTION
        "Parameter 'dest_mac_address' in event DLS.231"
    ::= { dlsEventObjects231 3 }

dls231_source_sap OBJECT-TYPE
    SYNTAX Integer32
    MAX-ACCESS accessible-for-notify
    STATUS current
    DESCRIPTION
        "Parameter 'source_sap' in event DLS.231"
    ::= { dlsEventObjects231 4 }

dls231_dest_sap OBJECT-TYPE
    SYNTAX Integer32
    MAX-ACCESS accessible-for-notify
    STATUS current
    DESCRIPTION
        "Parameter 'dest_sap' in event DLS.231"
    ::= { dlsEventObjects231 5 }

dlsEventObjects232 OBJECT-IDENTITY
    STATUS current
    DESCRIPTION
        "Event DLS.232
        DLS successfully sent out an ICANREACH SSP message over TCP to its
        DLS peer."
    ::= { dlsEventsGroup 232 }

dls232_ip_address OBJECT-TYPE
    SYNTAX IpAddress
    MAX-ACCESS accessible-for-notify
    STATUS current
    DESCRIPTION
        "Parameter 'ip_address' in event DLS.232"
    ::= { dlsEventObjects232 1 }

dls232_source_mac_address OBJECT-TYPE
    SYNTAX DisplayString
    MAX-ACCESS accessible-for-notify
    STATUS current
    DESCRIPTION
        "Parameter 'source_mac_address' in event DLS.232"
    ::= { dlsEventObjects232 2 }

dls232_dest_mac_address OBJECT-TYPE
    SYNTAX DisplayString
    MAX-ACCESS accessible-for-notify
    STATUS current
    DESCRIPTION
        "Parameter 'dest_mac_address' in event DLS.232"
    ::= { dlsEventObjects232 3 }

dls232_source_sap OBJECT-TYPE
    SYNTAX Integer32
    MAX-ACCESS accessible-for-notify
    STATUS current
    DESCRIPTION
        "Parameter 'source_sap' in event DLS.232"
    ::= { dlsEventObjects232 4 }

dls232_dest_sap OBJECT-TYPE
    SYNTAX Integer32
    MAX-ACCESS accessible-for-notify
    STATUS current
    DESCRIPTION
        "Parameter 'dest_sap' in event DLS.232"
    ::= { dlsEventObjects232 5 }

dlsEventObjects233 OBJECT-IDENTITY
    STATUS current
    DESCRIPTION
        "Event DLS.233
        DLS successfully sent out a REACH_ACK SSP message over TCP to its
        DLS peer."
    ::= { dlsEventsGroup 233 }

dls233_ip_address OBJECT-TYPE
    SYNTAX IpAddress
    MAX-ACCESS accessible-for-notify
    STATUS current
    DESCRIPTION
        "Parameter 'ip_address' in event DLS.233"
    ::= { dlsEventObjects233 1 }

dls233_source_mac_address OBJECT-TYPE
    SYNTAX DisplayString
    MAX-ACCESS accessible-for-notify
    STATUS current
    DESCRIPTION
        "Parameter 'source_mac_address' in event DLS.233"
    ::= { dlsEventObjects233 2 }

dls233_dest_mac_address OBJECT-TYPE
    SYNTAX DisplayString
    MAX-ACCESS accessible-for-notify
    STATUS current
    DESCRIPTION
        "Parameter 'dest_mac_address' in event DLS.233"
    ::= { dlsEventObjects233 3 }

dls233_source_sap OBJECT-TYPE
    SYNTAX Integer32
    MAX-ACCESS accessible-for-notify
    STATUS current
    DESCRIPTION
        "Parameter 'source_sap' in event DLS.233"
    ::= { dlsEventObjects233 4 }

dls233_dest_sap OBJECT-TYPE
    SYNTAX Integer32
    MAX-ACCESS accessible-for-notify
    STATUS current
    DESCRIPTION
        "Parameter 'dest_sap' in event DLS.233"
    ::= { dlsEventObjects233 5 }

dlsEventObjects234 OBJECT-IDENTITY
    STATUS current
    DESCRIPTION
        "Event DLS.234
        DLS successfully sent out a CONTACT SSP message over TCP to its
        DLS peer."
    ::= { dlsEventsGroup 234 }

dls234_ip_address OBJECT-TYPE
    SYNTAX IpAddress
    MAX-ACCESS accessible-for-notify
    STATUS current
    DESCRIPTION
        "Parameter 'ip_address' in event DLS.234"
    ::= { dlsEventObjects234 1 }

dls234_source_mac_address OBJECT-TYPE
    SYNTAX DisplayString
    MAX-ACCESS accessible-for-notify
    STATUS current
    DESCRIPTION
        "Parameter 'source_mac_address' in event DLS.234"
    ::= { dlsEventObjects234 2 }

dls234_dest_mac_address OBJECT-TYPE
    SYNTAX DisplayString
    MAX-ACCESS accessible-for-notify
    STATUS current
    DESCRIPTION
        "Parameter 'dest_mac_address' in event DLS.234"
    ::= { dlsEventObjects234 3 }

dls234_source_sap OBJECT-TYPE
    SYNTAX Integer32
    MAX-ACCESS accessible-for-notify
    STATUS current
    DESCRIPTION
        "Parameter 'source_sap' in event DLS.234"
    ::= { dlsEventObjects234 4 }

dls234_dest_sap OBJECT-TYPE
    SYNTAX Integer32
    MAX-ACCESS accessible-for-notify
    STATUS current
    DESCRIPTION
        "Parameter 'dest_sap' in event DLS.234"
    ::= { dlsEventObjects234 5 }

dlsEventObjects235 OBJECT-IDENTITY
    STATUS current
    DESCRIPTION
        "Event DLS.235
        DLS successfully sent out a CONTACTED SSP message over TCP to its
        DLS peer."
    ::= { dlsEventsGroup 235 }

dls235_ip_address OBJECT-TYPE
    SYNTAX IpAddress
    MAX-ACCESS accessible-for-notify
    STATUS current
    DESCRIPTION
        "Parameter 'ip_address' in event DLS.235"
    ::= { dlsEventObjects235 1 }

dls235_source_mac_address OBJECT-TYPE
    SYNTAX DisplayString
    MAX-ACCESS accessible-for-notify
    STATUS current
    DESCRIPTION
        "Parameter 'source_mac_address' in event DLS.235"
    ::= { dlsEventObjects235 2 }

dls235_dest_mac_address OBJECT-TYPE
    SYNTAX DisplayString
    MAX-ACCESS accessible-for-notify
    STATUS current
    DESCRIPTION
        "Parameter 'dest_mac_address' in event DLS.235"
    ::= { dlsEventObjects235 3 }

dls235_source_sap OBJECT-TYPE
    SYNTAX Integer32
    MAX-ACCESS accessible-for-notify
    STATUS current
    DESCRIPTION
        "Parameter 'source_sap' in event DLS.235"
    ::= { dlsEventObjects235 4 }

dls235_dest_sap OBJECT-TYPE
    SYNTAX Integer32
    MAX-ACCESS accessible-for-notify
    STATUS current
    DESCRIPTION
        "Parameter 'dest_sap' in event DLS.235"
    ::= { dlsEventObjects235 5 }

dlsEventObjects236 OBJECT-IDENTITY
    STATUS current
    DESCRIPTION
        "Event DLS.236
        DLS successfully sent out a RESTART_DL SSP message over TCP to its
        DLS peer."
    ::= { dlsEventsGroup 236 }

dls236_ip_address OBJECT-TYPE
    SYNTAX IpAddress
    MAX-ACCESS accessible-for-notify
    STATUS current
    DESCRIPTION
        "Parameter 'ip_address' in event DLS.236"
    ::= { dlsEventObjects236 1 }

dls236_source_mac_address OBJECT-TYPE
    SYNTAX DisplayString
    MAX-ACCESS accessible-for-notify
    STATUS current
    DESCRIPTION
        "Parameter 'source_mac_address' in event DLS.236"
    ::= { dlsEventObjects236 2 }

dls236_dest_mac_address OBJECT-TYPE
    SYNTAX DisplayString
    MAX-ACCESS accessible-for-notify
    STATUS current
    DESCRIPTION
        "Parameter 'dest_mac_address' in event DLS.236"
    ::= { dlsEventObjects236 3 }

dls236_source_sap OBJECT-TYPE
    SYNTAX Integer32
    MAX-ACCESS accessible-for-notify
    STATUS current
    DESCRIPTION
        "Parameter 'source_sap' in event DLS.236"
    ::= { dlsEventObjects236 4 }

dls236_dest_sap OBJECT-TYPE
    SYNTAX Integer32
    MAX-ACCESS accessible-for-notify
    STATUS current
    DESCRIPTION
        "Parameter 'dest_sap' in event DLS.236"
    ::= { dlsEventObjects236 5 }

dlsEventObjects237 OBJECT-IDENTITY
    STATUS current
    DESCRIPTION
        "Event DLS.237
        DLS successfully sent out a DL_RESTARTED SSP message over TCP to its
        DLS peer."
    ::= { dlsEventsGroup 237 }

dls237_ip_address OBJECT-TYPE
    SYNTAX IpAddress
    MAX-ACCESS accessible-for-notify
    STATUS current
    DESCRIPTION
        "Parameter 'ip_address' in event DLS.237"
    ::= { dlsEventObjects237 1 }

dls237_source_mac_address OBJECT-TYPE
    SYNTAX DisplayString
    MAX-ACCESS accessible-for-notify
    STATUS current
    DESCRIPTION
        "Parameter 'source_mac_address' in event DLS.237"
    ::= { dlsEventObjects237 2 }

dls237_dest_mac_address OBJECT-TYPE
    SYNTAX DisplayString
    MAX-ACCESS accessible-for-notify
    STATUS current
    DESCRIPTION
        "Parameter 'dest_mac_address' in event DLS.237"
    ::= { dlsEventObjects237 3 }

dls237_source_sap OBJECT-TYPE
    SYNTAX Integer32
    MAX-ACCESS accessible-for-notify
    STATUS current
    DESCRIPTION
        "Parameter 'source_sap' in event DLS.237"
    ::= { dlsEventObjects237 4 }

dls237_dest_sap OBJECT-TYPE
    SYNTAX Integer32
    MAX-ACCESS accessible-for-notify
    STATUS current
    DESCRIPTION
        "Parameter 'dest_sap' in event DLS.237"
    ::= { dlsEventObjects237 5 }

dlsEventObjects238 OBJECT-IDENTITY
    STATUS current
    DESCRIPTION
        "Event DLS.238
        DLS successfully sent out an ENTER_BUSY SSP message over TCP to its
        DLS peer."
    ::= { dlsEventsGroup 238 }

dls238_ip_address OBJECT-TYPE
    SYNTAX IpAddress
    MAX-ACCESS accessible-for-notify
    STATUS current
    DESCRIPTION
        "Parameter 'ip_address' in event DLS.238"
    ::= { dlsEventObjects238 1 }

dls238_source_mac_address OBJECT-TYPE
    SYNTAX DisplayString
    MAX-ACCESS accessible-for-notify
    STATUS current
    DESCRIPTION
        "Parameter 'source_mac_address' in event DLS.238"
    ::= { dlsEventObjects238 2 }

dls238_dest_mac_address OBJECT-TYPE
    SYNTAX DisplayString
    MAX-ACCESS accessible-for-notify
    STATUS current
    DESCRIPTION
        "Parameter 'dest_mac_address' in event DLS.238"
    ::= { dlsEventObjects238 3 }

dls238_source_sap OBJECT-TYPE
    SYNTAX Integer32
    MAX-ACCESS accessible-for-notify
    STATUS current
    DESCRIPTION
        "Parameter 'source_sap' in event DLS.238"
    ::= { dlsEventObjects238 4 }

dls238_dest_sap OBJECT-TYPE
    SYNTAX Integer32
    MAX-ACCESS accessible-for-notify
    STATUS current
    DESCRIPTION
        "Parameter 'dest_sap' in event DLS.238"
    ::= { dlsEventObjects238 5 }

dlsEventObjects239 OBJECT-IDENTITY
    STATUS current
    DESCRIPTION
        "Event DLS.239
        DLS successfully sent out an EXIT_BUSY SSP message over TCP to its
        DLS peer."
    ::= { dlsEventsGroup 239 }

dls239_ip_address OBJECT-TYPE
    SYNTAX IpAddress
    MAX-ACCESS accessible-for-notify
    STATUS current
    DESCRIPTION
        "Parameter 'ip_address' in event DLS.239"
    ::= { dlsEventObjects239 1 }

dls239_source_mac_address OBJECT-TYPE
    SYNTAX DisplayString
    MAX-ACCESS accessible-for-notify
    STATUS current
    DESCRIPTION
        "Parameter 'source_mac_address' in event DLS.239"
    ::= { dlsEventObjects239 2 }

dls239_dest_mac_address OBJECT-TYPE
    SYNTAX DisplayString
    MAX-ACCESS accessible-for-notify
    STATUS current
    DESCRIPTION
        "Parameter 'dest_mac_address' in event DLS.239"
    ::= { dlsEventObjects239 3 }

dls239_source_sap OBJECT-TYPE
    SYNTAX Integer32
    MAX-ACCESS accessible-for-notify
    STATUS current
    DESCRIPTION
        "Parameter 'source_sap' in event DLS.239"
    ::= { dlsEventObjects239 4 }

dls239_dest_sap OBJECT-TYPE
    SYNTAX Integer32
    MAX-ACCESS accessible-for-notify
    STATUS current
    DESCRIPTION
        "Parameter 'dest_sap' in event DLS.239"
    ::= { dlsEventObjects239 5 }

dlsEventObjects240 OBJECT-IDENTITY
    STATUS current
    DESCRIPTION
        "Event DLS.240
        DLS successfully sent out a HALT_DL SSP message over TCP to its
        DLS peer."
    ::= { dlsEventsGroup 240 }

dls240_ip_address OBJECT-TYPE
    SYNTAX IpAddress
    MAX-ACCESS accessible-for-notify
    STATUS current
    DESCRIPTION
        "Parameter 'ip_address' in event DLS.240"
    ::= { dlsEventObjects240 1 }

dls240_source_mac_address OBJECT-TYPE
    SYNTAX DisplayString
    MAX-ACCESS accessible-for-notify
    STATUS current
    DESCRIPTION
        "Parameter 'source_mac_address' in event DLS.240"
    ::= { dlsEventObjects240 2 }

dls240_dest_mac_address OBJECT-TYPE
    SYNTAX DisplayString
    MAX-ACCESS accessible-for-notify
    STATUS current
    DESCRIPTION
        "Parameter 'dest_mac_address' in event DLS.240"
    ::= { dlsEventObjects240 3 }

dls240_source_sap OBJECT-TYPE
    SYNTAX Integer32
    MAX-ACCESS accessible-for-notify
    STATUS current
    DESCRIPTION
        "Parameter 'source_sap' in event DLS.240"
    ::= { dlsEventObjects240 4 }

dls240_dest_sap OBJECT-TYPE
    SYNTAX Integer32
    MAX-ACCESS accessible-for-notify
    STATUS current
    DESCRIPTION
        "Parameter 'dest_sap' in event DLS.240"
    ::= { dlsEventObjects240 5 }

dlsEventObjects241 OBJECT-IDENTITY
    STATUS current
    DESCRIPTION
        "Event DLS.241
        DLS successfully sent out a DL_HALTED SSP message over TCP to its
        DLS peer."
    ::= { dlsEventsGroup 241 }

dls241_ip_address OBJECT-TYPE
    SYNTAX IpAddress
    MAX-ACCESS accessible-for-notify
    STATUS current
    DESCRIPTION
        "Parameter 'ip_address' in event DLS.241"
    ::= { dlsEventObjects241 1 }

dls241_source_mac_address OBJECT-TYPE
    SYNTAX DisplayString
    MAX-ACCESS accessible-for-notify
    STATUS current
    DESCRIPTION
        "Parameter 'source_mac_address' in event DLS.241"
    ::= { dlsEventObjects241 2 }

dls241_dest_mac_address OBJECT-TYPE
    SYNTAX DisplayString
    MAX-ACCESS accessible-for-notify
    STATUS current
    DESCRIPTION
        "Parameter 'dest_mac_address' in event DLS.241"
    ::= { dlsEventObjects241 3 }

dls241_source_sap OBJECT-TYPE
    SYNTAX Integer32
    MAX-ACCESS accessible-for-notify
    STATUS current
    DESCRIPTION
        "Parameter 'source_sap' in event DLS.241"
    ::= { dlsEventObjects241 4 }

dls241_dest_sap OBJECT-TYPE
    SYNTAX Integer32
    MAX-ACCESS accessible-for-notify
    STATUS current
    DESCRIPTION
        "Parameter 'dest_sap' in event DLS.241"
    ::= { dlsEventObjects241 5 }

dlsEventObjects242 OBJECT-IDENTITY
    STATUS current
    DESCRIPTION
        "Event DLS.242
        DLS successfully sent out a HALT_DL_NOACK SSP message over TCP to its
        DLS peer."
    ::= { dlsEventsGroup 242 }

dls242_ip_address OBJECT-TYPE
    SYNTAX IpAddress
    MAX-ACCESS accessible-for-notify
    STATUS current
    DESCRIPTION
        "Parameter 'ip_address' in event DLS.242"
    ::= { dlsEventObjects242 1 }

dls242_source_mac_address OBJECT-TYPE
    SYNTAX DisplayString
    MAX-ACCESS accessible-for-notify
    STATUS current
    DESCRIPTION
        "Parameter 'source_mac_address' in event DLS.242"
    ::= { dlsEventObjects242 2 }

dls242_dest_mac_address OBJECT-TYPE
    SYNTAX DisplayString
    MAX-ACCESS accessible-for-notify
    STATUS current
    DESCRIPTION
        "Parameter 'dest_mac_address' in event DLS.242"
    ::= { dlsEventObjects242 3 }

dls242_source_sap OBJECT-TYPE
    SYNTAX Integer32
    MAX-ACCESS accessible-for-notify
    STATUS current
    DESCRIPTION
        "Parameter 'source_sap' in event DLS.242"
    ::= { dlsEventObjects242 4 }

dls242_dest_sap OBJECT-TYPE
    SYNTAX Integer32
    MAX-ACCESS accessible-for-notify
    STATUS current
    DESCRIPTION
        "Parameter 'dest_sap' in event DLS.242"
    ::= { dlsEventObjects242 5 }

dlsEventObjects243 OBJECT-IDENTITY
    STATUS current
    DESCRIPTION
        "Event DLS.243
        DLS successfully sent out a TEST_CIRCUIT_RSP SSP message over TCP to
        its DLS peer."
    ::= { dlsEventsGroup 243 }

dls243_ip_address OBJECT-TYPE
    SYNTAX IpAddress
    MAX-ACCESS accessible-for-notify
    STATUS current
    DESCRIPTION
        "Parameter 'ip_address' in event DLS.243"
    ::= { dlsEventObjects243 1 }

dls243_source_mac_address OBJECT-TYPE
    SYNTAX DisplayString
    MAX-ACCESS accessible-for-notify
    STATUS current
    DESCRIPTION
        "Parameter 'source_mac_address' in event DLS.243"
    ::= { dlsEventObjects243 2 }

dls243_dest_mac_address OBJECT-TYPE
    SYNTAX DisplayString
    MAX-ACCESS accessible-for-notify
    STATUS current
    DESCRIPTION
        "Parameter 'dest_mac_address' in event DLS.243"
    ::= { dlsEventObjects243 3 }

dls243_source_sap OBJECT-TYPE
    SYNTAX Integer32
    MAX-ACCESS accessible-for-notify
    STATUS current
    DESCRIPTION
        "Parameter 'source_sap' in event DLS.243"
    ::= { dlsEventObjects243 4 }

dls243_dest_sap OBJECT-TYPE
    SYNTAX Integer32
    MAX-ACCESS accessible-for-notify
    STATUS current
    DESCRIPTION
        "Parameter 'dest_sap' in event DLS.243"
    ::= { dlsEventObjects243 5 }

dlsEventObjects244 OBJECT-IDENTITY
    STATUS current
    DESCRIPTION
        "Event DLS.244
        Due to some problems with TCP connection to its DLS peer, a
        CANUREACH SSP control message could not be sent out."
    ::= { dlsEventsGroup 244 }

dls244_ip_address OBJECT-TYPE
    SYNTAX IpAddress
    MAX-ACCESS accessible-for-notify
    STATUS current
    DESCRIPTION
        "Parameter 'ip_address' in event DLS.244"
    ::= { dlsEventObjects244 1 }

dls244_source_mac_address OBJECT-TYPE
    SYNTAX DisplayString
    MAX-ACCESS accessible-for-notify
    STATUS current
    DESCRIPTION
        "Parameter 'source_mac_address' in event DLS.244"
    ::= { dlsEventObjects244 2 }

dls244_dest_mac_address OBJECT-TYPE
    SYNTAX DisplayString
    MAX-ACCESS accessible-for-notify
    STATUS current
    DESCRIPTION
        "Parameter 'dest_mac_address' in event DLS.244"
    ::= { dlsEventObjects244 3 }

dls244_source_sap OBJECT-TYPE
    SYNTAX Integer32
    MAX-ACCESS accessible-for-notify
    STATUS current
    DESCRIPTION
        "Parameter 'source_sap' in event DLS.244"
    ::= { dlsEventObjects244 4 }

dls244_dest_sap OBJECT-TYPE
    SYNTAX Integer32
    MAX-ACCESS accessible-for-notify
    STATUS current
    DESCRIPTION
        "Parameter 'dest_sap' in event DLS.244"
    ::= { dlsEventObjects244 5 }

dlsEventObjects245 OBJECT-IDENTITY
    STATUS current
    DESCRIPTION
        "Event DLS.245
        Due to some problems with TCP connection to its DLS peer, an
        ICANREACH SSP control message could not be sent out."
    ::= { dlsEventsGroup 245 }

dls245_ip_address OBJECT-TYPE
    SYNTAX IpAddress
    MAX-ACCESS accessible-for-notify
    STATUS current
    DESCRIPTION
        "Parameter 'ip_address' in event DLS.245"
    ::= { dlsEventObjects245 1 }

dls245_source_mac_address OBJECT-TYPE
    SYNTAX DisplayString
    MAX-ACCESS accessible-for-notify
    STATUS current
    DESCRIPTION
        "Parameter 'source_mac_address' in event DLS.245"
    ::= { dlsEventObjects245 2 }

dls245_dest_mac_address OBJECT-TYPE
    SYNTAX DisplayString
    MAX-ACCESS accessible-for-notify
    STATUS current
    DESCRIPTION
        "Parameter 'dest_mac_address' in event DLS.245"
    ::= { dlsEventObjects245 3 }

dls245_source_sap OBJECT-TYPE
    SYNTAX Integer32
    MAX-ACCESS accessible-for-notify
    STATUS current
    DESCRIPTION
        "Parameter 'source_sap' in event DLS.245"
    ::= { dlsEventObjects245 4 }

dls245_dest_sap OBJECT-TYPE
    SYNTAX Integer32
    MAX-ACCESS accessible-for-notify
    STATUS current
    DESCRIPTION
        "Parameter 'dest_sap' in event DLS.245"
    ::= { dlsEventObjects245 5 }

dlsEventObjects246 OBJECT-IDENTITY
    STATUS current
    DESCRIPTION
        "Event DLS.246
        Due to some problems with TCP connection to its DLS peer, a
        REACH_ACK SSP control message could not be sent out."
    ::= { dlsEventsGroup 246 }

dls246_ip_address OBJECT-TYPE
    SYNTAX IpAddress
    MAX-ACCESS accessible-for-notify
    STATUS current
    DESCRIPTION
        "Parameter 'ip_address' in event DLS.246"
    ::= { dlsEventObjects246 1 }

dls246_source_mac_address OBJECT-TYPE
    SYNTAX DisplayString
    MAX-ACCESS accessible-for-notify
    STATUS current
    DESCRIPTION
        "Parameter 'source_mac_address' in event DLS.246"
    ::= { dlsEventObjects246 2 }

dls246_dest_mac_address OBJECT-TYPE
    SYNTAX DisplayString
    MAX-ACCESS accessible-for-notify
    STATUS current
    DESCRIPTION
        "Parameter 'dest_mac_address' in event DLS.246"
    ::= { dlsEventObjects246 3 }

dls246_source_sap OBJECT-TYPE
    SYNTAX Integer32
    MAX-ACCESS accessible-for-notify
    STATUS current
    DESCRIPTION
        "Parameter 'source_sap' in event DLS.246"
    ::= { dlsEventObjects246 4 }

dls246_dest_sap OBJECT-TYPE
    SYNTAX Integer32
    MAX-ACCESS accessible-for-notify
    STATUS current
    DESCRIPTION
        "Parameter 'dest_sap' in event DLS.246"
    ::= { dlsEventObjects246 5 }

dlsEventObjects247 OBJECT-IDENTITY
    STATUS current
    DESCRIPTION
        "Event DLS.247
        Due to some problems with TCP connection to its DLS peer, a
        CONTACT SSP control message could not be sent out."
    ::= { dlsEventsGroup 247 }

dls247_ip_address OBJECT-TYPE
    SYNTAX IpAddress
    MAX-ACCESS accessible-for-notify
    STATUS current
    DESCRIPTION
        "Parameter 'ip_address' in event DLS.247"
    ::= { dlsEventObjects247 1 }

dls247_source_mac_address OBJECT-TYPE
    SYNTAX DisplayString
    MAX-ACCESS accessible-for-notify
    STATUS current
    DESCRIPTION
        "Parameter 'source_mac_address' in event DLS.247"
    ::= { dlsEventObjects247 2 }

dls247_dest_mac_address OBJECT-TYPE
    SYNTAX DisplayString
    MAX-ACCESS accessible-for-notify
    STATUS current
    DESCRIPTION
        "Parameter 'dest_mac_address' in event DLS.247"
    ::= { dlsEventObjects247 3 }

dls247_source_sap OBJECT-TYPE
    SYNTAX Integer32
    MAX-ACCESS accessible-for-notify
    STATUS current
    DESCRIPTION
        "Parameter 'source_sap' in event DLS.247"
    ::= { dlsEventObjects247 4 }

dls247_dest_sap OBJECT-TYPE
    SYNTAX Integer32
    MAX-ACCESS accessible-for-notify
    STATUS current
    DESCRIPTION
        "Parameter 'dest_sap' in event DLS.247"
    ::= { dlsEventObjects247 5 }

dlsEventObjects248 OBJECT-IDENTITY
    STATUS current
    DESCRIPTION
        "Event DLS.248
        Due to some problems with TCP connection to its DLS peer, a
        CONTACTED SSP control message could not be sent out."
    ::= { dlsEventsGroup 248 }

dls248_ip_address OBJECT-TYPE
    SYNTAX IpAddress
    MAX-ACCESS accessible-for-notify
    STATUS current
    DESCRIPTION
        "Parameter 'ip_address' in event DLS.248"
    ::= { dlsEventObjects248 1 }

dls248_source_mac_address OBJECT-TYPE
    SYNTAX DisplayString
    MAX-ACCESS accessible-for-notify
    STATUS current
    DESCRIPTION
        "Parameter 'source_mac_address' in event DLS.248"
    ::= { dlsEventObjects248 2 }

dls248_dest_mac_address OBJECT-TYPE
    SYNTAX DisplayString
    MAX-ACCESS accessible-for-notify
    STATUS current
    DESCRIPTION
        "Parameter 'dest_mac_address' in event DLS.248"
    ::= { dlsEventObjects248 3 }

dls248_source_sap OBJECT-TYPE
    SYNTAX Integer32
    MAX-ACCESS accessible-for-notify
    STATUS current
    DESCRIPTION
        "Parameter 'source_sap' in event DLS.248"
    ::= { dlsEventObjects248 4 }

dls248_dest_sap OBJECT-TYPE
    SYNTAX Integer32
    MAX-ACCESS accessible-for-notify
    STATUS current
    DESCRIPTION
        "Parameter 'dest_sap' in event DLS.248"
    ::= { dlsEventObjects248 5 }

dlsEventObjects249 OBJECT-IDENTITY
    STATUS current
    DESCRIPTION
        "Event DLS.249
        Due to some problems with TCP connection to its DLS peer, a
        RESTART_DL SSP control message could not be sent out."
    ::= { dlsEventsGroup 249 }

dls249_ip_address OBJECT-TYPE
    SYNTAX IpAddress
    MAX-ACCESS accessible-for-notify
    STATUS current
    DESCRIPTION
        "Parameter 'ip_address' in event DLS.249"
    ::= { dlsEventObjects249 1 }

dls249_source_mac_address OBJECT-TYPE
    SYNTAX DisplayString
    MAX-ACCESS accessible-for-notify
    STATUS current
    DESCRIPTION
        "Parameter 'source_mac_address' in event DLS.249"
    ::= { dlsEventObjects249 2 }

dls249_dest_mac_address OBJECT-TYPE
    SYNTAX DisplayString
    MAX-ACCESS accessible-for-notify
    STATUS current
    DESCRIPTION
        "Parameter 'dest_mac_address' in event DLS.249"
    ::= { dlsEventObjects249 3 }

dls249_source_sap OBJECT-TYPE
    SYNTAX Integer32
    MAX-ACCESS accessible-for-notify
    STATUS current
    DESCRIPTION
        "Parameter 'source_sap' in event DLS.249"
    ::= { dlsEventObjects249 4 }

dls249_dest_sap OBJECT-TYPE
    SYNTAX Integer32
    MAX-ACCESS accessible-for-notify
    STATUS current
    DESCRIPTION
        "Parameter 'dest_sap' in event DLS.249"
    ::= { dlsEventObjects249 5 }

dlsEventObjects250 OBJECT-IDENTITY
    STATUS current
    DESCRIPTION
        "Event DLS.250
        Due to some problems with TCP connection to its DLS peer, a
        DL_RESTARTED SSP control message could not be sent out."
    ::= { dlsEventsGroup 250 }

dls250_ip_address OBJECT-TYPE
    SYNTAX IpAddress
    MAX-ACCESS accessible-for-notify
    STATUS current
    DESCRIPTION
        "Parameter 'ip_address' in event DLS.250"
    ::= { dlsEventObjects250 1 }

dls250_source_mac_address OBJECT-TYPE
    SYNTAX DisplayString
    MAX-ACCESS accessible-for-notify
    STATUS current
    DESCRIPTION
        "Parameter 'source_mac_address' in event DLS.250"
    ::= { dlsEventObjects250 2 }

dls250_dest_mac_address OBJECT-TYPE
    SYNTAX DisplayString
    MAX-ACCESS accessible-for-notify
    STATUS current
    DESCRIPTION
        "Parameter 'dest_mac_address' in event DLS.250"
    ::= { dlsEventObjects250 3 }

dls250_source_sap OBJECT-TYPE
    SYNTAX Integer32
    MAX-ACCESS accessible-for-notify
    STATUS current
    DESCRIPTION
        "Parameter 'source_sap' in event DLS.250"
    ::= { dlsEventObjects250 4 }

dls250_dest_sap OBJECT-TYPE
    SYNTAX Integer32
    MAX-ACCESS accessible-for-notify
    STATUS current
    DESCRIPTION
        "Parameter 'dest_sap' in event DLS.250"
    ::= { dlsEventObjects250 5 }

dlsEventObjects251 OBJECT-IDENTITY
    STATUS current
    DESCRIPTION
        "Event DLS.251
        Due to some problems with TCP connection to its DLS peer, an
        ENTER_BUSY SSP control message could not be sent out."
    ::= { dlsEventsGroup 251 }

dls251_ip_address OBJECT-TYPE
    SYNTAX IpAddress
    MAX-ACCESS accessible-for-notify
    STATUS current
    DESCRIPTION
        "Parameter 'ip_address' in event DLS.251"
    ::= { dlsEventObjects251 1 }

dls251_source_mac_address OBJECT-TYPE
    SYNTAX DisplayString
    MAX-ACCESS accessible-for-notify
    STATUS current
    DESCRIPTION
        "Parameter 'source_mac_address' in event DLS.251"
    ::= { dlsEventObjects251 2 }

dls251_dest_mac_address OBJECT-TYPE
    SYNTAX DisplayString
    MAX-ACCESS accessible-for-notify
    STATUS current
    DESCRIPTION
        "Parameter 'dest_mac_address' in event DLS.251"
    ::= { dlsEventObjects251 3 }

dls251_source_sap OBJECT-TYPE
    SYNTAX Integer32
    MAX-ACCESS accessible-for-notify
    STATUS current
    DESCRIPTION
        "Parameter 'source_sap' in event DLS.251"
    ::= { dlsEventObjects251 4 }

dls251_dest_sap OBJECT-TYPE
    SYNTAX Integer32
    MAX-ACCESS accessible-for-notify
    STATUS current
    DESCRIPTION
        "Parameter 'dest_sap' in event DLS.251"
    ::= { dlsEventObjects251 5 }

dlsEventObjects252 OBJECT-IDENTITY
    STATUS current
    DESCRIPTION
        "Event DLS.252
        Due to some problems with TCP connection to its DLS peer, an
        EXIT_BUSY SSP control message could not be sent out."
    ::= { dlsEventsGroup 252 }

dls252_ip_address OBJECT-TYPE
    SYNTAX IpAddress
    MAX-ACCESS accessible-for-notify
    STATUS current
    DESCRIPTION
        "Parameter 'ip_address' in event DLS.252"
    ::= { dlsEventObjects252 1 }

dls252_source_mac_address OBJECT-TYPE
    SYNTAX DisplayString
    MAX-ACCESS accessible-for-notify
    STATUS current
    DESCRIPTION
        "Parameter 'source_mac_address' in event DLS.252"
    ::= { dlsEventObjects252 2 }

dls252_dest_mac_address OBJECT-TYPE
    SYNTAX DisplayString
    MAX-ACCESS accessible-for-notify
    STATUS current
    DESCRIPTION
        "Parameter 'dest_mac_address' in event DLS.252"
    ::= { dlsEventObjects252 3 }

dls252_source_sap OBJECT-TYPE
    SYNTAX Integer32
    MAX-ACCESS accessible-for-notify
    STATUS current
    DESCRIPTION
        "Parameter 'source_sap' in event DLS.252"
    ::= { dlsEventObjects252 4 }

dls252_dest_sap OBJECT-TYPE
    SYNTAX Integer32
    MAX-ACCESS accessible-for-notify
    STATUS current
    DESCRIPTION
        "Parameter 'dest_sap' in event DLS.252"
    ::= { dlsEventObjects252 5 }

dlsEventObjects253 OBJECT-IDENTITY
    STATUS current
    DESCRIPTION
        "Event DLS.253
        Due to some problems with TCP connection to its DLS peer, a
        SSP control message could not be sent out."
    ::= { dlsEventsGroup 253 }

dls253_ip_address OBJECT-TYPE
    SYNTAX IpAddress
    MAX-ACCESS accessible-for-notify
    STATUS current
    DESCRIPTION
        "Parameter 'ip_address' in event DLS.253"
    ::= { dlsEventObjects253 1 }

dls253_source_mac_address OBJECT-TYPE
    SYNTAX DisplayString
    MAX-ACCESS accessible-for-notify
    STATUS current
    DESCRIPTION
        "Parameter 'source_mac_address' in event DLS.253"
    ::= { dlsEventObjects253 2 }

dls253_dest_mac_address OBJECT-TYPE
    SYNTAX DisplayString
    MAX-ACCESS accessible-for-notify
    STATUS current
    DESCRIPTION
        "Parameter 'dest_mac_address' in event DLS.253"
    ::= { dlsEventObjects253 3 }

dls253_source_sap OBJECT-TYPE
    SYNTAX Integer32
    MAX-ACCESS accessible-for-notify
    STATUS current
    DESCRIPTION
        "Parameter 'source_sap' in event DLS.253"
    ::= { dlsEventObjects253 4 }

dls253_dest_sap OBJECT-TYPE
    SYNTAX Integer32
    MAX-ACCESS accessible-for-notify
    STATUS current
    DESCRIPTION
        "Parameter 'dest_sap' in event DLS.253"
    ::= { dlsEventObjects253 5 }

dlsEventObjects254 OBJECT-IDENTITY
    STATUS current
    DESCRIPTION
        "Event DLS.254
        Due to some problems with TCP connection to its DLS peer, a
        DL_HALTED SSP control message could not be sent out."
    ::= { dlsEventsGroup 254 }

dls254_ip_address OBJECT-TYPE
    SYNTAX IpAddress
    MAX-ACCESS accessible-for-notify
    STATUS current
    DESCRIPTION
        "Parameter 'ip_address' in event DLS.254"
    ::= { dlsEventObjects254 1 }

dls254_source_mac_address OBJECT-TYPE
    SYNTAX DisplayString
    MAX-ACCESS accessible-for-notify
    STATUS current
    DESCRIPTION
        "Parameter 'source_mac_address' in event DLS.254"
    ::= { dlsEventObjects254 2 }

dls254_dest_mac_address OBJECT-TYPE
    SYNTAX DisplayString
    MAX-ACCESS accessible-for-notify
    STATUS current
    DESCRIPTION
        "Parameter 'dest_mac_address' in event DLS.254"
    ::= { dlsEventObjects254 3 }

dls254_source_sap OBJECT-TYPE
    SYNTAX Integer32
    MAX-ACCESS accessible-for-notify
    STATUS current
    DESCRIPTION
        "Parameter 'source_sap' in event DLS.254"
    ::= { dlsEventObjects254 4 }

dls254_dest_sap OBJECT-TYPE
    SYNTAX Integer32
    MAX-ACCESS accessible-for-notify
    STATUS current
    DESCRIPTION
        "Parameter 'dest_sap' in event DLS.254"
    ::= { dlsEventObjects254 5 }

dlsEventObjects255 OBJECT-IDENTITY
    STATUS current
    DESCRIPTION
        "Event DLS.255
        Due to some problems with TCP connection to its DLS peer, a
        HALT_DL_NOACK SSP control message could not be sent out."
    ::= { dlsEventsGroup 255 }

dls255_ip_address OBJECT-TYPE
    SYNTAX IpAddress
    MAX-ACCESS accessible-for-notify
    STATUS current
    DESCRIPTION
        "Parameter 'ip_address' in event DLS.255"
    ::= { dlsEventObjects255 1 }

dls255_source_mac_address OBJECT-TYPE
    SYNTAX DisplayString
    MAX-ACCESS accessible-for-notify
    STATUS current
    DESCRIPTION
        "Parameter 'source_mac_address' in event DLS.255"
    ::= { dlsEventObjects255 2 }

dls255_dest_mac_address OBJECT-TYPE
    SYNTAX DisplayString
    MAX-ACCESS accessible-for-notify
    STATUS current
    DESCRIPTION
        "Parameter 'dest_mac_address' in event DLS.255"
    ::= { dlsEventObjects255 3 }

dls255_source_sap OBJECT-TYPE
    SYNTAX Integer32
    MAX-ACCESS accessible-for-notify
    STATUS current
    DESCRIPTION
        "Parameter 'source_sap' in event DLS.255"
    ::= { dlsEventObjects255 4 }

dls255_dest_sap OBJECT-TYPE
    SYNTAX Integer32
    MAX-ACCESS accessible-for-notify
    STATUS current
    DESCRIPTION
        "Parameter 'dest_sap' in event DLS.255"
    ::= { dlsEventObjects255 5 }

dlsEventObjects256 OBJECT-IDENTITY
    STATUS current
    DESCRIPTION
        "Event DLS.256
        Due to some problems with TCP connection to its DLS peer, a
        TEST_CIRCUIT_RSP SSP control message could not be sent out."
    ::= { dlsEventsGroup 256 }

dls256_ip_address OBJECT-TYPE
    SYNTAX IpAddress
    MAX-ACCESS accessible-for-notify
    STATUS current
    DESCRIPTION
        "Parameter 'ip_address' in event DLS.256"
    ::= { dlsEventObjects256 1 }

dls256_source_mac_address OBJECT-TYPE
    SYNTAX DisplayString
    MAX-ACCESS accessible-for-notify
    STATUS current
    DESCRIPTION
        "Parameter 'source_mac_address' in event DLS.256"
    ::= { dlsEventObjects256 2 }

dls256_dest_mac_address OBJECT-TYPE
    SYNTAX DisplayString
    MAX-ACCESS accessible-for-notify
    STATUS current
    DESCRIPTION
        "Parameter 'dest_mac_address' in event DLS.256"
    ::= { dlsEventObjects256 3 }

dls256_source_sap OBJECT-TYPE
    SYNTAX Integer32
    MAX-ACCESS accessible-for-notify
    STATUS current
    DESCRIPTION
        "Parameter 'source_sap' in event DLS.256"
    ::= { dlsEventObjects256 4 }

dls256_dest_sap OBJECT-TYPE
    SYNTAX Integer32
    MAX-ACCESS accessible-for-notify
    STATUS current
    DESCRIPTION
        "Parameter 'dest_sap' in event DLS.256"
    ::= { dlsEventObjects256 5 }

dlsEventObjects257 OBJECT-IDENTITY
    STATUS current
    DESCRIPTION
        "Event DLS.257
        DLS successfully sent out a DL_HALTED SSP message over TCP to its
        DLS peer."
    ::= { dlsEventsGroup 257 }

dls257_ip_address OBJECT-TYPE
    SYNTAX IpAddress
    MAX-ACCESS accessible-for-notify
    STATUS current
    DESCRIPTION
        "Parameter 'ip_address' in event DLS.257"
    ::= { dlsEventObjects257 1 }

dls257_source_mac_address OBJECT-TYPE
    SYNTAX DisplayString
    MAX-ACCESS accessible-for-notify
    STATUS current
    DESCRIPTION
        "Parameter 'source_mac_address' in event DLS.257"
    ::= { dlsEventObjects257 2 }

dls257_dest_mac_address OBJECT-TYPE
    SYNTAX DisplayString
    MAX-ACCESS accessible-for-notify
    STATUS current
    DESCRIPTION
        "Parameter 'dest_mac_address' in event DLS.257"
    ::= { dlsEventObjects257 3 }

dls257_source_sap OBJECT-TYPE
    SYNTAX Integer32
    MAX-ACCESS accessible-for-notify
    STATUS current
    DESCRIPTION
        "Parameter 'source_sap' in event DLS.257"
    ::= { dlsEventObjects257 4 }

dls257_dest_sap OBJECT-TYPE
    SYNTAX Integer32
    MAX-ACCESS accessible-for-notify
    STATUS current
    DESCRIPTION
        "Parameter 'dest_sap' in event DLS.257"
    ::= { dlsEventObjects257 5 }

dlsEventObjects258 OBJECT-IDENTITY
    STATUS current
    DESCRIPTION
        "Event DLS.258
        DLS successfully sent out a XIDFRAME SSP message over TCP to its
        DLS peer."
    ::= { dlsEventsGroup 258 }

dls258_ip_address OBJECT-TYPE
    SYNTAX IpAddress
    MAX-ACCESS accessible-for-notify
    STATUS current
    DESCRIPTION
        "Parameter 'ip_address' in event DLS.258"
    ::= { dlsEventObjects258 1 }

dls258_source_mac_address OBJECT-TYPE
    SYNTAX DisplayString
    MAX-ACCESS accessible-for-notify
    STATUS current
    DESCRIPTION
        "Parameter 'source_mac_address' in event DLS.258"
    ::= { dlsEventObjects258 2 }

dls258_dest_mac_address OBJECT-TYPE
    SYNTAX DisplayString
    MAX-ACCESS accessible-for-notify
    STATUS current
    DESCRIPTION
        "Parameter 'dest_mac_address' in event DLS.258"
    ::= { dlsEventObjects258 3 }

dls258_source_sap OBJECT-TYPE
    SYNTAX Integer32
    MAX-ACCESS accessible-for-notify
    STATUS current
    DESCRIPTION
        "Parameter 'source_sap' in event DLS.258"
    ::= { dlsEventObjects258 4 }

dls258_dest_sap OBJECT-TYPE
    SYNTAX Integer32
    MAX-ACCESS accessible-for-notify
    STATUS current
    DESCRIPTION
        "Parameter 'dest_sap' in event DLS.258"
    ::= { dlsEventObjects258 5 }

dlsEventObjects259 OBJECT-IDENTITY
    STATUS current
    DESCRIPTION
        "Event DLS.259
        DLS successfully sent out a DGRMFRAME SSP message over TCP to its
        DLS peer."
    ::= { dlsEventsGroup 259 }

dls259_ip_address OBJECT-TYPE
    SYNTAX IpAddress
    MAX-ACCESS accessible-for-notify
    STATUS current
    DESCRIPTION
        "Parameter 'ip_address' in event DLS.259"
    ::= { dlsEventObjects259 1 }

dls259_source_mac_address OBJECT-TYPE
    SYNTAX DisplayString
    MAX-ACCESS accessible-for-notify
    STATUS current
    DESCRIPTION
        "Parameter 'source_mac_address' in event DLS.259"
    ::= { dlsEventObjects259 2 }

dls259_dest_mac_address OBJECT-TYPE
    SYNTAX DisplayString
    MAX-ACCESS accessible-for-notify
    STATUS current
    DESCRIPTION
        "Parameter 'dest_mac_address' in event DLS.259"
    ::= { dlsEventObjects259 3 }

dls259_source_sap OBJECT-TYPE
    SYNTAX Integer32
    MAX-ACCESS accessible-for-notify
    STATUS current
    DESCRIPTION
        "Parameter 'source_sap' in event DLS.259"
    ::= { dlsEventObjects259 4 }

dls259_dest_sap OBJECT-TYPE
    SYNTAX Integer32
    MAX-ACCESS accessible-for-notify
    STATUS current
    DESCRIPTION
        "Parameter 'dest_sap' in event DLS.259"
    ::= { dlsEventObjects259 5 }

dlsEventObjects260 OBJECT-IDENTITY
    STATUS current
    DESCRIPTION
        "Event DLS.260
        DLS successfully sent out a DATAFRAME SSP message over TCP to its
        DLS peer."
    ::= { dlsEventsGroup 260 }

dls260_ip_address OBJECT-TYPE
    SYNTAX IpAddress
    MAX-ACCESS accessible-for-notify
    STATUS current
    DESCRIPTION
        "Parameter 'ip_address' in event DLS.260"
    ::= { dlsEventObjects260 1 }

dls260_source_mac_address OBJECT-TYPE
    SYNTAX DisplayString
    MAX-ACCESS accessible-for-notify
    STATUS current
    DESCRIPTION
        "Parameter 'source_mac_address' in event DLS.260"
    ::= { dlsEventObjects260 2 }

dls260_dest_mac_address OBJECT-TYPE
    SYNTAX DisplayString
    MAX-ACCESS accessible-for-notify
    STATUS current
    DESCRIPTION
        "Parameter 'dest_mac_address' in event DLS.260"
    ::= { dlsEventObjects260 3 }

dls260_source_sap OBJECT-TYPE
    SYNTAX Integer32
    MAX-ACCESS accessible-for-notify
    STATUS current
    DESCRIPTION
        "Parameter 'source_sap' in event DLS.260"
    ::= { dlsEventObjects260 4 }

dls260_dest_sap OBJECT-TYPE
    SYNTAX Integer32
    MAX-ACCESS accessible-for-notify
    STATUS current
    DESCRIPTION
        "Parameter 'dest_sap' in event DLS.260"
    ::= { dlsEventObjects260 5 }

dlsEventObjects261 OBJECT-IDENTITY
    STATUS current
    DESCRIPTION
        "Event DLS.261
        DLS successfully sent out an INFOFRAME SSP message over TCP to its
        DLS peer."
    ::= { dlsEventsGroup 261 }

dls261_ip_address OBJECT-TYPE
    SYNTAX IpAddress
    MAX-ACCESS accessible-for-notify
    STATUS current
    DESCRIPTION
        "Parameter 'ip_address' in event DLS.261"
    ::= { dlsEventObjects261 1 }

dls261_source_mac_address OBJECT-TYPE
    SYNTAX DisplayString
    MAX-ACCESS accessible-for-notify
    STATUS current
    DESCRIPTION
        "Parameter 'source_mac_address' in event DLS.261"
    ::= { dlsEventObjects261 2 }

dls261_dest_mac_address OBJECT-TYPE
    SYNTAX DisplayString
    MAX-ACCESS accessible-for-notify
    STATUS current
    DESCRIPTION
        "Parameter 'dest_mac_address' in event DLS.261"
    ::= { dlsEventObjects261 3 }

dls261_source_sap OBJECT-TYPE
    SYNTAX Integer32
    MAX-ACCESS accessible-for-notify
    STATUS current
    DESCRIPTION
        "Parameter 'source_sap' in event DLS.261"
    ::= { dlsEventObjects261 4 }

dls261_dest_sap OBJECT-TYPE
    SYNTAX Integer32
    MAX-ACCESS accessible-for-notify
    STATUS current
    DESCRIPTION
        "Parameter 'dest_sap' in event DLS.261"
    ::= { dlsEventObjects261 5 }

dlsEventObjects262 OBJECT-IDENTITY
    STATUS current
    DESCRIPTION
        "Event DLS.262
        DLS forwarder received a Switch to Switch Protocol message of
        TEST_CIRCUIT_REQ over TCP."
    ::= { dlsEventsGroup 262 }

dls262_ip_address OBJECT-TYPE
    SYNTAX IpAddress
    MAX-ACCESS accessible-for-notify
    STATUS current
    DESCRIPTION
        "Parameter 'ip_address' in event DLS.262"
    ::= { dlsEventObjects262 1 }

dls262_source_mac_address OBJECT-TYPE
    SYNTAX DisplayString
    MAX-ACCESS accessible-for-notify
    STATUS current
    DESCRIPTION
        "Parameter 'source_mac_address' in event DLS.262"
    ::= { dlsEventObjects262 2 }

dls262_dest_mac_address OBJECT-TYPE
    SYNTAX DisplayString
    MAX-ACCESS accessible-for-notify
    STATUS current
    DESCRIPTION
        "Parameter 'dest_mac_address' in event DLS.262"
    ::= { dlsEventObjects262 3 }

dls262_source_sap OBJECT-TYPE
    SYNTAX Integer32
    MAX-ACCESS accessible-for-notify
    STATUS current
    DESCRIPTION
        "Parameter 'source_sap' in event DLS.262"
    ::= { dlsEventObjects262 4 }

dls262_dest_sap OBJECT-TYPE
    SYNTAX Integer32
    MAX-ACCESS accessible-for-notify
    STATUS current
    DESCRIPTION
        "Parameter 'dest_sap' in event DLS.262"
    ::= { dlsEventObjects262 5 }

dlsEventObjects263 OBJECT-IDENTITY
    STATUS current
    DESCRIPTION
        "Event DLS.263
        DLS forwarder received a Switch to Switch Protocol message of
        TEST_CIRCUIT_RSP over TCP."
    ::= { dlsEventsGroup 263 }

dls263_ip_address OBJECT-TYPE
    SYNTAX IpAddress
    MAX-ACCESS accessible-for-notify
    STATUS current
    DESCRIPTION
        "Parameter 'ip_address' in event DLS.263"
    ::= { dlsEventObjects263 1 }

dls263_source_mac_address OBJECT-TYPE
    SYNTAX DisplayString
    MAX-ACCESS accessible-for-notify
    STATUS current
    DESCRIPTION
        "Parameter 'source_mac_address' in event DLS.263"
    ::= { dlsEventObjects263 2 }

dls263_dest_mac_address OBJECT-TYPE
    SYNTAX DisplayString
    MAX-ACCESS accessible-for-notify
    STATUS current
    DESCRIPTION
        "Parameter 'dest_mac_address' in event DLS.263"
    ::= { dlsEventObjects263 3 }

dls263_source_sap OBJECT-TYPE
    SYNTAX Integer32
    MAX-ACCESS accessible-for-notify
    STATUS current
    DESCRIPTION
        "Parameter 'source_sap' in event DLS.263"
    ::= { dlsEventObjects263 4 }

dls263_dest_sap OBJECT-TYPE
    SYNTAX Integer32
    MAX-ACCESS accessible-for-notify
    STATUS current
    DESCRIPTION
        "Parameter 'dest_sap' in event DLS.263"
    ::= { dlsEventObjects263 5 }

dlsEventObjects264 OBJECT-IDENTITY
    STATUS current
    DESCRIPTION
        "Event DLS.264
        An information frame received from DLS cloud was successfully flushed
        to an LLC end station."
    ::= { dlsEventsGroup 264 }

dls264_source_mac_address OBJECT-TYPE
    SYNTAX DisplayString
    MAX-ACCESS accessible-for-notify
    STATUS current
    DESCRIPTION
        "Parameter 'source_mac_address' in event DLS.264"
    ::= { dlsEventObjects264 1 }

dls264_dest_mac_address OBJECT-TYPE
    SYNTAX DisplayString
    MAX-ACCESS accessible-for-notify
    STATUS current
    DESCRIPTION
        "Parameter 'dest_mac_address' in event DLS.264"
    ::= { dlsEventObjects264 2 }

dls264_source_sap OBJECT-TYPE
    SYNTAX Integer32
    MAX-ACCESS accessible-for-notify
    STATUS current
    DESCRIPTION
        "Parameter 'source_sap' in event DLS.264"
    ::= { dlsEventObjects264 3 }

dls264_dest_sap OBJECT-TYPE
    SYNTAX Integer32
    MAX-ACCESS accessible-for-notify
    STATUS current
    DESCRIPTION
        "Parameter 'dest_sap' in event DLS.264"
    ::= { dlsEventObjects264 4 }

dlsEventObjects265 OBJECT-IDENTITY
    STATUS current
    DESCRIPTION
        "Event DLS.265
        A TEST Command frame was successfully sent to an LLC end station as
        a result of receiving a CANUREACH from a DLSw peer router."
    ::= { dlsEventsGroup 265 }

dls265_source_mac_address OBJECT-TYPE
    SYNTAX DisplayString
    MAX-ACCESS accessible-for-notify
    STATUS current
    DESCRIPTION
        "Parameter 'source_mac_address' in event DLS.265"
    ::= { dlsEventObjects265 1 }

dls265_dest_mac_address OBJECT-TYPE
    SYNTAX DisplayString
    MAX-ACCESS accessible-for-notify
    STATUS current
    DESCRIPTION
        "Parameter 'dest_mac_address' in event DLS.265"
    ::= { dlsEventObjects265 2 }

dls265_source_sap OBJECT-TYPE
    SYNTAX Integer32
    MAX-ACCESS accessible-for-notify
    STATUS current
    DESCRIPTION
        "Parameter 'source_sap' in event DLS.265"
    ::= { dlsEventObjects265 3 }

dls265_dest_sap OBJECT-TYPE
    SYNTAX Integer32
    MAX-ACCESS accessible-for-notify
    STATUS current
    DESCRIPTION
        "Parameter 'dest_sap' in event DLS.265"
    ::= { dlsEventObjects265 4 }

dlsEventObjects266 OBJECT-IDENTITY
    STATUS current
    DESCRIPTION
        "Event DLS.266
        A TEST Response frame was successfully sent to an LLC end station as
        a result of receiving an ICANREACH from a DLSw peer router."
    ::= { dlsEventsGroup 266 }

dls266_source_mac_address OBJECT-TYPE
    SYNTAX DisplayString
    MAX-ACCESS accessible-for-notify
    STATUS current
    DESCRIPTION
        "Parameter 'source_mac_address' in event DLS.266"
    ::= { dlsEventObjects266 1 }

dls266_dest_mac_address OBJECT-TYPE
    SYNTAX DisplayString
    MAX-ACCESS accessible-for-notify
    STATUS current
    DESCRIPTION
        "Parameter 'dest_mac_address' in event DLS.266"
    ::= { dlsEventObjects266 2 }

dls266_source_sap OBJECT-TYPE
    SYNTAX Integer32
    MAX-ACCESS accessible-for-notify
    STATUS current
    DESCRIPTION
        "Parameter 'source_sap' in event DLS.266"
    ::= { dlsEventObjects266 3 }

dls266_dest_sap OBJECT-TYPE
    SYNTAX Integer32
    MAX-ACCESS accessible-for-notify
    STATUS current
    DESCRIPTION
        "Parameter 'dest_sap' in event DLS.266"
    ::= { dlsEventObjects266 4 }

dlsEventObjects267 OBJECT-IDENTITY
    STATUS current
    DESCRIPTION
        "Event DLS.267
        A XID frame was successfully sent to an LLC end station."
    ::= { dlsEventsGroup 267 }

dls267_source_mac_address OBJECT-TYPE
    SYNTAX DisplayString
    MAX-ACCESS accessible-for-notify
    STATUS current
    DESCRIPTION
        "Parameter 'source_mac_address' in event DLS.267"
    ::= { dlsEventObjects267 1 }

dls267_dest_mac_address OBJECT-TYPE
    SYNTAX DisplayString
    MAX-ACCESS accessible-for-notify
    STATUS current
    DESCRIPTION
        "Parameter 'dest_mac_address' in event DLS.267"
    ::= { dlsEventObjects267 2 }

dls267_source_sap OBJECT-TYPE
    SYNTAX Integer32
    MAX-ACCESS accessible-for-notify
    STATUS current
    DESCRIPTION
        "Parameter 'source_sap' in event DLS.267"
    ::= { dlsEventObjects267 3 }

dls267_dest_sap OBJECT-TYPE
    SYNTAX Integer32
    MAX-ACCESS accessible-for-notify
    STATUS current
    DESCRIPTION
        "Parameter 'dest_sap' in event DLS.267"
    ::= { dlsEventObjects267 4 }

dlsEventObjects268 OBJECT-IDENTITY
    STATUS current
    DESCRIPTION
        "Event DLS.268
        An UI frame was successfully sent to an LLC end station."
    ::= { dlsEventsGroup 268 }

dls268_source_mac_address OBJECT-TYPE
    SYNTAX DisplayString
    MAX-ACCESS accessible-for-notify
    STATUS current
    DESCRIPTION
        "Parameter 'source_mac_address' in event DLS.268"
    ::= { dlsEventObjects268 1 }

dls268_dest_mac_address OBJECT-TYPE
    SYNTAX DisplayString
    MAX-ACCESS accessible-for-notify
    STATUS current
    DESCRIPTION
        "Parameter 'dest_mac_address' in event DLS.268"
    ::= { dlsEventObjects268 2 }

dls268_source_sap OBJECT-TYPE
    SYNTAX Integer32
    MAX-ACCESS accessible-for-notify
    STATUS current
    DESCRIPTION
        "Parameter 'source_sap' in event DLS.268"
    ::= { dlsEventObjects268 3 }

dls268_dest_sap OBJECT-TYPE
    SYNTAX Integer32
    MAX-ACCESS accessible-for-notify
    STATUS current
    DESCRIPTION
        "Parameter 'dest_sap' in event DLS.268"
    ::= { dlsEventObjects268 4 }

dlsEventObjects269 OBJECT-IDENTITY
    STATUS current
    DESCRIPTION
        "Event DLS.269
        A TEST command frame was not processed by the DLS-LLC interface
        module's state machine as it could not be successfully relayed via
        DLS. This instance is normal for TEST command frame as DLS
        copies the frame and still refuses the frame so that it
        can also be sent via the bridge path."
    ::= { dlsEventsGroup 269 }

dls269_source_mac_address OBJECT-TYPE
    SYNTAX DisplayString
    MAX-ACCESS accessible-for-notify
    STATUS current
    DESCRIPTION
        "Parameter 'source_mac_address' in event DLS.269"
    ::= { dlsEventObjects269 1 }

dls269_dest_mac_address OBJECT-TYPE
    SYNTAX DisplayString
    MAX-ACCESS accessible-for-notify
    STATUS current
    DESCRIPTION
        "Parameter 'dest_mac_address' in event DLS.269"
    ::= { dlsEventObjects269 2 }

dls269_source_sap OBJECT-TYPE
    SYNTAX Integer32
    MAX-ACCESS accessible-for-notify
    STATUS current
    DESCRIPTION
        "Parameter 'source_sap' in event DLS.269"
    ::= { dlsEventObjects269 3 }

dls269_dest_sap OBJECT-TYPE
    SYNTAX Integer32
    MAX-ACCESS accessible-for-notify
    STATUS current
    DESCRIPTION
        "Parameter 'dest_sap' in event DLS.269"
    ::= { dlsEventObjects269 4 }

dlsEventObjects270 OBJECT-IDENTITY
    STATUS current
    DESCRIPTION
        "Event DLS.270
        A TEST response frame was not processed by the DLS-LLC interface
        module's state machine as it could not be successfully relayed via
        DLS."
    ::= { dlsEventsGroup 270 }

dls270_source_mac_address OBJECT-TYPE
    SYNTAX DisplayString
    MAX-ACCESS accessible-for-notify
    STATUS current
    DESCRIPTION
        "Parameter 'source_mac_address' in event DLS.270"
    ::= { dlsEventObjects270 1 }

dls270_dest_mac_address OBJECT-TYPE
    SYNTAX DisplayString
    MAX-ACCESS accessible-for-notify
    STATUS current
    DESCRIPTION
        "Parameter 'dest_mac_address' in event DLS.270"
    ::= { dlsEventObjects270 2 }

dls270_source_sap OBJECT-TYPE
    SYNTAX Integer32
    MAX-ACCESS accessible-for-notify
    STATUS current
    DESCRIPTION
        "Parameter 'source_sap' in event DLS.270"
    ::= { dlsEventObjects270 3 }

dls270_dest_sap OBJECT-TYPE
    SYNTAX Integer32
    MAX-ACCESS accessible-for-notify
    STATUS current
    DESCRIPTION
        "Parameter 'dest_sap' in event DLS.270"
    ::= { dlsEventObjects270 4 }

dlsEventObjects271 OBJECT-IDENTITY
    STATUS current
    DESCRIPTION
        "Event DLS.271
        A XID command frame was not processed by the DLS-LLC interface
        module's state machine as it could not be successfully relayed via
        DLS."
    ::= { dlsEventsGroup 271 }

dls271_source_mac_address OBJECT-TYPE
    SYNTAX DisplayString
    MAX-ACCESS accessible-for-notify
    STATUS current
    DESCRIPTION
        "Parameter 'source_mac_address' in event DLS.271"
    ::= { dlsEventObjects271 1 }

dls271_dest_mac_address OBJECT-TYPE
    SYNTAX DisplayString
    MAX-ACCESS accessible-for-notify
    STATUS current
    DESCRIPTION
        "Parameter 'dest_mac_address' in event DLS.271"
    ::= { dlsEventObjects271 2 }

dls271_source_sap OBJECT-TYPE
    SYNTAX Integer32
    MAX-ACCESS accessible-for-notify
    STATUS current
    DESCRIPTION
        "Parameter 'source_sap' in event DLS.271"
    ::= { dlsEventObjects271 3 }

dls271_dest_sap OBJECT-TYPE
    SYNTAX Integer32
    MAX-ACCESS accessible-for-notify
    STATUS current
    DESCRIPTION
        "Parameter 'dest_sap' in event DLS.271"
    ::= { dlsEventObjects271 4 }

dlsEventObjects272 OBJECT-IDENTITY
    STATUS current
    DESCRIPTION
        "Event DLS.272
        A XID response frame was not processed by the DLS-LLC interface
        module's state machine as it could not be successfully relayed via
        DLS."
    ::= { dlsEventsGroup 272 }

dls272_source_mac_address OBJECT-TYPE
    SYNTAX DisplayString
    MAX-ACCESS accessible-for-notify
    STATUS current
    DESCRIPTION
        "Parameter 'source_mac_address' in event DLS.272"
    ::= { dlsEventObjects272 1 }

dls272_dest_mac_address OBJECT-TYPE
    SYNTAX DisplayString
    MAX-ACCESS accessible-for-notify
    STATUS current
    DESCRIPTION
        "Parameter 'dest_mac_address' in event DLS.272"
    ::= { dlsEventObjects272 2 }

dls272_source_sap OBJECT-TYPE
    SYNTAX Integer32
    MAX-ACCESS accessible-for-notify
    STATUS current
    DESCRIPTION
        "Parameter 'source_sap' in event DLS.272"
    ::= { dlsEventObjects272 3 }

dls272_dest_sap OBJECT-TYPE
    SYNTAX Integer32
    MAX-ACCESS accessible-for-notify
    STATUS current
    DESCRIPTION
        "Parameter 'dest_sap' in event DLS.272"
    ::= { dlsEventObjects272 4 }

dlsEventObjects273 OBJECT-IDENTITY
    STATUS current
    DESCRIPTION
        "Event DLS.273
        An UI frame was not processed by the DLS-LLC interface
        module's state machine as it could not be successfully relayed via
        DLS."
    ::= { dlsEventsGroup 273 }

dls273_source_mac_address OBJECT-TYPE
    SYNTAX DisplayString
    MAX-ACCESS accessible-for-notify
    STATUS current
    DESCRIPTION
        "Parameter 'source_mac_address' in event DLS.273"
    ::= { dlsEventObjects273 1 }

dls273_dest_mac_address OBJECT-TYPE
    SYNTAX DisplayString
    MAX-ACCESS accessible-for-notify
    STATUS current
    DESCRIPTION
        "Parameter 'dest_mac_address' in event DLS.273"
    ::= { dlsEventObjects273 2 }

dls273_source_sap OBJECT-TYPE
    SYNTAX Integer32
    MAX-ACCESS accessible-for-notify
    STATUS current
    DESCRIPTION
        "Parameter 'source_sap' in event DLS.273"
    ::= { dlsEventObjects273 3 }

dls273_dest_sap OBJECT-TYPE
    SYNTAX Integer32
    MAX-ACCESS accessible-for-notify
    STATUS current
    DESCRIPTION
        "Parameter 'dest_sap' in event DLS.273"
    ::= { dlsEventObjects273 4 }

dlsEventObjects274 OBJECT-IDENTITY
    STATUS current
    DESCRIPTION
        "Event DLS.274
        An INFO frame was not processed by the DLS-LLC interface
        module's state machine as it could not be successfully relayed via
        DLS."
    ::= { dlsEventsGroup 274 }

dls274_source_mac_address OBJECT-TYPE
    SYNTAX DisplayString
    MAX-ACCESS accessible-for-notify
    STATUS current
    DESCRIPTION
        "Parameter 'source_mac_address' in event DLS.274"
    ::= { dlsEventObjects274 1 }

dls274_dest_mac_address OBJECT-TYPE
    SYNTAX DisplayString
    MAX-ACCESS accessible-for-notify
    STATUS current
    DESCRIPTION
        "Parameter 'dest_mac_address' in event DLS.274"
    ::= { dlsEventObjects274 2 }

dls274_source_sap OBJECT-TYPE
    SYNTAX Integer32
    MAX-ACCESS accessible-for-notify
    STATUS current
    DESCRIPTION
        "Parameter 'source_sap' in event DLS.274"
    ::= { dlsEventObjects274 3 }

dls274_dest_sap OBJECT-TYPE
    SYNTAX Integer32
    MAX-ACCESS accessible-for-notify
    STATUS current
    DESCRIPTION
        "Parameter 'dest_sap' in event DLS.274"
    ::= { dlsEventObjects274 4 }

dlsEventObjects275 OBJECT-IDENTITY
    STATUS current
    DESCRIPTION
        "Event DLS.275
        LLC Connect Indication Passive event was not processed. Passive
        opens are not supported in the DLSw environment."
    ::= { dlsEventsGroup 275 }

dls275_source_mac_address OBJECT-TYPE
    SYNTAX DisplayString
    MAX-ACCESS accessible-for-notify
    STATUS current
    DESCRIPTION
        "Parameter 'source_mac_address' in event DLS.275"
    ::= { dlsEventObjects275 1 }

dls275_dest_mac_address OBJECT-TYPE
    SYNTAX DisplayString
    MAX-ACCESS accessible-for-notify
    STATUS current
    DESCRIPTION
        "Parameter 'dest_mac_address' in event DLS.275"
    ::= { dlsEventObjects275 2 }

dls275_source_sap OBJECT-TYPE
    SYNTAX Integer32
    MAX-ACCESS accessible-for-notify
    STATUS current
    DESCRIPTION
        "Parameter 'source_sap' in event DLS.275"
    ::= { dlsEventObjects275 3 }

dls275_dest_sap OBJECT-TYPE
    SYNTAX Integer32
    MAX-ACCESS accessible-for-notify
    STATUS current
    DESCRIPTION
        "Parameter 'dest_sap' in event DLS.275"
    ::= { dlsEventObjects275 4 }

dlsEventObjects276 OBJECT-IDENTITY
    STATUS current
    DESCRIPTION
        "Event DLS.276
        LLC interface module for the DLS received a LLCIM_NETUP event."
    ::= { dlsEventsGroup 276 }

dls276_source_mac_address OBJECT-TYPE
    SYNTAX DisplayString
    MAX-ACCESS accessible-for-notify
    STATUS current
    DESCRIPTION
        "Parameter 'source_mac_address' in event DLS.276"
    ::= { dlsEventObjects276 1 }

dls276_dest_mac_address OBJECT-TYPE
    SYNTAX DisplayString
    MAX-ACCESS accessible-for-notify
    STATUS current
    DESCRIPTION
        "Parameter 'dest_mac_address' in event DLS.276"
    ::= { dlsEventObjects276 2 }

dls276_source_sap OBJECT-TYPE
    SYNTAX Integer32
    MAX-ACCESS accessible-for-notify
    STATUS current
    DESCRIPTION
        "Parameter 'source_sap' in event DLS.276"
    ::= { dlsEventObjects276 3 }

dls276_dest_sap OBJECT-TYPE
    SYNTAX Integer32
    MAX-ACCESS accessible-for-notify
    STATUS current
    DESCRIPTION
        "Parameter 'dest_sap' in event DLS.276"
    ::= { dlsEventObjects276 4 }

dlsEventObjects277 OBJECT-IDENTITY
    STATUS current
    DESCRIPTION
        "Event DLS.277
        LLC interface module for the DLS received a LLCIM_NETDOWN event."
    ::= { dlsEventsGroup 277 }

dls277_source_mac_address OBJECT-TYPE
    SYNTAX DisplayString
    MAX-ACCESS accessible-for-notify
    STATUS current
    DESCRIPTION
        "Parameter 'source_mac_address' in event DLS.277"
    ::= { dlsEventObjects277 1 }

dls277_dest_mac_address OBJECT-TYPE
    SYNTAX DisplayString
    MAX-ACCESS accessible-for-notify
    STATUS current
    DESCRIPTION
        "Parameter 'dest_mac_address' in event DLS.277"
    ::= { dlsEventObjects277 2 }

dls277_source_sap OBJECT-TYPE
    SYNTAX Integer32
    MAX-ACCESS accessible-for-notify
    STATUS current
    DESCRIPTION
        "Parameter 'source_sap' in event DLS.277"
    ::= { dlsEventObjects277 3 }

dls277_dest_sap OBJECT-TYPE
    SYNTAX Integer32
    MAX-ACCESS accessible-for-notify
    STATUS current
    DESCRIPTION
        "Parameter 'dest_sap' in event DLS.277"
    ::= { dlsEventObjects277 4 }

dlsEventObjects278 OBJECT-IDENTITY
    STATUS current
    DESCRIPTION
        "Event DLS.278
        LLC interface module for the DLS received a LLCIM_LLC_CONNECT_IND
        event from LLC."
    ::= { dlsEventsGroup 278 }

dls278_source_mac_address OBJECT-TYPE
    SYNTAX DisplayString
    MAX-ACCESS accessible-for-notify
    STATUS current
    DESCRIPTION
        "Parameter 'source_mac_address' in event DLS.278"
    ::= { dlsEventObjects278 1 }

dls278_dest_mac_address OBJECT-TYPE
    SYNTAX DisplayString
    MAX-ACCESS accessible-for-notify
    STATUS current
    DESCRIPTION
        "Parameter 'dest_mac_address' in event DLS.278"
    ::= { dlsEventObjects278 2 }

dls278_source_sap OBJECT-TYPE
    SYNTAX Integer32
    MAX-ACCESS accessible-for-notify
    STATUS current
    DESCRIPTION
        "Parameter 'source_sap' in event DLS.278"
    ::= { dlsEventObjects278 3 }

dls278_dest_sap OBJECT-TYPE
    SYNTAX Integer32
    MAX-ACCESS accessible-for-notify
    STATUS current
    DESCRIPTION
        "Parameter 'dest_sap' in event DLS.278"
    ::= { dlsEventObjects278 4 }

dlsEventObjects279 OBJECT-IDENTITY
    STATUS current
    DESCRIPTION
        "Event DLS.279
        LLC interface module for the DLS received a LLCIM_LLC_CONNECT_CONF
        event from LLC."
    ::= { dlsEventsGroup 279 }

dls279_source_mac_address OBJECT-TYPE
    SYNTAX DisplayString
    MAX-ACCESS accessible-for-notify
    STATUS current
    DESCRIPTION
        "Parameter 'source_mac_address' in event DLS.279"
    ::= { dlsEventObjects279 1 }

dls279_dest_mac_address OBJECT-TYPE
    SYNTAX DisplayString
    MAX-ACCESS accessible-for-notify
    STATUS current
    DESCRIPTION
        "Parameter 'dest_mac_address' in event DLS.279"
    ::= { dlsEventObjects279 2 }

dls279_source_sap OBJECT-TYPE
    SYNTAX Integer32
    MAX-ACCESS accessible-for-notify
    STATUS current
    DESCRIPTION
        "Parameter 'source_sap' in event DLS.279"
    ::= { dlsEventObjects279 3 }

dls279_dest_sap OBJECT-TYPE
    SYNTAX Integer32
    MAX-ACCESS accessible-for-notify
    STATUS current
    DESCRIPTION
        "Parameter 'dest_sap' in event DLS.279"
    ::= { dlsEventObjects279 4 }

dlsEventObjects280 OBJECT-IDENTITY
    STATUS current
    DESCRIPTION
        "Event DLS.280
        LLC interface module for the DLS received a LLCIM_LLC_ENTER_BUSY
        event from LLC."
    ::= { dlsEventsGroup 280 }

dls280_source_mac_address OBJECT-TYPE
    SYNTAX DisplayString
    MAX-ACCESS accessible-for-notify
    STATUS current
    DESCRIPTION
        "Parameter 'source_mac_address' in event DLS.280"
    ::= { dlsEventObjects280 1 }

dls280_dest_mac_address OBJECT-TYPE
    SYNTAX DisplayString
    MAX-ACCESS accessible-for-notify
    STATUS current
    DESCRIPTION
        "Parameter 'dest_mac_address' in event DLS.280"
    ::= { dlsEventObjects280 2 }

dls280_source_sap OBJECT-TYPE
    SYNTAX Integer32
    MAX-ACCESS accessible-for-notify
    STATUS current
    DESCRIPTION
        "Parameter 'source_sap' in event DLS.280"
    ::= { dlsEventObjects280 3 }

dls280_dest_sap OBJECT-TYPE
    SYNTAX Integer32
    MAX-ACCESS accessible-for-notify
    STATUS current
    DESCRIPTION
        "Parameter 'dest_sap' in event DLS.280"
    ::= { dlsEventObjects280 4 }

dlsEventObjects281 OBJECT-IDENTITY
    STATUS current
    DESCRIPTION
        "Event DLS.281
        LLC interface module for the DLS received a LLCIM_LLC_EXIT_BUSY
        event from LLC."
    ::= { dlsEventsGroup 281 }

dls281_source_mac_address OBJECT-TYPE
    SYNTAX DisplayString
    MAX-ACCESS accessible-for-notify
    STATUS current
    DESCRIPTION
        "Parameter 'source_mac_address' in event DLS.281"
    ::= { dlsEventObjects281 1 }

dls281_dest_mac_address OBJECT-TYPE
    SYNTAX DisplayString
    MAX-ACCESS accessible-for-notify
    STATUS current
    DESCRIPTION
        "Parameter 'dest_mac_address' in event DLS.281"
    ::= { dlsEventObjects281 2 }

dls281_source_sap OBJECT-TYPE
    SYNTAX Integer32
    MAX-ACCESS accessible-for-notify
    STATUS current
    DESCRIPTION
        "Parameter 'source_sap' in event DLS.281"
    ::= { dlsEventObjects281 3 }

dls281_dest_sap OBJECT-TYPE
    SYNTAX Integer32
    MAX-ACCESS accessible-for-notify
    STATUS current
    DESCRIPTION
        "Parameter 'dest_sap' in event DLS.281"
    ::= { dlsEventObjects281 4 }

dlsEventObjects282 OBJECT-IDENTITY
    STATUS current
    DESCRIPTION
        "Event DLS.282
        LLC interface module for the DLS received a LLCIM_LLC_DISC_IND
        event from LLC."
    ::= { dlsEventsGroup 282 }

dls282_source_mac_address OBJECT-TYPE
    SYNTAX DisplayString
    MAX-ACCESS accessible-for-notify
    STATUS current
    DESCRIPTION
        "Parameter 'source_mac_address' in event DLS.282"
    ::= { dlsEventObjects282 1 }

dls282_dest_mac_address OBJECT-TYPE
    SYNTAX DisplayString
    MAX-ACCESS accessible-for-notify
    STATUS current
    DESCRIPTION
        "Parameter 'dest_mac_address' in event DLS.282"
    ::= { dlsEventObjects282 2 }

dls282_source_sap OBJECT-TYPE
    SYNTAX Integer32
    MAX-ACCESS accessible-for-notify
    STATUS current
    DESCRIPTION
        "Parameter 'source_sap' in event DLS.282"
    ::= { dlsEventObjects282 3 }

dls282_dest_sap OBJECT-TYPE
    SYNTAX Integer32
    MAX-ACCESS accessible-for-notify
    STATUS current
    DESCRIPTION
        "Parameter 'dest_sap' in event DLS.282"
    ::= { dlsEventObjects282 4 }

dlsEventObjects283 OBJECT-IDENTITY
    STATUS current
    DESCRIPTION
        "Event DLS.283
        LLC interface module for the DLS received a LLCIM_LLC_DISC_CONF
        event from LLC."
    ::= { dlsEventsGroup 283 }

dls283_source_mac_address OBJECT-TYPE
    SYNTAX DisplayString
    MAX-ACCESS accessible-for-notify
    STATUS current
    DESCRIPTION
        "Parameter 'source_mac_address' in event DLS.283"
    ::= { dlsEventObjects283 1 }

dls283_dest_mac_address OBJECT-TYPE
    SYNTAX DisplayString
    MAX-ACCESS accessible-for-notify
    STATUS current
    DESCRIPTION
        "Parameter 'dest_mac_address' in event DLS.283"
    ::= { dlsEventObjects283 2 }

dls283_source_sap OBJECT-TYPE
    SYNTAX Integer32
    MAX-ACCESS accessible-for-notify
    STATUS current
    DESCRIPTION
        "Parameter 'source_sap' in event DLS.283"
    ::= { dlsEventObjects283 3 }

dls283_dest_sap OBJECT-TYPE
    SYNTAX Integer32
    MAX-ACCESS accessible-for-notify
    STATUS current
    DESCRIPTION
        "Parameter 'dest_sap' in event DLS.283"
    ::= { dlsEventObjects283 4 }

dlsEventObjects284 OBJECT-IDENTITY
    STATUS current
    DESCRIPTION
        "Event DLS.284
        LLC interface module for the DLS received a LLCIM_LLC_RESET_IND
        event from LLC."
    ::= { dlsEventsGroup 284 }

dls284_source_mac_address OBJECT-TYPE
    SYNTAX DisplayString
    MAX-ACCESS accessible-for-notify
    STATUS current
    DESCRIPTION
        "Parameter 'source_mac_address' in event DLS.284"
    ::= { dlsEventObjects284 1 }

dls284_dest_mac_address OBJECT-TYPE
    SYNTAX DisplayString
    MAX-ACCESS accessible-for-notify
    STATUS current
    DESCRIPTION
        "Parameter 'dest_mac_address' in event DLS.284"
    ::= { dlsEventObjects284 2 }

dls284_source_sap OBJECT-TYPE
    SYNTAX Integer32
    MAX-ACCESS accessible-for-notify
    STATUS current
    DESCRIPTION
        "Parameter 'source_sap' in event DLS.284"
    ::= { dlsEventObjects284 3 }

dls284_dest_sap OBJECT-TYPE
    SYNTAX Integer32
    MAX-ACCESS accessible-for-notify
    STATUS current
    DESCRIPTION
        "Parameter 'dest_sap' in event DLS.284"
    ::= { dlsEventObjects284 4 }

dlsEventObjects285 OBJECT-IDENTITY
    STATUS current
    DESCRIPTION
        "Event DLS.285
        LLC interface module for the DLS received a LLCIM_LLC_TEST_C
        event from LLC."
    ::= { dlsEventsGroup 285 }

dls285_source_mac_address OBJECT-TYPE
    SYNTAX DisplayString
    MAX-ACCESS accessible-for-notify
    STATUS current
    DESCRIPTION
        "Parameter 'source_mac_address' in event DLS.285"
    ::= { dlsEventObjects285 1 }

dls285_dest_mac_address OBJECT-TYPE
    SYNTAX DisplayString
    MAX-ACCESS accessible-for-notify
    STATUS current
    DESCRIPTION
        "Parameter 'dest_mac_address' in event DLS.285"
    ::= { dlsEventObjects285 2 }

dls285_source_sap OBJECT-TYPE
    SYNTAX Integer32
    MAX-ACCESS accessible-for-notify
    STATUS current
    DESCRIPTION
        "Parameter 'source_sap' in event DLS.285"
    ::= { dlsEventObjects285 3 }

dls285_dest_sap OBJECT-TYPE
    SYNTAX Integer32
    MAX-ACCESS accessible-for-notify
    STATUS current
    DESCRIPTION
        "Parameter 'dest_sap' in event DLS.285"
    ::= { dlsEventObjects285 4 }

dlsEventObjects286 OBJECT-IDENTITY
    STATUS current
    DESCRIPTION
        "Event DLS.286
        LLC interface module for the DLS received a LLCIM_LLC_TEST_R
        event from LLC."
    ::= { dlsEventsGroup 286 }

dls286_source_mac_address OBJECT-TYPE
    SYNTAX DisplayString
    MAX-ACCESS accessible-for-notify
    STATUS current
    DESCRIPTION
        "Parameter 'source_mac_address' in event DLS.286"
    ::= { dlsEventObjects286 1 }

dls286_dest_mac_address OBJECT-TYPE
    SYNTAX DisplayString
    MAX-ACCESS accessible-for-notify
    STATUS current
    DESCRIPTION
        "Parameter 'dest_mac_address' in event DLS.286"
    ::= { dlsEventObjects286 2 }

dls286_source_sap OBJECT-TYPE
    SYNTAX Integer32
    MAX-ACCESS accessible-for-notify
    STATUS current
    DESCRIPTION
        "Parameter 'source_sap' in event DLS.286"
    ::= { dlsEventObjects286 3 }

dls286_dest_sap OBJECT-TYPE
    SYNTAX Integer32
    MAX-ACCESS accessible-for-notify
    STATUS current
    DESCRIPTION
        "Parameter 'dest_sap' in event DLS.286"
    ::= { dlsEventObjects286 4 }

dlsEventObjects287 OBJECT-IDENTITY
    STATUS current
    DESCRIPTION
        "Event DLS.287
        LLC interface module for the DLS received a LLCIM_LLC_XID_C
        event from LLC."
    ::= { dlsEventsGroup 287 }

dls287_source_mac_address OBJECT-TYPE
    SYNTAX DisplayString
    MAX-ACCESS accessible-for-notify
    STATUS current
    DESCRIPTION
        "Parameter 'source_mac_address' in event DLS.287"
    ::= { dlsEventObjects287 1 }

dls287_dest_mac_address OBJECT-TYPE
    SYNTAX DisplayString
    MAX-ACCESS accessible-for-notify
    STATUS current
    DESCRIPTION
        "Parameter 'dest_mac_address' in event DLS.287"
    ::= { dlsEventObjects287 2 }

dls287_source_sap OBJECT-TYPE
    SYNTAX Integer32
    MAX-ACCESS accessible-for-notify
    STATUS current
    DESCRIPTION
        "Parameter 'source_sap' in event DLS.287"
    ::= { dlsEventObjects287 3 }

dls287_dest_sap OBJECT-TYPE
    SYNTAX Integer32
    MAX-ACCESS accessible-for-notify
    STATUS current
    DESCRIPTION
        "Parameter 'dest_sap' in event DLS.287"
    ::= { dlsEventObjects287 4 }

dlsEventObjects288 OBJECT-IDENTITY
    STATUS current
    DESCRIPTION
        "Event DLS.288
        LLC interface module for the DLS received a LLCIM_LLC_XID_R
        event from LLC."
    ::= { dlsEventsGroup 288 }

dls288_source_mac_address OBJECT-TYPE
    SYNTAX DisplayString
    MAX-ACCESS accessible-for-notify
    STATUS current
    DESCRIPTION
        "Parameter 'source_mac_address' in event DLS.288"
    ::= { dlsEventObjects288 1 }

dls288_dest_mac_address OBJECT-TYPE
    SYNTAX DisplayString
    MAX-ACCESS accessible-for-notify
    STATUS current
    DESCRIPTION
        "Parameter 'dest_mac_address' in event DLS.288"
    ::= { dlsEventObjects288 2 }

dls288_source_sap OBJECT-TYPE
    SYNTAX Integer32
    MAX-ACCESS accessible-for-notify
    STATUS current
    DESCRIPTION
        "Parameter 'source_sap' in event DLS.288"
    ::= { dlsEventObjects288 3 }

dls288_dest_sap OBJECT-TYPE
    SYNTAX Integer32
    MAX-ACCESS accessible-for-notify
    STATUS current
    DESCRIPTION
        "Parameter 'dest_sap' in event DLS.288"
    ::= { dlsEventObjects288 4 }

dlsEventObjects289 OBJECT-IDENTITY
    STATUS current
    DESCRIPTION
        "Event DLS.289
        LLC interface module for the DLS received a LLCIM_LLC_UI
        event from LLC."
    ::= { dlsEventsGroup 289 }

dls289_source_mac_address OBJECT-TYPE
    SYNTAX DisplayString
    MAX-ACCESS accessible-for-notify
    STATUS current
    DESCRIPTION
        "Parameter 'source_mac_address' in event DLS.289"
    ::= { dlsEventObjects289 1 }

dls289_dest_mac_address OBJECT-TYPE
    SYNTAX DisplayString
    MAX-ACCESS accessible-for-notify
    STATUS current
    DESCRIPTION
        "Parameter 'dest_mac_address' in event DLS.289"
    ::= { dlsEventObjects289 2 }

dls289_source_sap OBJECT-TYPE
    SYNTAX Integer32
    MAX-ACCESS accessible-for-notify
    STATUS current
    DESCRIPTION
        "Parameter 'source_sap' in event DLS.289"
    ::= { dlsEventObjects289 3 }

dls289_dest_sap OBJECT-TYPE
    SYNTAX Integer32
    MAX-ACCESS accessible-for-notify
    STATUS current
    DESCRIPTION
        "Parameter 'dest_sap' in event DLS.289"
    ::= { dlsEventObjects289 4 }

dlsEventObjects290 OBJECT-IDENTITY
    STATUS current
    DESCRIPTION
        "Event DLS.290
        LLC interface module for the DLS received a LLCIM_DLC_START_DL
        event from DLS."
    ::= { dlsEventsGroup 290 }

dls290_source_mac_address OBJECT-TYPE
    SYNTAX DisplayString
    MAX-ACCESS accessible-for-notify
    STATUS current
    DESCRIPTION
        "Parameter 'source_mac_address' in event DLS.290"
    ::= { dlsEventObjects290 1 }

dls290_dest_mac_address OBJECT-TYPE
    SYNTAX DisplayString
    MAX-ACCESS accessible-for-notify
    STATUS current
    DESCRIPTION
        "Parameter 'dest_mac_address' in event DLS.290"
    ::= { dlsEventObjects290 2 }

dls290_source_sap OBJECT-TYPE
    SYNTAX Integer32
    MAX-ACCESS accessible-for-notify
    STATUS current
    DESCRIPTION
        "Parameter 'source_sap' in event DLS.290"
    ::= { dlsEventObjects290 3 }

dls290_dest_sap OBJECT-TYPE
    SYNTAX Integer32
    MAX-ACCESS accessible-for-notify
    STATUS current
    DESCRIPTION
        "Parameter 'dest_sap' in event DLS.290"
    ::= { dlsEventObjects290 4 }

dlsEventObjects291 OBJECT-IDENTITY
    STATUS current
    DESCRIPTION
        "Event DLS.291
        LLC interface module for the DLS received a LLCIM_DLC_RESOLVE_R
        event from DLS."
    ::= { dlsEventsGroup 291 }

dls291_source_mac_address OBJECT-TYPE
    SYNTAX DisplayString
    MAX-ACCESS accessible-for-notify
    STATUS current
    DESCRIPTION
        "Parameter 'source_mac_address' in event DLS.291"
    ::= { dlsEventObjects291 1 }

dls291_dest_mac_address OBJECT-TYPE
    SYNTAX DisplayString
    MAX-ACCESS accessible-for-notify
    STATUS current
    DESCRIPTION
        "Parameter 'dest_mac_address' in event DLS.291"
    ::= { dlsEventObjects291 2 }

dls291_source_sap OBJECT-TYPE
    SYNTAX Integer32
    MAX-ACCESS accessible-for-notify
    STATUS current
    DESCRIPTION
        "Parameter 'source_sap' in event DLS.291"
    ::= { dlsEventObjects291 3 }

dls291_dest_sap OBJECT-TYPE
    SYNTAX Integer32
    MAX-ACCESS accessible-for-notify
    STATUS current
    DESCRIPTION
        "Parameter 'dest_sap' in event DLS.291"
    ::= { dlsEventObjects291 4 }

dlsEventObjects292 OBJECT-IDENTITY
    STATUS current
    DESCRIPTION
        "Event DLS.292
        LLC interface module for the DLS received a LLCIM_DLC_CONTACT
        event from DLS."
    ::= { dlsEventsGroup 292 }

dls292_source_mac_address OBJECT-TYPE
    SYNTAX DisplayString
    MAX-ACCESS accessible-for-notify
    STATUS current
    DESCRIPTION
        "Parameter 'source_mac_address' in event DLS.292"
    ::= { dlsEventObjects292 1 }

dls292_dest_mac_address OBJECT-TYPE
    SYNTAX DisplayString
    MAX-ACCESS accessible-for-notify
    STATUS current
    DESCRIPTION
        "Parameter 'dest_mac_address' in event DLS.292"
    ::= { dlsEventObjects292 2 }

dls292_source_sap OBJECT-TYPE
    SYNTAX Integer32
    MAX-ACCESS accessible-for-notify
    STATUS current
    DESCRIPTION
        "Parameter 'source_sap' in event DLS.292"
    ::= { dlsEventObjects292 3 }

dls292_dest_sap OBJECT-TYPE
    SYNTAX Integer32
    MAX-ACCESS accessible-for-notify
    STATUS current
    DESCRIPTION
        "Parameter 'dest_sap' in event DLS.292"
    ::= { dlsEventObjects292 4 }

dlsEventObjects293 OBJECT-IDENTITY
    STATUS current
    DESCRIPTION
        "Event DLS.293
        LLC interface module for the DLS received a LLCIM_DLC_DGRM
        event from DLS."
    ::= { dlsEventsGroup 293 }

dls293_source_mac_address OBJECT-TYPE
    SYNTAX DisplayString
    MAX-ACCESS accessible-for-notify
    STATUS current
    DESCRIPTION
        "Parameter 'source_mac_address' in event DLS.293"
    ::= { dlsEventObjects293 1 }

dls293_dest_mac_address OBJECT-TYPE
    SYNTAX DisplayString
    MAX-ACCESS accessible-for-notify
    STATUS current
    DESCRIPTION
        "Parameter 'dest_mac_address' in event DLS.293"
    ::= { dlsEventObjects293 2 }

dls293_source_sap OBJECT-TYPE
    SYNTAX Integer32
    MAX-ACCESS accessible-for-notify
    STATUS current
    DESCRIPTION
        "Parameter 'source_sap' in event DLS.293"
    ::= { dlsEventObjects293 3 }

dls293_dest_sap OBJECT-TYPE
    SYNTAX Integer32
    MAX-ACCESS accessible-for-notify
    STATUS current
    DESCRIPTION
        "Parameter 'dest_sap' in event DLS.293"
    ::= { dlsEventObjects293 4 }

dlsEventObjects294 OBJECT-IDENTITY
    STATUS current
    DESCRIPTION
        "Event DLS.294
        LLC interface module for the DLS received a LLCIM_DLC_XID
        event from DLS."
    ::= { dlsEventsGroup 294 }

dls294_source_mac_address OBJECT-TYPE
    SYNTAX DisplayString
    MAX-ACCESS accessible-for-notify
    STATUS current
    DESCRIPTION
        "Parameter 'source_mac_address' in event DLS.294"
    ::= { dlsEventObjects294 1 }

dls294_dest_mac_address OBJECT-TYPE
    SYNTAX DisplayString
    MAX-ACCESS accessible-for-notify
    STATUS current
    DESCRIPTION
        "Parameter 'dest_mac_address' in event DLS.294"
    ::= { dlsEventObjects294 2 }

dls294_source_sap OBJECT-TYPE
    SYNTAX Integer32
    MAX-ACCESS accessible-for-notify
    STATUS current
    DESCRIPTION
        "Parameter 'source_sap' in event DLS.294"
    ::= { dlsEventObjects294 3 }

dls294_dest_sap OBJECT-TYPE
    SYNTAX Integer32
    MAX-ACCESS accessible-for-notify
    STATUS current
    DESCRIPTION
        "Parameter 'dest_sap' in event DLS.294"
    ::= { dlsEventObjects294 4 }

dlsEventObjects295 OBJECT-IDENTITY
    STATUS current
    DESCRIPTION
        "Event DLS.295
        LLC interface module for the DLS received a LLCIM_DLC_HALT_DL
        event from DLS."
    ::= { dlsEventsGroup 295 }

dls295_source_mac_address OBJECT-TYPE
    SYNTAX DisplayString
    MAX-ACCESS accessible-for-notify
    STATUS current
    DESCRIPTION
        "Parameter 'source_mac_address' in event DLS.295"
    ::= { dlsEventObjects295 1 }

dls295_dest_mac_address OBJECT-TYPE
    SYNTAX DisplayString
    MAX-ACCESS accessible-for-notify
    STATUS current
    DESCRIPTION
        "Parameter 'dest_mac_address' in event DLS.295"
    ::= { dlsEventObjects295 2 }

dls295_source_sap OBJECT-TYPE
    SYNTAX Integer32
    MAX-ACCESS accessible-for-notify
    STATUS current
    DESCRIPTION
        "Parameter 'source_sap' in event DLS.295"
    ::= { dlsEventObjects295 3 }

dls295_dest_sap OBJECT-TYPE
    SYNTAX Integer32
    MAX-ACCESS accessible-for-notify
    STATUS current
    DESCRIPTION
        "Parameter 'dest_sap' in event DLS.295"
    ::= { dlsEventObjects295 4 }

dlsEventObjects296 OBJECT-IDENTITY
    STATUS current
    DESCRIPTION
        "Event DLS.296
        LLC interface module for the DLS received a LLCIM_DLC_ENTER_BUSY
        event from DLS."
    ::= { dlsEventsGroup 296 }

dls296_source_mac_address OBJECT-TYPE
    SYNTAX DisplayString
    MAX-ACCESS accessible-for-notify
    STATUS current
    DESCRIPTION
        "Parameter 'source_mac_address' in event DLS.296"
    ::= { dlsEventObjects296 1 }

dls296_dest_mac_address OBJECT-TYPE
    SYNTAX DisplayString
    MAX-ACCESS accessible-for-notify
    STATUS current
    DESCRIPTION
        "Parameter 'dest_mac_address' in event DLS.296"
    ::= { dlsEventObjects296 2 }

dls296_source_sap OBJECT-TYPE
    SYNTAX Integer32
    MAX-ACCESS accessible-for-notify
    STATUS current
    DESCRIPTION
        "Parameter 'source_sap' in event DLS.296"
    ::= { dlsEventObjects296 3 }

dls296_dest_sap OBJECT-TYPE
    SYNTAX Integer32
    MAX-ACCESS accessible-for-notify
    STATUS current
    DESCRIPTION
        "Parameter 'dest_sap' in event DLS.296"
    ::= { dlsEventObjects296 4 }

dlsEventObjects297 OBJECT-IDENTITY
    STATUS current
    DESCRIPTION
        "Event DLS.297
        LLC interface module for the DLS received a LLCIM_DLC_EXIT_BUSY
        event from DLS."
    ::= { dlsEventsGroup 297 }

dls297_source_mac_address OBJECT-TYPE
    SYNTAX DisplayString
    MAX-ACCESS accessible-for-notify
    STATUS current
    DESCRIPTION
        "Parameter 'source_mac_address' in event DLS.297"
    ::= { dlsEventObjects297 1 }

dls297_dest_mac_address OBJECT-TYPE
    SYNTAX DisplayString
    MAX-ACCESS accessible-for-notify
    STATUS current
    DESCRIPTION
        "Parameter 'dest_mac_address' in event DLS.297"
    ::= { dlsEventObjects297 2 }

dls297_source_sap OBJECT-TYPE
    SYNTAX Integer32
    MAX-ACCESS accessible-for-notify
    STATUS current
    DESCRIPTION
        "Parameter 'source_sap' in event DLS.297"
    ::= { dlsEventObjects297 3 }

dls297_dest_sap OBJECT-TYPE
    SYNTAX Integer32
    MAX-ACCESS accessible-for-notify
    STATUS current
    DESCRIPTION
        "Parameter 'dest_sap' in event DLS.297"
    ::= { dlsEventObjects297 4 }

dlsEventObjects298 OBJECT-IDENTITY
    STATUS current
    DESCRIPTION
        "Event DLS.298
        LLC interface module for the DLS received a LLCIM_LLC_INFO
        event from LLC."
    ::= { dlsEventsGroup 298 }

dls298_source_mac_address OBJECT-TYPE
    SYNTAX DisplayString
    MAX-ACCESS accessible-for-notify
    STATUS current
    DESCRIPTION
        "Parameter 'source_mac_address' in event DLS.298"
    ::= { dlsEventObjects298 1 }

dls298_dest_mac_address OBJECT-TYPE
    SYNTAX DisplayString
    MAX-ACCESS accessible-for-notify
    STATUS current
    DESCRIPTION
        "Parameter 'dest_mac_address' in event DLS.298"
    ::= { dlsEventObjects298 2 }

dls298_source_sap OBJECT-TYPE
    SYNTAX Integer32
    MAX-ACCESS accessible-for-notify
    STATUS current
    DESCRIPTION
        "Parameter 'source_sap' in event DLS.298"
    ::= { dlsEventObjects298 3 }

dls298_dest_sap OBJECT-TYPE
    SYNTAX Integer32
    MAX-ACCESS accessible-for-notify
    STATUS current
    DESCRIPTION
        "Parameter 'dest_sap' in event DLS.298"
    ::= { dlsEventObjects298 4 }

dlsEventObjects299 OBJECT-IDENTITY
    STATUS current
    DESCRIPTION
        "Event DLS.299
        LLC interface module for the DLS received a LLCIM_DLC_INFO
        event from DLS."
    ::= { dlsEventsGroup 299 }

dls299_source_mac_address OBJECT-TYPE
    SYNTAX DisplayString
    MAX-ACCESS accessible-for-notify
    STATUS current
    DESCRIPTION
        "Parameter 'source_mac_address' in event DLS.299"
    ::= { dlsEventObjects299 1 }

dls299_dest_mac_address OBJECT-TYPE
    SYNTAX DisplayString
    MAX-ACCESS accessible-for-notify
    STATUS current
    DESCRIPTION
        "Parameter 'dest_mac_address' in event DLS.299"
    ::= { dlsEventObjects299 2 }

dls299_source_sap OBJECT-TYPE
    SYNTAX Integer32
    MAX-ACCESS accessible-for-notify
    STATUS current
    DESCRIPTION
        "Parameter 'source_sap' in event DLS.299"
    ::= { dlsEventObjects299 3 }

dls299_dest_sap OBJECT-TYPE
    SYNTAX Integer32
    MAX-ACCESS accessible-for-notify
    STATUS current
    DESCRIPTION
        "Parameter 'dest_sap' in event DLS.299"
    ::= { dlsEventObjects299 4 }

dlsEventObjects300 OBJECT-IDENTITY
    STATUS current
    DESCRIPTION
        "Event DLS.300
        LLC interface module for the DLS is transitioning to the
        LLCIM_CONTACTED state."
    ::= { dlsEventsGroup 300 }

dls300_source_mac_address OBJECT-TYPE
    SYNTAX DisplayString
    MAX-ACCESS accessible-for-notify
    STATUS current
    DESCRIPTION
        "Parameter 'source_mac_address' in event DLS.300"
    ::= { dlsEventObjects300 1 }

dls300_dest_mac_address OBJECT-TYPE
    SYNTAX DisplayString
    MAX-ACCESS accessible-for-notify
    STATUS current
    DESCRIPTION
        "Parameter 'dest_mac_address' in event DLS.300"
    ::= { dlsEventObjects300 2 }

dls300_source_sap OBJECT-TYPE
    SYNTAX Integer32
    MAX-ACCESS accessible-for-notify
    STATUS current
    DESCRIPTION
        "Parameter 'source_sap' in event DLS.300"
    ::= { dlsEventObjects300 3 }

dls300_dest_sap OBJECT-TYPE
    SYNTAX Integer32
    MAX-ACCESS accessible-for-notify
    STATUS current
    DESCRIPTION
        "Parameter 'dest_sap' in event DLS.300"
    ::= { dlsEventObjects300 4 }

dlsEventObjects301 OBJECT-IDENTITY
    STATUS current
    DESCRIPTION
        "Event DLS.301
        LLC interface module for the DLS is transitioning to the
        LLCIM_RESOLVE_PEND state."
    ::= { dlsEventsGroup 301 }

dls301_source_mac_address OBJECT-TYPE
    SYNTAX DisplayString
    MAX-ACCESS accessible-for-notify
    STATUS current
    DESCRIPTION
        "Parameter 'source_mac_address' in event DLS.301"
    ::= { dlsEventObjects301 1 }

dls301_dest_mac_address OBJECT-TYPE
    SYNTAX DisplayString
    MAX-ACCESS accessible-for-notify
    STATUS current
    DESCRIPTION
        "Parameter 'dest_mac_address' in event DLS.301"
    ::= { dlsEventObjects301 2 }

dls301_source_sap OBJECT-TYPE
    SYNTAX Integer32
    MAX-ACCESS accessible-for-notify
    STATUS current
    DESCRIPTION
        "Parameter 'source_sap' in event DLS.301"
    ::= { dlsEventObjects301 3 }

dls301_dest_sap OBJECT-TYPE
    SYNTAX Integer32
    MAX-ACCESS accessible-for-notify
    STATUS current
    DESCRIPTION
        "Parameter 'dest_sap' in event DLS.301"
    ::= { dlsEventObjects301 4 }

dlsEventObjects302 OBJECT-IDENTITY
    STATUS current
    DESCRIPTION
        "Event DLS.302
        LLC interface module for the DLS is transitioning to the
        LLCIM_CONNECTED state."
    ::= { dlsEventsGroup 302 }

dls302_source_mac_address OBJECT-TYPE
    SYNTAX DisplayString
    MAX-ACCESS accessible-for-notify
    STATUS current
    DESCRIPTION
        "Parameter 'source_mac_address' in event DLS.302"
    ::= { dlsEventObjects302 1 }

dls302_dest_mac_address OBJECT-TYPE
    SYNTAX DisplayString
    MAX-ACCESS accessible-for-notify
    STATUS current
    DESCRIPTION
        "Parameter 'dest_mac_address' in event DLS.302"
    ::= { dlsEventObjects302 2 }

dls302_source_sap OBJECT-TYPE
    SYNTAX Integer32
    MAX-ACCESS accessible-for-notify
    STATUS current
    DESCRIPTION
        "Parameter 'source_sap' in event DLS.302"
    ::= { dlsEventObjects302 3 }

dls302_dest_sap OBJECT-TYPE
    SYNTAX Integer32
    MAX-ACCESS accessible-for-notify
    STATUS current
    DESCRIPTION
        "Parameter 'dest_sap' in event DLS.302"
    ::= { dlsEventObjects302 4 }

dlsEventObjects303 OBJECT-IDENTITY
    STATUS current
    DESCRIPTION
        "Event DLS.303
        LLC interface module for the DLS is transitioning to the
        LLCIM_CONNECT_PEND state."
    ::= { dlsEventsGroup 303 }

dls303_source_mac_address OBJECT-TYPE
    SYNTAX DisplayString
    MAX-ACCESS accessible-for-notify
    STATUS current
    DESCRIPTION
        "Parameter 'source_mac_address' in event DLS.303"
    ::= { dlsEventObjects303 1 }

dls303_dest_mac_address OBJECT-TYPE
    SYNTAX DisplayString
    MAX-ACCESS accessible-for-notify
    STATUS current
    DESCRIPTION
        "Parameter 'dest_mac_address' in event DLS.303"
    ::= { dlsEventObjects303 2 }

dls303_source_sap OBJECT-TYPE
    SYNTAX Integer32
    MAX-ACCESS accessible-for-notify
    STATUS current
    DESCRIPTION
        "Parameter 'source_sap' in event DLS.303"
    ::= { dlsEventObjects303 3 }

dls303_dest_sap OBJECT-TYPE
    SYNTAX Integer32
    MAX-ACCESS accessible-for-notify
    STATUS current
    DESCRIPTION
        "Parameter 'dest_sap' in event DLS.303"
    ::= { dlsEventObjects303 4 }

dlsEventObjects304 OBJECT-IDENTITY
    STATUS current
    DESCRIPTION
        "Event DLS.304
        LLC interface module for the DLS is transitioning to the
        LLCIM_CONTACT_PEND state."
    ::= { dlsEventsGroup 304 }

dls304_source_mac_address OBJECT-TYPE
    SYNTAX DisplayString
    MAX-ACCESS accessible-for-notify
    STATUS current
    DESCRIPTION
        "Parameter 'source_mac_address' in event DLS.304"
    ::= { dlsEventObjects304 1 }

dls304_dest_mac_address OBJECT-TYPE
    SYNTAX DisplayString
    MAX-ACCESS accessible-for-notify
    STATUS current
    DESCRIPTION
        "Parameter 'dest_mac_address' in event DLS.304"
    ::= { dlsEventObjects304 2 }

dls304_source_sap OBJECT-TYPE
    SYNTAX Integer32
    MAX-ACCESS accessible-for-notify
    STATUS current
    DESCRIPTION
        "Parameter 'source_sap' in event DLS.304"
    ::= { dlsEventObjects304 3 }

dls304_dest_sap OBJECT-TYPE
    SYNTAX Integer32
    MAX-ACCESS accessible-for-notify
    STATUS current
    DESCRIPTION
        "Parameter 'dest_sap' in event DLS.304"
    ::= { dlsEventObjects304 4 }

dlsEventObjects305 OBJECT-IDENTITY
    STATUS current
    DESCRIPTION
        "Event DLS.305
        LLC interface module for the DLS is transitioning to the
        LLCIM_DISCONNECTED state."
    ::= { dlsEventsGroup 305 }

dls305_source_mac_address OBJECT-TYPE
    SYNTAX DisplayString
    MAX-ACCESS accessible-for-notify
    STATUS current
    DESCRIPTION
        "Parameter 'source_mac_address' in event DLS.305"
    ::= { dlsEventObjects305 1 }

dls305_dest_mac_address OBJECT-TYPE
    SYNTAX DisplayString
    MAX-ACCESS accessible-for-notify
    STATUS current
    DESCRIPTION
        "Parameter 'dest_mac_address' in event DLS.305"
    ::= { dlsEventObjects305 2 }

dls305_source_sap OBJECT-TYPE
    SYNTAX Integer32
    MAX-ACCESS accessible-for-notify
    STATUS current
    DESCRIPTION
        "Parameter 'source_sap' in event DLS.305"
    ::= { dlsEventObjects305 3 }

dls305_dest_sap OBJECT-TYPE
    SYNTAX Integer32
    MAX-ACCESS accessible-for-notify
    STATUS current
    DESCRIPTION
        "Parameter 'dest_sap' in event DLS.305"
    ::= { dlsEventObjects305 4 }

dlsEventObjects306 OBJECT-IDENTITY
    STATUS current
    DESCRIPTION
        "Event DLS.306
        LLC interface module for the DLS is transitioning to the
        LLCIM_DISC_PEND state."
    ::= { dlsEventsGroup 306 }

dls306_source_mac_address OBJECT-TYPE
    SYNTAX DisplayString
    MAX-ACCESS accessible-for-notify
    STATUS current
    DESCRIPTION
        "Parameter 'source_mac_address' in event DLS.306"
    ::= { dlsEventObjects306 1 }

dls306_dest_mac_address OBJECT-TYPE
    SYNTAX DisplayString
    MAX-ACCESS accessible-for-notify
    STATUS current
    DESCRIPTION
        "Parameter 'dest_mac_address' in event DLS.306"
    ::= { dlsEventObjects306 2 }

dls306_source_sap OBJECT-TYPE
    SYNTAX Integer32
    MAX-ACCESS accessible-for-notify
    STATUS current
    DESCRIPTION
        "Parameter 'source_sap' in event DLS.306"
    ::= { dlsEventObjects306 3 }

dls306_dest_sap OBJECT-TYPE
    SYNTAX Integer32
    MAX-ACCESS accessible-for-notify
    STATUS current
    DESCRIPTION
        "Parameter 'dest_sap' in event DLS.306"
    ::= { dlsEventObjects306 4 }

dlsEventObjects313 OBJECT-IDENTITY
    STATUS current
    DESCRIPTION
        "Event DLS.313
        An INFO frame received from DLS cloud was successfully sent to a
        LLC end station."
    ::= { dlsEventsGroup 313 }

dls313_source_mac_address OBJECT-TYPE
    SYNTAX DisplayString
    MAX-ACCESS accessible-for-notify
    STATUS current
    DESCRIPTION
        "Parameter 'source_mac_address' in event DLS.313"
    ::= { dlsEventObjects313 1 }

dls313_dest_mac_address OBJECT-TYPE
    SYNTAX DisplayString
    MAX-ACCESS accessible-for-notify
    STATUS current
    DESCRIPTION
        "Parameter 'dest_mac_address' in event DLS.313"
    ::= { dlsEventObjects313 2 }

dls313_source_sap OBJECT-TYPE
    SYNTAX Integer32
    MAX-ACCESS accessible-for-notify
    STATUS current
    DESCRIPTION
        "Parameter 'source_sap' in event DLS.313"
    ::= { dlsEventObjects313 3 }

dls313_dest_sap OBJECT-TYPE
    SYNTAX Integer32
    MAX-ACCESS accessible-for-notify
    STATUS current
    DESCRIPTION
        "Parameter 'dest_sap' in event DLS.313"
    ::= { dlsEventObjects313 4 }

dlsEventObjects314 OBJECT-IDENTITY
    STATUS current
    DESCRIPTION
        "Event DLS.314
        The user configured a TCP transmit buffer size in the group
        configuration that cannot be handled by the router. It has
        automatically been set to a lower value than can be allocated
        by the router."
    ::= { dlsEventsGroup 314 }

dls314_group OBJECT-TYPE
    SYNTAX Integer32
    MAX-ACCESS accessible-for-notify
    STATUS current
    DESCRIPTION
        "Parameter 'group' in event DLS.314"
    ::= { dlsEventObjects314 1 }

dls314_transmit_buffer_size OBJECT-TYPE
    SYNTAX Integer32
    MAX-ACCESS accessible-for-notify
    STATUS current
    DESCRIPTION
        "Parameter 'transmit_buffer_size' in event DLS.314"
    ::= { dlsEventObjects314 2 }

dlsEventObjects315 OBJECT-IDENTITY
    STATUS current
    DESCRIPTION
        "Event DLS.315
        The user configured a TCP transmit buffer size that the router cannot
        handle. It has automatically been set to a lower value that the
        router can allocate."
    ::= { dlsEventsGroup 315 }

dls315_neighbour_address OBJECT-TYPE
    SYNTAX IpAddress
    MAX-ACCESS accessible-for-notify
    STATUS current
    DESCRIPTION
        "Parameter 'neighbour_address' in event DLS.315"
    ::= { dlsEventObjects315 1 }

dls315_transmit_buffer_size OBJECT-TYPE
    SYNTAX Integer32
    MAX-ACCESS accessible-for-notify
    STATUS current
    DESCRIPTION
        "Parameter 'transmit_buffer_size' in event DLS.315"
    ::= { dlsEventObjects315 2 }

dlsEventObjects316 OBJECT-IDENTITY
    STATUS current
    DESCRIPTION
        "Event DLS.316
        A CANUREACH frame was received from the DLS cloud, but could not
        be processed because a CANUREACH is already outstanding from this
        router for the MAC addresses and SAPs specified in the CANUREACH,
        and the origin MAC address for the existing circuit is greater than
        the origin MAC address specified in the CANUREACH."
    ::= { dlsEventsGroup 316 }

dls316_source_mac_address OBJECT-TYPE
    SYNTAX DisplayString
    MAX-ACCESS accessible-for-notify
    STATUS current
    DESCRIPTION
        "Parameter 'source_mac_address' in event DLS.316"
    ::= { dlsEventObjects316 1 }

dls316_dest_mac_address OBJECT-TYPE
    SYNTAX DisplayString
    MAX-ACCESS accessible-for-notify
    STATUS current
    DESCRIPTION
        "Parameter 'dest_mac_address' in event DLS.316"
    ::= { dlsEventObjects316 2 }

dls316_source_sap OBJECT-TYPE
    SYNTAX Integer32
    MAX-ACCESS accessible-for-notify
    STATUS current
    DESCRIPTION
        "Parameter 'source_sap' in event DLS.316"
    ::= { dlsEventObjects316 3 }

dls316_dest_sap OBJECT-TYPE
    SYNTAX Integer32
    MAX-ACCESS accessible-for-notify
    STATUS current
    DESCRIPTION
        "Parameter 'dest_sap' in event DLS.316"
    ::= { dlsEventObjects316 4 }

dlsEventObjects317 OBJECT-IDENTITY
    STATUS current
    DESCRIPTION
        "Event DLS.317
        An XID_C frame was successfully sent to an LLC end station."
    ::= { dlsEventsGroup 317 }

dls317_xid_data_len OBJECT-TYPE
    SYNTAX Integer32
    MAX-ACCESS accessible-for-notify
    STATUS current
    DESCRIPTION
        "Parameter 'xid_data_len' in event DLS.317"
    ::= { dlsEventObjects317 1 }

dls317_source_mac_address OBJECT-TYPE
    SYNTAX DisplayString
    MAX-ACCESS accessible-for-notify
    STATUS current
    DESCRIPTION
        "Parameter 'source_mac_address' in event DLS.317"
    ::= { dlsEventObjects317 2 }

dls317_dest_mac_address OBJECT-TYPE
    SYNTAX DisplayString
    MAX-ACCESS accessible-for-notify
    STATUS current
    DESCRIPTION
        "Parameter 'dest_mac_address' in event DLS.317"
    ::= { dlsEventObjects317 3 }

dls317_source_sap OBJECT-TYPE
    SYNTAX Integer32
    MAX-ACCESS accessible-for-notify
    STATUS current
    DESCRIPTION
        "Parameter 'source_sap' in event DLS.317"
    ::= { dlsEventObjects317 4 }

dls317_dest_sap OBJECT-TYPE
    SYNTAX Integer32
    MAX-ACCESS accessible-for-notify
    STATUS current
    DESCRIPTION
        "Parameter 'dest_sap' in event DLS.317"
    ::= { dlsEventObjects317 5 }

dlsEventObjects318 OBJECT-IDENTITY
    STATUS current
    DESCRIPTION
        "Event DLS.318
        An XID_R frame was successfully sent to an LLC end station."
    ::= { dlsEventsGroup 318 }

dls318_xid_data_len OBJECT-TYPE
    SYNTAX Integer32
    MAX-ACCESS accessible-for-notify
    STATUS current
    DESCRIPTION
        "Parameter 'xid_data_len' in event DLS.318"
    ::= { dlsEventObjects318 1 }

dls318_source_mac_address OBJECT-TYPE
    SYNTAX DisplayString
    MAX-ACCESS accessible-for-notify
    STATUS current
    DESCRIPTION
        "Parameter 'source_mac_address' in event DLS.318"
    ::= { dlsEventObjects318 2 }

dls318_dest_mac_address OBJECT-TYPE
    SYNTAX DisplayString
    MAX-ACCESS accessible-for-notify
    STATUS current
    DESCRIPTION
        "Parameter 'dest_mac_address' in event DLS.318"
    ::= { dlsEventObjects318 3 }

dls318_source_sap OBJECT-TYPE
    SYNTAX Integer32
    MAX-ACCESS accessible-for-notify
    STATUS current
    DESCRIPTION
        "Parameter 'source_sap' in event DLS.318"
    ::= { dlsEventObjects318 4 }

dls318_dest_sap OBJECT-TYPE
    SYNTAX Integer32
    MAX-ACCESS accessible-for-notify
    STATUS current
    DESCRIPTION
        "Parameter 'dest_sap' in event DLS.318"
    ::= { dlsEventObjects318 5 }

dlsEventObjects319 OBJECT-IDENTITY
    STATUS current
    DESCRIPTION
        "Event DLS.319
        A received XID_C frame was discarded because a previously received
        XID_C is being processed by DLSw.
        This XID_C is considered a duplicate. This will occur frequently
        since the end station retries XID_Cs."
    ::= { dlsEventsGroup 319 }

dls319_xid_data_len OBJECT-TYPE
    SYNTAX Integer32
    MAX-ACCESS accessible-for-notify
    STATUS current
    DESCRIPTION
        "Parameter 'xid_data_len' in event DLS.319"
    ::= { dlsEventObjects319 1 }

dls319_source_mac_address OBJECT-TYPE
    SYNTAX DisplayString
    MAX-ACCESS accessible-for-notify
    STATUS current
    DESCRIPTION
        "Parameter 'source_mac_address' in event DLS.319"
    ::= { dlsEventObjects319 2 }

dls319_dest_mac_address OBJECT-TYPE
    SYNTAX DisplayString
    MAX-ACCESS accessible-for-notify
    STATUS current
    DESCRIPTION
        "Parameter 'dest_mac_address' in event DLS.319"
    ::= { dlsEventObjects319 3 }

dls319_source_sap OBJECT-TYPE
    SYNTAX Integer32
    MAX-ACCESS accessible-for-notify
    STATUS current
    DESCRIPTION
        "Parameter 'source_sap' in event DLS.319"
    ::= { dlsEventObjects319 4 }

dls319_dest_sap OBJECT-TYPE
    SYNTAX Integer32
    MAX-ACCESS accessible-for-notify
    STATUS current
    DESCRIPTION
        "Parameter 'dest_sap' in event DLS.319"
    ::= { dlsEventObjects319 5 }

dlsEventObjects320 OBJECT-IDENTITY
    STATUS current
    DESCRIPTION
        "Event DLS.320
        A received XID_R frame was discarded because there is no
        XID command outstanding. This occurs normally since DLSw
        retries XID_Cs and it is possible for many XID_Rs to come back."
    ::= { dlsEventsGroup 320 }

dls320_xid_data_len OBJECT-TYPE
    SYNTAX Integer32
    MAX-ACCESS accessible-for-notify
    STATUS current
    DESCRIPTION
        "Parameter 'xid_data_len' in event DLS.320"
    ::= { dlsEventObjects320 1 }

dls320_source_mac_address OBJECT-TYPE
    SYNTAX DisplayString
    MAX-ACCESS accessible-for-notify
    STATUS current
    DESCRIPTION
        "Parameter 'source_mac_address' in event DLS.320"
    ::= { dlsEventObjects320 2 }

dls320_dest_mac_address OBJECT-TYPE
    SYNTAX DisplayString
    MAX-ACCESS accessible-for-notify
    STATUS current
    DESCRIPTION
        "Parameter 'dest_mac_address' in event DLS.320"
    ::= { dlsEventObjects320 3 }

dls320_source_sap OBJECT-TYPE
    SYNTAX Integer32
    MAX-ACCESS accessible-for-notify
    STATUS current
    DESCRIPTION
        "Parameter 'source_sap' in event DLS.320"
    ::= { dlsEventObjects320 4 }

dls320_dest_sap OBJECT-TYPE
    SYNTAX Integer32
    MAX-ACCESS accessible-for-notify
    STATUS current
    DESCRIPTION
        "Parameter 'dest_sap' in event DLS.320"
    ::= { dlsEventObjects320 5 }

dlsEventObjects321 OBJECT-IDENTITY
    STATUS current
    DESCRIPTION
        "Event DLS.321
        An unexpected received XIDFRAME frame was discarded. The
        LLC does not normally expect to receive an XID in this state."
    ::= { dlsEventsGroup 321 }

dls321_xid_data_len OBJECT-TYPE
    SYNTAX Integer32
    MAX-ACCESS accessible-for-notify
    STATUS current
    DESCRIPTION
        "Parameter 'xid_data_len' in event DLS.321"
    ::= { dlsEventObjects321 1 }

dls321_source_mac_address OBJECT-TYPE
    SYNTAX DisplayString
    MAX-ACCESS accessible-for-notify
    STATUS current
    DESCRIPTION
        "Parameter 'source_mac_address' in event DLS.321"
    ::= { dlsEventObjects321 2 }

dls321_dest_mac_address OBJECT-TYPE
    SYNTAX DisplayString
    MAX-ACCESS accessible-for-notify
    STATUS current
    DESCRIPTION
        "Parameter 'dest_mac_address' in event DLS.321"
    ::= { dlsEventObjects321 3 }

dls321_source_sap OBJECT-TYPE
    SYNTAX Integer32
    MAX-ACCESS accessible-for-notify
    STATUS current
    DESCRIPTION
        "Parameter 'source_sap' in event DLS.321"
    ::= { dlsEventObjects321 4 }

dls321_dest_sap OBJECT-TYPE
    SYNTAX Integer32
    MAX-ACCESS accessible-for-notify
    STATUS current
    DESCRIPTION
        "Parameter 'dest_sap' in event DLS.321"
    ::= { dlsEventObjects321 5 }

dlsEventObjects322 OBJECT-IDENTITY
    STATUS current
    DESCRIPTION
        "Event DLS.322
        A null XID has been received after the SABME/UA exchange.
        This is not normal in this state and indicates that the end station
        is trying to start a new session. The current DLSw session will
        be terminated."
    ::= { dlsEventsGroup 322 }

dls322_source_mac_address OBJECT-TYPE
    SYNTAX DisplayString
    MAX-ACCESS accessible-for-notify
    STATUS current
    DESCRIPTION
        "Parameter 'source_mac_address' in event DLS.322"
    ::= { dlsEventObjects322 1 }

dls322_dest_mac_address OBJECT-TYPE
    SYNTAX DisplayString
    MAX-ACCESS accessible-for-notify
    STATUS current
    DESCRIPTION
        "Parameter 'dest_mac_address' in event DLS.322"
    ::= { dlsEventObjects322 2 }

dls322_source_sap OBJECT-TYPE
    SYNTAX Integer32
    MAX-ACCESS accessible-for-notify
    STATUS current
    DESCRIPTION
        "Parameter 'source_sap' in event DLS.322"
    ::= { dlsEventObjects322 3 }

dls322_dest_sap OBJECT-TYPE
    SYNTAX Integer32
    MAX-ACCESS accessible-for-notify
    STATUS current
    DESCRIPTION
        "Parameter 'dest_sap' in event DLS.322"
    ::= { dlsEventObjects322 4 }

dlsEventObjects323 OBJECT-IDENTITY
    STATUS current
    DESCRIPTION
        "Event DLS.323
        A received activation XIDFRAME is not allowed in the DLSw
        DLS_CONNECTED or DLS_CONNECT_PENDING state. The frame is discarded."
    ::= { dlsEventsGroup 323 }

dls323_xid_data_len OBJECT-TYPE
    SYNTAX Integer32
    MAX-ACCESS accessible-for-notify
    STATUS current
    DESCRIPTION
        "Parameter 'xid_data_len' in event DLS.323"
    ::= { dlsEventObjects323 1 }

dls323_source_mac_address OBJECT-TYPE
    SYNTAX DisplayString
    MAX-ACCESS accessible-for-notify
    STATUS current
    DESCRIPTION
        "Parameter 'source_mac_address' in event DLS.323"
    ::= { dlsEventObjects323 2 }

dls323_dest_mac_address OBJECT-TYPE
    SYNTAX DisplayString
    MAX-ACCESS accessible-for-notify
    STATUS current
    DESCRIPTION
        "Parameter 'dest_mac_address' in event DLS.323"
    ::= { dlsEventObjects323 3 }

dls323_source_sap OBJECT-TYPE
    SYNTAX Integer32
    MAX-ACCESS accessible-for-notify
    STATUS current
    DESCRIPTION
        "Parameter 'source_sap' in event DLS.323"
    ::= { dlsEventObjects323 4 }

dls323_dest_sap OBJECT-TYPE
    SYNTAX Integer32
    MAX-ACCESS accessible-for-notify
    STATUS current
    DESCRIPTION
        "Parameter 'dest_sap' in event DLS.323"
    ::= { dlsEventObjects323 5 }

dlsEventObjects324 OBJECT-IDENTITY
    STATUS current
    DESCRIPTION
        "Event DLS.324
        A received activation XID is not allowed in the DLSw
        DLS_CONNECTED or DLS_CONNECT_PENDING state. The frame is discarded."
    ::= { dlsEventsGroup 324 }

dls324_xid_data_len OBJECT-TYPE
    SYNTAX Integer32
    MAX-ACCESS accessible-for-notify
    STATUS current
    DESCRIPTION
        "Parameter 'xid_data_len' in event DLS.324"
    ::= { dlsEventObjects324 1 }

dls324_source_mac_address OBJECT-TYPE
    SYNTAX DisplayString
    MAX-ACCESS accessible-for-notify
    STATUS current
    DESCRIPTION
        "Parameter 'source_mac_address' in event DLS.324"
    ::= { dlsEventObjects324 2 }

dls324_dest_mac_address OBJECT-TYPE
    SYNTAX DisplayString
    MAX-ACCESS accessible-for-notify
    STATUS current
    DESCRIPTION
        "Parameter 'dest_mac_address' in event DLS.324"
    ::= { dlsEventObjects324 3 }

dls324_source_sap OBJECT-TYPE
    SYNTAX Integer32
    MAX-ACCESS accessible-for-notify
    STATUS current
    DESCRIPTION
        "Parameter 'source_sap' in event DLS.324"
    ::= { dlsEventObjects324 4 }

dls324_dest_sap OBJECT-TYPE
    SYNTAX Integer32
    MAX-ACCESS accessible-for-notify
    STATUS current
    DESCRIPTION
        "Parameter 'dest_sap' in event DLS.324"
    ::= { dlsEventObjects324 5 }

dlsEventObjects326 OBJECT-IDENTITY
    STATUS current
    DESCRIPTION
        "Event DLS.326
        Due to an error receiving a previous DLSw SSP message, DLSw
        cannot find the message header for the next message. In order
        to recover, the TCP session must be closed. This could
        possibly happen due to an invalid message length in the
        previous SSP message."
    ::= { dlsEventsGroup 326 }

dls326_ip_address OBJECT-TYPE
    SYNTAX IpAddress
    MAX-ACCESS accessible-for-notify
    STATUS current
    DESCRIPTION
        "Parameter 'ip_address' in event DLS.326"
    ::= { dlsEventObjects326 1 }

dlsEventObjects327 OBJECT-IDENTITY
    STATUS current
    DESCRIPTION
        "Event DLS.327
        An expected DL_HALTED SSP message has not been received in
        response to a previously sent HALT_DL message. As a result,
        the connection is now considered to be in the disconnected
        state."
    ::= { dlsEventsGroup 327 }

dls327_source_mac_address OBJECT-TYPE
    SYNTAX DisplayString
    MAX-ACCESS accessible-for-notify
    STATUS current
    DESCRIPTION
        "Parameter 'source_mac_address' in event DLS.327"
    ::= { dlsEventObjects327 1 }

dls327_dest_mac_address OBJECT-TYPE
    SYNTAX DisplayString
    MAX-ACCESS accessible-for-notify
    STATUS current
    DESCRIPTION
        "Parameter 'dest_mac_address' in event DLS.327"
    ::= { dlsEventObjects327 2 }

dls327_source_sap OBJECT-TYPE
    SYNTAX Integer32
    MAX-ACCESS accessible-for-notify
    STATUS current
    DESCRIPTION
        "Parameter 'source_sap' in event DLS.327"
    ::= { dlsEventObjects327 3 }

dls327_dest_sap OBJECT-TYPE
    SYNTAX Integer32
    MAX-ACCESS accessible-for-notify
    STATUS current
    DESCRIPTION
        "Parameter 'dest_sap' in event DLS.327"
    ::= { dlsEventObjects327 4 }

dlsEventObjects328 OBJECT-IDENTITY
    STATUS current
    DESCRIPTION
        "Event DLS.328
        A previously down TCP connection is being re-established, because
        the user has enabled the TCP reconnect option with the 'ENABLE
        TCP-RECONNECT' command in the DLSw configurator. To prevent
        automatic reconnection, disable the option."
    ::= { dlsEventsGroup 328 }

dls328_ip_address OBJECT-TYPE
    SYNTAX IpAddress
    MAX-ACCESS accessible-for-notify
    STATUS current
    DESCRIPTION
        "Parameter 'ip_address' in event DLS.328"
    ::= { dlsEventObjects328 1 }

dlsEventObjects329 OBJECT-IDENTITY
    STATUS current
    DESCRIPTION
        "Event DLS.329
        The user configured a global TCP receive buffer size that
        cannot be handled by the router. It has automatically been
        set to a lower value that can be allocated by the router."
    ::= { dlsEventsGroup 329 }

dls329_receive_buffer_size OBJECT-TYPE
    SYNTAX Integer32
    MAX-ACCESS accessible-for-notify
    STATUS current
    DESCRIPTION
        "Parameter 'receive_buffer_size' in event DLS.329"
    ::= { dlsEventObjects329 1 }

dlsEventObjects330 OBJECT-IDENTITY
    STATUS current
    DESCRIPTION
        "Event DLS.330
        The SDLC link station for the link address has been successfully
        re-opened on the network interface because the SDLC link station
        was added again on the SDLC console."
    ::= { dlsEventsGroup 330 }

dls330_link_address OBJECT-TYPE
    SYNTAX Integer32
    MAX-ACCESS accessible-for-notify
    STATUS current
    DESCRIPTION
        "Parameter 'link_address' in event DLS.330"
    ::= { dlsEventObjects330 1 }

dls330_interface OBJECT-TYPE
    SYNTAX DisplayString
    MAX-ACCESS accessible-for-notify
    STATUS current
    DESCRIPTION
        "Parameter 'interface' in event DLS.330"
    ::= { dlsEventObjects330 2 }

dlsEventObjects331 OBJECT-IDENTITY
    STATUS current
    DESCRIPTION
        "Event DLS.331
        There is insufficient memory in the router to create a new TCP
        connection."
    ::= { dlsEventsGroup 331 }

dls331_ip_address OBJECT-TYPE
    SYNTAX IpAddress
    MAX-ACCESS accessible-for-notify
    STATUS current
    DESCRIPTION
        "Parameter 'ip_address' in event DLS.331"
    ::= { dlsEventObjects331 1 }

dlsEventObjects332 OBJECT-IDENTITY
    STATUS current
    DESCRIPTION
        "Event DLS.332
        While processing a DLC event that expects and requires a valid DLS SCB,
        the DLS state machine discovered that the passed pointer to the SCB was
        NULL."
    ::= { dlsEventsGroup 332 }

dls332_event OBJECT-TYPE
    SYNTAX Integer32
    MAX-ACCESS accessible-for-notify
    STATUS current
    DESCRIPTION
        "Parameter 'event' in event DLS.332"
    ::= { dlsEventObjects332 1 }

dls332_dlc_name OBJECT-TYPE
    SYNTAX DisplayString
    MAX-ACCESS accessible-for-notify
    STATUS current
    DESCRIPTION
        "Parameter 'dlc_name' in event DLS.332"
    ::= { dlsEventObjects332 2 }

dls332_ccb_state OBJECT-TYPE
    SYNTAX Integer32
    MAX-ACCESS accessible-for-notify
    STATUS current
    DESCRIPTION
        "Parameter 'ccb_state' in event DLS.332"
    ::= { dlsEventObjects332 3 }

dls332_source_mac_address OBJECT-TYPE
    SYNTAX DisplayString
    MAX-ACCESS accessible-for-notify
    STATUS current
    DESCRIPTION
        "Parameter 'source_mac_address' in event DLS.332"
    ::= { dlsEventObjects332 4 }

dls332_dest_mac_address OBJECT-TYPE
    SYNTAX DisplayString
    MAX-ACCESS accessible-for-notify
    STATUS current
    DESCRIPTION
        "Parameter 'dest_mac_address' in event DLS.332"
    ::= { dlsEventObjects332 5 }

dls332_source_sap OBJECT-TYPE
    SYNTAX Integer32
    MAX-ACCESS accessible-for-notify
    STATUS current
    DESCRIPTION
        "Parameter 'source_sap' in event DLS.332"
    ::= { dlsEventObjects332 6 }

dls332_dest_sap OBJECT-TYPE
    SYNTAX Integer32
    MAX-ACCESS accessible-for-notify
    STATUS current
    DESCRIPTION
        "Parameter 'dest_sap' in event DLS.332"
    ::= { dlsEventObjects332 7 }

dlsEventObjects333 OBJECT-IDENTITY
    STATUS current
    DESCRIPTION
        "Event DLS.333
        While processing a DLC event that expects and requires a valid DLS SCB
        and a DLC CCB, the DLS state machine discovered that the passed pointers
        to both were NULL."
    ::= { dlsEventsGroup 333 }

dls333_event OBJECT-TYPE
    SYNTAX Integer32
    MAX-ACCESS accessible-for-notify
    STATUS current
    DESCRIPTION
        "Parameter 'event' in event DLS.333"
    ::= { dlsEventObjects333 1 }

dlsEventObjects334 OBJECT-IDENTITY
    STATUS current
    DESCRIPTION
        "Event DLS.334
        While processing a DLC event that expects and requires a valid DLS SCB
        and a DLC CCB, the DLS state machine discovered that the passed pointer
        to the SCB was NULL and the DLC CCB identifier was invalid."
    ::= { dlsEventsGroup 334 }

dls334_event OBJECT-TYPE
    SYNTAX Integer32
    MAX-ACCESS accessible-for-notify
    STATUS current
    DESCRIPTION
        "Parameter 'event' in event DLS.334"
    ::= { dlsEventObjects334 1 }

dlsEventObjects335 OBJECT-IDENTITY
    STATUS current
    DESCRIPTION
        "Event DLS.335
        While processing an SSP event that expects and requires a valid DLS SCB,
        the DLS state machine discovered that the passed pointer to the SCB was
        NULL."
    ::= { dlsEventsGroup 335 }

dls335_transport_state OBJECT-TYPE
    SYNTAX Integer32
    MAX-ACCESS accessible-for-notify
    STATUS current
    DESCRIPTION
        "Parameter 'transport_state' in event DLS.335"
    ::= { dlsEventObjects335 1 }

dls335_remote_ip_addr OBJECT-TYPE
    SYNTAX IpAddress
    MAX-ACCESS accessible-for-notify
    STATUS current
    DESCRIPTION
        "Parameter 'remote_ip_addr' in event DLS.335"
    ::= { dlsEventObjects335 2 }

dlsEventObjects336 OBJECT-IDENTITY
    STATUS current
    DESCRIPTION
        "Event DLS.336
        The TCP connection used for this session was closed. This and
        all other unsent data frames will be discarded."
    ::= { dlsEventsGroup 336 }

dls336_source_mac_address OBJECT-TYPE
    SYNTAX DisplayString
    MAX-ACCESS accessible-for-notify
    STATUS current
    DESCRIPTION
        "Parameter 'source_mac_address' in event DLS.336"
    ::= { dlsEventObjects336 1 }

dls336_dest_mac_address OBJECT-TYPE
    SYNTAX DisplayString
    MAX-ACCESS accessible-for-notify
    STATUS current
    DESCRIPTION
        "Parameter 'dest_mac_address' in event DLS.336"
    ::= { dlsEventObjects336 2 }

dls336_source_sap OBJECT-TYPE
    SYNTAX Integer32
    MAX-ACCESS accessible-for-notify
    STATUS current
    DESCRIPTION
        "Parameter 'source_sap' in event DLS.336"
    ::= { dlsEventObjects336 3 }

dls336_dest_sap OBJECT-TYPE
    SYNTAX Integer32
    MAX-ACCESS accessible-for-notify
    STATUS current
    DESCRIPTION
        "Parameter 'dest_sap' in event DLS.336"
    ::= { dlsEventObjects336 4 }

dlsEventObjects338 OBJECT-IDENTITY
    STATUS current
    DESCRIPTION
        "Event DLS.338
        The router could not send a response control message due to a lack of a
        buffer to send it in. Terminate the DLSw session by sending
        a HALT_DL_NOACK."
    ::= { dlsEventsGroup 338 }

dls338_source_mac_address OBJECT-TYPE
    SYNTAX DisplayString
    MAX-ACCESS accessible-for-notify
    STATUS current
    DESCRIPTION
        "Parameter 'source_mac_address' in event DLS.338"
    ::= { dlsEventObjects338 1 }

dls338_dest_mac_address OBJECT-TYPE
    SYNTAX DisplayString
    MAX-ACCESS accessible-for-notify
    STATUS current
    DESCRIPTION
        "Parameter 'dest_mac_address' in event DLS.338"
    ::= { dlsEventObjects338 2 }

dls338_source_sap OBJECT-TYPE
    SYNTAX Integer32
    MAX-ACCESS accessible-for-notify
    STATUS current
    DESCRIPTION
        "Parameter 'source_sap' in event DLS.338"
    ::= { dlsEventObjects338 3 }

dls338_dest_sap OBJECT-TYPE
    SYNTAX Integer32
    MAX-ACCESS accessible-for-notify
    STATUS current
    DESCRIPTION
        "Parameter 'dest_sap' in event DLS.338"
    ::= { dlsEventObjects338 4 }

dlsEventObjects339 OBJECT-IDENTITY
    STATUS current
    DESCRIPTION
        "Event DLS.339
        DLS successfully sent out a HALT_DL_NOACK SSP message over TCP to its
        DLS peer as a result of an out of buffer condition when attempting to
        send a control message."
    ::= { dlsEventsGroup 339 }

dls339_ip_address OBJECT-TYPE
    SYNTAX IpAddress
    MAX-ACCESS accessible-for-notify
    STATUS current
    DESCRIPTION
        "Parameter 'ip_address' in event DLS.339"
    ::= { dlsEventObjects339 1 }

dls339_source_mac_address OBJECT-TYPE
    SYNTAX DisplayString
    MAX-ACCESS accessible-for-notify
    STATUS current
    DESCRIPTION
        "Parameter 'source_mac_address' in event DLS.339"
    ::= { dlsEventObjects339 2 }

dls339_dest_mac_address OBJECT-TYPE
    SYNTAX DisplayString
    MAX-ACCESS accessible-for-notify
    STATUS current
    DESCRIPTION
        "Parameter 'dest_mac_address' in event DLS.339"
    ::= { dlsEventObjects339 3 }

dls339_source_sap OBJECT-TYPE
    SYNTAX Integer32
    MAX-ACCESS accessible-for-notify
    STATUS current
    DESCRIPTION
        "Parameter 'source_sap' in event DLS.339"
    ::= { dlsEventObjects339 4 }

dls339_dest_sap OBJECT-TYPE
    SYNTAX Integer32
    MAX-ACCESS accessible-for-notify
    STATUS current
    DESCRIPTION
        "Parameter 'dest_sap' in event DLS.339"
    ::= { dlsEventObjects339 5 }

dlsEventObjects340 OBJECT-IDENTITY
    STATUS current
    DESCRIPTION
        "Event DLS.340
        The DLSw TCP Interface module determined that the TCP Transport is
        capable of conducting a Capabilities Exchange. The DLSw TCP interface
        module has sent the Capabilities Exchange Request to the DLSw neighbor."
    ::= { dlsEventsGroup 340 }

dls340_ip_address OBJECT-TYPE
    SYNTAX IpAddress
    MAX-ACCESS accessible-for-notify
    STATUS current
    DESCRIPTION
        "Parameter 'ip_address' in event DLS.340"
    ::= { dlsEventObjects340 1 }

dlsEventObjects341 OBJECT-IDENTITY
    STATUS current
    DESCRIPTION
        "Event DLS.341
        The DLSw TCP Interface module received a Capabilities Exchange
        message from a DLSw neighbor. The parsing module determined that the
        message type is a request."
    ::= { dlsEventsGroup 341 }

dls341_ip_address OBJECT-TYPE
    SYNTAX IpAddress
    MAX-ACCESS accessible-for-notify
    STATUS current
    DESCRIPTION
        "Parameter 'ip_address' in event DLS.341"
    ::= { dlsEventObjects341 1 }

dlsEventObjects342 OBJECT-IDENTITY
    STATUS current
    DESCRIPTION
        "Event DLS.342
        The DLSw Capabilities Exchange parsing module successfully processed
        a Capabilities Exchange Request from a DLSw neighbor."
    ::= { dlsEventsGroup 342 }

dls342_ip_address OBJECT-TYPE
    SYNTAX IpAddress
    MAX-ACCESS accessible-for-notify
    STATUS current
    DESCRIPTION
        "Parameter 'ip_address' in event DLS.342"
    ::= { dlsEventObjects342 1 }

dlsEventObjects343 OBJECT-IDENTITY
    STATUS current
    DESCRIPTION
        "Event DLS.343
        The DLSw TCP Interface module received a Capabilities Exchange
        message from a DLSw neighbor. The parsing module determined that
        the message type is a Positive Response."
    ::= { dlsEventsGroup 343 }

dls343_ip_address OBJECT-TYPE
    SYNTAX IpAddress
    MAX-ACCESS accessible-for-notify
    STATUS current
    DESCRIPTION
        "Parameter 'ip_address' in event DLS.343"
    ::= { dlsEventObjects343 1 }

dlsEventObjects344 OBJECT-IDENTITY
    STATUS current
    DESCRIPTION
        "Event DLS.344
        The DLSw Capabilities Exchange parsing module processed a
        Capabilities Exchange Request from a DLSw neighbor. The Request was
        determined to contain an error or invalid Control Vector."
    ::= { dlsEventsGroup 344 }

dls344_ip_address OBJECT-TYPE
    SYNTAX IpAddress
    MAX-ACCESS accessible-for-notify
    STATUS current
    DESCRIPTION
        "Parameter 'ip_address' in event DLS.344"
    ::= { dlsEventObjects344 1 }

dls344_reason_code OBJECT-TYPE
    SYNTAX Integer32
    MAX-ACCESS accessible-for-notify
    STATUS current
    DESCRIPTION
        "Parameter 'reason_code' in event DLS.344"
    ::= { dlsEventObjects344 2 }

dls344_offset_value OBJECT-TYPE
    SYNTAX Integer32
    MAX-ACCESS accessible-for-notify
    STATUS current
    DESCRIPTION
        "Parameter 'offset_value' in event DLS.344"
    ::= { dlsEventObjects344 3 }

dlsEventObjects345 OBJECT-IDENTITY
    STATUS current
    DESCRIPTION
        "Event DLS.345
        The DLSw TCP Interface module received a Capabilities Exchange message
        from a DLSw neighbor. The parsing module determined that the message
        type is a Negative Response."
    ::= { dlsEventsGroup 345 }

dls345_ip_address OBJECT-TYPE
    SYNTAX IpAddress
    MAX-ACCESS accessible-for-notify
    STATUS current
    DESCRIPTION
        "Parameter 'ip_address' in event DLS.345"
    ::= { dlsEventObjects345 1 }

dls345_reason_code OBJECT-TYPE
    SYNTAX Integer32
    MAX-ACCESS accessible-for-notify
    STATUS current
    DESCRIPTION
        "Parameter 'reason_code' in event DLS.345"
    ::= { dlsEventObjects345 2 }

dls345_offset_value OBJECT-TYPE
    SYNTAX Integer32
    MAX-ACCESS accessible-for-notify
    STATUS current
    DESCRIPTION
        "Parameter 'offset_value' in event DLS.345"
    ::= { dlsEventObjects345 3 }

dlsEventObjects346 OBJECT-IDENTITY
    STATUS current
    DESCRIPTION
        "Event DLS.346
        The DLSw Capabilities Exchange manager determined that the neighbor
        is not capable of supporting DLSw AIW_V1. Assume that the
        neighbor is capable of supporting DLSw RFC 1434+."
    ::= { dlsEventsGroup 346 }

dls346_ip_address OBJECT-TYPE
    SYNTAX IpAddress
    MAX-ACCESS accessible-for-notify
    STATUS current
    DESCRIPTION
        "Parameter 'ip_address' in event DLS.346"
    ::= { dlsEventObjects346 1 }

dlsEventObjects347 OBJECT-IDENTITY
    STATUS current
    DESCRIPTION
        "Event DLS.347
        The DLSw neighbor sent an Unknown Capabilities Exchange message.
        Capabilities Exchange may fail if this was meant to be a Request
        or Response."
    ::= { dlsEventsGroup 347 }

dls347_ip_address OBJECT-TYPE
    SYNTAX IpAddress
    MAX-ACCESS accessible-for-notify
    STATUS current
    DESCRIPTION
        "Parameter 'ip_address' in event DLS.347"
    ::= { dlsEventObjects347 1 }

dlsEventObjects348 OBJECT-IDENTITY
    STATUS current
    DESCRIPTION
        "Event DLS.348
        There is no memory available to allocate the resources that the router
        needs to build a Capabilities Exchange message. Capabilities Exchange
        will fail with this neighbor."
    ::= { dlsEventsGroup 348 }

dls348_ip_address OBJECT-TYPE
    SYNTAX IpAddress
    MAX-ACCESS accessible-for-notify
    STATUS current
    DESCRIPTION
        "Parameter 'ip_address' in event DLS.348"
    ::= { dlsEventObjects348 1 }

dlsEventObjects349 OBJECT-IDENTITY
    STATUS current
    DESCRIPTION
        "Event DLS.349
        The DLSw Capabilities Exchange manager determined that the neighbor
        is not capable of supporting DLSw AIW_V1. The TCP Transport connection
        will be terminated with the neighbor."
    ::= { dlsEventsGroup 349 }

dls349_ip_address OBJECT-TYPE
    SYNTAX IpAddress
    MAX-ACCESS accessible-for-notify
    STATUS current
    DESCRIPTION
        "Parameter 'ip_address' in event DLS.349"
    ::= { dlsEventObjects349 1 }

dlsEventObjects350 OBJECT-IDENTITY
    STATUS current
    DESCRIPTION
        "Event DLS.350
        The DLSw Capabilities Exchange manager determined that the neighbor
        is capable of supporting DLSw AIW_V1."
    ::= { dlsEventsGroup 350 }

dls350_ip_address OBJECT-TYPE
    SYNTAX IpAddress
    MAX-ACCESS accessible-for-notify
    STATUS current
    DESCRIPTION
        "Parameter 'ip_address' in event DLS.350"
    ::= { dlsEventObjects350 1 }

dlsEventObjects351 OBJECT-IDENTITY
    STATUS current
    DESCRIPTION
        "Event DLS.351
        DLS forwarder received a Switch to Switch Protocol (SSP) message of
        an Isolated Flow Control Message (IFCM)."
    ::= { dlsEventsGroup 351 }

dls351_indmsg OBJECT-TYPE
    SYNTAX DisplayString
    MAX-ACCESS accessible-for-notify
    STATUS current
    DESCRIPTION
        "Parameter 'indmsg' in event DLS.351"
    ::= { dlsEventObjects351 1 }

dls351_ackmsg OBJECT-TYPE
    SYNTAX DisplayString
    MAX-ACCESS accessible-for-notify
    STATUS current
    DESCRIPTION
        "Parameter 'ackmsg' in event DLS.351"
    ::= { dlsEventObjects351 2 }

dls351_ip_address OBJECT-TYPE
    SYNTAX IpAddress
    MAX-ACCESS accessible-for-notify
    STATUS current
    DESCRIPTION
        "Parameter 'ip_address' in event DLS.351"
    ::= { dlsEventObjects351 3 }

dls351_source_mac_address OBJECT-TYPE
    SYNTAX DisplayString
    MAX-ACCESS accessible-for-notify
    STATUS current
    DESCRIPTION
        "Parameter 'source_mac_address' in event DLS.351"
    ::= { dlsEventObjects351 4 }

dls351_dest_mac_address OBJECT-TYPE
    SYNTAX DisplayString
    MAX-ACCESS accessible-for-notify
    STATUS current
    DESCRIPTION
        "Parameter 'dest_mac_address' in event DLS.351"
    ::= { dlsEventObjects351 5 }

dls351_source_sap OBJECT-TYPE
    SYNTAX Integer32
    MAX-ACCESS accessible-for-notify
    STATUS current
    DESCRIPTION
        "Parameter 'source_sap' in event DLS.351"
    ::= { dlsEventObjects351 6 }

dls351_dest_sap OBJECT-TYPE
    SYNTAX Integer32
    MAX-ACCESS accessible-for-notify
    STATUS current
    DESCRIPTION
        "Parameter 'dest_sap' in event DLS.351"
    ::= { dlsEventObjects351 7 }

dlsEventObjects352 OBJECT-IDENTITY
    STATUS current
    DESCRIPTION
        "Event DLS.352
        The DLS state machine discovered that the passed pointer to the SCB
        was NULL while processing an SSP event containing flow control data
        that expects and requires a valid DLS SCB."
    ::= { dlsEventsGroup 352 }

dls352_transport_state OBJECT-TYPE
    SYNTAX Integer32
    MAX-ACCESS accessible-for-notify
    STATUS current
    DESCRIPTION
        "Parameter 'transport_state' in event DLS.352"
    ::= { dlsEventObjects352 1 }

dls352_remote_ip_addr OBJECT-TYPE
    SYNTAX IpAddress
    MAX-ACCESS accessible-for-notify
    STATUS current
    DESCRIPTION
        "Parameter 'remote_ip_addr' in event DLS.352"
    ::= { dlsEventObjects352 2 }

dlsEventObjects353 OBJECT-IDENTITY
    STATUS current
    DESCRIPTION
        "Event DLS.353
        The sender granted Service Access Point (SAP) units for this circuit
        and the SAP was decremented to a value less than zero. This is a
        protocol violation and the router took the circuit down."
    ::= { dlsEventsGroup 353 }

dls353_source_mac_address OBJECT-TYPE
    SYNTAX DisplayString
    MAX-ACCESS accessible-for-notify
    STATUS current
    DESCRIPTION
        "Parameter 'source_mac_address' in event DLS.353"
    ::= { dlsEventObjects353 1 }

dls353_dest_mac_address OBJECT-TYPE
    SYNTAX DisplayString
    MAX-ACCESS accessible-for-notify
    STATUS current
    DESCRIPTION
        "Parameter 'dest_mac_address' in event DLS.353"
    ::= { dlsEventObjects353 2 }

dls353_source_sap OBJECT-TYPE
    SYNTAX Integer32
    MAX-ACCESS accessible-for-notify
    STATUS current
    DESCRIPTION
        "Parameter 'source_sap' in event DLS.353"
    ::= { dlsEventObjects353 3 }

dls353_dest_sap OBJECT-TYPE
    SYNTAX Integer32
    MAX-ACCESS accessible-for-notify
    STATUS current
    DESCRIPTION
        "Parameter 'dest_sap' in event DLS.353"
    ::= { dlsEventObjects353 4 }

dlsEventObjects354 OBJECT-IDENTITY
    STATUS current
    DESCRIPTION
        "Event DLS.354
        DLSw received an increment window operator while the window size is
        equal to the maximum size."
    ::= { dlsEventsGroup 354 }

dls354_source_mac_address OBJECT-TYPE
    SYNTAX DisplayString
    MAX-ACCESS accessible-for-notify
    STATUS current
    DESCRIPTION
        "Parameter 'source_mac_address' in event DLS.354"
    ::= { dlsEventObjects354 1 }

dls354_dest_mac_address OBJECT-TYPE
    SYNTAX DisplayString
    MAX-ACCESS accessible-for-notify
    STATUS current
    DESCRIPTION
        "Parameter 'dest_mac_address' in event DLS.354"
    ::= { dlsEventObjects354 2 }

dls354_source_sap OBJECT-TYPE
    SYNTAX Integer32
    MAX-ACCESS accessible-for-notify
    STATUS current
    DESCRIPTION
        "Parameter 'source_sap' in event DLS.354"
    ::= { dlsEventObjects354 3 }

dls354_dest_sap OBJECT-TYPE
    SYNTAX Integer32
    MAX-ACCESS accessible-for-notify
    STATUS current
    DESCRIPTION
        "Parameter 'dest_sap' in event DLS.354"
    ::= { dlsEventObjects354 4 }

dlsEventObjects355 OBJECT-IDENTITY
    STATUS current
    DESCRIPTION
        "Event DLS.355
        DLSw received a decrement window operator while the window size is
        equal to 1."
    ::= { dlsEventsGroup 355 }

dls355_source_mac_address OBJECT-TYPE
    SYNTAX DisplayString
    MAX-ACCESS accessible-for-notify
    STATUS current
    DESCRIPTION
        "Parameter 'source_mac_address' in event DLS.355"
    ::= { dlsEventObjects355 1 }

dls355_dest_mac_address OBJECT-TYPE
    SYNTAX DisplayString
    MAX-ACCESS accessible-for-notify
    STATUS current
    DESCRIPTION
        "Parameter 'dest_mac_address' in event DLS.355"
    ::= { dlsEventObjects355 2 }

dls355_source_sap OBJECT-TYPE
    SYNTAX Integer32
    MAX-ACCESS accessible-for-notify
    STATUS current
    DESCRIPTION
        "Parameter 'source_sap' in event DLS.355"
    ::= { dlsEventObjects355 3 }

dls355_dest_sap OBJECT-TYPE
    SYNTAX Integer32
    MAX-ACCESS accessible-for-notify
    STATUS current
    DESCRIPTION
        "Parameter 'dest_sap' in event DLS.355"
    ::= { dlsEventObjects355 4 }

dlsEventObjects356 OBJECT-IDENTITY
    STATUS current
    DESCRIPTION
        "Event DLS.356
        Received an unrecognized flow control operator."
    ::= { dlsEventsGroup 356 }

dls356_source_mac_address OBJECT-TYPE
    SYNTAX DisplayString
    MAX-ACCESS accessible-for-notify
    STATUS current
    DESCRIPTION
        "Parameter 'source_mac_address' in event DLS.356"
    ::= { dlsEventObjects356 1 }

dls356_dest_mac_address OBJECT-TYPE
    SYNTAX DisplayString
    MAX-ACCESS accessible-for-notify
    STATUS current
    DESCRIPTION
        "Parameter 'dest_mac_address' in event DLS.356"
    ::= { dlsEventObjects356 2 }

dls356_source_sap OBJECT-TYPE
    SYNTAX Integer32
    MAX-ACCESS accessible-for-notify
    STATUS current
    DESCRIPTION
        "Parameter 'source_sap' in event DLS.356"
    ::= { dlsEventObjects356 3 }

dls356_dest_sap OBJECT-TYPE
    SYNTAX Integer32
    MAX-ACCESS accessible-for-notify
    STATUS current
    DESCRIPTION
        "Parameter 'dest_sap' in event DLS.356"
    ::= { dlsEventObjects356 4 }

dlsEventObjects357 OBJECT-IDENTITY
    STATUS current
    DESCRIPTION
        "Event DLS.357
        The router received an Isolated Flow Control Message (IFCM) or
        piggybacked flow control indication Switch to Switch Protocol (SSP)
        message."
    ::= { dlsEventsGroup 357 }

dls357_operator OBJECT-TYPE
    SYNTAX DisplayString
    MAX-ACCESS accessible-for-notify
    STATUS current
    DESCRIPTION
        "Parameter 'operator' in event DLS.357"
    ::= { dlsEventObjects357 1 }

dls357_source_mac_address OBJECT-TYPE
    SYNTAX DisplayString
    MAX-ACCESS accessible-for-notify
    STATUS current
    DESCRIPTION
        "Parameter 'source_mac_address' in event DLS.357"
    ::= { dlsEventObjects357 2 }

dls357_dest_mac_address OBJECT-TYPE
    SYNTAX DisplayString
    MAX-ACCESS accessible-for-notify
    STATUS current
    DESCRIPTION
        "Parameter 'dest_mac_address' in event DLS.357"
    ::= { dlsEventObjects357 3 }

dls357_source_sap OBJECT-TYPE
    SYNTAX Integer32
    MAX-ACCESS accessible-for-notify
    STATUS current
    DESCRIPTION
        "Parameter 'source_sap' in event DLS.357"
    ::= { dlsEventObjects357 4 }

dls357_dest_sap OBJECT-TYPE
    SYNTAX Integer32
    MAX-ACCESS accessible-for-notify
    STATUS current
    DESCRIPTION
        "Parameter 'dest_sap' in event DLS.357"
    ::= { dlsEventObjects357 5 }

dls357_txgrant OBJECT-TYPE
    SYNTAX Integer32
    MAX-ACCESS accessible-for-notify
    STATUS current
    DESCRIPTION
        "Parameter 'txgrant' in event DLS.357"
    ::= { dlsEventObjects357 6 }

dls357_txwindow OBJECT-TYPE
    SYNTAX Integer32
    MAX-ACCESS accessible-for-notify
    STATUS current
    DESCRIPTION
        "Parameter 'txwindow' in event DLS.357"
    ::= { dlsEventObjects357 7 }

dlsEventObjects358 OBJECT-IDENTITY
    STATUS current
    DESCRIPTION
        "Event DLS.358
        The router received an IFCM or piggybacked flow control acknowledgement
        in an invalid state."
    ::= { dlsEventsGroup 358 }

dls358_source_mac_address OBJECT-TYPE
    SYNTAX DisplayString
    MAX-ACCESS accessible-for-notify
    STATUS current
    DESCRIPTION
        "Parameter 'source_mac_address' in event DLS.358"
    ::= { dlsEventObjects358 1 }

dls358_dest_mac_address OBJECT-TYPE
    SYNTAX DisplayString
    MAX-ACCESS accessible-for-notify
    STATUS current
    DESCRIPTION
        "Parameter 'dest_mac_address' in event DLS.358"
    ::= { dlsEventObjects358 2 }

dls358_source_sap OBJECT-TYPE
    SYNTAX Integer32
    MAX-ACCESS accessible-for-notify
    STATUS current
    DESCRIPTION
        "Parameter 'source_sap' in event DLS.358"
    ::= { dlsEventObjects358 3 }

dls358_dest_sap OBJECT-TYPE
    SYNTAX Integer32
    MAX-ACCESS accessible-for-notify
    STATUS current
    DESCRIPTION
        "Parameter 'dest_sap' in event DLS.358"
    ::= { dlsEventObjects358 4 }

dlsEventObjects359 OBJECT-IDENTITY
    STATUS current
    DESCRIPTION
        "Event DLS.359
        The DLS forwarder sent a Switch to Switch Protocol (SSP) message of
        IFCM."
    ::= { dlsEventsGroup 359 }

dls359_operator OBJECT-TYPE
    SYNTAX DisplayString
    MAX-ACCESS accessible-for-notify
    STATUS current
    DESCRIPTION
        "Parameter 'operator' in event DLS.359"
    ::= { dlsEventObjects359 1 }

dls359_ip_address OBJECT-TYPE
    SYNTAX IpAddress
    MAX-ACCESS accessible-for-notify
    STATUS current
    DESCRIPTION
        "Parameter 'ip_address' in event DLS.359"
    ::= { dlsEventObjects359 2 }

dls359_source_mac_address OBJECT-TYPE
    SYNTAX DisplayString
    MAX-ACCESS accessible-for-notify
    STATUS current
    DESCRIPTION
        "Parameter 'source_mac_address' in event DLS.359"
    ::= { dlsEventObjects359 3 }

dls359_dest_mac_address OBJECT-TYPE
    SYNTAX DisplayString
    MAX-ACCESS accessible-for-notify
    STATUS current
    DESCRIPTION
        "Parameter 'dest_mac_address' in event DLS.359"
    ::= { dlsEventObjects359 4 }

dls359_source_sap OBJECT-TYPE
    SYNTAX Integer32
    MAX-ACCESS accessible-for-notify
    STATUS current
    DESCRIPTION
        "Parameter 'source_sap' in event DLS.359"
    ::= { dlsEventObjects359 5 }

dls359_dest_sap OBJECT-TYPE
    SYNTAX Integer32
    MAX-ACCESS accessible-for-notify
    STATUS current
    DESCRIPTION
        "Parameter 'dest_sap' in event DLS.359"
    ::= { dlsEventObjects359 6 }

dlsEventObjects360 OBJECT-IDENTITY
    STATUS current
    DESCRIPTION
        "Event DLS.360
        The router received an SSP_INFOFRAME or SSP_DGRMFRAME that caused
        the granted units to be exceeded."
    ::= { dlsEventsGroup 360 }

dls360_source_mac_address OBJECT-TYPE
    SYNTAX DisplayString
    MAX-ACCESS accessible-for-notify
    STATUS current
    DESCRIPTION
        "Parameter 'source_mac_address' in event DLS.360"
    ::= { dlsEventObjects360 1 }

dls360_dest_mac_address OBJECT-TYPE
    SYNTAX DisplayString
    MAX-ACCESS accessible-for-notify
    STATUS current
    DESCRIPTION
        "Parameter 'dest_mac_address' in event DLS.360"
    ::= { dlsEventObjects360 2 }

dls360_source_sap OBJECT-TYPE
    SYNTAX Integer32
    MAX-ACCESS accessible-for-notify
    STATUS current
    DESCRIPTION
        "Parameter 'source_sap' in event DLS.360"
    ::= { dlsEventObjects360 3 }

dls360_dest_sap OBJECT-TYPE
    SYNTAX Integer32
    MAX-ACCESS accessible-for-notify
    STATUS current
    DESCRIPTION
        "Parameter 'dest_sap' in event DLS.360"
    ::= { dlsEventObjects360 4 }

dlsEventObjects361 OBJECT-IDENTITY
    STATUS current
    DESCRIPTION
        "Event DLS.361
        The receiver did not get flow control ack before the end of the
        current window."
    ::= { dlsEventsGroup 361 }

dls361_source_mac_address OBJECT-TYPE
    SYNTAX DisplayString
    MAX-ACCESS accessible-for-notify
    STATUS current
    DESCRIPTION
        "Parameter 'source_mac_address' in event DLS.361"
    ::= { dlsEventObjects361 1 }

dls361_dest_mac_address OBJECT-TYPE
    SYNTAX DisplayString
    MAX-ACCESS accessible-for-notify
    STATUS current
    DESCRIPTION
        "Parameter 'dest_mac_address' in event DLS.361"
    ::= { dlsEventObjects361 2 }

dls361_source_sap OBJECT-TYPE
    SYNTAX Integer32
    MAX-ACCESS accessible-for-notify
    STATUS current
    DESCRIPTION
        "Parameter 'source_sap' in event DLS.361"
    ::= { dlsEventObjects361 3 }

dls361_dest_sap OBJECT-TYPE
    SYNTAX Integer32
    MAX-ACCESS accessible-for-notify
    STATUS current
    DESCRIPTION
        "Parameter 'dest_sap' in event DLS.361"
    ::= { dlsEventObjects361 4 }

dlsEventObjects362 OBJECT-IDENTITY
    STATUS current
    DESCRIPTION
        "Event DLS.362
        The receiver attempted to increment the window beyond the maximum
        window size."
    ::= { dlsEventsGroup 362 }

dls362_source_mac_address OBJECT-TYPE
    SYNTAX DisplayString
    MAX-ACCESS accessible-for-notify
    STATUS current
    DESCRIPTION
        "Parameter 'source_mac_address' in event DLS.362"
    ::= { dlsEventObjects362 1 }

dls362_dest_mac_address OBJECT-TYPE
    SYNTAX DisplayString
    MAX-ACCESS accessible-for-notify
    STATUS current
    DESCRIPTION
        "Parameter 'dest_mac_address' in event DLS.362"
    ::= { dlsEventObjects362 2 }

dls362_source_sap OBJECT-TYPE
    SYNTAX Integer32
    MAX-ACCESS accessible-for-notify
    STATUS current
    DESCRIPTION
        "Parameter 'source_sap' in event DLS.362"
    ::= { dlsEventObjects362 3 }

dls362_dest_sap OBJECT-TYPE
    SYNTAX Integer32
    MAX-ACCESS accessible-for-notify
    STATUS current
    DESCRIPTION
        "Parameter 'dest_sap' in event DLS.362"
    ::= { dlsEventObjects362 4 }

dlsEventObjects363 OBJECT-IDENTITY
    STATUS current
    DESCRIPTION
        "Event DLS.363
        The receiver attempted to decrement the window beyond the minimum
        window size."
    ::= { dlsEventsGroup 363 }

dls363_source_mac_address OBJECT-TYPE
    SYNTAX DisplayString
    MAX-ACCESS accessible-for-notify
    STATUS current
    DESCRIPTION
        "Parameter 'source_mac_address' in event DLS.363"
    ::= { dlsEventObjects363 1 }

dls363_dest_mac_address OBJECT-TYPE
    SYNTAX DisplayString
    MAX-ACCESS accessible-for-notify
    STATUS current
    DESCRIPTION
        "Parameter 'dest_mac_address' in event DLS.363"
    ::= { dlsEventObjects363 2 }

dls363_source_sap OBJECT-TYPE
    SYNTAX Integer32
    MAX-ACCESS accessible-for-notify
    STATUS current
    DESCRIPTION
        "Parameter 'source_sap' in event DLS.363"
    ::= { dlsEventObjects363 3 }

dls363_dest_sap OBJECT-TYPE
    SYNTAX Integer32
    MAX-ACCESS accessible-for-notify
    STATUS current
    DESCRIPTION
        "Parameter 'dest_sap' in event DLS.363"
    ::= { dlsEventObjects363 4 }

dlsEventObjects364 OBJECT-IDENTITY
    STATUS current
    DESCRIPTION
        "Event DLS.364
        DLSw found an entry in the MAC cache for the target MAC address of
        this circuit. The router selected the partner with the indicated IP
        address for this circuit."
    ::= { dlsEventsGroup 364 }

dls364_ip_address OBJECT-TYPE
    SYNTAX IpAddress
    MAX-ACCESS accessible-for-notify
    STATUS current
    DESCRIPTION
        "Parameter 'ip_address' in event DLS.364"
    ::= { dlsEventObjects364 1 }

dls364_source_mac_address OBJECT-TYPE
    SYNTAX DisplayString
    MAX-ACCESS accessible-for-notify
    STATUS current
    DESCRIPTION
        "Parameter 'source_mac_address' in event DLS.364"
    ::= { dlsEventObjects364 2 }

dls364_dest_mac_address OBJECT-TYPE
    SYNTAX DisplayString
    MAX-ACCESS accessible-for-notify
    STATUS current
    DESCRIPTION
        "Parameter 'dest_mac_address' in event DLS.364"
    ::= { dlsEventObjects364 3 }

dls364_source_sap OBJECT-TYPE
    SYNTAX Integer32
    MAX-ACCESS accessible-for-notify
    STATUS current
    DESCRIPTION
        "Parameter 'source_sap' in event DLS.364"
    ::= { dlsEventObjects364 4 }

dls364_dest_sap OBJECT-TYPE
    SYNTAX Integer32
    MAX-ACCESS accessible-for-notify
    STATUS current
    DESCRIPTION
        "Parameter 'dest_sap' in event DLS.364"
    ::= { dlsEventObjects364 5 }

dlsEventObjects365 OBJECT-IDENTITY
    STATUS current
    DESCRIPTION
        "Event DLS.365
        DLSw found an entry in the MAC cache for the target MAC address of
        this circuit with an explorer already outstanding. The router
        queued this MAC explorer request and will process it when the
        outstanding explorer completes."
    ::= { dlsEventsGroup 365 }

dls365_source_mac_address OBJECT-TYPE
    SYNTAX DisplayString
    MAX-ACCESS accessible-for-notify
    STATUS current
    DESCRIPTION
        "Parameter 'source_mac_address' in event DLS.365"
    ::= { dlsEventObjects365 1 }

dls365_dest_mac_address OBJECT-TYPE
    SYNTAX DisplayString
    MAX-ACCESS accessible-for-notify
    STATUS current
    DESCRIPTION
        "Parameter 'dest_mac_address' in event DLS.365"
    ::= { dlsEventObjects365 2 }

dls365_source_sap OBJECT-TYPE
    SYNTAX Integer32
    MAX-ACCESS accessible-for-notify
    STATUS current
    DESCRIPTION
        "Parameter 'source_sap' in event DLS.365"
    ::= { dlsEventObjects365 3 }

dls365_dest_sap OBJECT-TYPE
    SYNTAX Integer32
    MAX-ACCESS accessible-for-notify
    STATUS current
    DESCRIPTION
        "Parameter 'dest_sap' in event DLS.365"
    ::= { dlsEventObjects365 4 }

dlsEventObjects366 OBJECT-IDENTITY
    STATUS current
    DESCRIPTION
        "Event DLS.366
        Due to a memory shortage condition, DLSw could not create an explorer
        control block for the specified circuit. The exploration fails
        and the router does not start a circuit."
    ::= { dlsEventsGroup 366 }

dls366_source_mac_address OBJECT-TYPE
    SYNTAX DisplayString
    MAX-ACCESS accessible-for-notify
    STATUS current
    DESCRIPTION
        "Parameter 'source_mac_address' in event DLS.366"
    ::= { dlsEventObjects366 1 }

dls366_dest_mac_address OBJECT-TYPE
    SYNTAX DisplayString
    MAX-ACCESS accessible-for-notify
    STATUS current
    DESCRIPTION
        "Parameter 'dest_mac_address' in event DLS.366"
    ::= { dlsEventObjects366 2 }

dls366_source_sap OBJECT-TYPE
    SYNTAX Integer32
    MAX-ACCESS accessible-for-notify
    STATUS current
    DESCRIPTION
        "Parameter 'source_sap' in event DLS.366"
    ::= { dlsEventObjects366 3 }

dls366_dest_sap OBJECT-TYPE
    SYNTAX Integer32
    MAX-ACCESS accessible-for-notify
    STATUS current
    DESCRIPTION
        "Parameter 'dest_sap' in event DLS.366"
    ::= { dlsEventObjects366 4 }

dlsEventObjects367 OBJECT-IDENTITY
    STATUS current
    DESCRIPTION
        "Event DLS.367
        The router creates a new cache entry for the
        specified target MAC address."
    ::= { dlsEventsGroup 367 }

dls367_target_mac_address OBJECT-TYPE
    SYNTAX DisplayString
    MAX-ACCESS accessible-for-notify
    STATUS current
    DESCRIPTION
        "Parameter 'target_mac_address' in event DLS.367"
    ::= { dlsEventObjects367 1 }

dlsEventObjects368 OBJECT-IDENTITY
    STATUS current
    DESCRIPTION
        "Event DLS.368
        The priority wait timer expired for the specified target MAC
        address. The router is now attempting to satisfy the explorer request
        with the known DLSw partners that can reach this MAC address."
    ::= { dlsEventsGroup 368 }

dls368_target_mac_address OBJECT-TYPE
    SYNTAX DisplayString
    MAX-ACCESS accessible-for-notify
    STATUS current
    DESCRIPTION
        "Parameter 'target_mac_address' in event DLS.368"
    ::= { dlsEventObjects368 1 }

dlsEventObjects369 OBJECT-IDENTITY
    STATUS current
    DESCRIPTION
        "Event DLS.369
        DLS found a partner DLSw router that satisfies the explorer for
        this circuit."
    ::= { dlsEventsGroup 369 }

dls369_source_mac_address OBJECT-TYPE
    SYNTAX DisplayString
    MAX-ACCESS accessible-for-notify
    STATUS current
    DESCRIPTION
        "Parameter 'source_mac_address' in event DLS.369"
    ::= { dlsEventObjects369 1 }

dls369_dest_mac_address OBJECT-TYPE
    SYNTAX DisplayString
    MAX-ACCESS accessible-for-notify
    STATUS current
    DESCRIPTION
        "Parameter 'dest_mac_address' in event DLS.369"
    ::= { dlsEventObjects369 2 }

dls369_source_sap OBJECT-TYPE
    SYNTAX Integer32
    MAX-ACCESS accessible-for-notify
    STATUS current
    DESCRIPTION
        "Parameter 'source_sap' in event DLS.369"
    ::= { dlsEventObjects369 3 }

dls369_dest_sap OBJECT-TYPE
    SYNTAX Integer32
    MAX-ACCESS accessible-for-notify
    STATUS current
    DESCRIPTION
        "Parameter 'dest_sap' in event DLS.369"
    ::= { dlsEventObjects369 4 }

dlsEventObjects370 OBJECT-IDENTITY
    STATUS current
    DESCRIPTION
        "Event DLS.370
        The ICANREACH-ex timer expired for the specified target MAC
        address. The router is now attempting to satisfy the explorer request
        with the known DLSw partners that can reach this MAC address."
    ::= { dlsEventsGroup 370 }

dls370_target_mac_address OBJECT-TYPE
    SYNTAX DisplayString
    MAX-ACCESS accessible-for-notify
    STATUS current
    DESCRIPTION
        "Parameter 'target_mac_address' in event DLS.370"
    ::= { dlsEventObjects370 1 }

dlsEventObjects371 OBJECT-IDENTITY
    STATUS current
    DESCRIPTION
        "Event DLS.371
        DLS failed to find a partner DLSw router that satisfies the MAC
        explorer for this circuit."
    ::= { dlsEventsGroup 371 }

dls371_source_mac_address OBJECT-TYPE
    SYNTAX DisplayString
    MAX-ACCESS accessible-for-notify
    STATUS current
    DESCRIPTION
        "Parameter 'source_mac_address' in event DLS.371"
    ::= { dlsEventObjects371 1 }

dls371_dest_mac_address OBJECT-TYPE
    SYNTAX DisplayString
    MAX-ACCESS accessible-for-notify
    STATUS current
    DESCRIPTION
        "Parameter 'dest_mac_address' in event DLS.371"
    ::= { dlsEventObjects371 2 }

dls371_source_sap OBJECT-TYPE
    SYNTAX Integer32
    MAX-ACCESS accessible-for-notify
    STATUS current
    DESCRIPTION
        "Parameter 'source_sap' in event DLS.371"
    ::= { dlsEventObjects371 3 }

dls371_dest_sap OBJECT-TYPE
    SYNTAX Integer32
    MAX-ACCESS accessible-for-notify
    STATUS current
    DESCRIPTION
        "Parameter 'dest_sap' in event DLS.371"
    ::= { dlsEventObjects371 4 }

dlsEventObjects372 OBJECT-IDENTITY
    STATUS current
    DESCRIPTION
        "Event DLS.372
        The target MAC explorer resolved timer expired without receiving
        a DLC_RESOLVED from any of the DLCs for the specified circuit. The
        target MAC address explorer failed."
    ::= { dlsEventsGroup 372 }

dls372_source_mac_address OBJECT-TYPE
    SYNTAX DisplayString
    MAX-ACCESS accessible-for-notify
    STATUS current
    DESCRIPTION
        "Parameter 'source_mac_address' in event DLS.372"
    ::= { dlsEventObjects372 1 }

dls372_dest_mac_address OBJECT-TYPE
    SYNTAX DisplayString
    MAX-ACCESS accessible-for-notify
    STATUS current
    DESCRIPTION
        "Parameter 'dest_mac_address' in event DLS.372"
    ::= { dlsEventObjects372 2 }

dls372_source_sap OBJECT-TYPE
    SYNTAX Integer32
    MAX-ACCESS accessible-for-notify
    STATUS current
    DESCRIPTION
        "Parameter 'source_sap' in event DLS.372"
    ::= { dlsEventObjects372 3 }

dls372_dest_sap OBJECT-TYPE
    SYNTAX Integer32
    MAX-ACCESS accessible-for-notify
    STATUS current
    DESCRIPTION
        "Parameter 'dest_sap' in event DLS.372"
    ::= { dlsEventObjects372 4 }

dlsEventObjects373 OBJECT-IDENTITY
    STATUS current
    DESCRIPTION
        "Event DLS.373
        The router received an ICANREACH-ex while it was already processing
        a previous ICANREACH-ex. The router ignored this new ICANREACH-ex
        request."
    ::= { dlsEventsGroup 373 }

dls373_source_mac_address OBJECT-TYPE
    SYNTAX DisplayString
    MAX-ACCESS accessible-for-notify
    STATUS current
    DESCRIPTION
        "Parameter 'source_mac_address' in event DLS.373"
    ::= { dlsEventObjects373 1 }

dls373_dest_mac_address OBJECT-TYPE
    SYNTAX DisplayString
    MAX-ACCESS accessible-for-notify
    STATUS current
    DESCRIPTION
        "Parameter 'dest_mac_address' in event DLS.373"
    ::= { dlsEventObjects373 2 }

dls373_source_sap OBJECT-TYPE
    SYNTAX Integer32
    MAX-ACCESS accessible-for-notify
    STATUS current
    DESCRIPTION
        "Parameter 'source_sap' in event DLS.373"
    ::= { dlsEventObjects373 3 }

dls373_dest_sap OBJECT-TYPE
    SYNTAX Integer32
    MAX-ACCESS accessible-for-notify
    STATUS current
    DESCRIPTION
        "Parameter 'dest_sap' in event DLS.373"
    ::= { dlsEventObjects373 4 }

dlsEventObjects374 OBJECT-IDENTITY
    STATUS current
    DESCRIPTION
        "Event DLS.374
        DLS could not create a target explorer control block for the specified
        circuit due to a memory shortage condition. The exploration fails
        and the router does not start a circuit."
    ::= { dlsEventsGroup 374 }

dls374_source_mac_address OBJECT-TYPE
    SYNTAX DisplayString
    MAX-ACCESS accessible-for-notify
    STATUS current
    DESCRIPTION
        "Parameter 'source_mac_address' in event DLS.374"
    ::= { dlsEventObjects374 1 }

dls374_dest_mac_address OBJECT-TYPE
    SYNTAX DisplayString
    MAX-ACCESS accessible-for-notify
    STATUS current
    DESCRIPTION
        "Parameter 'dest_mac_address' in event DLS.374"
    ::= { dlsEventObjects374 2 }

dls374_source_sap OBJECT-TYPE
    SYNTAX Integer32
    MAX-ACCESS accessible-for-notify
    STATUS current
    DESCRIPTION
        "Parameter 'source_sap' in event DLS.374"
    ::= { dlsEventObjects374 3 }

dls374_dest_sap OBJECT-TYPE
    SYNTAX Integer32
    MAX-ACCESS accessible-for-notify
    STATUS current
    DESCRIPTION
        "Parameter 'dest_sap' in event DLS.374"
    ::= { dlsEventObjects374 4 }

dlsEventObjects375 OBJECT-IDENTITY
    STATUS current
    DESCRIPTION
        "Event DLS.375
        A DLC sent DLC_RESOLVED. The router could not process the
        DLC_RESOLVED because the router could not find the corresponding
        control block. This may occur if the resolved timer already expired,
        or a DLC_RESOLVED from a different DLC already satisfied the target
        MAC address explorer."
    ::= { dlsEventsGroup 375 }

dls375_source_mac_address OBJECT-TYPE
    SYNTAX DisplayString
    MAX-ACCESS accessible-for-notify
    STATUS current
    DESCRIPTION
        "Parameter 'source_mac_address' in event DLS.375"
    ::= { dlsEventObjects375 1 }

dls375_dest_mac_address OBJECT-TYPE
    SYNTAX DisplayString
    MAX-ACCESS accessible-for-notify
    STATUS current
    DESCRIPTION
        "Parameter 'dest_mac_address' in event DLS.375"
    ::= { dlsEventObjects375 2 }

dls375_source_sap OBJECT-TYPE
    SYNTAX Integer32
    MAX-ACCESS accessible-for-notify
    STATUS current
    DESCRIPTION
        "Parameter 'source_sap' in event DLS.375"
    ::= { dlsEventObjects375 3 }

dls375_dest_sap OBJECT-TYPE
    SYNTAX Integer32
    MAX-ACCESS accessible-for-notify
    STATUS current
    DESCRIPTION
        "Parameter 'dest_sap' in event DLS.375"
    ::= { dlsEventObjects375 4 }

dlsEventObjects376 OBJECT-IDENTITY
    STATUS current
    DESCRIPTION
        "Event DLS.376
        The router sent an ICANREACH-ex for the specified circuit."
    ::= { dlsEventsGroup 376 }

dls376_source_mac_address OBJECT-TYPE
    SYNTAX DisplayString
    MAX-ACCESS accessible-for-notify
    STATUS current
    DESCRIPTION
        "Parameter 'source_mac_address' in event DLS.376"
    ::= { dlsEventObjects376 1 }

dls376_dest_mac_address OBJECT-TYPE
    SYNTAX DisplayString
    MAX-ACCESS accessible-for-notify
    STATUS current
    DESCRIPTION
        "Parameter 'dest_mac_address' in event DLS.376"
    ::= { dlsEventObjects376 2 }

dls376_source_sap OBJECT-TYPE
    SYNTAX Integer32
    MAX-ACCESS accessible-for-notify
    STATUS current
    DESCRIPTION
        "Parameter 'source_sap' in event DLS.376"
    ::= { dlsEventObjects376 3 }

dls376_dest_sap OBJECT-TYPE
    SYNTAX Integer32
    MAX-ACCESS accessible-for-notify
    STATUS current
    DESCRIPTION
        "Parameter 'dest_sap' in event DLS.376"
    ::= { dlsEventObjects376 4 }

dls376_largest_frame_size OBJECT-TYPE
    SYNTAX Integer32
    MAX-ACCESS accessible-for-notify
    STATUS current
    DESCRIPTION
        "Parameter 'largest_frame_size' in event DLS.376"
    ::= { dlsEventObjects376 5 }

dlsEventObjects377 OBJECT-IDENTITY
    STATUS current
    DESCRIPTION
        "Event DLS.377
        The router deleted the MAC cache entry for the specified address."
    ::= { dlsEventsGroup 377 }

dls377_target_mac_address OBJECT-TYPE
    SYNTAX DisplayString
    MAX-ACCESS accessible-for-notify
    STATUS current
    DESCRIPTION
        "Parameter 'target_mac_address' in event DLS.377"
    ::= { dlsEventObjects377 1 }

dlsEventObjects378 OBJECT-IDENTITY
    STATUS current
    DESCRIPTION
        "Event DLS.378
        LLC interface module for the DLS received a LLCIM_DLC_RESOLVE
        event from DLS."
    ::= { dlsEventsGroup 378 }

dls378_source_mac_address OBJECT-TYPE
    SYNTAX DisplayString
    MAX-ACCESS accessible-for-notify
    STATUS current
    DESCRIPTION
        "Parameter 'source_mac_address' in event DLS.378"
    ::= { dlsEventObjects378 1 }

dls378_dest_mac_address OBJECT-TYPE
    SYNTAX DisplayString
    MAX-ACCESS accessible-for-notify
    STATUS current
    DESCRIPTION
        "Parameter 'dest_mac_address' in event DLS.378"
    ::= { dlsEventObjects378 2 }

dls378_source_sap OBJECT-TYPE
    SYNTAX Integer32
    MAX-ACCESS accessible-for-notify
    STATUS current
    DESCRIPTION
        "Parameter 'source_sap' in event DLS.378"
    ::= { dlsEventObjects378 3 }

dls378_dest_sap OBJECT-TYPE
    SYNTAX Integer32
    MAX-ACCESS accessible-for-notify
    STATUS current
    DESCRIPTION
        "Parameter 'dest_sap' in event DLS.378"
    ::= { dlsEventObjects378 4 }

dlsEventObjects379 OBJECT-IDENTITY
    STATUS current
    DESCRIPTION
        "Event DLS.379
        Passive open of station for LLC data link services failed because
        the SAP to open the station is invalid."
    ::= { dlsEventsGroup 379 }

dls379_Destination OBJECT-TYPE
    SYNTAX DisplayString
    MAX-ACCESS accessible-for-notify
    STATUS current
    DESCRIPTION
        "Parameter 'Destination' in event DLS.379"
    ::= { dlsEventObjects379 1 }

dls379_Source OBJECT-TYPE
    SYNTAX DisplayString
    MAX-ACCESS accessible-for-notify
    STATUS current
    DESCRIPTION
        "Parameter 'Source' in event DLS.379"
    ::= { dlsEventObjects379 2 }

dls379_Dsap OBJECT-TYPE
    SYNTAX Integer32
    MAX-ACCESS accessible-for-notify
    STATUS current
    DESCRIPTION
        "Parameter 'Dsap' in event DLS.379"
    ::= { dlsEventObjects379 3 }

dls379_Ssap OBJECT-TYPE
    SYNTAX Integer32
    MAX-ACCESS accessible-for-notify
    STATUS current
    DESCRIPTION
        "Parameter 'Ssap' in event DLS.379"
    ::= { dlsEventObjects379 4 }

dlsEventObjects380 OBJECT-IDENTITY
    STATUS current
    DESCRIPTION
        "Event DLS.380
        Passive open of station for LLC data link services failed because
        there is no memory available to create a control block to manage
        the connection."
    ::= { dlsEventsGroup 380 }

dls380_Destination OBJECT-TYPE
    SYNTAX DisplayString
    MAX-ACCESS accessible-for-notify
    STATUS current
    DESCRIPTION
        "Parameter 'Destination' in event DLS.380"
    ::= { dlsEventObjects380 1 }

dls380_Source OBJECT-TYPE
    SYNTAX DisplayString
    MAX-ACCESS accessible-for-notify
    STATUS current
    DESCRIPTION
        "Parameter 'Source' in event DLS.380"
    ::= { dlsEventObjects380 2 }

dls380_Dsap OBJECT-TYPE
    SYNTAX Integer32
    MAX-ACCESS accessible-for-notify
    STATUS current
    DESCRIPTION
        "Parameter 'Dsap' in event DLS.380"
    ::= { dlsEventObjects380 3 }

dls380_Ssap OBJECT-TYPE
    SYNTAX Integer32
    MAX-ACCESS accessible-for-notify
    STATUS current
    DESCRIPTION
        "Parameter 'Ssap' in event DLS.380"
    ::= { dlsEventObjects380 4 }

dlsEventObjects381 OBJECT-IDENTITY
    STATUS current
    DESCRIPTION
        "Event DLS.381
        Passive open of station for LLC data link services failed due to
        some problems within LLC. The reason code is indicative of
        the specific problem."
    ::= { dlsEventsGroup 381 }

dls381_Reason OBJECT-TYPE
    SYNTAX Integer32
    MAX-ACCESS accessible-for-notify
    STATUS current
    DESCRIPTION
        "Parameter 'Reason' in event DLS.381"
    ::= { dlsEventObjects381 1 }

dls381_Destination OBJECT-TYPE
    SYNTAX DisplayString
    MAX-ACCESS accessible-for-notify
    STATUS current
    DESCRIPTION
        "Parameter 'Destination' in event DLS.381"
    ::= { dlsEventObjects381 2 }

dls381_Source OBJECT-TYPE
    SYNTAX DisplayString
    MAX-ACCESS accessible-for-notify
    STATUS current
    DESCRIPTION
        "Parameter 'Source' in event DLS.381"
    ::= { dlsEventObjects381 3 }

dls381_Dsap OBJECT-TYPE
    SYNTAX Integer32
    MAX-ACCESS accessible-for-notify
    STATUS current
    DESCRIPTION
        "Parameter 'Dsap' in event DLS.381"
    ::= { dlsEventObjects381 4 }

dls381_Ssap OBJECT-TYPE
    SYNTAX Integer32
    MAX-ACCESS accessible-for-notify
    STATUS current
    DESCRIPTION
        "Parameter 'Ssap' in event DLS.381"
    ::= { dlsEventObjects381 5 }

dlsEventObjects382 OBJECT-IDENTITY
    STATUS current
    DESCRIPTION
        "Event DLS.382
        LLC interface module for the DLS received a LLCIM_DLC_CS_CONFIRM
        event from DLS."
    ::= { dlsEventsGroup 382 }

dls382_source_mac_address OBJECT-TYPE
    SYNTAX DisplayString
    MAX-ACCESS accessible-for-notify
    STATUS current
    DESCRIPTION
        "Parameter 'source_mac_address' in event DLS.382"
    ::= { dlsEventObjects382 1 }

dls382_dest_mac_address OBJECT-TYPE
    SYNTAX DisplayString
    MAX-ACCESS accessible-for-notify
    STATUS current
    DESCRIPTION
        "Parameter 'dest_mac_address' in event DLS.382"
    ::= { dlsEventObjects382 2 }

dls382_source_sap OBJECT-TYPE
    SYNTAX Integer32
    MAX-ACCESS accessible-for-notify
    STATUS current
    DESCRIPTION
        "Parameter 'source_sap' in event DLS.382"
    ::= { dlsEventObjects382 3 }

dls382_dest_sap OBJECT-TYPE
    SYNTAX Integer32
    MAX-ACCESS accessible-for-notify
    STATUS current
    DESCRIPTION
        "Parameter 'dest_sap' in event DLS.382"
    ::= { dlsEventObjects382 4 }

dlsEventObjects383 OBJECT-IDENTITY
    STATUS current
    DESCRIPTION
        "Event DLS.383
        LLC interface module for the DLS received a LLCIM_DLC_HALT_NOACK
        event from DLS during exploration."
    ::= { dlsEventsGroup 383 }

dls383_source_mac_address OBJECT-TYPE
    SYNTAX DisplayString
    MAX-ACCESS accessible-for-notify
    STATUS current
    DESCRIPTION
        "Parameter 'source_mac_address' in event DLS.383"
    ::= { dlsEventObjects383 1 }

dls383_dest_mac_address OBJECT-TYPE
    SYNTAX DisplayString
    MAX-ACCESS accessible-for-notify
    STATUS current
    DESCRIPTION
        "Parameter 'dest_mac_address' in event DLS.383"
    ::= { dlsEventObjects383 2 }

dls383_source_sap OBJECT-TYPE
    SYNTAX Integer32
    MAX-ACCESS accessible-for-notify
    STATUS current
    DESCRIPTION
        "Parameter 'source_sap' in event DLS.383"
    ::= { dlsEventObjects383 3 }

dls383_dest_sap OBJECT-TYPE
    SYNTAX Integer32
    MAX-ACCESS accessible-for-notify
    STATUS current
    DESCRIPTION
        "Parameter 'dest_sap' in event DLS.383"
    ::= { dlsEventObjects383 4 }

dlsEventObjects384 OBJECT-IDENTITY
    STATUS current
    DESCRIPTION
        "Event DLS.384
        LLC interface module for the DLS received a LLCIM_DLC_HALT_NOACK
        event from DLS during target side exploration."
    ::= { dlsEventsGroup 384 }

dls384_source_mac_address OBJECT-TYPE
    SYNTAX DisplayString
    MAX-ACCESS accessible-for-notify
    STATUS current
    DESCRIPTION
        "Parameter 'source_mac_address' in event DLS.384"
    ::= { dlsEventObjects384 1 }

dls384_dest_mac_address OBJECT-TYPE
    SYNTAX DisplayString
    MAX-ACCESS accessible-for-notify
    STATUS current
    DESCRIPTION
        "Parameter 'dest_mac_address' in event DLS.384"
    ::= { dlsEventObjects384 2 }

dls384_source_sap OBJECT-TYPE
    SYNTAX Integer32
    MAX-ACCESS accessible-for-notify
    STATUS current
    DESCRIPTION
        "Parameter 'source_sap' in event DLS.384"
    ::= { dlsEventObjects384 3 }

dls384_dest_sap OBJECT-TYPE
    SYNTAX Integer32
    MAX-ACCESS accessible-for-notify
    STATUS current
    DESCRIPTION
        "Parameter 'dest_sap' in event DLS.384"
    ::= { dlsEventObjects384 4 }

dlsEventObjects385 OBJECT-IDENTITY
    STATUS current
    DESCRIPTION
        "Event DLS.385
        LLC interface module for the DLS received a LLCIM_DLC_HALT_NOACK
        event from DLS."
    ::= { dlsEventsGroup 385 }

dls385_source_mac_address OBJECT-TYPE
    SYNTAX DisplayString
    MAX-ACCESS accessible-for-notify
    STATUS current
    DESCRIPTION
        "Parameter 'source_mac_address' in event DLS.385"
    ::= { dlsEventObjects385 1 }

dls385_dest_mac_address OBJECT-TYPE
    SYNTAX DisplayString
    MAX-ACCESS accessible-for-notify
    STATUS current
    DESCRIPTION
        "Parameter 'dest_mac_address' in event DLS.385"
    ::= { dlsEventObjects385 2 }

dls385_source_sap OBJECT-TYPE
    SYNTAX Integer32
    MAX-ACCESS accessible-for-notify
    STATUS current
    DESCRIPTION
        "Parameter 'source_sap' in event DLS.385"
    ::= { dlsEventObjects385 3 }

dls385_dest_sap OBJECT-TYPE
    SYNTAX Integer32
    MAX-ACCESS accessible-for-notify
    STATUS current
    DESCRIPTION
        "Parameter 'dest_sap' in event DLS.385"
    ::= { dlsEventObjects385 4 }

dlsEventObjects386 OBJECT-IDENTITY
    STATUS current
    DESCRIPTION
        "Event DLS.386
        Due to a memory shortage condition, LLCIM could not create an explorer
        control block for the specified circuit. The exploration fails and
        the router does not start a circuit."
    ::= { dlsEventsGroup 386 }

dls386_source_mac_address OBJECT-TYPE
    SYNTAX DisplayString
    MAX-ACCESS accessible-for-notify
    STATUS current
    DESCRIPTION
        "Parameter 'source_mac_address' in event DLS.386"
    ::= { dlsEventObjects386 1 }

dls386_dest_mac_address OBJECT-TYPE
    SYNTAX DisplayString
    MAX-ACCESS accessible-for-notify
    STATUS current
    DESCRIPTION
        "Parameter 'dest_mac_address' in event DLS.386"
    ::= { dlsEventObjects386 2 }

dls386_source_sap OBJECT-TYPE
    SYNTAX Integer32
    MAX-ACCESS accessible-for-notify
    STATUS current
    DESCRIPTION
        "Parameter 'source_sap' in event DLS.386"
    ::= { dlsEventObjects386 3 }

dls386_dest_sap OBJECT-TYPE
    SYNTAX Integer32
    MAX-ACCESS accessible-for-notify
    STATUS current
    DESCRIPTION
        "Parameter 'dest_sap' in event DLS.386"
    ::= { dlsEventObjects386 4 }

dlsEventObjects387 OBJECT-IDENTITY
    STATUS current
    DESCRIPTION
        "Event DLS.387
        The LLC Interface module for the DLS received a SABME for a station
        that the router had not opened. This causes a passive open for the
        LLC station."
    ::= { dlsEventsGroup 387 }

dls387_source_mac_address OBJECT-TYPE
    SYNTAX DisplayString
    MAX-ACCESS accessible-for-notify
    STATUS current
    DESCRIPTION
        "Parameter 'source_mac_address' in event DLS.387"
    ::= { dlsEventObjects387 1 }

dls387_dest_mac_address OBJECT-TYPE
    SYNTAX DisplayString
    MAX-ACCESS accessible-for-notify
    STATUS current
    DESCRIPTION
        "Parameter 'dest_mac_address' in event DLS.387"
    ::= { dlsEventObjects387 2 }

dls387_source_sap OBJECT-TYPE
    SYNTAX Integer32
    MAX-ACCESS accessible-for-notify
    STATUS current
    DESCRIPTION
        "Parameter 'source_sap' in event DLS.387"
    ::= { dlsEventObjects387 3 }

dls387_dest_sap OBJECT-TYPE
    SYNTAX Integer32
    MAX-ACCESS accessible-for-notify
    STATUS current
    DESCRIPTION
        "Parameter 'dest_sap' in event DLS.387"
    ::= { dlsEventObjects387 4 }

dlsEventObjects388 OBJECT-IDENTITY
    STATUS current
    DESCRIPTION
        "Event DLS.388
        Due to a memory shortage condition, the LLC interface module could not
        allocate an explorer buffer for the specified circuit. The
        exploration fails and the router does not start a circuit."
    ::= { dlsEventsGroup 388 }

dls388_source_mac_address OBJECT-TYPE
    SYNTAX DisplayString
    MAX-ACCESS accessible-for-notify
    STATUS current
    DESCRIPTION
        "Parameter 'source_mac_address' in event DLS.388"
    ::= { dlsEventObjects388 1 }

dls388_dest_mac_address OBJECT-TYPE
    SYNTAX DisplayString
    MAX-ACCESS accessible-for-notify
    STATUS current
    DESCRIPTION
        "Parameter 'dest_mac_address' in event DLS.388"
    ::= { dlsEventObjects388 2 }

dls388_source_sap OBJECT-TYPE
    SYNTAX Integer32
    MAX-ACCESS accessible-for-notify
    STATUS current
    DESCRIPTION
        "Parameter 'source_sap' in event DLS.388"
    ::= { dlsEventObjects388 3 }

dls388_dest_sap OBJECT-TYPE
    SYNTAX Integer32
    MAX-ACCESS accessible-for-notify
    STATUS current
    DESCRIPTION
        "Parameter 'dest_sap' in event DLS.388"
    ::= { dlsEventObjects388 4 }

dlsEventObjects389 OBJECT-IDENTITY
    STATUS current
    DESCRIPTION
        "Event DLS.389
        Due to a memory shortage condition, LLCIM could not create a target
        explorer control block for the specified circuit. The exploration
        fails and the router does not start a circuit."
    ::= { dlsEventsGroup 389 }

dls389_source_mac_address OBJECT-TYPE
    SYNTAX DisplayString
    MAX-ACCESS accessible-for-notify
    STATUS current
    DESCRIPTION
        "Parameter 'source_mac_address' in event DLS.389"
    ::= { dlsEventObjects389 1 }

dls389_dest_mac_address OBJECT-TYPE
    SYNTAX DisplayString
    MAX-ACCESS accessible-for-notify
    STATUS current
    DESCRIPTION
        "Parameter 'dest_mac_address' in event DLS.389"
    ::= { dlsEventObjects389 2 }

dls389_source_sap OBJECT-TYPE
    SYNTAX Integer32
    MAX-ACCESS accessible-for-notify
    STATUS current
    DESCRIPTION
        "Parameter 'source_sap' in event DLS.389"
    ::= { dlsEventObjects389 3 }

dls389_dest_sap OBJECT-TYPE
    SYNTAX Integer32
    MAX-ACCESS accessible-for-notify
    STATUS current
    DESCRIPTION
        "Parameter 'dest_sap' in event DLS.389"
    ::= { dlsEventObjects389 4 }

dlsEventObjects390 OBJECT-IDENTITY
    STATUS current
    DESCRIPTION
        "Event DLS.390
        Passive open of station for LLC data link services succeeded."
    ::= { dlsEventsGroup 390 }

dls390_Destination OBJECT-TYPE
    SYNTAX DisplayString
    MAX-ACCESS accessible-for-notify
    STATUS current
    DESCRIPTION
        "Parameter 'Destination' in event DLS.390"
    ::= { dlsEventObjects390 1 }

dls390_Source OBJECT-TYPE
    SYNTAX DisplayString
    MAX-ACCESS accessible-for-notify
    STATUS current
    DESCRIPTION
        "Parameter 'Source' in event DLS.390"
    ::= { dlsEventObjects390 2 }

dls390_Dsap OBJECT-TYPE
    SYNTAX Integer32
    MAX-ACCESS accessible-for-notify
    STATUS current
    DESCRIPTION
        "Parameter 'Dsap' in event DLS.390"
    ::= { dlsEventObjects390 3 }

dls390_Ssap OBJECT-TYPE
    SYNTAX Integer32
    MAX-ACCESS accessible-for-notify
    STATUS current
    DESCRIPTION
        "Parameter 'Ssap' in event DLS.390"
    ::= { dlsEventObjects390 4 }

dlsEventObjects391 OBJECT-IDENTITY
    STATUS current
    DESCRIPTION
        "Event DLS.391
        LLCIM has changed the transmit window to match the receive window
        requested in an XID-3 received from a PU 2.1 LLC end station."
    ::= { dlsEventsGroup 391 }

dls391_old_tx_window OBJECT-TYPE
    SYNTAX Integer32
    MAX-ACCESS accessible-for-notify
    STATUS current
    DESCRIPTION
        "Parameter 'old_tx_window' in event DLS.391"
    ::= { dlsEventObjects391 1 }

dls391_new_tx_window OBJECT-TYPE
    SYNTAX Integer32
    MAX-ACCESS accessible-for-notify
    STATUS current
    DESCRIPTION
        "Parameter 'new_tx_window' in event DLS.391"
    ::= { dlsEventObjects391 2 }

dls391_source_mac_address OBJECT-TYPE
    SYNTAX DisplayString
    MAX-ACCESS accessible-for-notify
    STATUS current
    DESCRIPTION
        "Parameter 'source_mac_address' in event DLS.391"
    ::= { dlsEventObjects391 3 }

dls391_dest_mac_address OBJECT-TYPE
    SYNTAX DisplayString
    MAX-ACCESS accessible-for-notify
    STATUS current
    DESCRIPTION
        "Parameter 'dest_mac_address' in event DLS.391"
    ::= { dlsEventObjects391 4 }

dls391_source_sap OBJECT-TYPE
    SYNTAX Integer32
    MAX-ACCESS accessible-for-notify
    STATUS current
    DESCRIPTION
        "Parameter 'source_sap' in event DLS.391"
    ::= { dlsEventObjects391 5 }

dls391_dest_sap OBJECT-TYPE
    SYNTAX Integer32
    MAX-ACCESS accessible-for-notify
    STATUS current
    DESCRIPTION
        "Parameter 'dest_sap' in event DLS.391"
    ::= { dlsEventObjects391 6 }

dlsEventObjects392 OBJECT-IDENTITY
    STATUS current
    DESCRIPTION
        "Event DLS.392
        LLCIM could not change the transmit window to match the window
        requested in an XID-3 received from a PU 2.1 LLC end station. The
        dl_open_station function call failed with the specified return_code."
    ::= { dlsEventsGroup 392 }

dls392_old_tx_window OBJECT-TYPE
    SYNTAX Integer32
    MAX-ACCESS accessible-for-notify
    STATUS current
    DESCRIPTION
        "Parameter 'old_tx_window' in event DLS.392"
    ::= { dlsEventObjects392 1 }

dls392_new_tx_window OBJECT-TYPE
    SYNTAX Integer32
    MAX-ACCESS accessible-for-notify
    STATUS current
    DESCRIPTION
        "Parameter 'new_tx_window' in event DLS.392"
    ::= { dlsEventObjects392 2 }

dls392_return_code OBJECT-TYPE
    SYNTAX Integer32
    MAX-ACCESS accessible-for-notify
    STATUS current
    DESCRIPTION
        "Parameter 'return_code' in event DLS.392"
    ::= { dlsEventObjects392 3 }

dls392_source_mac_address OBJECT-TYPE
    SYNTAX DisplayString
    MAX-ACCESS accessible-for-notify
    STATUS current
    DESCRIPTION
        "Parameter 'source_mac_address' in event DLS.392"
    ::= { dlsEventObjects392 4 }

dls392_dest_mac_address OBJECT-TYPE
    SYNTAX DisplayString
    MAX-ACCESS accessible-for-notify
    STATUS current
    DESCRIPTION
        "Parameter 'dest_mac_address' in event DLS.392"
    ::= { dlsEventObjects392 5 }

dls392_source_sap OBJECT-TYPE
    SYNTAX Integer32
    MAX-ACCESS accessible-for-notify
    STATUS current
    DESCRIPTION
        "Parameter 'source_sap' in event DLS.392"
    ::= { dlsEventObjects392 6 }

dls392_dest_sap OBJECT-TYPE
    SYNTAX Integer32
    MAX-ACCESS accessible-for-notify
    STATUS current
    DESCRIPTION
        "Parameter 'dest_sap' in event DLS.392"
    ::= { dlsEventObjects392 7 }

dlsEventObjects393 OBJECT-IDENTITY
    STATUS current
    DESCRIPTION
        "Event DLS.393
        The router sent a runtime Capabilities Exchange Request message
        to the DLSw neighbor. This is the result of a change to the information
        that was initially exchanged."
    ::= { dlsEventsGroup 393 }

dls393_ip_address OBJECT-TYPE
    SYNTAX IpAddress
    MAX-ACCESS accessible-for-notify
    STATUS current
    DESCRIPTION
        "Parameter 'ip_address' in event DLS.393"
    ::= { dlsEventObjects393 1 }

dlsEventObjects394 OBJECT-IDENTITY
    STATUS current
    DESCRIPTION
        "Event DLS.394
        DLSw detected an invalid configuration parameter at start-up time.
        The interface on which DLSw is to open an LLC SAP does not exist on
        the router. You should change the configuration and restart
        the router."
    ::= { dlsEventsGroup 394 }

dls394_interface OBJECT-TYPE
    SYNTAX Integer32
    MAX-ACCESS accessible-for-notify
    STATUS current
    DESCRIPTION
        "Parameter 'interface' in event DLS.394"
    ::= { dlsEventObjects394 1 }

dls394_sap OBJECT-TYPE
    SYNTAX Integer32
    MAX-ACCESS accessible-for-notify
    STATUS current
    DESCRIPTION
        "Parameter 'sap' in event DLS.394"
    ::= { dlsEventObjects394 2 }

dlsEventObjects395 OBJECT-IDENTITY
    STATUS current
    DESCRIPTION
        "Event DLS.395
        DLSw detected an invalid configuration parameter at start-up time.
        The interface specified for a DLSw SDLC link station either does not
        exist or is not of type SDLC. You should change the configuration and
        restart the router."
    ::= { dlsEventsGroup 395 }

dls395_interface OBJECT-TYPE
    SYNTAX Integer32
    MAX-ACCESS accessible-for-notify
    STATUS current
    DESCRIPTION
        "Parameter 'interface' in event DLS.395"
    ::= { dlsEventObjects395 1 }

dls395_link_address OBJECT-TYPE
    SYNTAX Integer32
    MAX-ACCESS accessible-for-notify
    STATUS current
    DESCRIPTION
        "Parameter 'link_address' in event DLS.395"
    ::= { dlsEventObjects395 2 }

dlsEventObjects396 OBJECT-IDENTITY
    STATUS current
    DESCRIPTION
        "Event DLS.396
        DLSw detected an invalid configuration parameter at start-up time.
        The SAP value that DLSw is to open on the specified interface is odd or
        outside the allowable range. Change the configuration and restart
        the router."
    ::= { dlsEventsGroup 396 }

dls396_sap OBJECT-TYPE
    SYNTAX Integer32
    MAX-ACCESS accessible-for-notify
    STATUS current
    DESCRIPTION
        "Parameter 'sap' in event DLS.396"
    ::= { dlsEventObjects396 1 }

dls396_interface OBJECT-TYPE
    SYNTAX Integer32
    MAX-ACCESS accessible-for-notify
    STATUS current
    DESCRIPTION
        "Parameter 'interface' in event DLS.396"
    ::= { dlsEventObjects396 2 }

dlsEventObjects397 OBJECT-IDENTITY
    STATUS current
    DESCRIPTION
        "Event DLS.397
        DLSw detected an invalid configuration parameter at start-up time.
        The source SAP for an SDLC link station is outside the allowable range.
        DLSw has not added this SDLC link station. You should change
        the configuration and restart the router."
    ::= { dlsEventsGroup 397 }

dls397_sap OBJECT-TYPE
    SYNTAX Integer32
    MAX-ACCESS accessible-for-notify
    STATUS current
    DESCRIPTION
        "Parameter 'sap' in event DLS.397"
    ::= { dlsEventObjects397 1 }

dls397_interface OBJECT-TYPE
    SYNTAX Integer32
    MAX-ACCESS accessible-for-notify
    STATUS current
    DESCRIPTION
        "Parameter 'interface' in event DLS.397"
    ::= { dlsEventObjects397 2 }

dls397_link_address OBJECT-TYPE
    SYNTAX Integer32
    MAX-ACCESS accessible-for-notify
    STATUS current
    DESCRIPTION
        "Parameter 'link_address' in event DLS.397"
    ::= { dlsEventObjects397 3 }

dlsEventObjects398 OBJECT-IDENTITY
    STATUS current
    DESCRIPTION
        "Event DLS.398
        DLSw detected an invalid configuration parameter at start-up time.
        The neighbor or group receive buffer size was outside the allowable
        range, but DLSw adjusted it to the nearest range limit and processed
        the configuration record anyway. Fix the configuration
        at some point by comparing with console information to isolate the
        problem and restart the router."
    ::= { dlsEventsGroup 398 }

dls398_buf_size OBJECT-TYPE
    SYNTAX Integer32
    MAX-ACCESS accessible-for-notify
    STATUS current
    DESCRIPTION
        "Parameter 'buf_size' in event DLS.398"
    ::= { dlsEventObjects398 1 }

dlsEventObjects399 OBJECT-IDENTITY
    STATUS current
    DESCRIPTION
        "Event DLS.399
        DLSw detected an invalid configuration parameter at start-up time.
        The neighbor priority value was outside the allowable range, but DLSw
        adjusted it to the nearest range limit and processed the configuration
        record anyway. Fix the configuration by comparing with
        console information to isolate the problem and restart the router."
    ::= { dlsEventsGroup 399 }

dls399_priority_value OBJECT-TYPE
    SYNTAX Integer32
    MAX-ACCESS accessible-for-notify
    STATUS current
    DESCRIPTION
        "Parameter 'priority_value' in event DLS.399"
    ::= { dlsEventObjects399 1 }

dlsEventObjects400 OBJECT-IDENTITY
    STATUS current
    DESCRIPTION
        "Event DLS.400
        DLSw detected an invalid configuration parameter at start-up time.
        The priority wait timer value was outside the allowable range, but
        DLSw adjusted it to the nearest range limit and will use the adjusted
        value. Fix the configuration and restart the router."
    ::= { dlsEventsGroup 400 }

dls400_timer_value OBJECT-TYPE
    SYNTAX Integer32
    MAX-ACCESS accessible-for-notify
    STATUS current
    DESCRIPTION
        "Parameter 'timer_value' in event DLS.400"
    ::= { dlsEventObjects400 1 }

dlsEventObjects401 OBJECT-IDENTITY
    STATUS current
    DESCRIPTION
        "Event DLS.401
        DLSw detected an invalid configuration parameter at start-up time.
        The session priority for either SNA or NetBIOS is out of
        range, but DLSw adjusted it to the nearest range limit and will
        use the adjusted value. Fix the configuration and
        restart the router."
    ::= { dlsEventsGroup 401 }

dls401_priority_value OBJECT-TYPE
    SYNTAX Integer32
    MAX-ACCESS accessible-for-notify
    STATUS current
    DESCRIPTION
        "Parameter 'priority_value' in event DLS.401"
    ::= { dlsEventObjects401 1 }

dls401_protocol OBJECT-TYPE
    SYNTAX DisplayString
    MAX-ACCESS accessible-for-notify
    STATUS current
    DESCRIPTION
        "Parameter 'protocol' in event DLS.401"
    ::= { dlsEventObjects401 2 }

dlsEventObjects402 OBJECT-IDENTITY
    STATUS current
    DESCRIPTION
        "Event DLS.402
        DLSw detected an invalid configuration parameter at start-up time.
        The value for the number of frames to be sent at one of the four
        session priorities is out of range, but DLSw adjusted it to the
        nearest range limit and will use the adjusted value.
        Fix the configuration by comparing with console information
        to isolate the problem and restart the router."
    ::= { dlsEventsGroup 402 }

dls402_frame_alloc_value OBJECT-TYPE
    SYNTAX Integer32
    MAX-ACCESS accessible-for-notify
    STATUS current
    DESCRIPTION
        "Parameter 'frame_alloc_value' in event DLS.402"
    ::= { dlsEventObjects402 1 }

dlsEventObjects403 OBJECT-IDENTITY
    STATUS current
    DESCRIPTION
        "Event DLS.403
        DLSw detected an invalid configuration parameter at start-up time.
        The NetBIOS MTU size is out of range, but DLSw adjusted it to
        the nearest range limit and will use the adjusted value.
        Fix the configuration and restart the router."
    ::= { dlsEventsGroup 403 }

dls403_mtu_size OBJECT-TYPE
    SYNTAX Integer32
    MAX-ACCESS accessible-for-notify
    STATUS current
    DESCRIPTION
        "Parameter 'mtu_size' in event DLS.403"
    ::= { dlsEventObjects403 1 }

dlsEventObjects404 OBJECT-IDENTITY
    STATUS current
    DESCRIPTION
        "Event DLS.404
        DLSw detected an invalid configuration condition at start-up time.
        One of the standard SNA SAPs (04, 08, or 0C) is open on an interface,
        but SAP 00 is not open on the same interface. Without SAP 00 open,
        SNA data link switching will not work. The router cannot establish
        circuits. If you did not intend to temporarily disable an interface
        for DLSw, fix the configuration by opening SAP 00, where
        needed, and restart the router."
    ::= { dlsEventsGroup 404 }

dls404_interface OBJECT-TYPE
    SYNTAX Integer32
    MAX-ACCESS accessible-for-notify
    STATUS current
    DESCRIPTION
        "Parameter 'interface' in event DLS.404"
    ::= { dlsEventObjects404 1 }

dlsEventObjects405 OBJECT-IDENTITY
    STATUS current
    DESCRIPTION
        "Event DLS.405
        DLSw detected an invalid configuration condition at start-up time.
        A DLSw SDLC source MAC address has been duplicated within the router,
        either on the same SDLC interface or on a different one. The router
        permits only one occurrence of a given source MAC address, and DLSw
        uses only the first one encountered. Fix the configuration
        and restart the router."
    ::= { dlsEventsGroup 405 }

dls405_source_mac_address OBJECT-TYPE
    SYNTAX DisplayString
    MAX-ACCESS accessible-for-notify
    STATUS current
    DESCRIPTION
        "Parameter 'source_mac_address' in event DLS.405"
    ::= { dlsEventObjects405 1 }

dlsEventObjects407 OBJECT-IDENTITY
    STATUS current
    DESCRIPTION
        "Event DLS.407
        The receiver attempted to halve the window below the minimum
        window size."
    ::= { dlsEventsGroup 407 }

dls407_source_mac_address OBJECT-TYPE
    SYNTAX DisplayString
    MAX-ACCESS accessible-for-notify
    STATUS current
    DESCRIPTION
        "Parameter 'source_mac_address' in event DLS.407"
    ::= { dlsEventObjects407 1 }

dls407_dest_mac_address OBJECT-TYPE
    SYNTAX DisplayString
    MAX-ACCESS accessible-for-notify
    STATUS current
    DESCRIPTION
        "Parameter 'dest_mac_address' in event DLS.407"
    ::= { dlsEventObjects407 2 }

dls407_source_sap OBJECT-TYPE
    SYNTAX Integer32
    MAX-ACCESS accessible-for-notify
    STATUS current
    DESCRIPTION
        "Parameter 'source_sap' in event DLS.407"
    ::= { dlsEventObjects407 3 }

dls407_dest_sap OBJECT-TYPE
    SYNTAX Integer32
    MAX-ACCESS accessible-for-notify
    STATUS current
    DESCRIPTION
        "Parameter 'dest_sap' in event DLS.407"
    ::= { dlsEventObjects407 4 }

dlsEventObjects408 OBJECT-IDENTITY
    STATUS current
    DESCRIPTION
        "Event DLS.408
        The router received an IFCM ACK or piggybacked flow control
        acknowledgement SSP message."
    ::= { dlsEventsGroup 408 }

dls408_source_mac_address OBJECT-TYPE
    SYNTAX DisplayString
    MAX-ACCESS accessible-for-notify
    STATUS current
    DESCRIPTION
        "Parameter 'source_mac_address' in event DLS.408"
    ::= { dlsEventObjects408 1 }

dls408_dest_mac_address OBJECT-TYPE
    SYNTAX DisplayString
    MAX-ACCESS accessible-for-notify
    STATUS current
    DESCRIPTION
        "Parameter 'dest_mac_address' in event DLS.408"
    ::= { dlsEventObjects408 2 }

dls408_source_sap OBJECT-TYPE
    SYNTAX Integer32
    MAX-ACCESS accessible-for-notify
    STATUS current
    DESCRIPTION
        "Parameter 'source_sap' in event DLS.408"
    ::= { dlsEventObjects408 3 }

dls408_dest_sap OBJECT-TYPE
    SYNTAX Integer32
    MAX-ACCESS accessible-for-notify
    STATUS current
    DESCRIPTION
        "Parameter 'dest_sap' in event DLS.408"
    ::= { dlsEventObjects408 4 }

dls408_rxgrant OBJECT-TYPE
    SYNTAX Integer32
    MAX-ACCESS accessible-for-notify
    STATUS current
    DESCRIPTION
        "Parameter 'rxgrant' in event DLS.408"
    ::= { dlsEventObjects408 5 }

dls408_rxwindow OBJECT-TYPE
    SYNTAX Integer32
    MAX-ACCESS accessible-for-notify
    STATUS current
    DESCRIPTION
        "Parameter 'rxwindow' in event DLS.408"
    ::= { dlsEventObjects408 6 }

dlsEventObjects409 OBJECT-IDENTITY
    STATUS current
    DESCRIPTION
        "Event DLS.409
        DLS successfully sent out a DGRMFRAME SSP message from the PacingQ
        over TCP to its DLS peer."
    ::= { dlsEventsGroup 409 }

dls409_ip_address OBJECT-TYPE
    SYNTAX IpAddress
    MAX-ACCESS accessible-for-notify
    STATUS current
    DESCRIPTION
        "Parameter 'ip_address' in event DLS.409"
    ::= { dlsEventObjects409 1 }

dls409_source_mac_address OBJECT-TYPE
    SYNTAX DisplayString
    MAX-ACCESS accessible-for-notify
    STATUS current
    DESCRIPTION
        "Parameter 'source_mac_address' in event DLS.409"
    ::= { dlsEventObjects409 2 }

dls409_dest_mac_address OBJECT-TYPE
    SYNTAX DisplayString
    MAX-ACCESS accessible-for-notify
    STATUS current
    DESCRIPTION
        "Parameter 'dest_mac_address' in event DLS.409"
    ::= { dlsEventObjects409 3 }

dls409_source_sap OBJECT-TYPE
    SYNTAX Integer32
    MAX-ACCESS accessible-for-notify
    STATUS current
    DESCRIPTION
        "Parameter 'source_sap' in event DLS.409"
    ::= { dlsEventObjects409 4 }

dls409_dest_sap OBJECT-TYPE
    SYNTAX Integer32
    MAX-ACCESS accessible-for-notify
    STATUS current
    DESCRIPTION
        "Parameter 'dest_sap' in event DLS.409"
    ::= { dlsEventObjects409 5 }

dlsEventObjects410 OBJECT-IDENTITY
    STATUS current
    DESCRIPTION
        "Event DLS.410
        DLS successfully sent out an INFOFRAME SSP message from the PacingQ
        over TCP to its DLS peer."
    ::= { dlsEventsGroup 410 }

dls410_ip_address OBJECT-TYPE
    SYNTAX IpAddress
    MAX-ACCESS accessible-for-notify
    STATUS current
    DESCRIPTION
        "Parameter 'ip_address' in event DLS.410"
    ::= { dlsEventObjects410 1 }

dls410_source_mac_address OBJECT-TYPE
    SYNTAX DisplayString
    MAX-ACCESS accessible-for-notify
    STATUS current
    DESCRIPTION
        "Parameter 'source_mac_address' in event DLS.410"
    ::= { dlsEventObjects410 2 }

dls410_dest_mac_address OBJECT-TYPE
    SYNTAX DisplayString
    MAX-ACCESS accessible-for-notify
    STATUS current
    DESCRIPTION
        "Parameter 'dest_mac_address' in event DLS.410"
    ::= { dlsEventObjects410 3 }

dls410_source_sap OBJECT-TYPE
    SYNTAX Integer32
    MAX-ACCESS accessible-for-notify
    STATUS current
    DESCRIPTION
        "Parameter 'source_sap' in event DLS.410"
    ::= { dlsEventObjects410 4 }

dls410_dest_sap OBJECT-TYPE
    SYNTAX Integer32
    MAX-ACCESS accessible-for-notify
    STATUS current
    DESCRIPTION
        "Parameter 'dest_sap' in event DLS.410"
    ::= { dlsEventObjects410 5 }

dlsEventObjects411 OBJECT-IDENTITY
    STATUS current
    DESCRIPTION
        "Event DLS.411
        The router reported the status of a DLSw buffer pool."
    ::= { dlsEventsGroup 411 }

dls411_pool OBJECT-TYPE
    SYNTAX DisplayString
    MAX-ACCESS accessible-for-notify
    STATUS current
    DESCRIPTION
        "Parameter 'pool' in event DLS.411"
    ::= { dlsEventObjects411 1 }

dls411_pstatus OBJECT-TYPE
    SYNTAX DisplayString
    MAX-ACCESS accessible-for-notify
    STATUS current
    DESCRIPTION
        "Parameter 'pstatus' in event DLS.411"
    ::= { dlsEventObjects411 2 }

dlsEventObjects412 OBJECT-IDENTITY
    STATUS current
    DESCRIPTION
        "Event DLS.412
        The router received an invalid window operator after receiving a
        RESET operator."
    ::= { dlsEventsGroup 412 }

dls412_operator OBJECT-TYPE
    SYNTAX DisplayString
    MAX-ACCESS accessible-for-notify
    STATUS current
    DESCRIPTION
        "Parameter 'operator' in event DLS.412"
    ::= { dlsEventObjects412 1 }

dls412_source_mac_address OBJECT-TYPE
    SYNTAX DisplayString
    MAX-ACCESS accessible-for-notify
    STATUS current
    DESCRIPTION
        "Parameter 'source_mac_address' in event DLS.412"
    ::= { dlsEventObjects412 2 }

dls412_dest_mac_address OBJECT-TYPE
    SYNTAX DisplayString
    MAX-ACCESS accessible-for-notify
    STATUS current
    DESCRIPTION
        "Parameter 'dest_mac_address' in event DLS.412"
    ::= { dlsEventObjects412 3 }

dls412_source_sap OBJECT-TYPE
    SYNTAX Integer32
    MAX-ACCESS accessible-for-notify
    STATUS current
    DESCRIPTION
        "Parameter 'source_sap' in event DLS.412"
    ::= { dlsEventObjects412 4 }

dls412_dest_sap OBJECT-TYPE
    SYNTAX Integer32
    MAX-ACCESS accessible-for-notify
    STATUS current
    DESCRIPTION
        "Parameter 'dest_sap' in event DLS.412"
    ::= { dlsEventObjects412 5 }

dlsEventObjects413 OBJECT-IDENTITY
    STATUS current
    DESCRIPTION
        "Event DLS.413
        The router called the pacing operator scheduler to process a scheduled
        pacing action."
    ::= { dlsEventsGroup 413 }

dls413_operator OBJECT-TYPE
    SYNTAX DisplayString
    MAX-ACCESS accessible-for-notify
    STATUS current
    DESCRIPTION
        "Parameter 'operator' in event DLS.413"
    ::= { dlsEventObjects413 1 }

dls413_source_mac_address OBJECT-TYPE
    SYNTAX DisplayString
    MAX-ACCESS accessible-for-notify
    STATUS current
    DESCRIPTION
        "Parameter 'source_mac_address' in event DLS.413"
    ::= { dlsEventObjects413 2 }

dls413_dest_mac_address OBJECT-TYPE
    SYNTAX DisplayString
    MAX-ACCESS accessible-for-notify
    STATUS current
    DESCRIPTION
        "Parameter 'dest_mac_address' in event DLS.413"
    ::= { dlsEventObjects413 3 }

dls413_source_sap OBJECT-TYPE
    SYNTAX Integer32
    MAX-ACCESS accessible-for-notify
    STATUS current
    DESCRIPTION
        "Parameter 'source_sap' in event DLS.413"
    ::= { dlsEventObjects413 4 }

dls413_dest_sap OBJECT-TYPE
    SYNTAX Integer32
    MAX-ACCESS accessible-for-notify
    STATUS current
    DESCRIPTION
        "Parameter 'dest_sap' in event DLS.413"
    ::= { dlsEventObjects413 5 }

dlsEventObjects415 OBJECT-IDENTITY
    STATUS current
    DESCRIPTION
        "Event DLS.415
        DLS forwarder received a Switch to Switch Protocol message of
        NETBIOS_NQ over TCP."
    ::= { dlsEventsGroup 415 }

dls415_ip_address OBJECT-TYPE
    SYNTAX IpAddress
    MAX-ACCESS accessible-for-notify
    STATUS current
    DESCRIPTION
        "Parameter 'ip_address' in event DLS.415"
    ::= { dlsEventObjects415 1 }

dls415_source_mac_address OBJECT-TYPE
    SYNTAX DisplayString
    MAX-ACCESS accessible-for-notify
    STATUS current
    DESCRIPTION
        "Parameter 'source_mac_address' in event DLS.415"
    ::= { dlsEventObjects415 2 }

dls415_dest_mac_address OBJECT-TYPE
    SYNTAX DisplayString
    MAX-ACCESS accessible-for-notify
    STATUS current
    DESCRIPTION
        "Parameter 'dest_mac_address' in event DLS.415"
    ::= { dlsEventObjects415 3 }

dls415_source_sap OBJECT-TYPE
    SYNTAX Integer32
    MAX-ACCESS accessible-for-notify
    STATUS current
    DESCRIPTION
        "Parameter 'source_sap' in event DLS.415"
    ::= { dlsEventObjects415 4 }

dls415_dest_sap OBJECT-TYPE
    SYNTAX Integer32
    MAX-ACCESS accessible-for-notify
    STATUS current
    DESCRIPTION
        "Parameter 'dest_sap' in event DLS.415"
    ::= { dlsEventObjects415 5 }

dlsEventObjects416 OBJECT-IDENTITY
    STATUS current
    DESCRIPTION
        "Event DLS.416
        DLS forwarder received a Switch to Switch Protocol message of
        NETBIOS_NR over TCP."
    ::= { dlsEventsGroup 416 }

dls416_ip_address OBJECT-TYPE
    SYNTAX IpAddress
    MAX-ACCESS accessible-for-notify
    STATUS current
    DESCRIPTION
        "Parameter 'ip_address' in event DLS.416"
    ::= { dlsEventObjects416 1 }

dls416_source_mac_address OBJECT-TYPE
    SYNTAX DisplayString
    MAX-ACCESS accessible-for-notify
    STATUS current
    DESCRIPTION
        "Parameter 'source_mac_address' in event DLS.416"
    ::= { dlsEventObjects416 2 }

dls416_dest_mac_address OBJECT-TYPE
    SYNTAX DisplayString
    MAX-ACCESS accessible-for-notify
    STATUS current
    DESCRIPTION
        "Parameter 'dest_mac_address' in event DLS.416"
    ::= { dlsEventObjects416 3 }

dls416_source_sap OBJECT-TYPE
    SYNTAX Integer32
    MAX-ACCESS accessible-for-notify
    STATUS current
    DESCRIPTION
        "Parameter 'source_sap' in event DLS.416"
    ::= { dlsEventObjects416 4 }

dls416_dest_sap OBJECT-TYPE
    SYNTAX Integer32
    MAX-ACCESS accessible-for-notify
    STATUS current
    DESCRIPTION
        "Parameter 'dest_sap' in event DLS.416"
    ::= { dlsEventObjects416 5 }

dlsEventObjects417 OBJECT-IDENTITY
    STATUS current
    DESCRIPTION
        "Event DLS.417
        DLS forwarder received a Switch to Switch Protocol message of
        NETBIOS_ANQ over TCP."
    ::= { dlsEventsGroup 417 }

dls417_ip_address OBJECT-TYPE
    SYNTAX IpAddress
    MAX-ACCESS accessible-for-notify
    STATUS current
    DESCRIPTION
        "Parameter 'ip_address' in event DLS.417"
    ::= { dlsEventObjects417 1 }

dls417_source_mac_address OBJECT-TYPE
    SYNTAX DisplayString
    MAX-ACCESS accessible-for-notify
    STATUS current
    DESCRIPTION
        "Parameter 'source_mac_address' in event DLS.417"
    ::= { dlsEventObjects417 2 }

dls417_dest_mac_address OBJECT-TYPE
    SYNTAX DisplayString
    MAX-ACCESS accessible-for-notify
    STATUS current
    DESCRIPTION
        "Parameter 'dest_mac_address' in event DLS.417"
    ::= { dlsEventObjects417 3 }

dls417_source_sap OBJECT-TYPE
    SYNTAX Integer32
    MAX-ACCESS accessible-for-notify
    STATUS current
    DESCRIPTION
        "Parameter 'source_sap' in event DLS.417"
    ::= { dlsEventObjects417 4 }

dls417_dest_sap OBJECT-TYPE
    SYNTAX Integer32
    MAX-ACCESS accessible-for-notify
    STATUS current
    DESCRIPTION
        "Parameter 'dest_sap' in event DLS.417"
    ::= { dlsEventObjects417 5 }

dlsEventObjects418 OBJECT-IDENTITY
    STATUS current
    DESCRIPTION
        "Event DLS.418
        DLS forwarder received a Switch to Switch Protocol message of
        NETBIOS_ANR over TCP."
    ::= { dlsEventsGroup 418 }

dls418_ip_address OBJECT-TYPE
    SYNTAX IpAddress
    MAX-ACCESS accessible-for-notify
    STATUS current
    DESCRIPTION
        "Parameter 'ip_address' in event DLS.418"
    ::= { dlsEventObjects418 1 }

dls418_source_mac_address OBJECT-TYPE
    SYNTAX DisplayString
    MAX-ACCESS accessible-for-notify
    STATUS current
    DESCRIPTION
        "Parameter 'source_mac_address' in event DLS.418"
    ::= { dlsEventObjects418 2 }

dls418_dest_mac_address OBJECT-TYPE
    SYNTAX DisplayString
    MAX-ACCESS accessible-for-notify
    STATUS current
    DESCRIPTION
        "Parameter 'dest_mac_address' in event DLS.418"
    ::= { dlsEventObjects418 3 }

dls418_source_sap OBJECT-TYPE
    SYNTAX Integer32
    MAX-ACCESS accessible-for-notify
    STATUS current
    DESCRIPTION
        "Parameter 'source_sap' in event DLS.418"
    ::= { dlsEventObjects418 4 }

dls418_dest_sap OBJECT-TYPE
    SYNTAX Integer32
    MAX-ACCESS accessible-for-notify
    STATUS current
    DESCRIPTION
        "Parameter 'dest_sap' in event DLS.418"
    ::= { dlsEventObjects418 5 }

dlsEventObjects419 OBJECT-IDENTITY
    STATUS current
    DESCRIPTION
        "Event DLS.419
        DLS successfully sent out a NETBIOS_NQ SSP message over TCP to its
        DLS peer."
    ::= { dlsEventsGroup 419 }

dls419_ip_address OBJECT-TYPE
    SYNTAX IpAddress
    MAX-ACCESS accessible-for-notify
    STATUS current
    DESCRIPTION
        "Parameter 'ip_address' in event DLS.419"
    ::= { dlsEventObjects419 1 }

dls419_source_mac_address OBJECT-TYPE
    SYNTAX DisplayString
    MAX-ACCESS accessible-for-notify
    STATUS current
    DESCRIPTION
        "Parameter 'source_mac_address' in event DLS.419"
    ::= { dlsEventObjects419 2 }

dls419_dest_mac_address OBJECT-TYPE
    SYNTAX DisplayString
    MAX-ACCESS accessible-for-notify
    STATUS current
    DESCRIPTION
        "Parameter 'dest_mac_address' in event DLS.419"
    ::= { dlsEventObjects419 3 }

dls419_source_sap OBJECT-TYPE
    SYNTAX Integer32
    MAX-ACCESS accessible-for-notify
    STATUS current
    DESCRIPTION
        "Parameter 'source_sap' in event DLS.419"
    ::= { dlsEventObjects419 4 }

dls419_dest_sap OBJECT-TYPE
    SYNTAX Integer32
    MAX-ACCESS accessible-for-notify
    STATUS current
    DESCRIPTION
        "Parameter 'dest_sap' in event DLS.419"
    ::= { dlsEventObjects419 5 }

dlsEventObjects420 OBJECT-IDENTITY
    STATUS current
    DESCRIPTION
        "Event DLS.420
        DLS successfully sent out a NETBIOS_NR SSP message over TCP to its
        DLS peer."
    ::= { dlsEventsGroup 420 }

dls420_ip_address OBJECT-TYPE
    SYNTAX IpAddress
    MAX-ACCESS accessible-for-notify
    STATUS current
    DESCRIPTION
        "Parameter 'ip_address' in event DLS.420"
    ::= { dlsEventObjects420 1 }

dls420_source_mac_address OBJECT-TYPE
    SYNTAX DisplayString
    MAX-ACCESS accessible-for-notify
    STATUS current
    DESCRIPTION
        "Parameter 'source_mac_address' in event DLS.420"
    ::= { dlsEventObjects420 2 }

dls420_dest_mac_address OBJECT-TYPE
    SYNTAX DisplayString
    MAX-ACCESS accessible-for-notify
    STATUS current
    DESCRIPTION
        "Parameter 'dest_mac_address' in event DLS.420"
    ::= { dlsEventObjects420 3 }

dls420_source_sap OBJECT-TYPE
    SYNTAX Integer32
    MAX-ACCESS accessible-for-notify
    STATUS current
    DESCRIPTION
        "Parameter 'source_sap' in event DLS.420"
    ::= { dlsEventObjects420 4 }

dls420_dest_sap OBJECT-TYPE
    SYNTAX Integer32
    MAX-ACCESS accessible-for-notify
    STATUS current
    DESCRIPTION
        "Parameter 'dest_sap' in event DLS.420"
    ::= { dlsEventObjects420 5 }

dlsEventObjects421 OBJECT-IDENTITY
    STATUS current
    DESCRIPTION
        "Event DLS.421
        DLS successfully sent out a NETBIOS_ANQ SSP message over TCP to its
        DLS peer."
    ::= { dlsEventsGroup 421 }

dls421_ip_address OBJECT-TYPE
    SYNTAX IpAddress
    MAX-ACCESS accessible-for-notify
    STATUS current
    DESCRIPTION
        "Parameter 'ip_address' in event DLS.421"
    ::= { dlsEventObjects421 1 }

dls421_source_mac_address OBJECT-TYPE
    SYNTAX DisplayString
    MAX-ACCESS accessible-for-notify
    STATUS current
    DESCRIPTION
        "Parameter 'source_mac_address' in event DLS.421"
    ::= { dlsEventObjects421 2 }

dls421_dest_mac_address OBJECT-TYPE
    SYNTAX DisplayString
    MAX-ACCESS accessible-for-notify
    STATUS current
    DESCRIPTION
        "Parameter 'dest_mac_address' in event DLS.421"
    ::= { dlsEventObjects421 3 }

dls421_source_sap OBJECT-TYPE
    SYNTAX Integer32
    MAX-ACCESS accessible-for-notify
    STATUS current
    DESCRIPTION
        "Parameter 'source_sap' in event DLS.421"
    ::= { dlsEventObjects421 4 }

dls421_dest_sap OBJECT-TYPE
    SYNTAX Integer32
    MAX-ACCESS accessible-for-notify
    STATUS current
    DESCRIPTION
        "Parameter 'dest_sap' in event DLS.421"
    ::= { dlsEventObjects421 5 }

dlsEventObjects422 OBJECT-IDENTITY
    STATUS current
    DESCRIPTION
        "Event DLS.422
        DLS successfully sent out a NETBIOS_ANR SSP message over TCP to its
        DLS peer."
    ::= { dlsEventsGroup 422 }

dls422_ip_address OBJECT-TYPE
    SYNTAX IpAddress
    MAX-ACCESS accessible-for-notify
    STATUS current
    DESCRIPTION
        "Parameter 'ip_address' in event DLS.422"
    ::= { dlsEventObjects422 1 }

dls422_source_mac_address OBJECT-TYPE
    SYNTAX DisplayString
    MAX-ACCESS accessible-for-notify
    STATUS current
    DESCRIPTION
        "Parameter 'source_mac_address' in event DLS.422"
    ::= { dlsEventObjects422 2 }

dls422_dest_mac_address OBJECT-TYPE
    SYNTAX DisplayString
    MAX-ACCESS accessible-for-notify
    STATUS current
    DESCRIPTION
        "Parameter 'dest_mac_address' in event DLS.422"
    ::= { dlsEventObjects422 3 }

dls422_source_sap OBJECT-TYPE
    SYNTAX Integer32
    MAX-ACCESS accessible-for-notify
    STATUS current
    DESCRIPTION
        "Parameter 'source_sap' in event DLS.422"
    ::= { dlsEventObjects422 4 }

dls422_dest_sap OBJECT-TYPE
    SYNTAX Integer32
    MAX-ACCESS accessible-for-notify
    STATUS current
    DESCRIPTION
        "Parameter 'dest_sap' in event DLS.422"
    ::= { dlsEventObjects422 5 }

dlsEventObjects424 OBJECT-IDENTITY
    STATUS current
    DESCRIPTION
        "Event DLS.424
        The router received an SSP NETBIOS_NQ message earlier with the largest
        frame field. The message indicated that DLSw could not lower the
        largest frame size. The router discarded this corresponding
        Name_Recognized frame because it would have lowered the largest frame
        size."
    ::= { dlsEventsGroup 424 }

dls424_NBName OBJECT-TYPE
    SYNTAX DisplayString
    MAX-ACCESS accessible-for-notify
    STATUS current
    DESCRIPTION
        "Parameter 'NBName' in event DLS.424"
    ::= { dlsEventObjects424 1 }

dlsEventObjects426 OBJECT-IDENTITY
    STATUS current
    DESCRIPTION
        "Event DLS.426
        DLS is learning a new NetBIOS name and IP association from an SSP
        message received from the peer DLS. This typically occurs during
        NETBIOS_NR message receipt time."
    ::= { dlsEventsGroup 426 }

dls426_ip_address OBJECT-TYPE
    SYNTAX IpAddress
    MAX-ACCESS accessible-for-notify
    STATUS current
    DESCRIPTION
        "Parameter 'ip_address' in event DLS.426"
    ::= { dlsEventObjects426 1 }

dls426_NBName OBJECT-TYPE
    SYNTAX DisplayString
    MAX-ACCESS accessible-for-notify
    STATUS current
    DESCRIPTION
        "Parameter 'NBName' in event DLS.426"
    ::= { dlsEventObjects426 2 }

dlsEventObjects427 OBJECT-IDENTITY
    STATUS current
    DESCRIPTION
        "Event DLS.427
        The opening of a NetBIOS station for LLC data link services failed
        due to some problems within LLC."
    ::= { dlsEventsGroup 427 }

dls427_Destination OBJECT-TYPE
    SYNTAX DisplayString
    MAX-ACCESS accessible-for-notify
    STATUS current
    DESCRIPTION
        "Parameter 'Destination' in event DLS.427"
    ::= { dlsEventObjects427 1 }

dls427_Source OBJECT-TYPE
    SYNTAX DisplayString
    MAX-ACCESS accessible-for-notify
    STATUS current
    DESCRIPTION
        "Parameter 'Source' in event DLS.427"
    ::= { dlsEventObjects427 2 }

dls427_Dsap OBJECT-TYPE
    SYNTAX Integer32
    MAX-ACCESS accessible-for-notify
    STATUS current
    DESCRIPTION
        "Parameter 'Dsap' in event DLS.427"
    ::= { dlsEventObjects427 3 }

dls427_Ssap OBJECT-TYPE
    SYNTAX Integer32
    MAX-ACCESS accessible-for-notify
    STATUS current
    DESCRIPTION
        "Parameter 'Ssap' in event DLS.427"
    ::= { dlsEventObjects427 4 }

dlsEventObjects428 OBJECT-IDENTITY
    STATUS current
    DESCRIPTION
        "Event DLS.428
        The LCC interface module is discarding the NetBIOS UI frames it
        received from the LLC. The NetBIOS UI frame buffer pool is congested."
    ::= { dlsEventsGroup 428 }

dls428_source_mac_address OBJECT-TYPE
    SYNTAX DisplayString
    MAX-ACCESS accessible-for-notify
    STATUS current
    DESCRIPTION
        "Parameter 'source_mac_address' in event DLS.428"
    ::= { dlsEventObjects428 1 }

dls428_dest_mac_address OBJECT-TYPE
    SYNTAX DisplayString
    MAX-ACCESS accessible-for-notify
    STATUS current
    DESCRIPTION
        "Parameter 'dest_mac_address' in event DLS.428"
    ::= { dlsEventObjects428 2 }

dls428_source_sap OBJECT-TYPE
    SYNTAX Integer32
    MAX-ACCESS accessible-for-notify
    STATUS current
    DESCRIPTION
        "Parameter 'source_sap' in event DLS.428"
    ::= { dlsEventObjects428 3 }

dls428_dest_sap OBJECT-TYPE
    SYNTAX Integer32
    MAX-ACCESS accessible-for-notify
    STATUS current
    DESCRIPTION
        "Parameter 'dest_sap' in event DLS.428"
    ::= { dlsEventObjects428 4 }

dlsEventObjects431 OBJECT-IDENTITY
    STATUS current
    DESCRIPTION
        "Event DLS.431
        The router could not send CANUREACH-ex to any DLSw partners. Either
        there are no DLSw partners with transport connections in the proper
        state, no DLSw partners that support circuits for the requested SAPs,
        or the router could not allocate buffers for sending the CANUREACH-ex.
        Exploring phases: (0) Broadcast to all DLS partner(s).
        (1) Broadcast to priorized DLS partner(s).
        (2) Broadcast to no priorized DLS partner(s)."
    ::= { dlsEventsGroup 431 }

dls431_source_mac_address OBJECT-TYPE
    SYNTAX DisplayString
    MAX-ACCESS accessible-for-notify
    STATUS current
    DESCRIPTION
        "Parameter 'source_mac_address' in event DLS.431"
    ::= { dlsEventObjects431 1 }

dls431_dest_mac_address OBJECT-TYPE
    SYNTAX DisplayString
    MAX-ACCESS accessible-for-notify
    STATUS current
    DESCRIPTION
        "Parameter 'dest_mac_address' in event DLS.431"
    ::= { dlsEventObjects431 2 }

dls431_source_sap OBJECT-TYPE
    SYNTAX Integer32
    MAX-ACCESS accessible-for-notify
    STATUS current
    DESCRIPTION
        "Parameter 'source_sap' in event DLS.431"
    ::= { dlsEventObjects431 3 }

dls431_dest_sap OBJECT-TYPE
    SYNTAX Integer32
    MAX-ACCESS accessible-for-notify
    STATUS current
    DESCRIPTION
        "Parameter 'dest_sap' in event DLS.431"
    ::= { dlsEventObjects431 4 }

dls431_phase OBJECT-TYPE
    SYNTAX Integer32
    MAX-ACCESS accessible-for-notify
    STATUS current
    DESCRIPTION
        "Parameter 'phase' in event DLS.431"
    ::= { dlsEventObjects431 5 }

dlsEventObjects432 OBJECT-IDENTITY
    STATUS current
    DESCRIPTION
        "Event DLS.432
        The router could not process a DLC_START_DL request because the source
        SAP specified has not been opened on any network interfaces."
    ::= { dlsEventsGroup 432 }

dls432_source_mac_address OBJECT-TYPE
    SYNTAX DisplayString
    MAX-ACCESS accessible-for-notify
    STATUS current
    DESCRIPTION
        "Parameter 'source_mac_address' in event DLS.432"
    ::= { dlsEventObjects432 1 }

dls432_dest_mac_address OBJECT-TYPE
    SYNTAX DisplayString
    MAX-ACCESS accessible-for-notify
    STATUS current
    DESCRIPTION
        "Parameter 'dest_mac_address' in event DLS.432"
    ::= { dlsEventObjects432 2 }

dls432_source_sap OBJECT-TYPE
    SYNTAX Integer32
    MAX-ACCESS accessible-for-notify
    STATUS current
    DESCRIPTION
        "Parameter 'source_sap' in event DLS.432"
    ::= { dlsEventObjects432 3 }

dls432_dest_sap OBJECT-TYPE
    SYNTAX Integer32
    MAX-ACCESS accessible-for-notify
    STATUS current
    DESCRIPTION
        "Parameter 'dest_sap' in event DLS.432"
    ::= { dlsEventObjects432 4 }

dlsEventObjects433 OBJECT-IDENTITY
    STATUS current
    DESCRIPTION
        "Event DLS.433
        DLSw successfully sent out a CANUREACH_ex SSP message over TCP
        to its DLSw peer."
    ::= { dlsEventsGroup 433 }

dls433_ip_address OBJECT-TYPE
    SYNTAX IpAddress
    MAX-ACCESS accessible-for-notify
    STATUS current
    DESCRIPTION
        "Parameter 'ip_address' in event DLS.433"
    ::= { dlsEventObjects433 1 }

dls433_source_mac_address OBJECT-TYPE
    SYNTAX DisplayString
    MAX-ACCESS accessible-for-notify
    STATUS current
    DESCRIPTION
        "Parameter 'source_mac_address' in event DLS.433"
    ::= { dlsEventObjects433 2 }

dls433_dest_mac_address OBJECT-TYPE
    SYNTAX DisplayString
    MAX-ACCESS accessible-for-notify
    STATUS current
    DESCRIPTION
        "Parameter 'dest_mac_address' in event DLS.433"
    ::= { dlsEventObjects433 3 }

dls433_source_sap OBJECT-TYPE
    SYNTAX Integer32
    MAX-ACCESS accessible-for-notify
    STATUS current
    DESCRIPTION
        "Parameter 'source_sap' in event DLS.433"
    ::= { dlsEventObjects433 4 }

dls433_dest_sap OBJECT-TYPE
    SYNTAX Integer32
    MAX-ACCESS accessible-for-notify
    STATUS current
    DESCRIPTION
        "Parameter 'dest_sap' in event DLS.433"
    ::= { dlsEventObjects433 5 }

dls433_largest_frame_size OBJECT-TYPE
    SYNTAX Integer32
    MAX-ACCESS accessible-for-notify
    STATUS current
    DESCRIPTION
        "Parameter 'largest_frame_size' in event DLS.433"
    ::= { dlsEventObjects433 6 }

dlsEventObjects434 OBJECT-IDENTITY
    STATUS current
    DESCRIPTION
        "Event DLS.434
        A remote DLSw neighbor is attempting to connect. A TCP
        connection already exists with this neighbor. The old TCP
        connection will be torn down. This happens when a remote DLSw either
        restarts or a remote communications problem caused the remote
        DLSw to close the connection, but the local DLSw TCP connection
        has not yet detected it."
    ::= { dlsEventsGroup 434 }

dls434_ip_address OBJECT-TYPE
    SYNTAX IpAddress
    MAX-ACCESS accessible-for-notify
    STATUS current
    DESCRIPTION
        "Parameter 'ip_address' in event DLS.434"
    ::= { dlsEventObjects434 1 }

dlsEventObjects436 OBJECT-IDENTITY
    STATUS current
    DESCRIPTION
        "Event DLS.436
        DLSw successfully sent out a CANUREACH_cs SSP message over TCP
        to its DLSw peer."
    ::= { dlsEventsGroup 436 }

dls436_ip_address OBJECT-TYPE
    SYNTAX IpAddress
    MAX-ACCESS accessible-for-notify
    STATUS current
    DESCRIPTION
        "Parameter 'ip_address' in event DLS.436"
    ::= { dlsEventObjects436 1 }

dls436_source_mac_address OBJECT-TYPE
    SYNTAX DisplayString
    MAX-ACCESS accessible-for-notify
    STATUS current
    DESCRIPTION
        "Parameter 'source_mac_address' in event DLS.436"
    ::= { dlsEventObjects436 2 }

dls436_dest_mac_address OBJECT-TYPE
    SYNTAX DisplayString
    MAX-ACCESS accessible-for-notify
    STATUS current
    DESCRIPTION
        "Parameter 'dest_mac_address' in event DLS.436"
    ::= { dlsEventObjects436 3 }

dls436_source_sap OBJECT-TYPE
    SYNTAX Integer32
    MAX-ACCESS accessible-for-notify
    STATUS current
    DESCRIPTION
        "Parameter 'source_sap' in event DLS.436"
    ::= { dlsEventObjects436 4 }

dls436_dest_sap OBJECT-TYPE
    SYNTAX Integer32
    MAX-ACCESS accessible-for-notify
    STATUS current
    DESCRIPTION
        "Parameter 'dest_sap' in event DLS.436"
    ::= { dlsEventObjects436 5 }

dls436_largest_frame_size OBJECT-TYPE
    SYNTAX Integer32
    MAX-ACCESS accessible-for-notify
    STATUS current
    DESCRIPTION
        "Parameter 'largest_frame_size' in event DLS.436"
    ::= { dlsEventObjects436 6 }

dlsEventObjects437 OBJECT-IDENTITY
    STATUS current
    DESCRIPTION
        "Event DLS.437
        An ICANREACH-cs SSP message received from a DLSw neighbor contained an
        lfsize value less than what the router sent in the CANUREACH-cs. This
        is a DLSw protocol violation by the neighbor DLSw because the lfsize
        control flag was set in the CANUREACH-cs indicating that the neighbor
        should fail the circuit setup if it cannot establish a circuit with
        the lfsize the router requested in the CANUREACH-cs."
    ::= { dlsEventsGroup 437 }

dls437_source_mac_address OBJECT-TYPE
    SYNTAX DisplayString
    MAX-ACCESS accessible-for-notify
    STATUS current
    DESCRIPTION
        "Parameter 'source_mac_address' in event DLS.437"
    ::= { dlsEventObjects437 1 }

dls437_dest_mac_address OBJECT-TYPE
    SYNTAX DisplayString
    MAX-ACCESS accessible-for-notify
    STATUS current
    DESCRIPTION
        "Parameter 'dest_mac_address' in event DLS.437"
    ::= { dlsEventObjects437 2 }

dls437_source_sap OBJECT-TYPE
    SYNTAX Integer32
    MAX-ACCESS accessible-for-notify
    STATUS current
    DESCRIPTION
        "Parameter 'source_sap' in event DLS.437"
    ::= { dlsEventObjects437 3 }

dls437_dest_sap OBJECT-TYPE
    SYNTAX Integer32
    MAX-ACCESS accessible-for-notify
    STATUS current
    DESCRIPTION
        "Parameter 'dest_sap' in event DLS.437"
    ::= { dlsEventObjects437 4 }

dlsEventObjects438 OBJECT-IDENTITY
    STATUS current
    DESCRIPTION
        "Event DLS.438
        The SDLC link station specified is transitioning to secondary or
        negotiable idle state."
    ::= { dlsEventsGroup 438 }

dls438_link_address OBJECT-TYPE
    SYNTAX Integer32
    MAX-ACCESS accessible-for-notify
    STATUS current
    DESCRIPTION
        "Parameter 'link_address' in event DLS.438"
    ::= { dlsEventObjects438 1 }

dls438_interface OBJECT-TYPE
    SYNTAX DisplayString
    MAX-ACCESS accessible-for-notify
    STATUS current
    DESCRIPTION
        "Parameter 'interface' in event DLS.438"
    ::= { dlsEventObjects438 2 }

dlsEventObjects439 OBJECT-IDENTITY
    STATUS current
    DESCRIPTION
        "Event DLS.439
        The primary SDLC link station sent an unexpected test cmd frame."
    ::= { dlsEventsGroup 439 }

dls439_link_address OBJECT-TYPE
    SYNTAX Integer32
    MAX-ACCESS accessible-for-notify
    STATUS current
    DESCRIPTION
        "Parameter 'link_address' in event DLS.439"
    ::= { dlsEventObjects439 1 }

dls439_interface OBJECT-TYPE
    SYNTAX DisplayString
    MAX-ACCESS accessible-for-notify
    STATUS current
    DESCRIPTION
        "Parameter 'interface' in event DLS.439"
    ::= { dlsEventObjects439 2 }

dlsEventObjects440 OBJECT-IDENTITY
    STATUS current
    DESCRIPTION
        "Event DLS.440
        A station with Node Type PU 2 was detected on an SDLC link configured
        with a role of Negotiable. This is a probable configuration error; a
        PU 2 link role is normally set Secondary."
    ::= { dlsEventsGroup 440 }

dls440_link_address OBJECT-TYPE
    SYNTAX Integer32
    MAX-ACCESS accessible-for-notify
    STATUS current
    DESCRIPTION
        "Parameter 'link_address' in event DLS.440"
    ::= { dlsEventObjects440 1 }

dls440_interface OBJECT-TYPE
    SYNTAX DisplayString
    MAX-ACCESS accessible-for-notify
    STATUS current
    DESCRIPTION
        "Parameter 'interface' in event DLS.440"
    ::= { dlsEventObjects440 2 }

dlsEventObjects441 OBJECT-IDENTITY
    STATUS current
    DESCRIPTION
        "Event DLS.441
        The primary SDLC link station sent an unexpected XID type for a
        secondary PU type 2 device."
    ::= { dlsEventsGroup 441 }

dls441_link_address OBJECT-TYPE
    SYNTAX Integer32
    MAX-ACCESS accessible-for-notify
    STATUS current
    DESCRIPTION
        "Parameter 'link_address' in event DLS.441"
    ::= { dlsEventObjects441 1 }

dls441_interface OBJECT-TYPE
    SYNTAX DisplayString
    MAX-ACCESS accessible-for-notify
    STATUS current
    DESCRIPTION
        "Parameter 'interface' in event DLS.441"
    ::= { dlsEventObjects441 2 }

dlsEventObjects442 OBJECT-IDENTITY
    STATUS current
    DESCRIPTION
        "Event DLS.442
        The specified SDLC link station sent an indication that a primary SDLC
        link station sent a SNRM."
    ::= { dlsEventsGroup 442 }

dls442_link_address OBJECT-TYPE
    SYNTAX Integer32
    MAX-ACCESS accessible-for-notify
    STATUS current
    DESCRIPTION
        "Parameter 'link_address' in event DLS.442"
    ::= { dlsEventObjects442 1 }

dls442_interface OBJECT-TYPE
    SYNTAX DisplayString
    MAX-ACCESS accessible-for-notify
    STATUS current
    DESCRIPTION
        "Parameter 'interface' in event DLS.442"
    ::= { dlsEventObjects442 2 }

dlsEventObjects443 OBJECT-IDENTITY
    STATUS current
    DESCRIPTION
        "Event DLS.443
        The specified SDLC link station sent an indication that an SDLC link
        station sent a SNRM in an invalid state."
    ::= { dlsEventsGroup 443 }

dls443_link_address OBJECT-TYPE
    SYNTAX Integer32
    MAX-ACCESS accessible-for-notify
    STATUS current
    DESCRIPTION
        "Parameter 'link_address' in event DLS.443"
    ::= { dlsEventObjects443 1 }

dls443_interface OBJECT-TYPE
    SYNTAX DisplayString
    MAX-ACCESS accessible-for-notify
    STATUS current
    DESCRIPTION
        "Parameter 'interface' in event DLS.443"
    ::= { dlsEventObjects443 2 }

dlsEventObjects444 OBJECT-IDENTITY
    STATUS current
    DESCRIPTION
        "Event DLS.444
        The specified SDLC link station sent an unexpected cs_confirm event."
    ::= { dlsEventsGroup 444 }

dls444_state OBJECT-TYPE
    SYNTAX Integer32
    MAX-ACCESS accessible-for-notify
    STATUS current
    DESCRIPTION
        "Parameter 'state' in event DLS.444"
    ::= { dlsEventObjects444 1 }

dls444_link_address OBJECT-TYPE
    SYNTAX Integer32
    MAX-ACCESS accessible-for-notify
    STATUS current
    DESCRIPTION
        "Parameter 'link_address' in event DLS.444"
    ::= { dlsEventObjects444 2 }

dls444_interface OBJECT-TYPE
    SYNTAX DisplayString
    MAX-ACCESS accessible-for-notify
    STATUS current
    DESCRIPTION
        "Parameter 'interface' in event DLS.444"
    ::= { dlsEventObjects444 3 }

dlsEventObjects445 OBJECT-IDENTITY
    STATUS current
    DESCRIPTION
        "Event DLS.445
        The DLS layer sent an unexpected XID type for a secondary PU type 2
        device."
    ::= { dlsEventsGroup 445 }

dls445_link_address OBJECT-TYPE
    SYNTAX Integer32
    MAX-ACCESS accessible-for-notify
    STATUS current
    DESCRIPTION
        "Parameter 'link_address' in event DLS.445"
    ::= { dlsEventObjects445 1 }

dls445_interface OBJECT-TYPE
    SYNTAX DisplayString
    MAX-ACCESS accessible-for-notify
    STATUS current
    DESCRIPTION
        "Parameter 'interface' in event DLS.445"
    ::= { dlsEventObjects445 2 }

dlsEventObjects446 OBJECT-IDENTITY
    STATUS current
    DESCRIPTION
        "Event DLS.446
        The secondary SDLC link station specified is transitioning to
        SEC_NULL_XID_PENDING state, meaning that it is awaiting a response to a
        NULL XID that was sent."
    ::= { dlsEventsGroup 446 }

dls446_link_address OBJECT-TYPE
    SYNTAX Integer32
    MAX-ACCESS accessible-for-notify
    STATUS current
    DESCRIPTION
        "Parameter 'link_address' in event DLS.446"
    ::= { dlsEventObjects446 1 }

dls446_interface OBJECT-TYPE
    SYNTAX DisplayString
    MAX-ACCESS accessible-for-notify
    STATUS current
    DESCRIPTION
        "Parameter 'interface' in event DLS.446"
    ::= { dlsEventObjects446 2 }

dlsEventObjects447 OBJECT-IDENTITY
    STATUS current
    DESCRIPTION
        "Event DLS.447
        The secondary SDLC link station specified is transitioning to secondary
        contact pending state."
    ::= { dlsEventsGroup 447 }

dls447_link_address OBJECT-TYPE
    SYNTAX Integer32
    MAX-ACCESS accessible-for-notify
    STATUS current
    DESCRIPTION
        "Parameter 'link_address' in event DLS.447"
    ::= { dlsEventObjects447 1 }

dls447_interface OBJECT-TYPE
    SYNTAX DisplayString
    MAX-ACCESS accessible-for-notify
    STATUS current
    DESCRIPTION
        "Parameter 'interface' in event DLS.447"
    ::= { dlsEventObjects447 2 }

dlsEventObjects448 OBJECT-IDENTITY
    STATUS current
    DESCRIPTION
        "Event DLS.448
        An attempt to send an SDLC connect response returned an unexpected
        return code from the DL."
    ::= { dlsEventsGroup 448 }

dls448_rtn_code OBJECT-TYPE
    SYNTAX Integer32
    MAX-ACCESS accessible-for-notify
    STATUS current
    DESCRIPTION
        "Parameter 'rtn_code' in event DLS.448"
    ::= { dlsEventObjects448 1 }

dls448_link_address OBJECT-TYPE
    SYNTAX Integer32
    MAX-ACCESS accessible-for-notify
    STATUS current
    DESCRIPTION
        "Parameter 'link_address' in event DLS.448"
    ::= { dlsEventObjects448 2 }

dls448_interface OBJECT-TYPE
    SYNTAX DisplayString
    MAX-ACCESS accessible-for-notify
    STATUS current
    DESCRIPTION
        "Parameter 'interface' in event DLS.448"
    ::= { dlsEventObjects448 3 }

dlsEventObjects449 OBJECT-IDENTITY
    STATUS current
    DESCRIPTION
        "Event DLS.449
        The specified SDLC link station sent an unexpected contacted_rcv event."
    ::= { dlsEventsGroup 449 }

dls449_state OBJECT-TYPE
    SYNTAX Integer32
    MAX-ACCESS accessible-for-notify
    STATUS current
    DESCRIPTION
        "Parameter 'state' in event DLS.449"
    ::= { dlsEventObjects449 1 }

dls449_link_address OBJECT-TYPE
    SYNTAX Integer32
    MAX-ACCESS accessible-for-notify
    STATUS current
    DESCRIPTION
        "Parameter 'link_address' in event DLS.449"
    ::= { dlsEventObjects449 2 }

dls449_interface OBJECT-TYPE
    SYNTAX DisplayString
    MAX-ACCESS accessible-for-notify
    STATUS current
    DESCRIPTION
        "Parameter 'interface' in event DLS.449"
    ::= { dlsEventObjects449 3 }

dlsEventObjects450 OBJECT-IDENTITY
    STATUS current
    DESCRIPTION
        "Event DLS.450
        A Start DL request from DLS to the SDLC interface module was not honored
        because the link role for the SDLC station was Secondary. This is not an
        error. This is due to the fact that SDLC is an unbalanced protocol that
        requires a secondary station to be polled by a primary before it can
        respond or initiate some action."
    ::= { dlsEventsGroup 450 }

dls450_source_mac_address OBJECT-TYPE
    SYNTAX DisplayString
    MAX-ACCESS accessible-for-notify
    STATUS current
    DESCRIPTION
        "Parameter 'source_mac_address' in event DLS.450"
    ::= { dlsEventObjects450 1 }

dls450_dest_mac_address OBJECT-TYPE
    SYNTAX DisplayString
    MAX-ACCESS accessible-for-notify
    STATUS current
    DESCRIPTION
        "Parameter 'dest_mac_address' in event DLS.450"
    ::= { dlsEventObjects450 2 }

dls450_source_sap OBJECT-TYPE
    SYNTAX Integer32
    MAX-ACCESS accessible-for-notify
    STATUS current
    DESCRIPTION
        "Parameter 'source_sap' in event DLS.450"
    ::= { dlsEventObjects450 3 }

dls450_dest_sap OBJECT-TYPE
    SYNTAX Integer32
    MAX-ACCESS accessible-for-notify
    STATUS current
    DESCRIPTION
        "Parameter 'dest_sap' in event DLS.450"
    ::= { dlsEventObjects450 4 }

dlsEventObjects451 OBJECT-IDENTITY
    STATUS current
    DESCRIPTION
        "Event DLS.451
        The secondary SDLC circuit initiation logic has received and ignored a
        Null XID from the neighbor router when it was expecting an XID0
        (internal state sec_nxid_pend). The Null XID is ignored, and the XID0
        is expected to follow."
    ::= { dlsEventsGroup 451 }

dls451_link_address OBJECT-TYPE
    SYNTAX Integer32
    MAX-ACCESS accessible-for-notify
    STATUS current
    DESCRIPTION
        "Parameter 'link_address' in event DLS.451"
    ::= { dlsEventObjects451 1 }

dls451_interface OBJECT-TYPE
    SYNTAX DisplayString
    MAX-ACCESS accessible-for-notify
    STATUS current
    DESCRIPTION
        "Parameter 'interface' in event DLS.451"
    ::= { dlsEventObjects451 2 }

dlsEventObjects452 OBJECT-IDENTITY
    STATUS current
    DESCRIPTION
        "Event DLS.452
        A qllc event has been received."
    ::= { dlsEventsGroup 452 }

dls452_event OBJECT-TYPE
    SYNTAX DisplayString
    MAX-ACCESS accessible-for-notify
    STATUS current
    DESCRIPTION
        "Parameter 'event' in event DLS.452"
    ::= { dlsEventObjects452 1 }

dlsEventObjects453 OBJECT-IDENTITY
    STATUS current
    DESCRIPTION
        "Event DLS.453
        The qllc event received has been assigned to the sesion especified."
    ::= { dlsEventsGroup 453 }

dls453_event OBJECT-TYPE
    SYNTAX DisplayString
    MAX-ACCESS accessible-for-notify
    STATUS current
    DESCRIPTION
        "Parameter 'event' in event DLS.453"
    ::= { dlsEventObjects453 1 }

dls453_source_mac_address OBJECT-TYPE
    SYNTAX DisplayString
    MAX-ACCESS accessible-for-notify
    STATUS current
    DESCRIPTION
        "Parameter 'source_mac_address' in event DLS.453"
    ::= { dlsEventObjects453 2 }

dls453_dest_mac_address OBJECT-TYPE
    SYNTAX DisplayString
    MAX-ACCESS accessible-for-notify
    STATUS current
    DESCRIPTION
        "Parameter 'dest_mac_address' in event DLS.453"
    ::= { dlsEventObjects453 3 }

dls453_source_sap OBJECT-TYPE
    SYNTAX Integer32
    MAX-ACCESS accessible-for-notify
    STATUS current
    DESCRIPTION
        "Parameter 'source_sap' in event DLS.453"
    ::= { dlsEventObjects453 4 }

dls453_dest_sap OBJECT-TYPE
    SYNTAX Integer32
    MAX-ACCESS accessible-for-notify
    STATUS current
    DESCRIPTION
        "Parameter 'dest_sap' in event DLS.453"
    ::= { dlsEventObjects453 5 }

dlsEventObjects454 OBJECT-IDENTITY
    STATUS current
    DESCRIPTION
        "Event DLS.454
        The qllc event received has been refused because there is not
        an adecuate session or the session assigned is in an state that
        no expect this event."
    ::= { dlsEventsGroup 454 }

dls454_event OBJECT-TYPE
    SYNTAX DisplayString
    MAX-ACCESS accessible-for-notify
    STATUS current
    DESCRIPTION
        "Parameter 'event' in event DLS.454"
    ::= { dlsEventObjects454 1 }

dlsEventObjects455 OBJECT-IDENTITY
    STATUS current
    DESCRIPTION
        "Event DLS.455
        A qllc request has been sent successfully."
    ::= { dlsEventsGroup 455 }

dls455_request OBJECT-TYPE
    SYNTAX DisplayString
    MAX-ACCESS accessible-for-notify
    STATUS current
    DESCRIPTION
        "Parameter 'request' in event DLS.455"
    ::= { dlsEventObjects455 1 }

dlsEventObjects456 OBJECT-IDENTITY
    STATUS current
    DESCRIPTION
        "Event DLS.456
        A qllc request has been sent successfully. If the request is a QDAT
        request, Qmsg is the Q message sent."
    ::= { dlsEventsGroup 456 }

dls456_request OBJECT-TYPE
    SYNTAX DisplayString
    MAX-ACCESS accessible-for-notify
    STATUS current
    DESCRIPTION
        "Parameter 'request' in event DLS.456"
    ::= { dlsEventObjects456 1 }

dls456_qmsg OBJECT-TYPE
    SYNTAX Integer32
    MAX-ACCESS accessible-for-notify
    STATUS current
    DESCRIPTION
        "Parameter 'qmsg' in event DLS.456"
    ::= { dlsEventObjects456 2 }

dls456_source_mac_address OBJECT-TYPE
    SYNTAX DisplayString
    MAX-ACCESS accessible-for-notify
    STATUS current
    DESCRIPTION
        "Parameter 'source_mac_address' in event DLS.456"
    ::= { dlsEventObjects456 3 }

dls456_dest_mac_address OBJECT-TYPE
    SYNTAX DisplayString
    MAX-ACCESS accessible-for-notify
    STATUS current
    DESCRIPTION
        "Parameter 'dest_mac_address' in event DLS.456"
    ::= { dlsEventObjects456 4 }

dls456_source_sap OBJECT-TYPE
    SYNTAX Integer32
    MAX-ACCESS accessible-for-notify
    STATUS current
    DESCRIPTION
        "Parameter 'source_sap' in event DLS.456"
    ::= { dlsEventObjects456 5 }

dls456_dest_sap OBJECT-TYPE
    SYNTAX Integer32
    MAX-ACCESS accessible-for-notify
    STATUS current
    DESCRIPTION
        "Parameter 'dest_sap' in event DLS.456"
    ::= { dlsEventObjects456 6 }

dlsEventObjects457 OBJECT-IDENTITY
    STATUS current
    DESCRIPTION
        "Event DLS.457
        The qllc request has not been sent because there aren't free buffers or
        because there is an error in the interface with X.25 node."
    ::= { dlsEventsGroup 457 }

dls457_request OBJECT-TYPE
    SYNTAX DisplayString
    MAX-ACCESS accessible-for-notify
    STATUS current
    DESCRIPTION
        "Parameter 'request' in event DLS.457"
    ::= { dlsEventObjects457 1 }

dlsEventObjects458 OBJECT-IDENTITY
    STATUS current
    DESCRIPTION
        "Event DLS.458
        A SSP message IAMOKAY has been sent successfully to DLSw neighbor
        to make a test of transport connection."
    ::= { dlsEventsGroup 458 }

dls458_ip_address OBJECT-TYPE
    SYNTAX IpAddress
    MAX-ACCESS accessible-for-notify
    STATUS current
    DESCRIPTION
        "Parameter 'ip_address' in event DLS.458"
    ::= { dlsEventObjects458 1 }

dlsEventObjects459 OBJECT-IDENTITY
    STATUS current
    DESCRIPTION
        "Event DLS.459
        There is no memory available to create a SSP message IAMOKAY and is not
        posible to send it through the transport connection."
    ::= { dlsEventsGroup 459 }

dls459_ip_address OBJECT-TYPE
    SYNTAX IpAddress
    MAX-ACCESS accessible-for-notify
    STATUS current
    DESCRIPTION
        "Parameter 'ip_address' in event DLS.459"
    ::= { dlsEventObjects459 1 }


dlsNotification1 NOTIFICATION-TYPE
    OBJECTS { 
              dls1_ip_address 
            }
    STATUS current
    DESCRIPTION
        "Notification of Event DLS.1

        Message: 'neighbour TCP configuration entry could not be found for this destination ip address $1'

        Parameters list:
              $1: dls1_ip_address

        As a result of DLS requesting an OPEN to a particular destination
        specified by the ip address, TCPIM tries to find the corresponding
        tcp configuration entry in the RAM list. If not found, it prints
        this message."
    ::= { dlsNotificationsPrefix 1 }

dlsNotification2 NOTIFICATION-TYPE
    OBJECTS { 
              dls2_ip_address 
            }
    STATUS current
    DESCRIPTION
        "Notification of Event DLS.2

        Message: 'opening a new transport connection to the neighbour at $1'

        Parameters list:
              $1: dls2_ip_address

        As a result of DLS requesting an OPEN to a particular destination
        specified by the ip address, TCPIM opens a connection to the
        destination."
    ::= { dlsNotificationsPrefix 2 }

dlsNotification3 NOTIFICATION-TYPE
    OBJECTS { 
              dls3_ip_address 
            }
    STATUS current
    DESCRIPTION
        "Notification of Event DLS.3

        Message: 'illegal entry through read port from ip address $1'

        Parameters list:
              $1: dls3_ip_address

        Our read tcp connection has been opened via an illegal neighbor
        (i.e., someone we do not know about). As a result, we reject
        the connection, and thereby close it."
    ::= { dlsNotificationsPrefix 3 }

dlsNotification4 NOTIFICATION-TYPE
    OBJECTS { 
              dls4_ip_address 
            }
    STATUS current
    DESCRIPTION
        "Notification of Event DLS.4

        Message: 'transport connection already in a pending/established state for ip address $1'

        Parameters list:
              $1: dls4_ip_address

        DLS has requested we open a connection to the destination ip address.
        However, a connection already exists (or is in the pending state)."
    ::= { dlsNotificationsPrefix 4 }

dlsNotification5 NOTIFICATION-TYPE
    OBJECTS { 
              dls5_ip_address 
            }
    STATUS current
    DESCRIPTION
        "Notification of Event DLS.5

        Message: 'opening a new transport connection to the neighbour at $1'

        Parameters list:
              $1: dls5_ip_address

        As a result of DLS requesting an OPEN to a particular destination
        specified by the ip address, TCPIM opens a connection to the
        destination."
    ::= { dlsNotificationsPrefix 5 }

dlsNotification6 NOTIFICATION-TYPE
    OBJECTS { 
              dls6_ip_address 
            }
    STATUS current
    DESCRIPTION
        "Notification of Event DLS.6

        Message: 'cannot close the transport connection - no established neighbour at ip address $1'

        Parameters list:
              $1: dls6_ip_address

        DLS is requesting a transport connection to be closed - however, it
        cannot be closed because there is no established connection to
        that neighbor."
    ::= { dlsNotificationsPrefix 6 }

dlsNotification7 NOTIFICATION-TYPE
    OBJECTS { 
              dls7_ip_address 
            }
    STATUS current
    DESCRIPTION
        "Notification of Event DLS.7

        Message: 'read port opened, now opening write port to neighbour at $1'

        Parameters list:
              $1: dls7_ip_address

        The other side has opened our read port, and as a result, we
        open our write port to the other side."
    ::= { dlsNotificationsPrefix 7 }

dlsNotification8 NOTIFICATION-TYPE
    STATUS current
    DESCRIPTION
        "Notification of Event DLS.8

        Message: 'DLSw forwarder disabled no SRB segment defined'

        The Data Link Switching forwarder has been disabled because of
        improper configuration. This was no SRB segment number defined,
        though there was LLC-2 saps defined."
    ::= { dlsNotificationsPrefix 8 }

dlsNotification9 NOTIFICATION-TYPE
    STATUS current
    DESCRIPTION
        "Notification of Event DLS.9

        Message: 'DLSw forwarder disabled no memory for configuration'

        The Data Link Switching forwarder has been disabled because there
        was not enough memory to create necessary data structures."
    ::= { dlsNotificationsPrefix 9 }

dlsNotification10 NOTIFICATION-TYPE
    OBJECTS { 
              dls10_ip_address 
            }
    STATUS current
    DESCRIPTION
        "Notification of Event DLS.10

        Message: 'establishing a local transport connection at $1'

        Parameters list:
              $1: dls10_ip_address

        As a result of DLS configured for local conversion, we must establish
        two transport connections to ourselves."
    ::= { dlsNotificationsPrefix 10 }

dlsNotification11 NOTIFICATION-TYPE
    OBJECTS { 
              dls11_ip_address 
            }
    STATUS current
    DESCRIPTION
        "Notification of Event DLS.11

        Message: 'neighbour TCP configuration entry could not be found for local connection $1'

        Parameters list:
              $1: dls11_ip_address

        As a result of DLS requesting an OPEN to ourself (due to local
        conversion), specified by the ip address, TCPIM tries to find the
        corresponding tcp configuration entry in the RAM list. If not found,
        it prints this message."
    ::= { dlsNotificationsPrefix 11 }

dlsNotification12 NOTIFICATION-TYPE
    OBJECTS { 
              dls12_ip_address 
            }
    STATUS current
    DESCRIPTION
        "Notification of Event DLS.12

        Message: 'establishing a local transport connection at $1'

        Parameters list:
              $1: dls12_ip_address

        As a result of DLS configured for local conversion, we must establish
        two transport connections to ourselves."
    ::= { dlsNotificationsPrefix 12 }

dlsNotification13 NOTIFICATION-TYPE
    STATUS current
    DESCRIPTION
        "Notification of Event DLS.13

        Message: 'can't register with UDP on DLS group port'

        Registration with UDP on DLS group port failed."
    ::= { dlsNotificationsPrefix 13 }

dlsNotification14 NOTIFICATION-TYPE
    STATUS current
    DESCRIPTION
        "Notification of Event DLS.14

        Message: 'no memory to join group'

        There was not enough free memory allocated to the data structures
        neccessary to join a group."
    ::= { dlsNotificationsPrefix 14 }

dlsNotification15 NOTIFICATION-TYPE
    STATUS current
    DESCRIPTION
        "Notification of Event DLS.15

        Message: 'no iorb to send group packet'

        There was no iorb buffer available to send a group join or join response."
    ::= { dlsNotificationsPrefix 15 }

dlsNotification16 NOTIFICATION-TYPE
    OBJECTS { 
              dls16_type, 
              dls16_group,
              dls16_role,
              dls16_destination 
            }
    STATUS current
    DESCRIPTION
        "Notification of Event DLS.16

        Message: 'Sent group packet type $1 group $2 role $3 dest $4'

        Parameters list:
              $1: dls16_type
              $2: dls16_group
              $3: dls16_role
              $4: dls16_destination

        A DLSw group packet was sent."
    ::= { dlsNotificationsPrefix 16 }

dlsNotification17 NOTIFICATION-TYPE
    STATUS current
    DESCRIPTION
        "Notification of Event DLS.17

        Message: 'DLSw forwarder disabled no source MAC defined'

        The Data Link Switching forwarder has been disabled because of
        improper configuration. SDLC was configured but no source MAC address
        was configured."
    ::= { dlsNotificationsPrefix 17 }

dlsNotification18 NOTIFICATION-TYPE
    OBJECTS { 
              dls18_type, 
              dls18_group,
              dls18_role,
              dls18_source 
            }
    STATUS current
    DESCRIPTION
        "Notification of Event DLS.18

        Message: 'Received group packet type $1 group $2 role $3 source $4'

        Parameters list:
              $1: dls18_type
              $2: dls18_group
              $3: dls18_role
              $4: dls18_source

        A DLSw group packet was received."
    ::= { dlsNotificationsPrefix 18 }

dlsNotification19 NOTIFICATION-TYPE
    OBJECTS { 
              dls19_version, 
              dls19_type,
              dls19_priority,
              dls19_domain 
            }
    STATUS current
    DESCRIPTION
        "Notification of Event DLS.19

        Message: 'Received bad group packet version $1 type $2 priority $3 domain $4'

        Parameters list:
              $1: dls19_version
              $2: dls19_type
              $3: dls19_priority
              $4: dls19_domain

        A DLSw group packet was received with either a bad version #, type,
        priority, or domain id."
    ::= { dlsNotificationsPrefix 19 }

dlsNotification20 NOTIFICATION-TYPE
    OBJECTS { 
              dls20_group 
            }
    STATUS current
    DESCRIPTION
        "Notification of Event DLS.20

        Message: 'Received group packet for deleted group $1'

        Parameters list:
              $1: dls20_group

        A group packet was received for a group that was dynamically deleted."
    ::= { dlsNotificationsPrefix 20 }

dlsNotification21 NOTIFICATION-TYPE
    OBJECTS { 
              dls21_group, 
              dls21_role 
            }
    STATUS current
    DESCRIPTION
        "Notification of Event DLS.21

        Message: 'Received group packet but mismatched roles group $1 role $2'

        Parameters list:
              $1: dls21_group
              $2: dls21_role

        A group packet was received but the roles were mismatched. The only
        valid role matches are Client/Server and Peer/Peer."
    ::= { dlsNotificationsPrefix 21 }

dlsNotification22 NOTIFICATION-TYPE
    OBJECTS { 
              dls22_address, 
              dls22_group 
            }
    STATUS current
    DESCRIPTION
        "Notification of Event DLS.22

        Message: 'Connecting to IP Address $1 group $2'

        Parameters list:
              $1: dls22_address
              $2: dls22_group

        A group match has been found and we are initiating a connect."
    ::= { dlsNotificationsPrefix 22 }

dlsNotification23 NOTIFICATION-TYPE
    OBJECTS { 
              dls23_address, 
              dls23_group 
            }
    STATUS current
    DESCRIPTION
        "Notification of Event DLS.23

        Message: 'Can't connect to $1 from group $2, IP address dynamically deleted'

        Parameters list:
              $1: dls23_address
              $2: dls23_group

        A group match has been found but we are not initiating a connection
        because a static IP connection to the partner has been deleted."
    ::= { dlsNotificationsPrefix 23 }

dlsNotification24 NOTIFICATION-TYPE
    OBJECTS { 
              dls24_address, 
              dls24_group 
            }
    STATUS current
    DESCRIPTION
        "Notification of Event DLS.24

        Message: 'Already connected to $1 via static IP address, group $2 not used'

        Parameters list:
              $1: dls24_address
              $2: dls24_group

        A group match has been found but we are not initiating a connection
        because a static IP connection to the partner already exists."
    ::= { dlsNotificationsPrefix 24 }

dlsNotification25 NOTIFICATION-TYPE
    STATUS current
    DESCRIPTION
        "Notification of Event DLS.25

        Message: 'No memory to queue group packet to tasker'

        There was not enough memory to get a queue header to add a task
        to send a group packet."
    ::= { dlsNotificationsPrefix 25 }

dlsNotification26 NOTIFICATION-TYPE
    STATUS current
    DESCRIPTION
        "Notification of Event DLS.26

        Message: 'group packet not sent, tasker queue full'

        A group packet could not be sent becuase the tasker queue was full."
    ::= { dlsNotificationsPrefix 26 }

dlsNotification27 NOTIFICATION-TYPE
    OBJECTS { 
              dls27_station, 
              dls27_interface 
            }
    STATUS current
    DESCRIPTION
        "Notification of Event DLS.27

        Message: 'maximum number of sdlc link stations exceeded sta $1 on ifc $2 not opened'

        Parameters list:
              $1: dls27_station
              $2: dls27_interface

        The maximum number of sdlc link stations has been exceeded since all
        available source SAPs have been allocated. The link station was not
        opened."
    ::= { dlsNotificationsPrefix 27 }

dlsNotification28 NOTIFICATION-TYPE
    OBJECTS { 
              dls28_interface 
            }
    STATUS current
    DESCRIPTION
        "Notification of Event DLS.28

        Message: 'no memory to initialize SDLC link interface $1'

        Parameters list:
              $1: dls28_interface

        There was not enough memory available to initialize an SDLC link."
    ::= { dlsNotificationsPrefix 28 }

dlsNotification29 NOTIFICATION-TYPE
    OBJECTS { 
              dls29_rtn_code, 
              dls29_interface 
            }
    STATUS current
    DESCRIPTION
        "Notification of Event DLS.29

        Message: 'unexpected return code from sdlc open station = $1 interface $2'

        Parameters list:
              $1: dls29_rtn_code
              $2: dls29_interface

        The sdlc open station function returned an unexpected return code."
    ::= { dlsNotificationsPrefix 29 }

dlsNotification30 NOTIFICATION-TYPE
    OBJECTS { 
              dls30_interface 
            }
    STATUS current
    DESCRIPTION
        "Notification of Event DLS.30

        Message: 'sdlc link control block not found during delete link interface $1'

        Parameters list:
              $1: dls30_interface

        The sdlc link control block was not found for the SDLC link being
        deleted."
    ::= { dlsNotificationsPrefix 30 }

dlsNotification31 NOTIFICATION-TYPE
    OBJECTS { 
              dls31_interface 
            }
    STATUS current
    DESCRIPTION
        "Notification of Event DLS.31

        Message: 'sdlc station closed interface $1'

        Parameters list:
              $1: dls31_interface

        The sdlc station for the network interface has been successfully closed."
    ::= { dlsNotificationsPrefix 31 }

dlsNotification32 NOTIFICATION-TYPE
    OBJECTS { 
              dls32_rtn_code, 
              dls32_interface 
            }
    STATUS current
    DESCRIPTION
        "Notification of Event DLS.32

        Message: 'unexpected return code from sdlc close station = $1 interface $2'

        Parameters list:
              $1: dls32_rtn_code
              $2: dls32_interface

        The sdlc close station function returned an unexpected return code."
    ::= { dlsNotificationsPrefix 32 }

dlsNotification33 NOTIFICATION-TYPE
    OBJECTS { 
              dls33_interface 
            }
    STATUS current
    DESCRIPTION
        "Notification of Event DLS.33

        Message: 'sdlc link control block not found during init link station interface $1'

        Parameters list:
              $1: dls33_interface

        The sdlc link control block was not found for the SDLC link station
        being initialized."
    ::= { dlsNotificationsPrefix 33 }

dlsNotification34 NOTIFICATION-TYPE
    OBJECTS { 
              dls34_interface 
            }
    STATUS current
    DESCRIPTION
        "Notification of Event DLS.34

        Message: 'no memory to initialize SDLC link station interface $1'

        Parameters list:
              $1: dls34_interface

        There was not enough memory available to initialize an SDLC link station."
    ::= { dlsNotificationsPrefix 34 }

dlsNotification35 NOTIFICATION-TYPE
    OBJECTS { 
              dls35_link_address, 
              dls35_interface 
            }
    STATUS current
    DESCRIPTION
        "Notification of Event DLS.35

        Message: 'sdlc link station opened address $1 interface $2'

        Parameters list:
              $1: dls35_link_address
              $2: dls35_interface

        The sdlc link station for the link address has been successfully opened
        on the network interface."
    ::= { dlsNotificationsPrefix 35 }

dlsNotification36 NOTIFICATION-TYPE
    OBJECTS { 
              dls36_link_address, 
              dls36_interface 
            }
    STATUS current
    DESCRIPTION
        "Notification of Event DLS.36

        Message: 'duplicate sdlc link station address $1 interface $2'

        Parameters list:
              $1: dls36_link_address
              $2: dls36_interface

        The specified sdlc link station could not be opened because it is a
        duplicate of one already opened."
    ::= { dlsNotificationsPrefix 36 }

dlsNotification37 NOTIFICATION-TYPE
    OBJECTS { 
              dls37_rtn_code, 
              dls37_interface 
            }
    STATUS current
    DESCRIPTION
        "Notification of Event DLS.37

        Message: 'unexpected return code from sdlc open link station = $1 interface $2'

        Parameters list:
              $1: dls37_rtn_code
              $2: dls37_interface

        The sdlc open link station function returned an unexpected return code."
    ::= { dlsNotificationsPrefix 37 }

dlsNotification38 NOTIFICATION-TYPE
    OBJECTS { 
              dls38_link_address, 
              dls38_interface 
            }
    STATUS current
    DESCRIPTION
        "Notification of Event DLS.38

        Message: 'sdlc station closed address $1 interface $2'

        Parameters list:
              $1: dls38_link_address
              $2: dls38_interface

        The sdlc link station for the address and network interface specified
        has been successfully closed."
    ::= { dlsNotificationsPrefix 38 }

dlsNotification39 NOTIFICATION-TYPE
    OBJECTS { 
              dls39_link_address, 
              dls39_interface 
            }
    STATUS current
    DESCRIPTION
        "Notification of Event DLS.39

        Message: 'processing sdlc net up for address $1 interface $2'

        Parameters list:
              $1: dls39_link_address
              $2: dls39_interface

        A net up indication has been received for an sdlc link station."
    ::= { dlsNotificationsPrefix 39 }

dlsNotification40 NOTIFICATION-TYPE
    OBJECTS { 
              dls40_link_address, 
              dls40_interface 
            }
    STATUS current
    DESCRIPTION
        "Notification of Event DLS.40

        Message: 'processing sdlc net down for address $1 interface $2'

        Parameters list:
              $1: dls40_link_address
              $2: dls40_interface

        A net down indication has been received for an sdlc link station."
    ::= { dlsNotificationsPrefix 40 }

dlsNotification41 NOTIFICATION-TYPE
    OBJECTS { 
              dls41_link_address, 
              dls41_interface 
            }
    STATUS current
    DESCRIPTION
        "Notification of Event DLS.41

        Message: 'received sdlc net up while not in down state for address $1 interface $2'

        Parameters list:
              $1: dls41_link_address
              $2: dls41_interface

        A net up indication has been received for an sdlc link station on
        an interface that is not down."
    ::= { dlsNotificationsPrefix 41 }

dlsNotification42 NOTIFICATION-TYPE
    OBJECTS { 
              dls42_link_address, 
              dls42_interface 
            }
    STATUS current
    DESCRIPTION
        "Notification of Event DLS.42

        Message: 'sdlc transition to resolve pending state for address $1 interface $2'

        Parameters list:
              $1: dls42_link_address
              $2: dls42_interface

        The sdlc link station specified is transitioning to resolve
        pending state."
    ::= { dlsNotificationsPrefix 42 }

dlsNotification43 NOTIFICATION-TYPE
    OBJECTS { 
              dls43_link_address, 
              dls43_interface 
            }
    STATUS current
    DESCRIPTION
        "Notification of Event DLS.43

        Message: 'unexpected sdlc test response for address $1 interface $2'

        Parameters list:
              $1: dls43_link_address
              $2: dls43_interface

        An unexpected test response was received from the sdlc link station
        specified."
    ::= { dlsNotificationsPrefix 43 }

dlsNotification44 NOTIFICATION-TYPE
    OBJECTS { 
              dls44_link_address, 
              dls44_interface 
            }
    STATUS current
    DESCRIPTION
        "Notification of Event DLS.44

        Message: 'unexpected sdlc non xid0 from pu 2 device for address $1 interface $2'

        Parameters list:
              $1: dls44_link_address
              $2: dls44_interface

        An unexpected XID type was received for a PU type 2 device from
        the sdlc link station specified."
    ::= { dlsNotificationsPrefix 44 }

dlsNotification45 NOTIFICATION-TYPE
    OBJECTS { 
              dls45_link_address, 
              dls45_interface 
            }
    STATUS current
    DESCRIPTION
        "Notification of Event DLS.45

        Message: 'invalid sdlc xid0 length from address $1 interface $2'

        Parameters list:
              $1: dls45_link_address
              $2: dls45_interface

        An invalid length XID-0 was received from the sdlc link station
        specified."
    ::= { dlsNotificationsPrefix 45 }

dlsNotification46 NOTIFICATION-TYPE
    OBJECTS { 
              dls46_link_address, 
              dls46_interface 
            }
    STATUS current
    DESCRIPTION
        "Notification of Event DLS.46

        Message: 'connection indication received from secondary sdlc station from address $1 interface $2'

        Parameters list:
              $1: dls46_link_address
              $2: dls46_interface

        An indication that a secondary SDLC link station sent a SNRM was
        received from the sdlc link station specified."
    ::= { dlsNotificationsPrefix 46 }

dlsNotification47 NOTIFICATION-TYPE
    OBJECTS { 
              dls47_link_address, 
              dls47_interface 
            }
    STATUS current
    DESCRIPTION
        "Notification of Event DLS.47

        Message: 'sdlc transition to contacted state for address $1 interface $2'

        Parameters list:
              $1: dls47_link_address
              $2: dls47_interface

        The sdlc link station specified is transitioning to contacted state."
    ::= { dlsNotificationsPrefix 47 }

dlsNotification48 NOTIFICATION-TYPE
    OBJECTS { 
              dls48_link_address, 
              dls48_interface 
            }
    STATUS current
    DESCRIPTION
        "Notification of Event DLS.48

        Message: 'unexpected sdlc connect confirm for address $1 interface $2'

        Parameters list:
              $1: dls48_link_address
              $2: dls48_interface

        An unexpected connect confirm was received from the sdlc link station
        specified."
    ::= { dlsNotificationsPrefix 48 }

dlsNotification49 NOTIFICATION-TYPE
    OBJECTS { 
              dls49_link_address, 
              dls49_interface 
            }
    STATUS current
    DESCRIPTION
        "Notification of Event DLS.49

        Message: 'sdlc disconnect indication received address $1 interface $2'

        Parameters list:
              $1: dls49_link_address
              $2: dls49_interface

        A disconnect indication was received from the SDLC link station
        specified."
    ::= { dlsNotificationsPrefix 49 }

dlsNotification50 NOTIFICATION-TYPE
    OBJECTS { 
              dls50_link_address, 
              dls50_interface 
            }
    STATUS current
    DESCRIPTION
        "Notification of Event DLS.50

        Message: 'sdlc disconnect complete address $1 interface $2'

        Parameters list:
              $1: dls50_link_address
              $2: dls50_interface

        The disconnect sequence for the SDLC link station specified is complete."
    ::= { dlsNotificationsPrefix 50 }

dlsNotification51 NOTIFICATION-TYPE
    OBJECTS { 
              dls51_state, 
              dls51_link_address,
              dls51_interface 
            }
    STATUS current
    DESCRIPTION
        "Notification of Event DLS.51

        Message: 'unexpected sdlc disconnect indication in state $1 for address $2 interface $3'

        Parameters list:
              $1: dls51_state
              $2: dls51_link_address
              $3: dls51_interface

        An unexpected disconnect indication was received from
        the sdlc link station specified."
    ::= { dlsNotificationsPrefix 51 }

dlsNotification52 NOTIFICATION-TYPE
    OBJECTS { 
              dls52_link_address, 
              dls52_interface 
            }
    STATUS current
    DESCRIPTION
        "Notification of Event DLS.52

        Message: 'sdlc disconnect confirm address $1 interface $2'

        Parameters list:
              $1: dls52_link_address
              $2: dls52_interface

        A disconnect confirm was received for the SDLC link station specified."
    ::= { dlsNotificationsPrefix 52 }

dlsNotification53 NOTIFICATION-TYPE
    OBJECTS { 
              dls53_state, 
              dls53_link_address,
              dls53_interface 
            }
    STATUS current
    DESCRIPTION
        "Notification of Event DLS.53

        Message: 'unexpected sdlc disconnect confirm in state $1 for address $2 interface $3'

        Parameters list:
              $1: dls53_state
              $2: dls53_link_address
              $3: dls53_interface

        An unexpected disconnect confirm was received from the sdlc link station
        specified."
    ::= { dlsNotificationsPrefix 53 }

dlsNotification54 NOTIFICATION-TYPE
    OBJECTS { 
              dls54_state, 
              dls54_link_address,
              dls54_interface 
            }
    STATUS current
    DESCRIPTION
        "Notification of Event DLS.54

        Message: 'unexpected sdlc resolve_r in state $1 for address $2 interface $3'

        Parameters list:
              $1: dls54_state
              $2: dls54_link_address
              $3: dls54_interface

        An unexpected resolve_r event was received for the sdlc link station
        specified."
    ::= { dlsNotificationsPrefix 54 }

dlsNotification55 NOTIFICATION-TYPE
    OBJECTS { 
              dls55_link_address, 
              dls55_interface 
            }
    STATUS current
    DESCRIPTION
        "Notification of Event DLS.55

        Message: 'sdlc transition to connected state for address $1 interface $2'

        Parameters list:
              $1: dls55_link_address
              $2: dls55_interface

        The sdlc link station specified is transitioning to connected state."
    ::= { dlsNotificationsPrefix 55 }

dlsNotification56 NOTIFICATION-TYPE
    OBJECTS { 
              dls56_rtn_code, 
              dls56_link_address,
              dls56_interface 
            }
    STATUS current
    DESCRIPTION
        "Notification of Event DLS.56

        Message: 'unexpected return code from sdlc connect request = $1 for address $2 interface $3'

        Parameters list:
              $1: dls56_rtn_code
              $2: dls56_link_address
              $3: dls56_interface

        The sdlc connect request function returned an unexpected return code."
    ::= { dlsNotificationsPrefix 56 }

dlsNotification57 NOTIFICATION-TYPE
    OBJECTS { 
              dls57_state, 
              dls57_link_address,
              dls57_interface 
            }
    STATUS current
    DESCRIPTION
        "Notification of Event DLS.57

        Message: 'unexpected sdlc xid from dls in state $1 for address $2 interface $3'

        Parameters list:
              $1: dls57_state
              $2: dls57_link_address
              $3: dls57_interface

        An unexpected xid event was received for the sdlc link station
        specified."
    ::= { dlsNotificationsPrefix 57 }

dlsNotification58 NOTIFICATION-TYPE
    OBJECTS { 
              dls58_link_address, 
              dls58_interface 
            }
    STATUS current
    DESCRIPTION
        "Notification of Event DLS.58

        Message: 'unexpected sdlc xid3 from dls for pu 2 device for address $1 interface $2'

        Parameters list:
              $1: dls58_link_address
              $2: dls58_interface

        An unexpected XID-3 was received from DLS for a PU type 2 device for
        the sdlc link station specified."
    ::= { dlsNotificationsPrefix 58 }

dlsNotification59 NOTIFICATION-TYPE
    OBJECTS { 
              dls59_state, 
              dls59_link_address,
              dls59_interface 
            }
    STATUS current
    DESCRIPTION
        "Notification of Event DLS.59

        Message: 'unexpected sdlc dlc_contact from dls in state $1 for address $2 interface $3'

        Parameters list:
              $1: dls59_state
              $2: dls59_link_address
              $3: dls59_interface

        An unexpected DLC_CONTACT event was received from DLS for
        the sdlc link station specified."
    ::= { dlsNotificationsPrefix 59 }

dlsNotification60 NOTIFICATION-TYPE
    OBJECTS { 
              dls60_state, 
              dls60_link_address,
              dls60_interface 
            }
    STATUS current
    DESCRIPTION
        "Notification of Event DLS.60

        Message: 'unexpected sdlc dlc_info from dls in state $1 for address $2 interface $3'

        Parameters list:
              $1: dls60_state
              $2: dls60_link_address
              $3: dls60_interface

        An unexpected DLC_INFO event was received from DLS for
        the sdlc link station specified."
    ::= { dlsNotificationsPrefix 60 }

dlsNotification61 NOTIFICATION-TYPE
    OBJECTS { 
              dls61_state, 
              dls61_link_address,
              dls61_interface 
            }
    STATUS current
    DESCRIPTION
        "Notification of Event DLS.61

        Message: 'unexpected sdlc dlc_dgrm from dls in state $1 for address $2 interface $3'

        Parameters list:
              $1: dls61_state
              $2: dls61_link_address
              $3: dls61_interface

        An unexpected DLC_DGRM event was received from DLS for
        the sdlc link station specified."
    ::= { dlsNotificationsPrefix 61 }

dlsNotification62 NOTIFICATION-TYPE
    OBJECTS { 
              dls62_state, 
              dls62_link_address,
              dls62_interface 
            }
    STATUS current
    DESCRIPTION
        "Notification of Event DLS.62

        Message: 'unexpected I-frame from sdlc in state $1 for address $2 interface $3'

        Parameters list:
              $1: dls62_state
              $2: dls62_link_address
              $3: dls62_interface

        An unexpected I-frame was received from SDLC for the sdlc link station
        specified."
    ::= { dlsNotificationsPrefix 62 }

dlsNotification63 NOTIFICATION-TYPE
    OBJECTS { 
              dls63_state, 
              dls63_link_address,
              dls63_interface 
            }
    STATUS current
    DESCRIPTION
        "Notification of Event DLS.63

        Message: 'unexpected UI-frame from sdlc in state $1 for address $2 interface $3'

        Parameters list:
              $1: dls63_state
              $2: dls63_link_address
              $3: dls63_interface

        An unexpected UI-frame was received from SDLC for the sdlc link station
        specified."
    ::= { dlsNotificationsPrefix 63 }

dlsNotification64 NOTIFICATION-TYPE
    OBJECTS { 
              dls64_link_address, 
              dls64_interface 
            }
    STATUS current
    DESCRIPTION
        "Notification of Event DLS.64

        Message: 'received halt_dl for sdlc address $1 interface $2'

        Parameters list:
              $1: dls64_link_address
              $2: dls64_interface

        A HALT_DL event was sent from DLS for the specified sdlc link station."
    ::= { dlsNotificationsPrefix 64 }

dlsNotification65 NOTIFICATION-TYPE
    OBJECTS { 
              dls65_link_address, 
              dls65_interface 
            }
    STATUS current
    DESCRIPTION
        "Notification of Event DLS.65

        Message: 'sdlc transition to disconnect pending state for address $1 interface $2'

        Parameters list:
              $1: dls65_link_address
              $2: dls65_interface

        The sdlc link station specified is transitioning
        to disconnect pending state."
    ::= { dlsNotificationsPrefix 65 }

dlsNotification66 NOTIFICATION-TYPE
    OBJECTS { 
              dls66_rtn_code, 
              dls66_link_address,
              dls66_interface 
            }
    STATUS current
    DESCRIPTION
        "Notification of Event DLS.66

        Message: 'unexpected return code from sdlc disconnect request = $1 addr $2 interface $3'

        Parameters list:
              $1: dls66_rtn_code
              $2: dls66_link_address
              $3: dls66_interface

        The sdlc disconnect request function returned an unexpected return code."
    ::= { dlsNotificationsPrefix 66 }

dlsNotification67 NOTIFICATION-TYPE
    OBJECTS { 
              dls67_link_address, 
              dls67_interface 
            }
    STATUS current
    DESCRIPTION
        "Notification of Event DLS.67

        Message: 'sdlc transition to disconnect state for address $1 interface $2'

        Parameters list:
              $1: dls67_link_address
              $2: dls67_interface

        The sdlc link station specified is transitioning to disconnect state."
    ::= { dlsNotificationsPrefix 67 }

dlsNotification68 NOTIFICATION-TYPE
    OBJECTS { 
              dls68_state, 
              dls68_link_address,
              dls68_interface 
            }
    STATUS current
    DESCRIPTION
        "Notification of Event DLS.68

        Message: 'unexpected sdlc dlc_halt_dl from dls in state $1 for address $2 interface $3'

        Parameters list:
              $1: dls68_state
              $2: dls68_link_address
              $3: dls68_interface

        An unexpected DLC_HALT_DL event was received from DLS for
        the sdlc link station specified."
    ::= { dlsNotificationsPrefix 68 }

dlsNotification69 NOTIFICATION-TYPE
    OBJECTS { 
              dls69_link_address, 
              dls69_interface 
            }
    STATUS current
    DESCRIPTION
        "Notification of Event DLS.69

        Message: 'cleanup timer expired for address $1 interface $2'

        Parameters list:
              $1: dls69_link_address
              $2: dls69_interface

        The cleanup timer expired for the specified sdlc link station."
    ::= { dlsNotificationsPrefix 69 }

dlsNotification70 NOTIFICATION-TYPE
    OBJECTS { 
              dls70_state, 
              dls70_link_address,
              dls70_interface 
            }
    STATUS current
    DESCRIPTION
        "Notification of Event DLS.70

        Message: 'unexpected sdlc cleanup timer expiration in state $1 for address $2 interface $3'

        Parameters list:
              $1: dls70_state
              $2: dls70_link_address
              $3: dls70_interface

        The sdlc cleanup timer expired, but the sdlc link station is in an
        unexpected state."
    ::= { dlsNotificationsPrefix 70 }

dlsNotification71 NOTIFICATION-TYPE
    OBJECTS { 
              dls71_link_address, 
              dls71_interface 
            }
    STATUS current
    DESCRIPTION
        "Notification of Event DLS.71

        Message: 'sdlc buffer retry timer expired for address $1 interface $2'

        Parameters list:
              $1: dls71_link_address
              $2: dls71_interface

        The buffer retry timer expired for the specified sdlc link station."
    ::= { dlsNotificationsPrefix 71 }

dlsNotification72 NOTIFICATION-TYPE
    OBJECTS { 
              dls72_state, 
              dls72_link_address,
              dls72_interface 
            }
    STATUS current
    DESCRIPTION
        "Notification of Event DLS.72

        Message: 'unexpected sdlc buffer retry timer expiration in state $1 for address $2 interface $3'

        Parameters list:
              $1: dls72_state
              $2: dls72_link_address
              $3: dls72_interface

        The sdlc buffer retry timer expired, but the sdlc link station is in an
        unexpected state."
    ::= { dlsNotificationsPrefix 72 }

dlsNotification73 NOTIFICATION-TYPE
    OBJECTS { 
              dls73_event, 
              dls73_link_address,
              dls73_interface 
            }
    STATUS current
    DESCRIPTION
        "Notification of Event DLS.73

        Message: 'unknown sdlc fsm input = $1 for address $2 interface $3'

        Parameters list:
              $1: dls73_event
              $2: dls73_link_address
              $3: dls73_interface

        The sdlc interface finite state machine was passed an unknown event."
    ::= { dlsNotificationsPrefix 73 }

dlsNotification74 NOTIFICATION-TYPE
    OBJECTS { 
              dls74_link_address, 
              dls74_interface 
            }
    STATUS current
    DESCRIPTION
        "Notification of Event DLS.74

        Message: 'sdlc net up transition to disconnect state for address $1 interface $2'

        Parameters list:
              $1: dls74_link_address
              $2: dls74_interface

        The sdlc link station specified is transitioning to disconnect state
        due to a net up indication."
    ::= { dlsNotificationsPrefix 74 }

dlsNotification75 NOTIFICATION-TYPE
    OBJECTS { 
              dls75_link_address, 
              dls75_interface 
            }
    STATUS current
    DESCRIPTION
        "Notification of Event DLS.75

        Message: 'unexpected sdlc non xid3 from pu 2.1 device for address $1 interface $2'

        Parameters list:
              $1: dls75_link_address
              $2: dls75_interface

        An unexpected XID type was received for a PU type 2.1 device from
        the sdlc link station specified."
    ::= { dlsNotificationsPrefix 75 }

dlsNotification76 NOTIFICATION-TYPE
    OBJECTS { 
              dls76_link_address, 
              dls76_interface 
            }
    STATUS current
    DESCRIPTION
        "Notification of Event DLS.76

        Message: 'unexpected sdlc xid0 from pu 2.1 device for address $1 interface $2'

        Parameters list:
              $1: dls76_link_address
              $2: dls76_interface

        An unexpected XID-0 was received for a PU type 2.1 device from
        the sdlc link station specified."
    ::= { dlsNotificationsPrefix 76 }

dlsNotification77 NOTIFICATION-TYPE
    OBJECTS { 
              dls77_link_address, 
              dls77_interface 
            }
    STATUS current
    DESCRIPTION
        "Notification of Event DLS.77

        Message: 'no buffer for sdlc test for address $1 interface $2'

        Parameters list:
              $1: dls77_link_address
              $2: dls77_interface

        No buffer could be obtained for sending a test frame to
        an SDLC link station. The operation will be retried later."
    ::= { dlsNotificationsPrefix 77 }

dlsNotification78 NOTIFICATION-TYPE
    OBJECTS { 
              dls78_rtn_code, 
              dls78_link_address,
              dls78_interface 
            }
    STATUS current
    DESCRIPTION
        "Notification of Event DLS.78

        Message: 'unexpected return code from sdlc test request = $1 addr $2 interface $3'

        Parameters list:
              $1: dls78_rtn_code
              $2: dls78_link_address
              $3: dls78_interface

        The sdlc test request function returned an unexpected return code."
    ::= { dlsNotificationsPrefix 78 }

dlsNotification79 NOTIFICATION-TYPE
    OBJECTS { 
              dls79_link_address, 
              dls79_interface 
            }
    STATUS current
    DESCRIPTION
        "Notification of Event DLS.79

        Message: 'no buffer for sdlc xid0 for address $1 interface $2'

        Parameters list:
              $1: dls79_link_address
              $2: dls79_interface

        No buffer could be obtained for sending an xid0 frame to
        an SDLC link station. The operation will be retried later."
    ::= { dlsNotificationsPrefix 79 }

dlsNotification80 NOTIFICATION-TYPE
    OBJECTS { 
              dls80_link_address, 
              dls80_interface 
            }
    STATUS current
    DESCRIPTION
        "Notification of Event DLS.80

        Message: 'no buffer for sdlc null xid for address $1 interface $2'

        Parameters list:
              $1: dls80_link_address
              $2: dls80_interface

        No buffer could be obtained for sending a null xid frame to
        an SDLC link station. The operation will be retried later."
    ::= { dlsNotificationsPrefix 80 }

dlsNotification81 NOTIFICATION-TYPE
    OBJECTS { 
              dls81_rtn_code, 
              dls81_link_address,
              dls81_interface 
            }
    STATUS current
    DESCRIPTION
        "Notification of Event DLS.81

        Message: 'unexpected return code from sdlc I frame request = $1 address $2 interface $3'

        Parameters list:
              $1: dls81_rtn_code
              $2: dls81_link_address
              $3: dls81_interface

        The sdlc I frame request function returned an unexpected return code."
    ::= { dlsNotificationsPrefix 81 }

dlsNotification82 NOTIFICATION-TYPE
    OBJECTS { 
              dls82_rtn_code, 
              dls82_link_address,
              dls82_interface 
            }
    STATUS current
    DESCRIPTION
        "Notification of Event DLS.82

        Message: 'unexpected return code from sdlc UI frame request = $1 addr $2 interface $3'

        Parameters list:
              $1: dls82_rtn_code
              $2: dls82_link_address
              $3: dls82_interface

        The sdlc UI frame request function returned an unexpected return code."
    ::= { dlsNotificationsPrefix 82 }

dlsNotification83 NOTIFICATION-TYPE
    OBJECTS { 
              dls83_rtn_code, 
              dls83_link_address,
              dls83_interface 
            }
    STATUS current
    DESCRIPTION
        "Notification of Event DLS.83

        Message: 'unexpected return code from sdlc force rnr request = $1 addr $2 interface $3'

        Parameters list:
              $1: dls83_rtn_code
              $2: dls83_link_address
              $3: dls83_interface

        The sdlc force rnr request function returned an unexpected return code."
    ::= { dlsNotificationsPrefix 83 }

dlsNotification84 NOTIFICATION-TYPE
    OBJECTS { 
              dls84_link_address, 
              dls84_interface 
            }
    STATUS current
    DESCRIPTION
        "Notification of Event DLS.84

        Message: 'no buffer for sdlc data copy for address $1 interface $2'

        Parameters list:
              $1: dls84_link_address
              $2: dls84_interface

        No buffer could be obtained for copying a data buffer for queueing
        while congested. The existing buffer is queued."
    ::= { dlsNotificationsPrefix 84 }

dlsNotification85 NOTIFICATION-TYPE
    STATUS current
    DESCRIPTION
        "Notification of Event DLS.85

        Message: 'sdlc resend data received but no congestion block'

        An sdlc resend data indication was received, but no corresponding
        congestion control block was found. No operation takes place."
    ::= { dlsNotificationsPrefix 85 }

dlsNotification86 NOTIFICATION-TYPE
    OBJECTS { 
              dls86_reason, 
              dls86_link_address,
              dls86_interface 
            }
    STATUS current
    DESCRIPTION
        "Notification of Event DLS.86

        Message: 'sdlc disconnect received reason $1 for address $2 interface $3'

        Parameters list:
              $1: dls86_reason
              $2: dls86_link_address
              $3: dls86_interface

        The specified SDLC connection was disconnected due to an error detected
        by the SDLC protocol."
    ::= { dlsNotificationsPrefix 86 }

dlsNotification87 NOTIFICATION-TYPE
    OBJECTS { 
              dls87_link_address, 
              dls87_interface 
            }
    STATUS current
    DESCRIPTION
        "Notification of Event DLS.87

        Message: 'sdlc transition to null_xid_pend state for address $1 interface $2'

        Parameters list:
              $1: dls87_link_address
              $2: dls87_interface

        The sdlc link station specified is transitioning to NULL_XID_PENDING
        state, meaning that it is awaiting a response to a NULL XID
        that was sent."
    ::= { dlsNotificationsPrefix 87 }

dlsNotification88 NOTIFICATION-TYPE
    OBJECTS { 
              dls88_link_address, 
              dls88_interface 
            }
    STATUS current
    DESCRIPTION
        "Notification of Event DLS.88

        Message: 'sdlc transition to xid_0_pend state for address $1 interface $2'

        Parameters list:
              $1: dls88_link_address
              $2: dls88_interface

        The sdlc link station specified is transitioning to XID_0_PENDING state,
        meaning that it is awaiting a response to an XID-0 that was sent."
    ::= { dlsNotificationsPrefix 88 }

dlsNotification89 NOTIFICATION-TYPE
    OBJECTS { 
              dls89_address, 
              dls89_source_mac_address,
              dls89_dest_mac_address,
              dls89_source_sap,
              dls89_dest_sap 
            }
    STATUS current
    DESCRIPTION
        "Notification of Event DLS.89

        Message: 'DLS forwarder experience a session loss due to TCP connection to $1 break, origin MAC $2->Target MAC $3, origin SAP $4->Target SAP $5'

        Parameters list:
              $1: dls89_address
              $2: dls89_source_mac_address
              $3: dls89_dest_mac_address
              $4: dls89_source_sap
              $5: dls89_dest_sap

        TCP connection to the DLS neighbor went down. All the DLS sessions
        active on that TCP connection are brought down individually."
    ::= { dlsNotificationsPrefix 89 }

dlsNotification90 NOTIFICATION-TYPE
    OBJECTS { 
              dls90_type, 
              dls90_ip_address,
              dls90_source_mac_address,
              dls90_dest_mac_address,
              dls90_source_sap,
              dls90_dest_sap 
            }
    STATUS current
    DESCRIPTION
        "Notification of Event DLS.90

        Message: 'DLS forwarder received a SSP message of type $1 over TCP connection to $2 for $3->$4, sap $5->$6'

        Parameters list:
              $1: dls90_type
              $2: dls90_ip_address
              $3: dls90_source_mac_address
              $4: dls90_dest_mac_address
              $5: dls90_source_sap
              $6: dls90_dest_sap

        DLS forwarder received a Switch to Switch Protocol message of over TCP."
    ::= { dlsNotificationsPrefix 90 }

dlsNotification91 NOTIFICATION-TYPE
    OBJECTS { 
              dls91_ip_address 
            }
    STATUS current
    DESCRIPTION
        "Notification of Event DLS.91

        Message: 'DLS forwarder received an indication from TCP that connection to $1 has now become uncongested'

        Parameters list:
              $1: dls91_ip_address

        TCP connection to a DLS Peer was previously congested. It has now
        become uncongested so that DLS can resume sending data over that
        connection."
    ::= { dlsNotificationsPrefix 91 }

dlsNotification92 NOTIFICATION-TYPE
    OBJECTS { 
              dls92_type, 
              dls92_source_mac_address,
              dls92_dest_mac_address,
              dls92_source_sap,
              dls92_dest_sap 
            }
    STATUS current
    DESCRIPTION
        "Notification of Event DLS.92

        Message: 'DLS forwarder received a DLC event of type $1 for $2->$3, sap $4->$5'

        Parameters list:
              $1: dls92_type
              $2: dls92_source_mac_address
              $3: dls92_dest_mac_address
              $4: dls92_source_sap
              $5: dls92_dest_sap

        DLS forwarder received a DLC event from the underlying LINK which
        could be LLC or SDLC to either perform some service or as an
        acknowledgement to previously issued command."
    ::= { dlsNotificationsPrefix 92 }

dlsNotification93 NOTIFICATION-TYPE
    OBJECTS { 
              dls93_state, 
              dls93_state,
              dls93_source_mac_address,
              dls93_dest_mac_address,
              dls93_source_sap,
              dls93_dest_sap 
            }
    STATUS current
    DESCRIPTION
        "Notification of Event DLS.93

        Message: 'DLS forwarder is changing the state from $1 to $2 for the DLS session with data link id $3->$4, sap $5->$6'

        Parameters list:
              $1: dls93_state
              $2: dls93_state
              $3: dls93_source_mac_address
              $4: dls93_dest_mac_address
              $5: dls93_source_sap
              $6: dls93_dest_sap

        While processing an event, either an SSP message received over
        TCP or an event presented from underlying DLC, the associated
        DLS session is stepping into a new state."
    ::= { dlsNotificationsPrefix 93 }

dlsNotification94 NOTIFICATION-TYPE
    OBJECTS { 
              dls94_state, 
              dls94_source_mac_address,
              dls94_dest_mac_address,
              dls94_source_sap,
              dls94_dest_sap 
            }
    STATUS current
    DESCRIPTION
        "Notification of Event DLS.94

        Message: 'DLS forwarder received an event in bad state $1 for the DLS session with data link id $2->$3, sap $4->$5'

        Parameters list:
              $1: dls94_state
              $2: dls94_source_mac_address
              $3: dls94_dest_mac_address
              $4: dls94_source_sap
              $5: dls94_dest_sap

        While processing an event, either an SSP message received over
        TCP or an event presented from underlying DLC, the DLS state
        machine discovered the event occurring in an unexpected state."
    ::= { dlsNotificationsPrefix 94 }

dlsNotification95 NOTIFICATION-TYPE
    STATUS current
    DESCRIPTION
        "Notification of Event DLS.95

        Message: 'DLS session is absent inappropriately for the event received'

        While processing an event, either an SSP message received over
        TCP or an event presented from underlying DLC, the DLS state
        machine discovered that a valid session is absent which it should
        not be."
    ::= { dlsNotificationsPrefix 95 }

dlsNotification96 NOTIFICATION-TYPE
    STATUS current
    DESCRIPTION
        "Notification of Event DLS.96

        Message: 'DLS DLC_DL_STARTED event from underlying DLCST in circuit established or circuit restart state'

        DLS state machine received DLC_DL_STARTED event indication
        from the underlying LINK (LLC or SDLC) when the circuit has
        already been established. This could be the dribbling TEST
        responses coming in via bridge multi-path. Ignore them."
    ::= { dlsNotificationsPrefix 96 }

dlsNotification97 NOTIFICATION-TYPE
    STATUS current
    DESCRIPTION
        "Notification of Event DLS.97

        Message: 'DLS, No memory available to create DLS session'

        There is no memory available to allocate the resources that are
        required to create a DLS session."
    ::= { dlsNotificationsPrefix 97 }

dlsNotification98 NOTIFICATION-TYPE
    OBJECTS { 
              dls98_source_mac_address, 
              dls98_dest_mac_address,
              dls98_source_sap,
              dls98_dest_sap 
            }
    STATUS current
    DESCRIPTION
        "Notification of Event DLS.98

        Message: 'DLS, DLC_RESOLVE_C is firewalled for the DLS session with data link id $1->$2, sap $3->$4'

        Parameters list:
              $1: dls98_source_mac_address
              $2: dls98_dest_mac_address
              $3: dls98_source_sap
              $4: dls98_dest_sap

        The TEST command frame received from the underlying DATA LINK is
        being enqueued in the firewall queue. This is true for the case
        when there is already a CANUREACH SSP message dispatched and
        is awaiting for the ICANREACH response."
    ::= { dlsNotificationsPrefix 98 }

dlsNotification99 NOTIFICATION-TYPE
    OBJECTS { 
              dls99_source_mac_address, 
              dls99_dest_mac_address,
              dls99_source_sap,
              dls99_dest_sap 
            }
    STATUS current
    DESCRIPTION
        "Notification of Event DLS.99

        Message: 'DLS, Broadcast CANUREACH failed for the DLS session with data link id $1->$2, sap $3->$4'

        Parameters list:
              $1: dls99_source_mac_address
              $2: dls99_dest_mac_address
              $3: dls99_source_sap
              $4: dls99_dest_sap

        While processing TEST(c) for a given destination, DLS sends out
        a broadcast of CANUREACH to all DLS partner. If there is not a
        single TCP connection established between DLS partners, this
        operation will fail. In such event, DLS session is terminated."
    ::= { dlsNotificationsPrefix 99 }

dlsNotification100 NOTIFICATION-TYPE
    OBJECTS { 
              dls100_ip_address, 
              dls100_source_mac_address,
              dls100_dest_mac_address,
              dls100_source_sap,
              dls100_dest_sap 
            }
    STATUS current
    DESCRIPTION
        "Notification of Event DLS.100

        Message: 'DLS, Unidirected CANUREACH to $1 failed for $2->$3, sap $4->$5'

        Parameters list:
              $1: dls100_ip_address
              $2: dls100_source_mac_address
              $3: dls100_dest_mac_address
              $4: dls100_source_sap
              $5: dls100_dest_sap

        While processing TEST(c) for a given destination, DLS sends out
        a CANUREACH to specific DLS partner(s) if it knows that
        destination station is connected to one of its LAN. If this
        operation fails, for some difficulty within TCP connection, this
        event is produced. This does not necessarily result in
        termination of the DLS session as there can be success
        sending to other DLS partner."
    ::= { dlsNotificationsPrefix 100 }

dlsNotification101 NOTIFICATION-TYPE
    OBJECTS { 
              dls101_ip_address, 
              dls101_source_mac_address,
              dls101_dest_mac_address,
              dls101_source_sap,
              dls101_dest_sap 
            }
    STATUS current
    DESCRIPTION
        "Notification of Event DLS.101

        Message: 'DLS, Unidirected CANUREACH to $1 sent for $2->$3, sap $4->$5'

        Parameters list:
              $1: dls101_ip_address
              $2: dls101_source_mac_address
              $3: dls101_dest_mac_address
              $4: dls101_source_sap
              $5: dls101_dest_sap

        While processing TEST(c) for a given destination, DLS sent out
        a CANUREACH to specific DLS partner(s) if it knows that
        destination station is connected to one of its LAN."
    ::= { dlsNotificationsPrefix 101 }

dlsNotification102 NOTIFICATION-TYPE
    OBJECTS { 
              dls102_source_mac_address, 
              dls102_dest_mac_address,
              dls102_source_sap,
              dls102_dest_sap,
              dls102_phase 
            }
    STATUS current
    DESCRIPTION
        "Notification of Event DLS.102

        Message: 'DLS, Broadcast CANUREACH sent for $1->$2, sap $3->$4 exploring phase $5'

        Parameters list:
              $1: dls102_source_mac_address
              $2: dls102_dest_mac_address
              $3: dls102_source_sap
              $4: dls102_dest_sap
              $5: dls102_phase

        While processing TEST(c) for a given destination, DLS sent out
        broadcast CANUREACH to all the DLS partner(s) it has TCP
        connection established with.
        Exploring phases: (0) Broadcast to all DLS partner(s).
        (1) Broadcast to priorized DLS partner(s).
        (2) Broadcast to no priorized DLS partner(s)."
    ::= { dlsNotificationsPrefix 102 }

dlsNotification103 NOTIFICATION-TYPE
    STATUS current
    DESCRIPTION
        "Notification of Event DLS.103

        Message: 'DLS, No memory for to create address entry in cache table'

        There is no memory left to allocate the resources that are
        required to create an IP entry in the address table database."
    ::= { dlsNotificationsPrefix 103 }

dlsNotification104 NOTIFICATION-TYPE
    OBJECTS { 
              dls104_source_mac_address, 
              dls104_dest_mac_address,
              dls104_source_sap,
              dls104_dest_sap 
            }
    STATUS current
    DESCRIPTION
        "Notification of Event DLS.104

        Message: 'DLS, SAPs resolved for $1->$2, sap $3->$4'

        Parameters list:
              $1: dls104_source_mac_address
              $2: dls104_dest_mac_address
              $3: dls104_source_sap
              $4: dls104_dest_sap

        DLS connection can get established without using the specific
        SAPs, for example, SAP 0 as DSAP or SSAP. However, when the
        specific SAPs are used, the same connection's SAPs are updated."
    ::= { dlsNotificationsPrefix 104 }

dlsNotification105 NOTIFICATION-TYPE
    STATUS current
    DESCRIPTION
        "Notification of Event DLS.105

        Message: 'DLS, No memory for to create IP entry in cache table'

        There is no memory left to allocate the resources that are
        required to create an IP entry in the address table database."
    ::= { dlsNotificationsPrefix 105 }

dlsNotification106 NOTIFICATION-TYPE
    OBJECTS { 
              dls106_source_mac_address, 
              dls106_dest_mac_address,
              dls106_source_sap,
              dls106_dest_sap 
            }
    STATUS current
    DESCRIPTION
        "Notification of Event DLS.106

        Message: 'DLS, received CANUREACH could not be processed by any DLC for $1->$2, sap $3->$4'

        Parameters list:
              $1: dls106_source_mac_address
              $2: dls106_dest_mac_address
              $3: dls106_source_sap
              $4: dls106_dest_sap

        A CANUREACH SSP message we received over the TCP from a DLS Peer.
        However, none of the underlying data link layer, SDLC or LLC, could
        translate this to a TEST(c) frame."
    ::= { dlsNotificationsPrefix 106 }

dlsNotification107 NOTIFICATION-TYPE
    OBJECTS { 
              dls107_ip_address, 
              dls107_mac_address 
            }
    STATUS current
    DESCRIPTION
        "Notification of Event DLS.107

        Message: 'DLS, Learning new MAC-IP association from $1 for $2'

        Parameters list:
              $1: dls107_ip_address
              $2: dls107_mac_address

        DLS is learning New MAC and IP association from an SSP message
        received from the peer DLS. This typically occurs during CANUREACH
        or ICANREACH message receipt time."
    ::= { dlsNotificationsPrefix 107 }

dlsNotification108 NOTIFICATION-TYPE
    OBJECTS { 
              dls108_ip_address, 
              dls108_mac_address 
            }
    STATUS current
    DESCRIPTION
        "Notification of Event DLS.108

        Message: 'DLS, unsolicited ICANREACH message, from $1 for $2, Ignored'

        Parameters list:
              $1: dls108_ip_address
              $2: dls108_mac_address

        DLS has received an unanticipated ICANREACH message. ICANREACH SSP
        message is usually expected only as a response to an CANUREACH SSP
        message sent earlier. The DLS state machine will not process this
        message. However, it still will go ahead and learn the IP address
        and MAC address association."
    ::= { dlsNotificationsPrefix 108 }

dlsNotification109 NOTIFICATION-TYPE
    OBJECTS { 
              dls109_ip_address, 
              dls109_mac_address 
            }
    STATUS current
    DESCRIPTION
        "Notification of Event DLS.109

        Message: 'DLS, secondary ICANREACH message, from $1 for $2, Ignored'

        Parameters list:
              $1: dls109_ip_address
              $2: dls109_mac_address

        DLS has received a secondary ICANREACH message from other
        DLS peer(s) which also claims reachability to the MAC address
        via him(them). This is normal. The DLS state machine takes note
        of these DLS peers, But no further communication takes place."
    ::= { dlsNotificationsPrefix 109 }

dlsNotification110 NOTIFICATION-TYPE
    OBJECTS { 
              dls110_mac_address 
            }
    STATUS current
    DESCRIPTION
        "Notification of Event DLS.110

        Message: 'DLS, Flushing Firewall Queue to $1'

        Parameters list:
              $1: dls110_mac_address

        DLS has received an ICANREACH message from one or more DLS
        peers. This has triggered sending of pending CANUREACH to the
        same destination MAC address. These messages were present in
        the firewall queue."
    ::= { dlsNotificationsPrefix 110 }

dlsNotification111 NOTIFICATION-TYPE
    OBJECTS { 
              dls111_message_type, 
              dls111_ip_address,
              dls111_source_mac_address,
              dls111_dest_mac_address,
              dls111_source_sap,
              dls111_dest_sap 
            }
    STATUS current
    DESCRIPTION
        "Notification of Event DLS.111

        Message: 'DLS, $1 to $2 sent for $3->$4, sap $5->$6'

        Parameters list:
              $1: dls111_message_type
              $2: dls111_ip_address
              $3: dls111_source_mac_address
              $4: dls111_dest_mac_address
              $5: dls111_source_sap
              $6: dls111_dest_sap

        DLS successfully sent out an SSP message over TCP to its DLS peer."
    ::= { dlsNotificationsPrefix 111 }

dlsNotification112 NOTIFICATION-TYPE
    OBJECTS { 
              dls112_message_type, 
              dls112_ip_address,
              dls112_source_mac_address,
              dls112_dest_mac_address,
              dls112_source_sap,
              dls112_dest_sap 
            }
    STATUS current
    DESCRIPTION
        "Notification of Event DLS.112

        Message: 'DLS, FAILED to send $1 to $2 for $3->$4, sap $5->$6'

        Parameters list:
              $1: dls112_message_type
              $2: dls112_ip_address
              $3: dls112_source_mac_address
              $4: dls112_dest_mac_address
              $5: dls112_source_sap
              $6: dls112_dest_sap

        Due to some problems with TCP connection to its DLS peer, an
        SSP control message could not be sent out."
    ::= { dlsNotificationsPrefix 112 }

dlsNotification113 NOTIFICATION-TYPE
    OBJECTS { 
              dls113_Sap 
            }
    STATUS current
    DESCRIPTION
        "Notification of Event DLS.113

        Message: 'LLC, Initialization FAILED for SAP $1'

        Parameters list:
              $1: dls113_Sap

        Due to some problems, SAP initialization with LLC failed."
    ::= { dlsNotificationsPrefix 113 }

dlsNotification114 NOTIFICATION-TYPE
    OBJECTS { 
              dls114_Sap, 
              dls114_reason 
            }
    STATUS current
    DESCRIPTION
        "Notification of Event DLS.114

        Message: 'LLC, parameter validation FAILED for SAP $1, rsn = $2'

        Parameters list:
              $1: dls114_Sap
              $2: dls114_reason

        LLC tunable parameters are out of range."
    ::= { dlsNotificationsPrefix 114 }

dlsNotification115 NOTIFICATION-TYPE
    OBJECTS { 
              dls115_Sap 
            }
    STATUS current
    DESCRIPTION
        "Notification of Event DLS.115

        Message: 'LLC, No Memory for SAP control block for SAP $1'

        Parameters list:
              $1: dls115_Sap

        No memory available for the SAP control block."
    ::= { dlsNotificationsPrefix 115 }

dlsNotification116 NOTIFICATION-TYPE
    OBJECTS { 
              dls116_Sap, 
              dls116_reason 
            }
    STATUS current
    DESCRIPTION
        "Notification of Event DLS.116

        Message: 'LLC, Opening of SAP $1 FAILED, rsn = $2'

        Parameters list:
              $1: dls116_Sap
              $2: dls116_reason

        Opening of SAP failed due to problems in the LLC.
        Reason code is indicative of the specific problem."
    ::= { dlsNotificationsPrefix 116 }

dlsNotification117 NOTIFICATION-TYPE
    OBJECTS { 
              dls117_Sap 
            }
    STATUS current
    DESCRIPTION
        "Notification of Event DLS.117

        Message: 'LLC, Closing SAP $1'

        Parameters list:
              $1: dls117_Sap

        Closing SAP with the LLC."
    ::= { dlsNotificationsPrefix 117 }

dlsNotification118 NOTIFICATION-TYPE
    OBJECTS { 
              dls118_Destination, 
              dls118_Source,
              dls118_Dsap,
              dls118_Ssap 
            }
    STATUS current
    DESCRIPTION
        "Notification of Event DLS.118

        Message: 'LLC, FAILED open stn, invalid sapcb, dst=$1, src=$2, dsap=$3, ssap=$4'

        Parameters list:
              $1: dls118_Destination
              $2: dls118_Source
              $3: dls118_Dsap
              $4: dls118_Ssap

        Opening of station for LLC data link services failed because
        the SAP under which station to be opened is invalid."
    ::= { dlsNotificationsPrefix 118 }

dlsNotification119 NOTIFICATION-TYPE
    OBJECTS { 
              dls119_Destination, 
              dls119_Source,
              dls119_Dsap,
              dls119_Ssap 
            }
    STATUS current
    DESCRIPTION
        "Notification of Event DLS.119

        Message: 'LLC, FAILED open stn, No memory, dst=$1, src=$2, dsap=$3, ssap=$4'

        Parameters list:
              $1: dls119_Destination
              $2: dls119_Source
              $3: dls119_Dsap
              $4: dls119_Ssap

        Opening of station for LLC data link services failed because
        there is no memory available to create control block to manage
        the connection."
    ::= { dlsNotificationsPrefix 119 }

dlsNotification120 NOTIFICATION-TYPE
    OBJECTS { 
              dls120_Reason, 
              dls120_Destination,
              dls120_Source,
              dls120_Dsap,
              dls120_Ssap 
            }
    STATUS current
    DESCRIPTION
        "Notification of Event DLS.120

        Message: 'LLC, FAILED open stn, rsn=$1, dst=$2, src=$3, dsap=$4, ssap=$5'

        Parameters list:
              $1: dls120_Reason
              $2: dls120_Destination
              $3: dls120_Source
              $4: dls120_Dsap
              $5: dls120_Ssap

        Opening of station for LLC data link services failed due to
        some problems within LLC. The reason code is indicative of
        the specific problem."
    ::= { dlsNotificationsPrefix 120 }

dlsNotification121 NOTIFICATION-TYPE
    OBJECTS { 
              dls121_Destination, 
              dls121_Source,
              dls121_Dsap,
              dls121_Ssap 
            }
    STATUS current
    DESCRIPTION
        "Notification of Event DLS.121

        Message: 'LLC, opened stn, dst=$1, src=$2, dsap=$3, ssap=$4'

        Parameters list:
              $1: dls121_Destination
              $2: dls121_Source
              $3: dls121_Dsap
              $4: dls121_Ssap

        Opening of station for LLC data link services succeeded."
    ::= { dlsNotificationsPrefix 121 }

dlsNotification122 NOTIFICATION-TYPE
    STATUS current
    DESCRIPTION
        "Notification of Event DLS.122

        Message: 'LLC, open station failed during XCHANGE'

        Opening of station for LLC data link services failed during
        exchange operation. Exchange operation involves opening an
        already opened station for LLC services under a different SAP.
        The reason of failure is reported earlier."
    ::= { dlsNotificationsPrefix 122 }

dlsNotification123 NOTIFICATION-TYPE
    OBJECTS { 
              dls123_Destination, 
              dls123_Source,
              dls123_Dsap,
              dls123_Ssap 
            }
    STATUS current
    DESCRIPTION
        "Notification of Event DLS.123

        Message: 'LLC, exchange station succeeded for destination=$1, source=$2, dsap=$3, ssap=$4'

        Parameters list:
              $1: dls123_Destination
              $2: dls123_Source
              $3: dls123_Dsap
              $4: dls123_Ssap

        Exchange of station for LLC data link services succeeded.
        Exchange operation involves opening an already opened station
        for LLC services under a different SAP."
    ::= { dlsNotificationsPrefix 123 }

dlsNotification124 NOTIFICATION-TYPE
    OBJECTS { 
              dls124_source_mac_address, 
              dls124_dest_mac_address,
              dls124_source_sap,
              dls124_dest_sap 
            }
    STATUS current
    DESCRIPTION
        "Notification of Event DLS.124

        Message: 'LLC, closed stn by force $1->$2, sap $3->$4'

        Parameters list:
              $1: dls124_source_mac_address
              $2: dls124_dest_mac_address
              $3: dls124_source_sap
              $4: dls124_dest_sap

        Closed station by force for LLC data link services."
    ::= { dlsNotificationsPrefix 124 }

dlsNotification125 NOTIFICATION-TYPE
    OBJECTS { 
              dls125_source_mac_address, 
              dls125_dest_mac_address,
              dls125_source_sap,
              dls125_dest_sap 
            }
    STATUS current
    DESCRIPTION
        "Notification of Event DLS.125

        Message: 'LLC, closed stn quietly $1->$2, sap $3->$4'

        Parameters list:
              $1: dls125_source_mac_address
              $2: dls125_dest_mac_address
              $3: dls125_source_sap
              $4: dls125_dest_sap

        Closed station quietly for LLC data link services."
    ::= { dlsNotificationsPrefix 125 }

dlsNotification126 NOTIFICATION-TYPE
    OBJECTS { 
              dls126_action, 
              dls126_reason,
              dls126_source_mac_address,
              dls126_dest_mac_address,
              dls126_source_sap,
              dls126_dest_sap 
            }
    STATUS current
    DESCRIPTION
        "Notification of Event DLS.126

        Message: 'LLC, $1 Send failed  rsn=$2, $3->$4, sap $5->$6'

        Parameters list:
              $1: dls126_action
              $2: dls126_reason
              $3: dls126_source_mac_address
              $4: dls126_dest_mac_address
              $5: dls126_source_sap
              $6: dls126_dest_sap

        LLC was unsuccessful in sending out a frame. The reason
        indicative of the specific problem."
    ::= { dlsNotificationsPrefix 126 }

dlsNotification127 NOTIFICATION-TYPE
    OBJECTS { 
              dls127_action, 
              dls127_source_mac_address,
              dls127_dest_mac_address,
              dls127_source_sap,
              dls127_dest_sap 
            }
    STATUS current
    DESCRIPTION
        "Notification of Event DLS.127

        Message: 'LLC, $1 became busy after sending, $2->$3, sap $4->$5'

        Parameters list:
              $1: dls127_action
              $2: dls127_source_mac_address
              $3: dls127_dest_mac_address
              $4: dls127_source_sap
              $5: dls127_dest_sap

        LLC became busy after sending out a frame. This busyness
        is an honor system and the frame submitted to LLC does
        get accepted for sending. However, DLS takes note of
        this condition and refrains from sending more frames."
    ::= { dlsNotificationsPrefix 127 }

dlsNotification128 NOTIFICATION-TYPE
    OBJECTS { 
              dls128_source_mac_address, 
              dls128_dest_mac_address,
              dls128_source_sap,
              dls128_dest_sap 
            }
    STATUS current
    DESCRIPTION
        "Notification of Event DLS.128

        Message: 'LLC BUSY, enqueue frame to pend queue, $1->$2, sap $3->$4'

        Parameters list:
              $1: dls128_source_mac_address
              $2: dls128_dest_mac_address
              $3: dls128_source_sap
              $4: dls128_dest_sap

        LLC is busy, frames received from TCP are being enqueued to
        the pending queue for that LLC session. When LLC exits busy
        condition, all the frames from the pending queue will be flushed."
    ::= { dlsNotificationsPrefix 128 }

dlsNotification129 NOTIFICATION-TYPE
    OBJECTS { 
              dls129_message_type, 
              dls129_source_mac_address,
              dls129_dest_mac_address,
              dls129_source_sap,
              dls129_dest_sap 
            }
    STATUS current
    DESCRIPTION
        "Notification of Event DLS.129

        Message: 'LLC, $1 frame sent, $2->$3, sap $4->$5'

        Parameters list:
              $1: dls129_message_type
              $2: dls129_source_mac_address
              $3: dls129_dest_mac_address
              $4: dls129_source_sap
              $5: dls129_dest_sap

        A frame received from DLS cloud was successfully sent to an
        LLC end station."
    ::= { dlsNotificationsPrefix 129 }

dlsNotification130 NOTIFICATION-TYPE
    OBJECTS { 
              dls130_source_mac_address, 
              dls130_dest_mac_address,
              dls130_source_sap,
              dls130_dest_sap 
            }
    STATUS current
    DESCRIPTION
        "Notification of Event DLS.130

        Message: 'LLC, frame not proc, $1->$2, sap $3->$4'

        Parameters list:
              $1: dls130_source_mac_address
              $2: dls130_dest_mac_address
              $3: dls130_source_sap
              $4: dls130_dest_sap

        Frame was not processed by the DLS as the SAP, as well as
        the station was not opened for LLC data link services."
    ::= { dlsNotificationsPrefix 130 }

dlsNotification131 NOTIFICATION-TYPE
    OBJECTS { 
              dls131_interface, 
              dls131_source_mac_address,
              dls131_dest_mac_address,
              dls131_source_sap,
              dls131_dest_sap 
            }
    STATUS current
    DESCRIPTION
        "Notification of Event DLS.131

        Message: 'LLC, frame refused, NOT switching for ifc $1, $2->$3, sap $4->$5'

        Parameters list:
              $1: dls131_interface
              $2: dls131_source_mac_address
              $3: dls131_dest_mac_address
              $4: dls131_source_sap
              $5: dls131_dest_sap

        Frame was not processed by the DLS as the DSAP of the frame
        is not configured to be switched for the interface on which the frame
        was received."
    ::= { dlsNotificationsPrefix 131 }

dlsNotification132 NOTIFICATION-TYPE
    OBJECTS { 
              dls132_frame_type, 
              dls132_source_mac_address,
              dls132_dest_mac_address,
              dls132_source_sap,
              dls132_dest_sap 
            }
    STATUS current
    DESCRIPTION
        "Notification of Event DLS.132

        Message: 'LLC, $1 frame refused by st mch, $2->$3, sap $4->$5'

        Parameters list:
              $1: dls132_frame_type
              $2: dls132_source_mac_address
              $3: dls132_dest_mac_address
              $4: dls132_source_sap
              $5: dls132_dest_sap

        Frame was not processed by the DLS-LLC interface modules
        state machine as it could not be successfully relayed via
        DLS. This instance is normal for TEST command frame as DLS
        copies the frame and still refuses the frame so that it
        can also be sent via the bridge path."
    ::= { dlsNotificationsPrefix 132 }

dlsNotification133 NOTIFICATION-TYPE
    OBJECTS { 
              dls133_eventtype, 
              dls133_source_mac_address,
              dls133_dest_mac_address,
              dls133_source_sap,
              dls133_dest_sap 
            }
    STATUS current
    DESCRIPTION
        "Notification of Event DLS.133

        Message: 'LLC, $1 event not proc, $2->$3, sap $4->$5'

        Parameters list:
              $1: dls133_eventtype
              $2: dls133_source_mac_address
              $3: dls133_dest_mac_address
              $4: dls133_source_sap
              $5: dls133_dest_sap

        LLC event was not processed."
    ::= { dlsNotificationsPrefix 133 }

dlsNotification134 NOTIFICATION-TYPE
    OBJECTS { 
              dls134_llcevent 
            }
    STATUS current
    DESCRIPTION
        "Notification of Event DLS.134

        Message: 'LLC, $1 event not proc, handle is bad'

        Parameters list:
              $1: dls134_llcevent

        An LLC event was not processed by the DLS as the handle
        by the LLC to DLS was bad."
    ::= { dlsNotificationsPrefix 134 }

dlsNotification135 NOTIFICATION-TYPE
    OBJECTS { 
              dls135_llcevent, 
              dls135_source_mac_address,
              dls135_dest_mac_address,
              dls135_source_sap,
              dls135_dest_sap 
            }
    STATUS current
    DESCRIPTION
        "Notification of Event DLS.135

        Message: 'LLC, $1 unknown event, not proc for $2->$3, sap $4->$5'

        Parameters list:
              $1: dls135_llcevent
              $2: dls135_source_mac_address
              $3: dls135_dest_mac_address
              $4: dls135_source_sap
              $5: dls135_dest_sap

        An unrecognizable LLC event occurred. This event is not processed."
    ::= { dlsNotificationsPrefix 135 }

dlsNotification136 NOTIFICATION-TYPE
    OBJECTS { 
              dls136_llcevent, 
              dls136_source_mac_address,
              dls136_dest_mac_address,
              dls136_source_sap,
              dls136_dest_sap 
            }
    STATUS current
    DESCRIPTION
        "Notification of Event DLS.136

        Message: 'LLC, $1 req not proc, inv handle, for $2->$3, sap $4->$5'

        Parameters list:
              $1: dls136_llcevent
              $2: dls136_source_mac_address
              $3: dls136_dest_mac_address
              $4: dls136_source_sap
              $5: dls136_dest_sap

        An LLC request from DLS was not processed by the LLC interface
        module as the handle passed from DLS is bad."
    ::= { dlsNotificationsPrefix 136 }

dlsNotification137 NOTIFICATION-TYPE
    OBJECTS { 
              dls137_source_mac_address, 
              dls137_dest_mac_address,
              dls137_source_sap,
              dls137_dest_sap 
            }
    STATUS current
    DESCRIPTION
        "Notification of Event DLS.137

        Message: 'LLC, not enabled, start_dl not honored, for $1->$2, sap $3->$4'

        Parameters list:
              $1: dls137_source_mac_address
              $2: dls137_dest_mac_address
              $3: dls137_source_sap
              $4: dls137_dest_sap

        A START_DL request from DLS to LLC interface module was not
        honored as LLC portion of the DLS is not enabled. This is not
        an error. When a CANUREACH is received, DLS will issue START_DL
        request to data link service interface modules. If they are not
        configured to switch for the SAP or not configured at all, it
        is common to discard such request."
    ::= { dlsNotificationsPrefix 137 }

dlsNotification138 NOTIFICATION-TYPE
    OBJECTS { 
              dls138_source_mac_address, 
              dls138_dest_mac_address,
              dls138_source_sap,
              dls138_dest_sap 
            }
    STATUS current
    DESCRIPTION
        "Notification of Event DLS.138

        Message: 'LLC, START_DL discard as error happened during open station operation, for $1->$2, sap $3->$4'

        Parameters list:
              $1: dls138_source_mac_address
              $2: dls138_dest_mac_address
              $3: dls138_source_sap
              $4: dls138_dest_sap

        A START_DL request from DLS to LLC interface module was not
        honored as data link station could not be opened with LLC."
    ::= { dlsNotificationsPrefix 138 }

dlsNotification139 NOTIFICATION-TYPE
    OBJECTS { 
              dls139_source_mac_address, 
              dls139_dest_mac_address,
              dls139_source_sap,
              dls139_dest_sap 
            }
    STATUS current
    DESCRIPTION
        "Notification of Event DLS.139

        Message: 'LLC, XID discard as error happened during exchange operation, for $1->$2, sap $3->$4'

        Parameters list:
              $1: dls139_source_mac_address
              $2: dls139_dest_mac_address
              $3: dls139_source_sap
              $4: dls139_dest_sap

        When the first XID is received, the real SAPs get resolved.
        During this time, data link station is opened with LLC and
        resources get exchanged from data link station opened with
        NULL SAP. This exchange operation has failed and therefore
        XID is not processed."
    ::= { dlsNotificationsPrefix 139 }

dlsNotification140 NOTIFICATION-TYPE
    OBJECTS { 
              dls140_source_mac_address, 
              dls140_dest_mac_address,
              dls140_source_sap,
              dls140_dest_sap 
            }
    STATUS current
    DESCRIPTION
        "Notification of Event DLS.140

        Message: 'LLC, XID discard as new SAP can not be found/opend, for $1->$2, sap $3->$4'

        Parameters list:
              $1: dls140_source_mac_address
              $2: dls140_dest_mac_address
              $3: dls140_source_sap
              $4: dls140_dest_sap

        When the first XID is received, the real SAPs get resolved.
        During this time, DLS's interface module to LLC verifies the
        SAP for which XID is received. If SAP can not be found or
        can not be opened for some reason, XID processing is
        discontinued."
    ::= { dlsNotificationsPrefix 140 }

dlsNotification141 NOTIFICATION-TYPE
    OBJECTS { 
              dls141_message_type, 
              dls141_source_mac_address,
              dls141_dest_mac_address,
              dls141_source_sap,
              dls141_dest_sap 
            }
    STATUS current
    DESCRIPTION
        "Notification of Event DLS.141

        Message: 'LLC, event $1 received for $2->$3, sap $4->$5'

        Parameters list:
              $1: dls141_message_type
              $2: dls141_source_mac_address
              $3: dls141_dest_mac_address
              $4: dls141_source_sap
              $5: dls141_dest_sap

        LLC interface module for the DLS received an event from either
        LLC or DLS."
    ::= { dlsNotificationsPrefix 141 }

dlsNotification142 NOTIFICATION-TYPE
    OBJECTS { 
              dls142_eventname, 
              dls142_statename,
              dls142_source_mac_address,
              dls142_dest_mac_address,
              dls142_source_sap,
              dls142_dest_sap 
            }
    STATUS current
    DESCRIPTION
        "Notification of Event DLS.142

        Message: 'LLC event $1 received in bad state $2, $3->$4, sap $5->$6'

        Parameters list:
              $1: dls142_eventname
              $2: dls142_statename
              $3: dls142_source_mac_address
              $4: dls142_dest_mac_address
              $5: dls142_source_sap
              $6: dls142_dest_sap

        DLS interface to LLC received an event in the bad state."
    ::= { dlsNotificationsPrefix 142 }

dlsNotification143 NOTIFICATION-TYPE
    OBJECTS { 
              dls143_oldstate, 
              dls143_newstate,
              dls143_source_mac_address,
              dls143_dest_mac_address,
              dls143_source_sap,
              dls143_dest_sap 
            }
    STATUS current
    DESCRIPTION
        "Notification of Event DLS.143

        Message: 'LLC Change state $1->$2 for $3->$4, sap $5->$6'

        Parameters list:
              $1: dls143_oldstate
              $2: dls143_newstate
              $3: dls143_source_mac_address
              $4: dls143_dest_mac_address
              $5: dls143_source_sap
              $6: dls143_dest_sap

        LLC interface module for the DLS is changing state as a
        result of processing an event either from LLC or DLS."
    ::= { dlsNotificationsPrefix 143 }

dlsNotification144 NOTIFICATION-TYPE
    OBJECTS { 
              dls144_source_mac_address, 
              dls144_dest_mac_address,
              dls144_source_sap,
              dls144_dest_sap 
            }
    STATUS current
    DESCRIPTION
        "Notification of Event DLS.144

        Message: 'LLC Secondary TEST_R is ignored, for $1->$2, sap $3->$4'

        Parameters list:
              $1: dls144_source_mac_address
              $2: dls144_dest_mac_address
              $3: dls144_source_sap
              $4: dls144_dest_sap

        In Multipath bridge environment, it is possible to receive
        multiple responses to the TEST command sent earlier. The
        LLC interface module discards such TEST responses."
    ::= { dlsNotificationsPrefix 144 }

dlsNotification145 NOTIFICATION-TYPE
    OBJECTS { 
              dls145_source_mac_address, 
              dls145_dest_mac_address,
              dls145_source_sap,
              dls145_dest_sap 
            }
    STATUS current
    DESCRIPTION
        "Notification of Event DLS.145

        Message: 'LLC, XID from LLC disc, NULL_SAPCB not found, for $1->$2, sap $3->$4'

        Parameters list:
              $1: dls145_source_mac_address
              $2: dls145_dest_mac_address
              $3: dls145_source_sap
              $4: dls145_dest_sap

        When the first XID is received, the real SAPs get resolved.
        The LLC interface module DLS first tries to locate the
        SAP control block for NULL SAP so that it can search for
        an open data link connection within this SAP. The SAP
        control block to NULL SAP could not be found and hence this
        frame does not get processed."
    ::= { dlsNotificationsPrefix 145 }

dlsNotification146 NOTIFICATION-TYPE
    OBJECTS { 
              dls146_source_mac_address, 
              dls146_dest_mac_address,
              dls146_source_sap,
              dls146_dest_sap 
            }
    STATUS current
    DESCRIPTION
        "Notification of Event DLS.146

        Message: 'LLC, XID from LLC disc as stn can not be opened, for $1->$2, sap $3->$4'

        Parameters list:
              $1: dls146_source_mac_address
              $2: dls146_dest_mac_address
              $3: dls146_source_sap
              $4: dls146_dest_sap

        When the first XID is received, the real SAPs get resolved.
        During this time, DLS's interface module to LLC opens a new
        data link connection on the real SAP. Wel, this operation
        failed."
    ::= { dlsNotificationsPrefix 146 }

dlsNotification147 NOTIFICATION-TYPE
    OBJECTS { 
              dls147_source_mac_address, 
              dls147_dest_mac_address,
              dls147_source_sap,
              dls147_dest_sap 
            }
    STATUS current
    DESCRIPTION
        "Notification of Event DLS.147

        Message: 'LLC, XID from LLC is discarded as error occurred during exchange operation, for $1->$2, sap $3->$4'

        Parameters list:
              $1: dls147_source_mac_address
              $2: dls147_dest_mac_address
              $3: dls147_source_sap
              $4: dls147_dest_sap

        When the first XID is received, the real SAPs get resolved.
        During this time, data link station is opened with LLC and
        resources gets exchanged from data link station opened with
        NULL SAP. This exchange operation has failed and therefore
        XID from LLC is not processed."
    ::= { dlsNotificationsPrefix 147 }

dlsNotification148 NOTIFICATION-TYPE
    OBJECTS { 
              dls148_frametype, 
              dls148_source_mac_address,
              dls148_dest_mac_address,
              dls148_source_sap,
              dls148_dest_sap 
            }
    STATUS current
    DESCRIPTION
        "Notification of Event DLS.148

        Message: 'LLC, $1 from LLC disc TCP is busy, for $2->$3, sap $4->$5'

        Parameters list:
              $1: dls148_frametype
              $2: dls148_source_mac_address
              $3: dls148_dest_mac_address
              $4: dls148_source_sap
              $5: dls148_dest_sap

        The data frames received from the LLC is being discarded by
        the LLC interface module as TCP connection is congested."
    ::= { dlsNotificationsPrefix 148 }

dlsNotification149 NOTIFICATION-TYPE
    OBJECTS { 
              dls149_event_type, 
              dls149_source_mac_address,
              dls149_dest_mac_address,
              dls149_source_sap,
              dls149_dest_sap 
            }
    STATUS current
    DESCRIPTION
        "Notification of Event DLS.149

        Message: 'LLC, event $1 received for $2->$3, sap $4->$5'

        Parameters list:
              $1: dls149_event_type
              $2: dls149_source_mac_address
              $3: dls149_dest_mac_address
              $4: dls149_source_sap
              $5: dls149_dest_sap

        LLC interface module for the DLS received an event from either
        LLC or DLS."
    ::= { dlsNotificationsPrefix 149 }

dlsNotification150 NOTIFICATION-TYPE
    OBJECTS { 
              dls150_event_type, 
              dls150_source_mac_address,
              dls150_dest_mac_address,
              dls150_source_sap,
              dls150_dest_sap 
            }
    STATUS current
    DESCRIPTION
        "Notification of Event DLS.150

        Message: 'DLS forwarder received a DLC event of type $1 for $2->$3, sap $4->$5'

        Parameters list:
              $1: dls150_event_type
              $2: dls150_source_mac_address
              $3: dls150_dest_mac_address
              $4: dls150_source_sap
              $5: dls150_dest_sap

        DLS forwarder received a DLC event from the underlying LINK which
        could be LLC or SDLC to either perform some service or as an
        acknowledgement to previously issued command."
    ::= { dlsNotificationsPrefix 150 }

dlsNotification151 NOTIFICATION-TYPE
    OBJECTS { 
              dls151_message_type, 
              dls151_ip_address,
              dls151_source_mac_address,
              dls151_dest_mac_address,
              dls151_source_sap,
              dls151_dest_sap 
            }
    STATUS current
    DESCRIPTION
        "Notification of Event DLS.151

        Message: 'DLS, $1 to $2 sent for $3->$4, sap $5->$6'

        Parameters list:
              $1: dls151_message_type
              $2: dls151_ip_address
              $3: dls151_source_mac_address
              $4: dls151_dest_mac_address
              $5: dls151_source_sap
              $6: dls151_dest_sap

        DLS successfully sent out an SSP message over TCP to its DLS peer."
    ::= { dlsNotificationsPrefix 151 }

dlsNotification152 NOTIFICATION-TYPE
    OBJECTS { 
              dls152_message_type, 
              dls152_ip_address,
              dls152_source_mac_address,
              dls152_dest_mac_address,
              dls152_source_sap,
              dls152_dest_sap 
            }
    STATUS current
    DESCRIPTION
        "Notification of Event DLS.152

        Message: 'DLS forwarder received a SSP message of type $1 over TCP connection to $2 for $3->$4, sap $5->$6'

        Parameters list:
              $1: dls152_message_type
              $2: dls152_ip_address
              $3: dls152_source_mac_address
              $4: dls152_dest_mac_address
              $5: dls152_source_sap
              $6: dls152_dest_sap

        DLS forwarder received a Switch to Switch Protocol message of over TCP."
    ::= { dlsNotificationsPrefix 152 }

dlsNotification153 NOTIFICATION-TYPE
    OBJECTS { 
              dls153_frame_type, 
              dls153_source_mac_address,
              dls153_dest_mac_address,
              dls153_source_sap,
              dls153_dest_sap 
            }
    STATUS current
    DESCRIPTION
        "Notification of Event DLS.153

        Message: 'LLC, $1 frame sent, $2->$3, sap $4->$5'

        Parameters list:
              $1: dls153_frame_type
              $2: dls153_source_mac_address
              $3: dls153_dest_mac_address
              $4: dls153_source_sap
              $5: dls153_dest_sap

        A frame received from DLS cloud was successfully sent to an
        LLC end station."
    ::= { dlsNotificationsPrefix 153 }

dlsNotification154 NOTIFICATION-TYPE
    OBJECTS { 
              dls154_frame_type, 
              dls154_source_mac_address,
              dls154_dest_mac_address,
              dls154_source_sap,
              dls154_dest_sap 
            }
    STATUS current
    DESCRIPTION
        "Notification of Event DLS.154

        Message: 'LLC, $1 frame drpped, $2->$3, sap $4->$5 prt nt up'

        Parameters list:
              $1: dls154_frame_type
              $2: dls154_source_mac_address
              $3: dls154_dest_mac_address
              $4: dls154_source_sap
              $5: dls154_dest_sap

        A frame received from DLS cloud was not successfully sent -
        bridge port not up."
    ::= { dlsNotificationsPrefix 154 }

dlsNotification155 NOTIFICATION-TYPE
    OBJECTS { 
              dls155_message_type, 
              dls155_ip_address,
              dls155_source_mac_address,
              dls155_dest_mac_address,
              dls155_source_sap,
              dls155_dest_sap 
            }
    STATUS current
    DESCRIPTION
        "Notification of Event DLS.155

        Message: 'DLS, FAILED to send $1 to $2 for $3->$4, sap $5->$6'

        Parameters list:
              $1: dls155_message_type
              $2: dls155_ip_address
              $3: dls155_source_mac_address
              $4: dls155_dest_mac_address
              $5: dls155_source_sap
              $6: dls155_dest_sap

        Due to some problems with TCP connection to its DLS peer, an
        SSP control message could not be sent out."
    ::= { dlsNotificationsPrefix 155 }

dlsNotification156 NOTIFICATION-TYPE
    OBJECTS { 
              dls156_count, 
              dls156_source_mac_address,
              dls156_dest_mac_address,
              dls156_source_sap,
              dls156_dest_sap 
            }
    STATUS current
    DESCRIPTION
        "Notification of Event DLS.156

        Message: 'DLS session pool of $1 bytes created for origin MAC $2->Target MAC $3, origin SAP $4->Target SAP $5'

        Parameters list:
              $1: dls156_count
              $2: dls156_source_mac_address
              $3: dls156_dest_mac_address
              $4: dls156_source_sap
              $5: dls156_dest_sap

        A session pool has been created for a new DLS connection.
        This pool is used exclusively by this session for data transfer."
    ::= { dlsNotificationsPrefix 156 }

dlsNotification157 NOTIFICATION-TYPE
    OBJECTS { 
              dls157_type, 
              dls157_count 
            }
    STATUS current
    DESCRIPTION
        "Notification of Event DLS.157

        Message: 'Global DLS $1 pool of $2 bytes created'

        Parameters list:
              $1: dls157_type
              $2: dls157_count

        The global DLS memory pool has been created. This is used for
        SSP control messages and other non-data transfer related items."
    ::= { dlsNotificationsPrefix 157 }

dlsNotification158 NOTIFICATION-TYPE
    OBJECTS { 
              dls158_count, 
              dls158_source_mac_address,
              dls158_dest_mac_address,
              dls158_source_sap,
              dls158_dest_sap 
            }
    STATUS current
    DESCRIPTION
        "Notification of Event DLS.158

        Message: 'Cannot create DLS session pool of $1 bytes for origin MAC $2->Target MAC $3, origin SAP $4->Target SAP $5'

        Parameters list:
              $1: dls158_count
              $2: dls158_source_mac_address
              $3: dls158_dest_mac_address
              $4: dls158_source_sap
              $5: dls158_dest_sap

        There is currently not enough memory available to support a
        new DLS session."
    ::= { dlsNotificationsPrefix 158 }

dlsNotification159 NOTIFICATION-TYPE
    OBJECTS { 
              dls159_type, 
              dls159_count 
            }
    STATUS current
    DESCRIPTION
        "Notification of Event DLS.159

        Message: 'Cannot alloc global DLS $1 pool of $2 bytes'

        Parameters list:
              $1: dls159_type
              $2: dls159_count

        There is not enough memory available to support DLS. DLS has
        been disabled."
    ::= { dlsNotificationsPrefix 159 }

dlsNotification160 NOTIFICATION-TYPE
    OBJECTS { 
              dls160_flow_ctrl_type, 
              dls160_source_mac_address,
              dls160_dest_mac_address,
              dls160_source_sap,
              dls160_dest_sap 
            }
    STATUS current
    DESCRIPTION
        "Notification of Event DLS.160

        Message: 'Entering $1 congestion for origin MAC $2->Target MAC $3, origin SAP $4->Target SAP $5'

        Parameters list:
              $1: dls160_flow_ctrl_type
              $2: dls160_source_mac_address
              $3: dls160_dest_mac_address
              $4: dls160_source_sap
              $5: dls160_dest_sap

        The DLS session is congested due to either TCP backup, or the
        receipt of a DLS_ENTER_BUSY SSP message. If this happens too
        frequently, consider increasing the amount of memory allocated
        to each DLS session."
    ::= { dlsNotificationsPrefix 160 }

dlsNotification161 NOTIFICATION-TYPE
    OBJECTS { 
              dls161_pool_type, 
              dls161_pool_state,
              dls161_memavail 
            }
    STATUS current
    DESCRIPTION
        "Notification of Event DLS.161

        Message: 'Entering GLOBAL congestion on global DLS $1 pool state=$2 mem=$3'

        Parameters list:
              $1: dls161_pool_type
              $2: dls161_pool_state
              $3: dls161_memavail

        The total amount of memory allocated by all currently active
        DLS sessions exceeded the amount pre-allocated by the user
        for DLS. As a result, the data links are temporarily being
        quiesced until some of the memory is freed up. If this happens too
        frequently, consider increasing the amount of memory allocated
        to DLSw."
    ::= { dlsNotificationsPrefix 161 }

dlsNotification162 NOTIFICATION-TYPE
    OBJECTS { 
              dls162_flow_ctrl_type, 
              dls162_source_mac_address,
              dls162_dest_mac_address,
              dls162_source_sap,
              dls162_dest_sap 
            }
    STATUS current
    DESCRIPTION
        "Notification of Event DLS.162

        Message: 'Exiting $1 congestion for origin MAC $2->Target MAC $3, origin SAP $4->Target SAP $5'

        Parameters list:
              $1: dls162_flow_ctrl_type
              $2: dls162_source_mac_address
              $3: dls162_dest_mac_address
              $4: dls162_source_sap
              $5: dls162_dest_sap

        Sufficient memory has been freed up since the last time DLS
        was congested to allow the data links to receive data again."
    ::= { dlsNotificationsPrefix 162 }

dlsNotification163 NOTIFICATION-TYPE
    OBJECTS { 
              dls163_pool_type, 
              dls163_pool_state,
              dls163_memavail 
            }
    STATUS current
    DESCRIPTION
        "Notification of Event DLS.163

        Message: 'Exiting GLOBAL congestion on global DLS $1 pool state=$2 mem=$3'

        Parameters list:
              $1: dls163_pool_type
              $2: dls163_pool_state
              $3: dls163_memavail

        Sufficient memory has been freed up since the last time DLS
        was congested to allow the data links to receive data again."
    ::= { dlsNotificationsPrefix 163 }

dlsNotification164 NOTIFICATION-TYPE
    OBJECTS { 
              dls164_source_mac_address, 
              dls164_dest_mac_address,
              dls164_source_sap,
              dls164_dest_sap 
            }
    STATUS current
    DESCRIPTION
        "Notification of Event DLS.164

        Message: 'no slow buffer for datalink->transport copy for origin MAC $1->Target MAC $2, origin SAP $3->Target SAP $4'

        Parameters list:
              $1: dls164_source_mac_address
              $2: dls164_dest_mac_address
              $3: dls164_source_sap
              $4: dls164_dest_sap

        No buffer could be obtained for copying a data buffer for
        queueing while the transport is congested. The existing
        device buffer is queued."
    ::= { dlsNotificationsPrefix 164 }

dlsNotification165 NOTIFICATION-TYPE
    OBJECTS { 
              dls165_source_mac_address, 
              dls165_dest_mac_address,
              dls165_source_sap,
              dls165_dest_sap 
            }
    STATUS current
    DESCRIPTION
        "Notification of Event DLS.165

        Message: 'DLS session pool deleted for origin MAC $1->Target MAC $2, origin SAP $3->Target SAP $4'

        Parameters list:
              $1: dls165_source_mac_address
              $2: dls165_dest_mac_address
              $3: dls165_source_sap
              $4: dls165_dest_sap

        All buffers have been returned to a DLSw session pool after
        the DLSw session has been closed. The pool may now be removed."
    ::= { dlsNotificationsPrefix 165 }

dlsNotification166 NOTIFICATION-TYPE
    OBJECTS { 
              dls166_ip_address, 
              dls166_source_mac_address,
              dls166_dest_mac_address,
              dls166_source_sap,
              dls166_dest_sap 
            }
    STATUS current
    DESCRIPTION
        "Notification of Event DLS.166

        Message: 'DLS forwarder received a SSP CANUREACH message over TCP connection to $1 for $2->$3, sap $4->$5'

        Parameters list:
              $1: dls166_ip_address
              $2: dls166_source_mac_address
              $3: dls166_dest_mac_address
              $4: dls166_source_sap
              $5: dls166_dest_sap

        DLS forwarder received a Switch to Switch Protocol message of
        CANUREACH over TCP."
    ::= { dlsNotificationsPrefix 166 }

dlsNotification167 NOTIFICATION-TYPE
    OBJECTS { 
              dls167_ip_address, 
              dls167_source_mac_address,
              dls167_dest_mac_address,
              dls167_source_sap,
              dls167_dest_sap 
            }
    STATUS current
    DESCRIPTION
        "Notification of Event DLS.167

        Message: 'DLS forwarder received a SSP ICANREACH message over TCP connection to $1 for $2->$3, sap $4->$5'

        Parameters list:
              $1: dls167_ip_address
              $2: dls167_source_mac_address
              $3: dls167_dest_mac_address
              $4: dls167_source_sap
              $5: dls167_dest_sap

        DLS forwarder received a Switch to Switch Protocol message of
        ICANREACH over TCP."
    ::= { dlsNotificationsPrefix 167 }

dlsNotification168 NOTIFICATION-TYPE
    OBJECTS { 
              dls168_ip_address, 
              dls168_source_mac_address,
              dls168_dest_mac_address,
              dls168_source_sap,
              dls168_dest_sap 
            }
    STATUS current
    DESCRIPTION
        "Notification of Event DLS.168

        Message: 'DLS forwarder received a SSP REACHACK message over TCP connection to $1 for $2->$3, sap $4->$5'

        Parameters list:
              $1: dls168_ip_address
              $2: dls168_source_mac_address
              $3: dls168_dest_mac_address
              $4: dls168_source_sap
              $5: dls168_dest_sap

        DLS forwarder received a Switch to Switch Protocol message of
        REACHACK over TCP."
    ::= { dlsNotificationsPrefix 168 }

dlsNotification169 NOTIFICATION-TYPE
    OBJECTS { 
              dls169_ip_address, 
              dls169_source_mac_address,
              dls169_dest_mac_address,
              dls169_source_sap,
              dls169_dest_sap 
            }
    STATUS current
    DESCRIPTION
        "Notification of Event DLS.169

        Message: 'DLS forwarder received a SSP XIDFRAME message over TCP connection to $1 for $2->$3, sap $4->$5'

        Parameters list:
              $1: dls169_ip_address
              $2: dls169_source_mac_address
              $3: dls169_dest_mac_address
              $4: dls169_source_sap
              $5: dls169_dest_sap

        DLS forwarder received a Switch to Switch Protocol message of
        XIDFRAME over TCP."
    ::= { dlsNotificationsPrefix 169 }

dlsNotification170 NOTIFICATION-TYPE
    OBJECTS { 
              dls170_ip_address, 
              dls170_source_mac_address,
              dls170_dest_mac_address,
              dls170_source_sap,
              dls170_dest_sap 
            }
    STATUS current
    DESCRIPTION
        "Notification of Event DLS.170

        Message: 'DLS forwarder received a SSP DGRMFRAME message over TCP connection to $1 for $2->$3, sap $4->$5'

        Parameters list:
              $1: dls170_ip_address
              $2: dls170_source_mac_address
              $3: dls170_dest_mac_address
              $4: dls170_source_sap
              $5: dls170_dest_sap

        DLS forwarder received a Switch to Switch Protocol message of
        DGRMFRAME over TCP."
    ::= { dlsNotificationsPrefix 170 }

dlsNotification171 NOTIFICATION-TYPE
    OBJECTS { 
              dls171_ip_address, 
              dls171_source_mac_address,
              dls171_dest_mac_address,
              dls171_source_sap,
              dls171_dest_sap 
            }
    STATUS current
    DESCRIPTION
        "Notification of Event DLS.171

        Message: 'DLS forwarder received a SSP CONTACT message over TCP connection to $1 for $2->$3, sap $4->$5'

        Parameters list:
              $1: dls171_ip_address
              $2: dls171_source_mac_address
              $3: dls171_dest_mac_address
              $4: dls171_source_sap
              $5: dls171_dest_sap

        DLS forwarder received a Switch to Switch Protocol message of
        CONTACT over TCP."
    ::= { dlsNotificationsPrefix 171 }

dlsNotification172 NOTIFICATION-TYPE
    OBJECTS { 
              dls172_ip_address, 
              dls172_source_mac_address,
              dls172_dest_mac_address,
              dls172_source_sap,
              dls172_dest_sap 
            }
    STATUS current
    DESCRIPTION
        "Notification of Event DLS.172

        Message: 'DLS forwarder received a SSP CONTACTED message over TCP connection to $1 for $2->$3, sap $4->$5'

        Parameters list:
              $1: dls172_ip_address
              $2: dls172_source_mac_address
              $3: dls172_dest_mac_address
              $4: dls172_source_sap
              $5: dls172_dest_sap

        DLS forwarder received a Switch to Switch Protocol message of
        CONTACTED over TCP."
    ::= { dlsNotificationsPrefix 172 }

dlsNotification173 NOTIFICATION-TYPE
    OBJECTS { 
              dls173_ip_address, 
              dls173_source_mac_address,
              dls173_dest_mac_address,
              dls173_source_sap,
              dls173_dest_sap 
            }
    STATUS current
    DESCRIPTION
        "Notification of Event DLS.173

        Message: 'DLS forwarder received a SSP DATAFRAME message over TCP connection to $1 for $2->$3, sap $4->$5'

        Parameters list:
              $1: dls173_ip_address
              $2: dls173_source_mac_address
              $3: dls173_dest_mac_address
              $4: dls173_source_sap
              $5: dls173_dest_sap

        DLS forwarder received a Switch to Switch Protocol message of
        DATAFRAME over TCP."
    ::= { dlsNotificationsPrefix 173 }

dlsNotification174 NOTIFICATION-TYPE
    OBJECTS { 
              dls174_ip_address, 
              dls174_source_mac_address,
              dls174_dest_mac_address,
              dls174_source_sap,
              dls174_dest_sap 
            }
    STATUS current
    DESCRIPTION
        "Notification of Event DLS.174

        Message: 'DLS forwarder received a SSP RESTART_DL message over TCP connection to $1 for $2->$3, sap $4->$5'

        Parameters list:
              $1: dls174_ip_address
              $2: dls174_source_mac_address
              $3: dls174_dest_mac_address
              $4: dls174_source_sap
              $5: dls174_dest_sap

        DLS forwarder received a Switch to Switch Protocol message of
        RESTART_DL over TCP."
    ::= { dlsNotificationsPrefix 174 }

dlsNotification175 NOTIFICATION-TYPE
    OBJECTS { 
              dls175_ip_address, 
              dls175_source_mac_address,
              dls175_dest_mac_address,
              dls175_source_sap,
              dls175_dest_sap 
            }
    STATUS current
    DESCRIPTION
        "Notification of Event DLS.175

        Message: 'DLS forwarder received a SSP RESTARTED message over TCP connection to $1 for $2->$3, sap $4->$5'

        Parameters list:
              $1: dls175_ip_address
              $2: dls175_source_mac_address
              $3: dls175_dest_mac_address
              $4: dls175_source_sap
              $5: dls175_dest_sap

        DLS forwarder received a Switch to Switch Protocol message of
        RESTARTED over TCP."
    ::= { dlsNotificationsPrefix 175 }

dlsNotification176 NOTIFICATION-TYPE
    OBJECTS { 
              dls176_ip_address, 
              dls176_source_mac_address,
              dls176_dest_mac_address,
              dls176_source_sap,
              dls176_dest_sap 
            }
    STATUS current
    DESCRIPTION
        "Notification of Event DLS.176

        Message: 'DLS forwarder received a SSP HALT_DL message over TCP connection to $1 for $2->$3, sap $4->$5'

        Parameters list:
              $1: dls176_ip_address
              $2: dls176_source_mac_address
              $3: dls176_dest_mac_address
              $4: dls176_source_sap
              $5: dls176_dest_sap

        DLS forwarder received a Switch to Switch Protocol message of
        HALT_DL over TCP."
    ::= { dlsNotificationsPrefix 176 }

dlsNotification177 NOTIFICATION-TYPE
    OBJECTS { 
              dls177_ip_address, 
              dls177_source_mac_address,
              dls177_dest_mac_address,
              dls177_source_sap,
              dls177_dest_sap 
            }
    STATUS current
    DESCRIPTION
        "Notification of Event DLS.177

        Message: 'DLS forwarder received a SSP DL_HALTED message over TCP connection to $1 for $2->$3, sap $4->$5'

        Parameters list:
              $1: dls177_ip_address
              $2: dls177_source_mac_address
              $3: dls177_dest_mac_address
              $4: dls177_source_sap
              $5: dls177_dest_sap

        DLS forwarder received a Switch to Switch Protocol message of
        DL_HALTED over TCP."
    ::= { dlsNotificationsPrefix 177 }

dlsNotification178 NOTIFICATION-TYPE
    OBJECTS { 
              dls178_ip_address, 
              dls178_source_mac_address,
              dls178_dest_mac_address,
              dls178_source_sap,
              dls178_dest_sap 
            }
    STATUS current
    DESCRIPTION
        "Notification of Event DLS.178

        Message: 'DLS forwarder received a SSP INFOFRAME message over TCP connection to $1 for $2->$3, sap $4->$5'

        Parameters list:
              $1: dls178_ip_address
              $2: dls178_source_mac_address
              $3: dls178_dest_mac_address
              $4: dls178_source_sap
              $5: dls178_dest_sap

        DLS forwarder received a Switch to Switch Protocol message of
        INFOFRAME over TCP."
    ::= { dlsNotificationsPrefix 178 }

dlsNotification179 NOTIFICATION-TYPE
    OBJECTS { 
              dls179_ip_address, 
              dls179_source_mac_address,
              dls179_dest_mac_address,
              dls179_source_sap,
              dls179_dest_sap 
            }
    STATUS current
    DESCRIPTION
        "Notification of Event DLS.179

        Message: 'DLS forwarder received a SSP ENTER_BUSY message over TCP connection to $1 for $2->$3, sap $4->$5'

        Parameters list:
              $1: dls179_ip_address
              $2: dls179_source_mac_address
              $3: dls179_dest_mac_address
              $4: dls179_source_sap
              $5: dls179_dest_sap

        DLS forwarder received a Switch to Switch Protocol message of
        ENTER_BUSY over TCP."
    ::= { dlsNotificationsPrefix 179 }

dlsNotification180 NOTIFICATION-TYPE
    OBJECTS { 
              dls180_ip_address, 
              dls180_source_mac_address,
              dls180_dest_mac_address,
              dls180_source_sap,
              dls180_dest_sap 
            }
    STATUS current
    DESCRIPTION
        "Notification of Event DLS.180

        Message: 'DLS forwarder received a SSP EXIT_BUSY message over TCP connection to $1 for $2->$3, sap $4->$5'

        Parameters list:
              $1: dls180_ip_address
              $2: dls180_source_mac_address
              $3: dls180_dest_mac_address
              $4: dls180_source_sap
              $5: dls180_dest_sap

        DLS forwarder received a Switch to Switch Protocol message of
        EXIT_BUSY over TCP."
    ::= { dlsNotificationsPrefix 180 }

dlsNotification181 NOTIFICATION-TYPE
    OBJECTS { 
              dls181_ip_address, 
              dls181_source_mac_address,
              dls181_dest_mac_address,
              dls181_source_sap,
              dls181_dest_sap 
            }
    STATUS current
    DESCRIPTION
        "Notification of Event DLS.181

        Message: 'DLS forwarder received a SSP HALT_DL_NOACK message over TCP connection to $1 for $2->$3, sap $4->$5'

        Parameters list:
              $1: dls181_ip_address
              $2: dls181_source_mac_address
              $3: dls181_dest_mac_address
              $4: dls181_source_sap
              $5: dls181_dest_sap

        DLS forwarder received a Switch to Switch Protocol message of
        HALT_DL_NOACK over TCP."
    ::= { dlsNotificationsPrefix 181 }

dlsNotification182 NOTIFICATION-TYPE
    OBJECTS { 
              dls182_ip_address 
            }
    STATUS current
    DESCRIPTION
        "Notification of Event DLS.182

        Message: 'DLS forwarder received a SSP IAMOKAY message over TCP connection to $1'

        Parameters list:
              $1: dls182_ip_address

        DLS forwarder received a Switch to Switch Protocol message of
        IAMOKAY over TCP."
    ::= { dlsNotificationsPrefix 182 }

dlsNotification183 NOTIFICATION-TYPE
    OBJECTS { 
              dls183_ip_address, 
              dls183_source_mac_address,
              dls183_dest_mac_address,
              dls183_source_sap,
              dls183_dest_sap 
            }
    STATUS current
    DESCRIPTION
        "Notification of Event DLS.183

        Message: 'DLS forwarder received an UNRECOGNIZED_SSP message over TCP connection to $1 for $2->$3, sap $4->$5'

        Parameters list:
              $1: dls183_ip_address
              $2: dls183_source_mac_address
              $3: dls183_dest_mac_address
              $4: dls183_source_sap
              $5: dls183_dest_sap

        DLS forwarder received an unrecognized Switch to Switch Protocol
        message over TCP."
    ::= { dlsNotificationsPrefix 183 }

dlsNotification184 NOTIFICATION-TYPE
    OBJECTS { 
              dls184_source_mac_address, 
              dls184_dest_mac_address,
              dls184_source_sap,
              dls184_dest_sap 
            }
    STATUS current
    DESCRIPTION
        "Notification of Event DLS.184

        Message: 'DLS forwarder received a DLC event of type DLC_CONTACTED for $1->$2, sap $3->$4'

        Parameters list:
              $1: dls184_source_mac_address
              $2: dls184_dest_mac_address
              $3: dls184_source_sap
              $4: dls184_dest_sap

        DLS forwarder received a DLC_CONTACTED event from the underlying
        data link which could be LLC or SDLC."
    ::= { dlsNotificationsPrefix 184 }

dlsNotification185 NOTIFICATION-TYPE
    OBJECTS { 
              dls185_source_mac_address, 
              dls185_dest_mac_address,
              dls185_source_sap,
              dls185_dest_sap 
            }
    STATUS current
    DESCRIPTION
        "Notification of Event DLS.185

        Message: 'DLS forwarder received a DLC event of type DLC_ERROR for $1->$2, sap $3->$4'

        Parameters list:
              $1: dls185_source_mac_address
              $2: dls185_dest_mac_address
              $3: dls185_source_sap
              $4: dls185_dest_sap

        DLS forwarder received a DLC_ERROR event from the underlying
        data link which could be LLC or SDLC."
    ::= { dlsNotificationsPrefix 185 }

dlsNotification186 NOTIFICATION-TYPE
    OBJECTS { 
              dls186_source_mac_address, 
              dls186_dest_mac_address,
              dls186_source_sap,
              dls186_dest_sap 
            }
    STATUS current
    DESCRIPTION
        "Notification of Event DLS.186

        Message: 'DLS forwarder received a DLC event of type DLC_RESET for $1->$2, sap $3->$4'

        Parameters list:
              $1: dls186_source_mac_address
              $2: dls186_dest_mac_address
              $3: dls186_source_sap
              $4: dls186_dest_sap

        DLS forwarder received a DLC_RESET event from the underlying
        data link which could be LLC or SDLC."
    ::= { dlsNotificationsPrefix 186 }

dlsNotification187 NOTIFICATION-TYPE
    OBJECTS { 
              dls187_source_mac_address, 
              dls187_dest_mac_address,
              dls187_source_sap,
              dls187_dest_sap 
            }
    STATUS current
    DESCRIPTION
        "Notification of Event DLS.187

        Message: 'DLS forwarder received a DLC event of type DLC_DL_HALTED for $1->$2, sap $3->$4'

        Parameters list:
              $1: dls187_source_mac_address
              $2: dls187_dest_mac_address
              $3: dls187_source_sap
              $4: dls187_dest_sap

        DLS forwarder received a DLC_DL_HALTED event from the underlying
        data link which could be LLC or SDLC."
    ::= { dlsNotificationsPrefix 187 }

dlsNotification188 NOTIFICATION-TYPE
    OBJECTS { 
              dls188_source_mac_address, 
              dls188_dest_mac_address,
              dls188_source_sap,
              dls188_dest_sap 
            }
    STATUS current
    DESCRIPTION
        "Notification of Event DLS.188

        Message: 'DLS forwarder received a DLC event of type DLC_DL_ENTER_BUSY for $1->$2, sap $3->$4'

        Parameters list:
              $1: dls188_source_mac_address
              $2: dls188_dest_mac_address
              $3: dls188_source_sap
              $4: dls188_dest_sap

        DLS forwarder received a DLC_DL_ENTER_BUSY event from the underlying
        data link which could be LLC or SDLC."
    ::= { dlsNotificationsPrefix 188 }

dlsNotification189 NOTIFICATION-TYPE
    OBJECTS { 
              dls189_source_mac_address, 
              dls189_dest_mac_address,
              dls189_source_sap,
              dls189_dest_sap 
            }
    STATUS current
    DESCRIPTION
        "Notification of Event DLS.189

        Message: 'DLS forwarder received a DLC event of type DLC_DL_EXIT_BUSY for $1->$2, sap $3->$4'

        Parameters list:
              $1: dls189_source_mac_address
              $2: dls189_dest_mac_address
              $3: dls189_source_sap
              $4: dls189_dest_sap

        DLS forwarder received a DLC_DL_EXIT_BUSY event from the underlying
        data link which could be LLC or SDLC."
    ::= { dlsNotificationsPrefix 189 }

dlsNotification190 NOTIFICATION-TYPE
    OBJECTS { 
              dls190_source_mac_address, 
              dls190_dest_mac_address,
              dls190_source_sap,
              dls190_dest_sap 
            }
    STATUS current
    DESCRIPTION
        "Notification of Event DLS.190

        Message: 'DLS forwarder received a DLC event of type DLC_DL_STARTED for $1->$2, sap $3->$4'

        Parameters list:
              $1: dls190_source_mac_address
              $2: dls190_dest_mac_address
              $3: dls190_source_sap
              $4: dls190_dest_sap

        DLS forwarder received a DLC_DL_STARTED event from the underlying
        data link which could be LLC or SDLC."
    ::= { dlsNotificationsPrefix 190 }

dlsNotification191 NOTIFICATION-TYPE
    OBJECTS { 
              dls191_source_mac_address, 
              dls191_dest_mac_address,
              dls191_source_sap,
              dls191_dest_sap 
            }
    STATUS current
    DESCRIPTION
        "Notification of Event DLS.191

        Message: 'DLS forwarder received a DLC event of type DLC_RESOLVE_C for $1->$2, sap $3->$4'

        Parameters list:
              $1: dls191_source_mac_address
              $2: dls191_dest_mac_address
              $3: dls191_source_sap
              $4: dls191_dest_sap

        DLS forwarder received a DLC_RESOLVE_C event from the underlying
        data link which could be LLC or SDLC."
    ::= { dlsNotificationsPrefix 191 }

dlsNotification192 NOTIFICATION-TYPE
    OBJECTS { 
              dls192_source_mac_address, 
              dls192_dest_mac_address,
              dls192_source_sap,
              dls192_dest_sap 
            }
    STATUS current
    DESCRIPTION
        "Notification of Event DLS.192

        Message: 'DLS forwarder received a DLC event of type DLC_INFO for $1->$2, sap $3->$4'

        Parameters list:
              $1: dls192_source_mac_address
              $2: dls192_dest_mac_address
              $3: dls192_source_sap
              $4: dls192_dest_sap

        DLS forwarder received a DLC_INFO event from the underlying
        data link which could be LLC or SDLC."
    ::= { dlsNotificationsPrefix 192 }

dlsNotification193 NOTIFICATION-TYPE
    OBJECTS { 
              dls193_source_mac_address, 
              dls193_dest_mac_address,
              dls193_source_sap,
              dls193_dest_sap 
            }
    STATUS current
    DESCRIPTION
        "Notification of Event DLS.193

        Message: 'DLS forwarder received a DLC event of type DLC_DGRM for $1->$2, sap $3->$4'

        Parameters list:
              $1: dls193_source_mac_address
              $2: dls193_dest_mac_address
              $3: dls193_source_sap
              $4: dls193_dest_sap

        DLS forwarder received a DLC_DGRM event from the underlying
        data link which could be LLC or SDLC."
    ::= { dlsNotificationsPrefix 193 }

dlsNotification194 NOTIFICATION-TYPE
    OBJECTS { 
              dls194_source_mac_address, 
              dls194_dest_mac_address,
              dls194_source_sap,
              dls194_dest_sap 
            }
    STATUS current
    DESCRIPTION
        "Notification of Event DLS.194

        Message: 'DLS forwarder received a DLC event of type DLC_XID for $1->$2, sap $3->$4'

        Parameters list:
              $1: dls194_source_mac_address
              $2: dls194_dest_mac_address
              $3: dls194_source_sap
              $4: dls194_dest_sap

        DLS forwarder received a DLC_XID event from the underlying
        data link which could be LLC or SDLC."
    ::= { dlsNotificationsPrefix 194 }

dlsNotification195 NOTIFICATION-TYPE
    OBJECTS { 
              dls195_source_mac_address, 
              dls195_dest_mac_address,
              dls195_source_sap,
              dls195_dest_sap 
            }
    STATUS current
    DESCRIPTION
        "Notification of Event DLS.195

        Message: 'DLS forwarder received a DLC event of type DLC_DATAFRAME for $1->$2, sap $3->$4'

        Parameters list:
              $1: dls195_source_mac_address
              $2: dls195_dest_mac_address
              $3: dls195_source_sap
              $4: dls195_dest_sap

        DLS forwarder received a DLC_DATAFRAME event from the underlying
        data link which could be LLC or SDLC."
    ::= { dlsNotificationsPrefix 195 }

dlsNotification196 NOTIFICATION-TYPE
    OBJECTS { 
              dls196_source_mac_address, 
              dls196_dest_mac_address,
              dls196_source_sap,
              dls196_dest_sap 
            }
    STATUS current
    DESCRIPTION
        "Notification of Event DLS.196

        Message: 'DLS forwarder is transitioning to DISCONNECTED state for the DLS session with data link id $1->$2, sap $3->$4'

        Parameters list:
              $1: dls196_source_mac_address
              $2: dls196_dest_mac_address
              $3: dls196_source_sap
              $4: dls196_dest_sap

        While processing an event, either an SSP message received over
        TCP or an event presented from underlying DLC, the associated
        DLS session is transitioning to DISCONNECTED state."
    ::= { dlsNotificationsPrefix 196 }

dlsNotification197 NOTIFICATION-TYPE
    OBJECTS { 
              dls197_source_mac_address, 
              dls197_dest_mac_address,
              dls197_source_sap,
              dls197_dest_sap 
            }
    STATUS current
    DESCRIPTION
        "Notification of Event DLS.197

        Message: 'DLS forwarder is transitioning to CONNECT_PENDING state for the DLS session with data link id $1->$2, sap $3->$4'

        Parameters list:
              $1: dls197_source_mac_address
              $2: dls197_dest_mac_address
              $3: dls197_source_sap
              $4: dls197_dest_sap

        While processing an event, either an SSP message received over
        TCP or an event presented from underlying DLC, the associated
        DLS session is transitioning to CONNECT_PENDING state."
    ::= { dlsNotificationsPrefix 197 }

dlsNotification198 NOTIFICATION-TYPE
    OBJECTS { 
              dls198_source_mac_address, 
              dls198_dest_mac_address,
              dls198_source_sap,
              dls198_dest_sap 
            }
    STATUS current
    DESCRIPTION
        "Notification of Event DLS.198

        Message: 'DLS forwarder is transitioning to CONNECTED state for the DLS session with data link id $1->$2, sap $3->$4'

        Parameters list:
              $1: dls198_source_mac_address
              $2: dls198_dest_mac_address
              $3: dls198_source_sap
              $4: dls198_dest_sap

        While processing an event, either an SSP message received over
        TCP or an event presented from underlying DLC, the associated
        DLS session is transitioning to CONNECTED state."
    ::= { dlsNotificationsPrefix 198 }

dlsNotification199 NOTIFICATION-TYPE
    OBJECTS { 
              dls199_source_mac_address, 
              dls199_dest_mac_address,
              dls199_source_sap,
              dls199_dest_sap 
            }
    STATUS current
    DESCRIPTION
        "Notification of Event DLS.199

        Message: 'DLS forwarder is transitioning to DISCONNECT_PENDING state for the DLS session with data link id $1->$2, sap $3->$4'

        Parameters list:
              $1: dls199_source_mac_address
              $2: dls199_dest_mac_address
              $3: dls199_source_sap
              $4: dls199_dest_sap

        While processing an event, either an SSP message received over
        TCP or an event presented from underlying DLC, the associated
        DLS session is transitioning to DISCONNECT_PENDING state."
    ::= { dlsNotificationsPrefix 199 }

dlsNotification200 NOTIFICATION-TYPE
    OBJECTS { 
              dls200_source_mac_address, 
              dls200_dest_mac_address,
              dls200_source_sap,
              dls200_dest_sap 
            }
    STATUS current
    DESCRIPTION
        "Notification of Event DLS.200

        Message: 'DLS forwarder is transitioning to CIRCUIT_ESTABLISHED state for the DLS session with data link id $1->$2, sap $3->$4'

        Parameters list:
              $1: dls200_source_mac_address
              $2: dls200_dest_mac_address
              $3: dls200_source_sap
              $4: dls200_dest_sap

        While processing an event, either an SSP message received over
        TCP or an event presented from underlying DLC, the associated
        DLS session is transitioning to CIRCUIT_ESTABLISHED state."
    ::= { dlsNotificationsPrefix 200 }

dlsNotification201 NOTIFICATION-TYPE
    OBJECTS { 
              dls201_source_mac_address, 
              dls201_dest_mac_address,
              dls201_source_sap,
              dls201_dest_sap 
            }
    STATUS current
    DESCRIPTION
        "Notification of Event DLS.201

        Message: 'DLS forwarder is transitioning to CIRCUIT_PENDING state for the DLS session with data link id $1->$2, sap $3->$4'

        Parameters list:
              $1: dls201_source_mac_address
              $2: dls201_dest_mac_address
              $3: dls201_source_sap
              $4: dls201_dest_sap

        While processing an event, either an SSP message received over
        TCP or an event presented from underlying DLC, the associated
        DLS session is transitioning to CIRCUIT_PENDING state."
    ::= { dlsNotificationsPrefix 201 }

dlsNotification202 NOTIFICATION-TYPE
    OBJECTS { 
              dls202_source_mac_address, 
              dls202_dest_mac_address,
              dls202_source_sap,
              dls202_dest_sap 
            }
    STATUS current
    DESCRIPTION
        "Notification of Event DLS.202

        Message: 'DLS forwarder is transitioning to CIRCUIT_RESTART state for the DLS session with data link id $1->$2, sap $3->$4'

        Parameters list:
              $1: dls202_source_mac_address
              $2: dls202_dest_mac_address
              $3: dls202_source_sap
              $4: dls202_dest_sap

        While processing an event, either an SSP message received over
        TCP or an event presented from underlying DLC, the associated
        DLS session is transitioning to CIRCUIT_RESTART state."
    ::= { dlsNotificationsPrefix 202 }

dlsNotification203 NOTIFICATION-TYPE
    OBJECTS { 
              dls203_source_mac_address, 
              dls203_dest_mac_address,
              dls203_source_sap,
              dls203_dest_sap 
            }
    STATUS current
    DESCRIPTION
        "Notification of Event DLS.203

        Message: 'DLS forwarder is transitioning to RESOLVE_PENDING state for the DLS session with data link id $1->$2, sap $3->$4'

        Parameters list:
              $1: dls203_source_mac_address
              $2: dls203_dest_mac_address
              $3: dls203_source_sap
              $4: dls203_dest_sap

        While processing an event, either an SSP message received over
        TCP or an event presented from underlying DLC, the associated
        DLS session is transitioning to RESOLVE_PENDING state."
    ::= { dlsNotificationsPrefix 203 }

dlsNotification204 NOTIFICATION-TYPE
    OBJECTS { 
              dls204_source_mac_address, 
              dls204_dest_mac_address,
              dls204_source_sap,
              dls204_dest_sap 
            }
    STATUS current
    DESCRIPTION
        "Notification of Event DLS.204

        Message: 'DLS forwarder is transitioning to CONTACT_PENDING state for the DLS session with data link id $1->$2, sap $3->$4'

        Parameters list:
              $1: dls204_source_mac_address
              $2: dls204_dest_mac_address
              $3: dls204_source_sap
              $4: dls204_dest_sap

        While processing an event, either an SSP message received over
        TCP or an event presented from underlying DLC, the associated
        DLS session is transitioning to CONTACT_PENDING state."
    ::= { dlsNotificationsPrefix 204 }

dlsNotification205 NOTIFICATION-TYPE
    OBJECTS { 
              dls205_source_mac_address, 
              dls205_dest_mac_address,
              dls205_source_sap,
              dls205_dest_sap 
            }
    STATUS current
    DESCRIPTION
        "Notification of Event DLS.205

        Message: 'DLS forwarder is transitioning to RESTART_PENDING state for the DLS session with data link id $1->$2, sap $3->$4'

        Parameters list:
              $1: dls205_source_mac_address
              $2: dls205_dest_mac_address
              $3: dls205_source_sap
              $4: dls205_dest_sap

        While processing an event, either an SSP message received over
        TCP or an event presented from underlying DLC, the associated
        DLS session is transitioning to RESTART_PENDING state."
    ::= { dlsNotificationsPrefix 205 }

dlsNotification206 NOTIFICATION-TYPE
    OBJECTS { 
              dls206_source_mac_address, 
              dls206_dest_mac_address,
              dls206_source_sap,
              dls206_dest_sap 
            }
    STATUS current
    DESCRIPTION
        "Notification of Event DLS.206

        Message: 'DLS forwarder is transitioning to HALT_PENDING state for the DLS session with data link id $1->$2, sap $3->$4'

        Parameters list:
              $1: dls206_source_mac_address
              $2: dls206_dest_mac_address
              $3: dls206_source_sap
              $4: dls206_dest_sap

        While processing an event, either an SSP message received over
        TCP or an event presented from underlying DLC, the associated
        DLS session is transitioning to HALT_PENDING state."
    ::= { dlsNotificationsPrefix 206 }

dlsNotification207 NOTIFICATION-TYPE
    OBJECTS { 
              dls207_state, 
              dls207_source_mac_address,
              dls207_dest_mac_address,
              dls207_source_sap,
              dls207_dest_sap 
            }
    STATUS current
    DESCRIPTION
        "Notification of Event DLS.207

        Message: 'DLS forwarder received a DLC_CONTACTED event in bad state $1 for the DLS session with data link id $2->$3, sap $4->$5'

        Parameters list:
              $1: dls207_state
              $2: dls207_source_mac_address
              $3: dls207_dest_mac_address
              $4: dls207_source_sap
              $5: dls207_dest_sap

        While processing a DLC_CONTACTED event, the DLS state
        machine discovered the event occurring in an unexpected state."
    ::= { dlsNotificationsPrefix 207 }

dlsNotification208 NOTIFICATION-TYPE
    OBJECTS { 
              dls208_state, 
              dls208_source_mac_address,
              dls208_dest_mac_address,
              dls208_source_sap,
              dls208_dest_sap 
            }
    STATUS current
    DESCRIPTION
        "Notification of Event DLS.208

        Message: 'DLS forwarder received a DLC_DGRM event in bad state $1 for the DLS session with data link id $2->$3, sap $4->$5'

        Parameters list:
              $1: dls208_state
              $2: dls208_source_mac_address
              $3: dls208_dest_mac_address
              $4: dls208_source_sap
              $5: dls208_dest_sap

        While processing a DLC_DGRM event, the DLS state
        machine discovered the event occurring in an unexpected state."
    ::= { dlsNotificationsPrefix 208 }

dlsNotification209 NOTIFICATION-TYPE
    OBJECTS { 
              dls209_state, 
              dls209_source_mac_address,
              dls209_dest_mac_address,
              dls209_source_sap,
              dls209_dest_sap 
            }
    STATUS current
    DESCRIPTION
        "Notification of Event DLS.209

        Message: 'DLS forwarder received a DLC_ERROR event in bad state $1 for the DLS session with data link id $2->$3, sap $4->$5'

        Parameters list:
              $1: dls209_state
              $2: dls209_source_mac_address
              $3: dls209_dest_mac_address
              $4: dls209_source_sap
              $5: dls209_dest_sap

        While processing a DLC_ERROR event, the DLS state
        machine discovered the event occurring in an unexpected state."
    ::= { dlsNotificationsPrefix 209 }

dlsNotification210 NOTIFICATION-TYPE
    OBJECTS { 
              dls210_state, 
              dls210_source_mac_address,
              dls210_dest_mac_address,
              dls210_source_sap,
              dls210_dest_sap 
            }
    STATUS current
    DESCRIPTION
        "Notification of Event DLS.210

        Message: 'DLS forwarder received a DLC_INFO event in bad state $1 for the DLS session with data link id $2->$3, sap $4->$5'

        Parameters list:
              $1: dls210_state
              $2: dls210_source_mac_address
              $3: dls210_dest_mac_address
              $4: dls210_source_sap
              $5: dls210_dest_sap

        While processing a DLC_INFO event, the DLS state
        machine discovered the event occurring in an unexpected state."
    ::= { dlsNotificationsPrefix 210 }

dlsNotification211 NOTIFICATION-TYPE
    OBJECTS { 
              dls211_state, 
              dls211_source_mac_address,
              dls211_dest_mac_address,
              dls211_source_sap,
              dls211_dest_sap 
            }
    STATUS current
    DESCRIPTION
        "Notification of Event DLS.211

        Message: 'DLS forwarder received a DLC_DL_HALTED event in bad state $1 for the DLS session with data link id $2->$3, sap $4->$5'

        Parameters list:
              $1: dls211_state
              $2: dls211_source_mac_address
              $3: dls211_dest_mac_address
              $4: dls211_source_sap
              $5: dls211_dest_sap

        While processing a DLC_DL_HALTED event, the DLS state
        machine discovered the event occurring in an unexpected state."
    ::= { dlsNotificationsPrefix 211 }

dlsNotification212 NOTIFICATION-TYPE
    OBJECTS { 
              dls212_state, 
              dls212_source_mac_address,
              dls212_dest_mac_address,
              dls212_source_sap,
              dls212_dest_sap 
            }
    STATUS current
    DESCRIPTION
        "Notification of Event DLS.212

        Message: 'DLS forwarder received a DLC_DL_STARTED event in bad state $1 for the DLS session with data link id $2->$3, sap $4->$5'

        Parameters list:
              $1: dls212_state
              $2: dls212_source_mac_address
              $3: dls212_dest_mac_address
              $4: dls212_source_sap
              $5: dls212_dest_sap

        While processing a DLC_DL_STARTED event, the DLS state
        machine discovered the event occurring in an unexpected state."
    ::= { dlsNotificationsPrefix 212 }

dlsNotification213 NOTIFICATION-TYPE
    OBJECTS { 
              dls213_state, 
              dls213_source_mac_address,
              dls213_dest_mac_address,
              dls213_source_sap,
              dls213_dest_sap 
            }
    STATUS current
    DESCRIPTION
        "Notification of Event DLS.213

        Message: 'DLS forwarder received a DLC_RESET event in bad state $1 for the DLS session with data link id $2->$3, sap $4->$5'

        Parameters list:
              $1: dls213_state
              $2: dls213_source_mac_address
              $3: dls213_dest_mac_address
              $4: dls213_source_sap
              $5: dls213_dest_sap

        While processing a DLC_RESET event, the DLS state
        machine discovered the event occurring in an unexpected state."
    ::= { dlsNotificationsPrefix 213 }

dlsNotification214 NOTIFICATION-TYPE
    OBJECTS { 
              dls214_state, 
              dls214_source_mac_address,
              dls214_dest_mac_address,
              dls214_source_sap,
              dls214_dest_sap 
            }
    STATUS current
    DESCRIPTION
        "Notification of Event DLS.214

        Message: 'DLS forwarder received a DLC_RESOLVE_C event in bad state $1 for the DLS session with data link id $2->$3, sap $4->$5'

        Parameters list:
              $1: dls214_state
              $2: dls214_source_mac_address
              $3: dls214_dest_mac_address
              $4: dls214_source_sap
              $5: dls214_dest_sap

        While processing a DLC_RESOLVE_C event, the DLS state
        machine discovered the event occurring in an unexpected state."
    ::= { dlsNotificationsPrefix 214 }

dlsNotification215 NOTIFICATION-TYPE
    OBJECTS { 
              dls215_state, 
              dls215_source_mac_address,
              dls215_dest_mac_address,
              dls215_source_sap,
              dls215_dest_sap 
            }
    STATUS current
    DESCRIPTION
        "Notification of Event DLS.215

        Message: 'DLS forwarder received a DLC_XID event in bad state $1 for the DLS session with data link id $2->$3, sap $4->$5'

        Parameters list:
              $1: dls215_state
              $2: dls215_source_mac_address
              $3: dls215_dest_mac_address
              $4: dls215_source_sap
              $5: dls215_dest_sap

        While processing a DLC_XID event, the DLS state
        machine discovered the event occurring in an unexpected state."
    ::= { dlsNotificationsPrefix 215 }

dlsNotification216 NOTIFICATION-TYPE
    OBJECTS { 
              dls216_state, 
              dls216_source_mac_address,
              dls216_dest_mac_address,
              dls216_source_sap,
              dls216_dest_sap 
            }
    STATUS current
    DESCRIPTION
        "Notification of Event DLS.216

        Message: 'DLS forwarder received a CANUREACH event in bad state $1 for the DLS session with data link id $2->$3, sap $4->$5'

        Parameters list:
              $1: dls216_state
              $2: dls216_source_mac_address
              $3: dls216_dest_mac_address
              $4: dls216_source_sap
              $5: dls216_dest_sap

        While processing a CANUREACH event, the DLS state
        machine discovered the event occurring in an unexpected state."
    ::= { dlsNotificationsPrefix 216 }

dlsNotification217 NOTIFICATION-TYPE
    OBJECTS { 
              dls217_state, 
              dls217_source_mac_address,
              dls217_dest_mac_address,
              dls217_source_sap,
              dls217_dest_sap 
            }
    STATUS current
    DESCRIPTION
        "Notification of Event DLS.217

        Message: 'DLS forwarder received a DGRMFRAME event in bad state $1 for the DLS session with data link id $2->$3, sap $4->$5'

        Parameters list:
              $1: dls217_state
              $2: dls217_source_mac_address
              $3: dls217_dest_mac_address
              $4: dls217_source_sap
              $5: dls217_dest_sap

        While processing a DGRMFRAME event, the DLS state
        machine discovered the event occurring in an unexpected state."
    ::= { dlsNotificationsPrefix 217 }

dlsNotification218 NOTIFICATION-TYPE
    OBJECTS { 
              dls218_state, 
              dls218_source_mac_address,
              dls218_dest_mac_address,
              dls218_source_sap,
              dls218_dest_sap 
            }
    STATUS current
    DESCRIPTION
        "Notification of Event DLS.218

        Message: 'DLS forwarder received a XIDFRAME event in bad state $1 for the DLS session with data link id $2->$3, sap $4->$5'

        Parameters list:
              $1: dls218_state
              $2: dls218_source_mac_address
              $3: dls218_dest_mac_address
              $4: dls218_source_sap
              $5: dls218_dest_sap

        While processing a XIDFRAME event, the DLS state
        machine discovered the event occurring in an unexpected state."
    ::= { dlsNotificationsPrefix 218 }

dlsNotification219 NOTIFICATION-TYPE
    OBJECTS { 
              dls219_state, 
              dls219_source_mac_address,
              dls219_dest_mac_address,
              dls219_source_sap,
              dls219_dest_sap 
            }
    STATUS current
    DESCRIPTION
        "Notification of Event DLS.219

        Message: 'DLS forwarder received a DATAFRAME event in bad state $1 for the DLS session with data link id $2->$3, sap $4->$5'

        Parameters list:
              $1: dls219_state
              $2: dls219_source_mac_address
              $3: dls219_dest_mac_address
              $4: dls219_source_sap
              $5: dls219_dest_sap

        While processing a DATAFRAME event, the DLS state
        machine discovered the event occurring in an unexpected state."
    ::= { dlsNotificationsPrefix 219 }

dlsNotification220 NOTIFICATION-TYPE
    OBJECTS { 
              dls220_state, 
              dls220_source_mac_address,
              dls220_dest_mac_address,
              dls220_source_sap,
              dls220_dest_sap 
            }
    STATUS current
    DESCRIPTION
        "Notification of Event DLS.220

        Message: 'DLS forwarder received a CONTACT event in bad state $1 for the DLS session with data link id $2->$3, sap $4->$5'

        Parameters list:
              $1: dls220_state
              $2: dls220_source_mac_address
              $3: dls220_dest_mac_address
              $4: dls220_source_sap
              $5: dls220_dest_sap

        While processing a CONTACT event, the DLS state
        machine discovered the event occurring in an unexpected state."
    ::= { dlsNotificationsPrefix 220 }

dlsNotification221 NOTIFICATION-TYPE
    OBJECTS { 
              dls221_state, 
              dls221_source_mac_address,
              dls221_dest_mac_address,
              dls221_source_sap,
              dls221_dest_sap 
            }
    STATUS current
    DESCRIPTION
        "Notification of Event DLS.221

        Message: 'DLS forwarder received a CONTACTED event in bad state $1 for the DLS session with data link id $2->$3, sap $4->$5'

        Parameters list:
              $1: dls221_state
              $2: dls221_source_mac_address
              $3: dls221_dest_mac_address
              $4: dls221_source_sap
              $5: dls221_dest_sap

        While processing a CONTACTED event, the DLS state
        machine discovered the event occurring in an unexpected state."
    ::= { dlsNotificationsPrefix 221 }

dlsNotification222 NOTIFICATION-TYPE
    OBJECTS { 
              dls222_state, 
              dls222_source_mac_address,
              dls222_dest_mac_address,
              dls222_source_sap,
              dls222_dest_sap 
            }
    STATUS current
    DESCRIPTION
        "Notification of Event DLS.222

        Message: 'DLS forwarder received a RESTART_DL event in bad state $1 for the DLS session with data link id $2->$3, sap $4->$5'

        Parameters list:
              $1: dls222_state
              $2: dls222_source_mac_address
              $3: dls222_dest_mac_address
              $4: dls222_source_sap
              $5: dls222_dest_sap

        While processing a RESTART_DL event, the DLS state
        machine discovered the event occurring in an unexpected state."
    ::= { dlsNotificationsPrefix 222 }

dlsNotification223 NOTIFICATION-TYPE
    OBJECTS { 
              dls223_state, 
              dls223_source_mac_address,
              dls223_dest_mac_address,
              dls223_source_sap,
              dls223_dest_sap 
            }
    STATUS current
    DESCRIPTION
        "Notification of Event DLS.223

        Message: 'DLS forwarder received a DL_RESTARTED event in bad state $1 for the DLS session with data link id $2->$3, sap $4->$5'

        Parameters list:
              $1: dls223_state
              $2: dls223_source_mac_address
              $3: dls223_dest_mac_address
              $4: dls223_source_sap
              $5: dls223_dest_sap

        While processing a DL_RESTARTED event, the DLS state
        machine discovered the event occurring in an unexpected state."
    ::= { dlsNotificationsPrefix 223 }

dlsNotification224 NOTIFICATION-TYPE
    OBJECTS { 
              dls224_state, 
              dls224_source_mac_address,
              dls224_dest_mac_address,
              dls224_source_sap,
              dls224_dest_sap 
            }
    STATUS current
    DESCRIPTION
        "Notification of Event DLS.224

        Message: 'DLS forwarder received a INFOFRAME event in bad state $1 for the DLS session with data link id $2->$3, sap $4->$5'

        Parameters list:
              $1: dls224_state
              $2: dls224_source_mac_address
              $3: dls224_dest_mac_address
              $4: dls224_source_sap
              $5: dls224_dest_sap

        While processing an INFOFRAME event, the DLS state
        machine discovered the event occurring in an unexpected state."
    ::= { dlsNotificationsPrefix 224 }

dlsNotification225 NOTIFICATION-TYPE
    OBJECTS { 
              dls225_state, 
              dls225_source_mac_address,
              dls225_dest_mac_address,
              dls225_source_sap,
              dls225_dest_sap 
            }
    STATUS current
    DESCRIPTION
        "Notification of Event DLS.225

        Message: 'DLS forwarder received a HALT_DL event in bad state $1 for the DLS session with data link id $2->$3, sap $4->$5'

        Parameters list:
              $1: dls225_state
              $2: dls225_source_mac_address
              $3: dls225_dest_mac_address
              $4: dls225_source_sap
              $5: dls225_dest_sap

        While processing a HALT_DL event, the DLS state
        machine discovered the event occurring in an unexpected state."
    ::= { dlsNotificationsPrefix 225 }

dlsNotification226 NOTIFICATION-TYPE
    OBJECTS { 
              dls226_state, 
              dls226_source_mac_address,
              dls226_dest_mac_address,
              dls226_source_sap,
              dls226_dest_sap 
            }
    STATUS current
    DESCRIPTION
        "Notification of Event DLS.226

        Message: 'DLS forwarder received a HALT_DL_NOACK event in bad state $1 for the DLS session with data link id $2->$3, sap $4->$5'

        Parameters list:
              $1: dls226_state
              $2: dls226_source_mac_address
              $3: dls226_dest_mac_address
              $4: dls226_source_sap
              $5: dls226_dest_sap

        While processing a HALT_DL_NOACK event, the DLS state
        machine discovered the event occurring in an unexpected state."
    ::= { dlsNotificationsPrefix 226 }

dlsNotification227 NOTIFICATION-TYPE
    OBJECTS { 
              dls227_state, 
              dls227_source_mac_address,
              dls227_dest_mac_address,
              dls227_source_sap,
              dls227_dest_sap 
            }
    STATUS current
    DESCRIPTION
        "Notification of Event DLS.227

        Message: 'DLS forwarder received a DL_HALTED event in bad state $1 for the DLS session with data link id $2->$3, sap $4->$5'

        Parameters list:
              $1: dls227_state
              $2: dls227_source_mac_address
              $3: dls227_dest_mac_address
              $4: dls227_source_sap
              $5: dls227_dest_sap

        While processing a DL_HALTED event, the DLS state
        machine discovered the event occurring in an unexpected state."
    ::= { dlsNotificationsPrefix 227 }

dlsNotification228 NOTIFICATION-TYPE
    OBJECTS { 
              dls228_state, 
              dls228_source_mac_address,
              dls228_dest_mac_address,
              dls228_source_sap,
              dls228_dest_sap 
            }
    STATUS current
    DESCRIPTION
        "Notification of Event DLS.228

        Message: 'DLS forwarder received a ENTER_BUSY event in bad state $1 for the DLS session with data link id $2->$3, sap $4->$5'

        Parameters list:
              $1: dls228_state
              $2: dls228_source_mac_address
              $3: dls228_dest_mac_address
              $4: dls228_source_sap
              $5: dls228_dest_sap

        While processing an ENTER_BUSY event, the DLS state
        machine discovered the event occurring in an unexpected state."
    ::= { dlsNotificationsPrefix 228 }

dlsNotification229 NOTIFICATION-TYPE
    OBJECTS { 
              dls229_state, 
              dls229_source_mac_address,
              dls229_dest_mac_address,
              dls229_source_sap,
              dls229_dest_sap 
            }
    STATUS current
    DESCRIPTION
        "Notification of Event DLS.229

        Message: 'DLS forwarder received a EXIT_BUSY event in bad state $1 for the DLS session with data link id $2->$3, sap $4->$5'

        Parameters list:
              $1: dls229_state
              $2: dls229_source_mac_address
              $3: dls229_dest_mac_address
              $4: dls229_source_sap
              $5: dls229_dest_sap

        While processing an EXIT_BUSY event, the DLS state
        machine discovered the event occurring in an unexpected state."
    ::= { dlsNotificationsPrefix 229 }

dlsNotification230 NOTIFICATION-TYPE
    OBJECTS { 
              dls230_state, 
              dls230_source_mac_address,
              dls230_dest_mac_address,
              dls230_source_sap,
              dls230_dest_sap 
            }
    STATUS current
    DESCRIPTION
        "Notification of Event DLS.230

        Message: 'DLS forwarder received a REACHACK event in bad state $1 for the DLS session with data link id $2->$3, sap $4->$5'

        Parameters list:
              $1: dls230_state
              $2: dls230_source_mac_address
              $3: dls230_dest_mac_address
              $4: dls230_source_sap
              $5: dls230_dest_sap

        While processing a REACHACK event, the DLS state
        machine discovered the event occurring in an unexpected state."
    ::= { dlsNotificationsPrefix 230 }

dlsNotification231 NOTIFICATION-TYPE
    OBJECTS { 
              dls231_ip_address, 
              dls231_source_mac_address,
              dls231_dest_mac_address,
              dls231_source_sap,
              dls231_dest_sap 
            }
    STATUS current
    DESCRIPTION
        "Notification of Event DLS.231

        Message: 'DLS, CANUREACH to $1 sent for $2->$3, sap $4->$5'

        Parameters list:
              $1: dls231_ip_address
              $2: dls231_source_mac_address
              $3: dls231_dest_mac_address
              $4: dls231_source_sap
              $5: dls231_dest_sap

        DLS successfully sent out a CANUREACH SSP message over TCP to its
        DLS peer."
    ::= { dlsNotificationsPrefix 231 }

dlsNotification232 NOTIFICATION-TYPE
    OBJECTS { 
              dls232_ip_address, 
              dls232_source_mac_address,
              dls232_dest_mac_address,
              dls232_source_sap,
              dls232_dest_sap 
            }
    STATUS current
    DESCRIPTION
        "Notification of Event DLS.232

        Message: 'DLS, ICANREACH to $1 sent for $2->$3, sap $4->$5'

        Parameters list:
              $1: dls232_ip_address
              $2: dls232_source_mac_address
              $3: dls232_dest_mac_address
              $4: dls232_source_sap
              $5: dls232_dest_sap

        DLS successfully sent out an ICANREACH SSP message over TCP to its
        DLS peer."
    ::= { dlsNotificationsPrefix 232 }

dlsNotification233 NOTIFICATION-TYPE
    OBJECTS { 
              dls233_ip_address, 
              dls233_source_mac_address,
              dls233_dest_mac_address,
              dls233_source_sap,
              dls233_dest_sap 
            }
    STATUS current
    DESCRIPTION
        "Notification of Event DLS.233

        Message: 'DLS, REACH_ACK to $1 sent for $2->$3, sap $4->$5'

        Parameters list:
              $1: dls233_ip_address
              $2: dls233_source_mac_address
              $3: dls233_dest_mac_address
              $4: dls233_source_sap
              $5: dls233_dest_sap

        DLS successfully sent out a REACH_ACK SSP message over TCP to its
        DLS peer."
    ::= { dlsNotificationsPrefix 233 }

dlsNotification234 NOTIFICATION-TYPE
    OBJECTS { 
              dls234_ip_address, 
              dls234_source_mac_address,
              dls234_dest_mac_address,
              dls234_source_sap,
              dls234_dest_sap 
            }
    STATUS current
    DESCRIPTION
        "Notification of Event DLS.234

        Message: 'DLS, CONTACT to $1 sent for $2->$3, sap $4->$5'

        Parameters list:
              $1: dls234_ip_address
              $2: dls234_source_mac_address
              $3: dls234_dest_mac_address
              $4: dls234_source_sap
              $5: dls234_dest_sap

        DLS successfully sent out a CONTACT SSP message over TCP to its
        DLS peer."
    ::= { dlsNotificationsPrefix 234 }

dlsNotification235 NOTIFICATION-TYPE
    OBJECTS { 
              dls235_ip_address, 
              dls235_source_mac_address,
              dls235_dest_mac_address,
              dls235_source_sap,
              dls235_dest_sap 
            }
    STATUS current
    DESCRIPTION
        "Notification of Event DLS.235

        Message: 'DLS, CONTACTED to $1 sent for $2->$3, sap $4->$5'

        Parameters list:
              $1: dls235_ip_address
              $2: dls235_source_mac_address
              $3: dls235_dest_mac_address
              $4: dls235_source_sap
              $5: dls235_dest_sap

        DLS successfully sent out a CONTACTED SSP message over TCP to its
        DLS peer."
    ::= { dlsNotificationsPrefix 235 }

dlsNotification236 NOTIFICATION-TYPE
    OBJECTS { 
              dls236_ip_address, 
              dls236_source_mac_address,
              dls236_dest_mac_address,
              dls236_source_sap,
              dls236_dest_sap 
            }
    STATUS current
    DESCRIPTION
        "Notification of Event DLS.236

        Message: 'DLS, RESTART_DL to $1 sent for $2->$3, sap $4->$5'

        Parameters list:
              $1: dls236_ip_address
              $2: dls236_source_mac_address
              $3: dls236_dest_mac_address
              $4: dls236_source_sap
              $5: dls236_dest_sap

        DLS successfully sent out a RESTART_DL SSP message over TCP to its
        DLS peer."
    ::= { dlsNotificationsPrefix 236 }

dlsNotification237 NOTIFICATION-TYPE
    OBJECTS { 
              dls237_ip_address, 
              dls237_source_mac_address,
              dls237_dest_mac_address,
              dls237_source_sap,
              dls237_dest_sap 
            }
    STATUS current
    DESCRIPTION
        "Notification of Event DLS.237

        Message: 'DLS, DL_RESTARTED to $1 sent for $2->$3, sap $4->$5'

        Parameters list:
              $1: dls237_ip_address
              $2: dls237_source_mac_address
              $3: dls237_dest_mac_address
              $4: dls237_source_sap
              $5: dls237_dest_sap

        DLS successfully sent out a DL_RESTARTED SSP message over TCP to its
        DLS peer."
    ::= { dlsNotificationsPrefix 237 }

dlsNotification238 NOTIFICATION-TYPE
    OBJECTS { 
              dls238_ip_address, 
              dls238_source_mac_address,
              dls238_dest_mac_address,
              dls238_source_sap,
              dls238_dest_sap 
            }
    STATUS current
    DESCRIPTION
        "Notification of Event DLS.238

        Message: 'DLS, ENTER_BUSY to $1 sent for $2->$3, sap $4->$5'

        Parameters list:
              $1: dls238_ip_address
              $2: dls238_source_mac_address
              $3: dls238_dest_mac_address
              $4: dls238_source_sap
              $5: dls238_dest_sap

        DLS successfully sent out an ENTER_BUSY SSP message over TCP to its
        DLS peer."
    ::= { dlsNotificationsPrefix 238 }

dlsNotification239 NOTIFICATION-TYPE
    OBJECTS { 
              dls239_ip_address, 
              dls239_source_mac_address,
              dls239_dest_mac_address,
              dls239_source_sap,
              dls239_dest_sap 
            }
    STATUS current
    DESCRIPTION
        "Notification of Event DLS.239

        Message: 'DLS, EXIT_BUSY to $1 sent for $2->$3, sap $4->$5'

        Parameters list:
              $1: dls239_ip_address
              $2: dls239_source_mac_address
              $3: dls239_dest_mac_address
              $4: dls239_source_sap
              $5: dls239_dest_sap

        DLS successfully sent out an EXIT_BUSY SSP message over TCP to its
        DLS peer."
    ::= { dlsNotificationsPrefix 239 }

dlsNotification240 NOTIFICATION-TYPE
    OBJECTS { 
              dls240_ip_address, 
              dls240_source_mac_address,
              dls240_dest_mac_address,
              dls240_source_sap,
              dls240_dest_sap 
            }
    STATUS current
    DESCRIPTION
        "Notification of Event DLS.240

        Message: 'DLS, HALT_DL to $1 sent for $2->$3, sap $4->$5'

        Parameters list:
              $1: dls240_ip_address
              $2: dls240_source_mac_address
              $3: dls240_dest_mac_address
              $4: dls240_source_sap
              $5: dls240_dest_sap

        DLS successfully sent out a HALT_DL SSP message over TCP to its
        DLS peer."
    ::= { dlsNotificationsPrefix 240 }

dlsNotification241 NOTIFICATION-TYPE
    OBJECTS { 
              dls241_ip_address, 
              dls241_source_mac_address,
              dls241_dest_mac_address,
              dls241_source_sap,
              dls241_dest_sap 
            }
    STATUS current
    DESCRIPTION
        "Notification of Event DLS.241

        Message: 'DLS, DL_HALTED to $1 sent for $2->$3, sap $4->$5'

        Parameters list:
              $1: dls241_ip_address
              $2: dls241_source_mac_address
              $3: dls241_dest_mac_address
              $4: dls241_source_sap
              $5: dls241_dest_sap

        DLS successfully sent out a DL_HALTED SSP message over TCP to its
        DLS peer."
    ::= { dlsNotificationsPrefix 241 }

dlsNotification242 NOTIFICATION-TYPE
    OBJECTS { 
              dls242_ip_address, 
              dls242_source_mac_address,
              dls242_dest_mac_address,
              dls242_source_sap,
              dls242_dest_sap 
            }
    STATUS current
    DESCRIPTION
        "Notification of Event DLS.242

        Message: 'DLS, HALT_DL_NOACK to $1 sent for $2->$3, sap $4->$5'

        Parameters list:
              $1: dls242_ip_address
              $2: dls242_source_mac_address
              $3: dls242_dest_mac_address
              $4: dls242_source_sap
              $5: dls242_dest_sap

        DLS successfully sent out a HALT_DL_NOACK SSP message over TCP to its
        DLS peer."
    ::= { dlsNotificationsPrefix 242 }

dlsNotification243 NOTIFICATION-TYPE
    OBJECTS { 
              dls243_ip_address, 
              dls243_source_mac_address,
              dls243_dest_mac_address,
              dls243_source_sap,
              dls243_dest_sap 
            }
    STATUS current
    DESCRIPTION
        "Notification of Event DLS.243

        Message: 'DLS, TEST_CIRCUIT_RSP to $1 sent for $2->$3, sap $4->$5'

        Parameters list:
              $1: dls243_ip_address
              $2: dls243_source_mac_address
              $3: dls243_dest_mac_address
              $4: dls243_source_sap
              $5: dls243_dest_sap

        DLS successfully sent out a TEST_CIRCUIT_RSP SSP message over TCP to
        its DLS peer."
    ::= { dlsNotificationsPrefix 243 }

dlsNotification244 NOTIFICATION-TYPE
    OBJECTS { 
              dls244_ip_address, 
              dls244_source_mac_address,
              dls244_dest_mac_address,
              dls244_source_sap,
              dls244_dest_sap 
            }
    STATUS current
    DESCRIPTION
        "Notification of Event DLS.244

        Message: 'DLS, FAILED to send CANUREACH to $1 for $2->$3, sap $4->$5'

        Parameters list:
              $1: dls244_ip_address
              $2: dls244_source_mac_address
              $3: dls244_dest_mac_address
              $4: dls244_source_sap
              $5: dls244_dest_sap

        Due to some problems with TCP connection to its DLS peer, a
        CANUREACH SSP control message could not be sent out."
    ::= { dlsNotificationsPrefix 244 }

dlsNotification245 NOTIFICATION-TYPE
    OBJECTS { 
              dls245_ip_address, 
              dls245_source_mac_address,
              dls245_dest_mac_address,
              dls245_source_sap,
              dls245_dest_sap 
            }
    STATUS current
    DESCRIPTION
        "Notification of Event DLS.245

        Message: 'DLS, FAILED to send ICANREACH to $1 for $2->$3, sap $4->$5'

        Parameters list:
              $1: dls245_ip_address
              $2: dls245_source_mac_address
              $3: dls245_dest_mac_address
              $4: dls245_source_sap
              $5: dls245_dest_sap

        Due to some problems with TCP connection to its DLS peer, an
        ICANREACH SSP control message could not be sent out."
    ::= { dlsNotificationsPrefix 245 }

dlsNotification246 NOTIFICATION-TYPE
    OBJECTS { 
              dls246_ip_address, 
              dls246_source_mac_address,
              dls246_dest_mac_address,
              dls246_source_sap,
              dls246_dest_sap 
            }
    STATUS current
    DESCRIPTION
        "Notification of Event DLS.246

        Message: 'DLS, FAILED to send REACH_ACK to $1 for $2->$3, sap $4->$5'

        Parameters list:
              $1: dls246_ip_address
              $2: dls246_source_mac_address
              $3: dls246_dest_mac_address
              $4: dls246_source_sap
              $5: dls246_dest_sap

        Due to some problems with TCP connection to its DLS peer, a
        REACH_ACK SSP control message could not be sent out."
    ::= { dlsNotificationsPrefix 246 }

dlsNotification247 NOTIFICATION-TYPE
    OBJECTS { 
              dls247_ip_address, 
              dls247_source_mac_address,
              dls247_dest_mac_address,
              dls247_source_sap,
              dls247_dest_sap 
            }
    STATUS current
    DESCRIPTION
        "Notification of Event DLS.247

        Message: 'DLS, FAILED to send CONTACT to $1 for $2->$3, sap $4->$5'

        Parameters list:
              $1: dls247_ip_address
              $2: dls247_source_mac_address
              $3: dls247_dest_mac_address
              $4: dls247_source_sap
              $5: dls247_dest_sap

        Due to some problems with TCP connection to its DLS peer, a
        CONTACT SSP control message could not be sent out."
    ::= { dlsNotificationsPrefix 247 }

dlsNotification248 NOTIFICATION-TYPE
    OBJECTS { 
              dls248_ip_address, 
              dls248_source_mac_address,
              dls248_dest_mac_address,
              dls248_source_sap,
              dls248_dest_sap 
            }
    STATUS current
    DESCRIPTION
        "Notification of Event DLS.248

        Message: 'DLS, FAILED to send CONTACTED to $1 for $2->$3, sap $4->$5'

        Parameters list:
              $1: dls248_ip_address
              $2: dls248_source_mac_address
              $3: dls248_dest_mac_address
              $4: dls248_source_sap
              $5: dls248_dest_sap

        Due to some problems with TCP connection to its DLS peer, a
        CONTACTED SSP control message could not be sent out."
    ::= { dlsNotificationsPrefix 248 }

dlsNotification249 NOTIFICATION-TYPE
    OBJECTS { 
              dls249_ip_address, 
              dls249_source_mac_address,
              dls249_dest_mac_address,
              dls249_source_sap,
              dls249_dest_sap 
            }
    STATUS current
    DESCRIPTION
        "Notification of Event DLS.249

        Message: 'DLS, FAILED to send RESTART_DL to $1 for $2->$3, sap $4->$5'

        Parameters list:
              $1: dls249_ip_address
              $2: dls249_source_mac_address
              $3: dls249_dest_mac_address
              $4: dls249_source_sap
              $5: dls249_dest_sap

        Due to some problems with TCP connection to its DLS peer, a
        RESTART_DL SSP control message could not be sent out."
    ::= { dlsNotificationsPrefix 249 }

dlsNotification250 NOTIFICATION-TYPE
    OBJECTS { 
              dls250_ip_address, 
              dls250_source_mac_address,
              dls250_dest_mac_address,
              dls250_source_sap,
              dls250_dest_sap 
            }
    STATUS current
    DESCRIPTION
        "Notification of Event DLS.250

        Message: 'DLS, FAILED to send DL_RESTARTED to $1 for $2->$3, sap $4->$5'

        Parameters list:
              $1: dls250_ip_address
              $2: dls250_source_mac_address
              $3: dls250_dest_mac_address
              $4: dls250_source_sap
              $5: dls250_dest_sap

        Due to some problems with TCP connection to its DLS peer, a
        DL_RESTARTED SSP control message could not be sent out."
    ::= { dlsNotificationsPrefix 250 }

dlsNotification251 NOTIFICATION-TYPE
    OBJECTS { 
              dls251_ip_address, 
              dls251_source_mac_address,
              dls251_dest_mac_address,
              dls251_source_sap,
              dls251_dest_sap 
            }
    STATUS current
    DESCRIPTION
        "Notification of Event DLS.251

        Message: 'DLS, FAILED to send ENTER_BUSY to $1 for $2->$3, sap $4->$5'

        Parameters list:
              $1: dls251_ip_address
              $2: dls251_source_mac_address
              $3: dls251_dest_mac_address
              $4: dls251_source_sap
              $5: dls251_dest_sap

        Due to some problems with TCP connection to its DLS peer, an
        ENTER_BUSY SSP control message could not be sent out."
    ::= { dlsNotificationsPrefix 251 }

dlsNotification252 NOTIFICATION-TYPE
    OBJECTS { 
              dls252_ip_address, 
              dls252_source_mac_address,
              dls252_dest_mac_address,
              dls252_source_sap,
              dls252_dest_sap 
            }
    STATUS current
    DESCRIPTION
        "Notification of Event DLS.252

        Message: 'DLS, FAILED to send EXIT_BUSY to $1 for $2->$3, sap $4->$5'

        Parameters list:
              $1: dls252_ip_address
              $2: dls252_source_mac_address
              $3: dls252_dest_mac_address
              $4: dls252_source_sap
              $5: dls252_dest_sap

        Due to some problems with TCP connection to its DLS peer, an
        EXIT_BUSY SSP control message could not be sent out."
    ::= { dlsNotificationsPrefix 252 }

dlsNotification253 NOTIFICATION-TYPE
    OBJECTS { 
              dls253_ip_address, 
              dls253_source_mac_address,
              dls253_dest_mac_address,
              dls253_source_sap,
              dls253_dest_sap 
            }
    STATUS current
    DESCRIPTION
        "Notification of Event DLS.253

        Message: 'DLS, FAILED to send HALT_DL to $1 for $2->$3, sap $4->$5'

        Parameters list:
              $1: dls253_ip_address
              $2: dls253_source_mac_address
              $3: dls253_dest_mac_address
              $4: dls253_source_sap
              $5: dls253_dest_sap

        Due to some problems with TCP connection to its DLS peer, a
        SSP control message could not be sent out."
    ::= { dlsNotificationsPrefix 253 }

dlsNotification254 NOTIFICATION-TYPE
    OBJECTS { 
              dls254_ip_address, 
              dls254_source_mac_address,
              dls254_dest_mac_address,
              dls254_source_sap,
              dls254_dest_sap 
            }
    STATUS current
    DESCRIPTION
        "Notification of Event DLS.254

        Message: 'DLS, FAILED to send DL_HALTED to $1 for $2->$3, sap $4->$5'

        Parameters list:
              $1: dls254_ip_address
              $2: dls254_source_mac_address
              $3: dls254_dest_mac_address
              $4: dls254_source_sap
              $5: dls254_dest_sap

        Due to some problems with TCP connection to its DLS peer, a
        DL_HALTED SSP control message could not be sent out."
    ::= { dlsNotificationsPrefix 254 }

dlsNotification255 NOTIFICATION-TYPE
    OBJECTS { 
              dls255_ip_address, 
              dls255_source_mac_address,
              dls255_dest_mac_address,
              dls255_source_sap,
              dls255_dest_sap 
            }
    STATUS current
    DESCRIPTION
        "Notification of Event DLS.255

        Message: 'DLS, FAILED to send HALT_DL_NOACK to $1 for $2->$3, sap $4->$5'

        Parameters list:
              $1: dls255_ip_address
              $2: dls255_source_mac_address
              $3: dls255_dest_mac_address
              $4: dls255_source_sap
              $5: dls255_dest_sap

        Due to some problems with TCP connection to its DLS peer, a
        HALT_DL_NOACK SSP control message could not be sent out."
    ::= { dlsNotificationsPrefix 255 }

dlsNotification256 NOTIFICATION-TYPE
    OBJECTS { 
              dls256_ip_address, 
              dls256_source_mac_address,
              dls256_dest_mac_address,
              dls256_source_sap,
              dls256_dest_sap 
            }
    STATUS current
    DESCRIPTION
        "Notification of Event DLS.256

        Message: 'DLS, FAILED to send TEST_CIRCUIT_RSP to $1 for $2->$3, sap $4->$5'

        Parameters list:
              $1: dls256_ip_address
              $2: dls256_source_mac_address
              $3: dls256_dest_mac_address
              $4: dls256_source_sap
              $5: dls256_dest_sap

        Due to some problems with TCP connection to its DLS peer, a
        TEST_CIRCUIT_RSP SSP control message could not be sent out."
    ::= { dlsNotificationsPrefix 256 }

dlsNotification257 NOTIFICATION-TYPE
    OBJECTS { 
              dls257_ip_address, 
              dls257_source_mac_address,
              dls257_dest_mac_address,
              dls257_source_sap,
              dls257_dest_sap 
            }
    STATUS current
    DESCRIPTION
        "Notification of Event DLS.257

        Message: 'DLS, DL_HALTED to $1 sent for $2->$3, sap $4->$5'

        Parameters list:
              $1: dls257_ip_address
              $2: dls257_source_mac_address
              $3: dls257_dest_mac_address
              $4: dls257_source_sap
              $5: dls257_dest_sap

        DLS successfully sent out a DL_HALTED SSP message over TCP to its
        DLS peer."
    ::= { dlsNotificationsPrefix 257 }

dlsNotification258 NOTIFICATION-TYPE
    OBJECTS { 
              dls258_ip_address, 
              dls258_source_mac_address,
              dls258_dest_mac_address,
              dls258_source_sap,
              dls258_dest_sap 
            }
    STATUS current
    DESCRIPTION
        "Notification of Event DLS.258

        Message: 'DLS, XIDFRAME to $1 sent for $2->$3, sap $4->$5'

        Parameters list:
              $1: dls258_ip_address
              $2: dls258_source_mac_address
              $3: dls258_dest_mac_address
              $4: dls258_source_sap
              $5: dls258_dest_sap

        DLS successfully sent out a XIDFRAME SSP message over TCP to its
        DLS peer."
    ::= { dlsNotificationsPrefix 258 }

dlsNotification259 NOTIFICATION-TYPE
    OBJECTS { 
              dls259_ip_address, 
              dls259_source_mac_address,
              dls259_dest_mac_address,
              dls259_source_sap,
              dls259_dest_sap 
            }
    STATUS current
    DESCRIPTION
        "Notification of Event DLS.259

        Message: 'DLS, DGRMFRAME to $1 sent for $2->$3, sap $4->$5'

        Parameters list:
              $1: dls259_ip_address
              $2: dls259_source_mac_address
              $3: dls259_dest_mac_address
              $4: dls259_source_sap
              $5: dls259_dest_sap

        DLS successfully sent out a DGRMFRAME SSP message over TCP to its
        DLS peer."
    ::= { dlsNotificationsPrefix 259 }

dlsNotification260 NOTIFICATION-TYPE
    OBJECTS { 
              dls260_ip_address, 
              dls260_source_mac_address,
              dls260_dest_mac_address,
              dls260_source_sap,
              dls260_dest_sap 
            }
    STATUS current
    DESCRIPTION
        "Notification of Event DLS.260

        Message: 'DLS, DATAFRAME to $1 sent for $2->$3, sap $4->$5'

        Parameters list:
              $1: dls260_ip_address
              $2: dls260_source_mac_address
              $3: dls260_dest_mac_address
              $4: dls260_source_sap
              $5: dls260_dest_sap

        DLS successfully sent out a DATAFRAME SSP message over TCP to its
        DLS peer."
    ::= { dlsNotificationsPrefix 260 }

dlsNotification261 NOTIFICATION-TYPE
    OBJECTS { 
              dls261_ip_address, 
              dls261_source_mac_address,
              dls261_dest_mac_address,
              dls261_source_sap,
              dls261_dest_sap 
            }
    STATUS current
    DESCRIPTION
        "Notification of Event DLS.261

        Message: 'DLS, INFOFRAME to $1 sent for $2->$3, sap $4->$5'

        Parameters list:
              $1: dls261_ip_address
              $2: dls261_source_mac_address
              $3: dls261_dest_mac_address
              $4: dls261_source_sap
              $5: dls261_dest_sap

        DLS successfully sent out an INFOFRAME SSP message over TCP to its
        DLS peer."
    ::= { dlsNotificationsPrefix 261 }

dlsNotification262 NOTIFICATION-TYPE
    OBJECTS { 
              dls262_ip_address, 
              dls262_source_mac_address,
              dls262_dest_mac_address,
              dls262_source_sap,
              dls262_dest_sap 
            }
    STATUS current
    DESCRIPTION
        "Notification of Event DLS.262

        Message: 'DLS forwarder received a SSP TEST_CIRCUIT_REQ message over TCP connection to $1 for $2->$3, sap $4->$5'

        Parameters list:
              $1: dls262_ip_address
              $2: dls262_source_mac_address
              $3: dls262_dest_mac_address
              $4: dls262_source_sap
              $5: dls262_dest_sap

        DLS forwarder received a Switch to Switch Protocol message of
        TEST_CIRCUIT_REQ over TCP."
    ::= { dlsNotificationsPrefix 262 }

dlsNotification263 NOTIFICATION-TYPE
    OBJECTS { 
              dls263_ip_address, 
              dls263_source_mac_address,
              dls263_dest_mac_address,
              dls263_source_sap,
              dls263_dest_sap 
            }
    STATUS current
    DESCRIPTION
        "Notification of Event DLS.263

        Message: 'DLS forwarder received a SSP TEST_CIRCUIT_RSP message over TCP connection to $1 for $2->$3, sap $4->$5'

        Parameters list:
              $1: dls263_ip_address
              $2: dls263_source_mac_address
              $3: dls263_dest_mac_address
              $4: dls263_source_sap
              $5: dls263_dest_sap

        DLS forwarder received a Switch to Switch Protocol message of
        TEST_CIRCUIT_RSP over TCP."
    ::= { dlsNotificationsPrefix 263 }

dlsNotification264 NOTIFICATION-TYPE
    OBJECTS { 
              dls264_source_mac_address, 
              dls264_dest_mac_address,
              dls264_source_sap,
              dls264_dest_sap 
            }
    STATUS current
    DESCRIPTION
        "Notification of Event DLS.264

        Message: 'LLC, Flushed info frame sent, $1->$2, sap $3->$4'

        Parameters list:
              $1: dls264_source_mac_address
              $2: dls264_dest_mac_address
              $3: dls264_source_sap
              $4: dls264_dest_sap

        An information frame received from DLS cloud was successfully flushed
        to an LLC end station."
    ::= { dlsNotificationsPrefix 264 }

dlsNotification265 NOTIFICATION-TYPE
    OBJECTS { 
              dls265_source_mac_address, 
              dls265_dest_mac_address,
              dls265_source_sap,
              dls265_dest_sap 
            }
    STATUS current
    DESCRIPTION
        "Notification of Event DLS.265

        Message: 'LLC, TEST_C frame sent, $1->$2, sap $3->$4'

        Parameters list:
              $1: dls265_source_mac_address
              $2: dls265_dest_mac_address
              $3: dls265_source_sap
              $4: dls265_dest_sap

        A TEST Command frame was successfully sent to an LLC end station as
        a result of receiving a CANUREACH from a DLSw peer router."
    ::= { dlsNotificationsPrefix 265 }

dlsNotification266 NOTIFICATION-TYPE
    OBJECTS { 
              dls266_source_mac_address, 
              dls266_dest_mac_address,
              dls266_source_sap,
              dls266_dest_sap 
            }
    STATUS current
    DESCRIPTION
        "Notification of Event DLS.266

        Message: 'LLC, TEST_R frame sent, $1->$2, sap $3->$4'

        Parameters list:
              $1: dls266_source_mac_address
              $2: dls266_dest_mac_address
              $3: dls266_source_sap
              $4: dls266_dest_sap

        A TEST Response frame was successfully sent to an LLC end station as
        a result of receiving an ICANREACH from a DLSw peer router."
    ::= { dlsNotificationsPrefix 266 }

dlsNotification267 NOTIFICATION-TYPE
    OBJECTS { 
              dls267_source_mac_address, 
              dls267_dest_mac_address,
              dls267_source_sap,
              dls267_dest_sap 
            }
    STATUS current
    DESCRIPTION
        "Notification of Event DLS.267

        Message: 'LLC, XID frame sent, $1->$2, sap $3->$4'

        Parameters list:
              $1: dls267_source_mac_address
              $2: dls267_dest_mac_address
              $3: dls267_source_sap
              $4: dls267_dest_sap

        A XID frame was successfully sent to an LLC end station."
    ::= { dlsNotificationsPrefix 267 }

dlsNotification268 NOTIFICATION-TYPE
    OBJECTS { 
              dls268_source_mac_address, 
              dls268_dest_mac_address,
              dls268_source_sap,
              dls268_dest_sap 
            }
    STATUS current
    DESCRIPTION
        "Notification of Event DLS.268

        Message: 'LLC, UI frame sent, $1->$2, sap $3->$4'

        Parameters list:
              $1: dls268_source_mac_address
              $2: dls268_dest_mac_address
              $3: dls268_source_sap
              $4: dls268_dest_sap

        An UI frame was successfully sent to an LLC end station."
    ::= { dlsNotificationsPrefix 268 }

dlsNotification269 NOTIFICATION-TYPE
    OBJECTS { 
              dls269_source_mac_address, 
              dls269_dest_mac_address,
              dls269_source_sap,
              dls269_dest_sap 
            }
    STATUS current
    DESCRIPTION
        "Notification of Event DLS.269

        Message: 'LLC, TEST_C frame refused by st mch, $1->$2, sap $3->$4'

        Parameters list:
              $1: dls269_source_mac_address
              $2: dls269_dest_mac_address
              $3: dls269_source_sap
              $4: dls269_dest_sap

        A TEST command frame was not processed by the DLS-LLC interface
        module's state machine as it could not be successfully relayed via
        DLS. This instance is normal for TEST command frame as DLS
        copies the frame and still refuses the frame so that it
        can also be sent via the bridge path."
    ::= { dlsNotificationsPrefix 269 }

dlsNotification270 NOTIFICATION-TYPE
    OBJECTS { 
              dls270_source_mac_address, 
              dls270_dest_mac_address,
              dls270_source_sap,
              dls270_dest_sap 
            }
    STATUS current
    DESCRIPTION
        "Notification of Event DLS.270

        Message: 'LLC, TEST_R frame refused by st mch, $1->$2, sap $3->$4'

        Parameters list:
              $1: dls270_source_mac_address
              $2: dls270_dest_mac_address
              $3: dls270_source_sap
              $4: dls270_dest_sap

        A TEST response frame was not processed by the DLS-LLC interface
        module's state machine as it could not be successfully relayed via
        DLS."
    ::= { dlsNotificationsPrefix 270 }

dlsNotification271 NOTIFICATION-TYPE
    OBJECTS { 
              dls271_source_mac_address, 
              dls271_dest_mac_address,
              dls271_source_sap,
              dls271_dest_sap 
            }
    STATUS current
    DESCRIPTION
        "Notification of Event DLS.271

        Message: 'LLC, XID_C frame refused by st mch, $1->$2, sap $3->$4'

        Parameters list:
              $1: dls271_source_mac_address
              $2: dls271_dest_mac_address
              $3: dls271_source_sap
              $4: dls271_dest_sap

        A XID command frame was not processed by the DLS-LLC interface
        module's state machine as it could not be successfully relayed via
        DLS."
    ::= { dlsNotificationsPrefix 271 }

dlsNotification272 NOTIFICATION-TYPE
    OBJECTS { 
              dls272_source_mac_address, 
              dls272_dest_mac_address,
              dls272_source_sap,
              dls272_dest_sap 
            }
    STATUS current
    DESCRIPTION
        "Notification of Event DLS.272

        Message: 'LLC, XID_R frame refused by st mch, $1->$2, sap $3->$4'

        Parameters list:
              $1: dls272_source_mac_address
              $2: dls272_dest_mac_address
              $3: dls272_source_sap
              $4: dls272_dest_sap

        A XID response frame was not processed by the DLS-LLC interface
        module's state machine as it could not be successfully relayed via
        DLS."
    ::= { dlsNotificationsPrefix 272 }

dlsNotification273 NOTIFICATION-TYPE
    OBJECTS { 
              dls273_source_mac_address, 
              dls273_dest_mac_address,
              dls273_source_sap,
              dls273_dest_sap 
            }
    STATUS current
    DESCRIPTION
        "Notification of Event DLS.273

        Message: 'LLC, UI frame refused by st mch, $1->$2, sap $3->$4'

        Parameters list:
              $1: dls273_source_mac_address
              $2: dls273_dest_mac_address
              $3: dls273_source_sap
              $4: dls273_dest_sap

        An UI frame was not processed by the DLS-LLC interface
        module's state machine as it could not be successfully relayed via
        DLS."
    ::= { dlsNotificationsPrefix 273 }

dlsNotification274 NOTIFICATION-TYPE
    OBJECTS { 
              dls274_source_mac_address, 
              dls274_dest_mac_address,
              dls274_source_sap,
              dls274_dest_sap 
            }
    STATUS current
    DESCRIPTION
        "Notification of Event DLS.274

        Message: 'LLC, INFO frame refused by st mch, $1->$2, sap $3->$4'

        Parameters list:
              $1: dls274_source_mac_address
              $2: dls274_dest_mac_address
              $3: dls274_source_sap
              $4: dls274_dest_sap

        An INFO frame was not processed by the DLS-LLC interface
        module's state machine as it could not be successfully relayed via
        DLS."
    ::= { dlsNotificationsPrefix 274 }

dlsNotification275 NOTIFICATION-TYPE
    OBJECTS { 
              dls275_source_mac_address, 
              dls275_dest_mac_address,
              dls275_source_sap,
              dls275_dest_sap 
            }
    STATUS current
    DESCRIPTION
        "Notification of Event DLS.275

        Message: 'LLC, Connect Indication Passive event not proc, $1->$2, sap $3->$4'

        Parameters list:
              $1: dls275_source_mac_address
              $2: dls275_dest_mac_address
              $3: dls275_source_sap
              $4: dls275_dest_sap

        LLC Connect Indication Passive event was not processed. Passive
        opens are not supported in the DLSw environment."
    ::= { dlsNotificationsPrefix 275 }

dlsNotification276 NOTIFICATION-TYPE
    OBJECTS { 
              dls276_source_mac_address, 
              dls276_dest_mac_address,
              dls276_source_sap,
              dls276_dest_sap 
            }
    STATUS current
    DESCRIPTION
        "Notification of Event DLS.276

        Message: 'LLC, event LLCIM_NETUP received for $1->$2, sap $3->$4'

        Parameters list:
              $1: dls276_source_mac_address
              $2: dls276_dest_mac_address
              $3: dls276_source_sap
              $4: dls276_dest_sap

        LLC interface module for the DLS received a LLCIM_NETUP event."
    ::= { dlsNotificationsPrefix 276 }

dlsNotification277 NOTIFICATION-TYPE
    OBJECTS { 
              dls277_source_mac_address, 
              dls277_dest_mac_address,
              dls277_source_sap,
              dls277_dest_sap 
            }
    STATUS current
    DESCRIPTION
        "Notification of Event DLS.277

        Message: 'LLC, event LLCIM_NETDOWN received for $1->$2, sap $3->$4'

        Parameters list:
              $1: dls277_source_mac_address
              $2: dls277_dest_mac_address
              $3: dls277_source_sap
              $4: dls277_dest_sap

        LLC interface module for the DLS received a LLCIM_NETDOWN event."
    ::= { dlsNotificationsPrefix 277 }

dlsNotification278 NOTIFICATION-TYPE
    OBJECTS { 
              dls278_source_mac_address, 
              dls278_dest_mac_address,
              dls278_source_sap,
              dls278_dest_sap 
            }
    STATUS current
    DESCRIPTION
        "Notification of Event DLS.278

        Message: 'LLC, event LLCIM_LLC_CONNECT_IND received for $1->$2, sap $3->$4'

        Parameters list:
              $1: dls278_source_mac_address
              $2: dls278_dest_mac_address
              $3: dls278_source_sap
              $4: dls278_dest_sap

        LLC interface module for the DLS received a LLCIM_LLC_CONNECT_IND
        event from LLC."
    ::= { dlsNotificationsPrefix 278 }

dlsNotification279 NOTIFICATION-TYPE
    OBJECTS { 
              dls279_source_mac_address, 
              dls279_dest_mac_address,
              dls279_source_sap,
              dls279_dest_sap 
            }
    STATUS current
    DESCRIPTION
        "Notification of Event DLS.279

        Message: 'LLC, event LLCIM_LLC_CONNECT_CONF received for $1->$2, sap $3->$4'

        Parameters list:
              $1: dls279_source_mac_address
              $2: dls279_dest_mac_address
              $3: dls279_source_sap
              $4: dls279_dest_sap

        LLC interface module for the DLS received a LLCIM_LLC_CONNECT_CONF
        event from LLC."
    ::= { dlsNotificationsPrefix 279 }

dlsNotification280 NOTIFICATION-TYPE
    OBJECTS { 
              dls280_source_mac_address, 
              dls280_dest_mac_address,
              dls280_source_sap,
              dls280_dest_sap 
            }
    STATUS current
    DESCRIPTION
        "Notification of Event DLS.280

        Message: 'LLC, event LLCIM_LLC_ENTER_BUSY received for $1->$2, sap $3->$4'

        Parameters list:
              $1: dls280_source_mac_address
              $2: dls280_dest_mac_address
              $3: dls280_source_sap
              $4: dls280_dest_sap

        LLC interface module for the DLS received a LLCIM_LLC_ENTER_BUSY
        event from LLC."
    ::= { dlsNotificationsPrefix 280 }

dlsNotification281 NOTIFICATION-TYPE
    OBJECTS { 
              dls281_source_mac_address, 
              dls281_dest_mac_address,
              dls281_source_sap,
              dls281_dest_sap 
            }
    STATUS current
    DESCRIPTION
        "Notification of Event DLS.281

        Message: 'LLC, event LLCIM_LLC_EXIT_BUSY received for $1->$2, sap $3->$4'

        Parameters list:
              $1: dls281_source_mac_address
              $2: dls281_dest_mac_address
              $3: dls281_source_sap
              $4: dls281_dest_sap

        LLC interface module for the DLS received a LLCIM_LLC_EXIT_BUSY
        event from LLC."
    ::= { dlsNotificationsPrefix 281 }

dlsNotification282 NOTIFICATION-TYPE
    OBJECTS { 
              dls282_source_mac_address, 
              dls282_dest_mac_address,
              dls282_source_sap,
              dls282_dest_sap 
            }
    STATUS current
    DESCRIPTION
        "Notification of Event DLS.282

        Message: 'LLC, event LLCIM_LLC_DISC_IND received for $1->$2, sap $3->$4'

        Parameters list:
              $1: dls282_source_mac_address
              $2: dls282_dest_mac_address
              $3: dls282_source_sap
              $4: dls282_dest_sap

        LLC interface module for the DLS received a LLCIM_LLC_DISC_IND
        event from LLC."
    ::= { dlsNotificationsPrefix 282 }

dlsNotification283 NOTIFICATION-TYPE
    OBJECTS { 
              dls283_source_mac_address, 
              dls283_dest_mac_address,
              dls283_source_sap,
              dls283_dest_sap 
            }
    STATUS current
    DESCRIPTION
        "Notification of Event DLS.283

        Message: 'LLC, event LLCIM_LLC_DISC_CONF received for $1->$2, sap $3->$4'

        Parameters list:
              $1: dls283_source_mac_address
              $2: dls283_dest_mac_address
              $3: dls283_source_sap
              $4: dls283_dest_sap

        LLC interface module for the DLS received a LLCIM_LLC_DISC_CONF
        event from LLC."
    ::= { dlsNotificationsPrefix 283 }

dlsNotification284 NOTIFICATION-TYPE
    OBJECTS { 
              dls284_source_mac_address, 
              dls284_dest_mac_address,
              dls284_source_sap,
              dls284_dest_sap 
            }
    STATUS current
    DESCRIPTION
        "Notification of Event DLS.284

        Message: 'LLC, event LLCIM_LLC_RESET_IND received for $1->$2, sap $3->$4'

        Parameters list:
              $1: dls284_source_mac_address
              $2: dls284_dest_mac_address
              $3: dls284_source_sap
              $4: dls284_dest_sap

        LLC interface module for the DLS received a LLCIM_LLC_RESET_IND
        event from LLC."
    ::= { dlsNotificationsPrefix 284 }

dlsNotification285 NOTIFICATION-TYPE
    OBJECTS { 
              dls285_source_mac_address, 
              dls285_dest_mac_address,
              dls285_source_sap,
              dls285_dest_sap 
            }
    STATUS current
    DESCRIPTION
        "Notification of Event DLS.285

        Message: 'LLC, event LLCIM_LLC_TEST_C received for $1->$2, sap $3->$4'

        Parameters list:
              $1: dls285_source_mac_address
              $2: dls285_dest_mac_address
              $3: dls285_source_sap
              $4: dls285_dest_sap

        LLC interface module for the DLS received a LLCIM_LLC_TEST_C
        event from LLC."
    ::= { dlsNotificationsPrefix 285 }

dlsNotification286 NOTIFICATION-TYPE
    OBJECTS { 
              dls286_source_mac_address, 
              dls286_dest_mac_address,
              dls286_source_sap,
              dls286_dest_sap 
            }
    STATUS current
    DESCRIPTION
        "Notification of Event DLS.286

        Message: 'LLC, event LLCIM_LLC_TEST_R received for $1->$2, sap $3->$4'

        Parameters list:
              $1: dls286_source_mac_address
              $2: dls286_dest_mac_address
              $3: dls286_source_sap
              $4: dls286_dest_sap

        LLC interface module for the DLS received a LLCIM_LLC_TEST_R
        event from LLC."
    ::= { dlsNotificationsPrefix 286 }

dlsNotification287 NOTIFICATION-TYPE
    OBJECTS { 
              dls287_source_mac_address, 
              dls287_dest_mac_address,
              dls287_source_sap,
              dls287_dest_sap 
            }
    STATUS current
    DESCRIPTION
        "Notification of Event DLS.287

        Message: 'LLC, event LLCIM_LLC_XID_C received for $1->$2, sap $3->$4'

        Parameters list:
              $1: dls287_source_mac_address
              $2: dls287_dest_mac_address
              $3: dls287_source_sap
              $4: dls287_dest_sap

        LLC interface module for the DLS received a LLCIM_LLC_XID_C
        event from LLC."
    ::= { dlsNotificationsPrefix 287 }

dlsNotification288 NOTIFICATION-TYPE
    OBJECTS { 
              dls288_source_mac_address, 
              dls288_dest_mac_address,
              dls288_source_sap,
              dls288_dest_sap 
            }
    STATUS current
    DESCRIPTION
        "Notification of Event DLS.288

        Message: 'LLC, event LLCIM_LLC_XID_R received for $1->$2, sap $3->$4'

        Parameters list:
              $1: dls288_source_mac_address
              $2: dls288_dest_mac_address
              $3: dls288_source_sap
              $4: dls288_dest_sap

        LLC interface module for the DLS received a LLCIM_LLC_XID_R
        event from LLC."
    ::= { dlsNotificationsPrefix 288 }

dlsNotification289 NOTIFICATION-TYPE
    OBJECTS { 
              dls289_source_mac_address, 
              dls289_dest_mac_address,
              dls289_source_sap,
              dls289_dest_sap 
            }
    STATUS current
    DESCRIPTION
        "Notification of Event DLS.289

        Message: 'LLC, event LLCIM_LLC_UI received for $1->$2, sap $3->$4'

        Parameters list:
              $1: dls289_source_mac_address
              $2: dls289_dest_mac_address
              $3: dls289_source_sap
              $4: dls289_dest_sap

        LLC interface module for the DLS received a LLCIM_LLC_UI
        event from LLC."
    ::= { dlsNotificationsPrefix 289 }

dlsNotification290 NOTIFICATION-TYPE
    OBJECTS { 
              dls290_source_mac_address, 
              dls290_dest_mac_address,
              dls290_source_sap,
              dls290_dest_sap 
            }
    STATUS current
    DESCRIPTION
        "Notification of Event DLS.290

        Message: 'LLC, event LLCIM_DLC_START_DL received for $1->$2, sap $3->$4'

        Parameters list:
              $1: dls290_source_mac_address
              $2: dls290_dest_mac_address
              $3: dls290_source_sap
              $4: dls290_dest_sap

        LLC interface module for the DLS received a LLCIM_DLC_START_DL
        event from DLS."
    ::= { dlsNotificationsPrefix 290 }

dlsNotification291 NOTIFICATION-TYPE
    OBJECTS { 
              dls291_source_mac_address, 
              dls291_dest_mac_address,
              dls291_source_sap,
              dls291_dest_sap 
            }
    STATUS current
    DESCRIPTION
        "Notification of Event DLS.291

        Message: 'LLC, event LLCIM_DLC_RESOLVE_R received for $1->$2, sap $3->$4'

        Parameters list:
              $1: dls291_source_mac_address
              $2: dls291_dest_mac_address
              $3: dls291_source_sap
              $4: dls291_dest_sap

        LLC interface module for the DLS received a LLCIM_DLC_RESOLVE_R
        event from DLS."
    ::= { dlsNotificationsPrefix 291 }

dlsNotification292 NOTIFICATION-TYPE
    OBJECTS { 
              dls292_source_mac_address, 
              dls292_dest_mac_address,
              dls292_source_sap,
              dls292_dest_sap 
            }
    STATUS current
    DESCRIPTION
        "Notification of Event DLS.292

        Message: 'LLC, event LLCIM_DLC_CONTACT received for $1->$2, sap $3->$4'

        Parameters list:
              $1: dls292_source_mac_address
              $2: dls292_dest_mac_address
              $3: dls292_source_sap
              $4: dls292_dest_sap

        LLC interface module for the DLS received a LLCIM_DLC_CONTACT
        event from DLS."
    ::= { dlsNotificationsPrefix 292 }

dlsNotification293 NOTIFICATION-TYPE
    OBJECTS { 
              dls293_source_mac_address, 
              dls293_dest_mac_address,
              dls293_source_sap,
              dls293_dest_sap 
            }
    STATUS current
    DESCRIPTION
        "Notification of Event DLS.293

        Message: 'LLC, event LLCIM_DLC_DGRM received for $1->$2, sap $3->$4'

        Parameters list:
              $1: dls293_source_mac_address
              $2: dls293_dest_mac_address
              $3: dls293_source_sap
              $4: dls293_dest_sap

        LLC interface module for the DLS received a LLCIM_DLC_DGRM
        event from DLS."
    ::= { dlsNotificationsPrefix 293 }

dlsNotification294 NOTIFICATION-TYPE
    OBJECTS { 
              dls294_source_mac_address, 
              dls294_dest_mac_address,
              dls294_source_sap,
              dls294_dest_sap 
            }
    STATUS current
    DESCRIPTION
        "Notification of Event DLS.294

        Message: 'LLC, event LLCIM_DLC_XID received for $1->$2, sap $3->$4'

        Parameters list:
              $1: dls294_source_mac_address
              $2: dls294_dest_mac_address
              $3: dls294_source_sap
              $4: dls294_dest_sap

        LLC interface module for the DLS received a LLCIM_DLC_XID
        event from DLS."
    ::= { dlsNotificationsPrefix 294 }

dlsNotification295 NOTIFICATION-TYPE
    OBJECTS { 
              dls295_source_mac_address, 
              dls295_dest_mac_address,
              dls295_source_sap,
              dls295_dest_sap 
            }
    STATUS current
    DESCRIPTION
        "Notification of Event DLS.295

        Message: 'LLC, event LLCIM_DLC_HALT_DL received for $1->$2, sap $3->$4'

        Parameters list:
              $1: dls295_source_mac_address
              $2: dls295_dest_mac_address
              $3: dls295_source_sap
              $4: dls295_dest_sap

        LLC interface module for the DLS received a LLCIM_DLC_HALT_DL
        event from DLS."
    ::= { dlsNotificationsPrefix 295 }

dlsNotification296 NOTIFICATION-TYPE
    OBJECTS { 
              dls296_source_mac_address, 
              dls296_dest_mac_address,
              dls296_source_sap,
              dls296_dest_sap 
            }
    STATUS current
    DESCRIPTION
        "Notification of Event DLS.296

        Message: 'LLC, event LLCIM_DLC_ENTER_BUSY received for $1->$2, sap $3->$4'

        Parameters list:
              $1: dls296_source_mac_address
              $2: dls296_dest_mac_address
              $3: dls296_source_sap
              $4: dls296_dest_sap

        LLC interface module for the DLS received a LLCIM_DLC_ENTER_BUSY
        event from DLS."
    ::= { dlsNotificationsPrefix 296 }

dlsNotification297 NOTIFICATION-TYPE
    OBJECTS { 
              dls297_source_mac_address, 
              dls297_dest_mac_address,
              dls297_source_sap,
              dls297_dest_sap 
            }
    STATUS current
    DESCRIPTION
        "Notification of Event DLS.297

        Message: 'LLC, event LLCIM_DLC_EXIT_BUSY received for $1->$2, sap $3->$4'

        Parameters list:
              $1: dls297_source_mac_address
              $2: dls297_dest_mac_address
              $3: dls297_source_sap
              $4: dls297_dest_sap

        LLC interface module for the DLS received a LLCIM_DLC_EXIT_BUSY
        event from DLS."
    ::= { dlsNotificationsPrefix 297 }

dlsNotification298 NOTIFICATION-TYPE
    OBJECTS { 
              dls298_source_mac_address, 
              dls298_dest_mac_address,
              dls298_source_sap,
              dls298_dest_sap 
            }
    STATUS current
    DESCRIPTION
        "Notification of Event DLS.298

        Message: 'LLC, event LLCIM_LLC_INFO received for $1->$2, sap $3->$4'

        Parameters list:
              $1: dls298_source_mac_address
              $2: dls298_dest_mac_address
              $3: dls298_source_sap
              $4: dls298_dest_sap

        LLC interface module for the DLS received a LLCIM_LLC_INFO
        event from LLC."
    ::= { dlsNotificationsPrefix 298 }

dlsNotification299 NOTIFICATION-TYPE
    OBJECTS { 
              dls299_source_mac_address, 
              dls299_dest_mac_address,
              dls299_source_sap,
              dls299_dest_sap 
            }
    STATUS current
    DESCRIPTION
        "Notification of Event DLS.299

        Message: 'LLC, event LLCIM_DLC_INFO received for $1->$2, sap $3->$4'

        Parameters list:
              $1: dls299_source_mac_address
              $2: dls299_dest_mac_address
              $3: dls299_source_sap
              $4: dls299_dest_sap

        LLC interface module for the DLS received a LLCIM_DLC_INFO
        event from DLS."
    ::= { dlsNotificationsPrefix 299 }

dlsNotification300 NOTIFICATION-TYPE
    OBJECTS { 
              dls300_source_mac_address, 
              dls300_dest_mac_address,
              dls300_source_sap,
              dls300_dest_sap 
            }
    STATUS current
    DESCRIPTION
        "Notification of Event DLS.300

        Message: 'LLC, Transition to LLCIM_CONTACTED state for $1->$2, sap $3->$4'

        Parameters list:
              $1: dls300_source_mac_address
              $2: dls300_dest_mac_address
              $3: dls300_source_sap
              $4: dls300_dest_sap

        LLC interface module for the DLS is transitioning to the
        LLCIM_CONTACTED state."
    ::= { dlsNotificationsPrefix 300 }

dlsNotification301 NOTIFICATION-TYPE
    OBJECTS { 
              dls301_source_mac_address, 
              dls301_dest_mac_address,
              dls301_source_sap,
              dls301_dest_sap 
            }
    STATUS current
    DESCRIPTION
        "Notification of Event DLS.301

        Message: 'LLC, Transition to LLCIM_RESOLVE_PEND state for $1->$2, sap $3->$4'

        Parameters list:
              $1: dls301_source_mac_address
              $2: dls301_dest_mac_address
              $3: dls301_source_sap
              $4: dls301_dest_sap

        LLC interface module for the DLS is transitioning to the
        LLCIM_RESOLVE_PEND state."
    ::= { dlsNotificationsPrefix 301 }

dlsNotification302 NOTIFICATION-TYPE
    OBJECTS { 
              dls302_source_mac_address, 
              dls302_dest_mac_address,
              dls302_source_sap,
              dls302_dest_sap 
            }
    STATUS current
    DESCRIPTION
        "Notification of Event DLS.302

        Message: 'LLC, Transition to LLCIM_CONNECTED state for $1->$2, sap $3->$4'

        Parameters list:
              $1: dls302_source_mac_address
              $2: dls302_dest_mac_address
              $3: dls302_source_sap
              $4: dls302_dest_sap

        LLC interface module for the DLS is transitioning to the
        LLCIM_CONNECTED state."
    ::= { dlsNotificationsPrefix 302 }

dlsNotification303 NOTIFICATION-TYPE
    OBJECTS { 
              dls303_source_mac_address, 
              dls303_dest_mac_address,
              dls303_source_sap,
              dls303_dest_sap 
            }
    STATUS current
    DESCRIPTION
        "Notification of Event DLS.303

        Message: 'LLC, Transition to LLCIM_CONNECT_PEND state for $1->$2, sap $3->$4'

        Parameters list:
              $1: dls303_source_mac_address
              $2: dls303_dest_mac_address
              $3: dls303_source_sap
              $4: dls303_dest_sap

        LLC interface module for the DLS is transitioning to the
        LLCIM_CONNECT_PEND state."
    ::= { dlsNotificationsPrefix 303 }

dlsNotification304 NOTIFICATION-TYPE
    OBJECTS { 
              dls304_source_mac_address, 
              dls304_dest_mac_address,
              dls304_source_sap,
              dls304_dest_sap 
            }
    STATUS current
    DESCRIPTION
        "Notification of Event DLS.304

        Message: 'LLC, Transition to LLCIM_CONTACT_PEND state for $1->$2, sap $3->$4'

        Parameters list:
              $1: dls304_source_mac_address
              $2: dls304_dest_mac_address
              $3: dls304_source_sap
              $4: dls304_dest_sap

        LLC interface module for the DLS is transitioning to the
        LLCIM_CONTACT_PEND state."
    ::= { dlsNotificationsPrefix 304 }

dlsNotification305 NOTIFICATION-TYPE
    OBJECTS { 
              dls305_source_mac_address, 
              dls305_dest_mac_address,
              dls305_source_sap,
              dls305_dest_sap 
            }
    STATUS current
    DESCRIPTION
        "Notification of Event DLS.305

        Message: 'LLC, Transition to LLCIM_DISCONNECTED state for $1->$2, sap $3->$4'

        Parameters list:
              $1: dls305_source_mac_address
              $2: dls305_dest_mac_address
              $3: dls305_source_sap
              $4: dls305_dest_sap

        LLC interface module for the DLS is transitioning to the
        LLCIM_DISCONNECTED state."
    ::= { dlsNotificationsPrefix 305 }

dlsNotification306 NOTIFICATION-TYPE
    OBJECTS { 
              dls306_source_mac_address, 
              dls306_dest_mac_address,
              dls306_source_sap,
              dls306_dest_sap 
            }
    STATUS current
    DESCRIPTION
        "Notification of Event DLS.306

        Message: 'LLC, Transition to LLCIM_DISC_PEND state for $1->$2, sap $3->$4'

        Parameters list:
              $1: dls306_source_mac_address
              $2: dls306_dest_mac_address
              $3: dls306_source_sap
              $4: dls306_dest_sap

        LLC interface module for the DLS is transitioning to the
        LLCIM_DISC_PEND state."
    ::= { dlsNotificationsPrefix 306 }

dlsNotification307 NOTIFICATION-TYPE
    STATUS current
    DESCRIPTION
        "Notification of Event DLS.307

        Message: 'DLSw forwarder disabled no memory for buffers'

        The Data Link Switching forwarder has been disabled because there
        was not enough memory to create the DLS private buffer pool."
    ::= { dlsNotificationsPrefix 307 }

dlsNotification308 NOTIFICATION-TYPE
    STATUS current
    DESCRIPTION
        "Notification of Event DLS.308

        Message: 'DLSw forwarder disabled no memory for llcim structures'

        The Data Link Switching forwarder has been disabled because there
        was not enough memory to create necessary llcim data structures."
    ::= { dlsNotificationsPrefix 308 }

dlsNotification309 NOTIFICATION-TYPE
    STATUS current
    DESCRIPTION
        "Notification of Event DLS.309

        Message: 'DLSw forwarder disabled no memory for tcpim structures'

        The Data Link Switching forwarder has been disabled because there
        was not enough memory to create necessary tcpim data structures."
    ::= { dlsNotificationsPrefix 309 }

dlsNotification310 NOTIFICATION-TYPE
    STATUS current
    DESCRIPTION
        "Notification of Event DLS.310

        Message: 'DLSw forwarder disabled no memory for sdlcim structures'

        The Data Link Switching forwarder has been disabled because there
        was not enough memory to create necessary sdlcim data structures."
    ::= { dlsNotificationsPrefix 310 }

dlsNotification311 NOTIFICATION-TYPE
    STATUS current
    DESCRIPTION
        "Notification of Event DLS.311

        Message: 'DLSw forwarder disabled no memory for group protocol structures'

        The Data Link Switching forwarder has been disabled because there
        was not enough memory to create necessary group protocol data
        structures."
    ::= { dlsNotificationsPrefix 311 }

dlsNotification312 NOTIFICATION-TYPE
    STATUS current
    DESCRIPTION
        "Notification of Event DLS.312

        Message: 'DLSw forwarder disabled no memory for dl correlator array'

        The Data Link Switching forwarder has been disabled because there
        was not enough memory to create necessary dl correlator array."
    ::= { dlsNotificationsPrefix 312 }

dlsNotification313 NOTIFICATION-TYPE
    OBJECTS { 
              dls313_source_mac_address, 
              dls313_dest_mac_address,
              dls313_source_sap,
              dls313_dest_sap 
            }
    STATUS current
    DESCRIPTION
        "Notification of Event DLS.313

        Message: 'LLC, INFO frame sent, $1->$2, sap $3->$4'

        Parameters list:
              $1: dls313_source_mac_address
              $2: dls313_dest_mac_address
              $3: dls313_source_sap
              $4: dls313_dest_sap

        An INFO frame received from DLS cloud was successfully sent to a
        LLC end station."
    ::= { dlsNotificationsPrefix 313 }

dlsNotification314 NOTIFICATION-TYPE
    OBJECTS { 
              dls314_group, 
              dls314_transmit_buffer_size 
            }
    STATUS current
    DESCRIPTION
        "Notification of Event DLS.314

        Message: 'TCP, configured transmit buffer size too large for group $1, clipped to $2'

        Parameters list:
              $1: dls314_group
              $2: dls314_transmit_buffer_size

        The user configured a TCP transmit buffer size in the group
        configuration that cannot be handled by the router. It has
        automatically been set to a lower value than can be allocated
        by the router."
    ::= { dlsNotificationsPrefix 314 }

dlsNotification315 NOTIFICATION-TYPE
    OBJECTS { 
              dls315_neighbour_address, 
              dls315_transmit_buffer_size 
            }
    STATUS current
    DESCRIPTION
        "Notification of Event DLS.315

        Message: 'TCP, configured transmit buffer size too large for $1, clipped to $2'

        Parameters list:
              $1: dls315_neighbour_address
              $2: dls315_transmit_buffer_size

        The user configured a TCP transmit buffer size that the router cannot
        handle. It has automatically been set to a lower value that the
        router can allocate."
    ::= { dlsNotificationsPrefix 315 }

dlsNotification316 NOTIFICATION-TYPE
    OBJECTS { 
              dls316_source_mac_address, 
              dls316_dest_mac_address,
              dls316_source_sap,
              dls316_dest_sap 
            }
    STATUS current
    DESCRIPTION
        "Notification of Event DLS.316

        Message: 'DLS, CANUREACH frame collision, frame ignored, $1->$2, sap $3->$4'

        Parameters list:
              $1: dls316_source_mac_address
              $2: dls316_dest_mac_address
              $3: dls316_source_sap
              $4: dls316_dest_sap

        A CANUREACH frame was received from the DLS cloud, but could not
        be processed because a CANUREACH is already outstanding from this
        router for the MAC addresses and SAPs specified in the CANUREACH,
        and the origin MAC address for the existing circuit is greater than
        the origin MAC address specified in the CANUREACH."
    ::= { dlsNotificationsPrefix 316 }

dlsNotification317 NOTIFICATION-TYPE
    OBJECTS { 
              dls317_xid_data_len, 
              dls317_source_mac_address,
              dls317_dest_mac_address,
              dls317_source_sap,
              dls317_dest_sap 
            }
    STATUS current
    DESCRIPTION
        "Notification of Event DLS.317

        Message: 'LLC, XID_C frame sent, len=$1, $2->$3, sap $4->$5'

        Parameters list:
              $1: dls317_xid_data_len
              $2: dls317_source_mac_address
              $3: dls317_dest_mac_address
              $4: dls317_source_sap
              $5: dls317_dest_sap

        An XID_C frame was successfully sent to an LLC end station."
    ::= { dlsNotificationsPrefix 317 }

dlsNotification318 NOTIFICATION-TYPE
    OBJECTS { 
              dls318_xid_data_len, 
              dls318_source_mac_address,
              dls318_dest_mac_address,
              dls318_source_sap,
              dls318_dest_sap 
            }
    STATUS current
    DESCRIPTION
        "Notification of Event DLS.318

        Message: 'LLC, XID_R frame sent, len=$1, $2->$3, sap $4->$5'

        Parameters list:
              $1: dls318_xid_data_len
              $2: dls318_source_mac_address
              $3: dls318_dest_mac_address
              $4: dls318_source_sap
              $5: dls318_dest_sap

        An XID_R frame was successfully sent to an LLC end station."
    ::= { dlsNotificationsPrefix 318 }

dlsNotification319 NOTIFICATION-TYPE
    OBJECTS { 
              dls319_xid_data_len, 
              dls319_source_mac_address,
              dls319_dest_mac_address,
              dls319_source_sap,
              dls319_dest_sap 
            }
    STATUS current
    DESCRIPTION
        "Notification of Event DLS.319

        Message: 'LLC, XID_C dropped, len=$1, $2->$3, sap $4->$5'

        Parameters list:
              $1: dls319_xid_data_len
              $2: dls319_source_mac_address
              $3: dls319_dest_mac_address
              $4: dls319_source_sap
              $5: dls319_dest_sap

        A received XID_C frame was discarded because a previously received
        XID_C is being processed by DLSw.
        This XID_C is considered a duplicate. This will occur frequently
        since the end station retries XID_Cs."
    ::= { dlsNotificationsPrefix 319 }

dlsNotification320 NOTIFICATION-TYPE
    OBJECTS { 
              dls320_xid_data_len, 
              dls320_source_mac_address,
              dls320_dest_mac_address,
              dls320_source_sap,
              dls320_dest_sap 
            }
    STATUS current
    DESCRIPTION
        "Notification of Event DLS.320

        Message: 'LLC, XID_R dropped, len=$1, $2->$3, sap $4->$5'

        Parameters list:
              $1: dls320_xid_data_len
              $2: dls320_source_mac_address
              $3: dls320_dest_mac_address
              $4: dls320_source_sap
              $5: dls320_dest_sap

        A received XID_R frame was discarded because there is no
        XID command outstanding. This occurs normally since DLSw
        retries XID_Cs and it is possible for many XID_Rs to come back."
    ::= { dlsNotificationsPrefix 320 }

dlsNotification321 NOTIFICATION-TYPE
    OBJECTS { 
              dls321_xid_data_len, 
              dls321_source_mac_address,
              dls321_dest_mac_address,
              dls321_source_sap,
              dls321_dest_sap 
            }
    STATUS current
    DESCRIPTION
        "Notification of Event DLS.321

        Message: 'LLC, XIDFRAME dropped-bad XID state, len=$1, $2->$3, sap $4->$5'

        Parameters list:
              $1: dls321_xid_data_len
              $2: dls321_source_mac_address
              $3: dls321_dest_mac_address
              $4: dls321_source_sap
              $5: dls321_dest_sap

        An unexpected received XIDFRAME frame was discarded. The
        LLC does not normally expect to receive an XID in this state."
    ::= { dlsNotificationsPrefix 321 }

dlsNotification322 NOTIFICATION-TYPE
    OBJECTS { 
              dls322_source_mac_address, 
              dls322_dest_mac_address,
              dls322_source_sap,
              dls322_dest_sap 
            }
    STATUS current
    DESCRIPTION
        "Notification of Event DLS.322

        Message: 'LLC, unexpected null XID, $1->$2, sap $3->$4'

        Parameters list:
              $1: dls322_source_mac_address
              $2: dls322_dest_mac_address
              $3: dls322_source_sap
              $4: dls322_dest_sap

        A null XID has been received after the SABME/UA exchange.
        This is not normal in this state and indicates that the end station
        is trying to start a new session. The current DLSw session will
        be terminated."
    ::= { dlsNotificationsPrefix 322 }

dlsNotification323 NOTIFICATION-TYPE
    OBJECTS { 
              dls323_xid_data_len, 
              dls323_source_mac_address,
              dls323_dest_mac_address,
              dls323_source_sap,
              dls323_dest_sap 
            }
    STATUS current
    DESCRIPTION
        "Notification of Event DLS.323

        Message: 'DLS, activ XIDFRAME dropped-bad state, len=$1, $2->$3, sap $4->$5'

        Parameters list:
              $1: dls323_xid_data_len
              $2: dls323_source_mac_address
              $3: dls323_dest_mac_address
              $4: dls323_source_sap
              $5: dls323_dest_sap

        A received activation XIDFRAME is not allowed in the DLSw
        DLS_CONNECTED or DLS_CONNECT_PENDING state. The frame is discarded."
    ::= { dlsNotificationsPrefix 323 }

dlsNotification324 NOTIFICATION-TYPE
    OBJECTS { 
              dls324_xid_data_len, 
              dls324_source_mac_address,
              dls324_dest_mac_address,
              dls324_source_sap,
              dls324_dest_sap 
            }
    STATUS current
    DESCRIPTION
        "Notification of Event DLS.324

        Message: 'DLS, activ XID dropped-bad state, len=$1, $2->$3, sap $4->$5'

        Parameters list:
              $1: dls324_xid_data_len
              $2: dls324_source_mac_address
              $3: dls324_dest_mac_address
              $4: dls324_source_sap
              $5: dls324_dest_sap

        A received activation XID is not allowed in the DLSw
        DLS_CONNECTED or DLS_CONNECT_PENDING state. The frame is discarded."
    ::= { dlsNotificationsPrefix 324 }

dlsNotification325 NOTIFICATION-TYPE
    STATUS current
    DESCRIPTION
        "Notification of Event DLS.325

        Message: 'DLS, Session not created - Maximum Number of DLS Sessions exceeded'

        A DLSw Session is not created since the configured Maximum Number of
        DLSw sessions is exceeded."
    ::= { dlsNotificationsPrefix 325 }

dlsNotification326 NOTIFICATION-TYPE
    OBJECTS { 
              dls326_ip_address 
            }
    STATUS current
    DESCRIPTION
        "Notification of Event DLS.326

        Message: 'closing transport connection to $1, unrecoverable SSP syncronization error'

        Parameters list:
              $1: dls326_ip_address

        Due to an error receiving a previous DLSw SSP message, DLSw
        cannot find the message header for the next message. In order
        to recover, the TCP session must be closed. This could
        possibly happen due to an invalid message length in the
        previous SSP message."
    ::= { dlsNotificationsPrefix 326 }

dlsNotification327 NOTIFICATION-TYPE
    OBJECTS { 
              dls327_source_mac_address, 
              dls327_dest_mac_address,
              dls327_source_sap,
              dls327_dest_sap 
            }
    STATUS current
    DESCRIPTION
        "Notification of Event DLS.327

        Message: 'DL_HALTED timer expired, closing session $1->$2, sap $3->$4'

        Parameters list:
              $1: dls327_source_mac_address
              $2: dls327_dest_mac_address
              $3: dls327_source_sap
              $4: dls327_dest_sap

        An expected DL_HALTED SSP message has not been received in
        response to a previously sent HALT_DL message. As a result,
        the connection is now considered to be in the disconnected
        state."
    ::= { dlsNotificationsPrefix 327 }

dlsNotification328 NOTIFICATION-TYPE
    OBJECTS { 
              dls328_ip_address 
            }
    STATUS current
    DESCRIPTION
        "Notification of Event DLS.328

        Message: 'TCP, automatically reconnecting to neighbor at $1'

        Parameters list:
              $1: dls328_ip_address

        A previously down TCP connection is being re-established, because
        the user has enabled the TCP reconnect option with the 'ENABLE
        TCP-RECONNECT' command in the DLSw configurator. To prevent
        automatic reconnection, disable the option."
    ::= { dlsNotificationsPrefix 328 }

dlsNotification329 NOTIFICATION-TYPE
    OBJECTS { 
              dls329_receive_buffer_size 
            }
    STATUS current
    DESCRIPTION
        "Notification of Event DLS.329

        Message: 'TCP, configured global TCP receive buffer size too large, clipped to $1'

        Parameters list:
              $1: dls329_receive_buffer_size

        The user configured a global TCP receive buffer size that
        cannot be handled by the router. It has automatically been
        set to a lower value that can be allocated by the router."
    ::= { dlsNotificationsPrefix 329 }

dlsNotification330 NOTIFICATION-TYPE
    OBJECTS { 
              dls330_link_address, 
              dls330_interface 
            }
    STATUS current
    DESCRIPTION
        "Notification of Event DLS.330

        Message: 'SDLC link station reopened address $1 interface $2'

        Parameters list:
              $1: dls330_link_address
              $2: dls330_interface

        The SDLC link station for the link address has been successfully
        re-opened on the network interface because the SDLC link station
        was added again on the SDLC console."
    ::= { dlsNotificationsPrefix 330 }

dlsNotification331 NOTIFICATION-TYPE
    OBJECTS { 
              dls331_ip_address 
            }
    STATUS current
    DESCRIPTION
        "Notification of Event DLS.331

        Message: 'TCP, cannot create a new connection to neighbor at $1 due to a memory shortage'

        Parameters list:
              $1: dls331_ip_address

        There is insufficient memory in the router to create a new TCP
        connection."
    ::= { dlsNotificationsPrefix 331 }

dlsNotification332 NOTIFICATION-TYPE
    OBJECTS { 
              dls332_event, 
              dls332_dlc_name,
              dls332_ccb_state,
              dls332_source_mac_address,
              dls332_dest_mac_address,
              dls332_source_sap,
              dls332_dest_sap 
            }
    STATUS current
    DESCRIPTION
        "Notification of Event DLS.332

        Message: 'Ptr to SCB is NULL. Event: $1; DLC: $2; CCB State: $3; MAC: $4->$5, SAP: $6->$7'

        Parameters list:
              $1: dls332_event
              $2: dls332_dlc_name
              $3: dls332_ccb_state
              $4: dls332_source_mac_address
              $5: dls332_dest_mac_address
              $6: dls332_source_sap
              $7: dls332_dest_sap

        While processing a DLC event that expects and requires a valid DLS SCB,
        the DLS state machine discovered that the passed pointer to the SCB was
        NULL."
    ::= { dlsNotificationsPrefix 332 }

dlsNotification333 NOTIFICATION-TYPE
    OBJECTS { 
              dls333_event 
            }
    STATUS current
    DESCRIPTION
        "Notification of Event DLS.333

        Message: 'Ptr to SCB is NULL and ptr to CCB is also NULL. Event: $1'

        Parameters list:
              $1: dls333_event

        While processing a DLC event that expects and requires a valid DLS SCB
        and a DLC CCB, the DLS state machine discovered that the passed pointers
        to both were NULL."
    ::= { dlsNotificationsPrefix 333 }

dlsNotification334 NOTIFICATION-TYPE
    OBJECTS { 
              dls334_event 
            }
    STATUS current
    DESCRIPTION
        "Notification of Event DLS.334

        Message: 'Ptr to SCB is NULL and CCB identifier is invalid. Event: $1'

        Parameters list:
              $1: dls334_event

        While processing a DLC event that expects and requires a valid DLS SCB
        and a DLC CCB, the DLS state machine discovered that the passed pointer
        to the SCB was NULL and the DLC CCB identifier was invalid."
    ::= { dlsNotificationsPrefix 334 }

dlsNotification335 NOTIFICATION-TYPE
    OBJECTS { 
              dls335_transport_state, 
              dls335_remote_ip_addr 
            }
    STATUS current
    DESCRIPTION
        "Notification of Event DLS.335

        Message: 'SSP msg received. Ptr to SCB is NULL. Xport state: $1; IP: $2'

        Parameters list:
              $1: dls335_transport_state
              $2: dls335_remote_ip_addr

        While processing an SSP event that expects and requires a valid DLS SCB,
        the DLS state machine discovered that the passed pointer to the SCB was
        NULL."
    ::= { dlsNotificationsPrefix 335 }

dlsNotification336 NOTIFICATION-TYPE
    OBJECTS { 
              dls336_source_mac_address, 
              dls336_dest_mac_address,
              dls336_source_sap,
              dls336_dest_sap 
            }
    STATUS current
    DESCRIPTION
        "Notification of Event DLS.336

        Message: 'TCP, transport connection closed, flushing frame for $1->$2, sap $3->$4'

        Parameters list:
              $1: dls336_source_mac_address
              $2: dls336_dest_mac_address
              $3: dls336_source_sap
              $4: dls336_dest_sap

        The TCP connection used for this session was closed. This and
        all other unsent data frames will be discarded."
    ::= { dlsNotificationsPrefix 336 }

dlsNotification337 NOTIFICATION-TYPE
    STATUS current
    DESCRIPTION
        "Notification of Event DLS.337

        Message: 'DLS, Session not created - DLSw disabled'

        A DLSw session could not be created because the DLSw subsystem is
        currently disabled. This message may also be displayed if the
        initialization of the DLSw susbsystem has failed."
    ::= { dlsNotificationsPrefix 337 }

dlsNotification338 NOTIFICATION-TYPE
    OBJECTS { 
              dls338_source_mac_address, 
              dls338_dest_mac_address,
              dls338_source_sap,
              dls338_dest_sap 
            }
    STATUS current
    DESCRIPTION
        "Notification of Event DLS.338

        Message: 'Could not send control message, closing session $1->$2, sap $3->$4'

        Parameters list:
              $1: dls338_source_mac_address
              $2: dls338_dest_mac_address
              $3: dls338_source_sap
              $4: dls338_dest_sap

        The router could not send a response control message due to a lack of a
        buffer to send it in. Terminate the DLSw session by sending
        a HALT_DL_NOACK."
    ::= { dlsNotificationsPrefix 338 }

dlsNotification339 NOTIFICATION-TYPE
    OBJECTS { 
              dls339_ip_address, 
              dls339_source_mac_address,
              dls339_dest_mac_address,
              dls339_source_sap,
              dls339_dest_sap 
            }
    STATUS current
    DESCRIPTION
        "Notification of Event DLS.339

        Message: 'DLS, Cleanup HALT_DL_NOACK to $1 sent for $2->$3, sap $4->$5'

        Parameters list:
              $1: dls339_ip_address
              $2: dls339_source_mac_address
              $3: dls339_dest_mac_address
              $4: dls339_source_sap
              $5: dls339_dest_sap

        DLS successfully sent out a HALT_DL_NOACK SSP message over TCP to its
        DLS peer as a result of an out of buffer condition when attempting to
        send a control message."
    ::= { dlsNotificationsPrefix 339 }

dlsNotification340 NOTIFICATION-TYPE
    OBJECTS { 
              dls340_ip_address 
            }
    STATUS current
    DESCRIPTION
        "Notification of Event DLS.340

        Message: 'A Capabilities Exchange Request has been sent to the DLSw neighbor at $1'

        Parameters list:
              $1: dls340_ip_address

        The DLSw TCP Interface module determined that the TCP Transport is
        capable of conducting a Capabilities Exchange. The DLSw TCP interface
        module has sent the Capabilities Exchange Request to the DLSw neighbor."
    ::= { dlsNotificationsPrefix 340 }

dlsNotification341 NOTIFICATION-TYPE
    OBJECTS { 
              dls341_ip_address 
            }
    STATUS current
    DESCRIPTION
        "Notification of Event DLS.341

        Message: 'A Capabilities Exchange Request has been received from the DLSw neighbor at $1'

        Parameters list:
              $1: dls341_ip_address

        The DLSw TCP Interface module received a Capabilities Exchange
        message from a DLSw neighbor. The parsing module determined that the
        message type is a request."
    ::= { dlsNotificationsPrefix 341 }

dlsNotification342 NOTIFICATION-TYPE
    OBJECTS { 
              dls342_ip_address 
            }
    STATUS current
    DESCRIPTION
        "Notification of Event DLS.342

        Message: 'A Capabilities Exchange Positive Response has been sent to the DLSw neighbor at $1'

        Parameters list:
              $1: dls342_ip_address

        The DLSw Capabilities Exchange parsing module successfully processed
        a Capabilities Exchange Request from a DLSw neighbor."
    ::= { dlsNotificationsPrefix 342 }

dlsNotification343 NOTIFICATION-TYPE
    OBJECTS { 
              dls343_ip_address 
            }
    STATUS current
    DESCRIPTION
        "Notification of Event DLS.343

        Message: 'A Capabilities Exchange Positive Response has been received from the DLSw neighbor at $1'

        Parameters list:
              $1: dls343_ip_address

        The DLSw TCP Interface module received a Capabilities Exchange
        message from a DLSw neighbor. The parsing module determined that
        the message type is a Positive Response."
    ::= { dlsNotificationsPrefix 343 }

dlsNotification344 NOTIFICATION-TYPE
    OBJECTS { 
              dls344_ip_address, 
              dls344_reason_code,
              dls344_offset_value 
            }
    STATUS current
    DESCRIPTION
        "Notification of Event DLS.344

        Message: 'A Capabilities Exchange Negative Response has been sent to the DLSw neighbor at $1 Reason $2 Offset $3'

        Parameters list:
              $1: dls344_ip_address
              $2: dls344_reason_code
              $3: dls344_offset_value

        The DLSw Capabilities Exchange parsing module processed a
        Capabilities Exchange Request from a DLSw neighbor. The Request was
        determined to contain an error or invalid Control Vector."
    ::= { dlsNotificationsPrefix 344 }

dlsNotification345 NOTIFICATION-TYPE
    OBJECTS { 
              dls345_ip_address, 
              dls345_reason_code,
              dls345_offset_value 
            }
    STATUS current
    DESCRIPTION
        "Notification of Event DLS.345

        Message: 'A Capabilities Exchange Negative Response has been received from the DLSw neighbor at $1. The Negative Response contained a Reason of $2 at Offset $3'

        Parameters list:
              $1: dls345_ip_address
              $2: dls345_reason_code
              $3: dls345_offset_value

        The DLSw TCP Interface module received a Capabilities Exchange message
        from a DLSw neighbor. The parsing module determined that the message
        type is a Negative Response."
    ::= { dlsNotificationsPrefix 345 }

dlsNotification346 NOTIFICATION-TYPE
    OBJECTS { 
              dls346_ip_address 
            }
    STATUS current
    DESCRIPTION
        "Notification of Event DLS.346

        Message: 'Capabilities Exchange has been aborted with the neighbor at $1. DLSw processing will continue by assuming that his neighbor is DLSw RFC 1434+ compliant'

        Parameters list:
              $1: dls346_ip_address

        The DLSw Capabilities Exchange manager determined that the neighbor
        is not capable of supporting DLSw AIW_V1. Assume that the
        neighbor is capable of supporting DLSw RFC 1434+."
    ::= { dlsNotificationsPrefix 346 }

dlsNotification347 NOTIFICATION-TYPE
    OBJECTS { 
              dls347_ip_address 
            }
    STATUS current
    DESCRIPTION
        "Notification of Event DLS.347

        Message: 'Received Unknown Capabilities Exchange Message from the neighbor at $1'

        Parameters list:
              $1: dls347_ip_address

        The DLSw neighbor sent an Unknown Capabilities Exchange message.
        Capabilities Exchange may fail if this was meant to be a Request
        or Response."
    ::= { dlsNotificationsPrefix 347 }

dlsNotification348 NOTIFICATION-TYPE
    OBJECTS { 
              dls348_ip_address 
            }
    STATUS current
    DESCRIPTION
        "Notification of Event DLS.348

        Message: 'An attempt to allocate the memory required to build a Capabilities Exchange message has failed. The message can not be sent to the neighbor at $1'

        Parameters list:
              $1: dls348_ip_address

        There is no memory available to allocate the resources that the router
        needs to build a Capabilities Exchange message. Capabilities Exchange
        will fail with this neighbor."
    ::= { dlsNotificationsPrefix 348 }

dlsNotification349 NOTIFICATION-TYPE
    OBJECTS { 
              dls349_ip_address 
            }
    STATUS current
    DESCRIPTION
        "Notification of Event DLS.349

        Message: 'Capabilities Exchange has failed with the neighbor at $1. DLSw processing can not continue. This neighbor is non compliant to DLSw AIW_V1'

        Parameters list:
              $1: dls349_ip_address

        The DLSw Capabilities Exchange manager determined that the neighbor
        is not capable of supporting DLSw AIW_V1. The TCP Transport connection
        will be terminated with the neighbor."
    ::= { dlsNotificationsPrefix 349 }

dlsNotification350 NOTIFICATION-TYPE
    OBJECTS { 
              dls350_ip_address 
            }
    STATUS current
    DESCRIPTION
        "Notification of Event DLS.350

        Message: 'Capabilities Exchange has completed successfully with the neighbor at $1. DLSw processing can now continue in a DLSw AIW_V1 compliant mode'

        Parameters list:
              $1: dls350_ip_address

        The DLSw Capabilities Exchange manager determined that the neighbor
        is capable of supporting DLSw AIW_V1."
    ::= { dlsNotificationsPrefix 350 }

dlsNotification351 NOTIFICATION-TYPE
    OBJECTS { 
              dls351_indmsg, 
              dls351_ackmsg,
              dls351_ip_address,
              dls351_source_mac_address,
              dls351_dest_mac_address,
              dls351_source_sap,
              dls351_dest_sap 
            }
    STATUS current
    DESCRIPTION
        "Notification of Event DLS.351

        Message: 'DLS, DLS forwarder received a SSP IFCM $1 $2 message over TCP connection to $3 for $4->$5, sap $6->$7'

        Parameters list:
              $1: dls351_indmsg
              $2: dls351_ackmsg
              $3: dls351_ip_address
              $4: dls351_source_mac_address
              $5: dls351_dest_mac_address
              $6: dls351_source_sap
              $7: dls351_dest_sap

        DLS forwarder received a Switch to Switch Protocol (SSP) message of
        an Isolated Flow Control Message (IFCM)."
    ::= { dlsNotificationsPrefix 351 }

dlsNotification352 NOTIFICATION-TYPE
    OBJECTS { 
              dls352_transport_state, 
              dls352_remote_ip_addr 
            }
    STATUS current
    DESCRIPTION
        "Notification of Event DLS.352

        Message: 'DLS, SSP msg received carrying flow control data. Ptr to SCB is NULL. Xport state: $1; IP: $2'

        Parameters list:
              $1: dls352_transport_state
              $2: dls352_remote_ip_addr

        The DLS state machine discovered that the passed pointer to the SCB
        was NULL while processing an SSP event containing flow control data
        that expects and requires a valid DLS SCB."
    ::= { dlsNotificationsPrefix 352 }

dlsNotification353 NOTIFICATION-TYPE
    OBJECTS { 
              dls353_source_mac_address, 
              dls353_dest_mac_address,
              dls353_source_sap,
              dls353_dest_sap 
            }
    STATUS current
    DESCRIPTION
        "Notification of Event DLS.353

        Message: 'DLS, Sender granted units for $1->$2, sap $3->$4 is less than zero'

        Parameters list:
              $1: dls353_source_mac_address
              $2: dls353_dest_mac_address
              $3: dls353_source_sap
              $4: dls353_dest_sap

        The sender granted Service Access Point (SAP) units for this circuit
        and the SAP was decremented to a value less than zero. This is a
        protocol violation and the router took the circuit down."
    ::= { dlsNotificationsPrefix 353 }

dlsNotification354 NOTIFICATION-TYPE
    OBJECTS { 
              dls354_source_mac_address, 
              dls354_dest_mac_address,
              dls354_source_sap,
              dls354_dest_sap 
            }
    STATUS current
    DESCRIPTION
        "Notification of Event DLS.354

        Message: 'DLS, Received increment window for $1->$2, sap $3->$4 when window equal maximum size'

        Parameters list:
              $1: dls354_source_mac_address
              $2: dls354_dest_mac_address
              $3: dls354_source_sap
              $4: dls354_dest_sap

        DLSw received an increment window operator while the window size is
        equal to the maximum size."
    ::= { dlsNotificationsPrefix 354 }

dlsNotification355 NOTIFICATION-TYPE
    OBJECTS { 
              dls355_source_mac_address, 
              dls355_dest_mac_address,
              dls355_source_sap,
              dls355_dest_sap 
            }
    STATUS current
    DESCRIPTION
        "Notification of Event DLS.355

        Message: 'DLS, Received decrement window for $1->$2, sap $3->$4 when window size equal 1'

        Parameters list:
              $1: dls355_source_mac_address
              $2: dls355_dest_mac_address
              $3: dls355_source_sap
              $4: dls355_dest_sap

        DLSw received a decrement window operator while the window size is
        equal to 1."
    ::= { dlsNotificationsPrefix 355 }

dlsNotification356 NOTIFICATION-TYPE
    OBJECTS { 
              dls356_source_mac_address, 
              dls356_dest_mac_address,
              dls356_source_sap,
              dls356_dest_sap 
            }
    STATUS current
    DESCRIPTION
        "Notification of Event DLS.356

        Message: 'DLS, Received unrecognized flow control operator for $1->$2, sap $3->$4'

        Parameters list:
              $1: dls356_source_mac_address
              $2: dls356_dest_mac_address
              $3: dls356_source_sap
              $4: dls356_dest_sap

        Received an unrecognized flow control operator."
    ::= { dlsNotificationsPrefix 356 }

dlsNotification357 NOTIFICATION-TYPE
    OBJECTS { 
              dls357_operator, 
              dls357_source_mac_address,
              dls357_dest_mac_address,
              dls357_source_sap,
              dls357_dest_sap,
              dls357_txgrant,
              dls357_txwindow 
            }
    STATUS current
    DESCRIPTION
        "Notification of Event DLS.357

        Message: 'DLS, FCIND $1 recv'd for $2->$3, sap $4->$5 tx_grant=$6 tx_window=$7'

        Parameters list:
              $1: dls357_operator
              $2: dls357_source_mac_address
              $3: dls357_dest_mac_address
              $4: dls357_source_sap
              $5: dls357_dest_sap
              $6: dls357_txgrant
              $7: dls357_txwindow

        The router received an Isolated Flow Control Message (IFCM) or
        piggybacked flow control indication Switch to Switch Protocol (SSP)
        message."
    ::= { dlsNotificationsPrefix 357 }

dlsNotification358 NOTIFICATION-TYPE
    OBJECTS { 
              dls358_source_mac_address, 
              dls358_dest_mac_address,
              dls358_source_sap,
              dls358_dest_sap 
            }
    STATUS current
    DESCRIPTION
        "Notification of Event DLS.358

        Message: 'DLS, Unexpected flow control acknowledgement recv'd for $1->$2, sap $3->$4'

        Parameters list:
              $1: dls358_source_mac_address
              $2: dls358_dest_mac_address
              $3: dls358_source_sap
              $4: dls358_dest_sap

        The router received an IFCM or piggybacked flow control acknowledgement
        in an invalid state."
    ::= { dlsNotificationsPrefix 358 }

dlsNotification359 NOTIFICATION-TYPE
    OBJECTS { 
              dls359_operator, 
              dls359_ip_address,
              dls359_source_mac_address,
              dls359_dest_mac_address,
              dls359_source_sap,
              dls359_dest_sap 
            }
    STATUS current
    DESCRIPTION
        "Notification of Event DLS.359

        Message: 'DLS, DLS forwarder sent an IFCM SSP message $1 over TCP connection to $2 for $3->$4, sap $5->$6'

        Parameters list:
              $1: dls359_operator
              $2: dls359_ip_address
              $3: dls359_source_mac_address
              $4: dls359_dest_mac_address
              $5: dls359_source_sap
              $6: dls359_dest_sap

        The DLS forwarder sent a Switch to Switch Protocol (SSP) message of
        IFCM."
    ::= { dlsNotificationsPrefix 359 }

dlsNotification360 NOTIFICATION-TYPE
    OBJECTS { 
              dls360_source_mac_address, 
              dls360_dest_mac_address,
              dls360_source_sap,
              dls360_dest_sap 
            }
    STATUS current
    DESCRIPTION
        "Notification of Event DLS.360

        Message: 'DLS, Receiver detected granted units exceeded for $1->$2, sap $3->$4'

        Parameters list:
              $1: dls360_source_mac_address
              $2: dls360_dest_mac_address
              $3: dls360_source_sap
              $4: dls360_dest_sap

        The router received an SSP_INFOFRAME or SSP_DGRMFRAME that caused
        the granted units to be exceeded."
    ::= { dlsNotificationsPrefix 360 }

dlsNotification361 NOTIFICATION-TYPE
    OBJECTS { 
              dls361_source_mac_address, 
              dls361_dest_mac_address,
              dls361_source_sap,
              dls361_dest_sap 
            }
    STATUS current
    DESCRIPTION
        "Notification of Event DLS.361

        Message: 'DLS, Receiver expected flow control ack before end of current window for $1->$2, sap $3->$4'

        Parameters list:
              $1: dls361_source_mac_address
              $2: dls361_dest_mac_address
              $3: dls361_source_sap
              $4: dls361_dest_sap

        The receiver did not get flow control ack before the end of the
        current window."
    ::= { dlsNotificationsPrefix 361 }

dlsNotification362 NOTIFICATION-TYPE
    OBJECTS { 
              dls362_source_mac_address, 
              dls362_dest_mac_address,
              dls362_source_sap,
              dls362_dest_sap 
            }
    STATUS current
    DESCRIPTION
        "Notification of Event DLS.362

        Message: 'DLS, Receiver attempted to increment window greater than maximum window size for $1->$2, sap $3->$4'

        Parameters list:
              $1: dls362_source_mac_address
              $2: dls362_dest_mac_address
              $3: dls362_source_sap
              $4: dls362_dest_sap

        The receiver attempted to increment the window beyond the maximum
        window size."
    ::= { dlsNotificationsPrefix 362 }

dlsNotification363 NOTIFICATION-TYPE
    OBJECTS { 
              dls363_source_mac_address, 
              dls363_dest_mac_address,
              dls363_source_sap,
              dls363_dest_sap 
            }
    STATUS current
    DESCRIPTION
        "Notification of Event DLS.363

        Message: 'DLS, Receiver attempted to decrement window less than minimum window size for $1->$2, sap $3->$4'

        Parameters list:
              $1: dls363_source_mac_address
              $2: dls363_dest_mac_address
              $3: dls363_source_sap
              $4: dls363_dest_sap

        The receiver attempted to decrement the window beyond the minimum
        window size."
    ::= { dlsNotificationsPrefix 363 }

dlsNotification364 NOTIFICATION-TYPE
    OBJECTS { 
              dls364_ip_address, 
              dls364_source_mac_address,
              dls364_dest_mac_address,
              dls364_source_sap,
              dls364_dest_sap 
            }
    STATUS current
    DESCRIPTION
        "Notification of Event DLS.364

        Message: 'DLS, MAC cache hit, selecting $1 for $2->$3, sap $4->$5'

        Parameters list:
              $1: dls364_ip_address
              $2: dls364_source_mac_address
              $3: dls364_dest_mac_address
              $4: dls364_source_sap
              $5: dls364_dest_sap

        DLSw found an entry in the MAC cache for the target MAC address of
        this circuit. The router selected the partner with the indicated IP
        address for this circuit."
    ::= { dlsNotificationsPrefix 364 }

dlsNotification365 NOTIFICATION-TYPE
    OBJECTS { 
              dls365_source_mac_address, 
              dls365_dest_mac_address,
              dls365_source_sap,
              dls365_dest_sap 
            }
    STATUS current
    DESCRIPTION
        "Notification of Event DLS.365

        Message: 'DLS, MAC explorer already outstanding, queueing the explorer request for $1->$2, sap $3->$4'

        Parameters list:
              $1: dls365_source_mac_address
              $2: dls365_dest_mac_address
              $3: dls365_source_sap
              $4: dls365_dest_sap

        DLSw found an entry in the MAC cache for the target MAC address of
        this circuit with an explorer already outstanding. The router
        queued this MAC explorer request and will process it when the
        outstanding explorer completes."
    ::= { dlsNotificationsPrefix 365 }

dlsNotification366 NOTIFICATION-TYPE
    OBJECTS { 
              dls366_source_mac_address, 
              dls366_dest_mac_address,
              dls366_source_sap,
              dls366_dest_sap 
            }
    STATUS current
    DESCRIPTION
        "Notification of Event DLS.366

        Message: 'DLS, No memory to create explorer control block for $1->$2, sap $3->$4'

        Parameters list:
              $1: dls366_source_mac_address
              $2: dls366_dest_mac_address
              $3: dls366_source_sap
              $4: dls366_dest_sap

        Due to a memory shortage condition, DLSw could not create an explorer
        control block for the specified circuit. The exploration fails
        and the router does not start a circuit."
    ::= { dlsNotificationsPrefix 366 }

dlsNotification367 NOTIFICATION-TYPE
    OBJECTS { 
              dls367_target_mac_address 
            }
    STATUS current
    DESCRIPTION
        "Notification of Event DLS.367

        Message: 'DLS, Creating new MAC cache entry for $1'

        Parameters list:
              $1: dls367_target_mac_address

        The router creates a new cache entry for the
        specified target MAC address."
    ::= { dlsNotificationsPrefix 367 }

dlsNotification368 NOTIFICATION-TYPE
    OBJECTS { 
              dls368_target_mac_address 
            }
    STATUS current
    DESCRIPTION
        "Notification of Event DLS.368

        Message: 'DLS, Explorer priority wait timer expired for $1'

        Parameters list:
              $1: dls368_target_mac_address

        The priority wait timer expired for the specified target MAC
        address. The router is now attempting to satisfy the explorer request
        with the known DLSw partners that can reach this MAC address."
    ::= { dlsNotificationsPrefix 368 }

dlsNotification369 NOTIFICATION-TYPE
    OBJECTS { 
              dls369_source_mac_address, 
              dls369_dest_mac_address,
              dls369_source_sap,
              dls369_dest_sap 
            }
    STATUS current
    DESCRIPTION
        "Notification of Event DLS.369

        Message: 'DLS, MAC explorer satisfied for $1->$2, sap $3->$4'

        Parameters list:
              $1: dls369_source_mac_address
              $2: dls369_dest_mac_address
              $3: dls369_source_sap
              $4: dls369_dest_sap

        DLS found a partner DLSw router that satisfies the explorer for
        this circuit."
    ::= { dlsNotificationsPrefix 369 }

dlsNotification370 NOTIFICATION-TYPE
    OBJECTS { 
              dls370_target_mac_address 
            }
    STATUS current
    DESCRIPTION
        "Notification of Event DLS.370

        Message: 'DLS, ICANREACH-ex timer expired for $1'

        Parameters list:
              $1: dls370_target_mac_address

        The ICANREACH-ex timer expired for the specified target MAC
        address. The router is now attempting to satisfy the explorer request
        with the known DLSw partners that can reach this MAC address."
    ::= { dlsNotificationsPrefix 370 }

dlsNotification371 NOTIFICATION-TYPE
    OBJECTS { 
              dls371_source_mac_address, 
              dls371_dest_mac_address,
              dls371_source_sap,
              dls371_dest_sap 
            }
    STATUS current
    DESCRIPTION
        "Notification of Event DLS.371

        Message: 'DLS, MAC explorer failed for $1->$2, sap $3->$4'

        Parameters list:
              $1: dls371_source_mac_address
              $2: dls371_dest_mac_address
              $3: dls371_source_sap
              $4: dls371_dest_sap

        DLS failed to find a partner DLSw router that satisfies the MAC
        explorer for this circuit."
    ::= { dlsNotificationsPrefix 371 }

dlsNotification372 NOTIFICATION-TYPE
    OBJECTS { 
              dls372_source_mac_address, 
              dls372_dest_mac_address,
              dls372_source_sap,
              dls372_dest_sap 
            }
    STATUS current
    DESCRIPTION
        "Notification of Event DLS.372

        Message: 'DLS, Resolved timer expired, target MAC explorer failed for $1->$2, sap $3->$4'

        Parameters list:
              $1: dls372_source_mac_address
              $2: dls372_dest_mac_address
              $3: dls372_source_sap
              $4: dls372_dest_sap

        The target MAC explorer resolved timer expired without receiving
        a DLC_RESOLVED from any of the DLCs for the specified circuit. The
        target MAC address explorer failed."
    ::= { dlsNotificationsPrefix 372 }

dlsNotification373 NOTIFICATION-TYPE
    OBJECTS { 
              dls373_source_mac_address, 
              dls373_dest_mac_address,
              dls373_source_sap,
              dls373_dest_sap 
            }
    STATUS current
    DESCRIPTION
        "Notification of Event DLS.373

        Message: 'DLS, ICANREACH-ex received while exploring for $1->$2, sap $3->$4'

        Parameters list:
              $1: dls373_source_mac_address
              $2: dls373_dest_mac_address
              $3: dls373_source_sap
              $4: dls373_dest_sap

        The router received an ICANREACH-ex while it was already processing
        a previous ICANREACH-ex. The router ignored this new ICANREACH-ex
        request."
    ::= { dlsNotificationsPrefix 373 }

dlsNotification374 NOTIFICATION-TYPE
    OBJECTS { 
              dls374_source_mac_address, 
              dls374_dest_mac_address,
              dls374_source_sap,
              dls374_dest_sap 
            }
    STATUS current
    DESCRIPTION
        "Notification of Event DLS.374

        Message: 'DLS, No memory to create target explorer control block for $1->$2, sap $3->$4'

        Parameters list:
              $1: dls374_source_mac_address
              $2: dls374_dest_mac_address
              $3: dls374_source_sap
              $4: dls374_dest_sap

        DLS could not create a target explorer control block for the specified
        circuit due to a memory shortage condition. The exploration fails
        and the router does not start a circuit."
    ::= { dlsNotificationsPrefix 374 }

dlsNotification375 NOTIFICATION-TYPE
    OBJECTS { 
              dls375_source_mac_address, 
              dls375_dest_mac_address,
              dls375_source_sap,
              dls375_dest_sap 
            }
    STATUS current
    DESCRIPTION
        "Notification of Event DLS.375

        Message: 'DLS, DLC_RESOLVED not processed, CB not found $1->$2, sap $3->$4'

        Parameters list:
              $1: dls375_source_mac_address
              $2: dls375_dest_mac_address
              $3: dls375_source_sap
              $4: dls375_dest_sap

        A DLC sent DLC_RESOLVED. The router could not process the
        DLC_RESOLVED because the router could not find the corresponding
        control block. This may occur if the resolved timer already expired,
        or a DLC_RESOLVED from a different DLC already satisfied the target
        MAC address explorer."
    ::= { dlsNotificationsPrefix 375 }

dlsNotification376 NOTIFICATION-TYPE
    OBJECTS { 
              dls376_source_mac_address, 
              dls376_dest_mac_address,
              dls376_source_sap,
              dls376_dest_sap,
              dls376_largest_frame_size 
            }
    STATUS current
    DESCRIPTION
        "Notification of Event DLS.376

        Message: 'DLS, ICANREACH-ex sent for $1->$2, sap $3->$4 lfsize $5'

        Parameters list:
              $1: dls376_source_mac_address
              $2: dls376_dest_mac_address
              $3: dls376_source_sap
              $4: dls376_dest_sap
              $5: dls376_largest_frame_size

        The router sent an ICANREACH-ex for the specified circuit."
    ::= { dlsNotificationsPrefix 376 }

dlsNotification377 NOTIFICATION-TYPE
    OBJECTS { 
              dls377_target_mac_address 
            }
    STATUS current
    DESCRIPTION
        "Notification of Event DLS.377

        Message: 'DLS, Deleting MAC cache entry for $1'

        Parameters list:
              $1: dls377_target_mac_address

        The router deleted the MAC cache entry for the specified address."
    ::= { dlsNotificationsPrefix 377 }

dlsNotification378 NOTIFICATION-TYPE
    OBJECTS { 
              dls378_source_mac_address, 
              dls378_dest_mac_address,
              dls378_source_sap,
              dls378_dest_sap 
            }
    STATUS current
    DESCRIPTION
        "Notification of Event DLS.378

        Message: 'LLC, event LLCIM_DLC_RESOLVE received for $1->$2, sap $3->$4'

        Parameters list:
              $1: dls378_source_mac_address
              $2: dls378_dest_mac_address
              $3: dls378_source_sap
              $4: dls378_dest_sap

        LLC interface module for the DLS received a LLCIM_DLC_RESOLVE
        event from DLS."
    ::= { dlsNotificationsPrefix 378 }

dlsNotification379 NOTIFICATION-TYPE
    OBJECTS { 
              dls379_Destination, 
              dls379_Source,
              dls379_Dsap,
              dls379_Ssap 
            }
    STATUS current
    DESCRIPTION
        "Notification of Event DLS.379

        Message: 'LLC, FAILED passive open station, invalid sapcb, dst=$1, src=$2, dsap=$3, ssap=$4'

        Parameters list:
              $1: dls379_Destination
              $2: dls379_Source
              $3: dls379_Dsap
              $4: dls379_Ssap

        Passive open of station for LLC data link services failed because
        the SAP to open the station is invalid."
    ::= { dlsNotificationsPrefix 379 }

dlsNotification380 NOTIFICATION-TYPE
    OBJECTS { 
              dls380_Destination, 
              dls380_Source,
              dls380_Dsap,
              dls380_Ssap 
            }
    STATUS current
    DESCRIPTION
        "Notification of Event DLS.380

        Message: 'LLC, FAILED passive open stn, No memory, dst=$1, src=$2, dsap=$3, ssap=$4'

        Parameters list:
              $1: dls380_Destination
              $2: dls380_Source
              $3: dls380_Dsap
              $4: dls380_Ssap

        Passive open of station for LLC data link services failed because
        there is no memory available to create a control block to manage
        the connection."
    ::= { dlsNotificationsPrefix 380 }

dlsNotification381 NOTIFICATION-TYPE
    OBJECTS { 
              dls381_Reason, 
              dls381_Destination,
              dls381_Source,
              dls381_Dsap,
              dls381_Ssap 
            }
    STATUS current
    DESCRIPTION
        "Notification of Event DLS.381

        Message: 'LLC, FAILED passive open stn, rsn=$1, dst=$2, src=$3, dsap=$4, ssap=$5'

        Parameters list:
              $1: dls381_Reason
              $2: dls381_Destination
              $3: dls381_Source
              $4: dls381_Dsap
              $5: dls381_Ssap

        Passive open of station for LLC data link services failed due to
        some problems within LLC. The reason code is indicative of
        the specific problem."
    ::= { dlsNotificationsPrefix 381 }

dlsNotification382 NOTIFICATION-TYPE
    OBJECTS { 
              dls382_source_mac_address, 
              dls382_dest_mac_address,
              dls382_source_sap,
              dls382_dest_sap 
            }
    STATUS current
    DESCRIPTION
        "Notification of Event DLS.382

        Message: 'LLC, event LLCIM_DLC_CS_CONFIRM received for $1->$2, sap $3->$4'

        Parameters list:
              $1: dls382_source_mac_address
              $2: dls382_dest_mac_address
              $3: dls382_source_sap
              $4: dls382_dest_sap

        LLC interface module for the DLS received a LLCIM_DLC_CS_CONFIRM
        event from DLS."
    ::= { dlsNotificationsPrefix 382 }

dlsNotification383 NOTIFICATION-TYPE
    OBJECTS { 
              dls383_source_mac_address, 
              dls383_dest_mac_address,
              dls383_source_sap,
              dls383_dest_sap 
            }
    STATUS current
    DESCRIPTION
        "Notification of Event DLS.383

        Message: 'LLC, event LLCIM_DLC_HALT_NOACK received during exploration for $1->$2, sap $3->$4'

        Parameters list:
              $1: dls383_source_mac_address
              $2: dls383_dest_mac_address
              $3: dls383_source_sap
              $4: dls383_dest_sap

        LLC interface module for the DLS received a LLCIM_DLC_HALT_NOACK
        event from DLS during exploration."
    ::= { dlsNotificationsPrefix 383 }

dlsNotification384 NOTIFICATION-TYPE
    OBJECTS { 
              dls384_source_mac_address, 
              dls384_dest_mac_address,
              dls384_source_sap,
              dls384_dest_sap 
            }
    STATUS current
    DESCRIPTION
        "Notification of Event DLS.384

        Message: 'LLC, event LLCIM_DLC_HALT_NOACK received during target exploration for $1->$2, sap $3->$4'

        Parameters list:
              $1: dls384_source_mac_address
              $2: dls384_dest_mac_address
              $3: dls384_source_sap
              $4: dls384_dest_sap

        LLC interface module for the DLS received a LLCIM_DLC_HALT_NOACK
        event from DLS during target side exploration."
    ::= { dlsNotificationsPrefix 384 }

dlsNotification385 NOTIFICATION-TYPE
    OBJECTS { 
              dls385_source_mac_address, 
              dls385_dest_mac_address,
              dls385_source_sap,
              dls385_dest_sap 
            }
    STATUS current
    DESCRIPTION
        "Notification of Event DLS.385

        Message: 'LLC, event LLCIM_DLC_HALT_NOACK received for $1->$2, sap $3->$4'

        Parameters list:
              $1: dls385_source_mac_address
              $2: dls385_dest_mac_address
              $3: dls385_source_sap
              $4: dls385_dest_sap

        LLC interface module for the DLS received a LLCIM_DLC_HALT_NOACK
        event from DLS."
    ::= { dlsNotificationsPrefix 385 }

dlsNotification386 NOTIFICATION-TYPE
    OBJECTS { 
              dls386_source_mac_address, 
              dls386_dest_mac_address,
              dls386_source_sap,
              dls386_dest_sap 
            }
    STATUS current
    DESCRIPTION
        "Notification of Event DLS.386

        Message: 'LLC, No memory to create LLC explorer control block for $1->$2, sap $3->$4'

        Parameters list:
              $1: dls386_source_mac_address
              $2: dls386_dest_mac_address
              $3: dls386_source_sap
              $4: dls386_dest_sap

        Due to a memory shortage condition, LLCIM could not create an explorer
        control block for the specified circuit. The exploration fails and
        the router does not start a circuit."
    ::= { dlsNotificationsPrefix 386 }

dlsNotification387 NOTIFICATION-TYPE
    OBJECTS { 
              dls387_source_mac_address, 
              dls387_dest_mac_address,
              dls387_source_sap,
              dls387_dest_sap 
            }
    STATUS current
    DESCRIPTION
        "Notification of Event DLS.387

        Message: 'LLC, Receivd passive open SABME for $1->$2, sap $3->$4'

        Parameters list:
              $1: dls387_source_mac_address
              $2: dls387_dest_mac_address
              $3: dls387_source_sap
              $4: dls387_dest_sap

        The LLC Interface module for the DLS received a SABME for a station
        that the router had not opened. This causes a passive open for the
        LLC station."
    ::= { dlsNotificationsPrefix 387 }

dlsNotification388 NOTIFICATION-TYPE
    OBJECTS { 
              dls388_source_mac_address, 
              dls388_dest_mac_address,
              dls388_source_sap,
              dls388_dest_sap 
            }
    STATUS current
    DESCRIPTION
        "Notification of Event DLS.388

        Message: 'LLC, No memory to allocate LLC explorer buffer for $1->$2, sap $3->$4'

        Parameters list:
              $1: dls388_source_mac_address
              $2: dls388_dest_mac_address
              $3: dls388_source_sap
              $4: dls388_dest_sap

        Due to a memory shortage condition, the LLC interface module could not
        allocate an explorer buffer for the specified circuit. The
        exploration fails and the router does not start a circuit."
    ::= { dlsNotificationsPrefix 388 }

dlsNotification389 NOTIFICATION-TYPE
    OBJECTS { 
              dls389_source_mac_address, 
              dls389_dest_mac_address,
              dls389_source_sap,
              dls389_dest_sap 
            }
    STATUS current
    DESCRIPTION
        "Notification of Event DLS.389

        Message: 'LLC, No memory to create LLC target explorer control block for $1->$2, sap $3->$4'

        Parameters list:
              $1: dls389_source_mac_address
              $2: dls389_dest_mac_address
              $3: dls389_source_sap
              $4: dls389_dest_sap

        Due to a memory shortage condition, LLCIM could not create a target
        explorer control block for the specified circuit. The exploration
        fails and the router does not start a circuit."
    ::= { dlsNotificationsPrefix 389 }

dlsNotification390 NOTIFICATION-TYPE
    OBJECTS { 
              dls390_Destination, 
              dls390_Source,
              dls390_Dsap,
              dls390_Ssap 
            }
    STATUS current
    DESCRIPTION
        "Notification of Event DLS.390

        Message: 'LLC, opened stn passive, dst=$1, src=$2, dsap=$3, ssap=$4'

        Parameters list:
              $1: dls390_Destination
              $2: dls390_Source
              $3: dls390_Dsap
              $4: dls390_Ssap

        Passive open of station for LLC data link services succeeded."
    ::= { dlsNotificationsPrefix 390 }

dlsNotification391 NOTIFICATION-TYPE
    OBJECTS { 
              dls391_old_tx_window, 
              dls391_new_tx_window,
              dls391_source_mac_address,
              dls391_dest_mac_address,
              dls391_source_sap,
              dls391_dest_sap 
            }
    STATUS current
    DESCRIPTION
        "Notification of Event DLS.391

        Message: 'LLC, Changed transmit window from $1 to $2 for $3->$4, sap $5->$6'

        Parameters list:
              $1: dls391_old_tx_window
              $2: dls391_new_tx_window
              $3: dls391_source_mac_address
              $4: dls391_dest_mac_address
              $5: dls391_source_sap
              $6: dls391_dest_sap

        LLCIM has changed the transmit window to match the receive window
        requested in an XID-3 received from a PU 2.1 LLC end station."
    ::= { dlsNotificationsPrefix 391 }

dlsNotification392 NOTIFICATION-TYPE
    OBJECTS { 
              dls392_old_tx_window, 
              dls392_new_tx_window,
              dls392_return_code,
              dls392_source_mac_address,
              dls392_dest_mac_address,
              dls392_source_sap,
              dls392_dest_sap 
            }
    STATUS current
    DESCRIPTION
        "Notification of Event DLS.392

        Message: 'LLC, Could not change transmit window from $1 to $2, return = $3 for $4->$5, sap $6->$7'

        Parameters list:
              $1: dls392_old_tx_window
              $2: dls392_new_tx_window
              $3: dls392_return_code
              $4: dls392_source_mac_address
              $5: dls392_dest_mac_address
              $6: dls392_source_sap
              $7: dls392_dest_sap

        LLCIM could not change the transmit window to match the window
        requested in an XID-3 received from a PU 2.1 LLC end station. The
        dl_open_station function call failed with the specified return_code."
    ::= { dlsNotificationsPrefix 392 }

dlsNotification393 NOTIFICATION-TYPE
    OBJECTS { 
              dls393_ip_address 
            }
    STATUS current
    DESCRIPTION
        "Notification of Event DLS.393

        Message: 'A Runtime Capabilities Exchange Request has been sent to the DLSw neighbor at $1'

        Parameters list:
              $1: dls393_ip_address

        The router sent a runtime Capabilities Exchange Request message
        to the DLSw neighbor. This is the result of a change to the information
        that was initially exchanged."
    ::= { dlsNotificationsPrefix 393 }

dlsNotification394 NOTIFICATION-TYPE
    OBJECTS { 
              dls394_interface, 
              dls394_sap 
            }
    STATUS current
    DESCRIPTION
        "Notification of Event DLS.394

        Message: 'Invalid interface number $1 in Intf/SAP record with SAP $2'

        Parameters list:
              $1: dls394_interface
              $2: dls394_sap

        DLSw detected an invalid configuration parameter at start-up time.
        The interface on which DLSw is to open an LLC SAP does not exist on
        the router. You should change the configuration and restart
        the router."
    ::= { dlsNotificationsPrefix 394 }

dlsNotification395 NOTIFICATION-TYPE
    OBJECTS { 
              dls395_interface, 
              dls395_link_address 
            }
    STATUS current
    DESCRIPTION
        "Notification of Event DLS.395

        Message: 'Invalid intf number $1 for SDLC station record with link addr $2'

        Parameters list:
              $1: dls395_interface
              $2: dls395_link_address

        DLSw detected an invalid configuration parameter at start-up time.
        The interface specified for a DLSw SDLC link station either does not
        exist or is not of type SDLC. You should change the configuration and
        restart the router."
    ::= { dlsNotificationsPrefix 395 }

dlsNotification396 NOTIFICATION-TYPE
    OBJECTS { 
              dls396_sap, 
              dls396_interface 
            }
    STATUS current
    DESCRIPTION
        "Notification of Event DLS.396

        Message: 'Invalid SAP number $1 in Intf/SAP record for interface $2'

        Parameters list:
              $1: dls396_sap
              $2: dls396_interface

        DLSw detected an invalid configuration parameter at start-up time.
        The SAP value that DLSw is to open on the specified interface is odd or
        outside the allowable range. Change the configuration and restart
        the router."
    ::= { dlsNotificationsPrefix 396 }

dlsNotification397 NOTIFICATION-TYPE
    OBJECTS { 
              dls397_sap, 
              dls397_interface,
              dls397_link_address 
            }
    STATUS current
    DESCRIPTION
        "Notification of Event DLS.397

        Message: 'Invalid source SAP $1 in SDLC record for intfc $2, addr $3'

        Parameters list:
              $1: dls397_sap
              $2: dls397_interface
              $3: dls397_link_address

        DLSw detected an invalid configuration parameter at start-up time.
        The source SAP for an SDLC link station is outside the allowable range.
        DLSw has not added this SDLC link station. You should change
        the configuration and restart the router."
    ::= { dlsNotificationsPrefix 397 }

dlsNotification398 NOTIFICATION-TYPE
    OBJECTS { 
              dls398_buf_size 
            }
    STATUS current
    DESCRIPTION
        "Notification of Event DLS.398

        Message: 'Invalid TCP receive buffer size $1 for a neighbor or group'

        Parameters list:
              $1: dls398_buf_size

        DLSw detected an invalid configuration parameter at start-up time.
        The neighbor or group receive buffer size was outside the allowable
        range, but DLSw adjusted it to the nearest range limit and processed
        the configuration record anyway. Fix the configuration
        at some point by comparing with console information to isolate the
        problem and restart the router."
    ::= { dlsNotificationsPrefix 398 }

dlsNotification399 NOTIFICATION-TYPE
    OBJECTS { 
              dls399_priority_value 
            }
    STATUS current
    DESCRIPTION
        "Notification of Event DLS.399

        Message: 'Invalid neighbor priority $1 for neighbor or group record'

        Parameters list:
              $1: dls399_priority_value

        DLSw detected an invalid configuration parameter at start-up time.
        The neighbor priority value was outside the allowable range, but DLSw
        adjusted it to the nearest range limit and processed the configuration
        record anyway. Fix the configuration by comparing with
        console information to isolate the problem and restart the router."
    ::= { dlsNotificationsPrefix 399 }

dlsNotification400 NOTIFICATION-TYPE
    OBJECTS { 
              dls400_timer_value 
            }
    STATUS current
    DESCRIPTION
        "Notification of Event DLS.400

        Message: 'Invalid priority wait timer $1 (in tenth seconds)'

        Parameters list:
              $1: dls400_timer_value

        DLSw detected an invalid configuration parameter at start-up time.
        The priority wait timer value was outside the allowable range, but
        DLSw adjusted it to the nearest range limit and will use the adjusted
        value. Fix the configuration and restart the router."
    ::= { dlsNotificationsPrefix 400 }

dlsNotification401 NOTIFICATION-TYPE
    OBJECTS { 
              dls401_priority_value, 
              dls401_protocol 
            }
    STATUS current
    DESCRIPTION
        "Notification of Event DLS.401

        Message: 'Invalid DLSw session priority $1 for $2 DLSw sessions'

        Parameters list:
              $1: dls401_priority_value
              $2: dls401_protocol

        DLSw detected an invalid configuration parameter at start-up time.
        The session priority for either SNA or NetBIOS is out of
        range, but DLSw adjusted it to the nearest range limit and will
        use the adjusted value. Fix the configuration and
        restart the router."
    ::= { dlsNotificationsPrefix 401 }

dlsNotification402 NOTIFICATION-TYPE
    OBJECTS { 
              dls402_frame_alloc_value 
            }
    STATUS current
    DESCRIPTION
        "Notification of Event DLS.402

        Message: 'Invalid session priority frame allocation value $1'

        Parameters list:
              $1: dls402_frame_alloc_value

        DLSw detected an invalid configuration parameter at start-up time.
        The value for the number of frames to be sent at one of the four
        session priorities is out of range, but DLSw adjusted it to the
        nearest range limit and will use the adjusted value.
        Fix the configuration by comparing with console information
        to isolate the problem and restart the router."
    ::= { dlsNotificationsPrefix 402 }

dlsNotification403 NOTIFICATION-TYPE
    OBJECTS { 
              dls403_mtu_size 
            }
    STATUS current
    DESCRIPTION
        "Notification of Event DLS.403

        Message: 'Invalid NetBIOS maximum transmission unit size $1'

        Parameters list:
              $1: dls403_mtu_size

        DLSw detected an invalid configuration parameter at start-up time.
        The NetBIOS MTU size is out of range, but DLSw adjusted it to
        the nearest range limit and will use the adjusted value.
        Fix the configuration and restart the router."
    ::= { dlsNotificationsPrefix 403 }

dlsNotification404 NOTIFICATION-TYPE
    OBJECTS { 
              dls404_interface 
            }
    STATUS current
    DESCRIPTION
        "Notification of Event DLS.404

        Message: 'SNA SAP configured on interface $1, but not SAP 00'

        Parameters list:
              $1: dls404_interface

        DLSw detected an invalid configuration condition at start-up time.
        One of the standard SNA SAPs (04, 08, or 0C) is open on an interface,
        but SAP 00 is not open on the same interface. Without SAP 00 open,
        SNA data link switching will not work. The router cannot establish
        circuits. If you did not intend to temporarily disable an interface
        for DLSw, fix the configuration by opening SAP 00, where
        needed, and restart the router."
    ::= { dlsNotificationsPrefix 404 }

dlsNotification405 NOTIFICATION-TYPE
    OBJECTS { 
              dls405_source_mac_address 
            }
    STATUS current
    DESCRIPTION
        "Notification of Event DLS.405

        Message: 'Duplicate SDLC source MAC address $1 detected'

        Parameters list:
              $1: dls405_source_mac_address

        DLSw detected an invalid configuration condition at start-up time.
        A DLSw SDLC source MAC address has been duplicated within the router,
        either on the same SDLC interface or on a different one. The router
        permits only one occurrence of a given source MAC address, and DLSw
        uses only the first one encountered. Fix the configuration
        and restart the router."
    ::= { dlsNotificationsPrefix 405 }

dlsNotification406 NOTIFICATION-TYPE
    STATUS current
    DESCRIPTION
        "Notification of Event DLS.406

        Message: 'dummy'

        dummy."
    ::= { dlsNotificationsPrefix 406 }

dlsNotification407 NOTIFICATION-TYPE
    OBJECTS { 
              dls407_source_mac_address, 
              dls407_dest_mac_address,
              dls407_source_sap,
              dls407_dest_sap 
            }
    STATUS current
    DESCRIPTION
        "Notification of Event DLS.407

        Message: 'DLS, Receiver attempted to halve window below the minimum window size for $1->$2, sap $3->$4'

        Parameters list:
              $1: dls407_source_mac_address
              $2: dls407_dest_mac_address
              $3: dls407_source_sap
              $4: dls407_dest_sap

        The receiver attempted to halve the window below the minimum
        window size."
    ::= { dlsNotificationsPrefix 407 }

dlsNotification408 NOTIFICATION-TYPE
    OBJECTS { 
              dls408_source_mac_address, 
              dls408_dest_mac_address,
              dls408_source_sap,
              dls408_dest_sap,
              dls408_rxgrant,
              dls408_rxwindow 
            }
    STATUS current
    DESCRIPTION
        "Notification of Event DLS.408

        Message: 'DLS, FCACK recv'd for $1->$2, sap $3->$4 rx_grant=$5 rx_window=$6'

        Parameters list:
              $1: dls408_source_mac_address
              $2: dls408_dest_mac_address
              $3: dls408_source_sap
              $4: dls408_dest_sap
              $5: dls408_rxgrant
              $6: dls408_rxwindow

        The router received an IFCM ACK or piggybacked flow control
        acknowledgement SSP message."
    ::= { dlsNotificationsPrefix 408 }

dlsNotification409 NOTIFICATION-TYPE
    OBJECTS { 
              dls409_ip_address, 
              dls409_source_mac_address,
              dls409_dest_mac_address,
              dls409_source_sap,
              dls409_dest_sap 
            }
    STATUS current
    DESCRIPTION
        "Notification of Event DLS.409

        Message: 'DLS, (PacingQ) DGRMFRAME to $1 sent for $2->$3, sap $4->$5'

        Parameters list:
              $1: dls409_ip_address
              $2: dls409_source_mac_address
              $3: dls409_dest_mac_address
              $4: dls409_source_sap
              $5: dls409_dest_sap

        DLS successfully sent out a DGRMFRAME SSP message from the PacingQ
        over TCP to its DLS peer."
    ::= { dlsNotificationsPrefix 409 }

dlsNotification410 NOTIFICATION-TYPE
    OBJECTS { 
              dls410_ip_address, 
              dls410_source_mac_address,
              dls410_dest_mac_address,
              dls410_source_sap,
              dls410_dest_sap 
            }
    STATUS current
    DESCRIPTION
        "Notification of Event DLS.410

        Message: 'DLS, (PacingQ) INFOFRAME to $1 sent for $2->$3, sap $4->$5'

        Parameters list:
              $1: dls410_ip_address
              $2: dls410_source_mac_address
              $3: dls410_dest_mac_address
              $4: dls410_source_sap
              $5: dls410_dest_sap

        DLS successfully sent out an INFOFRAME SSP message from the PacingQ
        over TCP to its DLS peer."
    ::= { dlsNotificationsPrefix 410 }

dlsNotification411 NOTIFICATION-TYPE
    OBJECTS { 
              dls411_pool, 
              dls411_pstatus 
            }
    STATUS current
    DESCRIPTION
        "Notification of Event DLS.411

        Message: 'DLS, Pool status for $1 pool is $2'

        Parameters list:
              $1: dls411_pool
              $2: dls411_pstatus

        The router reported the status of a DLSw buffer pool."
    ::= { dlsNotificationsPrefix 411 }

dlsNotification412 NOTIFICATION-TYPE
    OBJECTS { 
              dls412_operator, 
              dls412_source_mac_address,
              dls412_dest_mac_address,
              dls412_source_sap,
              dls412_dest_sap 
            }
    STATUS current
    DESCRIPTION
        "Notification of Event DLS.412

        Message: 'DLS, Received invalid window operator $1 for $2->$3, sap $4->$5 after receiving RESET operator'

        Parameters list:
              $1: dls412_operator
              $2: dls412_source_mac_address
              $3: dls412_dest_mac_address
              $4: dls412_source_sap
              $5: dls412_dest_sap

        The router received an invalid window operator after receiving a
        RESET operator."
    ::= { dlsNotificationsPrefix 412 }

dlsNotification413 NOTIFICATION-TYPE
    OBJECTS { 
              dls413_operator, 
              dls413_source_mac_address,
              dls413_dest_mac_address,
              dls413_source_sap,
              dls413_dest_sap 
            }
    STATUS current
    DESCRIPTION
        "Notification of Event DLS.413

        Message: 'DLS, Pacing task called to process $1 for $2->$3, sap $4->$5'

        Parameters list:
              $1: dls413_operator
              $2: dls413_source_mac_address
              $3: dls413_dest_mac_address
              $4: dls413_source_sap
              $5: dls413_dest_sap

        The router called the pacing operator scheduler to process a scheduled
        pacing action."
    ::= { dlsNotificationsPrefix 413 }

dlsNotification414 NOTIFICATION-TYPE
    STATUS current
    DESCRIPTION
        "Notification of Event DLS.414

        Message: 'Placeholder for wntaylor'

        Placeholder for wntaylor."
    ::= { dlsNotificationsPrefix 414 }

dlsNotification415 NOTIFICATION-TYPE
    OBJECTS { 
              dls415_ip_address, 
              dls415_source_mac_address,
              dls415_dest_mac_address,
              dls415_source_sap,
              dls415_dest_sap 
            }
    STATUS current
    DESCRIPTION
        "Notification of Event DLS.415

        Message: 'DLS forwarder received a SSP NETBIOS_NQ message over TCP connection to $1 for $2->$3, sap $4->$5'

        Parameters list:
              $1: dls415_ip_address
              $2: dls415_source_mac_address
              $3: dls415_dest_mac_address
              $4: dls415_source_sap
              $5: dls415_dest_sap

        DLS forwarder received a Switch to Switch Protocol message of
        NETBIOS_NQ over TCP."
    ::= { dlsNotificationsPrefix 415 }

dlsNotification416 NOTIFICATION-TYPE
    OBJECTS { 
              dls416_ip_address, 
              dls416_source_mac_address,
              dls416_dest_mac_address,
              dls416_source_sap,
              dls416_dest_sap 
            }
    STATUS current
    DESCRIPTION
        "Notification of Event DLS.416

        Message: 'DLS forwarder received a SSP NETBIOS_NR message over TCP connection to $1 for $2->$3, sap $4->$5'

        Parameters list:
              $1: dls416_ip_address
              $2: dls416_source_mac_address
              $3: dls416_dest_mac_address
              $4: dls416_source_sap
              $5: dls416_dest_sap

        DLS forwarder received a Switch to Switch Protocol message of
        NETBIOS_NR over TCP."
    ::= { dlsNotificationsPrefix 416 }

dlsNotification417 NOTIFICATION-TYPE
    OBJECTS { 
              dls417_ip_address, 
              dls417_source_mac_address,
              dls417_dest_mac_address,
              dls417_source_sap,
              dls417_dest_sap 
            }
    STATUS current
    DESCRIPTION
        "Notification of Event DLS.417

        Message: 'DLS forwarder received a SSP NETBIOS_ANQ message over TCP connection to $1 for $2->$3, sap $4->$5'

        Parameters list:
              $1: dls417_ip_address
              $2: dls417_source_mac_address
              $3: dls417_dest_mac_address
              $4: dls417_source_sap
              $5: dls417_dest_sap

        DLS forwarder received a Switch to Switch Protocol message of
        NETBIOS_ANQ over TCP."
    ::= { dlsNotificationsPrefix 417 }

dlsNotification418 NOTIFICATION-TYPE
    OBJECTS { 
              dls418_ip_address, 
              dls418_source_mac_address,
              dls418_dest_mac_address,
              dls418_source_sap,
              dls418_dest_sap 
            }
    STATUS current
    DESCRIPTION
        "Notification of Event DLS.418

        Message: 'DLS forwarder received a SSP NETBIOS_ANR message over TCP connection to $1 for $2->$3, sap $4->$5'

        Parameters list:
              $1: dls418_ip_address
              $2: dls418_source_mac_address
              $3: dls418_dest_mac_address
              $4: dls418_source_sap
              $5: dls418_dest_sap

        DLS forwarder received a Switch to Switch Protocol message of
        NETBIOS_ANR over TCP."
    ::= { dlsNotificationsPrefix 418 }

dlsNotification419 NOTIFICATION-TYPE
    OBJECTS { 
              dls419_ip_address, 
              dls419_source_mac_address,
              dls419_dest_mac_address,
              dls419_source_sap,
              dls419_dest_sap 
            }
    STATUS current
    DESCRIPTION
        "Notification of Event DLS.419

        Message: 'DLS, NETBIOS_NQ to $1 sent for $2->$3, sap $4->$5'

        Parameters list:
              $1: dls419_ip_address
              $2: dls419_source_mac_address
              $3: dls419_dest_mac_address
              $4: dls419_source_sap
              $5: dls419_dest_sap

        DLS successfully sent out a NETBIOS_NQ SSP message over TCP to its
        DLS peer."
    ::= { dlsNotificationsPrefix 419 }

dlsNotification420 NOTIFICATION-TYPE
    OBJECTS { 
              dls420_ip_address, 
              dls420_source_mac_address,
              dls420_dest_mac_address,
              dls420_source_sap,
              dls420_dest_sap 
            }
    STATUS current
    DESCRIPTION
        "Notification of Event DLS.420

        Message: 'DLS, NETBIOS_NR to $1 sent for $2->$3, sap $4->$5'

        Parameters list:
              $1: dls420_ip_address
              $2: dls420_source_mac_address
              $3: dls420_dest_mac_address
              $4: dls420_source_sap
              $5: dls420_dest_sap

        DLS successfully sent out a NETBIOS_NR SSP message over TCP to its
        DLS peer."
    ::= { dlsNotificationsPrefix 420 }

dlsNotification421 NOTIFICATION-TYPE
    OBJECTS { 
              dls421_ip_address, 
              dls421_source_mac_address,
              dls421_dest_mac_address,
              dls421_source_sap,
              dls421_dest_sap 
            }
    STATUS current
    DESCRIPTION
        "Notification of Event DLS.421

        Message: 'DLS, NETBIOS_ANQ to $1 sent for $2->$3, sap $4->$5'

        Parameters list:
              $1: dls421_ip_address
              $2: dls421_source_mac_address
              $3: dls421_dest_mac_address
              $4: dls421_source_sap
              $5: dls421_dest_sap

        DLS successfully sent out a NETBIOS_ANQ SSP message over TCP to its
        DLS peer."
    ::= { dlsNotificationsPrefix 421 }

dlsNotification422 NOTIFICATION-TYPE
    OBJECTS { 
              dls422_ip_address, 
              dls422_source_mac_address,
              dls422_dest_mac_address,
              dls422_source_sap,
              dls422_dest_sap 
            }
    STATUS current
    DESCRIPTION
        "Notification of Event DLS.422

        Message: 'DLS, NETBIOS_ANR to $1 sent for $2->$3, sap $4->$5'

        Parameters list:
              $1: dls422_ip_address
              $2: dls422_source_mac_address
              $3: dls422_dest_mac_address
              $4: dls422_source_sap
              $5: dls422_dest_sap

        DLS successfully sent out a NETBIOS_ANR SSP message over TCP to its
        DLS peer."
    ::= { dlsNotificationsPrefix 422 }

dlsNotification423 NOTIFICATION-TYPE
    STATUS current
    DESCRIPTION
        "Notification of Event DLS.423

        Message: 'no memory to initialize NetBIOS DLSw function'

        There was not enough memory available to initialize the NetBIOS
        DLSw function. The router needs memory for a session control block
        and a UI traffic buffer pool."
    ::= { dlsNotificationsPrefix 423 }

dlsNotification424 NOTIFICATION-TYPE
    OBJECTS { 
              dls424_NBName 
            }
    STATUS current
    DESCRIPTION
        "Notification of Event DLS.424

        Message: 'NetBIOS Name_Recognized frame for dest name $1 rejected because it lowered the largest frame size'

        Parameters list:
              $1: dls424_NBName

        The router received an SSP NETBIOS_NQ message earlier with the largest
        frame field. The message indicated that DLSw could not lower the
        largest frame size. The router discarded this corresponding
        Name_Recognized frame because it would have lowered the largest frame
        size."
    ::= { dlsNotificationsPrefix 424 }

dlsNotification425 NOTIFICATION-TYPE
    STATUS current
    DESCRIPTION
        "Notification of Event DLS.425

        Message: 'NetBIOS SSP message received without the required DLC header'

        All NetBIOS SSP messages must have a DLC header.
        This SSP message did not have one, but the router will continue to
        process the frame. This indicates an RFC 1795 compatibility problem."
    ::= { dlsNotificationsPrefix 425 }

dlsNotification426 NOTIFICATION-TYPE
    OBJECTS { 
              dls426_ip_address, 
              dls426_NBName 
            }
    STATUS current
    DESCRIPTION
        "Notification of Event DLS.426

        Message: 'DLS, Learning new NBName-IP association from $1 for $2'

        Parameters list:
              $1: dls426_ip_address
              $2: dls426_NBName

        DLS is learning a new NetBIOS name and IP association from an SSP
        message received from the peer DLS. This typically occurs during
        NETBIOS_NR message receipt time."
    ::= { dlsNotificationsPrefix 426 }

dlsNotification427 NOTIFICATION-TYPE
    OBJECTS { 
              dls427_Destination, 
              dls427_Source,
              dls427_Dsap,
              dls427_Ssap 
            }
    STATUS current
    DESCRIPTION
        "Notification of Event DLS.427

        Message: 'LLC, FAILED open NetBIOS stn, dst=$1, src=$2, dsap=$3, ssap=$4'

        Parameters list:
              $1: dls427_Destination
              $2: dls427_Source
              $3: dls427_Dsap
              $4: dls427_Ssap

        The opening of a NetBIOS station for LLC data link services failed
        due to some problems within LLC."
    ::= { dlsNotificationsPrefix 427 }

dlsNotification428 NOTIFICATION-TYPE
    OBJECTS { 
              dls428_source_mac_address, 
              dls428_dest_mac_address,
              dls428_source_sap,
              dls428_dest_sap 
            }
    STATUS current
    DESCRIPTION
        "Notification of Event DLS.428

        Message: 'LLC, NetBIOS UI frame discarded (pool congested) for $1->$2, sap $3->$4'

        Parameters list:
              $1: dls428_source_mac_address
              $2: dls428_dest_mac_address
              $3: dls428_source_sap
              $4: dls428_dest_sap

        The LCC interface module is discarding the NetBIOS UI frames it
        received from the LLC. The NetBIOS UI frame buffer pool is congested."
    ::= { dlsNotificationsPrefix 428 }

dlsNotification429 NOTIFICATION-TYPE
    STATUS current
    DESCRIPTION
        "Notification of Event DLS.429

        Message: 'DLS, NetBIOS function is enabled'

        DLSw NetBIOS function is now enabled. This occurs whenever the
        NetBIOS SAP (0xf0) is enabled on at least one port."
    ::= { dlsNotificationsPrefix 429 }

dlsNotification430 NOTIFICATION-TYPE
    STATUS current
    DESCRIPTION
        "Notification of Event DLS.430

        Message: 'DLS, NetBIOS function is disabled'

        DLSw NetBIOS function is now disabled. This occurs whenever the
        NetBIOS SAP (0xf0) is disabled on all ports."
    ::= { dlsNotificationsPrefix 430 }

dlsNotification431 NOTIFICATION-TYPE
    OBJECTS { 
              dls431_source_mac_address, 
              dls431_dest_mac_address,
              dls431_source_sap,
              dls431_dest_sap,
              dls431_phase 
            }
    STATUS current
    DESCRIPTION
        "Notification of Event DLS.431

        Message: 'DLS, Broadcast CANUREACH-ex unsuccessful for $1->$2, sap $3->$4 explore phase $5'

        Parameters list:
              $1: dls431_source_mac_address
              $2: dls431_dest_mac_address
              $3: dls431_source_sap
              $4: dls431_dest_sap
              $5: dls431_phase

        The router could not send CANUREACH-ex to any DLSw partners. Either
        there are no DLSw partners with transport connections in the proper
        state, no DLSw partners that support circuits for the requested SAPs,
        or the router could not allocate buffers for sending the CANUREACH-ex.
        Exploring phases: (0) Broadcast to all DLS partner(s).
        (1) Broadcast to priorized DLS partner(s).
        (2) Broadcast to no priorized DLS partner(s)."
    ::= { dlsNotificationsPrefix 431 }

dlsNotification432 NOTIFICATION-TYPE
    OBJECTS { 
              dls432_source_mac_address, 
              dls432_dest_mac_address,
              dls432_source_sap,
              dls432_dest_sap 
            }
    STATUS current
    DESCRIPTION
        "Notification of Event DLS.432

        Message: 'LLC, Source SAP not open, DLS_START_DL not processed for $1->$2, sap $3->$4'

        Parameters list:
              $1: dls432_source_mac_address
              $2: dls432_dest_mac_address
              $3: dls432_source_sap
              $4: dls432_dest_sap

        The router could not process a DLC_START_DL request because the source
        SAP specified has not been opened on any network interfaces."
    ::= { dlsNotificationsPrefix 432 }

dlsNotification433 NOTIFICATION-TYPE
    OBJECTS { 
              dls433_ip_address, 
              dls433_source_mac_address,
              dls433_dest_mac_address,
              dls433_source_sap,
              dls433_dest_sap,
              dls433_largest_frame_size 
            }
    STATUS current
    DESCRIPTION
        "Notification of Event DLS.433

        Message: 'DLS, CANUREACH_ex to $1 sent for $2->$3, sap $4->$5 lfsize $6'

        Parameters list:
              $1: dls433_ip_address
              $2: dls433_source_mac_address
              $3: dls433_dest_mac_address
              $4: dls433_source_sap
              $5: dls433_dest_sap
              $6: dls433_largest_frame_size

        DLSw successfully sent out a CANUREACH_ex SSP message over TCP
        to its DLSw peer."
    ::= { dlsNotificationsPrefix 433 }

dlsNotification434 NOTIFICATION-TYPE
    OBJECTS { 
              dls434_ip_address 
            }
    STATUS current
    DESCRIPTION
        "Notification of Event DLS.434

        Message: 'TCP, new connect request from neighbor $1, closing existing connection'

        Parameters list:
              $1: dls434_ip_address

        A remote DLSw neighbor is attempting to connect. A TCP
        connection already exists with this neighbor. The old TCP
        connection will be torn down. This happens when a remote DLSw either
        restarts or a remote communications problem caused the remote
        DLSw to close the connection, but the local DLSw TCP connection
        has not yet detected it."
    ::= { dlsNotificationsPrefix 434 }

dlsNotification435 NOTIFICATION-TYPE
    STATUS current
    DESCRIPTION
        "Notification of Event DLS.435

        Message: 'TCP, no memory to post a new TCP listen - will retry later'

        There is insufficient memory to post a new TCP listen. The router
        will attempt to post another TCP listen in 10 seconds.
        During this time, the router will not accept any new TCP connections
        until sufficient memory becomes available."
    ::= { dlsNotificationsPrefix 435 }

dlsNotification436 NOTIFICATION-TYPE
    OBJECTS { 
              dls436_ip_address, 
              dls436_source_mac_address,
              dls436_dest_mac_address,
              dls436_source_sap,
              dls436_dest_sap,
              dls436_largest_frame_size 
            }
    STATUS current
    DESCRIPTION
        "Notification of Event DLS.436

        Message: 'DLS, CANUREACH_cs to $1 sent for $2->$3, sap $4->$5 lfsize $6'

        Parameters list:
              $1: dls436_ip_address
              $2: dls436_source_mac_address
              $3: dls436_dest_mac_address
              $4: dls436_source_sap
              $5: dls436_dest_sap
              $6: dls436_largest_frame_size

        DLSw successfully sent out a CANUREACH_cs SSP message over TCP
        to its DLSw peer."
    ::= { dlsNotificationsPrefix 436 }

dlsNotification437 NOTIFICATION-TYPE
    OBJECTS { 
              dls437_source_mac_address, 
              dls437_dest_mac_address,
              dls437_source_sap,
              dls437_dest_sap 
            }
    STATUS current
    DESCRIPTION
        "Notification of Event DLS.437

        Message: 'DLS, ICANREACH-cs received with lfsize less than requested for $1->$2, sap $3->$4'

        Parameters list:
              $1: dls437_source_mac_address
              $2: dls437_dest_mac_address
              $3: dls437_source_sap
              $4: dls437_dest_sap

        An ICANREACH-cs SSP message received from a DLSw neighbor contained an
        lfsize value less than what the router sent in the CANUREACH-cs. This
        is a DLSw protocol violation by the neighbor DLSw because the lfsize
        control flag was set in the CANUREACH-cs indicating that the neighbor
        should fail the circuit setup if it cannot establish a circuit with
        the lfsize the router requested in the CANUREACH-cs."
    ::= { dlsNotificationsPrefix 437 }

dlsNotification438 NOTIFICATION-TYPE
    OBJECTS { 
              dls438_link_address, 
              dls438_interface 
            }
    STATUS current
    DESCRIPTION
        "Notification of Event DLS.438

        Message: 'sdlc transition to secondary or negotiable idle state for address $1 interface $2'

        Parameters list:
              $1: dls438_link_address
              $2: dls438_interface

        The SDLC link station specified is transitioning to secondary or
        negotiable idle state."
    ::= { dlsNotificationsPrefix 438 }

dlsNotification439 NOTIFICATION-TYPE
    OBJECTS { 
              dls439_link_address, 
              dls439_interface 
            }
    STATUS current
    DESCRIPTION
        "Notification of Event DLS.439

        Message: 'unexpected sdlc test cmd for address $1 interface $2'

        Parameters list:
              $1: dls439_link_address
              $2: dls439_interface

        The primary SDLC link station sent an unexpected test cmd frame."
    ::= { dlsNotificationsPrefix 439 }

dlsNotification440 NOTIFICATION-TYPE
    OBJECTS { 
              dls440_link_address, 
              dls440_interface 
            }
    STATUS current
    DESCRIPTION
        "Notification of Event DLS.440

        Message: 'pu 2 station on negotiable link detected, address $1 interface $2'

        Parameters list:
              $1: dls440_link_address
              $2: dls440_interface

        A station with Node Type PU 2 was detected on an SDLC link configured
        with a role of Negotiable. This is a probable configuration error; a
        PU 2 link role is normally set Secondary."
    ::= { dlsNotificationsPrefix 440 }

dlsNotification441 NOTIFICATION-TYPE
    OBJECTS { 
              dls441_link_address, 
              dls441_interface 
            }
    STATUS current
    DESCRIPTION
        "Notification of Event DLS.441

        Message: 'unexpected sdlc non-null xid recv from primary for addr $1 interface $2'

        Parameters list:
              $1: dls441_link_address
              $2: dls441_interface

        The primary SDLC link station sent an unexpected XID type for a
        secondary PU type 2 device."
    ::= { dlsNotificationsPrefix 441 }

dlsNotification442 NOTIFICATION-TYPE
    OBJECTS { 
              dls442_link_address, 
              dls442_interface 
            }
    STATUS current
    DESCRIPTION
        "Notification of Event DLS.442

        Message: 'connection indication received from primary sdlc station address $1 interface $2'

        Parameters list:
              $1: dls442_link_address
              $2: dls442_interface

        The specified SDLC link station sent an indication that a primary SDLC
        link station sent a SNRM."
    ::= { dlsNotificationsPrefix 442 }

dlsNotification443 NOTIFICATION-TYPE
    OBJECTS { 
              dls443_link_address, 
              dls443_interface 
            }
    STATUS current
    DESCRIPTION
        "Notification of Event DLS.443

        Message: 'connection indication received in invalid state from sdlc station to address $1 interface $2'

        Parameters list:
              $1: dls443_link_address
              $2: dls443_interface

        The specified SDLC link station sent an indication that an SDLC link
        station sent a SNRM in an invalid state."
    ::= { dlsNotificationsPrefix 443 }

dlsNotification444 NOTIFICATION-TYPE
    OBJECTS { 
              dls444_state, 
              dls444_link_address,
              dls444_interface 
            }
    STATUS current
    DESCRIPTION
        "Notification of Event DLS.444

        Message: 'unexpected sdlc cs_confirm in state $1 for address $2 interface $3'

        Parameters list:
              $1: dls444_state
              $2: dls444_link_address
              $3: dls444_interface

        The specified SDLC link station sent an unexpected cs_confirm event."
    ::= { dlsNotificationsPrefix 444 }

dlsNotification445 NOTIFICATION-TYPE
    OBJECTS { 
              dls445_link_address, 
              dls445_interface 
            }
    STATUS current
    DESCRIPTION
        "Notification of Event DLS.445

        Message: 'unexpected sdlc xid recv from DLS for sdlc pu 2 sec addr $1 interface $2'

        Parameters list:
              $1: dls445_link_address
              $2: dls445_interface

        The DLS layer sent an unexpected XID type for a secondary PU type 2
        device."
    ::= { dlsNotificationsPrefix 445 }

dlsNotification446 NOTIFICATION-TYPE
    OBJECTS { 
              dls446_link_address, 
              dls446_interface 
            }
    STATUS current
    DESCRIPTION
        "Notification of Event DLS.446

        Message: 'sdlc transition to secondary null_xid_pend state for address $1 interface $2'

        Parameters list:
              $1: dls446_link_address
              $2: dls446_interface

        The secondary SDLC link station specified is transitioning to
        SEC_NULL_XID_PENDING state, meaning that it is awaiting a response to a
        NULL XID that was sent."
    ::= { dlsNotificationsPrefix 446 }

dlsNotification447 NOTIFICATION-TYPE
    OBJECTS { 
              dls447_link_address, 
              dls447_interface 
            }
    STATUS current
    DESCRIPTION
        "Notification of Event DLS.447

        Message: 'sdlc transition to secondary contact pending state for address $1 interface $2'

        Parameters list:
              $1: dls447_link_address
              $2: dls447_interface

        The secondary SDLC link station specified is transitioning to secondary
        contact pending state."
    ::= { dlsNotificationsPrefix 447 }

dlsNotification448 NOTIFICATION-TYPE
    OBJECTS { 
              dls448_rtn_code, 
              dls448_link_address,
              dls448_interface 
            }
    STATUS current
    DESCRIPTION
        "Notification of Event DLS.448

        Message: 'unexpected return code from sdlc dl connect response = $1 for address $2 interface $3'

        Parameters list:
              $1: dls448_rtn_code
              $2: dls448_link_address
              $3: dls448_interface

        An attempt to send an SDLC connect response returned an unexpected
        return code from the DL."
    ::= { dlsNotificationsPrefix 448 }

dlsNotification449 NOTIFICATION-TYPE
    OBJECTS { 
              dls449_state, 
              dls449_link_address,
              dls449_interface 
            }
    STATUS current
    DESCRIPTION
        "Notification of Event DLS.449

        Message: 'unexpected sdlc contacted_rcv in state $1 for address $2 interface $3'

        Parameters list:
              $1: dls449_state
              $2: dls449_link_address
              $3: dls449_interface

        The specified SDLC link station sent an unexpected contacted_rcv event."
    ::= { dlsNotificationsPrefix 449 }

dlsNotification450 NOTIFICATION-TYPE
    OBJECTS { 
              dls450_source_mac_address, 
              dls450_dest_mac_address,
              dls450_source_sap,
              dls450_dest_sap 
            }
    STATUS current
    DESCRIPTION
        "Notification of Event DLS.450

        Message: 'SDLC, link role secondary, start_dl not honored, for $1->$2, sap $3->$4'

        Parameters list:
              $1: dls450_source_mac_address
              $2: dls450_dest_mac_address
              $3: dls450_source_sap
              $4: dls450_dest_sap

        A Start DL request from DLS to the SDLC interface module was not honored
        because the link role for the SDLC station was Secondary. This is not an
        error. This is due to the fact that SDLC is an unbalanced protocol that
        requires a secondary station to be polled by a primary before it can
        respond or initiate some action."
    ::= { dlsNotificationsPrefix 450 }

dlsNotification451 NOTIFICATION-TYPE
    OBJECTS { 
              dls451_link_address, 
              dls451_interface 
            }
    STATUS current
    DESCRIPTION
        "Notification of Event DLS.451

        Message: 'sdlc secondary recv a NXID from DLS in sec_nxid_pend state for address $1 interface $2'

        Parameters list:
              $1: dls451_link_address
              $2: dls451_interface

        The secondary SDLC circuit initiation logic has received and ignored a
        Null XID from the neighbor router when it was expecting an XID0
        (internal state sec_nxid_pend). The Null XID is ignored, and the XID0
        is expected to follow."
    ::= { dlsNotificationsPrefix 451 }

dlsNotification452 NOTIFICATION-TYPE
    OBJECTS { 
              dls452_event 
            }
    STATUS current
    DESCRIPTION
        "Notification of Event DLS.452

        Message: 'QLLC: received qllc event $1'

        Parameters list:
              $1: dls452_event

        A qllc event has been received."
    ::= { dlsNotificationsPrefix 452 }

dlsNotification453 NOTIFICATION-TYPE
    OBJECTS { 
              dls453_event, 
              dls453_source_mac_address,
              dls453_dest_mac_address,
              dls453_source_sap,
              dls453_dest_sap 
            }
    STATUS current
    DESCRIPTION
        "Notification of Event DLS.453

        Message: 'QLLC: qllc event $1 assigned to $2->$3, sap $4->$5'

        Parameters list:
              $1: dls453_event
              $2: dls453_source_mac_address
              $3: dls453_dest_mac_address
              $4: dls453_source_sap
              $5: dls453_dest_sap

        The qllc event received has been assigned to the sesion especified."
    ::= { dlsNotificationsPrefix 453 }

dlsNotification454 NOTIFICATION-TYPE
    OBJECTS { 
              dls454_event 
            }
    STATUS current
    DESCRIPTION
        "Notification of Event DLS.454

        Message: 'QLLC: refused qllc event $1'

        Parameters list:
              $1: dls454_event

        The qllc event received has been refused because there is not
        an adecuate session or the session assigned is in an state that
        no expect this event."
    ::= { dlsNotificationsPrefix 454 }

dlsNotification455 NOTIFICATION-TYPE
    OBJECTS { 
              dls455_request 
            }
    STATUS current
    DESCRIPTION
        "Notification of Event DLS.455

        Message: 'QLLC: sent qllc request $1'

        Parameters list:
              $1: dls455_request

        A qllc request has been sent successfully."
    ::= { dlsNotificationsPrefix 455 }

dlsNotification456 NOTIFICATION-TYPE
    OBJECTS { 
              dls456_request, 
              dls456_qmsg,
              dls456_source_mac_address,
              dls456_dest_mac_address,
              dls456_source_sap,
              dls456_dest_sap 
            }
    STATUS current
    DESCRIPTION
        "Notification of Event DLS.456

        Message: 'QLLC: sent qllc request $1 (Qmsg $2) to $3->$4, sap $5->$6'

        Parameters list:
              $1: dls456_request
              $2: dls456_qmsg
              $3: dls456_source_mac_address
              $4: dls456_dest_mac_address
              $5: dls456_source_sap
              $6: dls456_dest_sap

        A qllc request has been sent successfully. If the request is a QDAT
        request, Qmsg is the Q message sent."
    ::= { dlsNotificationsPrefix 456 }

dlsNotification457 NOTIFICATION-TYPE
    OBJECTS { 
              dls457_request 
            }
    STATUS current
    DESCRIPTION
        "Notification of Event DLS.457

        Message: 'QLLC: error sending qllc request $1'

        Parameters list:
              $1: dls457_request

        The qllc request has not been sent because there aren't free buffers or
        because there is an error in the interface with X.25 node."
    ::= { dlsNotificationsPrefix 457 }

dlsNotification458 NOTIFICATION-TYPE
    OBJECTS { 
              dls458_ip_address 
            }
    STATUS current
    DESCRIPTION
        "Notification of Event DLS.458

        Message: 'DLS, a SSP message IAMOKAY has been sent to DLSw neighbor at $1'

        Parameters list:
              $1: dls458_ip_address

        A SSP message IAMOKAY has been sent successfully to DLSw neighbor
        to make a test of transport connection."
    ::= { dlsNotificationsPrefix 458 }

dlsNotification459 NOTIFICATION-TYPE
    OBJECTS { 
              dls459_ip_address 
            }
    STATUS current
    DESCRIPTION
        "Notification of Event DLS.459

        Message: 'DLS, No memory to create SSP message IAMOKAY to neighbor $1'

        Parameters list:
              $1: dls459_ip_address

        There is no memory available to create a SSP message IAMOKAY and is not
        posible to send it through the transport connection."
    ::= { dlsNotificationsPrefix 459 }


END
