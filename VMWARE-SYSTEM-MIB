-- **********************************************************
-- Copyright 2007 VMware, Inc.  All rights reserved. 
-- 
--  This MIB Module provides objects equivalent to 
--  SNMPv2-MIB. The sysDescr.0 and sysObjectId.0 provides
--  the same information.
--
-- **********************************************************


VMWARE-SYSTEM-MIB DEFINITIONS ::= BEGIN

IMPORTS
   OBJECT-TYPE
      FROM RFC-1212
   DisplayString 
      FROM RFC1213-MIB

-- MIB items for vmwSystem subtree (general VMware system information).

   vmwSystem  -- OBJECT IDENTIFIER ::= { vmware 1 }
      FROM VMWARE-ROOT-MIB;

vmwProdName    OBJECT-TYPE 
   SYNTAX      DisplayString
   ACCESS      read-only
   STATUS      obsolete
   DESCRIPTION
      "The product name."
   ::= { vmwSystem 1 }

vmwProdVersion OBJECT-TYPE 
   SYNTAX      DisplayString
   ACCESS      read-only
   STATUS      obsolete   
   DESCRIPTION
      "Product version."
   ::= { vmwSystem 2 }

vmwProdOID     OBJECT-TYPE 
   SYNTAX      OBJECT IDENTIFIER 
   ACCESS      read-only
   STATUS      obsolete      
   DESCRIPTION
      "Version-specific unique OID for product in the VMware MIB."
   ::= { vmwSystem 3 } 

vmwProdBuild   OBJECT-TYPE 
   SYNTAX      DisplayString 
   ACCESS      read-only
   STATUS      obsolete         
   DESCRIPTION
      "Build number of the product."
   ::= { vmwSystem 4 } 
END
