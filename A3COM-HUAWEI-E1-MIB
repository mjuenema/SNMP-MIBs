-- =============================================================
-- Copyright (C) 2002 by HUAWEI-3COM TECHNOLOGIES. All rights reserved.
--
-- Description: 
-- Reference:  extension of RFC 1213 and RFC 2233
-- Version: V1.0
-- History:
--   V1.0 2004-12-01
--        Initial Version  by lizhiyong and fangmin
-- =============================================================
A3COM-HUAWEI-E1-MIB DEFINITIONS ::= BEGIN
 
IMPORTS
        MODULE-IDENTITY,
        OBJECT-TYPE,
        Integer32,
        Counter32
                FROM SNMPv2-SMI
        MODULE-COMPLIANCE,
        OBJECT-GROUP
                FROM SNMPv2-CONF
        ifIndex
                FROM RFC1213-MIB
        h3cCommon
                FROM A3COM-HUAWEI-OID-MIB; 
                
                
-- =============================================================
-- E1 Module
-- =============================================================              
h3cE1    MODULE-IDENTITY
        LAST-UPDATED    "200412011436Z"
        ORGANIZATION    "Huawei-3com Technologies co.,Ltd."
        CONTACT-INFO
            "Platform Team Beijing Institute Huawei-3com Tech, Inc.
             Http://www.huawei-3com.com                                       
             E-mail:support@huawei-3com.com "
        DESCRIPTION
             "This MIB provides E1 interface information that are 
             excluded by RFC 1213 and RFC 2233"
        REVISION        "200412011436Z"
        DESCRIPTION
                "Initial version of this MIB module."
        ::= { h3cCommon 28 }
 
 
e1InterfaceStatusTable OBJECT-TYPE
        SYNTAX      SEQUENCE OF E1InterfaceStatusEntry
        MAX-ACCESS   not-accessible
        STATUS       current
        DESCRIPTION
         "This  table contains E1 interface packet statistics  "
        ::= { h3cE1 1 }
 
e1InterfaceStatusEntry OBJECT-TYPE
        SYNTAX         E1InterfaceStatusEntry
        MAX-ACCESS     not-accessible
        STATUS         current
        DESCRIPTION
         "This entry contains E1 interface packet statistics.
         The index of this Entry is ifIndex defined in ifTable
         of RFC1213-MIB"
        INDEX { ifIndex }
        ::= { e1InterfaceStatusTable 1 }
 
E1InterfaceStatusEntry ::= SEQUENCE  {    
        e1InterfaceInErrs            Counter32,
        e1InterfaceInRuntsErrs	     Counter32,
        e1InterfaceInGiantsErrs	     Counter32,
        e1InterfaceInCrcErrs         Counter32,  
        e1InterfaceInAlignErrs	     Counter32,
        e1InterfaceInOverRunsErrs    Counter32,
        e1InterfaceInDribblesErrs    Counter32,
        e1InterfaceInAbortedSeqErrs  Counter32,
        e1InterfaceInNoBufferErrs    Counter32,
        e1InterfaceInFramingErrs     Counter32,
        e1InterfaceOutputErrs        Counter32,
        e1InterfaceOutUnderRunErrs   Counter32,
        e1InterfaceOutCollisonsErrs  Counter32,
        e1InterfaceOutDeferedErrs    Counter32                             
        }
        
e1InterfaceInErrs        OBJECT-TYPE
        SYNTAX          Counter32
        MAX-ACCESS      read-only
        STATUS          current
        DESCRIPTION
         "The total number of error received on this interface"
        ::= { e1InterfaceStatusEntry 1 }
 
e1InterfaceInRuntsErrs   OBJECT-TYPE
        SYNTAX          Counter32
        MAX-ACCESS      read-only
        STATUS          current
        DESCRIPTION
         "The number of Runts Error(too short packet) received on this interface"
	::= { e1InterfaceStatusEntry 2 }
 
e1InterfaceInGiantsErrs	OBJECT-TYPE
        SYNTAX          Counter32
        MAX-ACCESS      read-only
        STATUS          current
        DESCRIPTION
         "The number of Giants Error(too long packet) received on this interface"
	::= { e1InterfaceStatusEntry 3 } 
	
e1InterfaceInCrcErrs     OBJECT-TYPE
        SYNTAX          Counter32
        MAX-ACCESS      read-only
        STATUS          current
        DESCRIPTION
         "The number of CRC Error received on this interface"
	::= { e1InterfaceStatusEntry 4 }  
	
e1InterfaceInAlignErrs   OBJECT-TYPE 
        SYNTAX          Counter32
        MAX-ACCESS      read-only
        STATUS          current
        DESCRIPTION
         "The number of Align Error received on this interface"
	::= { e1InterfaceStatusEntry 5 }

e1InterfaceInOverRunsErrs OBJECT-TYPE
        SYNTAX           Counter32
        MAX-ACCESS       read-only
        STATUS          current
        DESCRIPTION
         "The number of Over Runs Error received on this interface"
	::= { e1InterfaceStatusEntry 6 }

e1InterfaceInDribblesErrs  OBJECT-TYPE
        SYNTAX            Counter32
        MAX-ACCESS  	  read-only
        STATUS            current
        DESCRIPTION
         "The number of dribble packets received"
	::= { e1InterfaceStatusEntry 7 }

e1InterfaceInAbortedSeqErrs    OBJECT-TYPE
        SYNTAX                Counter32
        MAX-ACCESS            read-only
        STATUS                current
        DESCRIPTION
         "The number of AbortedSeq Error received on this interface"
	::= { e1InterfaceStatusEntry 8 }

e1InterfaceInNoBufferErrs      OBJECT-TYPE
        SYNTAX                Counter32
        MAX-ACCESS            read-only
        STATUS                current
        DESCRIPTION
         "The number of Error (no buffer available)"
	::= { e1InterfaceStatusEntry 9 }
 
e1InterfaceInFramingErrs      OBJECT-TYPE
        SYNTAX                Counter32
        MAX-ACCESS            read-only
        STATUS                current
        DESCRIPTION
         "The number of framing Errors"
	::= { e1InterfaceStatusEntry 10 }
	
e1InterfaceOutputErrs          OBJECT-TYPE
        SYNTAX                Counter32
        MAX-ACCESS            read-only
        STATUS                current
        DESCRIPTION
         "The number of total Error transmited on this interface"
	::= { e1InterfaceStatusEntry 11 }

e1InterfaceOutUnderRunErrs     OBJECT-TYPE
        SYNTAX                Counter32
        MAX-ACCESS            read-only
        STATUS                current
        DESCRIPTION
         "The number of UnderRun Error transmited on this interface"
	::= { e1InterfaceStatusEntry 12 }

e1InterfaceOutCollisonsErrs    OBJECT-TYPE
        SYNTAX                Counter32
        MAX-ACCESS            read-only
        STATUS                current
        DESCRIPTION
         "The number of Collisions Error transmited on this interface"
	::= { e1InterfaceStatusEntry 13 }

e1InterfaceOutDeferedErrs      OBJECT-TYPE
        SYNTAX                Counter32
        MAX-ACCESS            read-only
        STATUS                current
        DESCRIPTION
         "The number of Deferred Error transmited on this interface"
	::= { e1InterfaceStatusEntry 14 }

END
