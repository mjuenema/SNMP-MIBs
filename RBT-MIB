RBT-MIB DEFINITIONS ::= BEGIN

IMPORTS
    MODULE-IDENTITY, enterprises FROM SNMPv2-SMI;

rbt MODULE-IDENTITY
    LAST-UPDATED        "200804100000Z"
    ORGANIZATION        "Riverbed Technology, Inc."
    CONTACT-INFO
       "   John Cho
           jcho@riverbed.com"
    DESCRIPTION         "Riverbed Technology MIB"
    REVISION            "200804100000Z"
    DESCRIPTION         "Riverbed Steelhead 5.0 Revisions"
    ::= { enterprises 17163 }

products OBJECT IDENTIFIER
    ::= { rbt 1 }

END
