-- ****************************************************************
-- BROCADE-PRODUCTS-MIB.my: Brocade Products MIB.
--
-- Feb 2012, Sanjeev C Joshi, Yasar Khan
--
-- Copyright (c) 2012 by Brocade Communications Systems, Inc.
-- All rights reserved.
--
-- ****************************************************************
BROCADE-PRODUCTS-MIB DEFINITIONS ::= BEGIN
IMPORTS
   MODULE-IDENTITY
      	FROM SNMPv2-SMI
        bcsiReg  
        	FROM Brocade-REG-MIB;

      brocadeProductsMIB MODULE-IDENTITY
        LAST-UPDATED "201202030000Z"
        ORGANIZATION "Brocade Communications Systems, Inc.,"
        CONTACT-INFO 
				"Brocade Communications Systems, Inc.
                Postal: 130 Holger Way
                San Jose, CA 95134
                U.S.A
				Tel: +1-408-333-8000
				E-mail: support@Brocade.com
				web: www.brocade.com."

        DESCRIPTION "This MIB module is for defining all the object 
		             identifiers to identify various hardware 
					 platforms. These identifiers are used as value
					 for 'sysObjectID'."

		REVISION "201202030000Z" 
	    DESCRIPTION "Initial version of this MIB module."
        ::= { bcsiReg 3 }

      brocadeProducts   OBJECT IDENTIFIER ::= { brocadeProductsMIB 1 }

      vdx6740		OBJECT IDENTIFIER ::= { brocadeProducts 131 }

      vdx6740T		OBJECT IDENTIFIER ::= { brocadeProducts 137 }

      vdx8770S4		OBJECT IDENTIFIER ::= { brocadeProducts 1000 }

      vdx8770S8   	OBJECT IDENTIFIER ::= { brocadeProducts 1001 }

      vdx8770S16  	OBJECT IDENTIFIER ::= { brocadeProducts 1002 }

END
