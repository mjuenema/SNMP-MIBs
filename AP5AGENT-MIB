--MibName=ap5Agent
--
--******************************************************************************
--*  WSA 5 Agent MIB prototype for Apache and IIS                              *
--*  edit ap5 to "ap5" prefix                                                   *
--*  edit Ap5 to "Ap5" prefix                                                   *
--*  edit AP5 to "AP5" prefix                                                   *
--*  edit 80 to OID                                                   	       *
--******************************************************************************

AP5AGENT-MIB DEFINITIONS ::= BEGIN

IMPORTS
	enterprises   FROM RFC1155-SMI
	OBJECT-TYPE   FROM RFC1155-SMI
	DisplayString FROM RFC1158-MIB;
        
-- Base OID  1.3.6.1.4.1.791.2.10.2.80

    cai         OBJECT IDENTIFIER ::= { enterprises 791 }

    caiSysMgr   OBJECT IDENTIFIER ::= { cai 2 }

    tng         OBJECT IDENTIFIER ::= { caiSysMgr 10 }

    unix-nt      OBJECT IDENTIFIER ::= { tng 2 }
                      
    ap5Agent   OBJECT IDENTIFIER ::= { unix-nt 80 }

    ap5ServerGroup           OBJECT IDENTIFIER   ::=  {  ap5Agent 1   }
    ap5ServiceGroup          OBJECT IDENTIFIER   ::=  {  ap5Agent 2   }
    ap5BadLinkGroup          OBJECT IDENTIFIER   ::=  {  ap5Agent 3   }
    ap5TopURLGroup           OBJECT IDENTIFIER   ::=  {  ap5Agent 4   }
    ap5URLAvailCounterGroup  OBJECT IDENTIFIER   ::=  {  ap5Agent 5   }
    ap5URLMntrGroup          OBJECT IDENTIFIER   ::=  {  ap5Agent 6   }
    ap5DiskGroup             OBJECT IDENTIFIER   ::=  {  ap5Agent 7   }
    ap5AvailCounterGroup     OBJECT IDENTIFIER   ::=  {  ap5Agent 8   }
    ap5PolledCounterGroup    OBJECT IDENTIFIER   ::=  {  ap5Agent 9   }
    ap5EventGroup            OBJECT IDENTIFIER   ::=  {  ap5Agent 10  }
    ap5AgentGroup            OBJECT IDENTIFIER   ::=  {  ap5Agent 11  }
    ap5WCGroup               OBJECT IDENTIFIER   ::=  {  ap5Agent 12  }
    ap5SHGroup               OBJECT IDENTIFIER   ::=  {  ap5Agent 13  }
    ap5LocalActionGroup      OBJECT IDENTIFIER   ::=  {  ap5Agent 14  }
    ap5ServLogGroup          OBJECT IDENTIFIER   ::=  {  ap5Agent 15  }
    ap5ExpressionGroup       OBJECT IDENTIFIER   ::=  {  ap5Agent 16  }
    ap5DetailGroup    	    OBJECT IDENTIFIER   ::=  {  ap5Agent 17  }
    ap5VHGroup    	    OBJECT IDENTIFIER   ::=  {  ap5Agent 18  }
    ap5IISAvailCounterGroup  OBJECT IDENTIFIER   ::=  {  ap5Agent 19  }
    ap5IISPolledCounterGroup OBJECT IDENTIFIER   ::=  {  ap5Agent 20  }

--******************************************************************************
--* ServerGroup - Site and summary information                               *
--******************************************************************************

        ap5ServerName OBJECT-TYPE
                SYNTAX  DisplayString
                ACCESS  read-only
                STATUS  mandatory
                DESCRIPTION
                "The host name of the computer."
                ::=  {  ap5ServerGroup 1   }

        ap5ServerSummaryStatus OBJECT-TYPE
                SYNTAX  INTEGER
                {
                    ok(1),
                    warning(2),
                    critical(3)
                }
                ACCESS  read-only
                STATUS  mandatory
                DESCRIPTION
                "The status of the monitored server."
                ::=  {  ap5ServerGroup 2   }

        ap5ServerPollingInterval OBJECT-TYPE
                SYNTAX  INTEGER
                ACCESS  read-write
                STATUS  mandatory
                DESCRIPTION
                "Poll interval for the server group in seconds."
                ::=  {  ap5ServerGroup 3   }

        ap5ServerResetCounts OBJECT-TYPE
                SYNTAX  INTEGER
                {
                    reset(1)
                }
                ACCESS  read-write
                STATUS  mandatory
                DESCRIPTION
                "Resets all history counts to zero when set."
                ::=  {  ap5ServerGroup 4   }

        ap5ServerResetTS OBJECT-TYPE
                SYNTAX  INTEGER
                ACCESS  read-only
                STATUS  mandatory
                DESCRIPTION
                "Time of last reset in ctime form."
                ::=  {  ap5ServerGroup 5   }

        ap5ServerResetTSEdit OBJECT-TYPE
                SYNTAX  DisplayString
                ACCESS  read-only
                STATUS  mandatory
                DESCRIPTION
                "Time of last reset in display form."
                ::=  {  ap5ServerGroup 6   }

        ap5ServerResetDays OBJECT-TYPE
                SYNTAX  INTEGER
                ACCESS  read-write
                STATUS  mandatory
                DESCRIPTION
                "Number of days between automatic history count resets."
                ::=  {  ap5ServerGroup 7   }

        ap5ServerVersion OBJECT-TYPE
                SYNTAX  DisplayString
                ACCESS  read-only
                STATUS  mandatory
                DESCRIPTION
                "The version of the web server."
                ::=  {  ap5ServerGroup 8   }

        ap5ServerPort OBJECT-TYPE
                SYNTAX  INTEGER
                ACCESS  read-only
                STATUS  mandatory
                DESCRIPTION
                "Port the server is listening on."
                ::=  {  ap5ServerGroup 9   }

        ap5ServerLBHost OBJECT-TYPE
                SYNTAX  DisplayString
                ACCESS  read-write
                STATUS  mandatory
                DESCRIPTION
                "Host name for Agent Collector."
                ::=  {  ap5ServerGroup 10   }

        ap5ServerLBPort OBJECT-TYPE
                SYNTAX  DisplayString
                ACCESS  read-write
                STATUS  mandatory
                DESCRIPTION
                "Agent Collector name."
                ::=  {  ap5ServerGroup 11   }

	ap5ServerLBEnaDis OBJECT-TYPE
		SYNTAX      INTEGER {enable(1), disable(2)}
		ACCESS      read-write
		STATUS      mandatory
		DESCRIPTION "Enable or disable the Agent Collector."
		::= {ap5ServerGroup 12}

        ap5SuperAgentRequest OBJECT-TYPE
                SYNTAX  DisplayString
                ACCESS  read-write
                STATUS  mandatory
                DESCRIPTION
                "Super Agent service request."
                ::=  {  ap5ServerGroup 13   }

        ap5ServerHiLevelVersion OBJECT-TYPE
                SYNTAX  DisplayString
                ACCESS  read-only
                STATUS  mandatory
                DESCRIPTION
                "Oracle server: The high level version number of the web server."
                ::=  {  ap5ServerGroup 14   }

        ap5ServerSetBaseLine OBJECT-TYPE
                SYNTAX  INTEGER {
                                set(1)
                               }
                ACCESS  write-only
                STATUS  mandatory
                DESCRIPTION
                "Immediately set Adaptive Configuration values."
                ::=  {  ap5ServerGroup 15   }

        ap5ServerBaseLineWarnWeight OBJECT-TYPE
                SYNTAX  INTEGER 
                ACCESS  read-write
                STATUS  mandatory
                DESCRIPTION
                "Adaptive Configuration warning weighing factor."
                ::=  {  ap5ServerGroup 16   }

        ap5ServerBaseLineCritWeight OBJECT-TYPE
                SYNTAX  INTEGER 
                ACCESS  read-write
                STATUS  mandatory
                DESCRIPTION
                "Adaptive Configuration critical weighing factor."
                ::=  {  ap5ServerGroup 17   }

	ap5ServerBaseLineEnaDis OBJECT-TYPE
		SYNTAX      INTEGER {disable(1), enable(2)}
		ACCESS      read-write
		STATUS      mandatory
		DESCRIPTION "Enable or disable Active Adaptive Configuration."
		::= {  ap5ServerGroup 18  }

	ap5ServerBaseLineTimer OBJECT-TYPE
		SYNTAX      INTEGER
		ACCESS      read-write
		STATUS      mandatory
		DESCRIPTION "Active Adaptive Configuration timer."
		::= {  ap5ServerGroup 19  }
                
        ap5ServerExportConfigSet OBJECT-TYPE
                SYNTAX  DisplayString
                ACCESS  read-write
                STATUS  mandatory
                DESCRIPTION
                "Name of config to export to."
                ::=  {  ap5ServerGroup 20   }
                
        ap5ServerImportConfigSet OBJECT-TYPE
                SYNTAX  DisplayString
                ACCESS  read-write
                STATUS  mandatory
                DESCRIPTION
                "Name of config to import from."
                ::=  {  ap5ServerGroup 21   }
               
        ap5retVHTableInterval OBJECT-TYPE
               SYNTAX  INTEGER
               ACCESS  read-write
               STATUS  mandatory
               DESCRIPTION
               "Seconds between polls for the VHTable."
               ::=  { ap5ServerGroup 22 }
               

	ap5retVHGPEnaDis OBJECT-TYPE
		SYNTAX      INTEGER {enable(1), disable(2)}
		ACCESS      read-write
		STATUS      mandatory
		DESCRIPTION "Enable or disable for the VHGroup."
		::= { ap5ServerGroup 23 }


--******************************************************************************
--* ServiceGroup - Services                                                  *
--******************************************************************************

        ap5ServiceTableEntries OBJECT-TYPE
                SYNTAX  INTEGER
                ACCESS  read-only
                STATUS  mandatory
                DESCRIPTION
                "The number of entries in the table."
                ::=  {  ap5ServiceGroup 1  }

        ap5ServiceSummaryStatus OBJECT-TYPE
                SYNTAX  INTEGER
                {
                    normal(1),
                    warning(2),
                    critical(3)
                }
                ACCESS  read-only
                STATUS  mandatory
                DESCRIPTION
                "Summary status of the service group."
                ::=  {  ap5ServiceGroup 2  }

        ap5ServicePollingInterval OBJECT-TYPE
                SYNTAX  INTEGER
                ACCESS  read-write
                STATUS  mandatory
                DESCRIPTION
                "Poll interval for the service group in seconds."
                ::=  {  ap5ServiceGroup 3  }

        -- Start, start service
        -- Stop, stop service, don't reset autorestart
        -- Recycle, stop and then restart service
        -- Stop no AutoRestart - stop and turn off autorestart
        ap5ServiceControl OBJECT-TYPE
                SYNTAX  INTEGER
                {
                    start(1),
                    stop(2),
                    recycle(3),
                    stop-noautorestart(4)
                }
                ACCESS  read-write
                STATUS  mandatory
                DESCRIPTION
                "Start and stop all services in the service table."
                ::=  {  ap5ServiceGroup 4  }

        ap5ServiceWarningCount OBJECT-TYPE
                SYNTAX  INTEGER
                ACCESS  read-only
                STATUS  mandatory
                DESCRIPTION
                "Number of services in warning state."
                ::=  {  ap5ServiceGroup 5  }

        ap5ServiceCriticalCount OBJECT-TYPE
                SYNTAX  INTEGER
                ACCESS  read-only
                STATUS  mandatory
                DESCRIPTION
                "Number of services in critical state."
                ::=  {  ap5ServiceGroup 6  }

        ap5NumberOfPolls OBJECT-TYPE
               SYNTAX  INTEGER
               ACCESS  read-only
               STATUS  mandatory
               DESCRIPTION
               "Number of times services have been polled"
               ::=  {  ap5ServiceGroup 7}

        ap5ServiceTable OBJECT-TYPE
                SYNTAX  SEQUENCE OF Ap5ServiceEntry
                ACCESS  not-accessible
                STATUS  mandatory
                DESCRIPTION
                "The list of all monitored services."
                ::=  {  ap5ServiceGroup 8}

	ap5ServiceGPEnaDis OBJECT-TYPE
		SYNTAX      INTEGER {enable(1), disable(2)}
		ACCESS      read-write
		STATUS      mandatory
		DESCRIPTION "Enable or disable for the Group."
		::= { ap5ServiceGroup 9 }
		
        ap5ServiceEntry OBJECT-TYPE
                 SYNTAX  Ap5ServiceEntry
                 ACCESS  not-accessible
                 STATUS  mandatory
                 DESCRIPTION
                 "The ServiceTable entry."
                 INDEX { ap5ServiceName }
                     ::=  { ap5ServiceTable 1 }

        Ap5ServiceEntry ::= SEQUENCE
        {
            ap5ServiceName           DisplayString,
            ap5ServiceState          INTEGER,
            ap5AutoRestart           INTEGER,
            ap5AutoReboot            INTEGER,
            ap5RestartAttempts       INTEGER,
            ap5RestartCount          INTEGER,
            ap5RebootAttempts        INTEGER,
            ap5RebootCount           INTEGER,
            ap5LocalAction           DisplayString,
            ap5TotalRestarts         INTEGER,
            ap5TotalReboots          INTEGER,
            ap5ServiceStateStatus    INTEGER,
            ap5ServiceWarnings       INTEGER,
            ap5ServiceCriticals      INTEGER,
            ap5StateIfStopped        INTEGER,
            ap5ServiceCtrl           INTEGER,
            ap5ServiceAvail          DisplayString,
            ap5ServiceRunningPolls   INTEGER,
	    ap5ServicePorts	    DisplayString,
            ap5ServiceType	    DisplayString,
	    ap5ServiceLagSetting	    INTEGER,
	    ap5ServiceLagValue	    INTEGER
        }

        ap5ServiceName OBJECT-TYPE
                SYNTAX  DisplayString
                ACCESS  read-only
                STATUS  mandatory
                DESCRIPTION
                "The name of the service."
                ::=  {  ap5ServiceEntry 1   }

        ap5ServiceState OBJECT-TYPE
                SYNTAX  INTEGER
                {
                    stopped(1),
                    started(2),
                    notinstalled(3),
                    actionpending(4)
                }
                ACCESS  read-only
                STATUS  mandatory
                DESCRIPTION
                "The state of the service."
                ::=  {  ap5ServiceEntry 2   }

        ap5AutoRestart OBJECT-TYPE
                SYNTAX  INTEGER
                {
                    yes(1),
                    no(2)
                }
                ACCESS  read-write
                STATUS  mandatory
                DESCRIPTION
                "Flag indicating whether to attempt to restart the service if it's down."
                ::=  {  ap5ServiceEntry 3   }

        ap5AutoReboot OBJECT-TYPE
                SYNTAX  INTEGER
                {
                    yes(1),
                    no(2)
                }
                ACCESS  read-write
                STATUS  mandatory
                DESCRIPTION
                "Flag indicating whether to attempt to reboot the host if service is down."
                ::=  {  ap5ServiceEntry 4   }

        ap5RestartAttempts OBJECT-TYPE
                SYNTAX  INTEGER
                ACCESS  read-write
                STATUS  mandatory
                DESCRIPTION
                "Reboot the host after this many restart attempts are unsuccessful."
                ::=  {  ap5ServiceEntry 5   }

        ap5RestartCount OBJECT-TYPE
                SYNTAX  INTEGER
                ACCESS  read-only
                STATUS  mandatory
                DESCRIPTION
                "Number of service restarts attempted since last successful service restart."
                ::=  {  ap5ServiceEntry 6   }

        ap5RebootAttempts OBJECT-TYPE
                SYNTAX  INTEGER
                ACCESS  read-write
                STATUS  mandatory
                DESCRIPTION
                "Execute local action after this many reboot attempts are unsuccessful."
                ::=  {  ap5ServiceEntry 7   }

        ap5RebootCount OBJECT-TYPE
                SYNTAX  INTEGER
                ACCESS  read-only
                STATUS  mandatory
                DESCRIPTION
                "Number of reboots attempted since last successful service restart."
                ::=  {  ap5ServiceEntry 8   }

        ap5LocalAction OBJECT-TYPE
                SYNTAX  DisplayString
                ACCESS  read-write
                STATUS  mandatory
                DESCRIPTION
                "Local action to perform when reboot attempts exceeded."
                ::=  {  ap5ServiceEntry 9   }

        ap5TotalRestarts OBJECT-TYPE
                SYNTAX  INTEGER
                ACCESS  read-only
                STATUS  mandatory
                DESCRIPTION
                "Total number of service restarts attempted."
                ::=  {  ap5ServiceEntry 10   }

        ap5TotalReboots OBJECT-TYPE
                SYNTAX  INTEGER
                ACCESS  read-only
                STATUS  mandatory
                DESCRIPTION
                "Total number of host reboots attempted."
                ::=  {  ap5ServiceEntry 11   }

        ap5ServiceStateStatus OBJECT-TYPE
                SYNTAX  INTEGER
                {
                    normal(1),
                    warning(2),
                    critical(3)
                }
                ACCESS  read-only
                STATUS  mandatory
                DESCRIPTION
                "Status of this service."
                ::=  {  ap5ServiceEntry 12   }

        ap5ServiceWarnings OBJECT-TYPE
                SYNTAX  INTEGER
                ACCESS  read-only
                STATUS  mandatory
                DESCRIPTION
                "Number of warnings generated by this service."
                ::=  {  ap5ServiceEntry 13   }

        ap5ServiceCriticals OBJECT-TYPE
                SYNTAX  INTEGER
                ACCESS  read-only
                STATUS  mandatory
                DESCRIPTION
                "Number of criticals generated by this service."
                ::=  {  ap5ServiceEntry 14   }

        ap5StateIfStopped OBJECT-TYPE
                SYNTAX  INTEGER
                {
                    normal(1),
                    warning(2),
                    critical(3)
                }
                ACCESS  read-write
                STATUS  mandatory
                DESCRIPTION
                "Service status reported if service is stopped."
                ::=  {  ap5ServiceEntry 15   }

        ap5ServiceCtrl OBJECT-TYPE
               SYNTAX  INTEGER {
                                start(1),
                                stop(2),
                                recycle(3),
                                stop-noautorestart(4)
                               }
               ACCESS  read-write
               STATUS  mandatory
               DESCRIPTION
               "Start and stop this service."
               ::=  {  ap5ServiceEntry 16   }

        ap5ServiceAvail OBJECT-TYPE
               SYNTAX  DisplayString
               ACCESS  read-only
               STATUS  mandatory
               DESCRIPTION
               "% of time service available (running) = running/number of polls"
               ::=  {  ap5ServiceEntry 17  }

        ap5ServiceRunningPolls OBJECT-TYPE
                SYNTAX  INTEGER
                ACCESS  read-only
                STATUS  mandatory
                DESCRIPTION
                "Number of polls showing service running(used for availability calc)."
                ::=  {  ap5ServiceEntry 18   }

        ap5ServicePorts OBJECT-TYPE
                SYNTAX  DisplayString
                ACCESS  read-write
                STATUS  mandatory
                DESCRIPTION
                "Additional PORTS to check for the service."
                ::=  {  ap5ServiceEntry 19   }

	 ap5ServiceType OBJECT-TYPE
	        SYNTAX      DisplayString
	        ACCESS      read-only
	        STATUS      mandatory
	        DESCRIPTION "Type of Service (Server, Admin, FTP)."
	        ::= { ap5ServiceEntry 20 }
		
        ap5ServiceLagSetting OBJECT-TYPE
                SYNTAX  INTEGER
                ACCESS  read-write
                STATUS  mandatory
                DESCRIPTION
                "Lag setting for the service."
                ::=  {  ap5ServiceEntry 21   }
		
        ap5ServiceLagValue OBJECT-TYPE
                SYNTAX  INTEGER
                ACCESS  read-only
                STATUS  mandatory
                DESCRIPTION
                "Current Lag value for the service."
                ::=  {  ap5ServiceEntry 22   }

--******************************************************************************
--* BadLinkGroup - URL links not found by requestors                            *
--******************************************************************************

        ap5BLTableEntries OBJECT-TYPE
                SYNTAX  INTEGER
                ACCESS  read-only
                STATUS  mandatory
                DESCRIPTION
                "The number of entries in the table."
                ::=  {  ap5BadLinkGroup 1   }


        ap5BLClearTable OBJECT-TYPE
               SYNTAX  INTEGER {
                                reset(1)
                               }
               ACCESS  read-write
               STATUS  mandatory
               DESCRIPTION
               "Clear the table when set."
               ::=  {  ap5BadLinkGroup 2   }

        ap5BLSummaryStatus OBJECT-TYPE
               SYNTAX  INTEGER {
                                normal(1),
                                warning(2),
                                critical(3)
                               }
               ACCESS  read-only
               STATUS  mandatory
               DESCRIPTION
               "Summary status for bad links."
               ::=  {  ap5BadLinkGroup 3   }

        ap5BLInterval OBJECT-TYPE
               SYNTAX  INTEGER
               ACCESS  read-write
               STATUS  mandatory
               DESCRIPTION
               "Seconds to poll for changes."
               ::=  {  ap5BadLinkGroup 4   }

        ap5BLCircularBuffSize OBJECT-TYPE
               SYNTAX  INTEGER
               ACCESS  read-write
               STATUS  mandatory
               DESCRIPTION
               "Max entries in the table (default 50)(Not a circular buffer)."
               ::=  {  ap5BadLinkGroup 5   }

        ap5BLWarningThreshold OBJECT-TYPE
               SYNTAX  INTEGER
               ACCESS  read-write
               STATUS  mandatory
               DESCRIPTION
               "Number of requests on a row before warning is generated."
               ::=  {  ap5BadLinkGroup 6   }

        ap5BLCriticalThreshold OBJECT-TYPE
               SYNTAX  INTEGER
               ACCESS  read-write
               STATUS  mandatory
               DESCRIPTION
               "Number of requests on a row before critical is generated."
               ::=  {  ap5BadLinkGroup 7   }

        ap5BLWarningCount OBJECT-TYPE
               SYNTAX  INTEGER
               ACCESS  read-only
               STATUS  mandatory
               DESCRIPTION
               "The number of entries in the table with a warning status."
               ::=  {  ap5BadLinkGroup 8   }

        ap5BLCriticalCount OBJECT-TYPE
               SYNTAX  INTEGER
               ACCESS  read-only
               STATUS  mandatory
               DESCRIPTION
               "The number of entries in the table with a critical status."
               ::=  {  ap5BadLinkGroup 9   }

        ap5BLWarningAction OBJECT-TYPE
               SYNTAX  DisplayString
               ACCESS  read-write
               STATUS  mandatory
               DESCRIPTION
               "Command to be executed when warning threshold is crossed on a row."
               ::=  {  ap5BadLinkGroup 10   }

        ap5BLCriticalAction OBJECT-TYPE
               SYNTAX  DisplayString
               ACCESS  read-write
               STATUS  mandatory
               DESCRIPTION
               "Command to be executed when critical threshold is crossed on a row."
               ::=  {  ap5BadLinkGroup 11   }


        ap5BLCreateReportURL OBJECT-TYPE
               SYNTAX  INTEGER {
                                Create(1)
                               }
               ACCESS  read-write
               STATUS  mandatory
               DESCRIPTION
               "When triggered, create report using path and file in BLReportURL."
               ::=  {  ap5BadLinkGroup 12   }

        ap5BLReportURL OBJECT-TYPE
               SYNTAX  DisplayString
               ACCESS  read-write
               STATUS  mandatory
               DESCRIPTION
               "Path and filename for report; Relative to DocumentRoot unless starts with '/'."
               ::=  {  ap5BadLinkGroup 13   }

        ap5BLTable OBJECT-TYPE
               SYNTAX  SEQUENCE OF Ap5BLEntry
               ACCESS  not-accessible
               STATUS  mandatory
               DESCRIPTION
               "This table contains a list bad links."
               ::=  {  ap5BadLinkGroup 14  }

	ap5BLGPEnaDis OBJECT-TYPE
		SYNTAX      INTEGER {enable(1), disable(2)}
		ACCESS      read-write
		STATUS      mandatory
		DESCRIPTION "Enable or disable for the Group."
		::= { ap5BadLinkGroup 15 }

        ap5BLEntry OBJECT-TYPE
               SYNTAX  Ap5BLEntry
               ACCESS  not-accessible
               STATUS  mandatory
               DESCRIPTION
               "This is an entry in the BLTable"
               INDEX { ap5BLURL, ap5BLReferringURL }
               ::=  { ap5BLTable 1 }

        Ap5BLEntry ::= SEQUENCE
        {
           ap5BLURL                              DisplayString,
           ap5BLReferringURL                     DisplayString,
           ap5BLFirstAccessTS                    DisplayString,
           ap5BLlastAccessTS                     DisplayString,
           ap5BLNumRequests                      INTEGER,
           ap5BLStatus                           INTEGER
        }

        ap5BLURL OBJECT-TYPE
               SYNTAX  DisplayString
               ACCESS  read-only
               STATUS  mandatory
               DESCRIPTION
               "Bad URL."
               ::=  {  ap5BLEntry 1   }

        ap5BLReferringURL OBJECT-TYPE
               SYNTAX  DisplayString
               ACCESS  read-only
               STATUS  mandatory
               DESCRIPTION
               "Referring URL to Bad URL."
               ::=  {  ap5BLEntry 2   }

        ap5BLFirstAccessTS OBJECT-TYPE
               SYNTAX  DisplayString
               ACCESS  read-only
               STATUS  mandatory
               DESCRIPTION
               "Time first bad access occurred (time row added to table)."
               ::=  {  ap5BLEntry 3   }

        ap5BLlastAccessTS OBJECT-TYPE
               SYNTAX  DisplayString
               ACCESS  read-only
               STATUS  mandatory
               DESCRIPTION
               "Time of last access to bad URL."
               ::=  {  ap5BLEntry 4   }

        ap5BLNumRequests OBJECT-TYPE
               SYNTAX  INTEGER
               ACCESS  read-only
               STATUS  mandatory
               DESCRIPTION
               "Count of requests."
               ::=  {  ap5BLEntry 5   }

        ap5BLStatus OBJECT-TYPE
               SYNTAX  INTEGER {
                                normal(1),
                                warning(2),
                                critical(3)
                               }
               ACCESS  read-only
               STATUS  mandatory
               DESCRIPTION
               "Summary status for BL."
               ::=  {  ap5BLEntry 6   }


--******************************************************************************
--* TopURLGroup - URLs with highest access rates                             *
--******************************************************************************

        ap5TopURLTableEntries OBJECT-TYPE
               SYNTAX  INTEGER
               ACCESS  read-only
               STATUS  mandatory
               DESCRIPTION
               "The number of entries in the table."
               ::=  {  ap5TopURLGroup 1   }

        ap5TopURLClearTable OBJECT-TYPE
               SYNTAX  INTEGER {
                                reset(1)
                               }
               ACCESS  read-write
               STATUS  mandatory
               DESCRIPTION
               "Clear the table when set."
               ::=  {  ap5TopURLGroup 2   }

        ap5TopURLInterval OBJECT-TYPE
               SYNTAX  INTEGER
               ACCESS  read-write
               STATUS  mandatory
               DESCRIPTION
               "Seconds to poll for changes."
               ::=  {  ap5TopURLGroup 3   }

        ap5TopURLCircularBuffSize OBJECT-TYPE
               SYNTAX  INTEGER
               ACCESS  read-write
               STATUS  mandatory
               DESCRIPTION
               "Max entries in the table (default 50)."
               ::=  {  ap5TopURLGroup 4   }


        ap5TopURLTable OBJECT-TYPE
               SYNTAX  SEQUENCE OF Ap5TopURLEntry
               ACCESS  not-accessible
               STATUS  mandatory
               DESCRIPTION
               "This table contains a list of the top URLs by hit count."
               ::=  {  ap5TopURLGroup 5 }

        ap5TopURLExclude OBJECT-TYPE
               SYNTAX  DisplayString
               ACCESS  read-write
               STATUS  mandatory
               DESCRIPTION
               "Exclude URLs with these extensions."
               ::=  {  ap5TopURLGroup 6   }

        ap5TopURLExcludeReset OBJECT-TYPE
               SYNTAX  INTEGER {
                                reset(1)
                               }
               ACCESS  read-write
               STATUS  mandatory
               DESCRIPTION
               "Reset exclude list to defaults."
               ::=  {  ap5TopURLGroup 7   }

	ap5TopURLGPEnaDis OBJECT-TYPE
		SYNTAX      INTEGER {enable(1), disable(2)}
		ACCESS      read-write
		STATUS      mandatory
		DESCRIPTION "Enable or disable for the Group."
		::= { ap5TopURLGroup 8 }

        ap5TopURLEntry OBJECT-TYPE
               SYNTAX  Ap5TopURLEntry
               ACCESS  not-accessible
               STATUS  mandatory
               DESCRIPTION
               "This is an entry in the TopURLTable"
               INDEX { ap5TopURLURL}
               ::=  { ap5TopURLTable 1 }

        Ap5TopURLEntry ::= SEQUENCE
        {
           ap5TopURLURL          DisplayString,
           ap5TopURLNumHits      INTEGER,
           ap5TopURLRank         INTEGER
        }

        ap5TopURLURL OBJECT-TYPE
               SYNTAX  DisplayString
               ACCESS  read-only
               STATUS  mandatory
               DESCRIPTION
               "URL."
               ::=  {  ap5TopURLEntry 1   }

        ap5TopURLNumHits OBJECT-TYPE
               SYNTAX  INTEGER
               ACCESS  read-only
               STATUS  mandatory
               DESCRIPTION
               "Number of hits."
               ::=  {  ap5TopURLEntry 2   }

        ap5TopURLRank OBJECT-TYPE
               SYNTAX  INTEGER
               ACCESS  read-only
               STATUS  mandatory
               DESCRIPTION
               "For easy sorting in Abrowser."
               ::=  {  ap5TopURLEntry 3   }


--******************************************************************************
--* URLAvailCounterGroup - Counters available for URL monitoring             *
--******************************************************************************

        ap5URLAvailCounterTableEntries OBJECT-TYPE
               SYNTAX  INTEGER
               ACCESS  read-only
               STATUS  mandatory
               DESCRIPTION
               "The number of entries in the table."
               ::=  {  ap5URLAvailCounterGroup 1   }

        ap5URLAvailCounterTable OBJECT-TYPE
           SYNTAX  SEQUENCE OF Ap5URLAvailCounterEntry
           ACCESS  not-accessible
           STATUS  mandatory
           DESCRIPTION
           "This table contains a list of all monitored AvailCounters"
           ::=  {  ap5URLAvailCounterGroup 2}

        ap5URLAvailCounterEntry OBJECT-TYPE
                                SYNTAX  Ap5URLAvailCounterEntry
                                ACCESS  not-accessible
                                STATUS  mandatory
                                DESCRIPTION
                                "This is an entry in the URLAvailCounterTable"
                                INDEX { ap5URLAvailCounterDescription }
                                        ::=  { ap5URLAvailCounterTable 1 }

        Ap5URLAvailCounterEntry ::= SEQUENCE {
                        ap5URLAvailCounterDescription    DisplayString
        }

        ap5URLAvailCounterDescription OBJECT-TYPE
               SYNTAX  DisplayString
               ACCESS  read-only
               STATUS  mandatory
               DESCRIPTION
               "The description of the AvailCounter"
               ::=  {  ap5URLAvailCounterEntry 1   }

--******************************************************************************
--* URLMntrGroup - Monitored URLs                                            *
--******************************************************************************

        ap5URLMntrTableEntries OBJECT-TYPE
               SYNTAX  INTEGER
               ACCESS  read-only
               STATUS  mandatory
               DESCRIPTION
               "The number of entries in the table."
               ::=  {  ap5URLMntrGroup 1   }

        ap5URLMntrInterval OBJECT-TYPE
               SYNTAX  INTEGER
               ACCESS  read-write
               STATUS  mandatory
               DESCRIPTION
               "Seconds between polls for the counter."
               ::=  {  ap5URLMntrGroup 2   }

        ap5URLMntrHitRate OBJECT-TYPE
               SYNTAX  INTEGER
               ACCESS  read-write
               STATUS  mandatory
               DESCRIPTION
               "Interval in seconds over which the counter is measured."
               ::=  {  ap5URLMntrGroup 3   }

--      Add a counter to the table.  The value must include at least the first four of
--      the 6 items listed, separated by commas.
--      <ap5URLAvailCounterDescription> is a value from ap5URLAvailCounterDescription in ap5URLAvailCounterTable.

        ap5URLMntrAdd OBJECT-TYPE
               SYNTAX  DisplayString
               ACCESS  write-only
               STATUS  mandatory
               DESCRIPTION
               "Add this entry to the table: <url>,<URLAvailCounterDescription>,<warning threshold>,<critical threshold>,<warning action>,<critical action>."
               ::=  {  ap5URLMntrGroup 4   }

--      Delete a counter from the table.  The value must include the 2 items listed.
        ap5URLMntrDelete OBJECT-TYPE
               SYNTAX  DisplayString
               ACCESS  write-only
               STATUS  mandatory
               DESCRIPTION
               "Delete entry from the table: <URLMntrDesc>,<url>."
               ::=  {  ap5URLMntrGroup 5   }

        ap5URLMntrUpdate OBJECT-TYPE
               SYNTAX  DisplayString
               ACCESS  write-only
               STATUS  mandatory
	       DESCRIPTION "Update this entry in the table."
               ::=  {  ap5URLMntrGroup 6   }

        ap5URLMntrSummaryStatus OBJECT-TYPE
               SYNTAX  INTEGER {
                                normal(1),
                                warning(2),
                                critical(3)
                               }
               ACCESS  read-only
               STATUS  mandatory
               DESCRIPTION
               "Most severe status of all rows in the table."
               ::=  {  ap5URLMntrGroup 7   }

        ap5URLMntrTable OBJECT-TYPE
               SYNTAX  SEQUENCE OF Ap5URLMntrEntry
               ACCESS  not-accessible
               STATUS  mandatory
               DESCRIPTION
               "This table contains a list of URLs to monitor."
               ::=  {  ap5URLMntrGroup 8}

        ap5URLMntrEntry OBJECT-TYPE
               SYNTAX  Ap5URLMntrEntry
               ACCESS  not-accessible
               STATUS  mandatory
               DESCRIPTION
               "This is an entry in the URLMntrTable"
               INDEX { ap5URLMntrURL, ap5URLMntrDesc}
               ::=  { ap5URLMntrTable 1 }

        Ap5URLMntrEntry ::= SEQUENCE
        {
           ap5URLMntrURL                 DisplayString,
           ap5URLMntrDesc                DisplayString,
           ap5URLMntrValue               DisplayString,
           ap5URLMntrWarningThreshold    INTEGER,
           ap5URLMntrCriticalThreshold   INTEGER,
           ap5URLMntrWarningAction       DisplayString,
           ap5URLMntrCriticalAction      DisplayString,
           ap5URLMntrStatus              INTEGER,
           ap5URLMntrEnableDisable       INTEGER,
           ap5URLMntrDescending          INTEGER,
           ap5URLMntrReset               INTEGER,
           ap5URLMntrResetTime           DisplayString,
	   ap5URLMntrValueReported	INTEGER,
           ap5URLMntrPrevStatus          INTEGER,
	   ap5URLMntrLagSetting		INTEGER,
	   ap5URLMntrLagValue		INTEGER
        }

        ap5URLMntrURL OBJECT-TYPE
               SYNTAX  DisplayString
               ACCESS  read-only
               STATUS  mandatory
               DESCRIPTION
               "URL to monitor."
               ::=  {  ap5URLMntrEntry 1   }

        ap5URLMntrDesc OBJECT-TYPE
               SYNTAX  DisplayString
               ACCESS  read-only
               STATUS  mandatory
               DESCRIPTION
               "Description of the monitored value."
               ::=  {  ap5URLMntrEntry 2   }

        ap5URLMntrValue OBJECT-TYPE
               SYNTAX  DisplayString
               ACCESS  read-only
               STATUS  mandatory
               DESCRIPTION
               "Peak number of hits per URLMntrHitRate seconds."
               ::=  {  ap5URLMntrEntry 3   }

        ap5URLMntrWarningThreshold OBJECT-TYPE
               SYNTAX  INTEGER
               ACCESS  read-write
               STATUS  mandatory
               DESCRIPTION
               "Warning threshold in MS"
               ::=  {  ap5URLMntrEntry 4   }

        ap5URLMntrCriticalThreshold OBJECT-TYPE
               SYNTAX  INTEGER
               ACCESS  read-write
               STATUS  mandatory
               DESCRIPTION
               "Critical threshold in MS"
               ::=  {  ap5URLMntrEntry 5   }

        ap5URLMntrWarningAction OBJECT-TYPE
               SYNTAX  DisplayString
               ACCESS  read-write
               STATUS  mandatory
               DESCRIPTION
               "Command to be executed when warning threshold is exceeded."
               ::=  {  ap5URLMntrEntry 6   }

        ap5URLMntrCriticalAction OBJECT-TYPE
               SYNTAX  DisplayString
               ACCESS  read-write
               STATUS  mandatory
               DESCRIPTION
               "Command to be executed when critical threshold is exceeded."
               ::=  {  ap5URLMntrEntry 7  }

        ap5URLMntrStatus OBJECT-TYPE
               SYNTAX  INTEGER {
                                normal(1),
                                warning(2),
                                critical(3)
                               }
               ACCESS  read-only
               STATUS  mandatory
               DESCRIPTION
               "Status of this URL."
               ::=  {  ap5URLMntrEntry 8 }

        ap5URLMntrEnableDisable OBJECT-TYPE
                SYNTAX  INTEGER
                {
                    enable(1),
                    disable(2)
                }
                ACCESS  read-write
                STATUS  mandatory
                DESCRIPTION
                "Enable or disable alerts for this URL."
                ::=  {  ap5URLMntrEntry 9   }

        ap5URLMntrDescending OBJECT-TYPE
               SYNTAX  INTEGER {
                                no(1),
                                yes(2)
                               }
               ACCESS  read-only
               STATUS  mandatory
               DESCRIPTION
               "Yes if lower value triggers thresholds."
               ::=  {  ap5URLMntrEntry 10 }

        ap5URLMntrReset OBJECT-TYPE
               SYNTAX  INTEGER {
                                reset(1)
                               }
               ACCESS  write-only
               STATUS  mandatory
               DESCRIPTION
               "Reset value for this counter."
               ::=  {  ap5URLMntrEntry 11 }

        ap5URLMntrResetTime OBJECT-TYPE
               SYNTAX  DisplayString
               ACCESS  read-only
               STATUS  mandatory
               DESCRIPTION
               "Time stamp of when this counter was reset."
               ::=  {  ap5URLMntrEntry 12  }
	       

        ap5URLMntrValueReported OBJECT-TYPE
               SYNTAX  INTEGER {
                                summary(1),
                                average(2),
				vhost(3)
                               }
               ACCESS  read-write
               STATUS  mandatory
               DESCRIPTION
               "The reported value of the counter is either a summary or average of all servers, or virtaul host."
               ::=  {  ap5URLMntrEntry 13 }

        ap5URLMntrPrevStatus OBJECT-TYPE
               SYNTAX  INTEGER {
                                normal(1),
                                warning(2),
                                critical(3)
                               }
               ACCESS  read-only
               STATUS  mandatory
               DESCRIPTION
               "Status of this URL."
               ::=  {  ap5URLMntrEntry 14 }
		
        ap5URLMntrLagSetting OBJECT-TYPE
                SYNTAX  INTEGER
                ACCESS  read-write
                STATUS  mandatory
                DESCRIPTION
                "Lag setting for the counter."
                ::=  {  ap5URLMntrEntry 15   }
		
        ap5URLMntrLagValue OBJECT-TYPE
                SYNTAX  INTEGER
                ACCESS  read-only
                STATUS  mandatory
                DESCRIPTION
                "Current Lag value for the counter."
                ::=  {  ap5URLMntrEntry 16   }


        ap5URLMntrDispTableEntries OBJECT-TYPE
               SYNTAX  INTEGER
               ACCESS  read-only
               STATUS  mandatory
               DESCRIPTION
               "The number of entries in the table."
               ::=  {  ap5URLMntrGroup 9   }

        ap5URLMntrDispTable OBJECT-TYPE
               SYNTAX  SEQUENCE OF Ap5URLMntrDispEntry
               ACCESS  not-accessible
               STATUS  mandatory
               DESCRIPTION
               "This table contains a list of URLs to monitor."
               ::=  {  ap5URLMntrGroup 10}

	ap5URLMntrGPEnaDis OBJECT-TYPE
		SYNTAX      INTEGER {enable(1), disable(2)}
		ACCESS      read-write
		STATUS      mandatory
		DESCRIPTION "Enable or disable for the Group."
		::= { ap5URLMntrGroup 11 }

        ap5URLMntrResetCmd OBJECT-TYPE
               SYNTAX  DisplayString
               ACCESS  write-only
               STATUS  mandatory
               DESCRIPTION
               "Reset entry from the table: <URLMntrDesc>,<url>."
               ::=  {  ap5URLMntrGroup 12 }

        ap5URLMntrDispEntry OBJECT-TYPE
               SYNTAX  Ap5URLMntrDispEntry
               ACCESS  not-accessible
               STATUS  mandatory
               DESCRIPTION
               "This is an entry in the URLMntrTable"
               INDEX { ap5URLMntrDispURL, ap5URLMntrDispDesc}
               ::=  { ap5URLMntrDispTable 1 }

        Ap5URLMntrDispEntry ::= SEQUENCE
        {
           ap5URLMntrDispURL                     DisplayString,
           ap5URLMntrDispDesc                    DisplayString,
           ap5URLMntrDispValue                   DisplayString,
           ap5URLMntrDispWarningThreshold        INTEGER,
           ap5URLMntrDispCriticalThreshold       INTEGER,
           ap5URLMntrDispWarningAction           DisplayString,
           ap5URLMntrDispCriticalAction          DisplayString,
           ap5URLMntrDispStatus                  INTEGER,
           ap5URLMntrDispEnableDisable           INTEGER,
           ap5URLMntrDispDescending              INTEGER,
           ap5URLMntrDispReset                   INTEGER,
           ap5URLMntrDispResetTime               DisplayString,
	   ap5URLMntrDispValueReported		INTEGER,
	   ap5URLMntrDispLagSetting		INTEGER,
	   ap5URLMntrDispLagValue		INTEGER
        }

        ap5URLMntrDispURL OBJECT-TYPE
               SYNTAX  DisplayString
               ACCESS  read-only
               STATUS  mandatory
               DESCRIPTION
               "URL to monitor."
               ::=  {  ap5URLMntrDispEntry 1   }

        ap5URLMntrDispDesc OBJECT-TYPE
               SYNTAX  DisplayString
               ACCESS  read-only
               STATUS  mandatory
               DESCRIPTION
               "Description of the monitored value."
               ::=  {  ap5URLMntrDispEntry 2   }

        ap5URLMntrDispValue OBJECT-TYPE
               SYNTAX  DisplayString
               ACCESS  read-only
               STATUS  mandatory
               DESCRIPTION
               "Peak number of hits per URLMntrDispHitRate seconds."
               ::=  {  ap5URLMntrDispEntry 3   }

        ap5URLMntrDispWarningThreshold OBJECT-TYPE
               SYNTAX  INTEGER
               ACCESS  read-write
               STATUS  mandatory
               DESCRIPTION
               "Warning threshold in MS"
               ::=  {  ap5URLMntrDispEntry 4   }

        ap5URLMntrDispCriticalThreshold OBJECT-TYPE
               SYNTAX  INTEGER
               ACCESS  read-write
               STATUS  mandatory
               DESCRIPTION
               "Critical threshold in MS"
               ::=  {  ap5URLMntrDispEntry 5   }

        ap5URLMntrDispWarningAction OBJECT-TYPE
               SYNTAX  DisplayString
               ACCESS  read-write
               STATUS  mandatory
               DESCRIPTION
               "Command to be executed when warning threshold is exceeded."
               ::=  {  ap5URLMntrDispEntry 6   }

        ap5URLMntrDispCriticalAction OBJECT-TYPE
               SYNTAX  DisplayString
               ACCESS  read-write
               STATUS  mandatory
               DESCRIPTION
               "Command to be executed when critical threshold is exceeded."
               ::=  {  ap5URLMntrDispEntry 7  }

        ap5URLMntrDispStatus OBJECT-TYPE
               SYNTAX  INTEGER {
                                normal(1),
                                warning(2),
                                critical(3)
                               }
               ACCESS  read-only
               STATUS  mandatory
               DESCRIPTION
               "Status of this URL."
               ::=  {  ap5URLMntrDispEntry 8 }

        ap5URLMntrDispEnableDisable OBJECT-TYPE
                SYNTAX  INTEGER
                {
                    enable(1),
                    disable(2)
                }
                ACCESS  read-write
                STATUS  mandatory
                DESCRIPTION
                "Enable or disable alerts for this URL."
                ::=  {  ap5URLMntrDispEntry 9   }

        ap5URLMntrDispDescending OBJECT-TYPE
               SYNTAX  INTEGER {
                                no(1),
                                yes(2)
                               }
               ACCESS  read-only
               STATUS  mandatory
               DESCRIPTION
               "Yes if lower value triggers thresholds."
               ::=  {  ap5URLMntrDispEntry 10 }

        ap5URLMntrDispReset OBJECT-TYPE
               SYNTAX  INTEGER {
                                reset(1)
                               }
               ACCESS  write-only
               STATUS  mandatory
               DESCRIPTION
               "Reset value for this counter."
               ::=  {  ap5URLMntrDispEntry 11 }

        ap5URLMntrDispResetTime OBJECT-TYPE
               SYNTAX  DisplayString
               ACCESS  read-only
               STATUS  mandatory
               DESCRIPTION
               "Time stamp of when this counter was reset."
               ::=  {  ap5URLMntrDispEntry 12  }
	       

        ap5URLMntrDispValueReported OBJECT-TYPE
               SYNTAX  INTEGER {
                                summary(1),
                                average(2),
				vhost(3)
                               }
               ACCESS  read-write
               STATUS  mandatory
               DESCRIPTION
               "The reported value of the counter is either a summary or average of all servers, or virtaul host."
               ::=  {  ap5URLMntrDispEntry 13 }
		
        ap5URLMntrDispLagSetting OBJECT-TYPE
                SYNTAX  INTEGER
                ACCESS  read-write
                STATUS  mandatory
                DESCRIPTION
                "Lag setting for the counter."
                ::=  {  ap5URLMntrDispEntry 14   }
		
        ap5URLMntrDispLagValue OBJECT-TYPE
                SYNTAX  INTEGER
                ACCESS  read-only
                STATUS  mandatory
                DESCRIPTION
                "Current Lag value for the counter."
                ::=  {  ap5URLMntrDispEntry 15   }


--******************************************************************************
--* DiskGroup - Primary disks used by the web server                         *
--******************************************************************************

        ap5DiskTableEntries OBJECT-TYPE
                SYNTAX  INTEGER
                ACCESS  read-only
                STATUS  mandatory
                DESCRIPTION
                "The number of entries in the table."
                ::=  {  ap5DiskGroup 1   }

        ap5DiskSummaryStatus OBJECT-TYPE
                SYNTAX  INTEGER
                {
                    ok(1),
                    warning(2),
                    critical(3)
                }
                ACCESS  read-only
                STATUS  mandatory
                DESCRIPTION
                "The summary status of all monitored disks."
                ::=  {  ap5DiskGroup 2   }

        ap5DiskPollingInterval OBJECT-TYPE
                SYNTAX  INTEGER
                ACCESS  read-write
                STATUS  mandatory
                DESCRIPTION
                "Poll interval for the disk group in seconds."
                ::=  {  ap5DiskGroup 3   }

        ap5DiskWarningCount OBJECT-TYPE
                SYNTAX  INTEGER
                ACCESS  read-only
                STATUS  mandatory
                DESCRIPTION
                "Number of disks in warning state."
                ::=  {  ap5DiskGroup 4   }

        ap5DiskCriticalCount OBJECT-TYPE
                SYNTAX  INTEGER
                ACCESS  read-only
                STATUS  mandatory
                DESCRIPTION
                "Number of disks in critical state."
                ::=  {  ap5DiskGroup 5  }

        ap5DiskTable OBJECT-TYPE
                SYNTAX  SEQUENCE OF Ap5DiskEntry
                ACCESS  not-accessible
                STATUS  mandatory
                DESCRIPTION
                "The list of all monitored disks."
                ::=  {  ap5DiskGroup 6 }

	ap5DiskGPEnaDis OBJECT-TYPE
		SYNTAX      INTEGER {enable(1), disable(2)}
		ACCESS      read-write
		STATUS      mandatory
		DESCRIPTION "Enable or disable for the Group."
		::= { ap5DiskGroup 7 }

        ap5DiskEntry OBJECT-TYPE
                SYNTAX  Ap5DiskEntry
                ACCESS  not-accessible
                STATUS  mandatory
                DESCRIPTION
                "The DiskTable entry."
                INDEX { ap5DiskID }
                    ::=  { ap5DiskTable 1 }

        Ap5DiskEntry ::= SEQUENCE
        {
            ap5DiskID                 	DisplayString,
            ap5DiskSize               	DisplayString,
            ap5DiskUsed              	DisplayString,
            ap5DiskFree               	DisplayString,
            ap5DiskWarningThreshold   	INTEGER,
            ap5DiskCriticalThreshold  	INTEGER,
            ap5DiskStatus             	INTEGER,
            ap5WarningCounts          	INTEGER,
            ap5CriticalCounts         	INTEGER,
            ap5DiskUsage              	DisplayString,
            ap5PrevWarningCounts      	INTEGER,
            ap5PrevCriticalCounts     	INTEGER,
	    ap5DiskLagSetting		INTEGER,
	    ap5DiskLagValue		INTEGER
        }

        ap5DiskID OBJECT-TYPE
                SYNTAX  DisplayString
                ACCESS  read-only
                STATUS  mandatory
                DESCRIPTION
                "The directory whose disk is measured."
                ::=  {  ap5DiskEntry 1   }

        ap5DiskSize OBJECT-TYPE
                SYNTAX  DisplayString
                ACCESS  read-only
                STATUS  mandatory
                DESCRIPTION
                "Size of the disk in Mbytes."
                ::=  {  ap5DiskEntry 2   }

        ap5DiskUsed OBJECT-TYPE
                SYNTAX  DisplayString
                ACCESS  read-only
                STATUS  mandatory
                DESCRIPTION
                "Space used on the disk in Mbytes"
                ::=  {  ap5DiskEntry 3   }

        ap5DiskFree OBJECT-TYPE
                SYNTAX  DisplayString
                ACCESS  read-only
                STATUS  mandatory
                DESCRIPTION
                "Free space on the disk in Mbytes"
                ::=  {  ap5DiskEntry 4   }

        ap5DiskWarningThreshold OBJECT-TYPE
                SYNTAX  INTEGER
                ACCESS  read-write
                STATUS  mandatory
                DESCRIPTION
                "Percentage of disk used which will trigger warning status."
                ::=  {  ap5DiskEntry 5   }

        ap5DiskCriticalThreshold OBJECT-TYPE
                SYNTAX  INTEGER
                ACCESS  read-write
                STATUS  mandatory
                DESCRIPTION
                "Percentage of disk used which will trigger critical status."
                ::=  {  ap5DiskEntry 6   }

        ap5DiskStatus OBJECT-TYPE
                SYNTAX  INTEGER
                {
                    ok(1),
                    warning(2),
                    critical(3)
                }
                ACCESS  read-only
                STATUS  mandatory
                DESCRIPTION
                "The status of the disk."
                ::=  {  ap5DiskEntry 7   }

        ap5WarningCounts OBJECT-TYPE
                SYNTAX  INTEGER
                ACCESS  read-only
                STATUS  mandatory
                DESCRIPTION
                "Number of times warning alert generated."
                ::=  {  ap5DiskEntry 8   }

        ap5CriticalCounts OBJECT-TYPE
                SYNTAX  INTEGER
                ACCESS  read-only
                STATUS  mandatory
                DESCRIPTION
                "Number of times critical alert generated."
                ::=  {  ap5DiskEntry 9   }

        ap5DiskUsage OBJECT-TYPE
                SYNTAX  DisplayString
                ACCESS  read-only
                STATUS  mandatory
                DESCRIPTION
                "What the web server uses this disk for."
                ::=  {  ap5DiskEntry 10   }

        ap5PrevWarningCounts OBJECT-TYPE
               SYNTAX  INTEGER
               ACCESS  read-only
               STATUS  mandatory
               DESCRIPTION
               "Previous number of times warning alert generated."
               ::=  {  ap5DiskEntry 11  }

        ap5PrevCriticalCounts OBJECT-TYPE
               SYNTAX  INTEGER
               ACCESS  read-only
               STATUS  mandatory
               DESCRIPTION
               "Previous number of times critical alert generated."
               ::=  {  ap5DiskEntry 12   }
		
        ap5DiskLagSetting OBJECT-TYPE
                SYNTAX  INTEGER
                ACCESS  read-write
                STATUS  mandatory
                DESCRIPTION
                "Lag setting for the disk."
                ::=  {  ap5DiskEntry 13   }
		
        ap5DiskLagValue OBJECT-TYPE
                SYNTAX  INTEGER
                ACCESS  read-only
                STATUS  mandatory
                DESCRIPTION
                "Current Lag value for the disk."
                ::=  {  ap5DiskEntry 14   }


--******************************************************************************
--* AvailCounterGroup - Counters currently available                         *
--******************************************************************************

        ap5AvailCounterTableEntries OBJECT-TYPE
                SYNTAX  INTEGER
                ACCESS  read-only
                STATUS  mandatory
                DESCRIPTION
                "The number of entries in the table."
                ::=  {  ap5AvailCounterGroup 1   }

        ap5AvailCounterTable OBJECT-TYPE
                SYNTAX  SEQUENCE OF Ap5AvailCounterEntry
                ACCESS  not-accessible
                STATUS  mandatory
                DESCRIPTION
                "The list of all available counters"
                ::=  {  ap5AvailCounterGroup 2}

        ap5AvailCounterEntry OBJECT-TYPE
                 SYNTAX  Ap5AvailCounterEntry
                 ACCESS  not-accessible
                 STATUS  mandatory
                 DESCRIPTION
                 "The AvailCounterTable entry."
                 INDEX { ap5AvailCounterDescription }
                     ::=  { ap5AvailCounterTable 1 }

        Ap5AvailCounterEntry ::= SEQUENCE
        {
            ap5AvailCounterDescription   DisplayString
        }

        ap5AvailCounterDescription OBJECT-TYPE
                SYNTAX  DisplayString
                ACCESS  read-only
                STATUS  mandatory
                DESCRIPTION
                "The description of the available counter"
                ::=  {  ap5AvailCounterEntry 1   }


--******************************************************************************
--* ap5PolledCounterGroup - Counters being polled                               *
--******************************************************************************

        ap5PolledCounterTableEntries OBJECT-TYPE
                SYNTAX  INTEGER
                ACCESS  read-only
                STATUS  mandatory
                DESCRIPTION
                "The number of entries in the table."
                ::=  {  ap5PolledCounterGroup 1   }

        ap5PolledCounterAdd OBJECT-TYPE
                SYNTAX  DisplayString
                ACCESS  write-only
                STATUS  mandatory
                DESCRIPTION
                "Add this counter to the polled counter table."
                ::=  {  ap5PolledCounterGroup 2   }

        ap5PolledCounterDelete OBJECT-TYPE
                SYNTAX  DisplayString
                ACCESS  write-only
                STATUS  mandatory
                DESCRIPTION
                "Delete this counter from the polled counter table."
                ::=  {  ap5PolledCounterGroup 3   }

        ap5PolledSummaryStatus OBJECT-TYPE
                SYNTAX  INTEGER
                {
                    normal(1),
                    warning(2),
                    critical(3)
                }
                ACCESS  read-only
                STATUS  mandatory
                DESCRIPTION
                "The summary status of all polled counters."
                ::=  {  ap5PolledCounterGroup 4   }

        ap5PollingInterval OBJECT-TYPE
                SYNTAX  INTEGER
                ACCESS  read-write
                STATUS  mandatory
                DESCRIPTION
                "Poll interval for the polled counter group in seconds."
                ::=  {  ap5PolledCounterGroup 5   }

        ap5PolledWarningCount OBJECT-TYPE
                SYNTAX  INTEGER
                ACCESS  read-only
                STATUS  mandatory
                DESCRIPTION
                "Number of polled counters in warning state."
                ::=  {  ap5PolledCounterGroup 6   }

        ap5PolledCriticalCount OBJECT-TYPE
                SYNTAX  INTEGER
                ACCESS  read-only
                STATUS  mandatory
                DESCRIPTION
                "Number of polled counters in critical state."
                ::=  {  ap5PolledCounterGroup 7   }

        ap5PolledCounterTable OBJECT-TYPE
                SYNTAX  SEQUENCE OF Ap5PolledCounterEntry
                ACCESS  not-accessible
                STATUS  mandatory
                DESCRIPTION
                "The list of all polled counters."
                ::=  {  ap5PolledCounterGroup 8}

        ap5PolledCounterEntry OBJECT-TYPE
                 SYNTAX  Ap5PolledCounterEntry
                 ACCESS  not-accessible
                 STATUS  mandatory
                 DESCRIPTION
                 "The PolledCounterTable entry."
                 INDEX { ap5Description }
                     ::=  { ap5PolledCounterTable 1 }

        Ap5PolledCounterEntry ::= SEQUENCE {
            ap5Description               DisplayString,
            ap5Available                 INTEGER,
            ap5WarningThreshold          DisplayString,
            ap5CriticalThreshold         DisplayString,
            ap5Value                     DisplayString,
            ap5WarningCount              INTEGER,
            ap5CriticalCount             INTEGER,
            ap5WarningAction             DisplayString,
            ap5CriticalAction            DisplayString,
            ap5Status                    INTEGER,
            ap5EnableDisable             INTEGER,
            ap5DescendingCounter         INTEGER,
            ap5Minimum                   DisplayString,
            ap5Maximum                   DisplayString,
            ap5Average                   DisplayString,
            ap5StdDev                    DisplayString,
	    ap5ValueReported		INTEGER,
            ap5PrevStatus          	INTEGER,
	    ap5LagSetting		INTEGER,
	    ap5LagValue			INTEGER
        }

        ap5Description OBJECT-TYPE
                SYNTAX  DisplayString
                ACCESS  read-only
                STATUS  mandatory
                DESCRIPTION
                "The description of the polled counter."
                ::=  {  ap5PolledCounterEntry 1   }

        ap5Available OBJECT-TYPE
                SYNTAX  INTEGER
                {
                    available(1),
                    notavailable(2)
                }
                ACCESS  read-only
                STATUS  mandatory
                DESCRIPTION
                "Describes whether this counter is currently available."
                ::=  {  ap5PolledCounterEntry 2   }

        ap5WarningThreshold OBJECT-TYPE
                SYNTAX  DisplayString
                ACCESS  read-write
                STATUS  mandatory
                DESCRIPTION
                "Counter value that will trigger warning status if value exceeds it."
                ::=  {  ap5PolledCounterEntry 3   }

        ap5CriticalThreshold OBJECT-TYPE
                SYNTAX  DisplayString
                ACCESS  read-write
                STATUS  mandatory
                DESCRIPTION
                "Counter value that will trigger critical status if value exceeds it."
                ::=  {  ap5PolledCounterEntry 4   }

        ap5Value OBJECT-TYPE
                SYNTAX  DisplayString
                ACCESS  read-only
                STATUS  mandatory
                DESCRIPTION
                "Value of the polled counter."
                ::=  {  ap5PolledCounterEntry 5   }

        ap5WarningCount OBJECT-TYPE
                SYNTAX  INTEGER
                ACCESS  read-only
                STATUS  mandatory
                DESCRIPTION
                "Number of times warning alert generated."
                ::=  {  ap5PolledCounterEntry 6   }

        ap5CriticalCount OBJECT-TYPE
                SYNTAX  INTEGER
                ACCESS  read-only
                STATUS  mandatory
                DESCRIPTION
                "Number of times critical alert generated."
                ::=  {  ap5PolledCounterEntry 7   }

        ap5WarningAction OBJECT-TYPE
                SYNTAX  DisplayString
                ACCESS  read-write
                STATUS  mandatory
                DESCRIPTION
                "Command to be executed when warning threshold is exceeded."
                ::=  {  ap5PolledCounterEntry 8   }

        ap5CriticalAction OBJECT-TYPE
                SYNTAX  DisplayString
                ACCESS  read-write
                STATUS  mandatory
                DESCRIPTION
                "Command to be executed when critical threshold is exceeded."
                ::=  {  ap5PolledCounterEntry 9   }

        ap5Status OBJECT-TYPE
                SYNTAX  INTEGER
                {
                    normal(1),
                    warning(2),
                    critical(3)
                }
                ACCESS  read-only
                STATUS  mandatory
                DESCRIPTION
                "Status of the polled counter."
                ::=  {  ap5PolledCounterEntry 10   }

        ap5EnableDisable OBJECT-TYPE
                SYNTAX  INTEGER
                {
                    enable(1),
                    disable(2)
                }
                ACCESS  read-write
                STATUS  mandatory
                DESCRIPTION
                "Enable or disable alerts for this counter."
                ::=  {  ap5PolledCounterEntry 11   }

        ap5DescendingCounter OBJECT-TYPE
                SYNTAX  INTEGER
                {
                    no(1),
                    yes(2)
                }
                ACCESS  read-write
                STATUS  mandatory
                DESCRIPTION
                "Yes if lower value triggers thresholds, no if higher value triggers thresholds."
                ::=  {  ap5PolledCounterEntry 12   }

        ap5Minimum OBJECT-TYPE
               SYNTAX  DisplayString
               ACCESS  read-only
               STATUS  mandatory
               DESCRIPTION
               "The minimum reading since the last reset."
               ::=  {  ap5PolledCounterEntry 13   }

        ap5Maximum OBJECT-TYPE
               SYNTAX  DisplayString
               ACCESS  read-only
               STATUS  mandatory
               DESCRIPTION
               "The maximum reading since the last reset."
               ::=  {  ap5PolledCounterEntry 14   }

        ap5Average OBJECT-TYPE
               SYNTAX  DisplayString
               ACCESS  read-only
               STATUS  mandatory
               DESCRIPTION
               "The average reading since the last reset."
               ::=  {  ap5PolledCounterEntry 15   }

        ap5StdDev OBJECT-TYPE
               SYNTAX  DisplayString
               ACCESS  read-only
               STATUS  mandatory
               DESCRIPTION
               "The standard deviation based on the last 100 readings."
               ::=  {  ap5PolledCounterEntry 16   }

        ap5ValueReported OBJECT-TYPE
               SYNTAX  INTEGER {
                                summary(1),
                                average(2),
				vhost(3)
                               }
               ACCESS  read-write
               STATUS  mandatory
               DESCRIPTION
               "The reported value of the counter is either a summary or average of all servers."
               ::=  {  ap5PolledCounterEntry 17 }

        ap5PrevStatus OBJECT-TYPE
                SYNTAX  INTEGER
                {
                    normal(1),
                    warning(2),
                    critical(3)
                }
                ACCESS  read-only
                STATUS  mandatory
                DESCRIPTION
                "Previous status of the polled counter."
                ::=  {  ap5PolledCounterEntry 18   }
		
        ap5LagSetting OBJECT-TYPE
                SYNTAX  INTEGER
                ACCESS  read-write
                STATUS  mandatory
                DESCRIPTION
                "Lag setting for the counter."
                ::=  {  ap5PolledCounterEntry 19   }
		
        ap5LagValue OBJECT-TYPE
                SYNTAX  INTEGER
                ACCESS  read-only
                STATUS  mandatory
                DESCRIPTION
                "Current Lag value for the counter."
                ::=  {  ap5PolledCounterEntry 20   }
	       

        ap5PolledCounterUpdate OBJECT-TYPE
               SYNTAX  DisplayString
               ACCESS  write-only
               STATUS  mandatory
	       DESCRIPTION "Update this entry in the table."
               ::=  {  ap5PolledCounterGroup 9  }
	       
        ap5PolledCounterDispTableEntries OBJECT-TYPE
                SYNTAX  INTEGER
                ACCESS  read-only
                STATUS  mandatory
                DESCRIPTION
                "The number of entries in the table."
                ::=  {  ap5PolledCounterGroup 10   }

        ap5PolledCounterDispTable OBJECT-TYPE
                SYNTAX  SEQUENCE OF Ap5PolledCounterDispEntry
                ACCESS  not-accessible
                STATUS  mandatory
                DESCRIPTION
                "The list of all polled counters."
                ::=  {  ap5PolledCounterGroup 11}

        ap5PolledCounterDispEntry OBJECT-TYPE
                 SYNTAX  Ap5PolledCounterDispEntry
                 ACCESS  not-accessible
                 STATUS  mandatory
                 DESCRIPTION
                 "The PolledCounterTable entry."
                 INDEX { ap5DispDescription }
                     ::=  { ap5PolledCounterDispTable 1 }

        Ap5PolledCounterDispEntry ::= SEQUENCE {
            ap5DispDescription           DisplayString,
            ap5DispAvailable             INTEGER,
            ap5DispWarningThreshold      DisplayString,
            ap5DispCriticalThreshold     DisplayString,
            ap5DispValue                 DisplayString,
            ap5DispWarningCount          INTEGER,
            ap5DispCriticalCount         INTEGER,
            ap5DispWarningAction         DisplayString,
            ap5DispCriticalAction        DisplayString,
            ap5DispStatus                INTEGER,
            ap5DispEnableDisable         INTEGER,
            ap5DispDescendingCounter     INTEGER,
            ap5DispMinimum               DisplayString,
            ap5DispMaximum               DisplayString,
            ap5DispAverage               DisplayString,
            ap5DispStdDev                DisplayString,
	    ap5DispValueReported		INTEGER,
	    ap5DispLagSetting		INTEGER,
	    ap5DispLagValue		INTEGER
        }

        ap5DispDescription OBJECT-TYPE
                SYNTAX  DisplayString
                ACCESS  read-only
                STATUS  mandatory
                DESCRIPTION
                "The description of the polled counter."
                ::=  {  ap5PolledCounterDispEntry 1   }

        ap5DispAvailable OBJECT-TYPE
                SYNTAX  INTEGER
                {
                    available(1),
                    notavailable(2)
                }
                ACCESS  read-only
                STATUS  mandatory
                DESCRIPTION
                "Describes whether this counter is currently available."
                ::=  {  ap5PolledCounterDispEntry 2   }

        ap5DispWarningThreshold OBJECT-TYPE
                SYNTAX  DisplayString
                ACCESS  read-write
                STATUS  mandatory
                DESCRIPTION
                "Counter value that will trigger warning status if value exceeds it."
                ::=  {  ap5PolledCounterDispEntry 3   }

        ap5DispCriticalThreshold OBJECT-TYPE
                SYNTAX  DisplayString
                ACCESS  read-write
                STATUS  mandatory
                DESCRIPTION
                "Counter value that will trigger critical status if value exceeds it."
                ::=  {  ap5PolledCounterDispEntry 4   }

        ap5DispValue OBJECT-TYPE
                SYNTAX  DisplayString
                ACCESS  read-only
                STATUS  mandatory
                DESCRIPTION
                "Value of the polled counter."
                ::=  {  ap5PolledCounterDispEntry 5   }

        ap5DispWarningCount OBJECT-TYPE
                SYNTAX  INTEGER
                ACCESS  read-only
                STATUS  mandatory
                DESCRIPTION
                "Number of times warning alert generated."
                ::=  {  ap5PolledCounterDispEntry 6   }

        ap5DispCriticalCount OBJECT-TYPE
                SYNTAX  INTEGER
                ACCESS  read-only
                STATUS  mandatory
                DESCRIPTION
                "Number of times critical alert generated."
                ::=  {  ap5PolledCounterDispEntry 7   }

        ap5DispWarningAction OBJECT-TYPE
                SYNTAX  DisplayString
                ACCESS  read-write
                STATUS  mandatory
                DESCRIPTION
                "Command to be executed when warning threshold is exceeded."
                ::=  {  ap5PolledCounterDispEntry 8   }

        ap5DispCriticalAction OBJECT-TYPE
                SYNTAX  DisplayString
                ACCESS  read-write
                STATUS  mandatory
                DESCRIPTION
                "Command to be executed when critical threshold is exceeded."
                ::=  {  ap5PolledCounterDispEntry 9   }

        ap5DispStatus OBJECT-TYPE
                SYNTAX  INTEGER
                {
                    normal(1),
                    warning(2),
                    critical(3)
                }
                ACCESS  read-only
                STATUS  mandatory
                DESCRIPTION
                "Status of the polled counter."
                ::=  {  ap5PolledCounterDispEntry 10   }

        ap5DispEnableDisable OBJECT-TYPE
                SYNTAX  INTEGER
                {
                    enable(1),
                    disable(2)
                }
                ACCESS  read-write
                STATUS  mandatory
                DESCRIPTION
                "Enable or disable alerts for this counter."
                ::=  {  ap5PolledCounterDispEntry 11   }

        ap5DispDescendingCounter OBJECT-TYPE
                SYNTAX  INTEGER
                {
                    no(1),
                    yes(2)
                }
                ACCESS  read-write
                STATUS  mandatory
                DESCRIPTION
                "Yes if lower value triggers thresholds, no if higher value triggers thresholds."
                ::=  {  ap5PolledCounterDispEntry 12   }

        ap5DispMinimum OBJECT-TYPE
               SYNTAX  DisplayString
               ACCESS  read-only
               STATUS  mandatory
               DESCRIPTION
               "The minimum reading since the last reset."
               ::=  {  ap5PolledCounterDispEntry 13   }

        ap5DispMaximum OBJECT-TYPE
               SYNTAX  DisplayString
               ACCESS  read-only
               STATUS  mandatory
               DESCRIPTION
               "The maximum reading since the last reset."
               ::=  {  ap5PolledCounterDispEntry 14   }

        ap5DispAverage OBJECT-TYPE
               SYNTAX  DisplayString
               ACCESS  read-only
               STATUS  mandatory
               DESCRIPTION
               "The average reading since the last reset."
               ::=  {  ap5PolledCounterDispEntry 15   }

        ap5DispStdDev OBJECT-TYPE
               SYNTAX  DisplayString
               ACCESS  read-only
               STATUS  mandatory
               DESCRIPTION
               "The standard deviation based on the last 100 readings."
               ::=  {  ap5PolledCounterDispEntry 16   }

        ap5DispValueReported OBJECT-TYPE
               SYNTAX  INTEGER {
                                summary(1),
                                average(2),
				vhost(3)
                               }
               ACCESS  read-write
               STATUS  mandatory
               DESCRIPTION
               "The reported value of the counter is either a summary or average of all servers."
               ::=  {  ap5PolledCounterDispEntry 17 }
		
        ap5DispLagSetting OBJECT-TYPE
                SYNTAX  INTEGER
                ACCESS  read-write
                STATUS  mandatory
                DESCRIPTION
                "Lag setting for the counter."
                ::=  {  ap5PolledCounterDispEntry 18   }
		
        ap5DispLagValue OBJECT-TYPE
                SYNTAX  INTEGER
                ACCESS  read-only
                STATUS  mandatory
                DESCRIPTION
                "Current Lag value for the counter."
                ::=  {  ap5PolledCounterDispEntry 19   }

	ap5PolledGPEnaDis OBJECT-TYPE
		SYNTAX      INTEGER {enable(1), disable(2)}
		ACCESS      read-write
		STATUS      mandatory
		DESCRIPTION "Enable or disable for the Group."
		::= { ap5PolledCounterGroup 12 }



--******************************************************************************
--* ap5EventGroup - user defined event monitoring                               *
--******************************************************************************
--      In this agent, we'll put available events in wsEventTable ahead of time
--      and allow the user to enable them for monitoring.

        ap5EventTableEntries OBJECT-TYPE
                SYNTAX  INTEGER
                ACCESS  read-only
                STATUS  mandatory
                DESCRIPTION
                "The number of entries in the event description table."
                ::=  {  ap5EventGroup 1   }

        ap5EventLogTableEntries OBJECT-TYPE
                SYNTAX  INTEGER
                ACCESS  read-only
                STATUS  mandatory
                DESCRIPTION
                "The number of entries in the event log table."
                ::=  {  ap5EventGroup 2   }

        ap5EventAdd OBJECT-TYPE
                SYNTAX  DisplayString
                ACCESS  write-only
                STATUS  mandatory
                DESCRIPTION
                "Event ID to be added to the event table."
                ::=  {  ap5EventGroup 3   }

        ap5EventDelete OBJECT-TYPE
                SYNTAX  INTEGER
                ACCESS  write-only
                STATUS  mandatory
                DESCRIPTION
                "Event ID to be deleted from the event table."
                ::=  {  ap5EventGroup 4   }

        ap5EventSummaryStatus OBJECT-TYPE
                SYNTAX  INTEGER
                {
                    normal(1),
                    warning(2),
                    critical(3)
                }
                ACCESS  read-write
                STATUS  mandatory
                DESCRIPTION
                "Summary status for events. Not automatic, must be manually reset to normal."
                ::=  {  ap5EventGroup 5   }

        ap5EventInterval OBJECT-TYPE
                SYNTAX  INTEGER
                ACCESS  read-write
                STATUS  mandatory
                DESCRIPTION
                "Poll interval for the Event group in seconds."
                ::=  {  ap5EventGroup 6   }

        ap5EventCircularBuffSize OBJECT-TYPE
                SYNTAX  INTEGER
                ACCESS  read-write
                STATUS  mandatory
                DESCRIPTION
                "Maximum number of entries in the event log table.  When this size is
                exceeded, oldest events are deleted to make room for the newest events."
                ::=  {  ap5EventGroup 7   }

        ap5EventTable OBJECT-TYPE
                SYNTAX  SEQUENCE OF Ap5EventEntry
                ACCESS  not-accessible
                STATUS  mandatory
                DESCRIPTION
                "The table of events being monitored."
                ::=  {  ap5EventGroup 8}

        ap5EventLogTable OBJECT-TYPE
                SYNTAX  SEQUENCE OF Ap5EventLogEntry
                ACCESS  not-accessible
                STATUS  mandatory
                DESCRIPTION
                "The table of events that occurred."
                ::=  {  ap5EventGroup 9}

        ap5EventWarningCount OBJECT-TYPE
                SYNTAX  INTEGER
                ACCESS  read-only
                STATUS  mandatory
                DESCRIPTION
                "Number of warning events since last reset."
                ::=  {  ap5EventGroup 10  }

        ap5EventCriticalCount OBJECT-TYPE
                SYNTAX  INTEGER
                ACCESS  read-only
                STATUS  mandatory
                DESCRIPTION
                "Number of critical events since last reset."
                ::=  {  ap5EventGroup 11 }

	ap5EventCmd OBJECT-TYPE
		SYNTAX      DisplayString
		ACCESS      read-write
		STATUS      mandatory
		DESCRIPTION 
		"Modify,id,severity,enabled.  EnableAll DisableAll"
		::= {ap5EventGroup 12 }

	ap5EventGPEnaDis OBJECT-TYPE
		SYNTAX      INTEGER {enable(1), disable(2)}
		ACCESS      read-write
		STATUS      mandatory
		DESCRIPTION "Enable or disable for the Group."
		::= { ap5EventGroup 13 }
		
        ap5EventEntry OBJECT-TYPE
                 SYNTAX  Ap5EventEntry
                 ACCESS  not-accessible
                 STATUS  mandatory
                 DESCRIPTION
                 "The EventTable entry."
                 INDEX { ap5EventID }
                 ::=  { ap5EventTable 1 }

        Ap5EventEntry ::= SEQUENCE
        {
                ap5EventID                    INTEGER,
                ap5EVDescription              DisplayString,
                ap5EVSeverity                 INTEGER,
                ap5EVSyslogText               DisplayString,
                ap5EVEnable                   INTEGER
        }

        ap5EventID OBJECT-TYPE
                SYNTAX  INTEGER
                ACCESS  read-only
                STATUS  mandatory
                DESCRIPTION
                "ID of the event."
                ::=  {  ap5EventEntry 1   }

        ap5EVDescription OBJECT-TYPE
                SYNTAX  DisplayString
                ACCESS  read-write
                STATUS  mandatory
                DESCRIPTION
                "Description of the event."
                ::=  {  ap5EventEntry 2   }

        ap5EVSeverity OBJECT-TYPE
                SYNTAX  INTEGER
                {
                    warning(1),
                    critical(2)
                }
                ACCESS  read-write
                STATUS  mandatory
                DESCRIPTION
                "Severity level of the event."
                ::=  {  ap5EventEntry 3   }

        ap5EVSyslogText OBJECT-TYPE
                SYNTAX  DisplayString
                ACCESS  read-write
                STATUS  mandatory
                DESCRIPTION
                "Text to search for in the syslog file that indicates this event occurred."
                ::=  {  ap5EventEntry 4   }

        ap5EVEnable OBJECT-TYPE
               SYNTAX  INTEGER {
                                dnabled(1),
                                disabled(2)
                               }
               ACCESS  read-write
               STATUS  mandatory
               DESCRIPTION
               "Enable logging of this event."
               ::=  {  ap5EventEntry 5   }


        ap5EventLogEntry OBJECT-TYPE
                 SYNTAX  Ap5EventLogEntry
                 ACCESS  not-accessible
                 STATUS  mandatory
                 DESCRIPTION
                 "The EventTable entry."
                 INDEX { ap5EVLTimestamp, ap5EVLIndex }
                 ::=  { ap5EventLogTable 1 }

        Ap5EventLogEntry ::= SEQUENCE {
           ap5EVLTimestamp               DisplayString,
           ap5EVLID                      INTEGER,
           ap5EVLDescription             DisplayString,
           ap5EVLStatus                  INTEGER,
           ap5EVLIndex                   INTEGER
        }

        ap5EVLTimestamp OBJECT-TYPE
                SYNTAX  DisplayString
                ACCESS  read-only
                STATUS  mandatory
                DESCRIPTION
                "Human-readable timestamp of when the event happened."
                ::=  {  ap5EventLogEntry 1   }

        ap5EVLID OBJECT-TYPE
                SYNTAX  INTEGER
                ACCESS  read-only
                STATUS  mandatory
                DESCRIPTION
                "ID of the event."
                ::=  {  ap5EventLogEntry 2   }

        ap5EVLDescription OBJECT-TYPE
                SYNTAX  DisplayString
                ACCESS  read-only
                STATUS  mandatory
                DESCRIPTION
                "Description of the event."
                ::=  {  ap5EventLogEntry 3   }

        ap5EVLStatus OBJECT-TYPE
                SYNTAX  INTEGER
                {
                    warning(1),
                    critical(2)
                }
                ACCESS  read-only
                STATUS  mandatory
                DESCRIPTION
                "Status caused by the event."
                ::=  {  ap5EventLogEntry 4   }

        ap5EVLIndex OBJECT-TYPE
                SYNTAX  INTEGER
                ACCESS  read-only
                STATUS  mandatory
                DESCRIPTION
                "Index value that ensures uniqueness of events with same ID and timestamp."
                ::=  {  ap5EventLogEntry 5   }


--******************************************************************************
--* ap5AgentGroup - Agent version and update information                        *
--******************************************************************************

        ap5AgentDescription OBJECT-TYPE
                SYNTAX  DisplayString
                ACCESS  read-only
                STATUS  mandatory
                DESCRIPTION
                "Description of the agent."
                ::=  {  ap5AgentGroup 1   }

        ap5AgentVersion OBJECT-TYPE
                SYNTAX  DisplayString
                ACCESS  read-only
                STATUS  mandatory
                DESCRIPTION
                "Version of the agent."
                ::=  {  ap5AgentGroup 2   }

        ap5AgentStartTime OBJECT-TYPE
                SYNTAX  DisplayString
                ACCESS  read-only
                STATUS  mandatory
                DESCRIPTION
                "The time the agent was started."
                ::=  {  ap5AgentGroup 3   }

        ap5ServerLastUpdate OBJECT-TYPE
                SYNTAX  DisplayString
                ACCESS  read-only
                STATUS  mandatory
                DESCRIPTION
                "The time the ServerGroup was last updated"
                ::=  {  ap5AgentGroup 4   }

        ap5ServicesLastUpdate OBJECT-TYPE
                SYNTAX  DisplayString
                ACCESS  read-only
                STATUS  mandatory
                DESCRIPTION
                "The time the ServicesGroup was last updated"
                ::=  {  ap5AgentGroup 5   }

        ap5DiskLastUpdate OBJECT-TYPE
                SYNTAX  DisplayString
                ACCESS  read-only
                STATUS  mandatory
                DESCRIPTION
                "The time the DiskGroup was last updated"
                ::=  {  ap5AgentGroup 6   }

        ap5PolledCounterLastUpdate OBJECT-TYPE
                SYNTAX  DisplayString
                ACCESS  read-only
                STATUS  mandatory
                DESCRIPTION
                "The time the PolledCounterGroup was last updated"
                ::=  {  ap5AgentGroup 7   }

        ap5EventsLastUpdate OBJECT-TYPE
                SYNTAX  DisplayString
                ACCESS  read-only
                STATUS  mandatory
                DESCRIPTION
                "The time the EventGroup was last updated"
                ::=  {  ap5AgentGroup 8   }

        ap5BadLinksLastUpdate OBJECT-TYPE
                SYNTAX  DisplayString
                ACCESS  read-only
                STATUS  mandatory
                DESCRIPTION
                "The time the LinkGroup was last updated"
                ::=  {  ap5AgentGroup 9   }

        ap5WebCrwlrLastUpdate OBJECT-TYPE
                SYNTAX  DisplayString
                ACCESS  read-only
                STATUS  mandatory
                DESCRIPTION
                "The time the WCGroup was last updated"
                ::=  {  ap5AgentGroup 10   }

        ap5URLMntrLastUpdate OBJECT-TYPE
                SYNTAX  DisplayString
                ACCESS  read-only
                STATUS  mandatory
                DESCRIPTION
                "The time the URLMntrGroup was last updated"
                ::=  {  ap5AgentGroup 11   }

        ap5TopURLsLastUpdate OBJECT-TYPE
                SYNTAX  DisplayString
                ACCESS  read-only
                STATUS  mandatory
                DESCRIPTION
                "The time the TopURLGroup was last updated"
                ::=  {  ap5AgentGroup 12   }

        ap5ServerHealthLastUpdate OBJECT-TYPE
               SYNTAX  DisplayString
               ACCESS  read-only
               STATUS  mandatory
               DESCRIPTION
               "The time the ServerHealthGroup was last updated"
               ::=  {  ap5AgentGroup 13   }

        ap5LocalActionLastUpdate OBJECT-TYPE
               SYNTAX  DisplayString
               ACCESS  read-only
               STATUS  mandatory
               DESCRIPTION
               "The last time a local action executed)"
               ::=  {  ap5AgentGroup 14   }

        ap5Ap5LogPath OBJECT-TYPE
               SYNTAX  DisplayString
               ACCESS  read-write
               STATUS  mandatory
               DESCRIPTION
               "OPTIONAL-File name for the Common Log format file"
               ::=  {  ap5AgentGroup 15   }

        ap5ServerRoot OBJECT-TYPE
               SYNTAX  DisplayString
               ACCESS  read-write
               STATUS  mandatory
               DESCRIPTION
               "Server root to prepend to paths in config file."
               ::=  {  ap5AgentGroup 16   }

        ap5ServerConfig OBJECT-TYPE
               SYNTAX  DisplayString
               ACCESS  read-write
               STATUS  mandatory
               DESCRIPTION
               "Server config file path."
               ::=  {  ap5AgentGroup 17   }

        ap5WebServerName OBJECT-TYPE
               SYNTAX  DisplayString
               ACCESS  read-write
               STATUS  mandatory
               DESCRIPTION
               "Service name in NT; command in UNIX; used for start/stop."
               ::=  {  ap5AgentGroup 18   }


        ap5FTPName OBJECT-TYPE
               SYNTAX  DisplayString
               ACCESS  read-write
               STATUS  mandatory
               DESCRIPTION
               "FTP service name in NT; command in UNIX; used for start/stop."
               ::=  {  ap5AgentGroup 19   }


        ap5CGIstrings OBJECT-TYPE
               SYNTAX  DisplayString
               ACCESS  read-write
               STATUS  mandatory
               DESCRIPTION
               "Comma seperated strings used to identify CGI URLs."
               ::=  {  ap5AgentGroup 20   }


        ap5AvailCounterLastUpdate OBJECT-TYPE
               SYNTAX  DisplayString
               ACCESS  read-only
               STATUS  mandatory
               DESCRIPTION
               "The last time a AvailCounter group was updated."
               ::=  {  ap5AgentGroup 21   }


        ap5InstanceName OBJECT-TYPE
               SYNTAX  DisplayString
               ACCESS  read-only
               STATUS  mandatory
               DESCRIPTION
               "The Instance name for this agent."
               ::=  {  ap5AgentGroup 22   }


        ap5ErrorMsg OBJECT-TYPE
               SYNTAX  DisplayString
               ACCESS  read-write
               STATUS  mandatory
               DESCRIPTION
               "The Last Error Message as a result of GET/SET of a MIB value."
               ::=  {  ap5AgentGroup 23   }


        ap5FTPPort OBJECT-TYPE
               SYNTAX  DisplayString
               ACCESS  read-write
               STATUS  mandatory
               DESCRIPTION
               "FTP service port; to change the default (21)."
               ::=  {  ap5AgentGroup 24 }

        ap5ExpressionsLastUpdate OBJECT-TYPE
                SYNTAX  DisplayString
                ACCESS  read-only
                STATUS  mandatory
                DESCRIPTION
                "The time the ExpressionsGroup was last updated"
                ::=  {  ap5AgentGroup 25   }
		
        ap5AdminConfig OBJECT-TYPE
               SYNTAX  DisplayString
               ACCESS  read-write
               STATUS  mandatory
               DESCRIPTION
               "Admin Server config file path."
               ::=  {  ap5AgentGroup 26   }

        ap5WebAdminName OBJECT-TYPE
               SYNTAX  DisplayString
               ACCESS  read-write
               STATUS  mandatory
               DESCRIPTION
               "Admin service name in NT; command qualifier in UNIX; used for start/stop."
               ::=  {  ap5AgentGroup 27   }

        ap5EnableDatabaseUse OBJECT-TYPE
                SYNTAX  INTEGER
                { yes(1), no(2) }
                ACCESS  read-only
                STATUS  mandatory
                DESCRIPTION
                "Domino server: 'Yes' indicates the agent obtains information from Domino Database.
                'No' indicates the agent obtains infomation from Domino generated logfiles."
                ::=  {  ap5AgentGroup 28  }

        ap5DominoName OBJECT-TYPE
                SYNTAX  DisplayString
                ACCESS  read-only
                STATUS  mandatory
                DESCRIPTION
                "Domino server: name for this HTTP server."
                ::=  {  ap5AgentGroup 29   }

        ap5PartitionPath OBJECT-TYPE
                SYNTAX  DisplayString
                ACCESS  read-only
                STATUS  mandatory
                DESCRIPTION
                "Domino server: partition PATH for this HTTP server."
                ::=  {  ap5AgentGroup 30  }

        ap5PartitionNumber OBJECT-TYPE
                SYNTAX  INTEGER
                ACCESS  read-only
                STATUS  mandatory
                DESCRIPTION
                "Domino server: partition number for this HTTP server."
                ::=  {  ap5AgentGroup 31  }
		
        ap5DocPath OBJECT-TYPE
               SYNTAX  DisplayString
               ACCESS  read-write
               STATUS  mandatory
               DESCRIPTION
               "Oracle server: Server doc path."
               ::=  {  ap5AgentGroup 32  }
	       
        ap5ListenerName OBJECT-TYPE
               SYNTAX  DisplayString
               ACCESS  read-write
               STATUS  mandatory
               DESCRIPTION
               "Oracle server: Web listener name."
               ::=  {  ap5AgentGroup 33  }

        ap5ProductRoot OBJECT-TYPE
               SYNTAX  DisplayString
               ACCESS  read-write
               STATUS  mandatory
               DESCRIPTION
               "Oracle server: Product root path."
               ::=  {  ap5AgentGroup 34  }
	       

        ap5IISAvailCounterLastUpdate OBJECT-TYPE
               SYNTAX  DisplayString
               ACCESS  read-only
               STATUS  mandatory
               DESCRIPTION
               "The last time a IISAvailCounter group was updated."
               ::=  {  ap5AgentGroup 35   }

        ap5IISPolledCounterLastUpdate OBJECT-TYPE
               SYNTAX  DisplayString
               ACCESS  read-only
               STATUS  mandatory
               DESCRIPTION
               "The last time a IISPolledCounter group was updated."
               ::=  {  ap5AgentGroup 36   }


--******************************************************************************
--* ServerHealthGroup - overall server performance indicators                  *
--******************************************************************************

        ap5SHSummaryStatus OBJECT-TYPE
               SYNTAX  INTEGER {
                                normal(1),
                                warning(2),
                                critical(3)
                                }
               ACCESS  read-only
               STATUS  mandatory
               DESCRIPTION
               "Summary status for group."
               ::=  {  ap5SHGroup 1   }

        ap5SHPollingInterval OBJECT-TYPE
               SYNTAX  INTEGER
               ACCESS  read-write
               STATUS  mandatory
               DESCRIPTION
               "Seconds to poll for changes."
               ::=  {  ap5SHGroup 2   }

        ap5SHCpuUsage OBJECT-TYPE
               SYNTAX  INTEGER
               ACCESS  read-only
               STATUS  mandatory
               DESCRIPTION
               "CPU usage of the web server."
               ::=  {  ap5SHGroup 3   }

        ap5SHCpuWarningThreshold OBJECT-TYPE
               SYNTAX  INTEGER
               ACCESS  read-write
               STATUS  mandatory
               DESCRIPTION
               "Generate a warning if SHCpuUsage exceeds this."
               ::=  {  ap5SHGroup 4   }

        ap5SHCpuCriticalThreshold OBJECT-TYPE
               SYNTAX  INTEGER
               ACCESS  read-write
               STATUS  mandatory
               DESCRIPTION
               "Generate a critical if SHCpuUsage exceeds this."
               ::=  {  ap5SHGroup 5   }

        ap5SHReqRate OBJECT-TYPE
               SYNTAX  INTEGER
               ACCESS  read-only
               STATUS  mandatory
               DESCRIPTION
               "Requests per second."
               ::=  {  ap5SHGroup 6   }

        ap5SHReqRateWarningThreshold OBJECT-TYPE
               SYNTAX  INTEGER
               ACCESS  read-write
               STATUS  mandatory
               DESCRIPTION
               "Generate a warning if SHReqRate exceeds this."
               ::=  {  ap5SHGroup 7   }

        ap5SHReqRateCriticalThreshold OBJECT-TYPE
               SYNTAX  INTEGER
               ACCESS  read-write
               STATUS  mandatory
               DESCRIPTION
               "Generate a critical if SHReqRate exceeds this."
               ::=  {  ap5SHGroup 8   }

        ap5SHByteRate OBJECT-TYPE
               SYNTAX  INTEGER
               ACCESS  read-only
               STATUS  mandatory
               DESCRIPTION
               "Kilobytes transferred per second."
               ::=  {  ap5SHGroup 9   }

        ap5SHByteRateWarningThreshold OBJECT-TYPE
               SYNTAX  INTEGER
               ACCESS  read-write
               STATUS  mandatory
               DESCRIPTION
               "Generate a warning if SHByteRate exceeds this."
               ::=  {  ap5SHGroup 10   }

        ap5SHByteRateCriticalThreshold OBJECT-TYPE
               SYNTAX  INTEGER
               ACCESS  read-write
               STATUS  mandatory
               DESCRIPTION
               "Generate a critical if SHByteRate exceeds this."
               ::=  {  ap5SHGroup 11   }

        ap5SHWarningAction OBJECT-TYPE
               SYNTAX  DisplayString
               ACCESS  read-write
               STATUS  mandatory
               DESCRIPTION
               "Command to be executed when any warning threshold is exceeded."
               ::=  {  ap5SHGroup 12   }

        ap5SHCriticalAction OBJECT-TYPE
               SYNTAX  DisplayString
               ACCESS  read-write
               STATUS  mandatory
               DESCRIPTION
               "Command to be executed when any critical threshold is exceeded."
               ::=  {  ap5SHGroup 13   }

        ap5SHProcesses OBJECT-TYPE
               SYNTAX  INTEGER
               ACCESS  read-only
               STATUS  mandatory
               DESCRIPTION
               "Number of current server processes."
               ::=  {  ap5SHGroup 14   }

        ap5SHTotalHits OBJECT-TYPE
               SYNTAX  INTEGER
               ACCESS  read-only
               STATUS  mandatory
               DESCRIPTION
               "Totals requests."
               ::=  {  ap5SHGroup 15   }

        ap5SHTotalErrors OBJECT-TYPE
               SYNTAX  INTEGER
               ACCESS  read-only
               STATUS  mandatory
               DESCRIPTION
               "Totals error requests."
               ::=  {  ap5SHGroup 16   }

        ap5SHTotalGETS OBJECT-TYPE
               SYNTAX  INTEGER
               ACCESS  read-only
               STATUS  mandatory
               DESCRIPTION
               "Totals GET requests."
               ::=  {  ap5SHGroup 17   }

        ap5SHTotalPOSTS OBJECT-TYPE
               SYNTAX  INTEGER
               ACCESS  read-only
               STATUS  mandatory
               DESCRIPTION
               "Totals POST requests."
               ::=  {  ap5SHGroup 18   }

        ap5SHTotalHEADS OBJECT-TYPE
               SYNTAX  INTEGER
               ACCESS  read-only
               STATUS  mandatory
               DESCRIPTION
               "Totals HEAD requests."
               ::=  {  ap5SHGroup 19   }

        ap5SHTotalCGI OBJECT-TYPE
               SYNTAX  INTEGER
               ACCESS  read-only
               STATUS  mandatory
               DESCRIPTION
               "Totals CGI requests."
               ::=  {  ap5SHGroup 20   }

        ap5SHServerUptime OBJECT-TYPE
               SYNTAX  INTEGER
               ACCESS  read-only
               STATUS  mandatory
               DESCRIPTION
               "Server uptime in days."
               ::=  {  ap5SHGroup 21   }

        ap5SHMaxReqRate OBJECT-TYPE
               SYNTAX  INTEGER
               ACCESS  read-write
               STATUS  mandatory
               DESCRIPTION
               "Max value for the abrowser max requests scale."
               ::=  {  ap5SHGroup 22   }

        ap5SHMaxByteRate OBJECT-TYPE
               SYNTAX  INTEGER
               ACCESS  read-write
               STATUS  mandatory
               DESCRIPTION
               "Max value for the abrowser max bytes scale."
               ::=  {  ap5SHGroup 23   }

	ap5SHGPEnaDis OBJECT-TYPE
		SYNTAX      INTEGER {enable(1), disable(2)}
		ACCESS      read-write
		STATUS      mandatory
		DESCRIPTION "Enable or disable for the Group."
		::= { ap5SHGroup 24 }
		
        ap5SHCPULagSetting OBJECT-TYPE
                SYNTAX  INTEGER
                ACCESS  read-write
                STATUS  mandatory
                DESCRIPTION
                "Lag setting for the counter."
                ::=  {  ap5SHGroup 25   }
		
        ap5SHCPULagValue OBJECT-TYPE
                SYNTAX  INTEGER
                ACCESS  read-only
                STATUS  mandatory
                DESCRIPTION
                "Current Lag value for the counter."
                ::=  {  ap5SHGroup 26   }
		
        ap5SHRSLagSetting OBJECT-TYPE
                SYNTAX  INTEGER
                ACCESS  read-write
                STATUS  mandatory
                DESCRIPTION
                "Lag setting for the counter."
                ::=  {  ap5SHGroup 27   }
		
        ap5SHRSLagValue OBJECT-TYPE
                SYNTAX  INTEGER
                ACCESS  read-only
                STATUS  mandatory
                DESCRIPTION
                "Current Lag value for the counter."
                ::=  {  ap5SHGroup 28   }
		
        ap5SHKSLagSetting OBJECT-TYPE
                SYNTAX  INTEGER
                ACCESS  read-write
                STATUS  mandatory
                DESCRIPTION
                "Lag setting for the counter."
                ::=  {  ap5SHGroup 29   }
		
        ap5SHKSLagValue OBJECT-TYPE
                SYNTAX  INTEGER
                ACCESS  read-only
                STATUS  mandatory
                DESCRIPTION
                "Current Lag value for the counter."
                ::=  {  ap5SHGroup 30   }


--******************************************************************************
--* Local action log - circular buffer of local actions performed              *
--* Dynamic get, not polled.                                                   *
--******************************************************************************

        ap5LocalActionTableEntries OBJECT-TYPE
               SYNTAX  INTEGER
               ACCESS  read-only
               STATUS  mandatory
               DESCRIPTION
               "The number of entries in the local action log table."
               ::=  {  ap5LocalActionGroup 1   }

        ap5LocalActionCircularBuffSize OBJECT-TYPE
               SYNTAX  INTEGER
               ACCESS  read-write
               STATUS  mandatory
               DESCRIPTION
               "Max entries in the LocalActionLogTable (default 50)."
               ::=  {  ap5LocalActionGroup 2   }

        ap5LocalActionRefresh OBJECT-TYPE
               SYNTAX  INTEGER
               ACCESS  read-write
               STATUS  mandatory
               DESCRIPTION
               "Refresh the table starting with the most recent action."
               ::=  {  ap5LocalActionGroup 3   }

        ap5LocalActionStartDateTime OBJECT-TYPE
               SYNTAX  DisplayString
               ACCESS  read-write
               STATUS  mandatory
               DESCRIPTION
               "Refresh the table starting at the specified date and time."
               ::=  {  ap5LocalActionGroup 4   }

        ap5LocalActionScrollDown OBJECT-TYPE
               SYNTAX  INTEGER
               ACCESS  read-write
               STATUS  mandatory
               DESCRIPTION
               "Read the next older set of log entries into the table."
               ::=  {  ap5LocalActionGroup 5   }

        ap5LocalActionScrollUp OBJECT-TYPE
               SYNTAX  INTEGER
               ACCESS  read-write
               STATUS  mandatory
               DESCRIPTION
               "Read the next newer set of log entries into the table."
               ::=  {  ap5LocalActionGroup 6   }

        ap5LocalActionLogTable OBJECT-TYPE
               SYNTAX  SEQUENCE OF Ap5LocalActionLogEntry
               ACCESS  not-accessible
               STATUS  mandatory
               DESCRIPTION
               "This table contains a list of command actions taken in response to events."
               ::=  {  ap5LocalActionGroup 7 }

        ap5LocalActionLogEntry OBJECT-TYPE
                                SYNTAX  Ap5LocalActionLogEntry
                                ACCESS  not-accessible
                                STATUS  mandatory
                                DESCRIPTION
                                "This is an entry in the LocalActionTable"
                                INDEX { ap5LocalActionSequencer }
                                ::=  { ap5LocalActionLogTable 1 }

        Ap5LocalActionLogEntry ::= SEQUENCE
        {
           ap5LocalActionSequencer               INTEGER,
           ap5LocalActionTimestamp               DisplayString,
           ap5LocalActionSeverity                INTEGER,
           ap5LocalActionReason                  DisplayString,
           ap5LocalActionCommand                 DisplayString
        }

        ap5LocalActionSequencer OBJECT-TYPE
               SYNTAX  INTEGER
               ACCESS  read-only
               STATUS  mandatory
               DESCRIPTION
               "Table sequencer"
               ::=  {  ap5LocalActionLogEntry 1   }

        ap5LocalActionTimestamp OBJECT-TYPE
               SYNTAX  DisplayString
               ACCESS  read-only
               STATUS  mandatory
               DESCRIPTION
               "Time the command was executed (action taken)."
               ::=  {  ap5LocalActionLogEntry 2   }

-- The Warning and Critical values for severity must match CLocalAction::enum Severity.
        ap5LocalActionSeverity OBJECT-TYPE
               SYNTAX  INTEGER
               {
                   normal(1),
                   warning(2),
                   critical(3)
               }
               ACCESS  read-only
               STATUS  mandatory
               DESCRIPTION
               "The severity of the event which triggered the action."
               ::=  {  ap5LocalActionLogEntry 3   }

        ap5LocalActionReason OBJECT-TYPE
               SYNTAX  DisplayString
               ACCESS  read-only
               STATUS  mandatory
               DESCRIPTION
               "The reason the action was taken."
               ::=  {  ap5LocalActionLogEntry 4   }

        ap5LocalActionCommand OBJECT-TYPE
               SYNTAX  DisplayString
               ACCESS  read-only
               STATUS  mandatory
               DESCRIPTION
               "Command executed (action taken)."
               ::=  {  ap5LocalActionLogEntry 5   }


--******************************************************************************
--* ap5ServLogGroup - buffer of server error log                                *
--******************************************************************************

        ap5ServLogTableEntries OBJECT-TYPE
               SYNTAX  INTEGER
               ACCESS  read-only
               STATUS  mandatory
               DESCRIPTION
               "The number of entries in the table."
               ::=  {  ap5ServLogGroup 1   }

        ap5ServLogStartDateTime OBJECT-TYPE
               SYNTAX  DisplayString
               ACCESS  read-write
               STATUS  mandatory
               DESCRIPTION
               "Refresh the table starting at the specified date and time."
               ::=  {  ap5ServLogGroup 2   }

        ap5ServLogReadLog OBJECT-TYPE
               SYNTAX  INTEGER
               ACCESS  read-write
               STATUS  mandatory
               DESCRIPTION
               "Refresh the table starting with the most recent entry."
               ::=  {  ap5ServLogGroup 3   }

        ap5ServLogScrollDown OBJECT-TYPE
               SYNTAX  INTEGER
               ACCESS  read-write
               STATUS  mandatory
               DESCRIPTION
               "Read the next older set of log entries into the table."
               ::=  {  ap5ServLogGroup 4   }

        ap5ServLogScrollUp OBJECT-TYPE
               SYNTAX  INTEGER
               ACCESS  read-write
               STATUS  mandatory
               DESCRIPTION
               "Read the next newer set of log entries into the table."
               ::=  {  ap5ServLogGroup 5   }

        ap5ServLogMaxBuffSize OBJECT-TYPE
               SYNTAX  INTEGER
               ACCESS  read-write
               STATUS  mandatory
               DESCRIPTION
               "Max lines in the wsServLogTable (default 50)."
               ::=  {  ap5ServLogGroup 6   }

        ap5ServLogTable OBJECT-TYPE
               SYNTAX  SEQUENCE OF Ap5ServLogEntry
               ACCESS  not-accessible
               STATUS  mandatory
               DESCRIPTION
               "This table contains the contents of the server log."
               ::=  {  ap5ServLogGroup 7}

        ap5ServLogEntry OBJECT-TYPE
                                SYNTAX  Ap5ServLogEntry
                                ACCESS  not-accessible
                                STATUS  mandatory
                                DESCRIPTION
                                "This is an entry in the ServLogTable"
                                INDEX { ap5ServLogSequencer }
                                ::=  { ap5ServLogTable 1 }

        Ap5ServLogEntry ::= SEQUENCE
        {
           ap5ServLogSequencer           INTEGER,
           ap5ServLogDateTime            DisplayString,
           ap5ServLogMsgType             DisplayString,
           ap5ServLogMsgText             DisplayString
        }

        ap5ServLogSequencer OBJECT-TYPE
               SYNTAX  INTEGER
               ACCESS  read-only
               STATUS  mandatory
               DESCRIPTION
               "Table sequencer"
               ::=  {  ap5ServLogEntry 1   }

        ap5ServLogDateTime OBJECT-TYPE
               SYNTAX  DisplayString
               ACCESS  read-only
               STATUS  mandatory
               DESCRIPTION
               "Log entry data and time"
               ::=  {  ap5ServLogEntry 2   }

        ap5ServLogMsgType OBJECT-TYPE
               SYNTAX  DisplayString
               ACCESS  read-only
               STATUS  mandatory
               DESCRIPTION
               "Log message type"
               ::=  {  ap5ServLogEntry 3   }

        ap5ServLogMsgText OBJECT-TYPE
               SYNTAX  DisplayString
               ACCESS  read-only
               STATUS  mandatory
               DESCRIPTION
               "Log message text."
               ::=  {  ap5ServLogEntry 4   }

--******************************************************************************
--* ap5WCGroup - WebCrawler Group                                               *
--******************************************************************************

        ap5WCSummaryStatus OBJECT-TYPE
                SYNTAX  INTEGER
                {
                    normal(1),
                    warning(2),
                    critical(3)
                }
                ACCESS  read-only
                STATUS  mandatory
                DESCRIPTION
                "Summary status for WebCrawler group."
                ::=  {  ap5WCGroup 1  }

        ap5WCTableEntries OBJECT-TYPE
               SYNTAX  INTEGER
               ACCESS  read-only
               STATUS  mandatory
               DESCRIPTION
               "The number of entries in the table."
               ::=  {  ap5WCGroup 2   }

        ap5WCMaxTableEntries OBJECT-TYPE
               SYNTAX  INTEGER
               ACCESS  read-write
               STATUS  mandatory
               DESCRIPTION
               "The maximum number of table entries allowed."
               ::=  {  ap5WCGroup 3   }

        ap5WCClearTrigger OBJECT-TYPE
               SYNTAX  INTEGER {
                                Execute(1)
                               }
               ACCESS  read-write
               STATUS  mandatory
               DESCRIPTION
               "Clear the data and trigger the WebCrawler."
               ::=  {  ap5WCGroup 4   }

        ap5WCTaskStatus OBJECT-TYPE
               SYNTAX  INTEGER {
                                inactive(1),
                                executing(2),
                                internalerror(3)
                               }
               ACCESS  read-only
               STATUS  mandatory
               DESCRIPTION
               "Current status of the Web crawler process."
               ::=  {  ap5WCGroup 5   }

        ap5WCLastRanTS OBJECT-TYPE
               SYNTAX  DisplayString
               ACCESS  read-only
               STATUS  mandatory
               DESCRIPTION
               "Time WebCrawler was last run."
               ::=  {  ap5WCGroup 6   }

        ap5WCInterval OBJECT-TYPE
               SYNTAX  INTEGER
               ACCESS  read-write
               STATUS  mandatory
               DESCRIPTION
               "Interval between executions of the Web Crawler process."
               ::=  {  ap5WCGroup 7  }

        ap5WCIntervalType OBJECT-TYPE
               SYNTAX  INTEGER {
                                hours(1),
                                days(2),
                                weeks(3)
                               }
               ACCESS  read-write
               STATUS  mandatory
               DESCRIPTION
               "Type of interval to be used in WCInterval."
               ::=  {  ap5WCGroup 8   }

        ap5WCStartTS OBJECT-TYPE
               SYNTAX  DisplayString
               ACCESS  read-write
               STATUS  mandatory
               DESCRIPTION
               "Time to start WebCrawler."
               ::=  {  ap5WCGroup 9   }

        ap5WCNewPageDays OBJECT-TYPE
               SYNTAX  INTEGER
               ACCESS  read-write
               STATUS  mandatory
               DESCRIPTION
               "Days previous to current that will be used by WebCrawler to determine new pages."
               ::=  {  ap5WCGroup 10   }

        ap5WCSlowSize OBJECT-TYPE
               SYNTAX  INTEGER
               ACCESS  read-write
               STATUS  mandatory
               DESCRIPTION
               "Size in bytes that will be used by WebCrawler to determine slow pages."
               ::=  {  ap5WCGroup 11  }

        ap5WCStartURL OBJECT-TYPE
               SYNTAX  DisplayString
               ACCESS  read-write
               STATUS  mandatory
               DESCRIPTION
               "First URL to start parsing with WebCrawler."
               ::=  {  ap5WCGroup 12   }

        ap5WCExecTime OBJECT-TYPE
               SYNTAX  DisplayString
               ACCESS  read-only
               STATUS  mandatory
               DESCRIPTION
               "WebCrawler elapsed execution time(mm:ss)."
               ::=  {  ap5WCGroup 13  }

        ap5WCReport OBJECT-TYPE
               SYNTAX  DisplayString
               ACCESS  read-write
               STATUS  mandatory
               DESCRIPTION
               "Web Crawler process report file path and name."
               ::=  {  ap5WCGroup 14   }

        ap5WCCheckExternal OBJECT-TYPE
               SYNTAX  INTEGER{
                               yes(1),
                               no(2)
                              }
               ACCESS  read-write
               STATUS  mandatory
               DESCRIPTION
               "Check external links in pages."
               ::=  {  ap5WCGroup 15  }

        ap5WCInvalidPages OBJECT-TYPE
               SYNTAX  INTEGER
               ACCESS  read-only
               STATUS  mandatory
               DESCRIPTION
               "Count of invalid pages based verify attributes."
               ::=  {  ap5WCGroup 16  }

        ap5WCIntWarningThreshold OBJECT-TYPE
               SYNTAX  INTEGER
               ACCESS  read-write
               STATUS  mandatory
               DESCRIPTION
               "WCIntStatus is Warning when WCInvalidPages exceeds this value."
               ::=  {  ap5WCGroup 17  }

        ap5WCIntCriticalThreshold OBJECT-TYPE
               SYNTAX  INTEGER
               ACCESS  read-write
               STATUS  mandatory
               DESCRIPTION
               "WCIntStatus is Critical when WCInvalidPages exceeds this value."
               ::=  {  ap5WCGroup 18  }

        ap5WCWarningAction OBJECT-TYPE
               SYNTAX  DisplayString
               ACCESS  read-write
               STATUS  mandatory
               DESCRIPTION
               "Command to be executed when WCSummaryStatus increases to Warning."
               ::=  {  ap5WCGroup 19  }

        ap5WCCriticalAction OBJECT-TYPE
               SYNTAX  DisplayString
               ACCESS  read-write
               STATUS  mandatory
               DESCRIPTION
               "Command to be executed when WCSummaryStatus increases to Critical."
               ::=  {  ap5WCGroup 20   }

        ap5WCVerifyIntLink OBJECT-TYPE
               SYNTAX  INTEGER{
                               yes(1),
                               no(2)
                              }
               ACCESS  read-write
               STATUS  mandatory
               DESCRIPTION
               "Verify internal links for page status."
               ::=  {  ap5WCGroup 21   }

        ap5WCVerifyExtLink OBJECT-TYPE
               SYNTAX  INTEGER{
                               yes(1),
                               no(2)
                              }
               ACCESS  read-write
               STATUS  mandatory
               DESCRIPTION
               "Verify external links for page status."
               ::=  {  ap5WCGroup 22   }

        ap5WCVerifyTitle OBJECT-TYPE
               SYNTAX  INTEGER{
                               yes(1),
                               no(2)
                              }
               ACCESS  read-write
               STATUS  mandatory
               DESCRIPTION
               "Verify title for page status."
               ::=  {  ap5WCGroup 23   }

        ap5WCVerifyAnchors OBJECT-TYPE
               SYNTAX  INTEGER{
                               yes(1),
                               no(2)
                              }
               ACCESS  read-write
               STATUS  mandatory
               DESCRIPTION
               "Verify anchors for page status."
               ::=  {  ap5WCGroup 24   }

        ap5WCVerifyImages OBJECT-TYPE
               SYNTAX  INTEGER{
                               yes(1),
                               no(2)
                              }
               ACCESS  read-write
               STATUS  mandatory
               DESCRIPTION
               "Verify images for page status."
               ::=  {  ap5WCGroup 25   }

        ap5WCPageCount OBJECT-TYPE
               SYNTAX  INTEGER
               ACCESS  read-only
               STATUS  mandatory
               DESCRIPTION
               "Count of pages."
               ::=  {  ap5WCGroup 26  }

        ap5WCNewPageCount OBJECT-TYPE
               SYNTAX  INTEGER
               ACCESS  read-only
               STATUS  mandatory
               DESCRIPTION
               "Count of new pages."
               ::=  {  ap5WCGroup 27  }

        ap5WCSlowPageCount OBJECT-TYPE
               SYNTAX  INTEGER
               ACCESS  read-only
               STATUS  mandatory
               DESCRIPTION
               "Count of slow pages."
               ::=  {  ap5WCGroup 28  }

        ap5WCImageCount OBJECT-TYPE
               SYNTAX  INTEGER
               ACCESS  read-only
               STATUS  mandatory
               DESCRIPTION
               "Count of images."
               ::=  {  ap5WCGroup 29  }

        ap5WCImageRefCount OBJECT-TYPE
               SYNTAX  INTEGER
               ACCESS  read-only
               STATUS  mandatory
               DESCRIPTION
               "Count of image references."
               ::=  {  ap5WCGroup 30  }

        ap5WCMissingImageCount OBJECT-TYPE
               SYNTAX  INTEGER
               ACCESS  read-only
               STATUS  mandatory
               DESCRIPTION
               "Count of missing images."
               ::=  {  ap5WCGroup 31  }

        ap5WCMissingImageRefCount OBJECT-TYPE
               SYNTAX  INTEGER
               ACCESS  read-only
               STATUS  mandatory
               DESCRIPTION
               "Count of missing image references."
               ::=  {  ap5WCGroup 32  }

        ap5WCNamedAnchorCount OBJECT-TYPE
               SYNTAX  INTEGER
               ACCESS  read-only
               STATUS  mandatory
               DESCRIPTION
               "Count of named anchors."
               ::=  {  ap5WCGroup 33  }

        ap5WCNamedAnchorRefCount OBJECT-TYPE
               SYNTAX  INTEGER
               ACCESS  read-only
               STATUS  mandatory
               DESCRIPTION
               "Count of named anchor references."
               ::=  {  ap5WCGroup 34  }

        ap5WCMissingNamedAnchorCount OBJECT-TYPE
               SYNTAX  INTEGER
               ACCESS  read-only
               STATUS  mandatory
               DESCRIPTION
               "Count of missing named anchors."
               ::=  {  ap5WCGroup 35  }

        ap5WCMissingNamedAnchorRefCount OBJECT-TYPE
               SYNTAX  INTEGER
               ACCESS  read-only
               STATUS  mandatory
               DESCRIPTION
               "Count of missing named anchor references."
               ::=  {  ap5WCGroup 36  }

        ap5WCHTTPCount OBJECT-TYPE
               SYNTAX  INTEGER
               ACCESS  read-only
               STATUS  mandatory
               DESCRIPTION
               "Count of HTTP URLs."
               ::=  {  ap5WCGroup 37  }

        ap5WCFTPCount OBJECT-TYPE
               SYNTAX  INTEGER
               ACCESS  read-only
               STATUS  mandatory
               DESCRIPTION
               "Count of FTP URLs."
               ::=  {  ap5WCGroup 38  }

        ap5WCMAILCount OBJECT-TYPE
               SYNTAX  INTEGER
               ACCESS  read-only
               STATUS  mandatory
               DESCRIPTION
               "Count of MAIL URLs."
               ::=  {  ap5WCGroup 39  }

        ap5WCNEWSCount OBJECT-TYPE
               SYNTAX  INTEGER
               ACCESS  read-only
               STATUS  mandatory
               DESCRIPTION
               "Count of NEWS URLs."
               ::=  {  ap5WCGroup 40  }

        ap5WCGOPHERCount OBJECT-TYPE
               SYNTAX  INTEGER
               ACCESS  read-only
               STATUS  mandatory
               DESCRIPTION
               "Count of GOPHER URLs."
               ::=  {  ap5WCGroup 41  }

        ap5WCFILECount OBJECT-TYPE
               SYNTAX  INTEGER
               ACCESS  read-only
               STATUS  mandatory
               DESCRIPTION
               "Count of FILE URLs."
               ::=  {  ap5WCGroup 42  }

        ap5WCThrottle OBJECT-TYPE
               SYNTAX  INTEGER{
                               fast(1),
                               background(2)
                              }
               ACCESS  read-write
               STATUS  mandatory
               DESCRIPTION
               "Control CPU usage."
               ::=  {  ap5WCGroup 43   }

        ap5WCProxy OBJECT-TYPE
               SYNTAX  DisplayString
               ACCESS  read-write
               STATUS  mandatory
               DESCRIPTION
               "Proxy server to use when checking external URLs"
               ::=  {  ap5WCGroup 44  }

        ap5WCReportType OBJECT-TYPE
               SYNTAX  INTEGER{
                               local(1),
                               remote(2)
                              }
               ACCESS  read-write
               STATUS  mandatory
               DESCRIPTION
               "Specify if report is local file or remote browse URL."
               ::=  {  ap5WCGroup 45   }

        ap5WCTimeoutExternal OBJECT-TYPE
               SYNTAX  INTEGER
               ACCESS  read-write
               STATUS  mandatory
               DESCRIPTION
               "Specify time to wait when checking an external URL"
               ::=  {  ap5WCGroup 46   }

        ap5WCOldPageDays OBJECT-TYPE
               SYNTAX  INTEGER
               ACCESS  read-write
               STATUS  mandatory
               DESCRIPTION
               "Days previous to current that will be used by WebCrawler to determine old pages."
               ::=  {  ap5WCGroup 47   }

        ap5WCOldPageCount OBJECT-TYPE
               SYNTAX  INTEGER
               ACCESS  read-only
               STATUS  mandatory
               DESCRIPTION
               "Count of old pages."
               ::=  {  ap5WCGroup 48  }

        ap5WCTable OBJECT-TYPE
               SYNTAX  SEQUENCE OF Ap5WCEntry
               ACCESS  not-accessible
               STATUS  mandatory
               DESCRIPTION
               "This table contains missing URL links found by WebCrawler."
               ::=  {  ap5WCGroup 49  }

        ap5WCReset OBJECT-TYPE
               SYNTAX  INTEGER{
                               reset(1)
                              }
               ACCESS  read-write
               STATUS  mandatory
               DESCRIPTION
               "Count of old pages."
               ::=  { ap5WCGroup 50  }

        ap5WCEntry OBJECT-TYPE
               SYNTAX  Ap5WCEntry
               ACCESS  not-accessible
               STATUS  mandatory
               DESCRIPTION
               "This is an entry in the WCTable"
               INDEX { ap5WCURL }
               ::=  { ap5WCTable 1 }

        Ap5WCEntry ::= SEQUENCE
        {
           ap5WCURL                      DisplayString,
           ap5WCReferences               INTEGER,
           ap5WCBadIntLink               INTEGER,
           ap5WCBadExtLink               INTEGER,
           ap5WCTitle                    INTEGER,
           ap5WCBadAnchors               INTEGER,
           ap5WCBadImages                INTEGER,
           ap5WCAccessTS                 DisplayString
        }

        ap5WCURL OBJECT-TYPE
               SYNTAX  DisplayString
               ACCESS  read-only
               STATUS  mandatory
               DESCRIPTION
               "Bad URL."
               ::=  {  ap5WCEntry 1   }

        ap5WCReferences OBJECT-TYPE
               SYNTAX  INTEGER
               ACCESS  read-only
               STATUS  mandatory
               DESCRIPTION
               "Count of references to this bad URL."
               ::=  {  ap5WCEntry 2   }

        ap5WCBadIntLink OBJECT-TYPE
               SYNTAX  INTEGER
               ACCESS  read-only
               STATUS  mandatory
               DESCRIPTION
               "Count of bad internal Links."
               ::=  {  ap5WCEntry 3   }

        ap5WCBadExtLink OBJECT-TYPE
               SYNTAX  INTEGER
               ACCESS  read-only
               STATUS  mandatory
               DESCRIPTION
               "Count of bad external Links."
               ::=  {  ap5WCEntry 4   }

        ap5WCTitle OBJECT-TYPE
               SYNTAX  INTEGER{
                               ok(1),
                               missing(2)
                              }
               ACCESS  read-only
               STATUS  mandatory
               DESCRIPTION
               "Does page have title."
               ::=  {  ap5WCEntry 5   }

        ap5WCBadAnchors OBJECT-TYPE
               SYNTAX  INTEGER
               ACCESS  read-only
               STATUS  mandatory
               DESCRIPTION
               "Count of bad anchors on page."
               ::=  {  ap5WCEntry 6   }

        ap5WCBadImages OBJECT-TYPE
               SYNTAX  INTEGER
               ACCESS  read-only
               STATUS  mandatory
               DESCRIPTION
               "Count of bad images on page."
               ::=  {  ap5WCEntry 7   }

        ap5WCAccessTS OBJECT-TYPE
               SYNTAX  DisplayString
               ACCESS  read-only
               STATUS  mandatory
               DESCRIPTION
               "Time first access occurred (time row added to table)."
               ::=  {  ap5WCEntry 8   }


--******************************************************************************
--* ap5ExpressionGroup - User defined expressions                               *
--******************************************************************************

        ap5ExpressionTableEntries OBJECT-TYPE
               SYNTAX  INTEGER
               ACCESS  read-only
               STATUS  mandatory
               DESCRIPTION
               "The number of entries in the table."
               ::=  {  ap5ExpressionGroup 1   }

        ap5ExpressionInterval OBJECT-TYPE
               SYNTAX  INTEGER
               ACCESS  read-write
               STATUS  mandatory
               DESCRIPTION
               "Seconds between polls for the counter."
               ::=  {  ap5ExpressionGroup 2   }

        ap5ExpressionCalcInterval OBJECT-TYPE
               SYNTAX  INTEGER
               ACCESS  read-write
               STATUS  mandatory
               DESCRIPTION
               "Interval in seconds over which the counter is measured."
               ::=  {  ap5ExpressionGroup 3   }

--      Update this comment.
--      Add a counter to the table.  The value must include at least the first four of
--      the 6 items listed, separated by commas.
--      <ap5URLAvailCounterDescription> is a value from ap5URLAvailCounterDescription in ap5URLAvailCounterTable.

        ap5ExpressionAdd OBJECT-TYPE
               SYNTAX  DisplayString
               ACCESS  write-only
               STATUS  mandatory
               DESCRIPTION
               "Add this entry to the table."
               ::=  {  ap5ExpressionGroup 4   }

--      Delete a counter from the table.  The value must include the 2 items listed.
        ap5ExpressionDelete OBJECT-TYPE
               SYNTAX  DisplayString
               ACCESS  write-only
               STATUS  mandatory
               DESCRIPTION
               "Delete entry from the table: <ExpressionDesc>,<Expression>."
               ::=  {  ap5ExpressionGroup 5   }

--      For future use with bulk load.  Currently ignored.
        ap5ExpressionUpdate OBJECT-TYPE
               SYNTAX  DisplayString
               ACCESS  write-only
               STATUS  mandatory
               DESCRIPTION
               "Reserved for future use."
               ::=  {  ap5ExpressionGroup 6   }

        ap5ExpressionSummaryStatus OBJECT-TYPE
               SYNTAX  INTEGER {
                                normal(1),
                                warning(2),
                                critical(3)
                               }
               ACCESS  read-only
               STATUS  mandatory
               DESCRIPTION
               "Most severe status of all rows in the table."
               ::=  {  ap5ExpressionGroup 7   }

        ap5ExpressionTable OBJECT-TYPE
               SYNTAX  SEQUENCE OF Ap5ExpressionEntry
               ACCESS  not-accessible
               STATUS  mandatory
               DESCRIPTION
               "This table contains a list of expressions to monitor."
               ::=  {  ap5ExpressionGroup 8}

        ap5ExpressionEntry OBJECT-TYPE
               SYNTAX  Ap5ExpressionEntry
               ACCESS  not-accessible
               STATUS  mandatory
               DESCRIPTION
               "This is an entry in the ExpressionTable"
               INDEX { ap5ExpressionIdentifier}
               ::=  { ap5ExpressionTable 1 }

        Ap5ExpressionEntry ::= SEQUENCE
        {
           ap5Expression                                    DisplayString,
           ap5ExpressionDesc                                DisplayString,
           ap5ExpressionValue                               DisplayString,
           ap5ExpressionWarningThreshold                    INTEGER,
           ap5ExpressionCriticalThreshold                   INTEGER,
           ap5ExpressionWarningAction                       DisplayString,
           ap5ExpressionCriticalAction                      DisplayString,
           ap5ExpressionStatus                              INTEGER,
           ap5ExpressionEnableDisable                       INTEGER,
           ap5ExpressionDescending                          INTEGER,
           ap5ExpressionResultType                          INTEGER,
           ap5ExpressionBooleanAlertLevel                   INTEGER,
           ap5ExpressionEvalErrorAlertLevel                 INTEGER,
           ap5ExpressionNumericMonitor                      INTEGER,
           ap5ExpressionEntryInterval                       INTEGER,
           ap5ExpressionReset                               INTEGER,
           ap5ExpressionResetTime                           DisplayString,
           ap5ExpressionEntryWarningCount                   INTEGER,
           ap5ExpressionEntryCriticalCount                  INTEGER,
           ap5ExpressionIdentifier                          DisplayString,
           ap5ExpressionErrorMsg                            DisplayString,
           ap5ExpressionEvalStatus                          INTEGER,
           ap5ExpressionBoolAlertCondition                  INTEGER,
	   ap5ExpressionLagSetting	                   INTEGER,
	   ap5ExpressionLagValue	                           INTEGER
        }

--     Changed from read only to read write to allow introducing evaluation errors
        ap5Expression OBJECT-TYPE
               SYNTAX  DisplayString
               ACCESS  read-write
               STATUS  mandatory
               DESCRIPTION
               "Expression to be monitored."
               ::=  {  ap5ExpressionEntry 1   }

        ap5ExpressionDesc OBJECT-TYPE
               SYNTAX  DisplayString
               ACCESS  read-write
               STATUS  mandatory
               DESCRIPTION
               "Description of the monitored expression."
               ::=  {  ap5ExpressionEntry 2   }

        ap5ExpressionValue OBJECT-TYPE
               SYNTAX  DisplayString
               ACCESS  read-only
               STATUS  mandatory
               DESCRIPTION
               "Expression evaluation."
               ::=  {  ap5ExpressionEntry 3   }

        ap5ExpressionWarningThreshold OBJECT-TYPE
               SYNTAX  INTEGER
               ACCESS  read-write
               STATUS  mandatory
               DESCRIPTION
               "Warning threshold"
               ::=  {  ap5ExpressionEntry 4   }

        ap5ExpressionCriticalThreshold OBJECT-TYPE
               SYNTAX  INTEGER
               ACCESS  read-write
               STATUS  mandatory
               DESCRIPTION
               "Critical threshold"
               ::=  {  ap5ExpressionEntry 5   }

        ap5ExpressionWarningAction OBJECT-TYPE
               SYNTAX  DisplayString
               ACCESS  read-write
               STATUS  mandatory
               DESCRIPTION
               "Command to be executed when warning threshold is exceeded."
               ::=  {  ap5ExpressionEntry 6   }

        ap5ExpressionCriticalAction OBJECT-TYPE
               SYNTAX  DisplayString
               ACCESS  read-write
               STATUS  mandatory
               DESCRIPTION
               "Command to be executed when critical threshold is exceeded."
               ::=  {  ap5ExpressionEntry 7  }

        ap5ExpressionStatus OBJECT-TYPE
               SYNTAX  INTEGER {
                                normal(1),
                                warning(2),
                                critical(3)
                               }
               ACCESS  read-only
               STATUS  mandatory
               DESCRIPTION
               "Status of this expression."
               ::=  {  ap5ExpressionEntry 8 }

        ap5ExpressionEnableDisable OBJECT-TYPE
                SYNTAX  INTEGER
                {
                    enable(1),
                    disable(2)
                }
                ACCESS  read-write
                STATUS  mandatory
                DESCRIPTION
                "Enable or disable alerts for this expression."
                ::=  {  ap5ExpressionEntry 9   }

        ap5ExpressionDescending OBJECT-TYPE
               SYNTAX  INTEGER {
                                no(1),
                                yes(2)
                               }
               ACCESS  read-only
               STATUS  mandatory
               DESCRIPTION
               "Yes if lower value triggers thresholds."
               ::=  {  ap5ExpressionEntry 10 }


        ap5ExpressionResultType OBJECT-TYPE
               SYNTAX  INTEGER {
                                numeric(1),
                                boolean(2)
                               }
               ACCESS  read-only
               STATUS  mandatory
               DESCRIPTION
               "Result type of expression."
               ::=  {  ap5ExpressionEntry 11 }

        ap5ExpressionBooleanAlertLevel OBJECT-TYPE
                SYNTAX INTEGER {
                                warning-on-false(1),
                                critical-on-false(2)
                               }
                ACCESS read-write
                STATUS mandatory
                DESCRIPTION
                "Flag indicating for boolean expressions the level of alert to raise on false."
                DEFVAL { 2 }
                ::= { ap5ExpressionEntry 12 }

        ap5ExpressionEvalErrorAlertLevel OBJECT-TYPE
                SYNTAX INTEGER {
                                do-not-monitor(1),
                                warning-on-error(2),
                                critical-on-error(3)
                               }
                ACCESS read-write
                STATUS mandatory
                DESCRIPTION
                "Flag indicating the level of alert to raise on an evaluation error."
                DEFVAL { 3 }
                ::= { ap5ExpressionEntry 13 }

        ap5ExpressionNumericMonitor OBJECT-TYPE
                SYNTAX INTEGER {
                                warning-only(1),
                                critical-only(2),
                                both(3)
                               }
                ACCESS read-write
                STATUS mandatory
                DESCRIPTION
                "Flag indicating for numeric expressions which thresholds should be evaluated."
                DEFVAL { 3 }
                ::= { ap5ExpressionEntry 14 }

        ap5ExpressionEntryInterval OBJECT-TYPE
               SYNTAX  INTEGER
               ACCESS  read-write
               STATUS  mandatory
               DESCRIPTION
               "Evaluation interval for expression"
               ::=  {  ap5ExpressionEntry 15   }

        ap5ExpressionReset OBJECT-TYPE
               SYNTAX  INTEGER {
                                reset(1)
                               }
               ACCESS  write-only
               STATUS  mandatory
               DESCRIPTION
               "Reset value for this counter."
               ::=  {  ap5ExpressionEntry 16 }

        ap5ExpressionResetTime OBJECT-TYPE
               SYNTAX  DisplayString
               ACCESS  read-only
               STATUS  mandatory
               DESCRIPTION
               "Time stamp of when this counter was reset."
               ::=  {  ap5ExpressionEntry 17  }

        ap5ExpressionEntryWarningCount OBJECT-TYPE
                SYNTAX  INTEGER
                ACCESS  read-only
                STATUS  mandatory
                DESCRIPTION
                "Number of warning events since last reset."
                ::=  {  ap5ExpressionEntry 18   }

        ap5ExpressionEntryCriticalCount OBJECT-TYPE
                SYNTAX  INTEGER
                ACCESS  read-only
                STATUS  mandatory
                DESCRIPTION
                "Number of critical events since last reset."
                ::=  {  ap5ExpressionEntry 19   }

        ap5ExpressionIdentifier OBJECT-TYPE
               SYNTAX  DisplayString
               ACCESS  read-write
               STATUS  mandatory
               DESCRIPTION
               "Short identifier of the monitored expression."
               ::=  {  ap5ExpressionEntry 20   }

        ap5ExpressionErrorMsg OBJECT-TYPE
               SYNTAX  DisplayString
               ACCESS  read-write
               STATUS  mandatory
               DESCRIPTION
               "Validation or evaluation error message."
               ::=  {  ap5ExpressionEntry 21   }

        ap5ExpressionEvalStatus OBJECT-TYPE
               SYNTAX  INTEGER {
                                normal(1),
                                error(2)
                               }
               ACCESS  read-only
               STATUS  mandatory
               DESCRIPTION
               "Was this expression able to be evaluated."
               ::=  {  ap5ExpressionEntry 22 }

        ap5ExpressionBoolAlertCondition OBJECT-TYPE
               SYNTAX  INTEGER {
                                alertonfalse(1),
                                alertontrue(2)
                               }
               ACCESS  read-write
               STATUS  mandatory
               DESCRIPTION
               "Alert on true or alert on false."
               ::=  {  ap5ExpressionEntry 23 }
		
        ap5ExpressionLagSetting OBJECT-TYPE
                SYNTAX  INTEGER
                ACCESS  read-write
                STATUS  mandatory
                DESCRIPTION
                "Lag setting for the expression."
                ::=  {  ap5ExpressionEntry 24   }
		
        ap5ExpressionLagValue OBJECT-TYPE
                SYNTAX  INTEGER
                ACCESS  read-only
                STATUS  mandatory
                DESCRIPTION
                "Current Lag value for the expression."
                ::=  {  ap5ExpressionEntry 25   }

--******************************************************************************
--*  End of expressions table                                                  *
--******************************************************************************

        ap5ExpressionWarningCount OBJECT-TYPE
                SYNTAX  INTEGER
                ACCESS  read-only
                STATUS  mandatory
                DESCRIPTION
                "Number of expressions in warning state."
                DEFVAL { 0 }
                ::=  {  ap5ExpressionGroup 9   }

        ap5ExpressionCriticalCount OBJECT-TYPE
                SYNTAX  INTEGER
                ACCESS  read-only
                STATUS  mandatory
                DESCRIPTION
                "Number of expressions in critical state."
                DEFVAL { 0 }
                ::=  {  ap5ExpressionGroup 10   }

       ap5ExpressionValidate OBJECT-TYPE
               SYNTAX  DisplayString
               ACCESS  write-only
               STATUS  mandatory
               DESCRIPTION
               "Validate this entry."
               ::=  {  ap5ExpressionGroup 11   }

        ap5ExpressionEvaluate OBJECT-TYPE
               SYNTAX  DisplayString
               ACCESS  write-only
               STATUS  mandatory
               DESCRIPTION
               "Evaluate this expression."
               ::=  {  ap5ExpressionGroup 12   }

        ap5ExpressionTemp OBJECT-TYPE
               SYNTAX  DisplayString
               ACCESS  read-write
               STATUS  mandatory
               DESCRIPTION
               "Temporary storage for expression building."
               ::=  {  ap5ExpressionGroup 13   }

        ap5ExpressionVariableTable OBJECT-TYPE
               SYNTAX  SEQUENCE OF Ap5ExpressionVariableEntry
               ACCESS  not-accessible
               STATUS  mandatory
               DESCRIPTION
               "This table contains a list of expressions to monitor."
               ::=  {  ap5ExpressionGroup 14}

        ap5ExpressionVariableEntry OBJECT-TYPE
               SYNTAX  Ap5ExpressionVariableEntry
               ACCESS  not-accessible
               STATUS  mandatory
               DESCRIPTION
               "This is an entry in the ExpressionVariableTable"
               INDEX { ap5ExpressionVariableDisplayName}
               ::=  { ap5ExpressionVariableTable 1 }

        Ap5ExpressionVariableEntry ::= SEQUENCE
        {
           ap5ExpressionVariableDisplayName        DisplayString,
           ap5ExpressionVariableAccessName         DisplayString,
           ap5ExpressionVariableGroup              DisplayString
        }

       ap5ExpressionVariableDisplayName OBJECT-TYPE
               SYNTAX  DisplayString
               ACCESS  read-only
               STATUS  mandatory
               DESCRIPTION
               "Expression variable displayed in list."
               ::=  {  ap5ExpressionVariableEntry 1   }

       ap5ExpressionVariableAccessName OBJECT-TYPE
               SYNTAX  DisplayString
               ACCESS  read-only
               STATUS  mandatory
               DESCRIPTION
               "Expression variable used to access MIB entry."
               ::=  {  ap5ExpressionVariableEntry 2   }

        ap5ExpressionVariableGroup OBJECT-TYPE
               SYNTAX  DisplayString
               ACCESS  read-only
               STATUS  mandatory
               DESCRIPTION
               "MIB group where the variable is stored."
               ::=  {  ap5ExpressionVariableEntry 3   }

--******************************************************************************
--*  End of expression variables table                                         *
--******************************************************************************

       ap5ExpressionVariableTableEntries OBJECT-TYPE
               SYNTAX  INTEGER
               ACCESS  read-only
               STATUS  mandatory
               DESCRIPTION
               "The number of entries in the variables table."
               ::=  {  ap5ExpressionGroup 15   }

       ap5ExpressionBuild OBJECT-TYPE
               SYNTAX  DisplayString
               ACCESS  write-only
               STATUS  mandatory
               DESCRIPTION
               "Add this variable to the expression."
               ::=  {  ap5ExpressionGroup 16   }

        ap5ExpressionTempValue OBJECT-TYPE
               SYNTAX  DisplayString
               ACCESS  read-write
               STATUS  mandatory
               DESCRIPTION
               "Temporary storage for result of expression validation or evaluation."
               ::=  {  ap5ExpressionGroup 17   }


        ap5ExpressionClear OBJECT-TYPE
               SYNTAX  INTEGER {
                                donotclear(1),
                                clear(2)
                               }
               ACCESS  read-only
               STATUS  mandatory
               DESCRIPTION
               "Clear the variables in the gui"
               ::=  {  ap5ExpressionGroup 18 }

--******************************************************************************
--*  Start of global expression variables table                                *
--******************************************************************************

        ap5ExpressionGlobalVariableTableEntries OBJECT-TYPE
               SYNTAX  INTEGER
               ACCESS  read-only
               STATUS  mandatory
               DESCRIPTION
               "The number of entries in the global variables table."
               ::=  {  ap5ExpressionGroup 19   }

        ap5ExpressionGlobalVariableTableAdd OBJECT-TYPE
               SYNTAX  DisplayString
               ACCESS  write-only
               STATUS  mandatory
               DESCRIPTION
               "Add this entry to the global variables table."
               ::=  {  ap5ExpressionGroup 20   }

--      Delete a counter from the table.  The value must include the 2 items listed.
        ap5ExpressionGlobalVariableTableDelete OBJECT-TYPE
               SYNTAX  DisplayString
               ACCESS  write-only
               STATUS  mandatory
               DESCRIPTION
               "Delete entry from the global varialbles table."
               ::=  {  ap5ExpressionGroup 21   }

        ap5ExpressionGlobalVariableTable OBJECT-TYPE
               SYNTAX  SEQUENCE OF Ap5ExpressionGlobalVariableEntry
               ACCESS  not-accessible
               STATUS  mandatory
               DESCRIPTION
               "This table contains a list of global variables used in expressions."
               ::=  {  ap5ExpressionGroup 22}

        ap5ExpressionGlobalVariableEntry OBJECT-TYPE
               SYNTAX  Ap5ExpressionGlobalVariableEntry
               ACCESS  not-accessible
               STATUS  mandatory
               DESCRIPTION
               "This is an entry in the ExpressionGlobalVariableTable"
               INDEX { ap5ExpressionGlobalVariableName}
               ::=  { ap5ExpressionGlobalVariableTable 1 }

        Ap5ExpressionGlobalVariableEntry ::= SEQUENCE
        {
           ap5ExpressionGlobalVariableName                DisplayString,
           ap5ExpressionGlobalVariableDisplayName         DisplayString,
           ap5ExpressionGlobalVariableDescription         DisplayString,
           ap5ExpressionGlobalVariableAccessKey           DisplayString,
           ap5ExpressionGlobalVariableType                DisplayString,
           ap5ExpressionGlobalVariablePollIntervalPeriod  INTEGER,
           ap5ExpressionGlobalVariableFunctionName        DisplayString,
           ap5ExpressionGlobalVariableFunctionTimePeriod  INTEGER
        }

        ap5ExpressionGlobalVariableName OBJECT-TYPE
               SYNTAX  DisplayString
               ACCESS  read-only
               STATUS  mandatory
               DESCRIPTION
               "Expression global variable name."
               ::=  {  ap5ExpressionGlobalVariableEntry 1   }

        ap5ExpressionGlobalVariableDisplayName OBJECT-TYPE
               SYNTAX  DisplayString
               ACCESS  read-only
               STATUS  mandatory
               DESCRIPTION
               "Expression global variable display name."
               ::=  {  ap5ExpressionGlobalVariableEntry 2   }

        ap5ExpressionGlobalVariableDescription OBJECT-TYPE
               SYNTAX  DisplayString
               ACCESS  read-only
               STATUS  mandatory
               DESCRIPTION
               "Expression global variable description."
               ::=  {  ap5ExpressionGlobalVariableEntry 3   }

        ap5ExpressionGlobalVariableAccessKey OBJECT-TYPE
               SYNTAX  DisplayString
               ACCESS  read-only
               STATUS  mandatory
               DESCRIPTION
               "Expression global variable key to access counter."
               ::=  {  ap5ExpressionGlobalVariableEntry 4   }

        ap5ExpressionGlobalVariableType OBJECT-TYPE
               SYNTAX  DisplayString
               ACCESS  read-only
               STATUS  mandatory
               DESCRIPTION
               "Expression global variable - interval or time variable."
               ::=  {  ap5ExpressionGlobalVariableEntry 5   }

        ap5ExpressionGlobalVariablePollIntervalPeriod OBJECT-TYPE
               SYNTAX  INTEGER
               ACCESS  read-only
               STATUS  mandatory
               DESCRIPTION
               "Expression global variable poll interval for interval type."
               ::=  {  ap5ExpressionGlobalVariableEntry 6   }

        ap5ExpressionGlobalVariableFunctionName OBJECT-TYPE
               SYNTAX  DisplayString
               ACCESS  read-only
               STATUS  mandatory
               DESCRIPTION
               "Expression global variable function name."
               ::=  {  ap5ExpressionGlobalVariableEntry 7   }

        ap5ExpressionGlobalVariableFunctionTimePeriod OBJECT-TYPE
               SYNTAX  INTEGER
               ACCESS  read-only
               STATUS  mandatory
               DESCRIPTION
               "Expression global variable function time period."
               ::=  {  ap5ExpressionGlobalVariableEntry 8   }

--******************************************************************************
--*  End of global expression variables table                                  *
--******************************************************************************

       ap5ExpressionGlobalVariableBuild OBJECT-TYPE
               SYNTAX  DisplayString
               ACCESS  write-only
               STATUS  mandatory
               DESCRIPTION
               "Add an access key to the variable using a friendly name."
               ::=  {  ap5ExpressionGroup 23   }

        ap5ExpressionGlobalVariableClear OBJECT-TYPE
               SYNTAX  INTEGER {
                                donotclear(1),
                                clear(2)
                               }
               ACCESS  read-only
               STATUS  mandatory
               DESCRIPTION
               "Clear the variables in the gui"
               ::=  {  ap5ExpressionGroup 24 }

        ap5ExpressionGlobalVariableTemp OBJECT-TYPE
               SYNTAX  DisplayString
               ACCESS  read-write
               STATUS  mandatory
               DESCRIPTION
               "Temporary storage for variable access key."
               ::=  {  ap5ExpressionGroup 25   }

        ap5ExpressionGlobalVariableTableModify OBJECT-TYPE
               SYNTAX  DisplayString
               ACCESS  write-only
               STATUS  mandatory
               DESCRIPTION
               "Modify entry in the global varialbles table."
               ::=  {  ap5ExpressionGroup 26   }

	ap5ExpressionGPEnaDis OBJECT-TYPE
		SYNTAX      INTEGER {enable(1), disable(2)}
		ACCESS      read-write
		STATUS      mandatory
		DESCRIPTION "Enable or disable for the Group."
		::= { ap5ExpressionGroup 27 }


--******************************************************************************
--* ap5DetailGroup - Detail table                                              *
--******************************************************************************

        ap5DetailTableEntries OBJECT-TYPE
                SYNTAX  INTEGER
                ACCESS  read-only
                STATUS  mandatory
                DESCRIPTION
                "The number of entries in the table."
                ::=  {  ap5DetailGroup 1   }

        ap5DetailRequest OBJECT-TYPE
                SYNTAX  DisplayString
                ACCESS  write-only
                STATUS  mandatory
                DESCRIPTION
                "Generate Detail table for this request."
                ::=  {  ap5DetailGroup 2   }


        ap5DetailTable OBJECT-TYPE
                SYNTAX  SEQUENCE OF Ap5DetailEntry
                ACCESS  not-accessible
                STATUS  mandatory
                DESCRIPTION
                "The list of details."
                ::=  {  ap5DetailGroup 3}

        ap5DetailEntry OBJECT-TYPE
                 SYNTAX  Ap5DetailEntry
                 ACCESS  not-accessible
                 STATUS  mandatory
                 DESCRIPTION
                 "The DetailTable entry."
                 INDEX { ap5DetailServer }
                     ::=  { ap5DetailTable 1 }

        Ap5DetailEntry ::= SEQUENCE {
            ap5DetailServer              DisplayString,
            ap5DetailValue               DisplayString,
            ap5DetailValue2              DisplayString,
            ap5DetailValue3              DisplayString,
            ap5DetailValue4              DisplayString,
            ap5DetailValue5              DisplayString,
            ap5DetailValue6              DisplayString,
            ap5DetailValue7              DisplayString,
            ap5DetailValue8              DisplayString,
            ap5DetailValue9              DisplayString,
            ap5DetailValue10             DisplayString
        }

        ap5DetailServer OBJECT-TYPE
                SYNTAX  DisplayString
                ACCESS  read-only
                STATUS  mandatory
                DESCRIPTION
                "The Server name for the entry."
                ::=  {  ap5DetailEntry 1   }

        ap5DetailValue OBJECT-TYPE
                SYNTAX  DisplayString
                ACCESS  read-only
                STATUS  mandatory
                DESCRIPTION
                "Detail value for the server."
                ::=  {  ap5DetailEntry 2   }

        ap5DetailValue2 OBJECT-TYPE
                SYNTAX  DisplayString
                ACCESS  read-only
                STATUS  mandatory
                DESCRIPTION
                "Detail value for the server."
                ::=  {  ap5DetailEntry 3   }

        ap5DetailValue3 OBJECT-TYPE
                SYNTAX  DisplayString
                ACCESS  read-only
                STATUS  mandatory
                DESCRIPTION
                "Detail value for the server."
                ::=  {  ap5DetailEntry 4   }

        ap5DetailValue4 OBJECT-TYPE
                SYNTAX  DisplayString
                ACCESS  read-only
                STATUS  mandatory
                DESCRIPTION
                "Detail value for the server."
                ::=  {  ap5DetailEntry 5   }

        ap5DetailValue5 OBJECT-TYPE
                SYNTAX  DisplayString
                ACCESS  read-only
                STATUS  mandatory
                DESCRIPTION
                "Detail value for the server."
                ::=  {  ap5DetailEntry 6   }

        ap5DetailValue6 OBJECT-TYPE
                SYNTAX  DisplayString
                ACCESS  read-only
                STATUS  mandatory
                DESCRIPTION
                "Detail value for the server."
                ::=  {  ap5DetailEntry 7   }

        ap5DetailValue7 OBJECT-TYPE
                SYNTAX  DisplayString
                ACCESS  read-only
                STATUS  mandatory
                DESCRIPTION
                "Detail value for the server."
                ::=  {  ap5DetailEntry 8   }

        ap5DetailValue8 OBJECT-TYPE
                SYNTAX  DisplayString
                ACCESS  read-only
                STATUS  mandatory
                DESCRIPTION
                "Detail value for the server."
                ::=  {  ap5DetailEntry 9   }

        ap5DetailValue9 OBJECT-TYPE
                SYNTAX  DisplayString
                ACCESS  read-only
                STATUS  mandatory
                DESCRIPTION
                "Detail value for the server."
                ::=  {  ap5DetailEntry 10   }

        ap5DetailValue10 OBJECT-TYPE
                SYNTAX  DisplayString
                ACCESS  read-only
                STATUS  mandatory
                DESCRIPTION
                "Detail value for the server."
                ::=  {  ap5DetailEntry 11   }

        ap5DetailHeading OBJECT-TYPE
                SYNTAX  DisplayString
                ACCESS  read-only
                STATUS  mandatory
                DESCRIPTION
                "The heading for the table."
                ::=  {  ap5DetailGroup 4   }




--******************************************************************************
--* ap5VHGroup - Virtual Hosts Group                                            *
--******************************************************************************


        ap5VHTableEntries OBJECT-TYPE
                SYNTAX  INTEGER
                ACCESS  read-only
                STATUS  mandatory
                DESCRIPTION
                "The number of entries in the VH table."
                ::=  {  ap5VHGroup 1   }

        ap5VHRequest OBJECT-TYPE
                SYNTAX  DisplayString
                ACCESS  read-write
                STATUS  mandatory
                DESCRIPTION
                "VH request description."
                ::=  {  ap5VHGroup 2   }

--*     List Section

        ap5VHTable OBJECT-TYPE
                SYNTAX  SEQUENCE OF Ap5VHEntry
                ACCESS  not-accessible
                STATUS  mandatory
                DESCRIPTION
                "The list of details."
                ::=  {  ap5VHGroup 3}

        ap5VHEntry OBJECT-TYPE
                 SYNTAX  Ap5VHEntry
                 ACCESS  not-accessible
                 STATUS  mandatory
                 DESCRIPTION
                 "The VHTable entry."
                 INDEX { ap5VHID }
                     ::=  { ap5VHTable 1 }

        Ap5VHEntry ::= SEQUENCE {
            ap5VHID                  INTEGER,
            ap5VHServer              DisplayString,
            ap5VHValue               DisplayString,
            ap5VHValue2              DisplayString,
            ap5VHValue3              DisplayString,
            ap5VHValue4              DisplayString,
            ap5VHValue5              DisplayString,
            ap5VHValue6              DisplayString,
            ap5VHValue7              DisplayString,
            ap5VHValue8              DisplayString,
            ap5VHValue9              DisplayString,
            ap5VHValue10             DisplayString
        }

	ap5VHID OBJECT-TYPE
		SYNTAX      INTEGER
		ACCESS      read-only
		STATUS      mandatory
		DESCRIPTION "A unique ID."
		::= {ap5VHEntry 1}
      
        ap5VHServer OBJECT-TYPE
                SYNTAX  DisplayString
                ACCESS  read-only
                STATUS  mandatory
                DESCRIPTION
                "The Server name for the entry."
                ::=  {  ap5VHEntry 2   }

        ap5VHValue OBJECT-TYPE
                SYNTAX  DisplayString
                ACCESS  read-only
                STATUS  mandatory
                DESCRIPTION
                "VH value for the server."
                ::=  {  ap5VHEntry 3   }

        ap5VHValue2 OBJECT-TYPE
                SYNTAX  DisplayString
                ACCESS  read-only
                STATUS  mandatory
                DESCRIPTION
                "VH value for the server."
                ::=  {  ap5VHEntry 4   }

        ap5VHValue3 OBJECT-TYPE
                SYNTAX  DisplayString
                ACCESS  read-only
                STATUS  mandatory
                DESCRIPTION
                "VH value for the server."
                ::=  {  ap5VHEntry 5   }

        ap5VHValue4 OBJECT-TYPE
                SYNTAX  DisplayString
                ACCESS  read-only
                STATUS  mandatory
                DESCRIPTION
                "VH value for the server."
                ::=  {  ap5VHEntry 6   }

        ap5VHValue5 OBJECT-TYPE
                SYNTAX  DisplayString
                ACCESS  read-only
                STATUS  mandatory
                DESCRIPTION
                "VH value for the server."
                ::=  {  ap5VHEntry 7   }

        ap5VHValue6 OBJECT-TYPE
                SYNTAX  DisplayString
                ACCESS  read-only
                STATUS  mandatory
                DESCRIPTION
                "VH value for the server."
                ::=  {  ap5VHEntry 8   }

        ap5VHValue7 OBJECT-TYPE
                SYNTAX  DisplayString
                ACCESS  read-only
                STATUS  mandatory
                DESCRIPTION
                "VH value for the server."
                ::=  {  ap5VHEntry 9   }

        ap5VHValue8 OBJECT-TYPE
                SYNTAX  DisplayString
                ACCESS  read-only
                STATUS  mandatory
                DESCRIPTION
                "VH value for the server."
                ::=  {  ap5VHEntry 10   }

        ap5VHValue9 OBJECT-TYPE
                SYNTAX  DisplayString
                ACCESS  read-only
                STATUS  mandatory
                DESCRIPTION
                "VH value for the server."
                ::=  {  ap5VHEntry 11   }

        ap5VHValue10 OBJECT-TYPE
                SYNTAX  DisplayString
                ACCESS  read-only
                STATUS  mandatory
                DESCRIPTION
                "VH value for the server."
                ::=  {  ap5VHEntry 12   }


--*     Health section

        ap5VHSHSummaryStatus OBJECT-TYPE
               SYNTAX  INTEGER {
                                normal(1),
                                warning(2),
                                critical(3)
                                }
               ACCESS  read-only
               STATUS  mandatory
               DESCRIPTION
               "Summary status for group."
                ::=  {  ap5VHGroup 4}

        ap5VHSHReqRate OBJECT-TYPE
               SYNTAX  INTEGER
               ACCESS  read-only
               STATUS  mandatory
               DESCRIPTION
               "Requests per second."
                ::=  {  ap5VHGroup 5}

        ap5VHSHReqRateWarningThreshold OBJECT-TYPE
               SYNTAX  INTEGER
               ACCESS  read-write
               STATUS  mandatory
               DESCRIPTION
               "Generate a warning if SHReqRate exceeds this."
                ::=  {  ap5VHGroup 6}

        ap5VHSHReqRateCriticalThreshold OBJECT-TYPE
               SYNTAX  INTEGER
               ACCESS  read-write
               STATUS  mandatory
               DESCRIPTION
               "Generate a critical if SHReqRate exceeds this."
                ::=  {  ap5VHGroup 7}

        ap5VHSHByteRate OBJECT-TYPE
               SYNTAX  INTEGER
               ACCESS  read-only
               STATUS  mandatory
               DESCRIPTION
               "Kilobytes transferred per second."
                ::=  {  ap5VHGroup 8}

        ap5VHSHByteRateWarningThreshold OBJECT-TYPE
               SYNTAX  INTEGER
               ACCESS  read-write
               STATUS  mandatory
               DESCRIPTION
               "Generate a warning if SHByteRate exceeds this."
                ::=  {  ap5VHGroup 9}

        ap5VHSHByteRateCriticalThreshold OBJECT-TYPE
               SYNTAX  INTEGER
               ACCESS  read-write
               STATUS  mandatory
               DESCRIPTION
               "Generate a critical if SHByteRate exceeds this."
                ::=  {  ap5VHGroup 10}

        ap5VHSHWarningAction OBJECT-TYPE
               SYNTAX  DisplayString
               ACCESS  read-write
               STATUS  mandatory
               DESCRIPTION
               "Command to be executed when any warning threshold is exceeded."
                ::=  {  ap5VHGroup 11}

        ap5VHSHCriticalAction OBJECT-TYPE
               SYNTAX  DisplayString
               ACCESS  read-write
               STATUS  mandatory
               DESCRIPTION
               "Command to be executed when any critical threshold is exceeded."
                ::=  {  ap5VHGroup 12}

        ap5VHSHTotalHits OBJECT-TYPE
               SYNTAX  INTEGER
               ACCESS  read-only
               STATUS  mandatory
               DESCRIPTION
               "Totals requests."
                ::=  {  ap5VHGroup 13}

        ap5VHSHTotalErrors OBJECT-TYPE
               SYNTAX  INTEGER
               ACCESS  read-only
               STATUS  mandatory
               DESCRIPTION
               "Totals error requests."
                ::=  {  ap5VHGroup 14}

        ap5VHSHTotalGETS OBJECT-TYPE
               SYNTAX  INTEGER
               ACCESS  read-only
               STATUS  mandatory
               DESCRIPTION
               "Totals GET requests."
                ::=  {  ap5VHGroup 15}

        ap5VHSHTotalPOSTS OBJECT-TYPE
               SYNTAX  INTEGER
               ACCESS  read-only
               STATUS  mandatory
               DESCRIPTION
               "Totals POST requests."
                ::=  {  ap5VHGroup 16}

        ap5VHSHTotalHEADS OBJECT-TYPE
               SYNTAX  INTEGER
               ACCESS  read-only
               STATUS  mandatory
               DESCRIPTION
               "Totals HEAD requests."
                ::=  {  ap5VHGroup 17}

        ap5VHSHTotalCGI OBJECT-TYPE
               SYNTAX  INTEGER
               ACCESS  read-only
               STATUS  mandatory
               DESCRIPTION
               "Totals CGI requests."
                ::=  {  ap5VHGroup 18}

        ap5VHSHMaxReqRate OBJECT-TYPE
               SYNTAX  INTEGER
               ACCESS  read-write
               STATUS  mandatory
               DESCRIPTION
               "Max value for the abrowser max requests scale."
                ::=  {  ap5VHGroup 19}

        ap5VHSHMaxByteRate OBJECT-TYPE
               SYNTAX  INTEGER
               ACCESS  read-write
               STATUS  mandatory
               DESCRIPTION
               "Max value for the abrowser max bytes scale."
                ::=  {  ap5VHGroup 20}
	     
   
--*     Top URL section
 

        ap5VHTopURLCircularBuffSize OBJECT-TYPE
               SYNTAX  INTEGER
               ACCESS  read-write
               STATUS  mandatory
               DESCRIPTION
               "Max entries in the table (default 50)."
               ::=  {  ap5VHGroup 21   }

        ap5VHTopURLExclude OBJECT-TYPE
               SYNTAX  DisplayString
               ACCESS  read-write
               STATUS  mandatory
               DESCRIPTION
               "Exclude URLs with these extensions."
               ::=  {  ap5VHGroup 22   }

        ap5VHTopURLTable OBJECT-TYPE
               SYNTAX  SEQUENCE OF Ap5VHTopURLEntry
               ACCESS  not-accessible
               STATUS  mandatory
               DESCRIPTION
               "This table contains a list of the top URLs by hit count."
               ::=  {  ap5VHGroup 23}

        ap5VHTopURLEntry OBJECT-TYPE
               SYNTAX  Ap5VHTopURLEntry
               ACCESS  not-accessible
               STATUS  mandatory
               DESCRIPTION
               "This is an entry in the VHTopURLTable"
               INDEX { ap5VHTopURLID}
               ::=  { ap5VHTopURLTable 1 }

        Ap5VHTopURLEntry ::= SEQUENCE
        {
           ap5VHTopURLID           INTEGER,
           ap5VHTopURLURL          DisplayString,
           ap5VHTopURLNumHits      INTEGER
        }

	ap5VHTopURLID OBJECT-TYPE
		SYNTAX      INTEGER
		ACCESS      read-only
		STATUS      mandatory
		DESCRIPTION "A unique ID."
		::= {ap5VHTopURLEntry 1}
		
        ap5VHTopURLURL OBJECT-TYPE
               SYNTAX  DisplayString
               ACCESS  read-only
               STATUS  mandatory
               DESCRIPTION
               "URL."
               ::=  {  ap5VHTopURLEntry 2   }

        ap5VHTopURLNumHits OBJECT-TYPE
               SYNTAX  INTEGER
               ACCESS  read-only
               STATUS  mandatory
               DESCRIPTION
               "Number of hits."
               ::=  {  ap5VHTopURLEntry 3   }


        ap5VHTopURLTableEntries OBJECT-TYPE
               SYNTAX  INTEGER
               ACCESS  read-only
               STATUS  mandatory
               DESCRIPTION
               "The number of entries in the table."
               ::=  {  ap5VHGroup 24   }

        ap5VHTopURLClearTable OBJECT-TYPE
               SYNTAX  INTEGER {
                                reset(1)
                               }
               ACCESS  read-write
               STATUS  mandatory
               DESCRIPTION
               "Clear the table when set."
               ::=  {  ap5VHGroup 25   }

        ap5VHTopURLExcludeReset OBJECT-TYPE
               SYNTAX  INTEGER {
                                reset(1)
                               }
               ACCESS  read-write
               STATUS  mandatory
               DESCRIPTION
               "Reset exclude list to defaults."
               ::=  {  ap5VHGroup 26   }
	       

--* BadLink section

        ap5VHBLTableEntries OBJECT-TYPE
                SYNTAX  INTEGER
                ACCESS  read-only
                STATUS  mandatory
                DESCRIPTION
                "The number of entries in the table."
                ::=  {  ap5VHGroup 27   }


        ap5VHBLClearTable OBJECT-TYPE
               SYNTAX  INTEGER {
                                reset(1)
                               }
               ACCESS  read-write
               STATUS  mandatory
               DESCRIPTION
               "Clear the table when set."
               ::=  {  ap5VHGroup 28   }

        ap5VHBLSummaryStatus OBJECT-TYPE
               SYNTAX  INTEGER {
                                normal(1),
                                warning(2),
                                critical(3)
                               }
               ACCESS  read-only
               STATUS  mandatory
               DESCRIPTION
               "Summary status for bad links."
               ::=  {  ap5VHGroup 29   }

        ap5VHBLCircularBuffSize OBJECT-TYPE
               SYNTAX  INTEGER
               ACCESS  read-write
               STATUS  mandatory
               DESCRIPTION
               "Max entries in the table (default 50)(Not a circular buffer)."
               ::=  {  ap5VHGroup 30   }

        ap5VHBLWarningThreshold OBJECT-TYPE
               SYNTAX  INTEGER
               ACCESS  read-write
               STATUS  mandatory
               DESCRIPTION
               "Number of requests on a row before warning is generated."
               ::=  {  ap5VHGroup 31   }

        ap5VHBLCriticalThreshold OBJECT-TYPE
               SYNTAX  INTEGER
               ACCESS  read-write
               STATUS  mandatory
               DESCRIPTION
               "Number of requests on a row before critical is generated."
               ::=  {  ap5VHGroup 32   }

        ap5VHBLWarningCount OBJECT-TYPE
               SYNTAX  INTEGER
               ACCESS  read-only
               STATUS  mandatory
               DESCRIPTION
               "The number of entries in the table with a warning status."
               ::=  {  ap5VHGroup 33   }

        ap5VHBLCriticalCount OBJECT-TYPE
               SYNTAX  INTEGER
               ACCESS  read-only
               STATUS  mandatory
               DESCRIPTION
               "The number of entries in the table with a critical status."
               ::=  {  ap5VHGroup 34   }

        ap5VHBLWarningAction OBJECT-TYPE
               SYNTAX  DisplayString
               ACCESS  read-write
               STATUS  mandatory
               DESCRIPTION
               "Command to be executed when warning threshold is crossed on a row."
               ::=  {  ap5VHGroup 35   }

        ap5VHBLCriticalAction OBJECT-TYPE
               SYNTAX  DisplayString
               ACCESS  read-write
               STATUS  mandatory
               DESCRIPTION
               "Command to be executed when critical threshold is crossed on a row."
               ::=  {  ap5VHGroup 36   }

        ap5VHBLCreateReportURL OBJECT-TYPE
               SYNTAX  INTEGER {
                                Create(1)
                               }
               ACCESS  read-write
               STATUS  mandatory
               DESCRIPTION
               "When triggered, create report using path and file in BLReportURL."
               ::=  {  ap5VHGroup 37   }

        ap5VHBLReportURL OBJECT-TYPE
               SYNTAX  DisplayString
               ACCESS  read-write
               STATUS  mandatory
               DESCRIPTION
               "Path and filename for report; Relative to DocumentRoot unless starts with '/'."
               ::=  {  ap5VHGroup 38   }

        ap5VHBLTable OBJECT-TYPE
               SYNTAX  SEQUENCE OF Ap5VHBLEntry
               ACCESS  not-accessible
               STATUS  mandatory
               DESCRIPTION
               "This table contains a list bad links."
               ::=  {  ap5VHGroup 39  }

        ap5VHBLEntry OBJECT-TYPE
               SYNTAX  Ap5VHBLEntry
               ACCESS  not-accessible
               STATUS  mandatory
               DESCRIPTION
               "This is an entry in the BLTable"
               INDEX { ap5VHBLID }
               ::=  { ap5VHBLTable 1 }

        Ap5VHBLEntry ::= SEQUENCE
        {
	   ap5VHBLID				  INTEGER,
           ap5VHBLURL                              DisplayString,
           ap5VHBLReferringURL                     DisplayString,
           ap5VHBLFirstAccessTS                    DisplayString,
           ap5VHBLlastAccessTS                     DisplayString,
           ap5VHBLNumRequests                      INTEGER,
           ap5VHBLStatus                           INTEGER
        }

	ap5VHBLID OBJECT-TYPE
		SYNTAX      INTEGER
		ACCESS      read-only
		STATUS      mandatory
		DESCRIPTION "A unique ID."
		::= {ap5VHBLEntry 1}
		
        ap5VHBLURL OBJECT-TYPE
               SYNTAX  DisplayString
               ACCESS  read-only
               STATUS  mandatory
               DESCRIPTION
               "Bad URL."
               ::=  {  ap5VHBLEntry 2   }

        ap5VHBLReferringURL OBJECT-TYPE
               SYNTAX  DisplayString
               ACCESS  read-only
               STATUS  mandatory
               DESCRIPTION
               "Referring URL to Bad URL."
               ::=  {  ap5VHBLEntry 3   }

        ap5VHBLFirstAccessTS OBJECT-TYPE
               SYNTAX  DisplayString
               ACCESS  read-only
               STATUS  mandatory
               DESCRIPTION
               "Time first bad access occurred (time row added to table)."
               ::=  {  ap5VHBLEntry 4   }

        ap5VHBLlastAccessTS OBJECT-TYPE
               SYNTAX  DisplayString
               ACCESS  read-only
               STATUS  mandatory
               DESCRIPTION
               "Time of last access to bad URL."
               ::=  {  ap5VHBLEntry 5   }

        ap5VHBLNumRequests OBJECT-TYPE
               SYNTAX  INTEGER
               ACCESS  read-only
               STATUS  mandatory
               DESCRIPTION
               "Count of requests."
               ::=  {  ap5VHBLEntry 6   }

        ap5VHBLStatus OBJECT-TYPE
               SYNTAX  INTEGER {
                                normal(1),
                                warning(2),
                                critical(3)
                               }
               ACCESS  read-only
               STATUS  mandatory
               DESCRIPTION
               "Summary status for BL."
               ::=  {  ap5VHBLEntry 7   }


--* VHost settings table


        ap5VHOPTTable OBJECT-TYPE
               SYNTAX  SEQUENCE OF Ap5VHOPTEntry
               ACCESS  not-accessible
               STATUS  mandatory
               DESCRIPTION
               "This table contains a list of vhost options."
               ::=  {  ap5VHGroup 40  }

        ap5VHOPTEntry OBJECT-TYPE
               SYNTAX  Ap5VHOPTEntry
               ACCESS  not-accessible
               STATUS  mandatory
               DESCRIPTION
               "This is an entry in the BLTable"
               INDEX { ap5VHOPTID }
               ::=  { ap5VHOPTTable 1 }

        Ap5VHOPTEntry ::= SEQUENCE
        {
	   ap5VHOPTID				DisplayString,
           ap5VHOPTSummaryStatus                 INTEGER,
           ap5VHOPTSHSummaryStatus               INTEGER,
           ap5VHOPTBLSummaryStatus               INTEGER,
           ap5VHOPTPUSummaryStatus               INTEGER,
           ap5VHOPTPCSummaryStatus               INTEGER,
           ap5VHOPTSHReqRateWarningThreshold     INTEGER,
           ap5VHOPTSHReqRateCriticalThreshold    INTEGER,
	   ap5VHOPTSHByteRateWarningThreshold	INTEGER,
	   ap5VHOPTSHByteRateCriticalThreshold	INTEGER,
	   ap5VHOPTSHWarningAction		DisplayString,
	   ap5VHOPTSHCriticalAction		DisplayString,
	   ap5VHOPTSHMaxReqRate			INTEGER,
	   ap5VHOPTSHMaxByteRate			INTEGER,
	   ap5VHOPTTopURLCircularBuffSize 	INTEGER,
	   ap5VHOPTTopURLExclude			DisplayString,
	   ap5VHOPTBLCircularBuffSize		INTEGER,
	   ap5VHOPTBLWarningThreshold		INTEGER,
	   ap5VHOPTBLCriticalThreshold		INTEGER,
	   ap5VHOPTBLWarningAction		DisplayString,
	   ap5VHOPTBLCriticalAction		DisplayString,
	   ap5VHOPTBLReportURL			DisplayString,
	   ap5VHOPTBLTableEntries		INTEGER,
	   ap5VHOPTBLWarningCount		INTEGER,
	   ap5VHOPTBLCriticalCount		INTEGER,
	   ap5VHOPTURLMntrTableEntries		INTEGER,
	   ap5VHOPTURLMntrHitRate		INTEGER,
	   ap5VHOPTPolledCounterTableEntries	INTEGER,
           ap5VHOPTIISPCSummaryStatus            INTEGER,
	   ap5VHOPTIISPolledCounterTableEntries	INTEGER,
	   ap5VHOPTSHRSLagSetting		INTEGER,
	   ap5VHOPTSHRSLagValue			INTEGER,
	   ap5VHOPTSHKSLagSetting		INTEGER,
	   ap5VHOPTSHKSLagValue			INTEGER
        }

	ap5VHOPTID OBJECT-TYPE
               SYNTAX  DisplayString
               ACCESS  read-only
               STATUS  mandatory
               DESCRIPTION
               "Vhost name."
               ::=  {  ap5VHOPTEntry 1   }

        ap5VHOPTSummaryStatus OBJECT-TYPE
               SYNTAX  INTEGER {
                                normal(1),
                                warning(2),
                                critical(3)
                               }
               ACCESS  read-only
               STATUS  mandatory
               DESCRIPTION
               "Overall status for Vhost."
               ::=  {  ap5VHOPTEntry 2   }

        ap5VHOPTSHSummaryStatus OBJECT-TYPE
               SYNTAX  INTEGER {
                                normal(1),
                                warning(2),
                                critical(3)
                               }
               ACCESS  read-only
               STATUS  mandatory
               DESCRIPTION
               "Health status for Vhost."
               ::=  {  ap5VHOPTEntry 3   }

        ap5VHOPTBLSummaryStatus OBJECT-TYPE
               SYNTAX  INTEGER {
                                normal(1),
                                warning(2),
                                critical(3)
                               }
               ACCESS  read-only
               STATUS  mandatory
               DESCRIPTION
               "Bad Urls status for Vhost."
               ::=  {  ap5VHOPTEntry 4   }

        ap5VHOPTPUSummaryStatus OBJECT-TYPE
               SYNTAX  INTEGER {
                                normal(1),
                                warning(2),
                                critical(3)
                               }
               ACCESS  read-only
               STATUS  mandatory
               DESCRIPTION
               "Polled URL status for Vhost."
               ::=  {  ap5VHOPTEntry 5   }

        ap5VHOPTPCSummaryStatus OBJECT-TYPE
               SYNTAX  INTEGER {
                                normal(1),
                                warning(2),
                                critical(3)
                               }
               ACCESS  read-only
               STATUS  mandatory
               DESCRIPTION
               "Polled Counter status for Vhost."
               ::=  {  ap5VHOPTEntry 6   }

        ap5VHOPTSHReqRateWarningThreshold OBJECT-TYPE
               SYNTAX  INTEGER
               ACCESS  read-write
               STATUS  mandatory
               DESCRIPTION
               "Generate a warning if SHReqRate exceeds this."
                ::=  {  ap5VHOPTEntry 7}

        ap5VHOPTSHReqRateCriticalThreshold OBJECT-TYPE
               SYNTAX  INTEGER
               ACCESS  read-write
               STATUS  mandatory
               DESCRIPTION
               "Generate a critical if SHReqRate exceeds this."
                ::=  {  ap5VHOPTEntry 8}

        ap5VHOPTSHByteRateWarningThreshold OBJECT-TYPE
               SYNTAX  INTEGER
               ACCESS  read-write
               STATUS  mandatory
               DESCRIPTION
               "Generate a warning if SHByteRate exceeds this."
                ::=  {  ap5VHOPTEntry 9}

        ap5VHOPTSHByteRateCriticalThreshold OBJECT-TYPE
               SYNTAX  INTEGER
               ACCESS  read-write
               STATUS  mandatory
               DESCRIPTION
               "Generate a critical if SHByteRate exceeds this."
                ::=  {  ap5VHOPTEntry 10}

        ap5VHOPTSHWarningAction OBJECT-TYPE
               SYNTAX  DisplayString
               ACCESS  read-write
               STATUS  mandatory
               DESCRIPTION
               "Command to be executed when any warning threshold is exceeded."
                ::=  {  ap5VHOPTEntry 11}

        ap5VHOPTSHCriticalAction OBJECT-TYPE
               SYNTAX  DisplayString
               ACCESS  read-write
               STATUS  mandatory
               DESCRIPTION
               "Command to be executed when any critical threshold is exceeded."
                ::=  {  ap5VHOPTEntry 12}
		
        ap5VHOPTSHMaxReqRate OBJECT-TYPE
               SYNTAX  INTEGER
               ACCESS  read-write
               STATUS  mandatory
               DESCRIPTION
               "Max value for the abrowser max requests scale."
                ::=  {  ap5VHOPTEntry 13}

        ap5VHOPTSHMaxByteRate OBJECT-TYPE
               SYNTAX  INTEGER
               ACCESS  read-write
               STATUS  mandatory
               DESCRIPTION
               "Max value for the abrowser max bytes scale."
                ::=  {  ap5VHOPTEntry 14}
		
        ap5VHOPTTopURLCircularBuffSize OBJECT-TYPE
               SYNTAX  INTEGER
               ACCESS  read-write
               STATUS  mandatory
               DESCRIPTION
               "Max entries in the table (default 50)."
               ::=  {  ap5VHOPTEntry 15   }

        ap5VHOPTTopURLExclude OBJECT-TYPE
               SYNTAX  DisplayString
               ACCESS  read-write
               STATUS  mandatory
               DESCRIPTION
               "Exclude URLs with these extensions."
               ::=  {  ap5VHOPTEntry 16   }
	       
        ap5VHOPTBLCircularBuffSize OBJECT-TYPE
               SYNTAX  INTEGER
               ACCESS  read-write
               STATUS  mandatory
               DESCRIPTION
               "Max entries in the table (default 50)(Not a circular buffer)."
               ::=  {  ap5VHOPTEntry 17   }

        ap5VHOPTBLWarningThreshold OBJECT-TYPE
               SYNTAX  INTEGER
               ACCESS  read-write
               STATUS  mandatory
               DESCRIPTION
               "Number of requests on a row before warning is generated."
               ::=  {  ap5VHOPTEntry 18   }

        ap5VHOPTBLCriticalThreshold OBJECT-TYPE
               SYNTAX  INTEGER
               ACCESS  read-write
               STATUS  mandatory
               DESCRIPTION
               "Number of requests on a row before critical is generated."
               ::=  {  ap5VHOPTEntry 19   }
	       
        ap5VHOPTBLWarningAction OBJECT-TYPE
               SYNTAX  DisplayString
               ACCESS  read-write
               STATUS  mandatory
               DESCRIPTION
               "Command to be executed when warning threshold is crossed on a row."
               ::=  {  ap5VHOPTEntry 20   }

        ap5VHOPTBLCriticalAction OBJECT-TYPE
               SYNTAX  DisplayString
               ACCESS  read-write
               STATUS  mandatory
               DESCRIPTION
               "Command to be executed when critical threshold is crossed on a row."
               ::=  {  ap5VHOPTEntry 21   }
	       
        ap5VHOPTBLReportURL OBJECT-TYPE
               SYNTAX  DisplayString
               ACCESS  read-write
               STATUS  mandatory
               DESCRIPTION
               "Path and filename for report; Relative to DocumentRoot unless starts with '/'."
               ::=  {  ap5VHOPTEntry 22   }

        ap5VHOPTBLTableEntries OBJECT-TYPE
                SYNTAX  INTEGER
                ACCESS  read-only
                STATUS  mandatory
                DESCRIPTION
                "The number of entries in the BL table."
                ::=  {  ap5VHOPTEntry 23   }

        ap5VHOPTBLWarningCount OBJECT-TYPE
               SYNTAX  INTEGER
               ACCESS  read-only
               STATUS  mandatory
               DESCRIPTION
               "The number of entries in the table with a warning status."
               ::=  {  ap5VHOPTEntry 24   }
	       
        ap5VHOPTBLCriticalCount OBJECT-TYPE
               SYNTAX  INTEGER
               ACCESS  read-only
               STATUS  mandatory
               DESCRIPTION
               "The number of entries in the table with a critical status."
               ::=  {  ap5VHOPTEntry 25   }
	       
        ap5VHOPTURLMntrTableEntries OBJECT-TYPE
               SYNTAX  INTEGER
               ACCESS  read-only
               STATUS  mandatory
               DESCRIPTION
               "The number of entries in the Mntr URL table."
               ::=  {  ap5VHOPTEntry 26   }

        ap5VHOPTURLMntrHitRate OBJECT-TYPE
               SYNTAX  INTEGER
               ACCESS  read-write
               STATUS  mandatory
               DESCRIPTION
               "Interval in seconds over which the counter is measured."
               ::=  {  ap5VHOPTEntry 27   }

        ap5VHOPTPolledCounterTableEntries OBJECT-TYPE
                SYNTAX  INTEGER
                ACCESS  read-only
                STATUS  mandatory
                DESCRIPTION
                "The number of entries in the table."
                ::=  { ap5VHOPTEntry 28 }

        ap5VHOPTIISPCSummaryStatus OBJECT-TYPE
               SYNTAX  INTEGER {
                                normal(1),
                                warning(2),
                                critical(3)
                               }
               ACCESS  read-only
               STATUS  mandatory
               DESCRIPTION
               "IIS Polled Counter status for Vhost."
               ::=  {  ap5VHOPTEntry 29   }

        ap5VHOPTIISPolledCounterTableEntries OBJECT-TYPE
                SYNTAX  INTEGER
                ACCESS  read-only
                STATUS  mandatory
                DESCRIPTION
                "The number of entries in the table."
                ::=  { ap5VHOPTEntry 30 }
		

        ap5VHOPTSHRSLagSetting OBJECT-TYPE
                SYNTAX  INTEGER
                ACCESS  read-only
                STATUS  mandatory
                DESCRIPTION
                "Lag setting for the counter."
                ::=  {  ap5VHOPTEntry 31   }
		
        ap5VHOPTSHRSLagValue OBJECT-TYPE
                SYNTAX  INTEGER
                ACCESS  read-only
                STATUS  mandatory
                DESCRIPTION
                "Current Lag value for the counter."
                ::=  {  ap5VHOPTEntry 32   }

        ap5VHOPTSHKSLagSetting OBJECT-TYPE
                SYNTAX  INTEGER
                ACCESS  read-only
                STATUS  mandatory
                DESCRIPTION
                "Lag setting for the counter."
                ::=  {  ap5VHOPTEntry 33   }
		
        ap5VHOPTSHKSLagValue OBJECT-TYPE
                SYNTAX  INTEGER
                ACCESS  read-only
                STATUS  mandatory
                DESCRIPTION
                "Current Lag value for the counter."
                ::=  {  ap5VHOPTEntry 34   }



--*	Global section

        ap5VHSummaryStatus OBJECT-TYPE
               SYNTAX  INTEGER
               ACCESS  read-only
               STATUS  mandatory
               DESCRIPTION
               "The Summary status of the Virtual Host."
               ::=  {  ap5VHGroup 41   }
	       

--*	MntrUrls section

        ap5VHURLMntrTableEntries OBJECT-TYPE
               SYNTAX  INTEGER
               ACCESS  read-only
               STATUS  mandatory
               DESCRIPTION
               "The number of entries in the table."
               ::=  {  ap5VHGroup 42   }

        ap5VHURLMntrHitRate OBJECT-TYPE
               SYNTAX  INTEGER
               ACCESS  read-write
               STATUS  mandatory
               DESCRIPTION
               "Interval in seconds over which the counter is measured."
               ::=  {  ap5VHGroup 43   }

        ap5VHURLMntrSummaryStatus OBJECT-TYPE
               SYNTAX  INTEGER {
                                normal(1),
                                warning(2),
                                critical(3)
                               }
               ACCESS  read-only
               STATUS  mandatory
               DESCRIPTION
               "Most severe status of all rows in the table."
               ::=  {  ap5VHGroup 44   }

        ap5VHURLMntrTable OBJECT-TYPE
               SYNTAX  SEQUENCE OF Ap5VHURLMntrEntry
               ACCESS  not-accessible
               STATUS  mandatory
               DESCRIPTION
               "This table contains a list of URLs to monitor."
               ::=  {  ap5VHGroup 45 }

        ap5VHURLMntrEntry OBJECT-TYPE
               SYNTAX  Ap5VHURLMntrEntry
               ACCESS  not-accessible
               STATUS  mandatory
               DESCRIPTION
               "This is an entry in the URLMntrTable"
               INDEX { ap5VHURLMntrID }
               ::=  { ap5VHURLMntrTable 1 }

        Ap5VHURLMntrEntry ::= SEQUENCE
        {
           ap5VHURLMntrID				INTEGER,
           ap5VHURLMntrURL                               DisplayString,
           ap5VHURLMntrDesc                              DisplayString,
           ap5VHURLMntrValue                             DisplayString,
           ap5VHURLMntrWarningThreshold                  INTEGER,
           ap5VHURLMntrCriticalThreshold                 INTEGER,
           ap5VHURLMntrWarningAction                     DisplayString,
           ap5VHURLMntrCriticalAction                    DisplayString,
           ap5VHURLMntrStatus                            INTEGER,
           ap5VHURLMntrEnableDisable                     INTEGER,
           ap5VHURLMntrDescending                        INTEGER,
           ap5VHURLMntrReset                             INTEGER,
           ap5VHURLMntrResetTime                         DisplayString,
	   ap5VHURLMntrLagSetting			INTEGER,
	   ap5VHURLMntrLagValue				INTEGER
        }

	ap5VHURLMntrID OBJECT-TYPE
		SYNTAX      INTEGER
		ACCESS      read-only
		STATUS      mandatory
		DESCRIPTION "A unique ID."
		::= {ap5VHURLMntrEntry 1}
		
        ap5VHURLMntrURL OBJECT-TYPE
               SYNTAX  DisplayString
               ACCESS  read-only
               STATUS  mandatory
               DESCRIPTION
               "URL to monitor."
               ::=  {  ap5VHURLMntrEntry 2   }

        ap5VHURLMntrDesc OBJECT-TYPE
               SYNTAX  DisplayString
               ACCESS  read-only
               STATUS  mandatory
               DESCRIPTION
               "Description of the monitored value."
               ::=  {  ap5VHURLMntrEntry 3   }

        ap5VHURLMntrValue OBJECT-TYPE
               SYNTAX  DisplayString
               ACCESS  read-only
               STATUS  mandatory
               DESCRIPTION
               "Peak number of hits per URLMntrHitRate seconds."
               ::=  {  ap5VHURLMntrEntry 4   }

        ap5VHURLMntrWarningThreshold OBJECT-TYPE
               SYNTAX  INTEGER
               ACCESS  read-write
               STATUS  mandatory
               DESCRIPTION
               "Warning threshold in MS"
               ::=  {  ap5VHURLMntrEntry 5   }

        ap5VHURLMntrCriticalThreshold OBJECT-TYPE
               SYNTAX  INTEGER
               ACCESS  read-write
               STATUS  mandatory
               DESCRIPTION
               "Critical threshold in MS"
               ::=  {  ap5VHURLMntrEntry 6   }

        ap5VHURLMntrWarningAction OBJECT-TYPE
               SYNTAX  DisplayString
               ACCESS  read-write
               STATUS  mandatory
               DESCRIPTION
               "Command to be executed when warning threshold is exceeded."
               ::=  {  ap5VHURLMntrEntry 7   }

        ap5VHURLMntrCriticalAction OBJECT-TYPE
               SYNTAX  DisplayString
               ACCESS  read-write
               STATUS  mandatory
               DESCRIPTION
               "Command to be executed when critical threshold is exceeded."
               ::=  {  ap5VHURLMntrEntry 8  }

        ap5VHURLMntrStatus OBJECT-TYPE
               SYNTAX  INTEGER {
                                normal(1),
                                warning(2),
                                critical(3)
                               }
               ACCESS  read-only
               STATUS  mandatory
               DESCRIPTION
               "Status of this URL."
               ::=  {  ap5VHURLMntrEntry 9 }

        ap5VHURLMntrEnableDisable OBJECT-TYPE
                SYNTAX  INTEGER
                {
                    enable(1),
                    disable(2)
                }
                ACCESS  read-write
                STATUS  mandatory
                DESCRIPTION
                "Enable or disable alerts for this URL."
                ::=  {  ap5VHURLMntrEntry 10   }

        ap5VHURLMntrDescending OBJECT-TYPE
               SYNTAX  INTEGER {
                                no(1),
                                yes(2)
                               }
               ACCESS  read-only
               STATUS  mandatory
               DESCRIPTION
               "Yes if lower value triggers thresholds."
               ::=  {  ap5VHURLMntrEntry 11 }

        ap5VHURLMntrReset OBJECT-TYPE
               SYNTAX  INTEGER {
                                reset(1)
                               }
               ACCESS  write-only
               STATUS  mandatory
               DESCRIPTION
               "Reset value for this counter."
               ::=  {  ap5VHURLMntrEntry 12 }

        ap5VHURLMntrResetTime OBJECT-TYPE
               SYNTAX  DisplayString
               ACCESS  read-only
               STATUS  mandatory
               DESCRIPTION
               "Time stamp of when this counter was reset."
               ::=  {  ap5VHURLMntrEntry 13  }
		
        ap5VHURLMntrLagSetting OBJECT-TYPE
                SYNTAX  INTEGER
                ACCESS  read-write
                STATUS  mandatory
                DESCRIPTION
                "Lag setting for the counter."
                ::=  {  ap5VHURLMntrEntry 14   }
		
        ap5VHURLMntrLagValue OBJECT-TYPE
                SYNTAX  INTEGER
                ACCESS  read-only
                STATUS  mandatory
                DESCRIPTION
                "Current Lag value for the counter."
                ::=  {  ap5VHURLMntrEntry 15   }


--* 	Global section    

        ap5VHGroupSummaryStatus OBJECT-TYPE
               SYNTAX  INTEGER {
                                normal(1),
                                warning(2),
                                critical(3)
                                }
               ACCESS  read-only
               STATUS  mandatory
               DESCRIPTION
               "Summary status for group."
                ::=  {  ap5VHGroup 46 }

        ap5VHTableInterval OBJECT-TYPE
               SYNTAX  INTEGER
               ACCESS  read-write
               STATUS  mandatory
               DESCRIPTION
               "Seconds between polls for the VHTable."
               ::=  { ap5VHGroup 47 }

--*	Polled Counter section

        ap5VHPolledCounterTableEntries OBJECT-TYPE
                SYNTAX  INTEGER
                ACCESS  read-only
                STATUS  mandatory
                DESCRIPTION
                "The number of entries in the table."
                ::=  { ap5VHGroup 48 }

        ap5VHPolledSummaryStatus OBJECT-TYPE
                SYNTAX  INTEGER
                {
                    normal(1),
                    warning(2),
                    critical(3)
                }
                ACCESS  read-only
                STATUS  mandatory
                DESCRIPTION
                "The summary status of all polled counters."
                ::=  {  ap5VHGroup 49   }

        ap5VHPolledWarningCount OBJECT-TYPE
                SYNTAX  INTEGER
                ACCESS  read-only
                STATUS  mandatory
                DESCRIPTION
                "Number of polled counters in warning state."
                ::=  {  ap5VHGroup 50  }

        ap5VHPolledCriticalCount OBJECT-TYPE
                SYNTAX  INTEGER
                ACCESS  read-only
                STATUS  mandatory
                DESCRIPTION
                "Number of polled counters in critical state."
                ::=  {  ap5VHGroup 51  }

        ap5VHPolledCounterTable OBJECT-TYPE
                SYNTAX  SEQUENCE OF Ap5VHPolledCounterEntry
                ACCESS  not-accessible
                STATUS  mandatory
                DESCRIPTION
                "The list of all polled counters."
                ::=  {  ap5VHGroup 52 }

        ap5VHPolledCounterEntry OBJECT-TYPE
                 SYNTAX  Ap5VHPolledCounterEntry
                 ACCESS  not-accessible
                 STATUS  mandatory
                 DESCRIPTION
                 "The PolledCounterTable entry."
                 INDEX { ap5VHPolledID }
                     ::=  { ap5VHPolledCounterTable 1 }

        Ap5VHPolledCounterEntry ::= SEQUENCE {
	    ap5VHPolledID		  INTEGER,
            ap5VHDescription               DisplayString,
            ap5VHAvailable                 INTEGER,
            ap5VHWarningThreshold          DisplayString,
            ap5VHCriticalThreshold         DisplayString,
            ap5VHPCValue                   DisplayString,
            ap5VHWarningCount              INTEGER,
            ap5VHCriticalCount             INTEGER,
            ap5VHWarningAction             DisplayString,
            ap5VHCriticalAction            DisplayString,
            ap5VHStatus                    INTEGER,
            ap5VHEnableDisable             INTEGER,
            ap5VHDescendingCounter         INTEGER,
            ap5VHMinimum                   DisplayString,
            ap5VHMaximum                   DisplayString,
            ap5VHAverage                   DisplayString,
            ap5VHStdDev                    DisplayString,
	    ap5VHLagSetting		  INTEGER,
	    ap5VHLagValue		  INTEGER
        }


	ap5VHPolledID OBJECT-TYPE
		SYNTAX      INTEGER
		ACCESS      read-only
		STATUS      mandatory
		DESCRIPTION "A unique ID."
		::= {ap5VHPolledCounterEntry 1}
		
        ap5VHDescription OBJECT-TYPE
                SYNTAX  DisplayString
                ACCESS  read-only
                STATUS  mandatory
                DESCRIPTION
                "The description of the polled counter."
                ::=  {  ap5VHPolledCounterEntry 2   }

        ap5VHAvailable OBJECT-TYPE
                SYNTAX  INTEGER
                {
                    available(1),
                    notavailable(2)
                }
                ACCESS  read-only
                STATUS  mandatory
                DESCRIPTION
                "Describes whether this counter is currently available."
                ::=  {  ap5VHPolledCounterEntry 3   }

        ap5VHWarningThreshold OBJECT-TYPE
                SYNTAX  DisplayString
                ACCESS  read-write
                STATUS  mandatory
                DESCRIPTION
                "Counter value that will trigger warning status if value exceeds it."
                ::=  {  ap5VHPolledCounterEntry 4   }

        ap5VHCriticalThreshold OBJECT-TYPE
                SYNTAX  DisplayString
                ACCESS  read-write
                STATUS  mandatory
                DESCRIPTION
                "Counter value that will trigger critical status if value exceeds it."
                ::=  {  ap5VHPolledCounterEntry 5   }

        ap5VHPCValue OBJECT-TYPE
                SYNTAX  DisplayString
                ACCESS  read-only
                STATUS  mandatory
                DESCRIPTION
                "Value of the polled counter."
                ::=  {  ap5VHPolledCounterEntry 6   }

        ap5VHWarningCount OBJECT-TYPE
                SYNTAX  INTEGER
                ACCESS  read-only
                STATUS  mandatory
                DESCRIPTION
                "Number of times warning alert generated."
                ::=  {  ap5VHPolledCounterEntry 7   }

        ap5VHCriticalCount OBJECT-TYPE
                SYNTAX  INTEGER
                ACCESS  read-only
                STATUS  mandatory
                DESCRIPTION
                "Number of times critical alert generated."
                ::=  {  ap5VHPolledCounterEntry 8   }

        ap5VHWarningAction OBJECT-TYPE
                SYNTAX  DisplayString
                ACCESS  read-write
                STATUS  mandatory
                DESCRIPTION
                "Command to be executed when warning threshold is exceeded."
                ::=  {  ap5VHPolledCounterEntry 9   }

        ap5VHCriticalAction OBJECT-TYPE
                SYNTAX  DisplayString
                ACCESS  read-write
                STATUS  mandatory
                DESCRIPTION
                "Command to be executed when critical threshold is exceeded."
                ::=  {  ap5VHPolledCounterEntry 10   }

        ap5VHStatus OBJECT-TYPE
                SYNTAX  INTEGER
                {
                    normal(1),
                    warning(2),
                    critical(3)
                }
                ACCESS  read-only
                STATUS  mandatory
                DESCRIPTION
                "Status of the polled counter."
                ::=  {  ap5VHPolledCounterEntry 11   }

        ap5VHEnableDisable OBJECT-TYPE
                SYNTAX  INTEGER
                {
                    enable(1),
                    disable(2)
                }
                ACCESS  read-write
                STATUS  mandatory
                DESCRIPTION
                "Enable or disable alerts for this counter."
                ::=  {  ap5VHPolledCounterEntry 12   }

        ap5VHDescendingCounter OBJECT-TYPE
                SYNTAX  INTEGER
                {
                    no(1),
                    yes(2)
                }
                ACCESS  read-write
                STATUS  mandatory
                DESCRIPTION
                "Yes if lower value triggers thresholds, no if higher value triggers thresholds."
                ::=  {  ap5VHPolledCounterEntry 13   }

        ap5VHMinimum OBJECT-TYPE
               SYNTAX  DisplayString
               ACCESS  read-only
               STATUS  mandatory
               DESCRIPTION
               "The minimum reading since the last reset."
               ::=  {  ap5VHPolledCounterEntry 14   }

        ap5VHMaximum OBJECT-TYPE
               SYNTAX  DisplayString
               ACCESS  read-only
               STATUS  mandatory
               DESCRIPTION
               "The maximum reading since the last reset."
               ::=  {  ap5VHPolledCounterEntry 15   }

        ap5VHAverage OBJECT-TYPE
               SYNTAX  DisplayString
               ACCESS  read-only
               STATUS  mandatory
               DESCRIPTION
               "The average reading since the last reset."
               ::=  {  ap5VHPolledCounterEntry 16   }

        ap5VHStdDev OBJECT-TYPE
               SYNTAX  DisplayString
               ACCESS  read-only
               STATUS  mandatory
               DESCRIPTION
               "The standard deviation based on the last 100 readings."
               ::=  {  ap5VHPolledCounterEntry 17   }
		
        ap5VHLagSetting OBJECT-TYPE
                SYNTAX  INTEGER
                ACCESS  read-write
                STATUS  mandatory
                DESCRIPTION
                "Lag setting for the counter."
                ::=  {  ap5VHPolledCounterEntry 18   }
		
        ap5VHLagValue OBJECT-TYPE
                SYNTAX  INTEGER
                ACCESS  read-only
                STATUS  mandatory
                DESCRIPTION
                "Current Lag value for the counter."
                ::=  {  ap5VHPolledCounterEntry 19   }
	       

--*	IIS Polled Counter section

        ap5VHIISPolledCounterTableEntries OBJECT-TYPE
                SYNTAX  INTEGER
                ACCESS  read-only
                STATUS  mandatory
                DESCRIPTION
                "The number of entries in the table."
                ::=  { ap5VHGroup 53 }

        ap5VHIISPolledSummaryStatus OBJECT-TYPE
                SYNTAX  INTEGER
                {
                    normal(1),
                    warning(2),
                    critical(3)
                }
                ACCESS  read-only
                STATUS  mandatory
                DESCRIPTION
                "The summary status of all polled counters."
                ::=  {  ap5VHGroup 54   }

        ap5VHIISPolledWarningCount OBJECT-TYPE
                SYNTAX  INTEGER
                ACCESS  read-only
                STATUS  mandatory
                DESCRIPTION
                "Number of polled counters in warning state."
                ::=  {  ap5VHGroup 55  }

        ap5VHIISPolledCriticalCount OBJECT-TYPE
                SYNTAX  INTEGER
                ACCESS  read-only
                STATUS  mandatory
                DESCRIPTION
                "Number of polled counters in critical state."
                ::=  {  ap5VHGroup 56  }

        ap5VHIISPolledCounterTable OBJECT-TYPE
                SYNTAX  SEQUENCE OF Ap5VHIISPolledCounterEntry
                ACCESS  not-accessible
                STATUS  mandatory
                DESCRIPTION
                "The list of all polled counters."
                ::=  {  ap5VHGroup 57 }

	ap5VHGPEnaDis OBJECT-TYPE
		SYNTAX      INTEGER {enable(1), disable(2)}
		ACCESS      read-write
		STATUS      mandatory
		DESCRIPTION "Enable or disable for the Group."
		::= { ap5VHGroup 58 }

        ap5VHIISPolledCounterEntry OBJECT-TYPE
                 SYNTAX  Ap5VHIISPolledCounterEntry
                 ACCESS  not-accessible
                 STATUS  mandatory
                 DESCRIPTION
                 "The IISPolledCounterTable entry."
                 INDEX { ap5VHIISPolledID }
                     ::=  { ap5VHIISPolledCounterTable 1 }

        Ap5VHIISPolledCounterEntry ::= SEQUENCE {
	    ap5VHIISPolledID		INTEGER,
            ap5VHIISDescription          DisplayString,
            ap5VHIISAvailable            INTEGER,
            ap5VHIISWarningThreshold     DisplayString,
            ap5VHIISCriticalThreshold    DisplayString,
            ap5VHIISPCValue              DisplayString,
            ap5VHIISWarningCount         INTEGER,
            ap5VHIISCriticalCount        INTEGER,
            ap5VHIISWarningAction        DisplayString,
            ap5VHIISCriticalAction       DisplayString,
            ap5VHIISStatus               INTEGER,
            ap5VHIISEnableDisable        INTEGER,
            ap5VHIISDescendingCounter    INTEGER,
            ap5VHIISMinimum              DisplayString,
            ap5VHIISMaximum              DisplayString,
            ap5VHIISAverage              DisplayString,
            ap5VHIISStdDev               DisplayString,
	    ap5VHIISLagSetting		INTEGER,
	    ap5VHIISLagValue		INTEGER
        }


	ap5VHIISPolledID OBJECT-TYPE
		SYNTAX      INTEGER
		ACCESS      read-only
		STATUS      mandatory
		DESCRIPTION "A unique ID."
		::= {ap5VHIISPolledCounterEntry 1}
		
        ap5VHIISDescription OBJECT-TYPE
                SYNTAX  DisplayString
                ACCESS  read-only
                STATUS  mandatory
                DESCRIPTION
                "The description of the polled counter."
                ::=  {  ap5VHIISPolledCounterEntry 2   }

        ap5VHIISAvailable OBJECT-TYPE
                SYNTAX  INTEGER
                {
                    available(1),
                    notavailable(2)
                }
                ACCESS  read-only
                STATUS  mandatory
                DESCRIPTION
                "Describes whether this counter is currently available."
                ::=  {  ap5VHIISPolledCounterEntry 3   }

        ap5VHIISWarningThreshold OBJECT-TYPE
                SYNTAX  DisplayString
                ACCESS  read-write
                STATUS  mandatory
                DESCRIPTION
                "Counter value that will trigger warning status if value exceeds it."
                ::=  {  ap5VHIISPolledCounterEntry 4   }

        ap5VHIISCriticalThreshold OBJECT-TYPE
                SYNTAX  DisplayString
                ACCESS  read-write
                STATUS  mandatory
                DESCRIPTION
                "Counter value that will trigger critical status if value exceeds it."
                ::=  {  ap5VHIISPolledCounterEntry 5   }

        ap5VHIISPCValue OBJECT-TYPE
                SYNTAX  DisplayString
                ACCESS  read-only
                STATUS  mandatory
                DESCRIPTION
                "Value of the polled counter."
                ::=  {  ap5VHIISPolledCounterEntry 6   }

        ap5VHIISWarningCount OBJECT-TYPE
                SYNTAX  INTEGER
                ACCESS  read-only
                STATUS  mandatory
                DESCRIPTION
                "Number of times warning alert generated."
                ::=  {  ap5VHIISPolledCounterEntry 7   }

        ap5VHIISCriticalCount OBJECT-TYPE
                SYNTAX  INTEGER
                ACCESS  read-only
                STATUS  mandatory
                DESCRIPTION
                "Number of times critical alert generated."
                ::=  {  ap5VHIISPolledCounterEntry 8   }

        ap5VHIISWarningAction OBJECT-TYPE
                SYNTAX  DisplayString
                ACCESS  read-write
                STATUS  mandatory
                DESCRIPTION
                "Command to be executed when warning threshold is exceeded."
                ::=  {  ap5VHIISPolledCounterEntry 9   }

        ap5VHIISCriticalAction OBJECT-TYPE
                SYNTAX  DisplayString
                ACCESS  read-write
                STATUS  mandatory
                DESCRIPTION
                "Command to be executed when critical threshold is exceeded."
                ::=  {  ap5VHIISPolledCounterEntry 10   }

        ap5VHIISStatus OBJECT-TYPE
                SYNTAX  INTEGER
                {
                    normal(1),
                    warning(2),
                    critical(3)
                }
                ACCESS  read-only
                STATUS  mandatory
                DESCRIPTION
                "Status of the polled counter."
                ::=  {  ap5VHIISPolledCounterEntry 11   }

        ap5VHIISEnableDisable OBJECT-TYPE
                SYNTAX  INTEGER
                {
                    enable(1),
                    disable(2)
                }
                ACCESS  read-write
                STATUS  mandatory
                DESCRIPTION
                "Enable or disable alerts for this counter."
                ::=  {  ap5VHIISPolledCounterEntry 12   }

        ap5VHIISDescendingCounter OBJECT-TYPE
                SYNTAX  INTEGER
                {
                    no(1),
                    yes(2)
                }
                ACCESS  read-write
                STATUS  mandatory
                DESCRIPTION
                "Yes if lower value triggers thresholds, no if higher value triggers thresholds."
                ::=  {  ap5VHIISPolledCounterEntry 13   }

        ap5VHIISMinimum OBJECT-TYPE
               SYNTAX  DisplayString
               ACCESS  read-only
               STATUS  mandatory
               DESCRIPTION
               "The minimum reading since the last reset."
               ::=  {  ap5VHIISPolledCounterEntry 14   }

        ap5VHIISMaximum OBJECT-TYPE
               SYNTAX  DisplayString
               ACCESS  read-only
               STATUS  mandatory
               DESCRIPTION
               "The maximum reading since the last reset."
               ::=  {  ap5VHIISPolledCounterEntry 15   }

        ap5VHIISAverage OBJECT-TYPE
               SYNTAX  DisplayString
               ACCESS  read-only
               STATUS  mandatory
               DESCRIPTION
               "The average reading since the last reset."
               ::=  {  ap5VHIISPolledCounterEntry 16   }

        ap5VHIISStdDev OBJECT-TYPE
               SYNTAX  DisplayString
               ACCESS  read-only
               STATUS  mandatory
               DESCRIPTION
               "The standard deviation based on the last 100 readings."
               ::=  {  ap5VHIISPolledCounterEntry 17   }
		
        ap5VHIISLagSetting OBJECT-TYPE
                SYNTAX  INTEGER
                ACCESS  read-write
                STATUS  mandatory
                DESCRIPTION
                "Lag setting for the counter."
                ::=  {  ap5VHIISPolledCounterEntry 18   }
		
        ap5VHIISLagValue OBJECT-TYPE
                SYNTAX  INTEGER
                ACCESS  read-only
                STATUS  mandatory
                DESCRIPTION
                "Current Lag value for the counter."
                ::=  {  ap5VHIISPolledCounterEntry 19   }


--*	Lag values

		
        ap5VHSHRSLagSetting OBJECT-TYPE
                SYNTAX  INTEGER
                ACCESS  read-write
                STATUS  mandatory
                DESCRIPTION
                "Lag setting for the counter."
                ::=  {  ap5VHGroup 59   }
		
        ap5VHSHRSLagValue OBJECT-TYPE
                SYNTAX  INTEGER
                ACCESS  read-only
                STATUS  mandatory
                DESCRIPTION
                "Current Lag value for the counter."
                ::=  {  ap5VHGroup 60   }

        ap5VHSHKSLagSetting OBJECT-TYPE
                SYNTAX  INTEGER
                ACCESS  read-write
                STATUS  mandatory
                DESCRIPTION
                "Lag setting for the counter."
                ::=  {  ap5VHGroup 61   }
		
        ap5VHSHKSLagValue OBJECT-TYPE
                SYNTAX  INTEGER
                ACCESS  read-only
                STATUS  mandatory
                DESCRIPTION
                "Current Lag value for the counter."
                ::=  {  ap5VHGroup 62   }


--******************************************************************************
--* IISAvailCounterGroup - Counters currently available
--******************************************************************************

   ap5IISAvailCounterTableEntries OBJECT-TYPE
      SYNTAX      INTEGER
      ACCESS      read-only
      STATUS      mandatory
      DESCRIPTION "The number of entries in the table."
      ::= {ap5IISAvailCounterGroup 1}

   ap5IISAvailCounterTable OBJECT-TYPE
      SYNTAX      SEQUENCE OF ap5IISAvailCounterEntryS
      ACCESS      not-accessible
      STATUS      mandatory
      DESCRIPTION "This table contains a list of all monitored AvailCounters"
      ::= {ap5IISAvailCounterGroup 2}

   ap5IISAvailCounterEntry OBJECT-TYPE
      SYNTAX      ap5IISAvailCounterEntryS
      ACCESS      not-accessible
      STATUS      mandatory
      DESCRIPTION "This is an entry in the AvailCounterTable"
      INDEX       { ap5IISAvailCounterDescription }
      ::= { ap5IISAvailCounterTable 1 }

   ap5IISAvailCounterEntryS ::= SEQUENCE
   {
      ap5IISAvailCounterDescription  DisplayString
   }

   ap5IISAvailCounterDescription OBJECT-TYPE
      SYNTAX      DisplayString
      ACCESS      read-only
      STATUS      mandatory
      DESCRIPTION "The description of the AvailCounter"
      ::= {ap5IISAvailCounterEntry 1}

   ap5IISAvailCounterTableEntriesVH OBJECT-TYPE
      SYNTAX      INTEGER
      ACCESS      read-only
      STATUS      mandatory
      DESCRIPTION "The number of entries in the table."
      ::= {ap5IISAvailCounterGroup 3}

--   ap5IISAvailCounterTableVH OBJECT-TYPE
--      SYNTAX      SEQUENCE OF ap5AvailCounterEntryVH
--      ACCESS      not-accessible
--      STATUS      mandatory
--      DESCRIPTION "This table contains a list of all monitored AvailCounters"
--      ::= {ap5IISAvailCounterGroup 4}

   ap5IISAvailCounterTableVH OBJECT-TYPE
      SYNTAX      SEQUENCE OF is5IISAvailCounterEntryVH
      ACCESS      not-accessible
      STATUS      mandatory
      DESCRIPTION "This table contains a list of all monitored AvailCounters"
      ::= {ap5IISAvailCounterGroup 4}

   ap5IISAvailCounterEntryVH OBJECT-TYPE
      SYNTAX      is5IISAvailCounterEntryVH
      ACCESS      not-accessible
      STATUS      mandatory
      DESCRIPTION "This is an entry in the AvailCounterTable"
      INDEX       { ap5IISAvailCounterDescriptionVH }
      ::= { ap5IISAvailCounterTableVH 1 }

   is5IISAvailCounterEntryVH ::= SEQUENCE
   {
      ap5IISAvailCounterDescriptionVH  DisplayString
   }

   ap5IISAvailCounterDescriptionVH OBJECT-TYPE
      SYNTAX      DisplayString
      ACCESS      read-only
      STATUS      mandatory
      DESCRIPTION "The description of the AvailCounter"
      ::= {ap5IISAvailCounterEntryVH 1}


--******************************************************************************
--* IISPolledCounterGroup - Counters being polled
--******************************************************************************

   ap5IISPolledCounterTableEntries OBJECT-TYPE
      SYNTAX      INTEGER
      ACCESS      read-only
      STATUS      mandatory
      DESCRIPTION "The number of entries in the table."
      ::= {ap5IISPolledCounterGroup 1}

   ap5IISPolledCounterAdd OBJECT-TYPE
      SYNTAX      DisplayString
      ACCESS      write-only
      STATUS      mandatory
      DESCRIPTION "Add this entry to the polled group."
      ::= {ap5IISPolledCounterGroup 2}

   ap5IISPolledCounterDelete OBJECT-TYPE
      SYNTAX      DisplayString
      ACCESS      write-only
      STATUS      mandatory
      DESCRIPTION "Delete this entry from the polled group."
      ::= {ap5IISPolledCounterGroup 3}

   ap5IISPolledCounterStatus OBJECT-TYPE
      SYNTAX      INTEGER {normal(1), warning(2), critical(3)}
      ACCESS      read-only
      STATUS      mandatory
      DESCRIPTION "Summary status for counters."
      ::= {ap5IISPolledCounterGroup 4}

   ap5IISPolledCounterInterval OBJECT-TYPE
      SYNTAX      INTEGER
      ACCESS      read-write
      STATUS      mandatory
      DESCRIPTION "Seconds to poll for changes."
      ::= {ap5IISPolledCounterGroup 5}

   ap5IISPolledCounterTable OBJECT-TYPE
      SYNTAX      SEQUENCE OF ap5IISPolledCounterEntryS
      ACCESS      not-accessible
      STATUS      mandatory
      DESCRIPTION "This table contains a list of all monitored PolledCounters"
      ::= {ap5IISPolledCounterGroup 6}

   ap5IISPolledCounterWarningCount OBJECT-TYPE
      SYNTAX      INTEGER
      ACCESS      read-only
      STATUS      mandatory
      DESCRIPTION "Times warning threshold exceeded."
      ::= {ap5IISPolledCounterGroup 7}

   ap5IISPolledCounterCriticalCount OBJECT-TYPE
      SYNTAX      INTEGER
      ACCESS      read-only
      STATUS      mandatory
      DESCRIPTION "Times critical threshold exceeded."
      ::= {ap5IISPolledCounterGroup 8}

   ap5IISPolledCounterCmd OBJECT-TYPE
      SYNTAX      DisplayString
      ACCESS      read-write
      STATUS      mandatory
      DESCRIPTION "Modify,desc,warn_thrsh,crit_thrsh,warn_act, crit_act,enabled,descend"
      ::= {ap5IISPolledCounterGroup 9}

   ap5IISPolledCounterEntry OBJECT-TYPE
      SYNTAX      ap5IISPolledCounterEntryS
      ACCESS      not-accessible
      STATUS      mandatory
      DESCRIPTION "This is an entry in the IISPolledCounterTable"
      INDEX       { ap5IISRecDescription }
      ::= { ap5IISPolledCounterTable 1 }

   ap5IISPolledCounterEntryS ::= SEQUENCE
   {
	ap5IISRecDescription           	DisplayString,
	ap5IISRecAvailable             	INTEGER,
	ap5IISRecWarningThreshold      	DisplayString,
	ap5IISRecCriticalThreshold     	DisplayString,
	ap5IISRecValue                 	DisplayString,
	ap5IISRecWarningCount          	INTEGER,
	ap5IISRecCriticalCount         	INTEGER,
	ap5IISRecWarningAction         	DisplayString,
	ap5IISRecCriticalAction        	DisplayString,
	ap5IISRecStatus                	INTEGER,
	ap5IISRecEnableDisable         	INTEGER,
	ap5IISRecMinimum               	DisplayString,
	ap5IISRecMaximum               	DisplayString,
	ap5IISRecAverage               	DisplayString,
	ap5IISRecStdDev               	DisplayString,
	ap5IISRecDescendingCounter     	INTEGER,
	ap5IISRecPrevStatus            	INTEGER,
	ap5IISRecLagSetting		INTEGER,
	ap5IISRecLagValue		INTEGER
   }

   ap5IISRecDescription OBJECT-TYPE
      SYNTAX      DisplayString
      ACCESS      read-only
      STATUS      mandatory
      DESCRIPTION "The description of the PolledCounter"
      ::= {ap5IISPolledCounterEntry 1}

   ap5IISRecAvailable OBJECT-TYPE
      SYNTAX      INTEGER {available(1), notavailable(2)}
      ACCESS      read-only
      STATUS      mandatory
      DESCRIPTION "Describes whether this counter is currently available."
      ::= {ap5IISPolledCounterEntry 2}

   ap5IISRecWarningThreshold OBJECT-TYPE
      SYNTAX      DisplayString
      ACCESS      read-write
      STATUS      mandatory
      DESCRIPTION "Generate a warning if value exceeds this."
      ::= {ap5IISPolledCounterEntry 3}

   ap5IISRecCriticalThreshold OBJECT-TYPE
      SYNTAX      DisplayString
      ACCESS      read-write
      STATUS      mandatory
      DESCRIPTION "Generate a critical if value exceeds this."
      ::= {ap5IISPolledCounterEntry 4}

   ap5IISRecValue OBJECT-TYPE
      SYNTAX      DisplayString
      ACCESS      read-only
      STATUS      mandatory
      DESCRIPTION "Value of the counter."
      ::= {ap5IISPolledCounterEntry 5}

   ap5IISRecWarningCount OBJECT-TYPE
      SYNTAX      INTEGER
      ACCESS      read-only
      STATUS      mandatory
      DESCRIPTION "Times warning threshold exceeded."
      ::= {ap5IISPolledCounterEntry 6}

   ap5IISRecCriticalCount OBJECT-TYPE
      SYNTAX      INTEGER
      ACCESS      read-only
      STATUS      mandatory
      DESCRIPTION "Times critical threshold exceeded."
      ::= {ap5IISPolledCounterEntry 7}

   ap5IISRecWarningAction OBJECT-TYPE
      SYNTAX      DisplayString
      ACCESS      read-write
      STATUS      mandatory
      DESCRIPTION "Command to be executed when warning threshold is exceeded."
      ::= {ap5IISPolledCounterEntry 8}

   ap5IISRecCriticalAction OBJECT-TYPE
      SYNTAX      DisplayString
      ACCESS      read-write
      STATUS      mandatory
      DESCRIPTION "Command to be executed when critical threshold is exceeded."
      ::= {ap5IISPolledCounterEntry 9}

   ap5IISRecStatus OBJECT-TYPE
      SYNTAX      INTEGER {normal(1), warning(2), critical(3)}
      ACCESS      read-only
      STATUS      mandatory
      DESCRIPTION "Status of this counter."
      ::= {ap5IISPolledCounterEntry 10}

   ap5IISRecEnableDisable OBJECT-TYPE
      SYNTAX      INTEGER {enable(1), disable(2)}
      ACCESS      read-write
      STATUS      mandatory
      DESCRIPTION "Enable or disable alerts for this counter."
      ::= {ap5IISPolledCounterEntry 11}

   ap5IISRecMinimum OBJECT-TYPE
      SYNTAX      DisplayString
      ACCESS      read-only
      STATUS      mandatory
      DESCRIPTION "The minimum reading since the last reset."
      ::= {ap5IISPolledCounterEntry 12}

   ap5IISRecMaximum OBJECT-TYPE
      SYNTAX      DisplayString
      ACCESS      read-only
      STATUS      mandatory
      DESCRIPTION "The maximum reading since the last reset."
      ::= {ap5IISPolledCounterEntry 13}

   ap5IISRecAverage OBJECT-TYPE
      SYNTAX      DisplayString
      ACCESS      read-only
      STATUS      mandatory
      DESCRIPTION "The average reading since the last reset."
      ::= {ap5IISPolledCounterEntry 14}

   ap5IISRecStdDev OBJECT-TYPE
      SYNTAX      DisplayString
      ACCESS      read-only
      STATUS      mandatory
      DESCRIPTION "The standard deviation based on the last 100 readings."
      ::= {ap5IISPolledCounterEntry 15}

   ap5IISRecDescendingCounter OBJECT-TYPE
      SYNTAX      INTEGER {no(1), yes(2)}
      ACCESS      read-write
      STATUS      mandatory
      DESCRIPTION "Yes if lower value triggers thresholds."
      ::= {ap5IISPolledCounterEntry 16}

   ap5IISRecPrevStatus OBJECT-TYPE
      SYNTAX      INTEGER {normal(1), warning(2), critical(3)}
      ACCESS      read-only
      STATUS      mandatory
      DESCRIPTION "Status of this counter."
      ::= {ap5IISPolledCounterEntry 17}
		
   ap5IISRecLagSetting OBJECT-TYPE
	SYNTAX  INTEGER
	ACCESS  read-write
	STATUS  mandatory
	DESCRIPTION
	"Lag setting for the counter."
	::=  {  ap5IISPolledCounterEntry 18   }
		
   ap5IISRecLagValue OBJECT-TYPE
	SYNTAX  INTEGER
	ACCESS  read-only
	STATUS  mandatory
	DESCRIPTION
	"Current Lag value for the counter."
	::=  {  ap5IISPolledCounterEntry 19   }
	       
   ap5IISPolledCounterDispTableEntries OBJECT-TYPE
	SYNTAX  INTEGER
	ACCESS  read-only
	STATUS  mandatory
	DESCRIPTION
	"The number of entries in the table."
	::=  {  ap5IISPolledCounterGroup 10   }

   ap5IISPolledCounterDispTable OBJECT-TYPE
	SYNTAX  SEQUENCE OF Ap5IISPolledCounterDispEntry
	ACCESS  not-accessible
	STATUS  mandatory
	DESCRIPTION
	"The list of all polled counters."
	::=  {  ap5IISPolledCounterGroup 11}

  ap5IISPolledGPEnaDis OBJECT-TYPE
	SYNTAX      INTEGER {enable(1), disable(2)}
	ACCESS      read-write
	STATUS      mandatory
	DESCRIPTION "Enable or disable for the Group."
	::= { ap5IISPolledCounterGroup 12 }

  ap5IISPolledCounterDispEntry OBJECT-TYPE
	 SYNTAX  Ap5IISPolledCounterDispEntry
	 ACCESS  not-accessible
	 STATUS  mandatory
	 DESCRIPTION
	 "The IISPolledCounterTable entry."
	 INDEX { ap5IISDispDescription }
	     ::=  { ap5IISPolledCounterDispTable 1 }
 
   Ap5IISPolledCounterDispEntry ::= SEQUENCE {
	ap5IISDispDescription            DisplayString,
	ap5IISDispAvailable              INTEGER,
	ap5IISDispWarningThreshold       DisplayString,
	ap5IISDispCriticalThreshold      DisplayString,
	ap5IISDispValue                  DisplayString,
	ap5IISDispWarningCount           INTEGER,
	ap5IISDispCriticalCount          INTEGER,
	ap5IISDispWarningAction          DisplayString,
	ap5IISDispCriticalAction         DisplayString,
	ap5IISDispStatus                 INTEGER,
	ap5IISDispEnableDisable          INTEGER,
	ap5IISDispDescendingCounter      INTEGER,
	ap5IISDispMinimum                DisplayString,
	ap5IISDispMaximum                DisplayString,
	ap5IISDispAverage                DisplayString,
	ap5IISDispStdDev                 DisplayString,
	ap5IISDispValueReported		INTEGER,
	ap5IISDispLagSetting		INTEGER,
	ap5IISDispLagValue		INTEGER
   }

   ap5IISDispDescription OBJECT-TYPE
	SYNTAX  DisplayString
	ACCESS  read-only
	STATUS  mandatory
	DESCRIPTION
	"The description of the polled counter."
	::=  {  ap5IISPolledCounterDispEntry 1   }

   ap5IISDispAvailable OBJECT-TYPE
	SYNTAX  INTEGER
	{
	    available(1),
	    notavailable(2)
	}
	ACCESS  read-only
	STATUS  mandatory
	DESCRIPTION
	"Describes whether this counter is currently available."
	::=  {  ap5IISPolledCounterDispEntry 2   }

   ap5IISDispWarningThreshold OBJECT-TYPE
	SYNTAX  DisplayString
	ACCESS  read-write
	STATUS  mandatory
	DESCRIPTION
	"Counter value that will trigger warning status if value exceeds it."
	::=  {  ap5IISPolledCounterDispEntry 3   }

   ap5IISDispCriticalThreshold OBJECT-TYPE
	SYNTAX  DisplayString
	ACCESS  read-write
	STATUS  mandatory
	DESCRIPTION
	"Counter value that will trigger critical status if value exceeds it."
	::=  {  ap5IISPolledCounterDispEntry 4   }

   ap5IISDispValue OBJECT-TYPE
	SYNTAX  DisplayString
	ACCESS  read-only
	STATUS  mandatory
	DESCRIPTION
	"Value of the polled counter."
	::=  {  ap5IISPolledCounterDispEntry 5   }

   ap5IISDispWarningCount OBJECT-TYPE
	SYNTAX  INTEGER
	ACCESS  read-only
	STATUS  mandatory
	DESCRIPTION
	"Number of times warning alert generated."
	::=  {  ap5IISPolledCounterDispEntry 6   }

   ap5IISDispCriticalCount OBJECT-TYPE
	SYNTAX  INTEGER
	ACCESS  read-only
	STATUS  mandatory
	DESCRIPTION
	"Number of times critical alert generated."
	::=  {  ap5IISPolledCounterDispEntry 7   }

   ap5IISDispWarningAction OBJECT-TYPE
	SYNTAX  DisplayString
	ACCESS  read-write
	STATUS  mandatory
	DESCRIPTION
	"Command to be executed when warning threshold is exceeded."
	::=  {  ap5IISPolledCounterDispEntry 8   }

   ap5IISDispCriticalAction OBJECT-TYPE
	SYNTAX  DisplayString
	ACCESS  read-write
	STATUS  mandatory
	DESCRIPTION
	"Command to be executed when critical threshold is exceeded."
	::=  {  ap5IISPolledCounterDispEntry 9   }

   ap5IISDispStatus OBJECT-TYPE
	SYNTAX  INTEGER
	{
	    normal(1),
	    warning(2),
	    critical(3)
	}
	ACCESS  read-only
	STATUS  mandatory
	DESCRIPTION
	"Status of the polled counter."
	::=  {  ap5IISPolledCounterDispEntry 10   }

   ap5IISDispEnableDisable OBJECT-TYPE
	SYNTAX  INTEGER
	{
	    enable(1),
	    disable(2)
	}
	ACCESS  read-write
	STATUS  mandatory
	DESCRIPTION
	"Enable or disable alerts for this counter."
	::=  {  ap5IISPolledCounterDispEntry 11   }

   ap5IISDispDescendingCounter OBJECT-TYPE
	SYNTAX  INTEGER
	{
	    no(1),
	    yes(2)
	}
	ACCESS  read-write
	STATUS  mandatory
	DESCRIPTION
	"Yes if lower value triggers thresholds, no if higher value triggers thresholds."
	::=  {  ap5IISPolledCounterDispEntry 12   }

   ap5IISDispMinimum OBJECT-TYPE
       SYNTAX  DisplayString
       ACCESS  read-only
       STATUS  mandatory
       DESCRIPTION
       "The minimum reading since the last reset."
       ::=  {  ap5IISPolledCounterDispEntry 13   }

   ap5IISDispMaximum OBJECT-TYPE
       SYNTAX  DisplayString
       ACCESS  read-only
       STATUS  mandatory
       DESCRIPTION
       "The maximum reading since the last reset."
       ::=  {  ap5IISPolledCounterDispEntry 14   }

   ap5IISDispAverage OBJECT-TYPE
       SYNTAX  DisplayString
       ACCESS  read-only
       STATUS  mandatory
       DESCRIPTION
       "The average reading since the last reset."
       ::=  {  ap5IISPolledCounterDispEntry 15   }

   ap5IISDispStdDev OBJECT-TYPE
       SYNTAX  DisplayString
       ACCESS  read-only
       STATUS  mandatory
       DESCRIPTION
       "The standard deviation based on the last 100 readings."
       ::=  {  ap5IISPolledCounterDispEntry 16   }

   ap5IISDispValueReported OBJECT-TYPE
       SYNTAX  INTEGER {
			summary(1),
			average(2),
			vhost(3)
		       }
       ACCESS  read-write
       STATUS  mandatory
       DESCRIPTION
       "The reported value of the counter is either a summary or average of all servers."
       ::=  {  ap5IISPolledCounterDispEntry 17 }
		
   ap5IISDispLagSetting OBJECT-TYPE
	SYNTAX  INTEGER
	ACCESS  read-write
	STATUS  mandatory
	DESCRIPTION
	"Lag setting for the counter."
	::=  {  ap5IISPolledCounterDispEntry 18   }
	
   ap5IISDispLagValue OBJECT-TYPE
	SYNTAX  INTEGER
	ACCESS  read-only
	STATUS  mandatory
	DESCRIPTION
	"Current Lag value for the counter."
	::=  {  ap5IISPolledCounterDispEntry 19   }


--******************************************************************************
--*  Traps                                                                     *
--******************************************************************************

    statusNormal TRAP-TYPE
        ENTERPRISE ap5Agent
        DESCRIPTION "Set status to normal"
        ::= 1

    statusWarning TRAP-TYPE
        ENTERPRISE ap5Agent
        DESCRIPTION "Set status to warning"
        ::= 2

    statusCritical TRAP-TYPE
        ENTERPRISE ap5Agent
        DESCRIPTION "Set status to critical"
        ::= 3

    statusDetailTrap TRAP-TYPE
        ENTERPRISE ap5Agent
--        VARIABLES   {szStatus}
        DESCRIPTION "Status of group or table (row) changed"
        ::= 4
END
