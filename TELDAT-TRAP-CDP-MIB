-- file automatically created


TELDAT-TRAP-CDP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


cdpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the CDP event subsystem."
    REVISION "201401200930Z"
    DESCRIPTION "Initial implementation"
        ::= { telEventTraps 216 }


cdpEventsGroup	OBJECT IDENTIFIER	::= { cdpTrapsMIB 1 }

cdpNotifications	OBJECT IDENTIFIER	::= { cdpTrapsMIB 2 }
cdpNotificationsPrefix	OBJECT IDENTIFIER	::= { cdpNotifications 0 }

cdpEventObjects1 OBJECT-IDENTITY
    STATUS current
    DESCRIPTION
        "Event CDP.1
        A CDP packet has been sent on the specified interface."
    ::= { cdpEventsGroup 1 }

cdp1_interface OBJECT-TYPE
    SYNTAX DisplayString
    MAX-ACCESS accessible-for-notify
    STATUS current
    DESCRIPTION
        "Parameter 'interface' in event CDP.1"
    ::= { cdpEventObjects1 1 }

cdpEventObjects3 OBJECT-IDENTITY
    STATUS current
    DESCRIPTION
        "Event CDP.3
        A CDP packet can not be sent because of lack of buffers."
    ::= { cdpEventsGroup 3 }

cdp3_interface OBJECT-TYPE
    SYNTAX DisplayString
    MAX-ACCESS accessible-for-notify
    STATUS current
    DESCRIPTION
        "Parameter 'interface' in event CDP.3"
    ::= { cdpEventObjects3 1 }

cdpEventObjects4 OBJECT-IDENTITY
    STATUS current
    DESCRIPTION
        "Event CDP.4
        A packet was not send because of errors in the outgoing interface."
    ::= { cdpEventsGroup 4 }

cdp4_interface OBJECT-TYPE
    SYNTAX DisplayString
    MAX-ACCESS accessible-for-notify
    STATUS current
    DESCRIPTION
        "Parameter 'interface' in event CDP.4"
    ::= { cdpEventObjects4 1 }

cdpEventObjects5 OBJECT-IDENTITY
    STATUS current
    DESCRIPTION
        "Event CDP.5
        Generic encapsulation error."
    ::= { cdpEventsGroup 5 }

cdp5_error_string OBJECT-TYPE
    SYNTAX DisplayString
    MAX-ACCESS accessible-for-notify
    STATUS current
    DESCRIPTION
        "Parameter 'error_string' in event CDP.5"
    ::= { cdpEventObjects5 1 }

cdp5_interface OBJECT-TYPE
    SYNTAX DisplayString
    MAX-ACCESS accessible-for-notify
    STATUS current
    DESCRIPTION
        "Parameter 'interface' in event CDP.5"
    ::= { cdpEventObjects5 2 }

cdpEventObjects6 OBJECT-IDENTITY
    STATUS current
    DESCRIPTION
        "Event CDP.6
        A CDP packet has been sent."
    ::= { cdpEventsGroup 6 }

cdp6_interface OBJECT-TYPE
    SYNTAX DisplayString
    MAX-ACCESS accessible-for-notify
    STATUS current
    DESCRIPTION
        "Parameter 'interface' in event CDP.6"
    ::= { cdpEventObjects6 1 }


cdpNotification1 NOTIFICATION-TYPE
    OBJECTS { 
              cdp1_interface 
            }
    STATUS current
    DESCRIPTION
        "Notification of Event CDP.1

        Message: 'Sending CDP packet on ifc $1'

        Parameters list:
              $1: cdp1_interface

        A CDP packet has been sent on the specified interface."
    ::= { cdpNotificationsPrefix 1 }

cdpNotification2 NOTIFICATION-TYPE
    STATUS current
    DESCRIPTION
        "Notification of Event CDP.2

        Message: 'Not enough memory to initialize CDP system'

        The CDP system can not be initialized because of lack of memory."
    ::= { cdpNotificationsPrefix 2 }

cdpNotification3 NOTIFICATION-TYPE
    OBJECTS { 
              cdp3_interface 
            }
    STATUS current
    DESCRIPTION
        "Notification of Event CDP.3

        Message: 'No buffer to send CDP packet on ifc $1'

        Parameters list:
              $1: cdp3_interface

        A CDP packet can not be sent because of lack of buffers."
    ::= { cdpNotificationsPrefix 3 }

cdpNotification4 NOTIFICATION-TYPE
    OBJECTS { 
              cdp4_interface 
            }
    STATUS current
    DESCRIPTION
        "Notification of Event CDP.4

        Message: 'error sending packet on interface $1'

        Parameters list:
              $1: cdp4_interface

        A packet was not send because of errors in the outgoing interface."
    ::= { cdpNotificationsPrefix 4 }

cdpNotification5 NOTIFICATION-TYPE
    OBJECTS { 
              cdp5_error_string, 
              cdp5_interface 
            }
    STATUS current
    DESCRIPTION
        "Notification of Event CDP.5

        Message: '$1 on interface $2'

        Parameters list:
              $1: cdp5_error_string
              $2: cdp5_interface

        Generic encapsulation error."
    ::= { cdpNotificationsPrefix 5 }

cdpNotification6 NOTIFICATION-TYPE
    OBJECTS { 
              cdp6_interface 
            }
    STATUS current
    DESCRIPTION
        "Notification of Event CDP.6

        Message: 'CDP packet sent on interface $1'

        Parameters list:
              $1: cdp6_interface

        A CDP packet has been sent."
    ::= { cdpNotificationsPrefix 6 }


END
