IBM-SYSTEM-TRAP-MIB DEFINITIONS ::= BEGIN

IMPORTS
   OBJECT-TYPE
      FROM RFC-1212

   TRAP-TYPE
      FROM RFC-1215

   ibmSystemTrap, ibmSystemMIB,
   Boolean, Uint8, Sint8, Uint16, Sint16, Uint32,
   Sint32, Uint64, Sint64, Real32, Real64, String, Datetime
      FROM IBM-SYSTEM-MIB
   SnmpAdminString
      FROM SNMP-FRAMEWORK-MIB;

--
-- Primitive types
--
Boolean  ::= INTEGER (0..1)
Uint8    ::= INTEGER (0..255)
Sint8    ::= INTEGER (-128..127)
Uint16   ::= INTEGER (0..65535)
Sint16   ::= INTEGER (-32767..32766)
Uint32   ::= INTEGER (0..4294967295)
Sint32   ::= INTEGER (-2147483647..2147483646)
Uint64   ::= OCTET STRING
Sint64   ::= OCTET STRING
Real32   ::= INTEGER (-1..1)
Real64   ::= INTEGER (-1..1)
String   ::= OCTET STRING
Datetime ::= OCTET STRING


ibmSystemTrapTemperature TRAP-TYPE
   ENTERPRISE     ibmSystemMIB
   VARIABLES    {
      ibmSystemTrapTemperatureProviderName,
      ibmSystemTrapTemperatureEventID,
      ibmSystemTrapTemperatureAlertingManagedElement,
      ibmSystemTrapTemperatureSeverity,
      ibmSystemTrapTemperatureDescription,
      ibmSystemTrapTemperatureTimeStamp
   }
   DESCRIPTION    "This event is sent when the state of a system's temperature sensor changes
                   with respect to a manufacturer-defined and/or user-defined threshold."
   REFERENCE      "IBMPSG_Temperature"
::= 2

ibmSystemTrapTemperatureBindings OBJECT IDENTIFIER ::= { ibmSystemTrap 2 }

ibmSystemTrapTemperatureProviderName OBJECT-TYPE
   SYNTAX         String
   ACCESS         read-write
   STATUS         mandatory
   DESCRIPTION    ""
   REFERENCE      "IBMPSG_Temperature.ProviderName"
::= { ibmSystemTrapTemperatureBindings 1 }

ibmSystemTrapTemperatureEventID OBJECT-TYPE
   SYNTAX         String
   ACCESS         read-write
   STATUS         mandatory
   DESCRIPTION    ""
   REFERENCE      "IBMPSG_Temperature.EventID"
::= { ibmSystemTrapTemperatureBindings 2 }

ibmSystemTrapTemperatureAlertingManagedElement OBJECT-TYPE
   SYNTAX         String
   ACCESS         read-write
   STATUS         mandatory
   DESCRIPTION    ""
   REFERENCE      "IBMPSG_Temperature.AlertingManagedElement"
::= { ibmSystemTrapTemperatureBindings 3 }

ibmSystemTrapTemperatureSeverity OBJECT-TYPE
   SYNTAX         Uint16
   ACCESS         read-write
   STATUS         mandatory
   DESCRIPTION    "1=Warning -- The temperature has exceeded a user-defined or manufacturer-defined warning level thresold
                   2=Critical -- The temperature has exceeded a user-defined or manufacturer-defined critical threshold"
   REFERENCE      "IBMPSG_Temperature.Severity"
::= { ibmSystemTrapTemperatureBindings 4 }

ibmSystemTrapTemperatureDescription OBJECT-TYPE
   SYNTAX         SnmpAdminString
   ACCESS         read-write
   STATUS         mandatory
   DESCRIPTION    ""
   REFERENCE      "IBMPSG_Temperature.Description"
::= { ibmSystemTrapTemperatureBindings 5 }

ibmSystemTrapTemperatureTimeStamp OBJECT-TYPE
   SYNTAX         Datetime
   ACCESS         read-write
   STATUS         mandatory
   DESCRIPTION    ""
   REFERENCE      "IBMPSG_Temperature.TimeStamp"
::= { ibmSystemTrapTemperatureBindings 6 }

ibmSystemTrapVoltage TRAP-TYPE
   ENTERPRISE     ibmSystemMIB
   VARIABLES    {
      ibmSystemTrapVoltageProviderName,
      ibmSystemTrapVoltageEventID,
      ibmSystemTrapVoltageAlertingManagedElement,
      ibmSystemTrapVoltageSeverity,
      ibmSystemTrapVoltageDescription,
      ibmSystemTrapVoltageTimeStamp
   }
   DESCRIPTION    "This event is sent when the state of a system's voltage sensor changes
                   with respect to a manufacturer-defined threshold."
   REFERENCE      "IBMPSG_Voltage"
::= 3

ibmSystemTrapVoltageBindings OBJECT IDENTIFIER ::= { ibmSystemTrap 3 }

ibmSystemTrapVoltageProviderName OBJECT-TYPE
   SYNTAX         String
   ACCESS         read-write
   STATUS         mandatory
   DESCRIPTION    ""
   REFERENCE      "IBMPSG_Voltage.ProviderName"
::= { ibmSystemTrapVoltageBindings 1 }

ibmSystemTrapVoltageEventID OBJECT-TYPE
   SYNTAX         String
   ACCESS         read-write
   STATUS         mandatory
   DESCRIPTION    ""
   REFERENCE      "IBMPSG_Voltage.EventID"
::= { ibmSystemTrapVoltageBindings 2 }

ibmSystemTrapVoltageAlertingManagedElement OBJECT-TYPE
   SYNTAX         String
   ACCESS         read-write
   STATUS         mandatory
   DESCRIPTION    ""
   REFERENCE      "IBMPSG_Voltage.AlertingManagedElement"
::= { ibmSystemTrapVoltageBindings 3 }

ibmSystemTrapVoltageSeverity OBJECT-TYPE
   SYNTAX         Uint16
   ACCESS         read-write
   STATUS         mandatory
   DESCRIPTION    "1=Warning -- The voltage has exceeded a manufacturer-defined warning level thresold
                   2=Critical -- The voltage has exceeded a manufacturer-defined critical threshold"
   REFERENCE      "IBMPSG_Voltage.Severity"
::= { ibmSystemTrapVoltageBindings 4 }

ibmSystemTrapVoltageDescription OBJECT-TYPE
   SYNTAX         SnmpAdminString
   ACCESS         read-write
   STATUS         mandatory
   DESCRIPTION    ""
   REFERENCE      "IBMPSG_Voltage.Description"
::= { ibmSystemTrapVoltageBindings 5 }

ibmSystemTrapVoltageTimeStamp OBJECT-TYPE
   SYNTAX         Datetime
   ACCESS         read-write
   STATUS         mandatory
   DESCRIPTION    ""
   REFERENCE      "IBMPSG_Voltage.TimeStamp"
::= { ibmSystemTrapVoltageBindings 6 }

ibmSystemTrapChassis TRAP-TYPE
   ENTERPRISE     ibmSystemMIB
   VARIABLES    {
      ibmSystemTrapChassisProviderName,
      ibmSystemTrapChassisEventID,
      ibmSystemTrapChassisAlertingManagedElement,
      ibmSystemTrapChassisSeverity,
      ibmSystemTrapChassisDescription,
      ibmSystemTrapChassisTimeStamp
   }
   DESCRIPTION    "This event is sent when the state of a system's chassis has changed."
   REFERENCE      "IBMPSG_Chassis"
::= 4

ibmSystemTrapChassisBindings OBJECT IDENTIFIER ::= { ibmSystemTrap 4 }

ibmSystemTrapChassisProviderName OBJECT-TYPE
   SYNTAX         String
   ACCESS         read-write
   STATUS         mandatory
   DESCRIPTION    ""
   REFERENCE      "IBMPSG_Chassis.ProviderName"
::= { ibmSystemTrapChassisBindings 1 }

ibmSystemTrapChassisEventID OBJECT-TYPE
   SYNTAX         String
   ACCESS         read-write
   STATUS         mandatory
   DESCRIPTION    ""
   REFERENCE      "IBMPSG_Chassis.EventID"
::= { ibmSystemTrapChassisBindings 2 }

ibmSystemTrapChassisAlertingManagedElement OBJECT-TYPE
   SYNTAX         String
   ACCESS         read-write
   STATUS         mandatory
   DESCRIPTION    ""
   REFERENCE      "IBMPSG_Chassis.AlertingManagedElement"
::= { ibmSystemTrapChassisBindings 3 }

ibmSystemTrapChassisSeverity OBJECT-TYPE
   SYNTAX         Uint16
   ACCESS         read-write
   STATUS         mandatory
   DESCRIPTION    "2=Critical -- The system's cover has been removed"
   REFERENCE      "IBMPSG_Chassis.Severity"
::= { ibmSystemTrapChassisBindings 4 }

ibmSystemTrapChassisDescription OBJECT-TYPE
   SYNTAX         SnmpAdminString
   ACCESS         read-write
   STATUS         mandatory
   DESCRIPTION    ""
   REFERENCE      "IBMPSG_Chassis.Description"
::= { ibmSystemTrapChassisBindings 5 }

ibmSystemTrapChassisTimeStamp OBJECT-TYPE
   SYNTAX         Datetime
   ACCESS         read-write
   STATUS         mandatory
   DESCRIPTION    ""
   REFERENCE      "IBMPSG_Chassis.TimeStamp"
::= { ibmSystemTrapChassisBindings 6 }

ibmSystemTrapFan TRAP-TYPE
   ENTERPRISE     ibmSystemMIB
   VARIABLES    {
      ibmSystemTrapFanProviderName,
      ibmSystemTrapFanEventID,
      ibmSystemTrapFanAlertingManagedElement,
      ibmSystemTrapFanSeverity,
      ibmSystemTrapFanDescription,
      ibmSystemTrapFanTimeStamp
   }
   DESCRIPTION    "This event is sent when state of a system's fan has changed with respect to
                   manufacturer-defined rpm values."
   REFERENCE      "IBMPSG_Fan"
::=  5

ibmSystemTrapFanBindings OBJECT IDENTIFIER ::= { ibmSystemTrap 5 }

ibmSystemTrapFanProviderName OBJECT-TYPE
   SYNTAX         String
   ACCESS         read-write
   STATUS         mandatory
   DESCRIPTION    ""
   REFERENCE      "IBMPSG_Fan.ProviderName"
::= { ibmSystemTrapFanBindings 1 }

ibmSystemTrapFanEventID OBJECT-TYPE
   SYNTAX         String
   ACCESS         read-write
   STATUS         mandatory
   DESCRIPTION    ""
   REFERENCE      "IBMPSG_Fan.EventID"
::= { ibmSystemTrapFanBindings 2 }

ibmSystemTrapFanAlertingManagedElement OBJECT-TYPE
   SYNTAX         String
   ACCESS         read-write
   STATUS         mandatory
   DESCRIPTION    ""
   REFERENCE      "IBMPSG_Fan.AlertingManagedElement"
::= { ibmSystemTrapFanBindings 3 }

ibmSystemTrapFanSeverity OBJECT-TYPE
   SYNTAX         Uint16
   ACCESS         read-write
   STATUS         mandatory
   DESCRIPTION    "2=Critical -- The fan has stopped."
   REFERENCE      "IBMPSG_Fan.Severity"
::= { ibmSystemTrapFanBindings 4 }

ibmSystemTrapFanDescription OBJECT-TYPE
   SYNTAX         SnmpAdminString
   ACCESS         read-write
   STATUS         mandatory
   DESCRIPTION    ""
   REFERENCE      "IBMPSG_Fan.Description"
::= { ibmSystemTrapFanBindings 5 }

ibmSystemTrapFanTimeStamp OBJECT-TYPE
   SYNTAX         Datetime
   ACCESS         read-write
   STATUS         mandatory
   DESCRIPTION    ""
   REFERENCE      "IBMPSG_Fan.TimeStamp"
::= { ibmSystemTrapFanBindings 6 }

ibmSystemTrapStorage TRAP-TYPE
   ENTERPRISE     ibmSystemMIB
   VARIABLES    {
      ibmSystemTrapStorageProviderName,
      ibmSystemTrapStorageEventID,
      ibmSystemTrapStorageAlertingManagedElement,
      ibmSystemTrapStorageSeverity,
      ibmSystemTrapStorageDescription,
      ibmSystemTrapStorageTimeStamp
   }
   DESCRIPTION    "On systems with no Remote Supervisor Adapter, this event is sent when the 
                   state of a system's hard drive space has changed with respect to user-defined 
                   levels of percentage hard drive space remaining.
                   On systems with a Remote Supervisor Adapter, this event is sent when the
                   system has experienced a DASD controller failure."
   REFERENCE      "IBMPSG_Storage"
::= 7

ibmSystemTrapStorageBindings OBJECT IDENTIFIER ::= { ibmSystemTrap 7 }

ibmSystemTrapStorageProviderName OBJECT-TYPE
   SYNTAX         String
   ACCESS         read-write
   STATUS         mandatory
   DESCRIPTION    ""
   REFERENCE      "IBMPSG_Storage.ProviderName"
::= { ibmSystemTrapStorageBindings 1 }

ibmSystemTrapStorageEventID OBJECT-TYPE
   SYNTAX         String
   ACCESS         read-write
   STATUS         mandatory
   DESCRIPTION    ""
   REFERENCE      "IBMPSG_Storage.EventID"
::= { ibmSystemTrapStorageBindings 2 }

ibmSystemTrapStorageAlertingManagedElement OBJECT-TYPE
   SYNTAX         String
   ACCESS         read-write
   STATUS         mandatory
   DESCRIPTION    ""
   REFERENCE      "IBMPSG_Storage.AlertingManagedElement"
::= { ibmSystemTrapStorageBindings 3 }

ibmSystemTrapStorageSeverity OBJECT-TYPE
   SYNTAX         Uint16
   ACCESS         read-write
   STATUS         mandatory
   DESCRIPTION    "1=Warning -- Percentage hard drive space remaining has fallen below user-defined Warning level threshold.
                   2=Critical -- Percentage hard drive space remaining has fallen below user-defined Critical level threshold.
                              -- On systems with Remote Supervisor Adapter, DASD Controller failure."
   REFERENCE      "IBMPSG_Storage.Severity"
::= { ibmSystemTrapStorageBindings 4 }

ibmSystemTrapStorageDescription OBJECT-TYPE
   SYNTAX         SnmpAdminString
   ACCESS         read-write
   STATUS         mandatory
   DESCRIPTION    ""
   REFERENCE      "IBMPSG_Storage.Description"
::= { ibmSystemTrapStorageBindings 5 }

ibmSystemTrapStorageTimeStamp OBJECT-TYPE
   SYNTAX         Datetime
   ACCESS         read-write
   STATUS         mandatory
   DESCRIPTION    ""
   REFERENCE      "IBMPSG_Storage.TimeStamp"
::= { ibmSystemTrapStorageBindings 6 }

ibmSystemTrapSMART TRAP-TYPE
   ENTERPRISE     ibmSystemMIB
   VARIABLES    {
      ibmSystemTrapSMARTProviderName,
      ibmSystemTrapSMARTEventID,
      ibmSystemTrapSMARTAlertingManagedElement,
      ibmSystemTrapSMARTSeverity,
      ibmSystemTrapSMARTDescription,
      ibmSystemTrapSMARTTimeStamp
   }
   DESCRIPTION    "This event is sent when the state of an IDE or SCSI hard drive that complies with the
                  Self-Monitoring, Analysis, and Reporting Technology changes with respect to
                  its availability."
   REFERENCE      "IBMPSG_SMART"
::= 9

ibmSystemTrapSMARTBindings OBJECT IDENTIFIER ::= { ibmSystemTrap 9 }

ibmSystemTrapSMARTProviderName OBJECT-TYPE
   SYNTAX         String
   ACCESS         read-write
   STATUS         mandatory
   DESCRIPTION    ""
   REFERENCE      "IBMPSG_SMART.ProviderName"
::= { ibmSystemTrapSMARTBindings 1 }

ibmSystemTrapSMARTEventID OBJECT-TYPE
   SYNTAX         String
   ACCESS         read-write
   STATUS         mandatory
   DESCRIPTION    ""
   REFERENCE      "IBMPSG_SMART.EventID"
::= { ibmSystemTrapSMARTBindings 2 }

ibmSystemTrapSMARTAlertingManagedElement OBJECT-TYPE
   SYNTAX         String
   ACCESS         read-write
   STATUS         mandatory
   DESCRIPTION    ""
   REFERENCE      "IBMPSG_SMART.AlertingManagedElement"
::= { ibmSystemTrapSMARTBindings 3 }

ibmSystemTrapSMARTSeverity OBJECT-TYPE
   SYNTAX         Uint16
   ACCESS         read-write
   STATUS         mandatory
   DESCRIPTION    "2=Critical - The hard drive is experiencing an imminent failure."
   REFERENCE      "IBMPSG_SMART.Severity"
::= { ibmSystemTrapSMARTBindings 4 }

ibmSystemTrapSMARTDescription OBJECT-TYPE
   SYNTAX         SnmpAdminString
   ACCESS         read-write
   STATUS         mandatory
   DESCRIPTION    ""
   REFERENCE      "IBMPSG_SMART.Description"
::= { ibmSystemTrapSMARTBindings 5 }

ibmSystemTrapSMARTTimeStamp OBJECT-TYPE
   SYNTAX         Datetime
   ACCESS         read-write
   STATUS         mandatory
   DESCRIPTION    ""
   REFERENCE      "IBMPSG_SMART.TimeStamp"
::= { ibmSystemTrapSMARTBindings 6 }

ibmSystemTrapLeaseExpiration TRAP-TYPE
   ENTERPRISE     ibmSystemMIB
   VARIABLES    {
      ibmSystemTrapLeaseExpirationProviderName,
      ibmSystemTrapLeaseExpirationEventID,
      ibmSystemTrapLeaseExpirationAlertingManagedElement,
      ibmSystemTrapLeaseExpirationSeverity,
      ibmSystemTrapLeaseExpirationDescription,
      ibmSystemTrapLeaseExpirationTimeStamp
   }
   DESCRIPTION    "This event is sent when a system's Lease Expiration date has been reached
                   with respect to the value configured for the date in the Asset ID tool."
   REFERENCE      "IBMPSG_LeaseExpiration"
::= 13

ibmSystemTrapLeaseExpirationBindings OBJECT IDENTIFIER ::= { ibmSystemTrap 13 }

ibmSystemTrapLeaseExpirationProviderName OBJECT-TYPE
   SYNTAX         String
   ACCESS         read-write
   STATUS         mandatory
   DESCRIPTION    ""
   REFERENCE      "IBMPSG_LeaseExpiration.ProviderName"
::= { ibmSystemTrapLeaseExpirationBindings 1 }

ibmSystemTrapLeaseExpirationEventID OBJECT-TYPE
   SYNTAX         String
   ACCESS         read-write
   STATUS         mandatory
   DESCRIPTION    ""
   REFERENCE      "IBMPSG_LeaseExpiration.EventID"
::= { ibmSystemTrapLeaseExpirationBindings 2 }

ibmSystemTrapLeaseExpirationAlertingManagedElement OBJECT-TYPE
   SYNTAX         String
   ACCESS         read-write
   STATUS         mandatory
   DESCRIPTION    ""
   REFERENCE      "IBMPSG_LeaseExpiration.AlertingManagedElement"
::= { ibmSystemTrapLeaseExpirationBindings 3 }

ibmSystemTrapLeaseExpirationSeverity OBJECT-TYPE
   SYNTAX         Uint16
   ACCESS         read-write
   STATUS         mandatory
   DESCRIPTION    "1=Warning -- The system's lease has expired."
   REFERENCE      "IBMPSG_LeaseExpiration.Severity"
::= { ibmSystemTrapLeaseExpirationBindings 4 }

ibmSystemTrapLeaseExpirationDescription OBJECT-TYPE
   SYNTAX         SnmpAdminString
   ACCESS         read-write
   STATUS         mandatory
   DESCRIPTION    ""
   REFERENCE      "IBMPSG_LeaseExpiration.Description"
::= { ibmSystemTrapLeaseExpirationBindings 5 }

ibmSystemTrapLeaseExpirationTimeStamp OBJECT-TYPE
   SYNTAX         Datetime
   ACCESS         read-write
   STATUS         mandatory
   DESCRIPTION    ""
   REFERENCE      "IBMPSG_LeaseExpiration.TimeStamp"
::= { ibmSystemTrapLeaseExpirationBindings 6 }

ibmSystemTrapWarrantyExpiration TRAP-TYPE
   ENTERPRISE     ibmSystemMIB
   VARIABLES    {
      ibmSystemTrapWarrantyExpirationProviderName,
      ibmSystemTrapWarrantyExpirationEventID,
      ibmSystemTrapWarrantyExpirationAlertingManagedElement,
      ibmSystemTrapWarrantyExpirationSeverity,
      ibmSystemTrapWarrantyExpirationDescription,
      ibmSystemTrapWarrantyExpirationTimeStamp
   }
   DESCRIPTION    "This event is sent when a system's Warranty Expiration date has been reached
                   with respect to the value configured for the date in the Asset ID tool."
   REFERENCE      "IBMPSG_WarrantyExpiration"
::= 14

ibmSystemTrapWarrantyExpirationBindings OBJECT IDENTIFIER ::= { ibmSystemTrap 14 }

ibmSystemTrapWarrantyExpirationProviderName OBJECT-TYPE
   SYNTAX         String
   ACCESS         read-write
   STATUS         mandatory
   DESCRIPTION    ""
   REFERENCE      "IBMPSG_WarrantyExpiration.ProviderName"
::= { ibmSystemTrapWarrantyExpirationBindings 1 }

ibmSystemTrapWarrantyExpirationEventID OBJECT-TYPE
   SYNTAX         String
   ACCESS         read-write
   STATUS         mandatory
   DESCRIPTION    ""
   REFERENCE      "IBMPSG_WarrantyExpiration.EventID"
::= { ibmSystemTrapWarrantyExpirationBindings 2 }

ibmSystemTrapWarrantyExpirationAlertingManagedElement OBJECT-TYPE
   SYNTAX         String
   ACCESS         read-write
   STATUS         mandatory
   DESCRIPTION    ""
   REFERENCE      "IBMPSG_WarrantyExpiration.AlertingManagedElement"
::= { ibmSystemTrapWarrantyExpirationBindings 3 }

ibmSystemTrapWarrantyExpirationSeverity OBJECT-TYPE
   SYNTAX         Uint16
   ACCESS         read-write
   STATUS         mandatory
   DESCRIPTION    "1=Warning -- The system's warranty has expired."
   REFERENCE      "IBMPSG_WarrantyExpiration.Severity"
::= { ibmSystemTrapWarrantyExpirationBindings 4 }

ibmSystemTrapWarrantyExpirationDescription OBJECT-TYPE
   SYNTAX         SnmpAdminString
   ACCESS         read-write
   STATUS         mandatory
   DESCRIPTION    ""
   REFERENCE      "IBMPSG_WarrantyExpiration.Description"
::= { ibmSystemTrapWarrantyExpirationBindings 5 }

ibmSystemTrapWarrantyExpirationTimeStamp OBJECT-TYPE
   SYNTAX         Datetime
   ACCESS         read-write
   STATUS         mandatory
   DESCRIPTION    ""
   REFERENCE      "IBMPSG_WarrantyExpiration.TimeStamp"
::= { ibmSystemTrapWarrantyExpirationBindings 6 }

ibmSystemTrapRedundantNIC TRAP-TYPE
   ENTERPRISE     ibmSystemMIB
   VARIABLES    {
      ibmSystemTrapRedundantNICProviderName,
      ibmSystemTrapRedundantNICEventID,
      ibmSystemTrapRedundantNICAlertingManagedElement,
      ibmSystemTrapRedundantNICSeverity,
      ibmSystemTrapRedundantNICDescription,
      ibmSystemTrapRedundantNICTimeStamp
   }
   DESCRIPTION	"This event is sent when the state of a system's NIC changes state with
                   respect to redundancy, but due to a limitation of the capabilities of
                   the NIC, a determination could not be made between a switchover and
                   a switchback."
   REFERENCE	"IBMPSG_RedundantNIC"
::= 15

ibmSystemTrapRedundantNICBindings OBJECT IDENTIFIER ::= { ibmSystemTrap 15 }

ibmSystemTrapRedundantNICProviderName OBJECT-TYPE
   SYNTAX         String
   ACCESS         read-write
   STATUS         mandatory
   DESCRIPTION    ""
   REFERENCE	  "IBMPSG_RedundantNIC.ProviderName"
::= { ibmSystemTrapRedundantNICBindings 1 }

ibmSystemTrapRedundantNICEventID OBJECT-TYPE
   SYNTAX         String
   ACCESS         read-write
   STATUS         mandatory
   DESCRIPTION    ""
   REFERENCE	  "IBMPSG_RedundantNIC.EventID"
::= { ibmSystemTrapRedundantNICBindings 2 }

ibmSystemTrapRedundantNICAlertingManagedElement OBJECT-TYPE
   SYNTAX         String
   ACCESS         read-write
   STATUS         mandatory
   DESCRIPTION    ""
   REFERENCE	  "IBMPSG_RedundantNIC.AlertingManagedElement"
::= { ibmSystemTrapRedundantNICBindings 3 }

ibmSystemTrapRedundantNICSeverity OBJECT-TYPE
   SYNTAX         Uint16
   ACCESS         read-write
   STATUS         mandatory
   DESCRIPTION    "1=Warning -- A redundant NIC event occurred."
   REFERENCE	  "IBMPSG_RedundantNIC.Severity"
::= { ibmSystemTrapRedundantNICBindings 4 }

ibmSystemTrapRedundantNICDescription OBJECT-TYPE
   SYNTAX         SnmpAdminString
   ACCESS         read-write
   STATUS         mandatory
   DESCRIPTION    ""
   REFERENCE	  "IBMPSG_RedundantNIC.Description"
::= { ibmSystemTrapRedundantNICBindings 5 }

ibmSystemTrapRedundantNICTimeStamp OBJECT-TYPE
   SYNTAX         Datetime
   ACCESS         read-write
   STATUS         mandatory
   DESCRIPTION    ""
   REFERENCE	  "IBMPSG_RedundantNIC.TimeStamp"
::= { ibmSystemTrapRedundantNICBindings 6 }

ibmSystemTrapRedundantNICSwitchover TRAP-TYPE
   ENTERPRISE     ibmSystemMIB
   VARIABLES    {
      ibmSystemTrapRedundantNICSwitchoverProviderName,
      ibmSystemTrapRedundantNICSwitchoverEventID,
      ibmSystemTrapRedundantNICSwitchoverAlertingManagedElement,
      ibmSystemTrapRedundantNICSwitchoverSeverity,
      ibmSystemTrapRedundantNICSwitchoverDescription,
      ibmSystemTrapRedundantNICSwitchoverTimeStamp
   }
   DESCRIPTION	"This event is sent when the active NIC in a system changes by failing over
                   to a redundant NIC."
   REFERENCE	"IBMPSG_RedundantNICSwitchover"
::= 16

ibmSystemTrapRedundantNICSwitchoverBindings OBJECT IDENTIFIER ::= { ibmSystemTrap 16 }

ibmSystemTrapRedundantNICSwitchoverProviderName OBJECT-TYPE
   SYNTAX         String
   ACCESS         read-write
   STATUS         mandatory
   DESCRIPTION    ""
   REFERENCE	  "IBMPSG_RedundantNIC.ProviderName"
::= { ibmSystemTrapRedundantNICSwitchoverBindings 1 }

ibmSystemTrapRedundantNICSwitchoverEventID OBJECT-TYPE
   SYNTAX         String
   ACCESS         read-write
   STATUS         mandatory
   DESCRIPTION    ""
   REFERENCE	  "IBMPSG_RedundantNICSwitchover.EventID"
::= { ibmSystemTrapRedundantNICSwitchoverBindings 2 }

ibmSystemTrapRedundantNICSwitchoverAlertingManagedElement OBJECT-TYPE
   SYNTAX         String
   ACCESS         read-write
   STATUS         mandatory
   DESCRIPTION    ""
   REFERENCE	  "IBMPSG_RedundantNICSwitchover.AlertingManagedElement"
::= { ibmSystemTrapRedundantNICSwitchoverBindings 3 }

ibmSystemTrapRedundantNICSwitchoverSeverity OBJECT-TYPE
   SYNTAX         Uint16
   ACCESS         read-write
   STATUS         mandatory
   DESCRIPTION    "1=Warning -- A failing NIC switched over to a redundant NIC."
   REFERENCE	  "IBMPSG_RedundantNICSwitchover.Severity"
::= { ibmSystemTrapRedundantNICSwitchoverBindings 4 }

ibmSystemTrapRedundantNICSwitchoverDescription OBJECT-TYPE
   SYNTAX         SnmpAdminString
   ACCESS         read-write
   STATUS         mandatory
   DESCRIPTION    ""
   REFERENCE	  "IBMPSG_RedundantNICSwitchover.Description"
::= { ibmSystemTrapRedundantNICSwitchoverBindings 5 }

ibmSystemTrapRedundantNICSwitchoverTimeStamp OBJECT-TYPE
   SYNTAX         Datetime
   ACCESS         read-write
   STATUS         mandatory
   DESCRIPTION    ""
   REFERENCE	  "IBMPSG_RedundantNICSwitchover.TimeStamp"
::= { ibmSystemTrapRedundantNICSwitchoverBindings 6 }

ibmSystemTrapRedundantNICSwitchback TRAP-TYPE
   ENTERPRISE     ibmSystemMIB
   VARIABLES    {
      ibmSystemTrapRedundantNICSwitchbackProviderName,
      ibmSystemTrapRedundantNICSwitchbackEventID,
      ibmSystemTrapRedundantNICSwitchbackAlertingManagedElement,
      ibmSystemTrapRedundantNICSwitchbackSeverity,
      ibmSystemTrapRedundantNICSwitchbackDescription,
      ibmSystemTrapRedundantNICSwitchbackTimeStamp
   }
   DESCRIPTION	"This event is sent when the active NIC in a system changes due
                   to a recovery from a redundant NIC."
   REFERENCE	"IBMPSG_RedundantNICSwitchback"
::= 17

ibmSystemTrapRedundantNICSwitchbackBindings OBJECT IDENTIFIER ::= { ibmSystemTrap 17 }

ibmSystemTrapRedundantNICSwitchbackProviderName OBJECT-TYPE
   SYNTAX         String
   ACCESS         read-write
   STATUS         mandatory
   DESCRIPTION    ""
   REFERENCE	  "IBMPSG_RedundantNICSwitchback.ProviderName"
::= { ibmSystemTrapRedundantNICSwitchbackBindings 1 }

ibmSystemTrapRedundantNICSwitchbackEventID OBJECT-TYPE
   SYNTAX         String
   ACCESS         read-write
   STATUS         mandatory
   DESCRIPTION    ""
   REFERENCE	  "IBMPSG_RedundantNICSwitchback.EventID"
::= { ibmSystemTrapRedundantNICSwitchbackBindings 2 }

ibmSystemTrapRedundantNICSwitchbackAlertingManagedElement OBJECT-TYPE
   SYNTAX         String
   ACCESS         read-write
   STATUS         mandatory
   DESCRIPTION    ""
   REFERENCE	  "IBMPSG_RedundantNICSwitchback.AlertingManagedElement"
::= { ibmSystemTrapRedundantNICSwitchbackBindings 3 }

ibmSystemTrapRedundantNICSwitchbackSeverity OBJECT-TYPE
   SYNTAX         Uint16
   ACCESS         read-write
   STATUS         mandatory
   DESCRIPTION    "1=Warning -- The system's NIC has recovered and switched back, re-instating redundancy."
   REFERENCE	  "IBMPSG_RedundantNICSwitchback.Severity"
::= { ibmSystemTrapRedundantNICSwitchbackBindings 4 }

ibmSystemTrapRedundantNICSwitchbackDescription OBJECT-TYPE
   SYNTAX         SnmpAdminString
   ACCESS         read-write
   STATUS         mandatory
   DESCRIPTION    ""
   REFERENCE	  "IBMPSG_RedundantNICSwitchback.Description"
::= { ibmSystemTrapRedundantNICSwitchbackBindings 5 }

ibmSystemTrapRedundantNICSwitchbackTimeStamp OBJECT-TYPE
   SYNTAX         Datetime
   ACCESS         read-write
   STATUS         mandatory
   DESCRIPTION    ""
   REFERENCE	  "IBMPSG_RedundantNICSwitchback.TimeStamp"
::= { ibmSystemTrapRedundantNICSwitchbackBindings 6 }

ibmSystemTrapProcessorPF TRAP-TYPE
   ENTERPRISE     ibmSystemMIB
   VARIABLES    {
      ibmSystemTrapProcessorPFProviderName,
      ibmSystemTrapProcessorPFEventID,
      ibmSystemTrapProcessorPFAlertingManagedElement,      
      ibmSystemTrapProcessorPFSeverity,
      ibmSystemTrapProcessorPFDescription,
      ibmSystemTrapProcessorPFTimeStamp
   }
   DESCRIPTION	"This event is sent when a system's processor changes state with respect to availability."
   REFERENCE	"IBMPSG_ProcessorPF"
::= 18

ibmSystemTrapProcessorPFBindings OBJECT IDENTIFIER ::= { ibmSystemTrap 18 }

ibmSystemTrapProcessorPFProviderName OBJECT-TYPE
   SYNTAX         String
   ACCESS         read-write
   STATUS         mandatory
   DESCRIPTION    ""
   REFERENCE	  "IBMPSG_ProcessorPF.ProviderName"
::= { ibmSystemTrapProcessorPFBindings 1 }

ibmSystemTrapProcessorPFEventID OBJECT-TYPE
   SYNTAX         String
   ACCESS         read-write
   STATUS         mandatory
   DESCRIPTION    ""
   REFERENCE	  "IBMPSG_ProcessorPF.EventID"
::= { ibmSystemTrapProcessorPFBindings 2 }

ibmSystemTrapProcessorPFAlertingManagedElement OBJECT-TYPE
   SYNTAX         String
   ACCESS         read-write
   STATUS         mandatory
   DESCRIPTION    ""
   REFERENCE	  "IBMPSG_ProcessorPF.AlertingManagedElement"
::= { ibmSystemTrapProcessorPFBindings 3 }

ibmSystemTrapProcessorPFSeverity OBJECT-TYPE
   SYNTAX         Uint16
   ACCESS         read-write
   STATUS         mandatory
   DESCRIPTION    "2=Critical -- The system's processor is experiencing an imminent failure."
   REFERENCE	  "IBMPSG_ProcessorPF.Severity"
::= { ibmSystemTrapProcessorPFBindings 4 }

ibmSystemTrapProcessorPFDescription OBJECT-TYPE
   SYNTAX         SnmpAdminString
   ACCESS         read-write
   STATUS         mandatory
   DESCRIPTION    ""
   REFERENCE	  "IBMPSG_ProcessorPF.Description"
::= { ibmSystemTrapProcessorPFBindings 5 }

ibmSystemTrapProcessorPFTimeStamp OBJECT-TYPE
   SYNTAX         Datetime
   ACCESS         read-write
   STATUS         mandatory
   DESCRIPTION    ""
   REFERENCE	  "IBMPSG_ProcessorPF.TimeStamp"
::= { ibmSystemTrapProcessorPFBindings 6 }

ibmSystemTrapMemoryPF TRAP-TYPE
   ENTERPRISE     ibmSystemMIB
   VARIABLES    {
      ibmSystemTrapMemoryPFProviderName,
      ibmSystemTrapMemoryPFEventID,
      ibmSystemTrapMemoryPFAlertingManagedElement,
      ibmSystemTrapMemoryPFSeverity,
      ibmSystemTrapMemoryPFDescription,
      ibmSystemTrapMemoryPFTimeStamp
   }
   DESCRIPTION	"This event is sent when a system's DIMM changes state with respect to availability."
   REFERENCE	"IBMPSG_MemoryPF"
::= 19

ibmSystemTrapMemoryPFBindings OBJECT IDENTIFIER ::= { ibmSystemTrap 19 }

ibmSystemTrapMemoryPFProviderName OBJECT-TYPE
   SYNTAX         String
   ACCESS         read-write
   STATUS         mandatory
   DESCRIPTION    ""
   REFERENCE	  "IBMPSG_MemoryPF.ProviderName"
::= { ibmSystemTrapMemoryPFBindings 1 }

ibmSystemTrapMemoryPFEventID OBJECT-TYPE
   SYNTAX         String
   ACCESS         read-write
   STATUS         mandatory
   DESCRIPTION    ""
   REFERENCE	  "IBMPSG_MemoryPF.EventID"
::= { ibmSystemTrapMemoryPFBindings 2 }

ibmSystemTrapMemoryPFAlertingManagedElement OBJECT-TYPE
   SYNTAX         String
   ACCESS         read-write
   STATUS         mandatory
   DESCRIPTION    ""
   REFERENCE	  "IBMPSG_MemoryPF.AlertingManagedElement"
::= { ibmSystemTrapMemoryPFBindings 3 }

ibmSystemTrapMemoryPFSeverity OBJECT-TYPE
   SYNTAX         Uint16
   ACCESS         read-write
   STATUS         mandatory
   DESCRIPTION    "2=Critical -- A DIMM in the system is experiencing an imminent failure."
   REFERENCE	  "IBMPSG_MemoryPF.Severity"
::= { ibmSystemTrapMemoryPFBindings 4 }

ibmSystemTrapMemoryPFDescription OBJECT-TYPE
   SYNTAX         SnmpAdminString
   ACCESS         read-write
   STATUS         mandatory
   DESCRIPTION    ""
   REFERENCE	  "IBMPSG_MemoryPF.Description"
::= { ibmSystemTrapMemoryPFBindings 5 }

ibmSystemTrapMemoryPFTimeStamp OBJECT-TYPE
   SYNTAX         Datetime
   ACCESS         read-write
   STATUS         mandatory
   DESCRIPTION    ""
   REFERENCE	  "IBMPSG_MemoryPF.TimeStamp"
::= { ibmSystemTrapMemoryPFBindings 6 }

ibmSystemTrapPFA TRAP-TYPE
   ENTERPRISE     ibmSystemMIB
   VARIABLES    {
      ibmSystemTrapPFAProviderName,
      ibmSystemTrapPFAEventID,
      ibmSystemTrapPFAAlertingManagedElement,
      ibmSystemTrapPFASeverity,
      ibmSystemTrapPFADescription,
      ibmSystemTrapPFATimeStamp
   }
   DESCRIPTION	"This event is sent when the Remote Supervisor Adapter detects that
                   a system is about to fail."
   REFERENCE	"IBMPSG_PFA"
::= 22

ibmSystemTrapPFABindings OBJECT IDENTIFIER ::= { ibmSystemTrap 22 }

ibmSystemTrapPFAProviderName OBJECT-TYPE
   SYNTAX         String
   ACCESS         read-write
   STATUS         mandatory
   DESCRIPTION    ""
   REFERENCE	  "IBMPSG_PFA.ProviderName"
::= { ibmSystemTrapPFABindings 1 }

ibmSystemTrapPFAEventID OBJECT-TYPE
   SYNTAX         String
   ACCESS         read-write
   STATUS         mandatory
   DESCRIPTION    ""
   REFERENCE	  "IBMPSG_PFA.EventID"
::= { ibmSystemTrapPFABindings 2 }

ibmSystemTrapPFAAlertingManagedElement OBJECT-TYPE
   SYNTAX         String
   ACCESS         read-write
   STATUS         mandatory
   DESCRIPTION    ""
   REFERENCE	  "IBMPSG_PFA.AlertingManagedElement"
::= { ibmSystemTrapPFABindings 3 }

ibmSystemTrapPFASeverity OBJECT-TYPE
   SYNTAX         Uint16
   ACCESS         read-write
   STATUS         mandatory
   DESCRIPTION    "2=Critical -- The system is experiencing an imminent failure."
   REFERENCE	  "IBMPSG_PFA.Severity"
::= { ibmSystemTrapPFABindings 4 }

ibmSystemTrapPFADescription OBJECT-TYPE
   SYNTAX         SnmpAdminString
   ACCESS         read-write
   STATUS         mandatory
   DESCRIPTION    ""
   REFERENCE	  "IBMPSG_PFA.Description"
::= { ibmSystemTrapPFABindings 5 }

ibmSystemTrapPFATimeStamp OBJECT-TYPE
   SYNTAX         Datetime
   ACCESS         read-write
   STATUS         mandatory
   DESCRIPTION    ""
   REFERENCE	  "IBMPSG_PFA.TimeStamp"
::= { ibmSystemTrapPFABindings 6 }

ibmSystemTrapPowerSupply TRAP-TYPE
   ENTERPRISE     ibmSystemMIB
   VARIABLES    {
      ibmSystemTrapPowerSupplyProviderName,
      ibmSystemTrapPowerSupplyEventID,
      ibmSystemTrapPowerSupplyAlertingManagedElement,
      ibmSystemTrapPowerSupplySeverity,
      ibmSystemTrapPowerSupplyDescription,
      ibmSystemTrapPowerSupplyTimeStamp
   }
   DESCRIPTION	"This event is sent when the Remote Supervisor Adapter detects that the
                   state of a system's power supply changes with respect to availability."
   REFERENCE	"IBMPSG_PowerSupply"
::= 23

ibmSystemTrapPowerSupplyBindings OBJECT IDENTIFIER ::= { ibmSystemTrap 23 }

ibmSystemTrapPowerSupplyProviderName OBJECT-TYPE
   SYNTAX         String
   ACCESS         read-write
   STATUS         mandatory
   DESCRIPTION    ""
   REFERENCE	  "IBMPSG_PowerSupply.ProviderName"
::= { ibmSystemTrapPowerSupplyBindings 1 }

ibmSystemTrapPowerSupplyEventID OBJECT-TYPE
   SYNTAX         String
   ACCESS         read-write
   STATUS         mandatory
   DESCRIPTION    ""
   REFERENCE	  "IBMPSG_PowerSupply.EventID"
::= { ibmSystemTrapPowerSupplyBindings 2 }

ibmSystemTrapPowerSupplyAlertingManagedElement OBJECT-TYPE
   SYNTAX         String
   ACCESS         read-write
   STATUS         mandatory
   DESCRIPTION    ""
   REFERENCE	  "IBMPSG_PowerSupply.AlertingManagedElement"
::= { ibmSystemTrapPowerSupplyBindings 3 }

ibmSystemTrapPowerSupplySeverity OBJECT-TYPE
   SYNTAX         Uint16
   ACCESS         read-write
   STATUS         mandatory
   DESCRIPTION    "0=Normal -- A failed power supply has been recovered.
                   2=Critical -- A power supply in a system has failed and there's been a possible loss of redundancy."
   REFERENCE	  "IBMPSG_PowerSupply.Severity"
::= { ibmSystemTrapPowerSupplyBindings 4 }

ibmSystemTrapPowerSupplyDescription OBJECT-TYPE
   SYNTAX         SnmpAdminString
   ACCESS         read-write
   STATUS         mandatory
   DESCRIPTION    ""
   REFERENCE	  "IBMPSG_PowerSupply.Description"
::= { ibmSystemTrapPowerSupplyBindings 5 }

ibmSystemTrapPowerSupplyTimeStamp OBJECT-TYPE
   SYNTAX         Datetime
   ACCESS         read-write
   STATUS         mandatory
   DESCRIPTION    ""
   REFERENCE	  "IBMPSG_PowerSupply.TimeStamp"
::= { ibmSystemTrapPowerSupplyBindings 6 }

ibmSystemTrapErrorLog TRAP-TYPE
   ENTERPRISE     ibmSystemMIB
   VARIABLES    {
      ibmSystemTrapErrorLogProviderName,
      ibmSystemTrapErrorLogEventID,
      ibmSystemTrapErrorLogAlertingManagedElement,
      ibmSystemTrapErrorLogSeverity,
      ibmSystemTrapErrorLogDescription,
      ibmSystemTrapErrorLogTimeStamp
   }
   DESCRIPTION	"This event is sent when the Remote Supervisor Adapter detects that its error
                   log is 75% full and/or 100% full."
   REFERENCE	"IBMPSG_ErrorLog"
::= 24

ibmSystemTrapErrorLogBindings OBJECT IDENTIFIER ::= { ibmSystemTrap 24 }

ibmSystemTrapErrorLogProviderName OBJECT-TYPE
   SYNTAX         String
   ACCESS         read-write
   STATUS         mandatory
   DESCRIPTION    ""
   REFERENCE	  "IBMPSG_ErrorLog.ProviderName"
::= { ibmSystemTrapErrorLogBindings 1 }

ibmSystemTrapErrorLogEventID OBJECT-TYPE
   SYNTAX         String
   ACCESS         read-write
   STATUS         mandatory
   DESCRIPTION    ""
   REFERENCE	  "IBMPSG_ErrorLog.EventID"
::= { ibmSystemTrapErrorLogBindings 2 }

ibmSystemTrapErrorLogAlertingManagedElement OBJECT-TYPE
   SYNTAX         String
   ACCESS         read-write
   STATUS         mandatory
   DESCRIPTION    ""
   REFERENCE	  "IBMPSG_ErrorLog.AlertingManagedElement"
::= { ibmSystemTrapErrorLogBindings 3 }

ibmSystemTrapErrorLogSeverity OBJECT-TYPE
   SYNTAX         Uint16
   ACCESS         read-write
   STATUS         mandatory
   DESCRIPTION    "1=Warning -- The Remote Supervisor Adapter's error log is 75% full.
                   2=Critical -- The Remote Supervisor Adapter's error log is 100% full."
   REFERENCE	  "IBMPSG_ErrorLog.Severity"
::= { ibmSystemTrapErrorLogBindings 4 }

ibmSystemTrapErrorLogDescription OBJECT-TYPE
   SYNTAX         SnmpAdminString
   ACCESS         read-write
   STATUS         mandatory
   DESCRIPTION    ""
   REFERENCE	  "IBMPSG_ErrorLog.Description"
::= { ibmSystemTrapErrorLogBindings 5 }

ibmSystemTrapErrorLogTimeStamp OBJECT-TYPE
   SYNTAX         Datetime
   ACCESS         read-write
   STATUS         mandatory
   DESCRIPTION    ""
   REFERENCE	  "IBMPSG_ErrorLog.TimeStamp"
::= { ibmSystemTrapErrorLogBindings 6 }

ibmSystemTrapRemoteLogin TRAP-TYPE
   ENTERPRISE     ibmSystemMIB
   VARIABLES    {
      ibmSystemTrapRemoteLoginProviderName,
      ibmSystemTrapRemoteLoginEventID,
      ibmSystemTrapRemoteLoginAlertingManagedElement,
      ibmSystemTrapRemoteLoginSeverity,
      ibmSystemTrapRemoteLoginDescription,
      ibmSystemTrapRemoteLoginTimeStamp
   }
   DESCRIPTION	"This event is sent when the state of the Remote Supervisor Adapter changes
                   with respect to security because a user has logged into it."
   REFERENCE	"IBMPSG_RemoteLogin"
::= 25

ibmSystemTrapRemoteLoginBindings OBJECT IDENTIFIER ::= { ibmSystemTrap 25 }

ibmSystemTrapRemoteLoginProviderName OBJECT-TYPE
   SYNTAX         String
   ACCESS         read-write
   STATUS         mandatory
   DESCRIPTION    ""
   REFERENCE	  "IBMPSG_RemoteLogin.ProviderName"
::= { ibmSystemTrapRemoteLoginBindings 1 }

ibmSystemTrapRemoteLoginEventID OBJECT-TYPE
   SYNTAX         String
   ACCESS         read-write
   STATUS         mandatory
   DESCRIPTION    ""
   REFERENCE	  "IBMPSG_RemoteLogin.EventID"
::= { ibmSystemTrapRemoteLoginBindings 2 }

ibmSystemTrapRemoteLoginAlertingManagedElement OBJECT-TYPE
   SYNTAX         String
   ACCESS         read-write
   STATUS         mandatory
   DESCRIPTION    ""
   REFERENCE	  "IBMPSG_RemoteLogin.AlertingManagedElement"
::= { ibmSystemTrapRemoteLoginBindings 3 }

ibmSystemTrapRemoteLoginSeverity OBJECT-TYPE
   SYNTAX         Uint16
   ACCESS         read-write
   STATUS         mandatory
   DESCRIPTION    "1=Warning -- Someone has logged in remotely to the Remote Supervisor Adapter."
   REFERENCE	  "IBMPSG_RemoteLogin.Severity"
::= { ibmSystemTrapRemoteLoginBindings 4 }

ibmSystemTrapRemoteLoginDescription OBJECT-TYPE
   SYNTAX         SnmpAdminString
   ACCESS         read-write
   STATUS         mandatory
   DESCRIPTION    ""
   REFERENCE	  "IBMPSG_RemoteLogin.Description"
::= { ibmSystemTrapRemoteLoginBindings 5 }

ibmSystemTrapRemoteLoginTimeStamp OBJECT-TYPE
   SYNTAX         Datetime
   ACCESS         read-write
   STATUS         mandatory
   DESCRIPTION    ""
   REFERENCE	  "IBMPSG_RemoteLogin.TimeStamp"
::= { ibmSystemTrapRemoteLoginBindings 6 }

ibmSystemTrapNetworkAdapterFailed TRAP-TYPE
   ENTERPRISE     ibmSystemMIB
   VARIABLES    {
      ibmSystemTrapNetworkAdapterFailedProviderName,
      ibmSystemTrapNetworkAdapterFailedEventID,
      ibmSystemTrapNetworkAdapterFailedAlertingManagedElement,
      ibmSystemTrapNetworkAdapterFailedSeverity,
      ibmSystemTrapNetworkAdapterFailedDescription,
      ibmSystemTrapNetworkAdapterFailedTimeStamp,
      ibmSystemTrapNetworkAdapterFailedComponentID
   }
   DESCRIPTION	"This event is sent when the state of a system's NIC fails."
   REFERENCE	"IBMPSG_NetworkAdapterFailed"
::= 26

ibmSystemTrapNetworkAdapterFailedBindings OBJECT IDENTIFIER ::= { ibmSystemTrap 26 }

ibmSystemTrapNetworkAdapterFailedProviderName OBJECT-TYPE
   SYNTAX         String
   ACCESS         read-write
   STATUS         mandatory
   DESCRIPTION    ""
   REFERENCE	  "IBMPSG_NetworkAdapterFailed.ProviderName"
::= { ibmSystemTrapNetworkAdapterFailedBindings 1 }

ibmSystemTrapNetworkAdapterFailedEventID OBJECT-TYPE
   SYNTAX         String
   ACCESS         read-write
   STATUS         mandatory
   DESCRIPTION    ""
   REFERENCE	  "IBMPSG_NetworkAdapterFailed.EventID"
::= { ibmSystemTrapNetworkAdapterFailedBindings 2 }

ibmSystemTrapNetworkAdapterFailedAlertingManagedElement OBJECT-TYPE
   SYNTAX         String
   ACCESS         read-write
   STATUS         mandatory
   DESCRIPTION    "The CIM ObjectPath of the physical network adapter instance that has experienced
		   a change in state."
   REFERENCE	  "IBMPSG_NetworkAdapterFailed.AlertingManagedElement"
::= { ibmSystemTrapNetworkAdapterFailedBindings 3 }

ibmSystemTrapNetworkAdapterFailedSeverity OBJECT-TYPE
   SYNTAX         Uint16
   ACCESS         read-write
   STATUS         mandatory
   DESCRIPTION    "2=Critical -- The network adapter referenced in the target object path has failed.
		   0=Normal -- The network adapter referenced in the target object path has been recovered."
   REFERENCE	  "IBMPSG_NetworkAdapterFailed.Severity"
::= { ibmSystemTrapNetworkAdapterFailedBindings 4 }

ibmSystemTrapNetworkAdapterFailedDescription OBJECT-TYPE
   SYNTAX         SnmpAdminString
   ACCESS         read-write
   STATUS         mandatory
   DESCRIPTION    "The network adapter in the specified slot or port has failed."
   REFERENCE	  "IBMPSG_NetworkAdapterFailed.Description"
::= { ibmSystemTrapNetworkAdapterFailedBindings 5 }

ibmSystemTrapNetworkAdapterFailedTimeStamp OBJECT-TYPE
   SYNTAX         Datetime
   ACCESS         read-write
   STATUS         mandatory
   DESCRIPTION    "The date and time of the adapter failure on the managed system."
   REFERENCE	  "IBMPSG_NetworkAdapterFailed.TimeStamp"
::= { ibmSystemTrapNetworkAdapterFailedBindings 6 }

ibmSystemTrapNetworkAdapterFailedComponentID OBJECT-TYPE
   SYNTAX	Uint16
   ACCESS	read-only
   STATUS	mandatory
   DESCRIPTION  "The physical PCI Slot number or the onboard Port number of the NIC."
   REFERENCE	"IBMPSG_NetworkAdapterFailed.ComponentID"
::= { ibmSystemTrapNetworkAdapterFailedBindings 7 }

ibmSystemTrapNetworkAdapterOffline TRAP-TYPE
   ENTERPRISE     ibmSystemMIB
   VARIABLES    {
      ibmSystemTrapNetworkAdapterOfflineProviderName,
      ibmSystemTrapNetworkAdapterOfflineEventID,
      ibmSystemTrapNetworkAdapterOfflineAlertingManagedElement,
      ibmSystemTrapNetworkAdapterOfflineSeverity,
      ibmSystemTrapNetworkAdapterOfflineDescription,
      ibmSystemTrapNetworkAdapterOfflineTimeStamp,
      ibmSystemTrapNetworkAdapterOfflineComponentID
   }
   DESCRIPTION	"This event is sent when the state of a system's NIC goes offline."
   REFERENCE	"IBMPSG_NetworkAdapterOffline"
::= 27

ibmSystemTrapNetworkAdapterOfflineBindings OBJECT IDENTIFIER ::= { ibmSystemTrap 27 }

ibmSystemTrapNetworkAdapterOfflineProviderName OBJECT-TYPE
   SYNTAX         String
   ACCESS         read-write
   STATUS         mandatory
   DESCRIPTION    ""
   REFERENCE	  "IBMPSG_NetworkAdapterOffline.ProviderName"
::= { ibmSystemTrapNetworkAdapterOfflineBindings 1 }

ibmSystemTrapNetworkAdapterOfflineEventID OBJECT-TYPE
   SYNTAX         String
   ACCESS         read-write
   STATUS         mandatory
   DESCRIPTION    ""
   REFERENCE	  "IBMPSG_NetworkAdapterOffline.EventID"
::= { ibmSystemTrapNetworkAdapterOfflineBindings 2 }

ibmSystemTrapNetworkAdapterOfflineAlertingManagedElement OBJECT-TYPE
   SYNTAX         String
   ACCESS         read-write
   STATUS         mandatory
   DESCRIPTION    "The CIM ObjectPath of the physical network adapter instance that has experienced
		   a change in state."
   REFERENCE	  "IBMPSG_NetworkAdapterOffline.AlertingManagedElement"
::= { ibmSystemTrapNetworkAdapterOfflineBindings 3 }

ibmSystemTrapNetworkAdapterOfflineSeverity OBJECT-TYPE
   SYNTAX         Uint16
   ACCESS         read-write
   STATUS         mandatory
   DESCRIPTION    "1=Warning -- The network adapter referenced in the target object path has gone offline."
   REFERENCE	  "IBMPSG_NetworkAdapterOffline.Severity"
::= { ibmSystemTrapNetworkAdapterOfflineBindings 4 }

ibmSystemTrapNetworkAdapterOfflineDescription OBJECT-TYPE
   SYNTAX         SnmpAdminString
   ACCESS         read-write
   STATUS         mandatory
   DESCRIPTION    "The network adapter in the specified slot or port has gone offline."
   REFERENCE	  "IBMPSG_NetworkAdapterOffline.Description"
::= { ibmSystemTrapNetworkAdapterOfflineBindings 5 }

ibmSystemTrapNetworkAdapterOfflineTimeStamp OBJECT-TYPE
   SYNTAX         Datetime
   ACCESS         read-write
   STATUS         mandatory
   DESCRIPTION    "The date and time that the network adapter went offline on the managed system."
   REFERENCE	  "IBMPSG_NetworkAdapterOffline.TimeStamp"
::= { ibmSystemTrapNetworkAdapterOfflineBindings 6 }

ibmSystemTrapNetworkAdapterOfflineComponentID OBJECT-TYPE
   SYNTAX	Uint16
   ACCESS	read-only
   STATUS	mandatory
   DESCRIPTION  "The physical PCI Slot number or the onboard Port number of the NIC."
   REFERENCE	"IBMPSG_NetworkAdapterOffline.ComponentID"
::= { ibmSystemTrapNetworkAdapterOfflineBindings 7 }

ibmSystemTrapNetworkAdapterOnline TRAP-TYPE
   ENTERPRISE     ibmSystemMIB
   VARIABLES    {
      ibmSystemTrapNetworkAdapterOnlineProviderName,
      ibmSystemTrapNetworkAdapterOnlineEventID,
      ibmSystemTrapNetworkAdapterOnlineAlertingManagedElement,
      ibmSystemTrapNetworkAdapterOnlineSeverity,
      ibmSystemTrapNetworkAdapterOnlineDescription,
      ibmSystemTrapNetworkAdapterOnlineTimeStamp,
      ibmSystemTrapNetworkAdapterOnlineComponentID
   }
   DESCRIPTION	"This event is sent when the state of a system's NIC goes online."
   REFERENCE	"IBMPSG_NetworkAdapterOnline"
::= 28

ibmSystemTrapNetworkAdapterOnlineBindings OBJECT IDENTIFIER ::= { ibmSystemTrap 28 }

ibmSystemTrapNetworkAdapterOnlineProviderName OBJECT-TYPE
   SYNTAX         String
   ACCESS         read-write
   STATUS         mandatory
   DESCRIPTION    ""
   REFERENCE	  "IBMPSG_NetworkAdapterOnline.ProviderName"
::= { ibmSystemTrapNetworkAdapterOnlineBindings 1 }

ibmSystemTrapNetworkAdapterOnlineEventID OBJECT-TYPE
   SYNTAX         String
   ACCESS         read-write
   STATUS         mandatory
   DESCRIPTION    ""
   REFERENCE	  "IBMPSG_NetworkAdapterOnline.EventID"
::= { ibmSystemTrapNetworkAdapterOnlineBindings 2 }

ibmSystemTrapNetworkAdapterOnlineAlertingManagedElement OBJECT-TYPE
   SYNTAX         String
   ACCESS         read-write
   STATUS         mandatory
   DESCRIPTION    "The CIM ObjectPath of the physical network adapter instance that has experienced
		   a change in state."
   REFERENCE	  "IBMPSG_NetworkAdapterOnline.AlertingManagedElement"
::= { ibmSystemTrapNetworkAdapterOnlineBindings 3 }

ibmSystemTrapNetworkAdapterOnlineSeverity OBJECT-TYPE
   SYNTAX         Uint16
   ACCESS         read-write
   STATUS         mandatory
   DESCRIPTION    "0=Normal -- The network adapter referenced in the target object path has come online."
   REFERENCE	  "IBMPSG_NetworkAdapterOnline.Severity"
::= { ibmSystemTrapNetworkAdapterOnlineBindings 4 }

ibmSystemTrapNetworkAdapterOnlineDescription OBJECT-TYPE
   SYNTAX         SnmpAdminString
   ACCESS         read-write
   STATUS         mandatory
   DESCRIPTION    "The network adapter in the specified slot or port has come online."
   REFERENCE	  "IBMPSG_NetworkAdapterOnline.Description"
::= { ibmSystemTrapNetworkAdapterOnlineBindings 5 }

ibmSystemTrapNetworkAdapterOnlineTimeStamp OBJECT-TYPE
   SYNTAX         Datetime
   ACCESS         read-write
   STATUS         mandatory
   DESCRIPTION    "The date and time that the network adapter came online on the managed system."
   REFERENCE	  "IBMPSG_NetworkAdapterOnline.TimeStamp"
::= { ibmSystemTrapNetworkAdapterOnlineBindings 6 }

ibmSystemTrapNetworkAdapterOnlineComponentID OBJECT-TYPE
   SYNTAX	Uint16
   ACCESS	read-only
   STATUS	mandatory
   DESCRIPTION  "The physical PCI Slot number or the onboard Port number of the NIC."
   REFERENCE	"IBMPSG_NetworkAdapterFailed.ComponentID"
::= { ibmSystemTrapNetworkAdapterOnlineBindings 7 }

ibmSystemTrapSPPowerSupply TRAP-TYPE
   ENTERPRISE     ibmSystemMIB
   VARIABLES    {
      ibmSystemTrapSPPowerSupplyProviderName,
      ibmSystemTrapSPPowerSupplyEventID,
      ibmSystemTrapSPPowerSupplyAlertingManagedElement,
      ibmSystemTrapSPPowerSupplySeverity,
      ibmSystemTrapSPPowerSupplyDescription,
      ibmSystemTrapSPPowerSupplyTimeStamp
   }
   DESCRIPTION	"This event is sent when the Remote Supervisor Adapter detects that the
                   state of a system's power supply changes with respect to availability."
   REFERENCE	"IBMPSG_SP_PowerSupply"
::= 29

ibmSystemTrapSPPowerSupplyBindings OBJECT IDENTIFIER ::= { ibmSystemTrap 29 }

ibmSystemTrapSPPowerSupplyProviderName OBJECT-TYPE
   SYNTAX         String
   ACCESS         read-write
   STATUS         mandatory
   DESCRIPTION    ""
   REFERENCE	  "IBMPSG_SP_PowerSupply.ProviderName"
::= { ibmSystemTrapSPPowerSupplyBindings 1 }

ibmSystemTrapSPPowerSupplyEventID OBJECT-TYPE
   SYNTAX         String
   ACCESS         read-write
   STATUS         mandatory
   DESCRIPTION    ""
   REFERENCE	  "IBMPSG_SP_PowerSupply.EventID"
::= { ibmSystemTrapSPPowerSupplyBindings 2 }

ibmSystemTrapSPPowerSupplyAlertingManagedElement OBJECT-TYPE
   SYNTAX         String
   ACCESS         read-write
   STATUS         mandatory
   DESCRIPTION    ""
   REFERENCE	  "IBMPSG_SP_PowerSupply.AlertingManagedElement"
::= { ibmSystemTrapSPPowerSupplyBindings 3 }

ibmSystemTrapSPPowerSupplySeverity OBJECT-TYPE
   SYNTAX         Uint16
   ACCESS         read-write
   STATUS         mandatory
   DESCRIPTION    "2=Critical -- A power supply in a system has failed and there has been a possible loss of redundancy."
   REFERENCE	  "IBMPSG_SP_PowerSupply.Severity"
::= { ibmSystemTrapSPPowerSupplyBindings 4 }

ibmSystemTrapSPPowerSupplyDescription OBJECT-TYPE
   SYNTAX         SnmpAdminString
   ACCESS         read-write
   STATUS         mandatory
   DESCRIPTION    ""
   REFERENCE	  "IBMPSG_SP_PowerSupply.Description"
::= { ibmSystemTrapSPPowerSupplyBindings 5 }

ibmSystemTrapSPPowerSupplyTimeStamp OBJECT-TYPE
   SYNTAX         Datetime
   ACCESS         read-write
   STATUS         mandatory
   DESCRIPTION    ""
   REFERENCE	  "IBMPSG_SP_PowerSupply.TimeStamp"
::= { ibmSystemTrapSPPowerSupplyBindings 6 }

ibmSystemTrapDASDBackplane TRAP-TYPE
   ENTERPRISE     ibmSystemMIB
   VARIABLES    {
      ibmSystemTrapDASDBackplaneProviderName,
      ibmSystemTrapDASDBackplaneEventID,
      ibmSystemTrapDASDBackplaneAlertingManagedElement,
      ibmSystemTrapDASDBackplaneSeverity,
      ibmSystemTrapDASDBackplaneDescription,
      ibmSystemTrapDASDBackplaneTimeStamp
   }
   DESCRIPTION	"This event is sent when the Remote Supervisor Adapter detects that the
                   drive backplane experiences a critical error."
   REFERENCE	"IBMPSG_DASDBackplane"
::= 30

ibmSystemTrapDASDBackplaneBindings OBJECT IDENTIFIER ::= { ibmSystemTrap 30 }

ibmSystemTrapDASDBackplaneProviderName OBJECT-TYPE
   SYNTAX         String
   ACCESS         read-write
   STATUS         mandatory
   DESCRIPTION    ""
   REFERENCE	  "IBMPSG_DASDBackplane.ProviderName"
::= { ibmSystemTrapDASDBackplaneBindings 1 }

ibmSystemTrapDASDBackplaneEventID OBJECT-TYPE
   SYNTAX         String
   ACCESS         read-write
   STATUS         mandatory
   DESCRIPTION    ""
   REFERENCE	  "IBMPSG_DASDBackplane.EventID"
::= { ibmSystemTrapDASDBackplaneBindings 2 }

ibmSystemTrapDASDBackplaneAlertingManagedElement OBJECT-TYPE
   SYNTAX         String
   ACCESS         read-write
   STATUS         mandatory
   DESCRIPTION    ""
   REFERENCE	  "IBMPSG_DASDBackplane.AlertingManagedElement"
::= { ibmSystemTrapDASDBackplaneBindings 3 }

ibmSystemTrapDASDBackplaneSeverity OBJECT-TYPE
   SYNTAX         Uint16
   ACCESS         read-write
   STATUS         mandatory
   DESCRIPTION    "2=Critical -- A hard drive failure has occured."
   REFERENCE	  "IBMPSG_DASDBackplane.Severity"
::= { ibmSystemTrapDASDBackplaneBindings 4 }

ibmSystemTrapDASDBackplaneDescription OBJECT-TYPE
   SYNTAX         SnmpAdminString
   ACCESS         read-write
   STATUS         mandatory
   DESCRIPTION    ""
   REFERENCE	  "IBMPSG_DASDBackplane.Description"
::= { ibmSystemTrapDASDBackplaneBindings 5 }

ibmSystemTrapDASDBackplaneTimeStamp OBJECT-TYPE
   SYNTAX         Datetime
   ACCESS         read-write
   STATUS         mandatory
   DESCRIPTION    ""
   REFERENCE	  "IBMPSG_DASDBackplane.TimeStamp"
::= { ibmSystemTrapDASDBackplaneBindings 6 }

ibmSystemTrapGenericFan TRAP-TYPE
   ENTERPRISE     ibmSystemMIB
   VARIABLES    {
      ibmSystemTrapGenericFanProviderName,
      ibmSystemTrapGenericFanEventID,
      ibmSystemTrapGenericFanAlertingManagedElement,
      ibmSystemTrapGenericFanSeverity,
      ibmSystemTrapGenericFanDescription,
      ibmSystemTrapGenericFanTimeStamp
   }
   DESCRIPTION	"This event is sent when the Remote Supervisor Adapter detects that the
                   state of a system's fan has changed with respect to
                   manufacturer-defined rpm values"
   REFERENCE	"IBMPSG_GenericFan"
::= 31

ibmSystemTrapGenericFanBindings OBJECT IDENTIFIER ::= { ibmSystemTrap 31 }

ibmSystemTrapGenericFanProviderName OBJECT-TYPE
   SYNTAX         String
   ACCESS         read-write
   STATUS         mandatory
   DESCRIPTION    ""
   REFERENCE	  "IBMPSG_GenericFan.ProviderName"
::= { ibmSystemTrapGenericFanBindings 1 }

ibmSystemTrapGenericFanEventID OBJECT-TYPE
   SYNTAX         String
   ACCESS         read-write
   STATUS         mandatory
   DESCRIPTION    ""
   REFERENCE	  "IBMPSG_GenericFan.EventID"
::= { ibmSystemTrapGenericFanBindings 2 }

ibmSystemTrapGenericFanAlertingManagedElement OBJECT-TYPE
   SYNTAX         String
   ACCESS         read-write
   STATUS         mandatory
   DESCRIPTION    ""
   REFERENCE	  "IBMPSG_GenericFan.AlertingManagedElement"
::= { ibmSystemTrapGenericFanBindings 3 }

ibmSystemTrapGenericFanSeverity OBJECT-TYPE
   SYNTAX         Uint16
   ACCESS         read-write
   STATUS         mandatory
   DESCRIPTION    "2=Critical -- The fan has stopped."
   REFERENCE	  "IBMPSG_GenericFan.Severity"
::= { ibmSystemTrapGenericFanBindings 4 }

ibmSystemTrapGenericFanDescription OBJECT-TYPE
   SYNTAX         SnmpAdminString
   ACCESS         read-write
   STATUS         mandatory
   DESCRIPTION    ""
   REFERENCE	  "IBMPSG_GenericFan.Description"
::= { ibmSystemTrapGenericFanBindings 5 }

ibmSystemTrapGenericFanTimeStamp OBJECT-TYPE
   SYNTAX         Datetime
   ACCESS         read-write
   STATUS         mandatory
   DESCRIPTION    ""
   REFERENCE	  "IBMPSG_GenericFan.TimeStamp"
::= { ibmSystemTrapGenericFanBindings 6 }

ibmSystemTrapGenericVoltage TRAP-TYPE
   ENTERPRISE     ibmSystemMIB
   VARIABLES    {
      ibmSystemTrapGenericVoltageProviderName,
      ibmSystemTrapGenericVoltageEventID,
      ibmSystemTrapGenericVoltageAlertingManagedElement,
      ibmSystemTrapGenericVoltageSeverity,
      ibmSystemTrapGenericVoltageDescription,
      ibmSystemTrapGenericVoltageTimeStamp
   }
   DESCRIPTION	"This event is sent when the Remote Supervisor Adapter detects that the
                   state of a system's voltage sensor changes with respect to a 
                   manufacturer-defined threshold."
   REFERENCE	"IBMPSG_GenericVoltage"
::= 32

ibmSystemTrapGenericVoltageBindings OBJECT IDENTIFIER ::= { ibmSystemTrap 32 }

ibmSystemTrapGenericVoltageProviderName OBJECT-TYPE
   SYNTAX         String
   ACCESS         read-write
   STATUS         mandatory
   DESCRIPTION    ""
   REFERENCE	  "IBMPSG_GenericVoltage.ProviderName"
::= { ibmSystemTrapGenericVoltageBindings 1 }

ibmSystemTrapGenericVoltageEventID OBJECT-TYPE
   SYNTAX         String
   ACCESS         read-write
   STATUS         mandatory
   DESCRIPTION    ""
   REFERENCE	  "IBMPSG_GenericVoltage.EventID"
::= { ibmSystemTrapGenericVoltageBindings 2 }

ibmSystemTrapGenericVoltageAlertingManagedElement OBJECT-TYPE
   SYNTAX         String
   ACCESS         read-write
   STATUS         mandatory
   DESCRIPTION    ""
   REFERENCE	  "IBMPSG_GenericVoltage.AlertingManagedElement"
::= { ibmSystemTrapGenericVoltageBindings 3 }

ibmSystemTrapGenericVoltageSeverity OBJECT-TYPE
   SYNTAX         Uint16
   ACCESS         read-write
   STATUS         mandatory
   DESCRIPTION    "1=Warning -- The voltage has exceeded a manufacturer-defined warning level thresold
                   2=Critical -- The voltage has exceeded a manufacturer-defined critical threshold"
   REFERENCE	  "IBMPSG_GenericVoltage.Severity"
::= { ibmSystemTrapGenericVoltageBindings 4 }

ibmSystemTrapGenericVoltageDescription OBJECT-TYPE
   SYNTAX         SnmpAdminString
   ACCESS         read-write
   STATUS         mandatory
   DESCRIPTION    ""
   REFERENCE	  "IBMPSG_GenericVoltage.Description"
::= { ibmSystemTrapGenericVoltageBindings 5 }

ibmSystemTrapGenericVoltageTimeStamp OBJECT-TYPE
   SYNTAX         Datetime
   ACCESS         read-write
   STATUS         mandatory
   DESCRIPTION    ""
   REFERENCE	  "IBMPSG_GenericVoltage.TimeStamp"
::= { ibmSystemTrapGenericVoltageBindings 6 }


ibmSystemTrapMgmtHwLogStatus TRAP-TYPE
   ENTERPRISE     ibmSystemMIB
   VARIABLES    {
      ibmSystemTrapMgmtHwLogStatusProviderName,
      ibmSystemTrapMgmtHwLogStatusEventID,
      ibmSystemTrapMgmtHwLogStatusAlertingManagedElement,
      ibmSystemTrapMgmtHwLogStatusSeverity,
      ibmSystemTrapMgmtHwLogStatusDescription,
      ibmSystemTrapMgmtHwLogStatusTimeStamp
   }
   DESCRIPTION	"This event is sent when the IPMI Status Log is full."
   REFERENCE	"IBM_MgmtHwLogStatus"
::= 33

ibmSystemTrapMgmtHwLogStatusBindings OBJECT IDENTIFIER ::= { ibmSystemTrap 33 }

ibmSystemTrapMgmtHwLogStatusProviderName OBJECT-TYPE
   SYNTAX         String
   ACCESS         read-write
   STATUS         mandatory
   DESCRIPTION    ""
   REFERENCE	  "IBM_MgmtHwLogStatus.ProviderName"
::= { ibmSystemTrapMgmtHwLogStatusBindings 1 }

ibmSystemTrapMgmtHwLogStatusEventID OBJECT-TYPE
   SYNTAX         String
   ACCESS         read-write
   STATUS         mandatory
   DESCRIPTION    ""
   REFERENCE	  "IBM_MgmtHwLogStatus.EventID"
::= { ibmSystemTrapMgmtHwLogStatusBindings 2 }

ibmSystemTrapMgmtHwLogStatusAlertingManagedElement OBJECT-TYPE
   SYNTAX         String
   ACCESS         read-write
   STATUS         mandatory
   DESCRIPTION    ""
   REFERENCE	  "IBM_MgmtHwLogStatus.AlertingManagedElement"
::= { ibmSystemTrapMgmtHwLogStatusBindings 3 }

ibmSystemTrapMgmtHwLogStatusSeverity OBJECT-TYPE
   SYNTAX         Uint16
   ACCESS         read-write
   STATUS         mandatory
   DESCRIPTION    ""
   REFERENCE	  "IBM_MgmtHwLogStatus.Severity"
::= { ibmSystemTrapMgmtHwLogStatusBindings 4 }

ibmSystemTrapMgmtHwLogStatusDescription OBJECT-TYPE
   SYNTAX         SnmpAdminString
   ACCESS         read-write
   STATUS         mandatory
   DESCRIPTION    ""
   REFERENCE	  "IBM_MgmtHwLogStatus.Description"
::= { ibmSystemTrapMgmtHwLogStatusBindings 5 }

ibmSystemTrapMgmtHwLogStatusTimeStamp OBJECT-TYPE
   SYNTAX         Datetime
   ACCESS         read-write
   STATUS         mandatory
   DESCRIPTION    ""
   REFERENCE	  "IBM_MgmtHwLogStatus.TimeStamp"
::= { ibmSystemTrapMgmtHwLogStatusBindings 6 }


ibmSystemTrapxProcessor TRAP-TYPE
   ENTERPRISE     ibmSystemMIB
   VARIABLES    {
      ibmSystemTrapxProcessorProviderName,
      ibmSystemTrapxProcessorEventID,
      ibmSystemTrapxProcessorAlertingManagedElement,
      ibmSystemTrapxProcessorSeverity,
      ibmSystemTrapxProcessorDescription,
      ibmSystemTrapxProcessorTimeStamp
   }
   DESCRIPTION	""
   REFERENCE	"IBMPSG_xProcessor"
::= 34

ibmSystemTrapxProcessorBindings OBJECT IDENTIFIER ::= { ibmSystemTrap 34 }

ibmSystemTrapxProcessorProviderName OBJECT-TYPE
   SYNTAX         String
   ACCESS         read-write
   STATUS         mandatory
   DESCRIPTION    ""
   REFERENCE	  "IBMx_ProcessorEvent.ProviderName"
::= { ibmSystemTrapxProcessorBindings 1 }

ibmSystemTrapxProcessorEventID OBJECT-TYPE
   SYNTAX         String
   ACCESS         read-write
   STATUS         mandatory
   DESCRIPTION    ""
   REFERENCE	  "IBMx_ProcessorEvent.EventID"
::= { ibmSystemTrapxProcessorBindings 2 }

ibmSystemTrapxProcessorAlertingManagedElement OBJECT-TYPE
   SYNTAX         String
   ACCESS         read-write
   STATUS         mandatory
   DESCRIPTION    ""
   REFERENCE	  "IBMx_ProcessorEvent.AlertingManagedElement"
::= { ibmSystemTrapxProcessorBindings 3 }

ibmSystemTrapxProcessorSeverity OBJECT-TYPE
   SYNTAX         Uint16
   ACCESS         read-write
   STATUS         mandatory
   DESCRIPTION    ""
   REFERENCE	  "IBMx_ProcessorEvent.Severity"
::= { ibmSystemTrapxProcessorBindings 4 }

ibmSystemTrapxProcessorDescription OBJECT-TYPE
   SYNTAX         SnmpAdminString
   ACCESS         read-write
   STATUS         mandatory
   DESCRIPTION    ""
   REFERENCE	  "IBMx_ProcessorEvent.Description"
::= { ibmSystemTrapxProcessorBindings 5 }

ibmSystemTrapxProcessorTimeStamp OBJECT-TYPE
   SYNTAX         Datetime
   ACCESS         read-write
   STATUS         mandatory
   DESCRIPTION    ""
   REFERENCE	  "IBMx_ProcessorEvent.TimeStamp"
::= { ibmSystemTrapxProcessorBindings 6 }


ibmSystemTrapxPhysicalMemory TRAP-TYPE
   ENTERPRISE     ibmSystemMIB
   VARIABLES    {
      ibmSystemTrapxPhysicalMemoryProviderName,
      ibmSystemTrapxPhysicalMemoryEventID,
      ibmSystemTrapxPhysicalMemoryAlertingManagedElement,
      ibmSystemTrapxPhysicalMemorySeverity,
      ibmSystemTrapxPhysicalMemoryDescription,
      ibmSystemTrapxPhysicalMemoryTimeStamp
   }
   DESCRIPTION	""
   REFERENCE	"IBMx_PhysicalMemoryEvent"
::= 35

ibmSystemTrapxPhysicalMemoryBindings OBJECT IDENTIFIER ::= { ibmSystemTrap 35 }

ibmSystemTrapxPhysicalMemoryProviderName OBJECT-TYPE
   SYNTAX         String
   ACCESS         read-write
   STATUS         mandatory
   DESCRIPTION    ""
   REFERENCE	  "IBMx_PhysicalMemoryEvent.ProviderName"
::= { ibmSystemTrapxPhysicalMemoryBindings 1 }

ibmSystemTrapxPhysicalMemoryEventID OBJECT-TYPE
   SYNTAX         String
   ACCESS         read-write
   STATUS         mandatory
   DESCRIPTION    ""
   REFERENCE	  "IBMx_PhysicalMemoryEvent.EventID"
::= { ibmSystemTrapxPhysicalMemoryBindings 2 }

ibmSystemTrapxPhysicalMemoryAlertingManagedElement OBJECT-TYPE
   SYNTAX         String
   ACCESS         read-write
   STATUS         mandatory
   DESCRIPTION    ""
   REFERENCE	  "IBMx_PhysicalMemoryEvent.AlertingManagedElement"
::= { ibmSystemTrapxPhysicalMemoryBindings 3 }

ibmSystemTrapxPhysicalMemorySeverity OBJECT-TYPE
   SYNTAX         Uint16
   ACCESS         read-write
   STATUS         mandatory
   DESCRIPTION    ""
   REFERENCE	  "IBMx_PhysicalMemoryEvent.Severity"
::= { ibmSystemTrapxPhysicalMemoryBindings 4 }

ibmSystemTrapxPhysicalMemoryDescription OBJECT-TYPE
   SYNTAX         SnmpAdminString
   ACCESS         read-write
   STATUS         mandatory
   DESCRIPTION    ""
   REFERENCE	  "IBMx_PhysicalMemoryEvent.Description"
::= { ibmSystemTrapxPhysicalMemoryBindings 5 }

ibmSystemTrapxPhysicalMemoryTimeStamp OBJECT-TYPE
   SYNTAX         Datetime
   ACCESS         read-write
   STATUS         mandatory
   DESCRIPTION    ""
   REFERENCE	  "IBMx_PhysicalMemoryEvent.TimeStamp"
::= { ibmSystemTrapxPhysicalMemoryBindings 6 }


ibmSystemTrapxAutomaticServerRestart TRAP-TYPE
   ENTERPRISE     ibmSystemMIB
   VARIABLES    {
      ibmSystemTrapxAutomaticServerRestartProviderName,
      ibmSystemTrapxAutomaticServerRestartEventID,
      ibmSystemTrapxAutomaticServerRestartAlertingManagedElement,
      ibmSystemTrapxAutomaticServerRestartSeverity,
      ibmSystemTrapxAutomaticServerRestartDescription,
      ibmSystemTrapxAutomaticServerRestartTimeStamp
   }
   DESCRIPTION	"This event is sent when the Remote Supervisor Adapter detects that the
                   state of a system's voltage sensor changes with respect to a 
                   manufacturer-defined threshold."
   REFERENCE	"IBMx_AutomaticServerRestartEvent"
::= 36

ibmSystemTrapxAutomaticServerRestartBindings OBJECT IDENTIFIER ::= { ibmSystemTrap 36 }

ibmSystemTrapxAutomaticServerRestartProviderName OBJECT-TYPE
   SYNTAX         String
   ACCESS         read-write
   STATUS         mandatory
   DESCRIPTION    ""
   REFERENCE	  "IBMx_AutomaticServerRestartEvent.ProviderName"
::= { ibmSystemTrapxAutomaticServerRestartBindings 1 }

ibmSystemTrapxAutomaticServerRestartEventID OBJECT-TYPE
   SYNTAX         String
   ACCESS         read-write
   STATUS         mandatory
   DESCRIPTION    ""
   REFERENCE	  "IBMx_AutomaticServerRestartEvent.EventID"
::= { ibmSystemTrapxAutomaticServerRestartBindings 2 }

ibmSystemTrapxAutomaticServerRestartAlertingManagedElement OBJECT-TYPE
   SYNTAX         String
   ACCESS         read-write
   STATUS         mandatory
   DESCRIPTION    ""
   REFERENCE	  "IBMx_AutomaticServerRestartEvent.AlertingManagedElement"
::= { ibmSystemTrapxAutomaticServerRestartBindings 3 }

ibmSystemTrapxAutomaticServerRestartSeverity OBJECT-TYPE
   SYNTAX         Uint16
   ACCESS         read-write
   STATUS         mandatory
   DESCRIPTION    "1=Warning -- The voltage has exceeded a manufacturer-defined warning level thresold
                   2=Critical -- The voltage has exceeded a manufacturer-defined critical threshold"
   REFERENCE	  "IBMx_AutomaticServerRestartEvent.Severity"
::= { ibmSystemTrapxAutomaticServerRestartBindings 4 }

ibmSystemTrapxAutomaticServerRestartDescription OBJECT-TYPE
   SYNTAX         SnmpAdminString
   ACCESS         read-write
   STATUS         mandatory
   DESCRIPTION    ""
   REFERENCE	  "IBMx_AutomaticServerRestartEvent.Description"
::= { ibmSystemTrapxAutomaticServerRestartBindings 5 }

ibmSystemTrapxAutomaticServerRestartTimeStamp OBJECT-TYPE
   SYNTAX         Datetime
   ACCESS         read-write
   STATUS         mandatory
   DESCRIPTION    ""
   REFERENCE	  "IBMx_AutomaticServerRestartEvent.TimeStamp"
::= { ibmSystemTrapxAutomaticServerRestartBindings 6 }
END
