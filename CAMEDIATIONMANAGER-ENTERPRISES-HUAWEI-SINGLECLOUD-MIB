CAMEDIATIONMANAGER-ENTERPRISES-HUAWEI-SINGLECLOUD-MIB DEFINITIONS ::= BEGIN

--
-- Huawei infrastructure of the CA MEDIATION MANAGER enterprise MIB tree
--

IMPORTS
    MODULE-IDENTITY, caMMHuawei FROM CAMEDIATIONMANAGER-ENTERPRISES-HUAWEI-MIB;




caMMHuaweiSingleCloud MODULE-IDENTITY
    LAST-UPDATED "201201300000Z"
    ORGANIZATION "www.CA.com"
    CONTACT-INFO   
                 "postal:   One CA Plaza
                        Islandia, NY 11749
                        USA
          email:    support@ca.com"
    DESCRIPTION
                "Hauwei infrastructure of the CA Mediation Manager enterprise MIB tree"
    REVISION     "201201300000Z"
    DESCRIPTION
                "First draft"
    ::= { caMMHuawei 2}


isOnline OBJECT-TYPE
	  SYNTAX  INTEGER
	  ACCESS  read-only
	  STATUS  mandatory
	  DESCRIPTION
	  	"Indicates that the MIBS are updated and complete for this object"
	  ::= { caMMHuaweiSingleCloud 7 }

--
--  CAMEDIATIONMANAGER HUAWEI SINGLECLOUD CLOUD OBJECTS
--

clTable OBJECT-TYPE
    SYNTAX  SEQUENCE OF clEntry
    ACCESS  not-accessible
    STATUS  mandatory
    DESCRIPTION
            "A list of Cloud entries."
    ::= { caMMHuaweiSingleCloud 1 }

clEntry OBJECT-TYPE
    SYNTAX  clEntry
    ACCESS  not-accessible
    STATUS  mandatory
    DESCRIPTION
            "An entry containing Cloud objects"
    INDEX   { clIndex }
    ::= { clTable 1 }

clEntry ::=
    SEQUENCE {
        clIndex
            INTEGER,
        clName
            DisplayString,
        clLastUpdated
            INTEGER,
        clDeltaTime
            Gauge
    }
    
clIndex OBJECT-TYPE
	  SYNTAX  INTEGER
	  ACCESS  read-only
	  STATUS  mandatory
	  DESCRIPTION
	  	"The Index of the Cloud Object"
	  ::= { clEntry 1 }
	  
clName OBJECT-TYPE
      SYNTAX DisplayString
      ACCESS read-only
      STATUS mandatory
      DESCRIPTION
	  	"A textual string containing the Cloud Name"
    ::= { clEntry 2 }

clLastUpdated OBJECT-TYPE
      SYNTAX INTEGER
      ACCESS read-only
      STATUS mandatory
      DESCRIPTION
	  	"The UTC timestamp indicating the last update for this cloud object"
    ::= { clEntry 3 }
    
clDeltaTime OBJECT-TYPE
      SYNTAX Gauge
      ACCESS read-only
      STATUS mandatory
      DESCRIPTION
	  	"An integer indicating the expecting time in seconds between updates"
    ::= { clEntry 4 }

--
--  CAMEDIATIONMANAGER HUAWEI SINGLECLOUD OMM OBJECTS
--

ommTable OBJECT-TYPE
    SYNTAX  SEQUENCE OF ommEntry
    ACCESS  not-accessible
    STATUS  mandatory
    DESCRIPTION
            "A list of OMM entries."
    ::= { caMMHuaweiSingleCloud 2 }

ommEntry OBJECT-TYPE
    SYNTAX  ommEntry
    ACCESS  not-accessible
    STATUS  mandatory
    DESCRIPTION
            "An entry containing OMM Objects"
    INDEX   { ommIndex }
    ::= { ommTable 1 }

ommEntry ::=
    SEQUENCE {
        ommIndex
            INTEGER,
        ommName
            DisplayString,
        ommAliasName
            DisplayString,
	ommAvailableState
		DisplayString,
	ommAvailableStateValue
		INTEGER,
	ommFip
		DisplayString,
	ommProcessDn
		DisplayString,
	ommProcessmanageStatus
		DisplayString,
	ommProcessmanageStatusValue
		INTEGER,
	ommDeployType
		DisplayString,
	ommIsVM
		DisplayString,
	ommIsVMValue
		INTEGER,
	ommhsIndex
		INTEGER,
	ommvmIndex
		INTEGER,
	ommDn
		DisplayString,
	ommCloudName
		DisplayString,
	ommclIndex
		INTEGER,
	ommLastUpdated
		INTEGER,
        ommDeltaTime
            Gauge
    }
    
ommIndex OBJECT-TYPE
	  SYNTAX  INTEGER
	  ACCESS  read-only
	  STATUS  mandatory
	  DESCRIPTION
	  	"The Index of the OMM Object"
	  ::= { ommEntry 1 }
	  
ommName OBJECT-TYPE
      SYNTAX DisplayString
      ACCESS read-only
      STATUS mandatory
      DESCRIPTION
	  	"A textual string containing The OMM Name"
    ::= { ommEntry 2 }

ommAliasName OBJECT-TYPE
      SYNTAX DisplayString
      ACCESS read-only
      STATUS mandatory
      DESCRIPTION
	  	"A textual string containing The OMM Alias Name"
    ::= { ommEntry 3 }

ommAvailableState OBJECT-TYPE
	SYNTAX DisplayString
	ACCESS read-only
	STATUS mandatory
	DESCRIPTION
		"The OMM Available State eg. NORMAL"
	::= { ommEntry 4 }

ommAvailableStateValue OBJECT-TYPE
	SYNTAX INTEGER
	ACCESS read-only
	STATUS mandatory
	DESCRIPTION
		"The OMM Available State Value 1=NORMAL 0=not NORMAL"
	::= { ommEntry 5 }

ommFip OBJECT-TYPE
	SYNTAX DisplayString
	ACCESS read-only
	STATUS mandatory
	DESCRIPTION
		"The OMM FIP"
	::= { ommEntry 6 }

ommProcessDn OBJECT-TYPE
	SYNTAX DisplayString
	ACCESS read-only
	STATUS mandatory
	DESCRIPTION
		"The OMM Process Distinguished Name"
	::= { ommEntry 7 }

ommProcessmanageStatus OBJECT-TYPE
	SYNTAX DisplayString
	ACCESS read-only
	STATUS mandatory
	DESCRIPTION
		"The OMM Manageable Status eg. ACTIVE"
	::= { ommEntry 8 }

ommProcessmanageStatusValue OBJECT-TYPE
	SYNTAX INTEGER
	ACCESS read-only
	STATUS mandatory
	DESCRIPTION
		"The OMM Manageable Status Value eg. 1=ACTIVE 0=not ACTIVE"
	::= { ommEntry 9 }

ommDeployType OBJECT-TYPE
	SYNTAX DisplayString
	ACCESS read-only
	STATUS mandatory
	DESCRIPTION
		"The OMM Deployment type eg: HostServer or VM"
	::= { ommEntry 10 }

ommIsVM OBJECT-TYPE
	SYNTAX DisplayString
	ACCESS read-only
	STATUS mandatory
	DESCRIPTION
		"A boolean value indicating if the OMM is deployed as a VM eg. false"
	::= { ommEntry 11 }

ommIsVMValue OBJECT-TYPE
	SYNTAX INTEGER
	ACCESS read-only
	STATUS mandatory
	DESCRIPTION
		"An integer value indicating if the OMM is deployed as a VM eg. true=1 false=0"
	::= { ommEntry 12 }

ommhsIndex OBJECT-TYPE
	SYNTAX INTEGER
	ACCESS read-only
	STATUS mandatory
	DESCRIPTION
		"The index of the HostServer hosting the OMM (if the OMM is deployed on a hostserver)"
	::= { ommEntry 13 }

ommvmIndex OBJECT-TYPE
	SYNTAX INTEGER
	ACCESS read-only
	STATUS mandatory
	DESCRIPTION
		"The index of the VM hosting the OMM (if the OMM is deployed on a VM"
	::= { ommEntry 14 }

ommDn OBJECT-TYPE
	SYNTAX DisplayString
	ACCESS read-only
	STATUS mandatory
	DESCRIPTION
		"The Cloud Name for this OMM"
	::= { ommEntry 15 }

ommCloudName OBJECT-TYPE
	SYNTAX DisplayString
	ACCESS read-only
	STATUS mandatory
	DESCRIPTION
		"The Cloud Name for this OMM"
	::= { ommEntry 16 }
	
ommclIndex OBJECT-TYPE
	SYNTAX INTEGER
	ACCESS read-only
	STATUS mandatory
	DESCRIPTION
		"The index of the related Cloud Object"
	::= { ommEntry 17 }

ommLastUpdated OBJECT-TYPE
	SYNTAX INTEGER
	ACCESS read-only
	STATUS mandatory
	DESCRIPTION
		"The UTC timestamp indicating the last update for this object"
	::= { ommEntry 18 }

ommDeltaTime OBJECT-TYPE
	SYNTAX Gauge
	ACCESS read-only
	STATUS mandatory
	DESCRIPTION
		"An integer indicating the expecting time in seconds between updates"
	::= { ommEntry 19 }
	
--
--  CAMEDIATIONMANAGER HUAWEI SINGLECLOUD CNA OBJECTS
--

cnaTable OBJECT-TYPE
    SYNTAX  SEQUENCE OF cnaEntry
    ACCESS  not-accessible
    STATUS  mandatory
    DESCRIPTION
            "A list of Cloud entries."
    ::= { caMMHuaweiSingleCloud 3 }

cnaEntry OBJECT-TYPE
    SYNTAX  cnaEntry
    ACCESS  not-accessible
    STATUS  mandatory
    DESCRIPTION
            "An Entry containing CNA Objects"
    INDEX   { cnaIndex }
    ::= { cnaTable 1 }

    
cnaEntry ::=
    SEQUENCE {
        cnaIndex
		INTEGER,
	cnaCNAName
		DisplayString,
	cnaAliasName
		DisplayString,
	cnaDn
		DisplayString,
	cnaCloudName
		DisplayString,
	cnaClusterName
		DisplayString,
	cnaType
		DisplayString,
	cnaDescription
		DisplayString,
	cnaCNAProcessaliasName
		DisplayString,
	cnaCNAProcessavailableState
		INTEGER,
	cnaCNAProcessavailableStateValue
		INTEGER,
	cnaCNAProcessCNAProcessName
		DisplayString,
	cnaCNAProcesscpuremain
		INTEGER,
	cnaCNAProcesscpuused
		INTEGER,
	cnaCNAProcessdescription
		DisplayString,
	cnaCNAProcessdn
		DisplayString,
	cnaCNAProcessmanageStatus
		DisplayString,
	cnaCNAProcessmemremain
		INTEGER,
	cnaCNAProcessmemused
		INTEGER,
	cnaFip
		DisplayString,
	cnaHostserveraliasName
		DisplayString,
	cnaHostserveravailablestate
		DisplayString,
	cnaHostserveravailablestateValue
		INTEGER,
	cnaHostserverbmcip
		DisplayString,
	cnaHostserverconnectedSwitchName
		DisplayString,
	cnaHostserverconnectedSwitchPort
		DisplayString,
	cnaHostserverdescription
		DisplayString,
	cnaHostserverhostName
		DisplayString,
	cnaHostserverip
		DisplayString,
	cnaHostserverposition
		DisplayString,
	cnaHostserverrackName
		DisplayString,
	cnaHostserverregionName
		DisplayString,
	cnaHostserverroomName
		DisplayString,
	cnaHostserverserverSN
		DisplayString,
	cnaHostserverservertype
		DisplayString,
	cnaHostserverzoneName
		DisplayString,
	cnaRackaliasName
		DisplayString,
	cnaRoomaliasName
		DisplayString,
	cnaCNAProcesscpuremain15
		INTEGER,
	cnaCNAProcesscpuused30
		INTEGER,
	cnaCNAProcessmemremain50
		INTEGER,
	cnaVmvmemusage30
		INTEGER,
	cnaVm_vcpu_usage45
		INTEGER,
	cnahsIndex
		INTEGER,
	cnaclIndex
		INTEGER,
	cnaLastUpdated
		INTEGER,
	cnaDeltaTime
		Gauge
    }


cnaIndex OBJECT-TYPE
	SYNTAX INTEGER
	ACCESS read-only
	STATUS mandatory
	DESCRIPTION
	"The Index of the CNA Object"
	::={ cnaEntry 1 }

cnaCNAName OBJECT-TYPE
	SYNTAX DisplayString
	ACCESS read-only
	STATUS mandatory
	DESCRIPTION
	"A textual string containing the CNA name"
	::={ cnaEntry 2 }

cnaAliasName OBJECT-TYPE
	SYNTAX DisplayString
	ACCESS read-only
	STATUS mandatory
	DESCRIPTION
	"A textual string containing the CNA Alias name"
	::={ cnaEntry 3 }

cnaDn OBJECT-TYPE
	SYNTAX DisplayString
	ACCESS read-only
	STATUS mandatory
	DESCRIPTION
	"A textual string containing the CNA dn name"
	::={ cnaEntry 4 }

cnaCloudName OBJECT-TYPE
	SYNTAX DisplayString
	ACCESS read-only
	STATUS mandatory
	DESCRIPTION
	"A textual string containing the cloud name to which the CNA belongs to"
	::={ cnaEntry 5 }

cnaClusterName OBJECT-TYPE
	SYNTAX DisplayString
	ACCESS read-only
	STATUS mandatory
	DESCRIPTION
	"A textual string indicating the cluster to which CNA belongs to"
	::={ cnaEntry 6 }

cnaType OBJECT-TYPE
	SYNTAX DisplayString
	ACCESS read-only
	STATUS mandatory
	DESCRIPTION
	"A textual string containing the CNA dn name"
	::={ cnaEntry 7 }

cnaDescription OBJECT-TYPE
	SYNTAX DisplayString
	ACCESS read-only
	STATUS mandatory
	DESCRIPTION
	"A textual string containing the CNA description"
	::={ cnaEntry 8 }

cnaCNAProcessaliasName OBJECT-TYPE
	SYNTAX DisplayString
	ACCESS read-only
	STATUS mandatory
	DESCRIPTION
	"A textual string displaying the alias name of the CNA process"
	::={ cnaEntry 9 }

cnaCNAProcessavailableState OBJECT-TYPE
	SYNTAX DisplayString
	ACCESS read-only
	STATUS mandatory
	DESCRIPTION
	"A textual string containing information of the CNA process avaialability state"
	::={ cnaEntry 10 }

cnaCNAProcessavailableStateValue OBJECT-TYPE
	SYNTAX INTEGER
	ACCESS read-only
	STATUS mandatory
	DESCRIPTION
	"A value containing information of the CNA process avaialability state value 1=NORMAL 0=not NORMAL"
	::={ cnaEntry 11 }

cnaCNAProcessCNAProcessName OBJECT-TYPE
	SYNTAX DisplayString
	ACCESS read-only
	STATUS mandatory
	DESCRIPTION
	"A textual string displaying the name of the CNA process"
	::={ cnaEntry 12 }

cnaCNAProcesscpuremain OBJECT-TYPE
	SYNTAX INTEGER
	ACCESS read-only
	STATUS mandatory
	DESCRIPTION
	"The remianing CPU available to the CNA"
	::={ cnaEntry 13 }

cnaCNAProcesscpuused OBJECT-TYPE
	SYNTAX INTEGER
	ACCESS read-only
	STATUS mandatory
	DESCRIPTION
	"The  CPU used by the CNA"
	::={ cnaEntry 14 }

cnaCNAProcessdescription OBJECT-TYPE
	SYNTAX DisplayString
	ACCESS read-only
	STATUS mandatory
	DESCRIPTION
	"A textual string containing the detials of the CNA Process"
	::={ cnaEntry 15 }

cnaCNAProcessdn OBJECT-TYPE
	SYNTAX DisplayString
	ACCESS read-only
	STATUS mandatory
	DESCRIPTION
	"A textual string containing the distinguised name of CNA process"
	::={ cnaEntry 16 }

cnaCNAProcessmanageStatus OBJECT-TYPE
	SYNTAX DisplayString
	ACCESS read-only
	STATUS mandatory
	DESCRIPTION
	"A textual string containing the status of the CNA Process management"
	::={ cnaEntry 17 }

cnaCNAProcessmemremain OBJECT-TYPE
	SYNTAX INTEGER
	ACCESS read-only
	STATUS mandatory
	DESCRIPTION
	"The remaining memory avialable to the CNA"
	::={ cnaEntry 18 }

cnaCNAProcessmemused OBJECT-TYPE
	SYNTAX INTEGER
	ACCESS read-only
	STATUS mandatory
	DESCRIPTION
	"The memory used by the CNA"
	::={ cnaEntry 19 }

cnaFip OBJECT-TYPE
	SYNTAX DisplayString
	ACCESS read-only
	STATUS mandatory
	DESCRIPTION
	"A IP address containing the details of the FIP address of CNA"
	::={ cnaEntry 20 }

cnaHostserveraliasName OBJECT-TYPE
	SYNTAX DisplayString
	ACCESS read-only
	STATUS mandatory
	DESCRIPTION
	"A textual string containing Host Server Alias Name"
	::={ cnaEntry 21 }

cnaHostserveravailablestate OBJECT-TYPE
	SYNTAX INTEGER
	ACCESS read-only
	STATUS mandatory
	DESCRIPTION
	"A textual string containing the CNA Host server availability state"
	::={ cnaEntry 22 }

cnaHostserveravailablestateValue OBJECT-TYPE
	SYNTAX INTEGER
	ACCESS read-only
	STATUS mandatory
	DESCRIPTION
	"The CNA Host server availability state value 1=NORMAL 0=not NORMAL"
	::={ cnaEntry 23 }

cnaHostserverbmcip OBJECT-TYPE
	SYNTAX DisplayString
	ACCESS read-only
	STATUS mandatory
	DESCRIPTION
	"The BMC server IP address"
	::={ cnaEntry 24 }

cnaHostserverconnectedSwitchName OBJECT-TYPE
	SYNTAX DisplayString
	ACCESS read-only
	STATUS mandatory
	DESCRIPTION
	"A textual string containing the details of CNA host server connected switch"
	::={ cnaEntry 25 }

cnaHostserverconnectedSwitchPort OBJECT-TYPE
	SYNTAX DisplayString
	ACCESS read-only
	STATUS mandatory
	DESCRIPTION
	"A textual string containing the details of CNA host server connected switch port"
	::={ cnaEntry 26 }

cnaHostserverdescription OBJECT-TYPE
	SYNTAX DisplayString
	ACCESS read-only
	STATUS mandatory
	DESCRIPTION
	"A textual string containing the details of CNA host server description"
	::={ cnaEntry 27 }

cnaHostserverhostName OBJECT-TYPE
	SYNTAX DisplayString
	ACCESS read-only
	STATUS mandatory
	DESCRIPTION
	"A textual string containing the details of CNA host server host name"
	::={ cnaEntry 28 }

cnaHostserverip OBJECT-TYPE
	SYNTAX DisplayString
	ACCESS read-only
	STATUS mandatory
	DESCRIPTION
	"The CNA host server IP"
	::={ cnaEntry 29 }

cnaHostserverposition OBJECT-TYPE
	SYNTAX DisplayString
	ACCESS read-only
	STATUS mandatory
	DESCRIPTION
	"A textual string containing the details of CNA host server position"
	::={ cnaEntry 30 }

cnaHostserverrackName OBJECT-TYPE
	SYNTAX DisplayString
	ACCESS read-only
	STATUS mandatory
	DESCRIPTION
	"A textual string containing the details of CNA host server rack name"
	::={ cnaEntry 31 }

cnaHostserverregionName OBJECT-TYPE
	SYNTAX DisplayString
	ACCESS read-only
	STATUS mandatory
	DESCRIPTION
	"A textual string containing the details of CNA host server region name"
	::={ cnaEntry 32 }

cnaHostserverroomName OBJECT-TYPE
	SYNTAX DisplayString
	ACCESS read-only
	STATUS mandatory
	DESCRIPTION
	"A textual string containing the details of CNA host server room name"
	::={ cnaEntry 33 }

cnaHostserverserverSN OBJECT-TYPE
	SYNTAX DisplayString
	ACCESS read-only
	STATUS mandatory
	DESCRIPTION
	"A textual string containing the details of CNA host server SN (Serial Number)"
	::={ cnaEntry 34 }

cnaHostserverservertype OBJECT-TYPE
	SYNTAX DisplayString
	ACCESS read-only
	STATUS mandatory
	DESCRIPTION
	"A textual string containing the details of CNA host server type"
	::={ cnaEntry 35 }

cnaHostserverzoneName OBJECT-TYPE
	SYNTAX DisplayString
	ACCESS read-only
	STATUS mandatory	
	DESCRIPTION
	"A textual string containing the details of CNA host server zone name"
	::={ cnaEntry 36 }

cnaRackaliasName OBJECT-TYPE
	SYNTAX DisplayString
	ACCESS read-only
	STATUS mandatory
	DESCRIPTION
	"A textual string containing the details of CNA rack alias name"
	::={ cnaEntry 37 }

cnaRoomaliasName OBJECT-TYPE
	SYNTAX DisplayString
	ACCESS read-only
	STATUS mandatory
	DESCRIPTION
	"A textual string containing the details of CNA room alias name"
	::={ cnaEntry 38 }

cnaCNAProcesscpuremain15 OBJECT-TYPE
	SYNTAX INTEGER
	ACCESS read-only
	STATUS deprecated
	DESCRIPTION
	"Obsolete"
	::={ cnaEntry 39 }

cnaCNAProcesscpuused30 OBJECT-TYPE
	SYNTAX INTEGER
	ACCESS read-only
	STATUS deprecated
	DESCRIPTION
	"Obsolete"
	::={ cnaEntry 40 }

cnaCNAProcessmemremain50 OBJECT-TYPE
	SYNTAX INTEGER
	ACCESS read-only
	STATUS deprecated
	DESCRIPTION
	"Obsolete"
	::={ cnaEntry 41 }

cnaVmvmemusage30 OBJECT-TYPE
	SYNTAX INTEGER
	ACCESS read-only
	STATUS mandatory
	DESCRIPTION
	"A Integer value containing the details of VM mem usage of CNA process in hundredths"
	::={ cnaEntry 42 }

cnaVm_vcpu_usage45 OBJECT-TYPE
	SYNTAX INTEGER
	ACCESS read-only
	STATUS mandatory
	DESCRIPTION
	"A Integer value containing the details of vCPU usage of CNA process in hundredths"
	::={ cnaEntry 43 }

cnahsIndex OBJECT-TYPE
	SYNTAX INTEGER
	ACCESS read-only
	STATUS mandatory
	DESCRIPTION
	"The Index of the related HostServer Object"
	::={ cnaEntry 44 }

cnaclIndex OBJECT-TYPE
	SYNTAX INTEGER
	ACCESS read-only
	STATUS mandatory
	DESCRIPTION
	"The Index of the related Cloud Object"
	::={ cnaEntry 45 }

cnaLastUpdated OBJECT-TYPE
	SYNTAX INTEGER
	ACCESS read-only
	STATUS mandatory
	DESCRIPTION
	"The UTC timestamp indicating the last update for this object"
	::={ cnaEntry 46 }

cnaDeltaTime OBJECT-TYPE
	SYNTAX Gauge
	ACCESS read-only
	STATUS mandatory
	DESCRIPTION
	"An integer indicating the expecting time in seconds between updates"
	::={ cnaEntry 47 }


--
--  CAMEDIATIONMANAGER HUAWEI SINGLECLOUD HOSTSERVER OBJECTS
--

hsTable OBJECT-TYPE
    SYNTAX  SEQUENCE OF hsEntry
    ACCESS  not-accessible
    STATUS  mandatory
    DESCRIPTION
            "A list of HostServer entries."
    ::= { caMMHuaweiSingleCloud 4 }

hsEntry OBJECT-TYPE
    SYNTAX  hsEntry
    ACCESS  not-accessible
    STATUS  mandatory
    DESCRIPTION
            "An entry containing HostServer objects"
    INDEX   { hsIndex }
    ::= { hsTable 1 }

hsEntry ::=
    SEQUENCE {
        hsIndex
		INTEGER,
	hsHostName
		DisplayString,
	hsAliasName
		DisplayString,
	hsDn
		DisplayString,
	hsServerSN
		DisplayString,
	hsAvailablestate
		DisplayString,
	hsServertype
		DisplayString,
	hsBmcip
		DisplayString,
	hsConnectedSwitchName
		DisplayString,
	hsConnectedSwitchPort
		DisplayString,
	hsDescription
		DisplayString,
	hsIp
		DisplayString,
	hsPosition
		DisplayString,
	hsRackName
		DisplayString,
	hsRegionName
		DisplayString,
	hsRoomName
		DisplayString,
	hsZoneName
		DisplayString,
	hsCpu_avg_temperature
		INTEGER,
	hsHost_pkg_rcv
		INTEGER,
	hsHost_pkg_send
		INTEGER,
	hsMem_size
		INTEGER,
	hsCore
		INTEGER,
	hsCpuLimit
		INTEGER,
	hsCurrentStateCode
		INTEGER,
	hsDisk
		DisplayString,
	hsDiskCount
		INTEGER,
	hsMem
		INTEGER,
	hsNic
		DisplayString,
	hsCpu_usage
		INTEGER,
	hsCpu_status
		INTEGER,
	hsHost_byte_in
		INTEGER,
	hsHost_byte_out
		INTEGER,
	hsMem_usage
		INTEGER,
	hsStorage_avg_usage
		INTEGER,
	hsDisk_status
		INTEGER,
	hsDisk_total
		INTEGER,
	hsCpuReserved
		INTEGER,
	hsMemReserved
		INTEGER,
	hsvm_vcpu_usage
		INTEGER,
	hsvm_vmem_usage
		INTEGER,
	hsAvailablestateValue
		INTEGER,
	hsswIndex
		INTEGER,
	haLastUpdated
		INTEGER,
	hsDeltaTime
		Gauge,
	hsMAC
		DisplayString
    }
    
hsIndex OBJECT-TYPE
	  SYNTAX  INTEGER
	  ACCESS  read-only
	  STATUS  mandatory
	  DESCRIPTION
	  	"The Index of the HostServer Object"
	  ::= { hsEntry 1 }
	  
hsHostName OBJECT-TYPE
      SYNTAX DisplayString
      ACCESS read-only
      STATUS mandatory
      DESCRIPTION
	  	"A textual string containing the Host Server hostname"
    ::= { hsEntry 2 }
    
    
hsAliasName OBJECT-TYPE
	SYNTAX DisplayString
	ACCESS read-only
	STATUS mandatory
	DESCRIPTION
	"A textual string containing the Host Server alias tname"
	::= { hsEntry 3 }

hsDn OBJECT-TYPE
	SYNTAX DisplayString
	ACCESS read-only
	STATUS mandatory
	DESCRIPTION
	"A textual string containing the Host Server distinguised name"
	::= { hsEntry 4 }

hsServerSN OBJECT-TYPE
	SYNTAX DisplayString
	ACCESS read-only
	STATUS mandatory
	DESCRIPTION
	"A textual string containing the Host Server serial numeber"
	::= { hsEntry 5 }

hsAvailablestate OBJECT-TYPE
	SYNTAX DisplayString
	ACCESS read-only
	STATUS mandatory
	DESCRIPTION
	"A textual string containing the Host Server availabilty state"
	::= { hsEntry 6 }

hsServertype OBJECT-TYPE
	SYNTAX DisplayString
	ACCESS read-only
	STATUS mandatory
	DESCRIPTION
	"A textual string containing the Host Server type"
	::= { hsEntry 7 }

hsBmcip OBJECT-TYPE
	SYNTAX DisplayString
	ACCESS read-only
	STATUS mandatory
	DESCRIPTION
	"A textual string containing the Host Server BMC ip"
	::= { hsEntry 8 }

hsConnectedSwitchName OBJECT-TYPE
	SYNTAX DisplayString
	ACCESS read-only
	STATUS mandatory
	DESCRIPTION
	"A textual string containing the Host Server connected switch name"
	::= { hsEntry 9 }

hsConnectedSwitchPort OBJECT-TYPE
	SYNTAX DisplayString
	ACCESS read-only
	STATUS mandatory
	DESCRIPTION
	"A textual string containing the Host Server connected switch port"
	::= { hsEntry 10 }

hsDescription OBJECT-TYPE
	SYNTAX DisplayString
	ACCESS read-only
	STATUS mandatory
	DESCRIPTION
	"A textual string containing the Host Server description"
	::= { hsEntry 11 }

hsIp OBJECT-TYPE
	SYNTAX DisplayString
	ACCESS read-only
	STATUS mandatory
	DESCRIPTION
	"A textual string containing the Host Server ip"
	::= { hsEntry 12 }

hsPosition OBJECT-TYPE
	SYNTAX DisplayString
	ACCESS read-only
	STATUS mandatory
	DESCRIPTION
	"A textual string containing the Host Server position"
	::= { hsEntry 13 }

hsRackName OBJECT-TYPE
	SYNTAX DisplayString
	ACCESS read-only
	STATUS mandatory
	DESCRIPTION
	"A textual string containing the Host Server rack name"
	::= { hsEntry 14 }

hsRegionName OBJECT-TYPE
	SYNTAX DisplayString
	ACCESS read-only
	STATUS mandatory
	DESCRIPTION
	"A textual string containing the Host Server region name"
	::= { hsEntry 15 }

hsRoomName OBJECT-TYPE
	SYNTAX DisplayString
	ACCESS read-only
	STATUS mandatory
	DESCRIPTION
	"A textual string containing the Host Server room name"
	::= { hsEntry 16 }

hsZoneName OBJECT-TYPE
	SYNTAX DisplayString
	ACCESS read-only
	STATUS mandatory
	DESCRIPTION
	"A textual string containing the Host Server zone name"
	::= { hsEntry 17 }

hsCpu_avg_temperature OBJECT-TYPE
	SYNTAX INTEGER
	ACCESS read-only
	STATUS mandatory
	DESCRIPTION
	"A Integer value containing the average temperature of the Host Server CPUs in hundredths"
	::= { hsEntry 18 }

hsHost_pkg_rcv OBJECT-TYPE
	SYNTAX INTEGER
	ACCESS read-only
	STATUS mandatory
	DESCRIPTION
	"A Integer value containing the number of Host Server host pkg received"
	::= { hsEntry 19 }

hsHost_pkg_send OBJECT-TYPE
	SYNTAX INTEGER
	ACCESS read-only
	STATUS mandatory
	DESCRIPTION
	"A Integer value containing the number of Host Server host pkg sent"
	::= { hsEntry 20 }

hsMem_size OBJECT-TYPE
	SYNTAX INTEGER
	ACCESS read-only
	STATUS mandatory
	DESCRIPTION
	"A Integer value containing the Host Server host memory size"
	::= { hsEntry 21 }

hsCore OBJECT-TYPE
	SYNTAX INTEGER
	ACCESS read-only
	STATUS mandatory
	DESCRIPTION
	"A Integer value containing the number of Host Server cores"
	::= { hsEntry 22 }

hsCpuLimit OBJECT-TYPE
	SYNTAX INTEGER
	ACCESS read-only
	STATUS deprecated
	DESCRIPTION
	"A Integer value containing the Host Server CPU limit"
	::= { hsEntry 23 }

hsCurrentStateCode OBJECT-TYPE
	SYNTAX INTEGER
	ACCESS read-only
	STATUS deprecated
	DESCRIPTION
	"A Integer value containing the Host Server current state code"
	::= { hsEntry 24 }

hsDisk OBJECT-TYPE
	SYNTAX DisplayString
	ACCESS read-only
	STATUS deprecated
	DESCRIPTION
	"A textual string containing the Host Server disk name"
	::= { hsEntry 25 }

hsDiskCount OBJECT-TYPE
	SYNTAX INTEGER
	ACCESS read-only
	STATUS deprecated
	DESCRIPTION
	"A Integer containing the Host Server disk count"
	::= { hsEntry 26 }

hsMem OBJECT-TYPE
	SYNTAX INTEGER
	ACCESS read-only
	STATUS deprecated
	DESCRIPTION
	"A Integer containing the Host Server memory utilization"
	::= { hsEntry 27 }

hsNic OBJECT-TYPE
	SYNTAX INTEGER
	ACCESS read-only
	STATUS deprecated
	DESCRIPTION
	"A textual string containing the Host Server NIC number"
	::= { hsEntry 28 }

hsCpu_usage OBJECT-TYPE
	SYNTAX INTEGER
	ACCESS read-only
	STATUS mandatory
	DESCRIPTION
	"A Integer value containing the Host Server CPU usage in hundredths"
	::= { hsEntry 29 }

hsCpu_status OBJECT-TYPE
	SYNTAX DisplayString
	ACCESS read-only
	STATUS deprecated
	DESCRIPTION
	"A textual string containing the Host Server CPU status"
	::= { hsEntry 30 }

hsHost_byte_in OBJECT-TYPE
	SYNTAX INTEGER
	ACCESS read-only
	STATUS mandatory
	DESCRIPTION
	"A integer containing the Host Server total bytes in in hundredths"
	::= { hsEntry 31 }

hsHost_byte_out OBJECT-TYPE
	SYNTAX INTEGER
	ACCESS read-only
	STATUS mandatory
	DESCRIPTION
	"A integer containing the Host Server total bytes out in hundredths"
	::= { hsEntry 32 }

hsMem_usage OBJECT-TYPE
	SYNTAX INTEGER
	ACCESS read-only
	STATUS mandatory
	DESCRIPTION
	"A Integer value containing the Host Server total memory usage in hundredths"
	::= { hsEntry 33 }

hsStorage_avg_usage OBJECT-TYPE
	SYNTAX INTEGER
	ACCESS read-only
	STATUS mandatory
	DESCRIPTION
	"A Integer value containing the Host Server total storage usage in hundredths"
	::= { hsEntry 34 }

hsDisk_status OBJECT-TYPE
	SYNTAX INTEGER
	ACCESS read-only
	STATUS deprecated
	DESCRIPTION
	"A Integer value containing the percentage of Host Server disks that are available in hundredths"
	::= { hsEntry 35 }

hsDisk_total OBJECT-TYPE
	SYNTAX INTEGER
	ACCESS read-only
	STATUS deprecated
	DESCRIPTION
	"A Integer value containing  the Host Server total disk utilization in hundredths"
	::= { hsEntry 36 }

hsCpuReserved OBJECT-TYPE
	SYNTAX INTEGER
	ACCESS read-only
	STATUS deprecated
	DESCRIPTION
	"A Integer value containing the CPU reserved for the Host Server"
	::= { hsEntry 37 }

hsMemReserved OBJECT-TYPE
	SYNTAX INTEGER
	ACCESS read-only
	STATUS deprecated
	DESCRIPTION
	"A Integer value containing the Memory reserved for the Host Server"
	::= { hsEntry 38 }

hsvm_vcpu_usage OBJECT-TYPE
	SYNTAX INTEGER
	ACCESS read-only
	STATUS deprecated
	DESCRIPTION
	"Obsolete - A Integer value containing the vm_vcpu usage for the Host Server"
	::= { hsEntry 39 }

hsvm_vmem_usage OBJECT-TYPE
	SYNTAX INTEGER
	ACCESS read-only
	STATUS deprecated
	DESCRIPTION
	"Obsolete - A Integer value containing the vm_vmem usage for the Host Server"
	::= { hsEntry 40 }

hsAvailablestateValue OBJECT-TYPE
	SYNTAX INTEGER
	ACCESS read-only
	STATUS mandatory
	DESCRIPTION
	"A Integer value containing the available state for the Host Server 1=NORMAL 0=not NORMAL"
	::= { hsEntry 41 }

hsswIndex OBJECT-TYPE
	SYNTAX INTEGER
	ACCESS read-only
	STATUS mandatory
	DESCRIPTION
	"The Index of the related Switch Object"
	::= { hsEntry 42 }

hsLastUpdated OBJECT-TYPE
      SYNTAX INTEGER
      ACCESS read-only
      STATUS mandatory
      DESCRIPTION
	  	"The UTC timestamp indicating the last update for this object"
    ::= { hsEntry 43 }
    
hsDeltaTime OBJECT-TYPE
      SYNTAX Gauge
      ACCESS read-only
      STATUS mandatory
      DESCRIPTION
	  	"An integer indicating the expecting time in seconds between updates"
    ::= { hsEntry 44 }

hsMAC OBJECT-TYPE
      SYNTAX DisplayString
      ACCESS read-only
      STATUS mandatory
      DESCRIPTION
	  	"The Host Server MAC Address"
    ::= { hsEntry 45 }
	

--
--  CAMEDIATIONMANAGER HUAWEI SINGLECLOUD VM OBJECTS
--

vmTable OBJECT-TYPE
    SYNTAX  SEQUENCE OF vmEntry
    ACCESS  not-accessible
    STATUS  mandatory
    DESCRIPTION
            "A list of VM entries."
    ::= { caMMHuaweiSingleCloud 5 }

vmEntry OBJECT-TYPE
    SYNTAX  vmEntry
    ACCESS  not-accessible
    STATUS  mandatory
    DESCRIPTION
            "An entry containing VM objects"
    INDEX   { vmIndex }
    ::= { vmTable 1 }

vmEntry ::=
    SEQUENCE {
	vmIndex
		INTEGER,
	vmVmName
		DisplayString,
	vmVmAliasName
		DisplayString,
	vmDn
		DisplayString,
	vmDescription
		DisplayString,
	vmCNAName
		DisplayString,
	vmCnaAliasName
		DisplayString,
	vmCloudName
		DisplayString,
	vmClusterName
		DisplayString,
	vmClusterAliasName
		DisplayString,
	vmBusinessAliasName
		DisplayString,
	vmBusinessName
		DisplayString,
	vmCore
		INTEGER,
	vmCpuLimit
		INTEGER,
	vmCpuReserved
		INTEGER,
	vmCurrentStateCode
		INTEGER,
	vmCurrentStateName
		DisplayString,
	vmDisk
		INTEGER,
	vmDiskCount
		INTEGER,
	vmInstanceId
		DisplayString,
	vmIp
		DisplayString,
	vmIsEnableHa
		DisplayString,
	vmIsoToolsStatus
		DisplayString,
	vmLaunchTime
		DisplayString,
	vmManageFlg
		DisplayString,
	vmMem
		INTEGER,
	vmMemReserved
		INTEGER,
	vmNcIp
		DisplayString,
	vmNic
		INTEGER,
	vmOwnerId
		DisplayString,
	vmServiceId
		DisplayString,
	vmStorageAliasName
		DisplayString,
	vmStorageName
		DisplayString,
	vmSystemOsType
		DisplayString,
	vmVmPort
		INTEGER,
	vmCore
		INTEGER,
	vmCpuLimit
		INTEGER,
	vmVm_cpu_usage_self
		INTEGER,
	vmVm_mem_usage_self
		INTEGER,
	vmVm_storage_usage_self
		INTEGER,
	vmcurrentStateValue
		INTEGER,
	vmclIndex
		INTEGER,
	vmcnaIndex
		INTEGER,
	vmLastUpdated
		INTEGER,
	vmDeltaTime
		Gauge,
	vmMAC
		DisplayString
    }
    
vmIndex OBJECT-TYPE
	  SYNTAX  INTEGER
	  ACCESS  read-only
	  STATUS  mandatory
	  DESCRIPTION
	  	"The Index of the VM Object"
	  ::= { vmEntry 1 }
	  
vmVmName OBJECT-TYPE
      SYNTAX DisplayString
      ACCESS read-only
      STATUS mandatory
      DESCRIPTION
	  	"A textual string containing the VM name"
    ::= { vmEntry 2 }
    
vmVmAliasName OBJECT-TYPE
      SYNTAX DisplayString
      ACCESS read-only
      STATUS mandatory
      DESCRIPTION
	  	"A textual string containing the VM Alias name"
    ::= { vmEntry 3 }
    
vmDn OBJECT-TYPE
	SYNTAX DisplayString
	ACCESS read-only
	STATUS mandatory
	DESCRIPTION
	"A textual string containing the VM Distinguished Name"
	::= { vmEntry 4 }

vmDescription OBJECT-TYPE
	SYNTAX DisplayString
	ACCESS read-only
	STATUS mandatory
	DESCRIPTION
	"A textual string containing the VM Description"
	::= { vmEntry 5 }

vmCNAName OBJECT-TYPE
	SYNTAX DisplayString
	ACCESS read-only
	STATUS mandatory
	DESCRIPTION
	"A textual string containing the VM CNA name"
	::= { vmEntry 6 }

vmCnaAliasName OBJECT-TYPE
	SYNTAX DisplayString
	ACCESS read-only
	STATUS mandatory
	DESCRIPTION
	"A textual string containing the VM CNA alias name"
	::= { vmEntry 7 }

vmCloudName OBJECT-TYPE
	SYNTAX DisplayString
	ACCESS read-only
	STATUS mandatory
	DESCRIPTION
	"A textual string containing the VM Cloud name"
	::= { vmEntry 8 }

vmClusterName OBJECT-TYPE
	SYNTAX DisplayString
	ACCESS read-only
	STATUS mandatory
	DESCRIPTION
	"A textual string containing the VM Cluster name"
	::= { vmEntry 9 }

vmClusterAliasName OBJECT-TYPE
	SYNTAX DisplayString
	ACCESS read-only
	STATUS mandatory
	DESCRIPTION
	"A textual string containing the VM Cluster alias name"
	::= { vmEntry 10 }

vmBusinessAliasName OBJECT-TYPE
	SYNTAX DisplayString
	ACCESS read-only
	STATUS mandatory
	DESCRIPTION
	"A textual string containing the VM Business alias name"
	::= { vmEntry 11 }

vmBusinessName OBJECT-TYPE
	SYNTAX DisplayString
	ACCESS read-only
	STATUS mandatory
	DESCRIPTION
	"A textual string containing the VM Business name"
	::= { vmEntry 12 }

vmCore OBJECT-TYPE
	SYNTAX INTEGER
	ACCESS read-only
	STATUS mandatory
	DESCRIPTION
	"A integer containing the number of VM Cores"
	::= { vmEntry 13 }

vmCpuLimit OBJECT-TYPE
	SYNTAX INTEGER
	ACCESS read-only
	STATUS mandatory
	DESCRIPTION
	"A integer containing the VM CPU Core limit"
	::= { vmEntry 14 }

vmCpuReserved OBJECT-TYPE
	SYNTAX INTEGER
	ACCESS read-only
	STATUS mandatory
	DESCRIPTION
	"A integer containing the VM CPU reserved"
	::= { vmEntry 15 }

vmCurrentStateCode OBJECT-TYPE
	SYNTAX INTEGER
	ACCESS read-only
	STATUS mandatory
	DESCRIPTION
	"A integer containing the VM current state code"
	::= { vmEntry 16 }

vmCurrentStateName OBJECT-TYPE
	SYNTAX DisplayString
	ACCESS read-only
	STATUS mandatory
	DESCRIPTION
	"A textual string containing the VM current state name"
	::= { vmEntry 17 }

vmDisk OBJECT-TYPE
	SYNTAX INTEGER
	ACCESS read-only
	STATUS mandatory
	DESCRIPTION
	"The VM allocated disk size in Gigabytes"
	::= { vmEntry 18 }

vmDiskCount OBJECT-TYPE
	SYNTAX INTEGER
	ACCESS read-only
	STATUS mandatory
	DESCRIPTION
	"A integer containing the VM disk count"
	::= { vmEntry 19 }

vmInstanceId OBJECT-TYPE
	SYNTAX DisplayString
	ACCESS read-only
	STATUS mandatory
	DESCRIPTION
	"A textual string containing the VM Instance ID"
	::= { vmEntry 20 }

vmIp OBJECT-TYPE
	SYNTAX DisplayString
	ACCESS read-only
	STATUS mandatory
	DESCRIPTION
	"A IP containing the VM IP address"
	::= { vmEntry 21 }

vmIsEnableHa OBJECT-TYPE
	SYNTAX DisplayString
	ACCESS read-only
	STATUS mandatory
	DESCRIPTION
	"A textual string indicating if HA is enabled for the VM"
	::= { vmEntry 22 }

vmIsoToolsStatus OBJECT-TYPE
	SYNTAX DisplayString
	ACCESS read-only
	STATUS mandatory
	DESCRIPTION
	"A textual string containing the VM ISO tools status"
	::= { vmEntry 23 }

vmLaunchTime OBJECT-TYPE
	SYNTAX DisplayString
	ACCESS read-only
	STATUS mandatory
	DESCRIPTION
	"A textual string containing the VM Launch time"
	::= { vmEntry 24 }

vmManageFlg OBJECT-TYPE
	SYNTAX DisplayString
	ACCESS read-only
	STATUS mandatory
	DESCRIPTION
	"A textual string containing the VM Manage Flag"
	::= { vmEntry 25 }

vmMem OBJECT-TYPE
	SYNTAX INTEGER
	ACCESS read-only
	STATUS mandatory
	DESCRIPTION
	"A integer containing the VM Memory details"
	::= { vmEntry 26 }

vmMemReserved OBJECT-TYPE
	SYNTAX INTEGER
	ACCESS read-only
	STATUS mandatory
	DESCRIPTION
	"A integer containing the VM Memory reserved"
	::= { vmEntry 27 }

vmNcIp OBJECT-TYPE
	SYNTAX DisplayString
	ACCESS read-only
	STATUS mandatory
	DESCRIPTION
	"A IP address containing the VM NCIP details"
	::= { vmEntry 28 }

vmNic OBJECT-TYPE
	SYNTAX INTEGER
	ACCESS read-only
	STATUS mandatory
	DESCRIPTION
	"A integer containing the number of VM Network interface cards"
	::= { vmEntry 29 }

vmOwnerId OBJECT-TYPE
	SYNTAX DisplayString
	ACCESS read-only
	STATUS mandatory
	DESCRIPTION
	"A textual string containing the VM OwnerID details"
	::= { vmEntry 30 }

vmServiceId OBJECT-TYPE
	SYNTAX DisplayString
	ACCESS read-only
	STATUS mandatory
	DESCRIPTION
	"A textual string containing the VM ServiceID details"
	::= { vmEntry 31 }

vmStorageAliasName OBJECT-TYPE
	SYNTAX DisplayString
	ACCESS read-only
	STATUS mandatory
	DESCRIPTION
	"A textual string containing the Storage alias name details"
	::= { vmEntry 32 }

vmStorageName OBJECT-TYPE
	SYNTAX DisplayString
	ACCESS read-only
	STATUS mandatory
	DESCRIPTION
	"A textual string containing the Storage name details"
	::= { vmEntry 33 }

vmSystemOsType OBJECT-TYPE
	SYNTAX DisplayString
	ACCESS read-only
	STATUS mandatory
	DESCRIPTION
	"A textual string containing the system OS type details"
	::= { vmEntry 34 }

vmVmPort OBJECT-TYPE
	SYNTAX INTEGER
	ACCESS read-only
	STATUS deprecated
	DESCRIPTION
	"A Integer containing the VM port details"
	::= { vmEntry 35 }

vmCore OBJECT-TYPE
	SYNTAX INTEGER
	ACCESS read-only
	STATUS deprecated
	DESCRIPTION
	"Obsolete"
	::= { vmEntry 36 }

vmCpuLimit OBJECT-TYPE
	SYNTAX INTEGER
	ACCESS read-only
	STATUS deprecated
	DESCRIPTION
	"Obsolete"
	::= { vmEntry 37 }

vmVm_cpu_usage_self OBJECT-TYPE
	SYNTAX INTEGER
	ACCESS read-only
	STATUS mandatory
	DESCRIPTION
	"A Integer containing the CPU Usage percent in hundredths"
	::= { vmEntry 38 }

vmVm_mem_usage_self OBJECT-TYPE
	SYNTAX INTEGER
	ACCESS read-only
	STATUS mandatory
	DESCRIPTION
	"A Integer containing VM_MEM_Usage details in hundredths"
	::= { vmEntry 39 }

vmVm_storage_usage_self OBJECT-TYPE
	SYNTAX INTEGER
	ACCESS read-only
	STATUS mandatory
	DESCRIPTION
	"A Integer containing VM_Storage details in hundredths"
	::= { vmEntry 40 }

vmcurrentStateValue OBJECT-TYPE
	SYNTAX INTEGER
	ACCESS read-only
	STATUS mandatory
	DESCRIPTION
	"A Integer value containing VM_Current state details"
	::= { vmEntry 41 }

vmclIndex OBJECT-TYPE
	SYNTAX INTEGER
	ACCESS read-only
	STATUS mandatory
	DESCRIPTION
	"The Index of the related Cloud Object"
	::= { vmEntry 42 }

vmcnaIndex OBJECT-TYPE
	SYNTAX INTEGER
	ACCESS read-only
	STATUS mandatory
	DESCRIPTION
	"The Index of the related CNA Object"
	::= { vmEntry 43 }

vmLastUpdated OBJECT-TYPE
      SYNTAX INTEGER
      ACCESS read-only
      STATUS mandatory
      DESCRIPTION
	  "The UTC timestamp indicating the last update for this object"
    ::= { vmEntry 44 }
    
vmDeltaTime OBJECT-TYPE
      SYNTAX Gauge
      ACCESS read-only
      STATUS mandatory
      DESCRIPTION
	  	"An integer indicating the expecting time in seconds between updates"
    ::= { vmEntry 45 }
    
vmMAC OBJECT-TYPE
      SYNTAX DisplayString
      ACCESS read-only
      STATUS mandatory
      DESCRIPTION
	  	"The VM MAC Address"
    ::= { vmEntry 46 }




--
--  CAMEDIATIONMANAGER HUAWEI SINGLECLOUD Switch OBJECTS
--


--
--  CAMEDIATIONMANAGER HUAWEI SINGLECLOUD Switch OBJECTS
--

swTable OBJECT-TYPE
    SYNTAX  SEQUENCE OF swEntry
    ACCESS  not-accessible
    STATUS  mandatory
    DESCRIPTION
            "A list of Switch entries."
    ::= { caMMHuaweiSingleCloud 6 }

swEntry OBJECT-TYPE
    SYNTAX  swEntry
    ACCESS  not-accessible
    STATUS  mandatory
    DESCRIPTION
            "An entry containing Switch objects"
    INDEX   { swIndex }
    ::= { swTable 1 }

swEntry ::=
    SEQUENCE {
	swIndex
		INTEGER,
	swSwitchName
		DisplayString,
	swAliasName
		DisplayString,
	swDn
		DisplayString,
	swServerSN
		DisplayString,
	swIp
		DisplayString,
	swPassword
		DisplayString,
	swPosition
		DisplayString,
	swRackName
		DisplayString,
	swRegionName
		DisplayString,
	swRoomName
		DisplayString,
	swScopeName
		DisplayString,
	swSwitchtype
		DisplayString,
	swUpport
		DisplayString,
	swZoneName
		DisplayString,
	swSwitch_flux_in
		INTEGER,
	swSwitch_flux_out
		INTEGER,
	swLastUpdated
		INTEGER,
	swDeltaTime
		Gauge
    }
    
swIndex OBJECT-TYPE
	  SYNTAX  INTEGER
	  ACCESS  read-only
	  STATUS  mandatory
	  DESCRIPTION
	  	"The Index of the Switch Object"
	  ::= { swEntry 1 }
	  
swSwitchName OBJECT-TYPE
      SYNTAX DisplayString
      ACCESS read-only
      STATUS mandatory
      DESCRIPTION
	  	"A textual string containing the Switch name"
    ::= { swEntry 2 }
    
swAliasName OBJECT-TYPE
	SYNTAX DisplayString
	ACCESS read-only
	STATUS mandatory
	DESCRIPTION
	"A textual string containing the Switch alias name"
	::= { swEntry 3 }

swDn OBJECT-TYPE
	SYNTAX DisplayString
	ACCESS read-only
	STATUS mandatory
	DESCRIPTION
	"A display string containing the Switch Distinguised name"
	::= { swEntry 4 }

swServerSN OBJECT-TYPE
	SYNTAX DisplayString
	ACCESS read-only
	STATUS mandatory
	DESCRIPTION
	"A display string containing the Switch Server Serial Number"
	::= { swEntry 5 }

swIp OBJECT-TYPE
	SYNTAX DisplayString
	ACCESS read-only
	STATUS mandatory
	DESCRIPTION
	"A IP containing the Switch IP "
	::= { swEntry 6 }

swPassword OBJECT-TYPE
	SYNTAX DisplayString
	ACCESS read-only
	STATUS mandatory
	DESCRIPTION
	"A display string containing the Switch password"
	::= { swEntry 7 }

swPosition OBJECT-TYPE
	SYNTAX DisplayString
	ACCESS read-only
	STATUS mandatory
	DESCRIPTION
	"A display string containing the Switch position"
	::= { swEntry 8 }

swRackName OBJECT-TYPE
	SYNTAX DisplayString
	ACCESS read-only
	STATUS mandatory
	DESCRIPTION
	"A display string containing the Switch rack name"
	::= { swEntry 9 }

swRegionName OBJECT-TYPE
	SYNTAX DisplayString
	ACCESS read-only
	STATUS mandatory
	DESCRIPTION
	"A display string containing the Switch region name"
	::= { swEntry 10 }

swRoomName OBJECT-TYPE
	SYNTAX DisplayString
	ACCESS read-only
	STATUS mandatory
	DESCRIPTION
	"A display string containing the Switch room name"
	::= { swEntry 11 }

swScopeName OBJECT-TYPE
	SYNTAX DisplayString
	ACCESS read-only
	STATUS mandatory
	DESCRIPTION
	"A display string containing the Switch scope name"
	::= { swEntry 12 }

swSwitchtype OBJECT-TYPE
	SYNTAX DisplayString
	ACCESS read-only
	STATUS mandatory
	DESCRIPTION
	"A display string containing the Switch type"
	::= { swEntry 13 }

swUpport OBJECT-TYPE
	SYNTAX DisplayString
	ACCESS read-only
	STATUS mandatory
	DESCRIPTION
	"A display string containing the Switch UP Link port"
	::= { swEntry 14 }

swZoneName OBJECT-TYPE
	SYNTAX DisplayString
	ACCESS read-only
	STATUS mandatory
	DESCRIPTION
	"A display string containing the Switch zone name"
	::= { swEntry 15 }

swSwitch_flux_in OBJECT-TYPE
	SYNTAX INTEGER
	ACCESS read-only
	STATUS mandatory
	DESCRIPTION
	"A Integer containing the Switch flux in"
	::= { swEntry 16 }

swSwitch_flux_out OBJECT-TYPE
	SYNTAX INTEGER
	ACCESS read-only
	STATUS mandatory
	DESCRIPTION
	"A Integer containing the Switch flux out "
	::= { swEntry 17 }

swLastUpdated OBJECT-TYPE
      SYNTAX INTEGER
      ACCESS read-only
      STATUS mandatory
      DESCRIPTION
	  	"The UTC timestamp indicating the last update for this object"
    ::= { swEntry 18 }
    
swDeltaTime OBJECT-TYPE
      SYNTAX Gauge
      ACCESS read-only
      STATUS mandatory
      DESCRIPTION
	  	"An integer indicating the expecting time in seconds between updates"
    ::= { swEntry 19 }
    
    



    
END
