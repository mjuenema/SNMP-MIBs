-- file automatically created


TELDAT-TRAP-UDP6-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


udp6TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the UDP6 event subsystem."
    REVISION "201401200930Z"
    DESCRIPTION "Initial implementation"
        ::= { telEventTraps 205 }


udp6EventsGroup	OBJECT IDENTIFIER	::= { udp6TrapsMIB 1 }

udp6Notifications	OBJECT IDENTIFIER	::= { udp6TrapsMIB 2 }
udp6NotificationsPrefix	OBJECT IDENTIFIER	::= { udp6Notifications 0 }

udp6EventObjects1 OBJECT-IDENTITY
    STATUS current
    DESCRIPTION
        "Event UDP6.1
        This message is generated when the function ip6udp starts processing the
        UDPv6 packet."
    ::= { udp6EventsGroup 1 }

udp61_source_ipv6_address OBJECT-TYPE
    SYNTAX DisplayString
    MAX-ACCESS accessible-for-notify
    STATUS current
    DESCRIPTION
        "Parameter 'source_ipv6_address' in event UDP6.1"
    ::= { udp6EventObjects1 1 }

udp61_destination_ipv6_address OBJECT-TYPE
    SYNTAX DisplayString
    MAX-ACCESS accessible-for-notify
    STATUS current
    DESCRIPTION
        "Parameter 'destination_ipv6_address' in event UDP6.1"
    ::= { udp6EventObjects1 2 }

udp61_port_number OBJECT-TYPE
    SYNTAX Integer32
    MAX-ACCESS accessible-for-notify
    STATUS current
    DESCRIPTION
        "Parameter 'port_number' in event UDP6.1"
    ::= { udp6EventObjects1 3 }

udp6EventObjects2 OBJECT-IDENTITY
    STATUS current
    DESCRIPTION
        "Event UDP6.2
        This message is generated when a packet is discarded because its
        IPv6 payload is less than its(extension headers length+ UDPv6 length)."
    ::= { udp6EventsGroup 2 }

udp62_source_ipv6_address OBJECT-TYPE
    SYNTAX DisplayString
    MAX-ACCESS accessible-for-notify
    STATUS current
    DESCRIPTION
        "Parameter 'source_ipv6_address' in event UDP6.2"
    ::= { udp6EventObjects2 1 }

udp62_length OBJECT-TYPE
    SYNTAX Integer32
    MAX-ACCESS accessible-for-notify
    STATUS current
    DESCRIPTION
        "Parameter 'length' in event UDP6.2"
    ::= { udp6EventObjects2 2 }

udp6EventObjects3 OBJECT-IDENTITY
    STATUS current
    DESCRIPTION
        "Event UDP6.3
        This message is generated when a packet is discarded because its UDPv6
        checksum field is cero."
    ::= { udp6EventsGroup 3 }

udp63_source_ipv6_address OBJECT-TYPE
    SYNTAX DisplayString
    MAX-ACCESS accessible-for-notify
    STATUS current
    DESCRIPTION
        "Parameter 'source_ipv6_address' in event UDP6.3"
    ::= { udp6EventObjects3 1 }

udp6EventObjects4 OBJECT-IDENTITY
    STATUS current
    DESCRIPTION
        "Event UDP6.4
        This message is generated when a packet is discarded because its UDPv6
        checksum field is wrong."
    ::= { udp6EventsGroup 4 }

udp64_source_ipv6_address OBJECT-TYPE
    SYNTAX DisplayString
    MAX-ACCESS accessible-for-notify
    STATUS current
    DESCRIPTION
        "Parameter 'source_ipv6_address' in event UDP6.4"
    ::= { udp6EventObjects4 1 }

udp64_checksum OBJECT-TYPE
    SYNTAX Integer32
    MAX-ACCESS accessible-for-notify
    STATUS current
    DESCRIPTION
        "Parameter 'checksum' in event UDP6.4"
    ::= { udp6EventObjects4 2 }

udp6EventObjects5 OBJECT-IDENTITY
    STATUS current
    DESCRIPTION
        "Event UDP6.5
        This message is generated when a packet is discarded because its
        destination port is CSCUDP6SOCK."
    ::= { udp6EventsGroup 5 }

udp65_source_ipv6_address OBJECT-TYPE
    SYNTAX DisplayString
    MAX-ACCESS accessible-for-notify
    STATUS current
    DESCRIPTION
        "Parameter 'source_ipv6_address' in event UDP6.5"
    ::= { udp6EventObjects5 1 }

udp65_port_number OBJECT-TYPE
    SYNTAX Integer32
    MAX-ACCESS accessible-for-notify
    STATUS current
    DESCRIPTION
        "Parameter 'port_number' in event UDP6.5"
    ::= { udp6EventObjects5 2 }

udp6EventObjects6 OBJECT-IDENTITY
    STATUS current
    DESCRIPTION
        "Event UDP6.6
        This message is generated when a packet is discarded because its
        destination port is not registered. Its destination IPv6 address is
        multicast."
    ::= { udp6EventsGroup 6 }

udp66_source_ipv6_address OBJECT-TYPE
    SYNTAX DisplayString
    MAX-ACCESS accessible-for-notify
    STATUS current
    DESCRIPTION
        "Parameter 'source_ipv6_address' in event UDP6.6"
    ::= { udp6EventObjects6 1 }

udp66_destination_ipv6_address OBJECT-TYPE
    SYNTAX DisplayString
    MAX-ACCESS accessible-for-notify
    STATUS current
    DESCRIPTION
        "Parameter 'destination_ipv6_address' in event UDP6.6"
    ::= { udp6EventObjects6 2 }

udp66_port_number OBJECT-TYPE
    SYNTAX Integer32
    MAX-ACCESS accessible-for-notify
    STATUS current
    DESCRIPTION
        "Parameter 'port_number' in event UDP6.6"
    ::= { udp6EventObjects6 3 }

udp6EventObjects7 OBJECT-IDENTITY
    STATUS current
    DESCRIPTION
        "Event UDP6.7
        This message is generated when a packet is discarded because its
        destination port is not registered. The packet was addressed
        to the router."
    ::= { udp6EventsGroup 7 }

udp67_source_ipv6_address OBJECT-TYPE
    SYNTAX DisplayString
    MAX-ACCESS accessible-for-notify
    STATUS current
    DESCRIPTION
        "Parameter 'source_ipv6_address' in event UDP6.7"
    ::= { udp6EventObjects7 1 }

udp67_destination_ipv6_address OBJECT-TYPE
    SYNTAX DisplayString
    MAX-ACCESS accessible-for-notify
    STATUS current
    DESCRIPTION
        "Parameter 'destination_ipv6_address' in event UDP6.7"
    ::= { udp6EventObjects7 2 }

udp67_port_number OBJECT-TYPE
    SYNTAX Integer32
    MAX-ACCESS accessible-for-notify
    STATUS current
    DESCRIPTION
        "Parameter 'port_number' in event UDP6.7"
    ::= { udp6EventObjects7 3 }

udp6EventObjects8 OBJECT-IDENTITY
    STATUS current
    DESCRIPTION
        "Event UDP6.8
        This message is generated when a packet is discarded because the upcall
        associated to the registered destination port discards the packet."
    ::= { udp6EventsGroup 8 }

udp68_port_number OBJECT-TYPE
    SYNTAX Integer32
    MAX-ACCESS accessible-for-notify
    STATUS current
    DESCRIPTION
        "Parameter 'port_number' in event UDP6.8"
    ::= { udp6EventObjects8 1 }

udp6EventObjects9 OBJECT-IDENTITY
    STATUS current
    DESCRIPTION
        "Event UDP6.9
        This message shows the hook for the UDPv6 packet."
    ::= { udp6EventsGroup 9 }

udp69_port_number OBJECT-TYPE
    SYNTAX Integer32
    MAX-ACCESS accessible-for-notify
    STATUS current
    DESCRIPTION
        "Parameter 'port_number' in event UDP6.9"
    ::= { udp6EventObjects9 1 }

udp69_ifc_number OBJECT-TYPE
    SYNTAX Integer32
    MAX-ACCESS accessible-for-notify
    STATUS current
    DESCRIPTION
        "Parameter 'ifc_number' in event UDP6.9"
    ::= { udp6EventObjects9 2 }

udp69_address OBJECT-TYPE
    SYNTAX DisplayString
    MAX-ACCESS accessible-for-notify
    STATUS current
    DESCRIPTION
        "Parameter 'address' in event UDP6.9"
    ::= { udp6EventObjects9 3 }


udp6Notification1 NOTIFICATION-TYPE
    OBJECTS { 
              udp61_source_ipv6_address, 
              udp61_destination_ipv6_address,
              udp61_port_number 
            }
    STATUS current
    DESCRIPTION
        "Notification of Event UDP6.1

        Message: 'Packet from $1 for $2 port $3'

        Parameters list:
              $1: udp61_source_ipv6_address
              $2: udp61_destination_ipv6_address
              $3: udp61_port_number

        This message is generated when the function ip6udp starts processing the
        UDPv6 packet."
    ::= { udp6NotificationsPrefix 1 }

udp6Notification2 NOTIFICATION-TYPE
    OBJECTS { 
              udp62_source_ipv6_address, 
              udp62_length 
            }
    STATUS current
    DESCRIPTION
        "Notification of Event UDP6.2

        Message: 'Discarded packet from $1, bad length $2'

        Parameters list:
              $1: udp62_source_ipv6_address
              $2: udp62_length

        This message is generated when a packet is discarded because its
        IPv6 payload is less than its(extension headers length+ UDPv6 length)."
    ::= { udp6NotificationsPrefix 2 }

udp6Notification3 NOTIFICATION-TYPE
    OBJECTS { 
              udp63_source_ipv6_address 
            }
    STATUS current
    DESCRIPTION
        "Notification of Event UDP6.3

        Message: 'Discarded packet from $1 checksum cero'

        Parameters list:
              $1: udp63_source_ipv6_address

        This message is generated when a packet is discarded because its UDPv6
        checksum field is cero."
    ::= { udp6NotificationsPrefix 3 }

udp6Notification4 NOTIFICATION-TYPE
    OBJECTS { 
              udp64_source_ipv6_address, 
              udp64_checksum,
              udp64_checksum 
            }
    STATUS current
    DESCRIPTION
        "Notification of Event UDP6.4

        Message: 'Discarded packet from $1 bad checksum: calculated $2, received $3'

        Parameters list:
              $1: udp64_source_ipv6_address
              $2: udp64_checksum
              $3: udp64_checksum

        This message is generated when a packet is discarded because its UDPv6
        checksum field is wrong."
    ::= { udp6NotificationsPrefix 4 }

udp6Notification5 NOTIFICATION-TYPE
    OBJECTS { 
              udp65_source_ipv6_address, 
              udp65_port_number 
            }
    STATUS current
    DESCRIPTION
        "Notification of Event UDP6.5

        Message: 'Discarded packet from $1 port $2 (CSCUDP6SOCK)'

        Parameters list:
              $1: udp65_source_ipv6_address
              $2: udp65_port_number

        This message is generated when a packet is discarded because its
        destination port is CSCUDP6SOCK."
    ::= { udp6NotificationsPrefix 5 }

udp6Notification6 NOTIFICATION-TYPE
    OBJECTS { 
              udp66_source_ipv6_address, 
              udp66_destination_ipv6_address,
              udp66_port_number 
            }
    STATUS current
    DESCRIPTION
        "Notification of Event UDP6.6

        Message: 'Discarded packet from $1 for $2 port $3 unregistered'

        Parameters list:
              $1: udp66_source_ipv6_address
              $2: udp66_destination_ipv6_address
              $3: udp66_port_number

        This message is generated when a packet is discarded because its
        destination port is not registered. Its destination IPv6 address is
        multicast."
    ::= { udp6NotificationsPrefix 6 }

udp6Notification7 NOTIFICATION-TYPE
    OBJECTS { 
              udp67_source_ipv6_address, 
              udp67_destination_ipv6_address,
              udp67_port_number 
            }
    STATUS current
    DESCRIPTION
        "Notification of Event UDP6.7

        Message: 'Discarded packet from $1 for$2 port $3 nunregistered'

        Parameters list:
              $1: udp67_source_ipv6_address
              $2: udp67_destination_ipv6_address
              $3: udp67_port_number

        This message is generated when a packet is discarded because its
        destination port is not registered. The packet was addressed
        to the router."
    ::= { udp6NotificationsPrefix 7 }

udp6Notification8 NOTIFICATION-TYPE
    OBJECTS { 
              udp68_port_number 
            }
    STATUS current
    DESCRIPTION
        "Notification of Event UDP6.8

        Message: 'port $1 registered'

        Parameters list:
              $1: udp68_port_number

        This message is generated when a packet is discarded because the upcall
        associated to the registered destination port discards the packet."
    ::= { udp6NotificationsPrefix 8 }

udp6Notification9 NOTIFICATION-TYPE
    OBJECTS { 
              udp69_port_number, 
              udp69_ifc_number,
              udp69_address 
            }
    STATUS current
    DESCRIPTION
        "Notification of Event UDP6.9

        Message: 'hook: port $1 interface $2 address $3'

        Parameters list:
              $1: udp69_port_number
              $2: udp69_ifc_number
              $3: udp69_address

        This message shows the hook for the UDPv6 packet."
    ::= { udp6NotificationsPrefix 9 }


END
