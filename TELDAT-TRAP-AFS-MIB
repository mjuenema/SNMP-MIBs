-- file automatically created


TELDAT-TRAP-AFS-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


afsTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the AFS event subsystem."
    REVISION "201401200930Z"
    DESCRIPTION "Initial implementation"
        ::= { telEventTraps 199 }


afsEventsGroup	OBJECT IDENTIFIER	::= { afsTrapsMIB 1 }

afsNotifications	OBJECT IDENTIFIER	::= { afsTrapsMIB 2 }
afsNotificationsPrefix	OBJECT IDENTIFIER	::= { afsNotifications 0 }

afsEventObjects1 OBJECT-IDENTITY
    STATUS current
    DESCRIPTION
        "Event AFS.1
        an in ip packet has been accepted"
    ::= { afsEventsGroup 1 }

afs1_ip-source OBJECT-TYPE
    SYNTAX IpAddress
    MAX-ACCESS accessible-for-notify
    STATUS current
    DESCRIPTION
        "Parameter 'ip-source' in event AFS.1"
    ::= { afsEventObjects1 1 }

afs1_ip-destination OBJECT-TYPE
    SYNTAX IpAddress
    MAX-ACCESS accessible-for-notify
    STATUS current
    DESCRIPTION
        "Parameter 'ip-destination' in event AFS.1"
    ::= { afsEventObjects1 2 }

afs1_protocol OBJECT-TYPE
    SYNTAX DisplayString
    MAX-ACCESS accessible-for-notify
    STATUS current
    DESCRIPTION
        "Parameter 'protocol' in event AFS.1"
    ::= { afsEventObjects1 3 }

afs1_in-ifc OBJECT-TYPE
    SYNTAX DisplayString
    MAX-ACCESS accessible-for-notify
    STATUS current
    DESCRIPTION
        "Parameter 'in-ifc' in event AFS.1"
    ::= { afsEventObjects1 4 }

afsEventObjects2 OBJECT-IDENTITY
    STATUS current
    DESCRIPTION
        "Event AFS.2
        an in ip packet has been discarded"
    ::= { afsEventsGroup 2 }

afs2_ip-source OBJECT-TYPE
    SYNTAX IpAddress
    MAX-ACCESS accessible-for-notify
    STATUS current
    DESCRIPTION
        "Parameter 'ip-source' in event AFS.2"
    ::= { afsEventObjects2 1 }

afs2_ip-destination OBJECT-TYPE
    SYNTAX IpAddress
    MAX-ACCESS accessible-for-notify
    STATUS current
    DESCRIPTION
        "Parameter 'ip-destination' in event AFS.2"
    ::= { afsEventObjects2 2 }

afs2_protocol OBJECT-TYPE
    SYNTAX DisplayString
    MAX-ACCESS accessible-for-notify
    STATUS current
    DESCRIPTION
        "Parameter 'protocol' in event AFS.2"
    ::= { afsEventObjects2 3 }

afs2_in-ifc OBJECT-TYPE
    SYNTAX DisplayString
    MAX-ACCESS accessible-for-notify
    STATUS current
    DESCRIPTION
        "Parameter 'in-ifc' in event AFS.2"
    ::= { afsEventObjects2 4 }

afsEventObjects3 OBJECT-IDENTITY
    STATUS current
    DESCRIPTION
        "Event AFS.3
        an out ip packet has been accepted"
    ::= { afsEventsGroup 3 }

afs3_ip-source OBJECT-TYPE
    SYNTAX IpAddress
    MAX-ACCESS accessible-for-notify
    STATUS current
    DESCRIPTION
        "Parameter 'ip-source' in event AFS.3"
    ::= { afsEventObjects3 1 }

afs3_ip-destination OBJECT-TYPE
    SYNTAX IpAddress
    MAX-ACCESS accessible-for-notify
    STATUS current
    DESCRIPTION
        "Parameter 'ip-destination' in event AFS.3"
    ::= { afsEventObjects3 2 }

afs3_protocol OBJECT-TYPE
    SYNTAX DisplayString
    MAX-ACCESS accessible-for-notify
    STATUS current
    DESCRIPTION
        "Parameter 'protocol' in event AFS.3"
    ::= { afsEventObjects3 3 }

afs3_in-ifc OBJECT-TYPE
    SYNTAX DisplayString
    MAX-ACCESS accessible-for-notify
    STATUS current
    DESCRIPTION
        "Parameter 'in-ifc' in event AFS.3"
    ::= { afsEventObjects3 4 }

afs3_out-ifc OBJECT-TYPE
    SYNTAX DisplayString
    MAX-ACCESS accessible-for-notify
    STATUS current
    DESCRIPTION
        "Parameter 'out-ifc' in event AFS.3"
    ::= { afsEventObjects3 5 }

afsEventObjects4 OBJECT-IDENTITY
    STATUS current
    DESCRIPTION
        "Event AFS.4
        an out ip packet has been discarded"
    ::= { afsEventsGroup 4 }

afs4_ip-source OBJECT-TYPE
    SYNTAX IpAddress
    MAX-ACCESS accessible-for-notify
    STATUS current
    DESCRIPTION
        "Parameter 'ip-source' in event AFS.4"
    ::= { afsEventObjects4 1 }

afs4_ip-destination OBJECT-TYPE
    SYNTAX IpAddress
    MAX-ACCESS accessible-for-notify
    STATUS current
    DESCRIPTION
        "Parameter 'ip-destination' in event AFS.4"
    ::= { afsEventObjects4 2 }

afs4_protocol OBJECT-TYPE
    SYNTAX DisplayString
    MAX-ACCESS accessible-for-notify
    STATUS current
    DESCRIPTION
        "Parameter 'protocol' in event AFS.4"
    ::= { afsEventObjects4 3 }

afs4_in-ifc OBJECT-TYPE
    SYNTAX DisplayString
    MAX-ACCESS accessible-for-notify
    STATUS current
    DESCRIPTION
        "Parameter 'in-ifc' in event AFS.4"
    ::= { afsEventObjects4 4 }

afs4_out-ifc OBJECT-TYPE
    SYNTAX DisplayString
    MAX-ACCESS accessible-for-notify
    STATUS current
    DESCRIPTION
        "Parameter 'out-ifc' in event AFS.4"
    ::= { afsEventObjects4 5 }

afsEventObjects5 OBJECT-IDENTITY
    STATUS current
    DESCRIPTION
        "Event AFS.5
        an local-in ip packet has been accepted"
    ::= { afsEventsGroup 5 }

afs5_ip-source OBJECT-TYPE
    SYNTAX IpAddress
    MAX-ACCESS accessible-for-notify
    STATUS current
    DESCRIPTION
        "Parameter 'ip-source' in event AFS.5"
    ::= { afsEventObjects5 1 }

afs5_ip-destination OBJECT-TYPE
    SYNTAX IpAddress
    MAX-ACCESS accessible-for-notify
    STATUS current
    DESCRIPTION
        "Parameter 'ip-destination' in event AFS.5"
    ::= { afsEventObjects5 2 }

afs5_protocol OBJECT-TYPE
    SYNTAX DisplayString
    MAX-ACCESS accessible-for-notify
    STATUS current
    DESCRIPTION
        "Parameter 'protocol' in event AFS.5"
    ::= { afsEventObjects5 3 }

afs5_in-ifc OBJECT-TYPE
    SYNTAX DisplayString
    MAX-ACCESS accessible-for-notify
    STATUS current
    DESCRIPTION
        "Parameter 'in-ifc' in event AFS.5"
    ::= { afsEventObjects5 4 }

afsEventObjects6 OBJECT-IDENTITY
    STATUS current
    DESCRIPTION
        "Event AFS.6
        a local-in ip packet has been discarded"
    ::= { afsEventsGroup 6 }

afs6_ip-source OBJECT-TYPE
    SYNTAX IpAddress
    MAX-ACCESS accessible-for-notify
    STATUS current
    DESCRIPTION
        "Parameter 'ip-source' in event AFS.6"
    ::= { afsEventObjects6 1 }

afs6_ip-destination OBJECT-TYPE
    SYNTAX IpAddress
    MAX-ACCESS accessible-for-notify
    STATUS current
    DESCRIPTION
        "Parameter 'ip-destination' in event AFS.6"
    ::= { afsEventObjects6 2 }

afs6_protocol OBJECT-TYPE
    SYNTAX DisplayString
    MAX-ACCESS accessible-for-notify
    STATUS current
    DESCRIPTION
        "Parameter 'protocol' in event AFS.6"
    ::= { afsEventObjects6 3 }

afs6_in-ifc OBJECT-TYPE
    SYNTAX DisplayString
    MAX-ACCESS accessible-for-notify
    STATUS current
    DESCRIPTION
        "Parameter 'in-ifc' in event AFS.6"
    ::= { afsEventObjects6 4 }

afsEventObjects7 OBJECT-IDENTITY
    STATUS current
    DESCRIPTION
        "Event AFS.7
        a local-out ip packet has been accepted"
    ::= { afsEventsGroup 7 }

afs7_ip-source OBJECT-TYPE
    SYNTAX IpAddress
    MAX-ACCESS accessible-for-notify
    STATUS current
    DESCRIPTION
        "Parameter 'ip-source' in event AFS.7"
    ::= { afsEventObjects7 1 }

afs7_ip-destination OBJECT-TYPE
    SYNTAX IpAddress
    MAX-ACCESS accessible-for-notify
    STATUS current
    DESCRIPTION
        "Parameter 'ip-destination' in event AFS.7"
    ::= { afsEventObjects7 2 }

afs7_protocol OBJECT-TYPE
    SYNTAX DisplayString
    MAX-ACCESS accessible-for-notify
    STATUS current
    DESCRIPTION
        "Parameter 'protocol' in event AFS.7"
    ::= { afsEventObjects7 3 }

afs7_out-ifc OBJECT-TYPE
    SYNTAX DisplayString
    MAX-ACCESS accessible-for-notify
    STATUS current
    DESCRIPTION
        "Parameter 'out-ifc' in event AFS.7"
    ::= { afsEventObjects7 4 }

afsEventObjects8 OBJECT-IDENTITY
    STATUS current
    DESCRIPTION
        "Event AFS.8
        a local-out ip packet has been discarded"
    ::= { afsEventsGroup 8 }

afs8_ip-source OBJECT-TYPE
    SYNTAX IpAddress
    MAX-ACCESS accessible-for-notify
    STATUS current
    DESCRIPTION
        "Parameter 'ip-source' in event AFS.8"
    ::= { afsEventObjects8 1 }

afs8_ip-destination OBJECT-TYPE
    SYNTAX IpAddress
    MAX-ACCESS accessible-for-notify
    STATUS current
    DESCRIPTION
        "Parameter 'ip-destination' in event AFS.8"
    ::= { afsEventObjects8 2 }

afs8_protocol OBJECT-TYPE
    SYNTAX DisplayString
    MAX-ACCESS accessible-for-notify
    STATUS current
    DESCRIPTION
        "Parameter 'protocol' in event AFS.8"
    ::= { afsEventObjects8 3 }

afs8_out-ifc OBJECT-TYPE
    SYNTAX DisplayString
    MAX-ACCESS accessible-for-notify
    STATUS current
    DESCRIPTION
        "Parameter 'out-ifc' in event AFS.8"
    ::= { afsEventObjects8 4 }

afsEventObjects9 OBJECT-IDENTITY
    STATUS current
    DESCRIPTION
        "Event AFS.9
        an incoming IP packet has matched a nat rule"
    ::= { afsEventsGroup 9 }

afs9_rule OBJECT-TYPE
    SYNTAX Integer32
    MAX-ACCESS accessible-for-notify
    STATUS current
    DESCRIPTION
        "Parameter 'rule' in event AFS.9"
    ::= { afsEventObjects9 1 }

afs9_acc-list OBJECT-TYPE
    SYNTAX Integer32
    MAX-ACCESS accessible-for-notify
    STATUS current
    DESCRIPTION
        "Parameter 'acc-list' in event AFS.9"
    ::= { afsEventObjects9 2 }

afs9_entry OBJECT-TYPE
    SYNTAX Integer32
    MAX-ACCESS accessible-for-notify
    STATUS current
    DESCRIPTION
        "Parameter 'entry' in event AFS.9"
    ::= { afsEventObjects9 3 }

afs9_ip-source OBJECT-TYPE
    SYNTAX IpAddress
    MAX-ACCESS accessible-for-notify
    STATUS current
    DESCRIPTION
        "Parameter 'ip-source' in event AFS.9"
    ::= { afsEventObjects9 4 }

afs9_ip-destination OBJECT-TYPE
    SYNTAX IpAddress
    MAX-ACCESS accessible-for-notify
    STATUS current
    DESCRIPTION
        "Parameter 'ip-destination' in event AFS.9"
    ::= { afsEventObjects9 5 }

afs9_protocol OBJECT-TYPE
    SYNTAX DisplayString
    MAX-ACCESS accessible-for-notify
    STATUS current
    DESCRIPTION
        "Parameter 'protocol' in event AFS.9"
    ::= { afsEventObjects9 6 }

afs9_in-ifc OBJECT-TYPE
    SYNTAX DisplayString
    MAX-ACCESS accessible-for-notify
    STATUS current
    DESCRIPTION
        "Parameter 'in-ifc' in event AFS.9"
    ::= { afsEventObjects9 7 }

afsEventObjects10 OBJECT-IDENTITY
    STATUS current
    DESCRIPTION
        "Event AFS.10
        an outgoing IP packet has matched a nat rule"
    ::= { afsEventsGroup 10 }

afs10_rule OBJECT-TYPE
    SYNTAX Integer32
    MAX-ACCESS accessible-for-notify
    STATUS current
    DESCRIPTION
        "Parameter 'rule' in event AFS.10"
    ::= { afsEventObjects10 1 }

afs10_acc-list OBJECT-TYPE
    SYNTAX Integer32
    MAX-ACCESS accessible-for-notify
    STATUS current
    DESCRIPTION
        "Parameter 'acc-list' in event AFS.10"
    ::= { afsEventObjects10 2 }

afs10_entry OBJECT-TYPE
    SYNTAX Integer32
    MAX-ACCESS accessible-for-notify
    STATUS current
    DESCRIPTION
        "Parameter 'entry' in event AFS.10"
    ::= { afsEventObjects10 3 }

afs10_ip-source OBJECT-TYPE
    SYNTAX IpAddress
    MAX-ACCESS accessible-for-notify
    STATUS current
    DESCRIPTION
        "Parameter 'ip-source' in event AFS.10"
    ::= { afsEventObjects10 4 }

afs10_ip-destination OBJECT-TYPE
    SYNTAX IpAddress
    MAX-ACCESS accessible-for-notify
    STATUS current
    DESCRIPTION
        "Parameter 'ip-destination' in event AFS.10"
    ::= { afsEventObjects10 5 }

afs10_protocol OBJECT-TYPE
    SYNTAX DisplayString
    MAX-ACCESS accessible-for-notify
    STATUS current
    DESCRIPTION
        "Parameter 'protocol' in event AFS.10"
    ::= { afsEventObjects10 6 }

afs10_in-ifc OBJECT-TYPE
    SYNTAX DisplayString
    MAX-ACCESS accessible-for-notify
    STATUS current
    DESCRIPTION
        "Parameter 'in-ifc' in event AFS.10"
    ::= { afsEventObjects10 7 }

afs10_out-ifc OBJECT-TYPE
    SYNTAX DisplayString
    MAX-ACCESS accessible-for-notify
    STATUS current
    DESCRIPTION
        "Parameter 'out-ifc' in event AFS.10"
    ::= { afsEventObjects10 8 }

afsEventObjects11 OBJECT-IDENTITY
    STATUS current
    DESCRIPTION
        "Event AFS.11
        an ip packet has been natted"
    ::= { afsEventsGroup 11 }

afs11_protocol OBJECT-TYPE
    SYNTAX DisplayString
    MAX-ACCESS accessible-for-notify
    STATUS current
    DESCRIPTION
        "Parameter 'protocol' in event AFS.11"
    ::= { afsEventObjects11 1 }

afs11_ip-src OBJECT-TYPE
    SYNTAX IpAddress
    MAX-ACCESS accessible-for-notify
    STATUS current
    DESCRIPTION
        "Parameter 'ip-src' in event AFS.11"
    ::= { afsEventObjects11 2 }

afs11_ip-dst OBJECT-TYPE
    SYNTAX IpAddress
    MAX-ACCESS accessible-for-notify
    STATUS current
    DESCRIPTION
        "Parameter 'ip-dst' in event AFS.11"
    ::= { afsEventObjects11 3 }

afs11_natip-src OBJECT-TYPE
    SYNTAX IpAddress
    MAX-ACCESS accessible-for-notify
    STATUS current
    DESCRIPTION
        "Parameter 'natip-src' in event AFS.11"
    ::= { afsEventObjects11 4 }

afs11_natip-dst OBJECT-TYPE
    SYNTAX IpAddress
    MAX-ACCESS accessible-for-notify
    STATUS current
    DESCRIPTION
        "Parameter 'natip-dst' in event AFS.11"
    ::= { afsEventObjects11 5 }

afsEventObjects12 OBJECT-IDENTITY
    STATUS current
    DESCRIPTION
        "Event AFS.12
        an in ip packet has been accepted by a filter rule"
    ::= { afsEventsGroup 12 }

afs12_in-ifc OBJECT-TYPE
    SYNTAX DisplayString
    MAX-ACCESS accessible-for-notify
    STATUS current
    DESCRIPTION
        "Parameter 'in-ifc' in event AFS.12"
    ::= { afsEventObjects12 1 }

afs12_access-list OBJECT-TYPE
    SYNTAX Integer32
    MAX-ACCESS accessible-for-notify
    STATUS current
    DESCRIPTION
        "Parameter 'access-list' in event AFS.12"
    ::= { afsEventObjects12 2 }

afs12_entry OBJECT-TYPE
    SYNTAX Integer32
    MAX-ACCESS accessible-for-notify
    STATUS current
    DESCRIPTION
        "Parameter 'entry' in event AFS.12"
    ::= { afsEventObjects12 3 }

afs12_ip-source OBJECT-TYPE
    SYNTAX IpAddress
    MAX-ACCESS accessible-for-notify
    STATUS current
    DESCRIPTION
        "Parameter 'ip-source' in event AFS.12"
    ::= { afsEventObjects12 4 }

afs12_ip-destination OBJECT-TYPE
    SYNTAX IpAddress
    MAX-ACCESS accessible-for-notify
    STATUS current
    DESCRIPTION
        "Parameter 'ip-destination' in event AFS.12"
    ::= { afsEventObjects12 5 }

afs12_protocol OBJECT-TYPE
    SYNTAX DisplayString
    MAX-ACCESS accessible-for-notify
    STATUS current
    DESCRIPTION
        "Parameter 'protocol' in event AFS.12"
    ::= { afsEventObjects12 6 }

afsEventObjects13 OBJECT-IDENTITY
    STATUS current
    DESCRIPTION
        "Event AFS.13
        an in ip packet has been discarded by a filter rule"
    ::= { afsEventsGroup 13 }

afs13_in-ifc OBJECT-TYPE
    SYNTAX DisplayString
    MAX-ACCESS accessible-for-notify
    STATUS current
    DESCRIPTION
        "Parameter 'in-ifc' in event AFS.13"
    ::= { afsEventObjects13 1 }

afs13_access-list OBJECT-TYPE
    SYNTAX Integer32
    MAX-ACCESS accessible-for-notify
    STATUS current
    DESCRIPTION
        "Parameter 'access-list' in event AFS.13"
    ::= { afsEventObjects13 2 }

afs13_entry OBJECT-TYPE
    SYNTAX Integer32
    MAX-ACCESS accessible-for-notify
    STATUS current
    DESCRIPTION
        "Parameter 'entry' in event AFS.13"
    ::= { afsEventObjects13 3 }

afs13_ip-source OBJECT-TYPE
    SYNTAX IpAddress
    MAX-ACCESS accessible-for-notify
    STATUS current
    DESCRIPTION
        "Parameter 'ip-source' in event AFS.13"
    ::= { afsEventObjects13 4 }

afs13_ip-destination OBJECT-TYPE
    SYNTAX IpAddress
    MAX-ACCESS accessible-for-notify
    STATUS current
    DESCRIPTION
        "Parameter 'ip-destination' in event AFS.13"
    ::= { afsEventObjects13 5 }

afs13_protocol OBJECT-TYPE
    SYNTAX DisplayString
    MAX-ACCESS accessible-for-notify
    STATUS current
    DESCRIPTION
        "Parameter 'protocol' in event AFS.13"
    ::= { afsEventObjects13 6 }

afsEventObjects14 OBJECT-IDENTITY
    STATUS current
    DESCRIPTION
        "Event AFS.14
        an out ip packet has been accepted by a filter rule"
    ::= { afsEventsGroup 14 }

afs14_out-ifc OBJECT-TYPE
    SYNTAX DisplayString
    MAX-ACCESS accessible-for-notify
    STATUS current
    DESCRIPTION
        "Parameter 'out-ifc' in event AFS.14"
    ::= { afsEventObjects14 1 }

afs14_access-list OBJECT-TYPE
    SYNTAX Integer32
    MAX-ACCESS accessible-for-notify
    STATUS current
    DESCRIPTION
        "Parameter 'access-list' in event AFS.14"
    ::= { afsEventObjects14 2 }

afs14_entry OBJECT-TYPE
    SYNTAX Integer32
    MAX-ACCESS accessible-for-notify
    STATUS current
    DESCRIPTION
        "Parameter 'entry' in event AFS.14"
    ::= { afsEventObjects14 3 }

afs14_ip-source OBJECT-TYPE
    SYNTAX IpAddress
    MAX-ACCESS accessible-for-notify
    STATUS current
    DESCRIPTION
        "Parameter 'ip-source' in event AFS.14"
    ::= { afsEventObjects14 4 }

afs14_ip-destination OBJECT-TYPE
    SYNTAX IpAddress
    MAX-ACCESS accessible-for-notify
    STATUS current
    DESCRIPTION
        "Parameter 'ip-destination' in event AFS.14"
    ::= { afsEventObjects14 5 }

afs14_protocol OBJECT-TYPE
    SYNTAX DisplayString
    MAX-ACCESS accessible-for-notify
    STATUS current
    DESCRIPTION
        "Parameter 'protocol' in event AFS.14"
    ::= { afsEventObjects14 6 }

afs14_in-ifc OBJECT-TYPE
    SYNTAX DisplayString
    MAX-ACCESS accessible-for-notify
    STATUS current
    DESCRIPTION
        "Parameter 'in-ifc' in event AFS.14"
    ::= { afsEventObjects14 7 }

afsEventObjects15 OBJECT-IDENTITY
    STATUS current
    DESCRIPTION
        "Event AFS.15
        an out ip packet has been discarded by a filter rule"
    ::= { afsEventsGroup 15 }

afs15_out-ifc OBJECT-TYPE
    SYNTAX DisplayString
    MAX-ACCESS accessible-for-notify
    STATUS current
    DESCRIPTION
        "Parameter 'out-ifc' in event AFS.15"
    ::= { afsEventObjects15 1 }

afs15_access-list OBJECT-TYPE
    SYNTAX Integer32
    MAX-ACCESS accessible-for-notify
    STATUS current
    DESCRIPTION
        "Parameter 'access-list' in event AFS.15"
    ::= { afsEventObjects15 2 }

afs15_entry OBJECT-TYPE
    SYNTAX Integer32
    MAX-ACCESS accessible-for-notify
    STATUS current
    DESCRIPTION
        "Parameter 'entry' in event AFS.15"
    ::= { afsEventObjects15 3 }

afs15_ip-source OBJECT-TYPE
    SYNTAX IpAddress
    MAX-ACCESS accessible-for-notify
    STATUS current
    DESCRIPTION
        "Parameter 'ip-source' in event AFS.15"
    ::= { afsEventObjects15 4 }

afs15_ip-destination OBJECT-TYPE
    SYNTAX IpAddress
    MAX-ACCESS accessible-for-notify
    STATUS current
    DESCRIPTION
        "Parameter 'ip-destination' in event AFS.15"
    ::= { afsEventObjects15 5 }

afs15_protocol OBJECT-TYPE
    SYNTAX DisplayString
    MAX-ACCESS accessible-for-notify
    STATUS current
    DESCRIPTION
        "Parameter 'protocol' in event AFS.15"
    ::= { afsEventObjects15 6 }

afs15_in-ifc OBJECT-TYPE
    SYNTAX DisplayString
    MAX-ACCESS accessible-for-notify
    STATUS current
    DESCRIPTION
        "Parameter 'in-ifc' in event AFS.15"
    ::= { afsEventObjects15 7 }

afsEventObjects16 OBJECT-IDENTITY
    STATUS current
    DESCRIPTION
        "Event AFS.16
        an local-in ip packet has been accepted by a filter rule"
    ::= { afsEventsGroup 16 }

afs16_access-list OBJECT-TYPE
    SYNTAX Integer32
    MAX-ACCESS accessible-for-notify
    STATUS current
    DESCRIPTION
        "Parameter 'access-list' in event AFS.16"
    ::= { afsEventObjects16 1 }

afs16_entry OBJECT-TYPE
    SYNTAX Integer32
    MAX-ACCESS accessible-for-notify
    STATUS current
    DESCRIPTION
        "Parameter 'entry' in event AFS.16"
    ::= { afsEventObjects16 2 }

afs16_ip-source OBJECT-TYPE
    SYNTAX IpAddress
    MAX-ACCESS accessible-for-notify
    STATUS current
    DESCRIPTION
        "Parameter 'ip-source' in event AFS.16"
    ::= { afsEventObjects16 3 }

afs16_ip-destination OBJECT-TYPE
    SYNTAX IpAddress
    MAX-ACCESS accessible-for-notify
    STATUS current
    DESCRIPTION
        "Parameter 'ip-destination' in event AFS.16"
    ::= { afsEventObjects16 4 }

afs16_protocol OBJECT-TYPE
    SYNTAX DisplayString
    MAX-ACCESS accessible-for-notify
    STATUS current
    DESCRIPTION
        "Parameter 'protocol' in event AFS.16"
    ::= { afsEventObjects16 5 }

afs16_in-ifc OBJECT-TYPE
    SYNTAX DisplayString
    MAX-ACCESS accessible-for-notify
    STATUS current
    DESCRIPTION
        "Parameter 'in-ifc' in event AFS.16"
    ::= { afsEventObjects16 6 }

afsEventObjects17 OBJECT-IDENTITY
    STATUS current
    DESCRIPTION
        "Event AFS.17
        a local-in ip packet has been discarded by a filter rule"
    ::= { afsEventsGroup 17 }

afs17_access-list OBJECT-TYPE
    SYNTAX Integer32
    MAX-ACCESS accessible-for-notify
    STATUS current
    DESCRIPTION
        "Parameter 'access-list' in event AFS.17"
    ::= { afsEventObjects17 1 }

afs17_entry OBJECT-TYPE
    SYNTAX Integer32
    MAX-ACCESS accessible-for-notify
    STATUS current
    DESCRIPTION
        "Parameter 'entry' in event AFS.17"
    ::= { afsEventObjects17 2 }

afs17_ip-source OBJECT-TYPE
    SYNTAX IpAddress
    MAX-ACCESS accessible-for-notify
    STATUS current
    DESCRIPTION
        "Parameter 'ip-source' in event AFS.17"
    ::= { afsEventObjects17 3 }

afs17_ip-destination OBJECT-TYPE
    SYNTAX IpAddress
    MAX-ACCESS accessible-for-notify
    STATUS current
    DESCRIPTION
        "Parameter 'ip-destination' in event AFS.17"
    ::= { afsEventObjects17 4 }

afs17_protocol OBJECT-TYPE
    SYNTAX DisplayString
    MAX-ACCESS accessible-for-notify
    STATUS current
    DESCRIPTION
        "Parameter 'protocol' in event AFS.17"
    ::= { afsEventObjects17 5 }

afs17_in-ifc OBJECT-TYPE
    SYNTAX DisplayString
    MAX-ACCESS accessible-for-notify
    STATUS current
    DESCRIPTION
        "Parameter 'in-ifc' in event AFS.17"
    ::= { afsEventObjects17 6 }

afsEventObjects18 OBJECT-IDENTITY
    STATUS current
    DESCRIPTION
        "Event AFS.18
        a local-out ip packet has been accepted by a filter rule"
    ::= { afsEventsGroup 18 }

afs18_access-list OBJECT-TYPE
    SYNTAX Integer32
    MAX-ACCESS accessible-for-notify
    STATUS current
    DESCRIPTION
        "Parameter 'access-list' in event AFS.18"
    ::= { afsEventObjects18 1 }

afs18_entry OBJECT-TYPE
    SYNTAX Integer32
    MAX-ACCESS accessible-for-notify
    STATUS current
    DESCRIPTION
        "Parameter 'entry' in event AFS.18"
    ::= { afsEventObjects18 2 }

afs18_ip-source OBJECT-TYPE
    SYNTAX IpAddress
    MAX-ACCESS accessible-for-notify
    STATUS current
    DESCRIPTION
        "Parameter 'ip-source' in event AFS.18"
    ::= { afsEventObjects18 3 }

afs18_ip-destination OBJECT-TYPE
    SYNTAX IpAddress
    MAX-ACCESS accessible-for-notify
    STATUS current
    DESCRIPTION
        "Parameter 'ip-destination' in event AFS.18"
    ::= { afsEventObjects18 4 }

afs18_protocol OBJECT-TYPE
    SYNTAX DisplayString
    MAX-ACCESS accessible-for-notify
    STATUS current
    DESCRIPTION
        "Parameter 'protocol' in event AFS.18"
    ::= { afsEventObjects18 5 }

afs18_out-ifc OBJECT-TYPE
    SYNTAX DisplayString
    MAX-ACCESS accessible-for-notify
    STATUS current
    DESCRIPTION
        "Parameter 'out-ifc' in event AFS.18"
    ::= { afsEventObjects18 6 }

afsEventObjects19 OBJECT-IDENTITY
    STATUS current
    DESCRIPTION
        "Event AFS.19
        a local-out ip packet has been discarded by a filter rule"
    ::= { afsEventsGroup 19 }

afs19_access-list OBJECT-TYPE
    SYNTAX Integer32
    MAX-ACCESS accessible-for-notify
    STATUS current
    DESCRIPTION
        "Parameter 'access-list' in event AFS.19"
    ::= { afsEventObjects19 1 }

afs19_entry OBJECT-TYPE
    SYNTAX Integer32
    MAX-ACCESS accessible-for-notify
    STATUS current
    DESCRIPTION
        "Parameter 'entry' in event AFS.19"
    ::= { afsEventObjects19 2 }

afs19_ip-source OBJECT-TYPE
    SYNTAX IpAddress
    MAX-ACCESS accessible-for-notify
    STATUS current
    DESCRIPTION
        "Parameter 'ip-source' in event AFS.19"
    ::= { afsEventObjects19 3 }

afs19_ip-destination OBJECT-TYPE
    SYNTAX IpAddress
    MAX-ACCESS accessible-for-notify
    STATUS current
    DESCRIPTION
        "Parameter 'ip-destination' in event AFS.19"
    ::= { afsEventObjects19 4 }

afs19_protocol OBJECT-TYPE
    SYNTAX DisplayString
    MAX-ACCESS accessible-for-notify
    STATUS current
    DESCRIPTION
        "Parameter 'protocol' in event AFS.19"
    ::= { afsEventObjects19 5 }

afs19_out-ifc OBJECT-TYPE
    SYNTAX DisplayString
    MAX-ACCESS accessible-for-notify
    STATUS current
    DESCRIPTION
        "Parameter 'out-ifc' in event AFS.19"
    ::= { afsEventObjects19 6 }

afsEventObjects20 OBJECT-IDENTITY
    STATUS current
    DESCRIPTION
        "Event AFS.20
        new connection event"
    ::= { afsEventsGroup 20 }

afs20_protocol OBJECT-TYPE
    SYNTAX DisplayString
    MAX-ACCESS accessible-for-notify
    STATUS current
    DESCRIPTION
        "Parameter 'protocol' in event AFS.20"
    ::= { afsEventObjects20 1 }

afs20_state OBJECT-TYPE
    SYNTAX DisplayString
    MAX-ACCESS accessible-for-notify
    STATUS current
    DESCRIPTION
        "Parameter 'state' in event AFS.20"
    ::= { afsEventObjects20 2 }

afs20_status OBJECT-TYPE
    SYNTAX DisplayString
    MAX-ACCESS accessible-for-notify
    STATUS current
    DESCRIPTION
        "Parameter 'status' in event AFS.20"
    ::= { afsEventObjects20 3 }

afs20_org_ip_src OBJECT-TYPE
    SYNTAX IpAddress
    MAX-ACCESS accessible-for-notify
    STATUS current
    DESCRIPTION
        "Parameter 'org_ip_src' in event AFS.20"
    ::= { afsEventObjects20 4 }

afs20_org_id_src OBJECT-TYPE
    SYNTAX Integer32
    MAX-ACCESS accessible-for-notify
    STATUS current
    DESCRIPTION
        "Parameter 'org_id_src' in event AFS.20"
    ::= { afsEventObjects20 5 }

afs20_org_ip_dst OBJECT-TYPE
    SYNTAX IpAddress
    MAX-ACCESS accessible-for-notify
    STATUS current
    DESCRIPTION
        "Parameter 'org_ip_dst' in event AFS.20"
    ::= { afsEventObjects20 6 }

afs20_org_id_dst OBJECT-TYPE
    SYNTAX Integer32
    MAX-ACCESS accessible-for-notify
    STATUS current
    DESCRIPTION
        "Parameter 'org_id_dst' in event AFS.20"
    ::= { afsEventObjects20 7 }

afs20_rply_ip_src OBJECT-TYPE
    SYNTAX IpAddress
    MAX-ACCESS accessible-for-notify
    STATUS current
    DESCRIPTION
        "Parameter 'rply_ip_src' in event AFS.20"
    ::= { afsEventObjects20 8 }

afs20_rply_id_src OBJECT-TYPE
    SYNTAX Integer32
    MAX-ACCESS accessible-for-notify
    STATUS current
    DESCRIPTION
        "Parameter 'rply_id_src' in event AFS.20"
    ::= { afsEventObjects20 9 }

afs20_rply_ip_dst OBJECT-TYPE
    SYNTAX IpAddress
    MAX-ACCESS accessible-for-notify
    STATUS current
    DESCRIPTION
        "Parameter 'rply_ip_dst' in event AFS.20"
    ::= { afsEventObjects20 10 }

afs20_rply_id_dst OBJECT-TYPE
    SYNTAX Integer32
    MAX-ACCESS accessible-for-notify
    STATUS current
    DESCRIPTION
        "Parameter 'rply_id_dst' in event AFS.20"
    ::= { afsEventObjects20 11 }

afsEventObjects21 OBJECT-IDENTITY
    STATUS current
    DESCRIPTION
        "Event AFS.21
        confirmed connection event"
    ::= { afsEventsGroup 21 }

afs21_protocol OBJECT-TYPE
    SYNTAX DisplayString
    MAX-ACCESS accessible-for-notify
    STATUS current
    DESCRIPTION
        "Parameter 'protocol' in event AFS.21"
    ::= { afsEventObjects21 1 }

afs21_state OBJECT-TYPE
    SYNTAX DisplayString
    MAX-ACCESS accessible-for-notify
    STATUS current
    DESCRIPTION
        "Parameter 'state' in event AFS.21"
    ::= { afsEventObjects21 2 }

afs21_status OBJECT-TYPE
    SYNTAX DisplayString
    MAX-ACCESS accessible-for-notify
    STATUS current
    DESCRIPTION
        "Parameter 'status' in event AFS.21"
    ::= { afsEventObjects21 3 }

afs21_org_ip_src OBJECT-TYPE
    SYNTAX IpAddress
    MAX-ACCESS accessible-for-notify
    STATUS current
    DESCRIPTION
        "Parameter 'org_ip_src' in event AFS.21"
    ::= { afsEventObjects21 4 }

afs21_org_id_src OBJECT-TYPE
    SYNTAX Integer32
    MAX-ACCESS accessible-for-notify
    STATUS current
    DESCRIPTION
        "Parameter 'org_id_src' in event AFS.21"
    ::= { afsEventObjects21 5 }

afs21_org_ip_dst OBJECT-TYPE
    SYNTAX IpAddress
    MAX-ACCESS accessible-for-notify
    STATUS current
    DESCRIPTION
        "Parameter 'org_ip_dst' in event AFS.21"
    ::= { afsEventObjects21 6 }

afs21_org_id_dst OBJECT-TYPE
    SYNTAX Integer32
    MAX-ACCESS accessible-for-notify
    STATUS current
    DESCRIPTION
        "Parameter 'org_id_dst' in event AFS.21"
    ::= { afsEventObjects21 7 }

afs21_rply_ip_src OBJECT-TYPE
    SYNTAX IpAddress
    MAX-ACCESS accessible-for-notify
    STATUS current
    DESCRIPTION
        "Parameter 'rply_ip_src' in event AFS.21"
    ::= { afsEventObjects21 8 }

afs21_rply_id_src OBJECT-TYPE
    SYNTAX Integer32
    MAX-ACCESS accessible-for-notify
    STATUS current
    DESCRIPTION
        "Parameter 'rply_id_src' in event AFS.21"
    ::= { afsEventObjects21 9 }

afs21_rply_ip_dst OBJECT-TYPE
    SYNTAX IpAddress
    MAX-ACCESS accessible-for-notify
    STATUS current
    DESCRIPTION
        "Parameter 'rply_ip_dst' in event AFS.21"
    ::= { afsEventObjects21 10 }

afs21_rply_id_dst OBJECT-TYPE
    SYNTAX Integer32
    MAX-ACCESS accessible-for-notify
    STATUS current
    DESCRIPTION
        "Parameter 'rply_id_dst' in event AFS.21"
    ::= { afsEventObjects21 11 }

afsEventObjects22 OBJECT-IDENTITY
    STATUS current
    DESCRIPTION
        "Event AFS.22
        deleted connection event"
    ::= { afsEventsGroup 22 }

afs22_protocol OBJECT-TYPE
    SYNTAX DisplayString
    MAX-ACCESS accessible-for-notify
    STATUS current
    DESCRIPTION
        "Parameter 'protocol' in event AFS.22"
    ::= { afsEventObjects22 1 }

afs22_state OBJECT-TYPE
    SYNTAX DisplayString
    MAX-ACCESS accessible-for-notify
    STATUS current
    DESCRIPTION
        "Parameter 'state' in event AFS.22"
    ::= { afsEventObjects22 2 }

afs22_status OBJECT-TYPE
    SYNTAX DisplayString
    MAX-ACCESS accessible-for-notify
    STATUS current
    DESCRIPTION
        "Parameter 'status' in event AFS.22"
    ::= { afsEventObjects22 3 }

afs22_org_ip_src OBJECT-TYPE
    SYNTAX IpAddress
    MAX-ACCESS accessible-for-notify
    STATUS current
    DESCRIPTION
        "Parameter 'org_ip_src' in event AFS.22"
    ::= { afsEventObjects22 4 }

afs22_org_id_src OBJECT-TYPE
    SYNTAX Integer32
    MAX-ACCESS accessible-for-notify
    STATUS current
    DESCRIPTION
        "Parameter 'org_id_src' in event AFS.22"
    ::= { afsEventObjects22 5 }

afs22_org_ip_dst OBJECT-TYPE
    SYNTAX IpAddress
    MAX-ACCESS accessible-for-notify
    STATUS current
    DESCRIPTION
        "Parameter 'org_ip_dst' in event AFS.22"
    ::= { afsEventObjects22 6 }

afs22_org_id_dst OBJECT-TYPE
    SYNTAX Integer32
    MAX-ACCESS accessible-for-notify
    STATUS current
    DESCRIPTION
        "Parameter 'org_id_dst' in event AFS.22"
    ::= { afsEventObjects22 7 }

afs22_rply_ip_src OBJECT-TYPE
    SYNTAX IpAddress
    MAX-ACCESS accessible-for-notify
    STATUS current
    DESCRIPTION
        "Parameter 'rply_ip_src' in event AFS.22"
    ::= { afsEventObjects22 8 }

afs22_rply_id_src OBJECT-TYPE
    SYNTAX Integer32
    MAX-ACCESS accessible-for-notify
    STATUS current
    DESCRIPTION
        "Parameter 'rply_id_src' in event AFS.22"
    ::= { afsEventObjects22 9 }

afs22_rply_ip_dst OBJECT-TYPE
    SYNTAX IpAddress
    MAX-ACCESS accessible-for-notify
    STATUS current
    DESCRIPTION
        "Parameter 'rply_ip_dst' in event AFS.22"
    ::= { afsEventObjects22 10 }

afs22_rply_id_dst OBJECT-TYPE
    SYNTAX Integer32
    MAX-ACCESS accessible-for-notify
    STATUS current
    DESCRIPTION
        "Parameter 'rply_id_dst' in event AFS.22"
    ::= { afsEventObjects22 11 }

afsEventObjects23 OBJECT-IDENTITY
    STATUS current
    DESCRIPTION
        "Event AFS.23
        failed confirmation connection event"
    ::= { afsEventsGroup 23 }

afs23_protocol OBJECT-TYPE
    SYNTAX DisplayString
    MAX-ACCESS accessible-for-notify
    STATUS current
    DESCRIPTION
        "Parameter 'protocol' in event AFS.23"
    ::= { afsEventObjects23 1 }

afs23_state OBJECT-TYPE
    SYNTAX DisplayString
    MAX-ACCESS accessible-for-notify
    STATUS current
    DESCRIPTION
        "Parameter 'state' in event AFS.23"
    ::= { afsEventObjects23 2 }

afs23_status OBJECT-TYPE
    SYNTAX DisplayString
    MAX-ACCESS accessible-for-notify
    STATUS current
    DESCRIPTION
        "Parameter 'status' in event AFS.23"
    ::= { afsEventObjects23 3 }

afs23_org_ip_src OBJECT-TYPE
    SYNTAX IpAddress
    MAX-ACCESS accessible-for-notify
    STATUS current
    DESCRIPTION
        "Parameter 'org_ip_src' in event AFS.23"
    ::= { afsEventObjects23 4 }

afs23_org_id_src OBJECT-TYPE
    SYNTAX Integer32
    MAX-ACCESS accessible-for-notify
    STATUS current
    DESCRIPTION
        "Parameter 'org_id_src' in event AFS.23"
    ::= { afsEventObjects23 5 }

afs23_org_ip_dst OBJECT-TYPE
    SYNTAX IpAddress
    MAX-ACCESS accessible-for-notify
    STATUS current
    DESCRIPTION
        "Parameter 'org_ip_dst' in event AFS.23"
    ::= { afsEventObjects23 6 }

afs23_org_id_dst OBJECT-TYPE
    SYNTAX Integer32
    MAX-ACCESS accessible-for-notify
    STATUS current
    DESCRIPTION
        "Parameter 'org_id_dst' in event AFS.23"
    ::= { afsEventObjects23 7 }

afs23_rply_ip_src OBJECT-TYPE
    SYNTAX IpAddress
    MAX-ACCESS accessible-for-notify
    STATUS current
    DESCRIPTION
        "Parameter 'rply_ip_src' in event AFS.23"
    ::= { afsEventObjects23 8 }

afs23_rply_id_src OBJECT-TYPE
    SYNTAX Integer32
    MAX-ACCESS accessible-for-notify
    STATUS current
    DESCRIPTION
        "Parameter 'rply_id_src' in event AFS.23"
    ::= { afsEventObjects23 9 }

afs23_rply_ip_dst OBJECT-TYPE
    SYNTAX IpAddress
    MAX-ACCESS accessible-for-notify
    STATUS current
    DESCRIPTION
        "Parameter 'rply_ip_dst' in event AFS.23"
    ::= { afsEventObjects23 10 }

afs23_rply_id_dst OBJECT-TYPE
    SYNTAX Integer32
    MAX-ACCESS accessible-for-notify
    STATUS current
    DESCRIPTION
        "Parameter 'rply_id_dst' in event AFS.23"
    ::= { afsEventObjects23 11 }

afsEventObjects24 OBJECT-IDENTITY
    STATUS current
    DESCRIPTION
        "Event AFS.24
        new expected connection added"
    ::= { afsEventsGroup 24 }

afs24_protocol OBJECT-TYPE
    SYNTAX DisplayString
    MAX-ACCESS accessible-for-notify
    STATUS current
    DESCRIPTION
        "Parameter 'protocol' in event AFS.24"
    ::= { afsEventObjects24 1 }

afs24_state OBJECT-TYPE
    SYNTAX DisplayString
    MAX-ACCESS accessible-for-notify
    STATUS current
    DESCRIPTION
        "Parameter 'state' in event AFS.24"
    ::= { afsEventObjects24 2 }

afs24_status OBJECT-TYPE
    SYNTAX DisplayString
    MAX-ACCESS accessible-for-notify
    STATUS current
    DESCRIPTION
        "Parameter 'status' in event AFS.24"
    ::= { afsEventObjects24 3 }

afs24_org_ip_src OBJECT-TYPE
    SYNTAX IpAddress
    MAX-ACCESS accessible-for-notify
    STATUS current
    DESCRIPTION
        "Parameter 'org_ip_src' in event AFS.24"
    ::= { afsEventObjects24 4 }

afs24_org_id_src OBJECT-TYPE
    SYNTAX Integer32
    MAX-ACCESS accessible-for-notify
    STATUS current
    DESCRIPTION
        "Parameter 'org_id_src' in event AFS.24"
    ::= { afsEventObjects24 5 }

afs24_org_ip_dst OBJECT-TYPE
    SYNTAX IpAddress
    MAX-ACCESS accessible-for-notify
    STATUS current
    DESCRIPTION
        "Parameter 'org_ip_dst' in event AFS.24"
    ::= { afsEventObjects24 6 }

afs24_org_id_dst OBJECT-TYPE
    SYNTAX Integer32
    MAX-ACCESS accessible-for-notify
    STATUS current
    DESCRIPTION
        "Parameter 'org_id_dst' in event AFS.24"
    ::= { afsEventObjects24 7 }

afs24_rply_ip_src OBJECT-TYPE
    SYNTAX IpAddress
    MAX-ACCESS accessible-for-notify
    STATUS current
    DESCRIPTION
        "Parameter 'rply_ip_src' in event AFS.24"
    ::= { afsEventObjects24 8 }

afs24_rply_id_src OBJECT-TYPE
    SYNTAX Integer32
    MAX-ACCESS accessible-for-notify
    STATUS current
    DESCRIPTION
        "Parameter 'rply_id_src' in event AFS.24"
    ::= { afsEventObjects24 9 }

afs24_rply_ip_dst OBJECT-TYPE
    SYNTAX IpAddress
    MAX-ACCESS accessible-for-notify
    STATUS current
    DESCRIPTION
        "Parameter 'rply_ip_dst' in event AFS.24"
    ::= { afsEventObjects24 10 }

afs24_rply_id_dst OBJECT-TYPE
    SYNTAX Integer32
    MAX-ACCESS accessible-for-notify
    STATUS current
    DESCRIPTION
        "Parameter 'rply_id_dst' in event AFS.24"
    ::= { afsEventObjects24 11 }

afsEventObjects25 OBJECT-IDENTITY
    STATUS current
    DESCRIPTION
        "Event AFS.25
        alg found event"
    ::= { afsEventsGroup 25 }

afs25_alg OBJECT-TYPE
    SYNTAX DisplayString
    MAX-ACCESS accessible-for-notify
    STATUS current
    DESCRIPTION
        "Parameter 'alg' in event AFS.25"
    ::= { afsEventObjects25 1 }

afs25_protocol OBJECT-TYPE
    SYNTAX DisplayString
    MAX-ACCESS accessible-for-notify
    STATUS current
    DESCRIPTION
        "Parameter 'protocol' in event AFS.25"
    ::= { afsEventObjects25 2 }

afs25_state OBJECT-TYPE
    SYNTAX DisplayString
    MAX-ACCESS accessible-for-notify
    STATUS current
    DESCRIPTION
        "Parameter 'state' in event AFS.25"
    ::= { afsEventObjects25 3 }

afs25_status OBJECT-TYPE
    SYNTAX DisplayString
    MAX-ACCESS accessible-for-notify
    STATUS current
    DESCRIPTION
        "Parameter 'status' in event AFS.25"
    ::= { afsEventObjects25 4 }

afs25_org_ip_src OBJECT-TYPE
    SYNTAX IpAddress
    MAX-ACCESS accessible-for-notify
    STATUS current
    DESCRIPTION
        "Parameter 'org_ip_src' in event AFS.25"
    ::= { afsEventObjects25 5 }

afs25_org_id_src OBJECT-TYPE
    SYNTAX Integer32
    MAX-ACCESS accessible-for-notify
    STATUS current
    DESCRIPTION
        "Parameter 'org_id_src' in event AFS.25"
    ::= { afsEventObjects25 6 }

afs25_org_ip_dst OBJECT-TYPE
    SYNTAX IpAddress
    MAX-ACCESS accessible-for-notify
    STATUS current
    DESCRIPTION
        "Parameter 'org_ip_dst' in event AFS.25"
    ::= { afsEventObjects25 7 }

afs25_org_id_dst OBJECT-TYPE
    SYNTAX Integer32
    MAX-ACCESS accessible-for-notify
    STATUS current
    DESCRIPTION
        "Parameter 'org_id_dst' in event AFS.25"
    ::= { afsEventObjects25 8 }

afs25_rply_ip_src OBJECT-TYPE
    SYNTAX IpAddress
    MAX-ACCESS accessible-for-notify
    STATUS current
    DESCRIPTION
        "Parameter 'rply_ip_src' in event AFS.25"
    ::= { afsEventObjects25 9 }

afs25_rply_id_src OBJECT-TYPE
    SYNTAX Integer32
    MAX-ACCESS accessible-for-notify
    STATUS current
    DESCRIPTION
        "Parameter 'rply_id_src' in event AFS.25"
    ::= { afsEventObjects25 10 }

afs25_rply_ip_dst OBJECT-TYPE
    SYNTAX IpAddress
    MAX-ACCESS accessible-for-notify
    STATUS current
    DESCRIPTION
        "Parameter 'rply_ip_dst' in event AFS.25"
    ::= { afsEventObjects25 11 }

afs25_rply_id_dst OBJECT-TYPE
    SYNTAX Integer32
    MAX-ACCESS accessible-for-notify
    STATUS current
    DESCRIPTION
        "Parameter 'rply_id_dst' in event AFS.25"
    ::= { afsEventObjects25 12 }

afsEventObjects26 OBJECT-IDENTITY
    STATUS current
    DESCRIPTION
        "Event AFS.26
        connection expected found event"
    ::= { afsEventsGroup 26 }

afs26_protocol OBJECT-TYPE
    SYNTAX DisplayString
    MAX-ACCESS accessible-for-notify
    STATUS current
    DESCRIPTION
        "Parameter 'protocol' in event AFS.26"
    ::= { afsEventObjects26 1 }

afs26_state OBJECT-TYPE
    SYNTAX DisplayString
    MAX-ACCESS accessible-for-notify
    STATUS current
    DESCRIPTION
        "Parameter 'state' in event AFS.26"
    ::= { afsEventObjects26 2 }

afs26_status OBJECT-TYPE
    SYNTAX DisplayString
    MAX-ACCESS accessible-for-notify
    STATUS current
    DESCRIPTION
        "Parameter 'status' in event AFS.26"
    ::= { afsEventObjects26 3 }

afs26_org_ip_src OBJECT-TYPE
    SYNTAX IpAddress
    MAX-ACCESS accessible-for-notify
    STATUS current
    DESCRIPTION
        "Parameter 'org_ip_src' in event AFS.26"
    ::= { afsEventObjects26 4 }

afs26_org_id_src OBJECT-TYPE
    SYNTAX Integer32
    MAX-ACCESS accessible-for-notify
    STATUS current
    DESCRIPTION
        "Parameter 'org_id_src' in event AFS.26"
    ::= { afsEventObjects26 5 }

afs26_org_ip_dst OBJECT-TYPE
    SYNTAX IpAddress
    MAX-ACCESS accessible-for-notify
    STATUS current
    DESCRIPTION
        "Parameter 'org_ip_dst' in event AFS.26"
    ::= { afsEventObjects26 6 }

afs26_org_id_dst OBJECT-TYPE
    SYNTAX Integer32
    MAX-ACCESS accessible-for-notify
    STATUS current
    DESCRIPTION
        "Parameter 'org_id_dst' in event AFS.26"
    ::= { afsEventObjects26 7 }

afs26_rply_ip_src OBJECT-TYPE
    SYNTAX IpAddress
    MAX-ACCESS accessible-for-notify
    STATUS current
    DESCRIPTION
        "Parameter 'rply_ip_src' in event AFS.26"
    ::= { afsEventObjects26 8 }

afs26_rply_id_src OBJECT-TYPE
    SYNTAX Integer32
    MAX-ACCESS accessible-for-notify
    STATUS current
    DESCRIPTION
        "Parameter 'rply_id_src' in event AFS.26"
    ::= { afsEventObjects26 9 }

afs26_rply_ip_dst OBJECT-TYPE
    SYNTAX IpAddress
    MAX-ACCESS accessible-for-notify
    STATUS current
    DESCRIPTION
        "Parameter 'rply_ip_dst' in event AFS.26"
    ::= { afsEventObjects26 10 }

afs26_rply_id_dst OBJECT-TYPE
    SYNTAX Integer32
    MAX-ACCESS accessible-for-notify
    STATUS current
    DESCRIPTION
        "Parameter 'rply_id_dst' in event AFS.26"
    ::= { afsEventObjects26 11 }

afsEventObjects27 OBJECT-IDENTITY
    STATUS current
    DESCRIPTION
        "Event AFS.27
        a non-overlapped nat association event has happened"
    ::= { afsEventsGroup 27 }

afs27_event OBJECT-TYPE
    SYNTAX DisplayString
    MAX-ACCESS accessible-for-notify
    STATUS current
    DESCRIPTION
        "Parameter 'event' in event AFS.27"
    ::= { afsEventObjects27 1 }

afs27_local-ip OBJECT-TYPE
    SYNTAX IpAddress
    MAX-ACCESS accessible-for-notify
    STATUS current
    DESCRIPTION
        "Parameter 'local-ip' in event AFS.27"
    ::= { afsEventObjects27 2 }

afs27_global-ip OBJECT-TYPE
    SYNTAX IpAddress
    MAX-ACCESS accessible-for-notify
    STATUS current
    DESCRIPTION
        "Parameter 'global-ip' in event AFS.27"
    ::= { afsEventObjects27 3 }

afsEventObjects28 OBJECT-IDENTITY
    STATUS current
    DESCRIPTION
        "Event AFS.28
        a connection has been matched by a packet"
    ::= { afsEventsGroup 28 }

afs28_protocol OBJECT-TYPE
    SYNTAX DisplayString
    MAX-ACCESS accessible-for-notify
    STATUS current
    DESCRIPTION
        "Parameter 'protocol' in event AFS.28"
    ::= { afsEventObjects28 1 }

afs28_state OBJECT-TYPE
    SYNTAX DisplayString
    MAX-ACCESS accessible-for-notify
    STATUS current
    DESCRIPTION
        "Parameter 'state' in event AFS.28"
    ::= { afsEventObjects28 2 }

afs28_status OBJECT-TYPE
    SYNTAX DisplayString
    MAX-ACCESS accessible-for-notify
    STATUS current
    DESCRIPTION
        "Parameter 'status' in event AFS.28"
    ::= { afsEventObjects28 3 }

afs28_org_ip_src OBJECT-TYPE
    SYNTAX IpAddress
    MAX-ACCESS accessible-for-notify
    STATUS current
    DESCRIPTION
        "Parameter 'org_ip_src' in event AFS.28"
    ::= { afsEventObjects28 4 }

afs28_org_id_src OBJECT-TYPE
    SYNTAX Integer32
    MAX-ACCESS accessible-for-notify
    STATUS current
    DESCRIPTION
        "Parameter 'org_id_src' in event AFS.28"
    ::= { afsEventObjects28 5 }

afs28_org_ip_dst OBJECT-TYPE
    SYNTAX IpAddress
    MAX-ACCESS accessible-for-notify
    STATUS current
    DESCRIPTION
        "Parameter 'org_ip_dst' in event AFS.28"
    ::= { afsEventObjects28 6 }

afs28_org_id_dst OBJECT-TYPE
    SYNTAX Integer32
    MAX-ACCESS accessible-for-notify
    STATUS current
    DESCRIPTION
        "Parameter 'org_id_dst' in event AFS.28"
    ::= { afsEventObjects28 7 }

afs28_rply_ip_src OBJECT-TYPE
    SYNTAX IpAddress
    MAX-ACCESS accessible-for-notify
    STATUS current
    DESCRIPTION
        "Parameter 'rply_ip_src' in event AFS.28"
    ::= { afsEventObjects28 8 }

afs28_rply_id_src OBJECT-TYPE
    SYNTAX Integer32
    MAX-ACCESS accessible-for-notify
    STATUS current
    DESCRIPTION
        "Parameter 'rply_id_src' in event AFS.28"
    ::= { afsEventObjects28 9 }

afs28_rply_ip_dst OBJECT-TYPE
    SYNTAX IpAddress
    MAX-ACCESS accessible-for-notify
    STATUS current
    DESCRIPTION
        "Parameter 'rply_ip_dst' in event AFS.28"
    ::= { afsEventObjects28 10 }

afs28_rply_id_dst OBJECT-TYPE
    SYNTAX Integer32
    MAX-ACCESS accessible-for-notify
    STATUS current
    DESCRIPTION
        "Parameter 'rply_id_dst' in event AFS.28"
    ::= { afsEventObjects28 11 }

afsEventObjects29 OBJECT-IDENTITY
    STATUS current
    DESCRIPTION
        "Event AFS.29
        an url filter has matched"
    ::= { afsEventsGroup 29 }

afs29_server_ip OBJECT-TYPE
    SYNTAX IpAddress
    MAX-ACCESS accessible-for-notify
    STATUS current
    DESCRIPTION
        "Parameter 'server_ip' in event AFS.29"
    ::= { afsEventObjects29 1 }

afs29_filename OBJECT-TYPE
    SYNTAX DisplayString
    MAX-ACCESS accessible-for-notify
    STATUS current
    DESCRIPTION
        "Parameter 'filename' in event AFS.29"
    ::= { afsEventObjects29 2 }

afs29_ev OBJECT-TYPE
    SYNTAX DisplayString
    MAX-ACCESS accessible-for-notify
    STATUS current
    DESCRIPTION
        "Parameter 'ev' in event AFS.29"
    ::= { afsEventObjects29 3 }

afs29_info OBJECT-TYPE
    SYNTAX DisplayString
    MAX-ACCESS accessible-for-notify
    STATUS current
    DESCRIPTION
        "Parameter 'info' in event AFS.29"
    ::= { afsEventObjects29 4 }

afsEventObjects30 OBJECT-IDENTITY
    STATUS current
    DESCRIPTION
        "Event AFS.30
        an in ipv6 packet has been accepted"
    ::= { afsEventsGroup 30 }

afs30_ip-source OBJECT-TYPE
    SYNTAX DisplayString
    MAX-ACCESS accessible-for-notify
    STATUS current
    DESCRIPTION
        "Parameter 'ip-source' in event AFS.30"
    ::= { afsEventObjects30 1 }

afs30_ip-destination OBJECT-TYPE
    SYNTAX DisplayString
    MAX-ACCESS accessible-for-notify
    STATUS current
    DESCRIPTION
        "Parameter 'ip-destination' in event AFS.30"
    ::= { afsEventObjects30 2 }

afs30_protocol OBJECT-TYPE
    SYNTAX DisplayString
    MAX-ACCESS accessible-for-notify
    STATUS current
    DESCRIPTION
        "Parameter 'protocol' in event AFS.30"
    ::= { afsEventObjects30 3 }

afs30_in-ifc OBJECT-TYPE
    SYNTAX DisplayString
    MAX-ACCESS accessible-for-notify
    STATUS current
    DESCRIPTION
        "Parameter 'in-ifc' in event AFS.30"
    ::= { afsEventObjects30 4 }

afsEventObjects31 OBJECT-IDENTITY
    STATUS current
    DESCRIPTION
        "Event AFS.31
        an in ipv6 packet has been discarded"
    ::= { afsEventsGroup 31 }

afs31_ip-source OBJECT-TYPE
    SYNTAX DisplayString
    MAX-ACCESS accessible-for-notify
    STATUS current
    DESCRIPTION
        "Parameter 'ip-source' in event AFS.31"
    ::= { afsEventObjects31 1 }

afs31_ip-destination OBJECT-TYPE
    SYNTAX DisplayString
    MAX-ACCESS accessible-for-notify
    STATUS current
    DESCRIPTION
        "Parameter 'ip-destination' in event AFS.31"
    ::= { afsEventObjects31 2 }

afs31_protocol OBJECT-TYPE
    SYNTAX DisplayString
    MAX-ACCESS accessible-for-notify
    STATUS current
    DESCRIPTION
        "Parameter 'protocol' in event AFS.31"
    ::= { afsEventObjects31 3 }

afs31_in-ifc OBJECT-TYPE
    SYNTAX DisplayString
    MAX-ACCESS accessible-for-notify
    STATUS current
    DESCRIPTION
        "Parameter 'in-ifc' in event AFS.31"
    ::= { afsEventObjects31 4 }

afsEventObjects32 OBJECT-IDENTITY
    STATUS current
    DESCRIPTION
        "Event AFS.32
        an out ipv6 packet has been accepted"
    ::= { afsEventsGroup 32 }

afs32_ip-source OBJECT-TYPE
    SYNTAX DisplayString
    MAX-ACCESS accessible-for-notify
    STATUS current
    DESCRIPTION
        "Parameter 'ip-source' in event AFS.32"
    ::= { afsEventObjects32 1 }

afs32_ip-destination OBJECT-TYPE
    SYNTAX DisplayString
    MAX-ACCESS accessible-for-notify
    STATUS current
    DESCRIPTION
        "Parameter 'ip-destination' in event AFS.32"
    ::= { afsEventObjects32 2 }

afs32_protocol OBJECT-TYPE
    SYNTAX DisplayString
    MAX-ACCESS accessible-for-notify
    STATUS current
    DESCRIPTION
        "Parameter 'protocol' in event AFS.32"
    ::= { afsEventObjects32 3 }

afs32_in-ifc OBJECT-TYPE
    SYNTAX DisplayString
    MAX-ACCESS accessible-for-notify
    STATUS current
    DESCRIPTION
        "Parameter 'in-ifc' in event AFS.32"
    ::= { afsEventObjects32 4 }

afs32_out-ifc OBJECT-TYPE
    SYNTAX DisplayString
    MAX-ACCESS accessible-for-notify
    STATUS current
    DESCRIPTION
        "Parameter 'out-ifc' in event AFS.32"
    ::= { afsEventObjects32 5 }

afsEventObjects33 OBJECT-IDENTITY
    STATUS current
    DESCRIPTION
        "Event AFS.33
        an out ipv6 packet has been discarded"
    ::= { afsEventsGroup 33 }

afs33_ip-source OBJECT-TYPE
    SYNTAX DisplayString
    MAX-ACCESS accessible-for-notify
    STATUS current
    DESCRIPTION
        "Parameter 'ip-source' in event AFS.33"
    ::= { afsEventObjects33 1 }

afs33_ip-destination OBJECT-TYPE
    SYNTAX DisplayString
    MAX-ACCESS accessible-for-notify
    STATUS current
    DESCRIPTION
        "Parameter 'ip-destination' in event AFS.33"
    ::= { afsEventObjects33 2 }

afs33_protocol OBJECT-TYPE
    SYNTAX DisplayString
    MAX-ACCESS accessible-for-notify
    STATUS current
    DESCRIPTION
        "Parameter 'protocol' in event AFS.33"
    ::= { afsEventObjects33 3 }

afs33_in-ifc OBJECT-TYPE
    SYNTAX DisplayString
    MAX-ACCESS accessible-for-notify
    STATUS current
    DESCRIPTION
        "Parameter 'in-ifc' in event AFS.33"
    ::= { afsEventObjects33 4 }

afs33_out-ifc OBJECT-TYPE
    SYNTAX DisplayString
    MAX-ACCESS accessible-for-notify
    STATUS current
    DESCRIPTION
        "Parameter 'out-ifc' in event AFS.33"
    ::= { afsEventObjects33 5 }

afsEventObjects34 OBJECT-IDENTITY
    STATUS current
    DESCRIPTION
        "Event AFS.34
        a local-in ipv6 packet has been accepted"
    ::= { afsEventsGroup 34 }

afs34_ip-source OBJECT-TYPE
    SYNTAX DisplayString
    MAX-ACCESS accessible-for-notify
    STATUS current
    DESCRIPTION
        "Parameter 'ip-source' in event AFS.34"
    ::= { afsEventObjects34 1 }

afs34_ip-destination OBJECT-TYPE
    SYNTAX DisplayString
    MAX-ACCESS accessible-for-notify
    STATUS current
    DESCRIPTION
        "Parameter 'ip-destination' in event AFS.34"
    ::= { afsEventObjects34 2 }

afs34_protocol OBJECT-TYPE
    SYNTAX DisplayString
    MAX-ACCESS accessible-for-notify
    STATUS current
    DESCRIPTION
        "Parameter 'protocol' in event AFS.34"
    ::= { afsEventObjects34 3 }

afs34_in-ifc OBJECT-TYPE
    SYNTAX DisplayString
    MAX-ACCESS accessible-for-notify
    STATUS current
    DESCRIPTION
        "Parameter 'in-ifc' in event AFS.34"
    ::= { afsEventObjects34 4 }

afsEventObjects35 OBJECT-IDENTITY
    STATUS current
    DESCRIPTION
        "Event AFS.35
        a local-in ipv6 packet has been discarded"
    ::= { afsEventsGroup 35 }

afs35_ip-source OBJECT-TYPE
    SYNTAX DisplayString
    MAX-ACCESS accessible-for-notify
    STATUS current
    DESCRIPTION
        "Parameter 'ip-source' in event AFS.35"
    ::= { afsEventObjects35 1 }

afs35_ip-destination OBJECT-TYPE
    SYNTAX DisplayString
    MAX-ACCESS accessible-for-notify
    STATUS current
    DESCRIPTION
        "Parameter 'ip-destination' in event AFS.35"
    ::= { afsEventObjects35 2 }

afs35_protocol OBJECT-TYPE
    SYNTAX DisplayString
    MAX-ACCESS accessible-for-notify
    STATUS current
    DESCRIPTION
        "Parameter 'protocol' in event AFS.35"
    ::= { afsEventObjects35 3 }

afs35_in-ifc OBJECT-TYPE
    SYNTAX DisplayString
    MAX-ACCESS accessible-for-notify
    STATUS current
    DESCRIPTION
        "Parameter 'in-ifc' in event AFS.35"
    ::= { afsEventObjects35 4 }

afsEventObjects36 OBJECT-IDENTITY
    STATUS current
    DESCRIPTION
        "Event AFS.36
        a local-out ipv6 packet has been accepted"
    ::= { afsEventsGroup 36 }

afs36_ip-source OBJECT-TYPE
    SYNTAX DisplayString
    MAX-ACCESS accessible-for-notify
    STATUS current
    DESCRIPTION
        "Parameter 'ip-source' in event AFS.36"
    ::= { afsEventObjects36 1 }

afs36_ip-destination OBJECT-TYPE
    SYNTAX DisplayString
    MAX-ACCESS accessible-for-notify
    STATUS current
    DESCRIPTION
        "Parameter 'ip-destination' in event AFS.36"
    ::= { afsEventObjects36 2 }

afs36_protocol OBJECT-TYPE
    SYNTAX DisplayString
    MAX-ACCESS accessible-for-notify
    STATUS current
    DESCRIPTION
        "Parameter 'protocol' in event AFS.36"
    ::= { afsEventObjects36 3 }

afs36_out-ifc OBJECT-TYPE
    SYNTAX DisplayString
    MAX-ACCESS accessible-for-notify
    STATUS current
    DESCRIPTION
        "Parameter 'out-ifc' in event AFS.36"
    ::= { afsEventObjects36 4 }

afsEventObjects37 OBJECT-IDENTITY
    STATUS current
    DESCRIPTION
        "Event AFS.37
        a local-out ipv6 packet has been discarded"
    ::= { afsEventsGroup 37 }

afs37_ip-source OBJECT-TYPE
    SYNTAX DisplayString
    MAX-ACCESS accessible-for-notify
    STATUS current
    DESCRIPTION
        "Parameter 'ip-source' in event AFS.37"
    ::= { afsEventObjects37 1 }

afs37_ip-destination OBJECT-TYPE
    SYNTAX DisplayString
    MAX-ACCESS accessible-for-notify
    STATUS current
    DESCRIPTION
        "Parameter 'ip-destination' in event AFS.37"
    ::= { afsEventObjects37 2 }

afs37_protocol OBJECT-TYPE
    SYNTAX DisplayString
    MAX-ACCESS accessible-for-notify
    STATUS current
    DESCRIPTION
        "Parameter 'protocol' in event AFS.37"
    ::= { afsEventObjects37 3 }

afs37_out-ifc OBJECT-TYPE
    SYNTAX DisplayString
    MAX-ACCESS accessible-for-notify
    STATUS current
    DESCRIPTION
        "Parameter 'out-ifc' in event AFS.37"
    ::= { afsEventObjects37 4 }

afsEventObjects38 OBJECT-IDENTITY
    STATUS current
    DESCRIPTION
        "Event AFS.38
        an in ipv6 packet has been accepted by a filter rule"
    ::= { afsEventsGroup 38 }

afs38_in-ifc OBJECT-TYPE
    SYNTAX DisplayString
    MAX-ACCESS accessible-for-notify
    STATUS current
    DESCRIPTION
        "Parameter 'in-ifc' in event AFS.38"
    ::= { afsEventObjects38 1 }

afs38_access-list OBJECT-TYPE
    SYNTAX Integer32
    MAX-ACCESS accessible-for-notify
    STATUS current
    DESCRIPTION
        "Parameter 'access-list' in event AFS.38"
    ::= { afsEventObjects38 2 }

afs38_entry OBJECT-TYPE
    SYNTAX Integer32
    MAX-ACCESS accessible-for-notify
    STATUS current
    DESCRIPTION
        "Parameter 'entry' in event AFS.38"
    ::= { afsEventObjects38 3 }

afs38_ip-source OBJECT-TYPE
    SYNTAX DisplayString
    MAX-ACCESS accessible-for-notify
    STATUS current
    DESCRIPTION
        "Parameter 'ip-source' in event AFS.38"
    ::= { afsEventObjects38 4 }

afs38_ip-destination OBJECT-TYPE
    SYNTAX DisplayString
    MAX-ACCESS accessible-for-notify
    STATUS current
    DESCRIPTION
        "Parameter 'ip-destination' in event AFS.38"
    ::= { afsEventObjects38 5 }

afs38_protocol OBJECT-TYPE
    SYNTAX DisplayString
    MAX-ACCESS accessible-for-notify
    STATUS current
    DESCRIPTION
        "Parameter 'protocol' in event AFS.38"
    ::= { afsEventObjects38 6 }

afsEventObjects39 OBJECT-IDENTITY
    STATUS current
    DESCRIPTION
        "Event AFS.39
        an in ipv6 packet has been discarded by a filter rule"
    ::= { afsEventsGroup 39 }

afs39_in-ifc OBJECT-TYPE
    SYNTAX DisplayString
    MAX-ACCESS accessible-for-notify
    STATUS current
    DESCRIPTION
        "Parameter 'in-ifc' in event AFS.39"
    ::= { afsEventObjects39 1 }

afs39_access-list OBJECT-TYPE
    SYNTAX Integer32
    MAX-ACCESS accessible-for-notify
    STATUS current
    DESCRIPTION
        "Parameter 'access-list' in event AFS.39"
    ::= { afsEventObjects39 2 }

afs39_entry OBJECT-TYPE
    SYNTAX Integer32
    MAX-ACCESS accessible-for-notify
    STATUS current
    DESCRIPTION
        "Parameter 'entry' in event AFS.39"
    ::= { afsEventObjects39 3 }

afs39_ip-source OBJECT-TYPE
    SYNTAX DisplayString
    MAX-ACCESS accessible-for-notify
    STATUS current
    DESCRIPTION
        "Parameter 'ip-source' in event AFS.39"
    ::= { afsEventObjects39 4 }

afs39_ip-destination OBJECT-TYPE
    SYNTAX DisplayString
    MAX-ACCESS accessible-for-notify
    STATUS current
    DESCRIPTION
        "Parameter 'ip-destination' in event AFS.39"
    ::= { afsEventObjects39 5 }

afs39_protocol OBJECT-TYPE
    SYNTAX DisplayString
    MAX-ACCESS accessible-for-notify
    STATUS current
    DESCRIPTION
        "Parameter 'protocol' in event AFS.39"
    ::= { afsEventObjects39 6 }

afsEventObjects40 OBJECT-IDENTITY
    STATUS current
    DESCRIPTION
        "Event AFS.40
        an out ipv6 packet has been accepted by a filter rule"
    ::= { afsEventsGroup 40 }

afs40_out-ifc OBJECT-TYPE
    SYNTAX DisplayString
    MAX-ACCESS accessible-for-notify
    STATUS current
    DESCRIPTION
        "Parameter 'out-ifc' in event AFS.40"
    ::= { afsEventObjects40 1 }

afs40_access-list OBJECT-TYPE
    SYNTAX Integer32
    MAX-ACCESS accessible-for-notify
    STATUS current
    DESCRIPTION
        "Parameter 'access-list' in event AFS.40"
    ::= { afsEventObjects40 2 }

afs40_entry OBJECT-TYPE
    SYNTAX Integer32
    MAX-ACCESS accessible-for-notify
    STATUS current
    DESCRIPTION
        "Parameter 'entry' in event AFS.40"
    ::= { afsEventObjects40 3 }

afs40_ip-source OBJECT-TYPE
    SYNTAX DisplayString
    MAX-ACCESS accessible-for-notify
    STATUS current
    DESCRIPTION
        "Parameter 'ip-source' in event AFS.40"
    ::= { afsEventObjects40 4 }

afs40_ip-destination OBJECT-TYPE
    SYNTAX DisplayString
    MAX-ACCESS accessible-for-notify
    STATUS current
    DESCRIPTION
        "Parameter 'ip-destination' in event AFS.40"
    ::= { afsEventObjects40 5 }

afs40_protocol OBJECT-TYPE
    SYNTAX DisplayString
    MAX-ACCESS accessible-for-notify
    STATUS current
    DESCRIPTION
        "Parameter 'protocol' in event AFS.40"
    ::= { afsEventObjects40 6 }

afs40_in-ifc OBJECT-TYPE
    SYNTAX DisplayString
    MAX-ACCESS accessible-for-notify
    STATUS current
    DESCRIPTION
        "Parameter 'in-ifc' in event AFS.40"
    ::= { afsEventObjects40 7 }

afsEventObjects41 OBJECT-IDENTITY
    STATUS current
    DESCRIPTION
        "Event AFS.41
        an out ipv6 packet has been discarded by a filter rule"
    ::= { afsEventsGroup 41 }

afs41_out-ifc OBJECT-TYPE
    SYNTAX DisplayString
    MAX-ACCESS accessible-for-notify
    STATUS current
    DESCRIPTION
        "Parameter 'out-ifc' in event AFS.41"
    ::= { afsEventObjects41 1 }

afs41_access-list OBJECT-TYPE
    SYNTAX Integer32
    MAX-ACCESS accessible-for-notify
    STATUS current
    DESCRIPTION
        "Parameter 'access-list' in event AFS.41"
    ::= { afsEventObjects41 2 }

afs41_entry OBJECT-TYPE
    SYNTAX Integer32
    MAX-ACCESS accessible-for-notify
    STATUS current
    DESCRIPTION
        "Parameter 'entry' in event AFS.41"
    ::= { afsEventObjects41 3 }

afs41_ip-source OBJECT-TYPE
    SYNTAX DisplayString
    MAX-ACCESS accessible-for-notify
    STATUS current
    DESCRIPTION
        "Parameter 'ip-source' in event AFS.41"
    ::= { afsEventObjects41 4 }

afs41_ip-destination OBJECT-TYPE
    SYNTAX DisplayString
    MAX-ACCESS accessible-for-notify
    STATUS current
    DESCRIPTION
        "Parameter 'ip-destination' in event AFS.41"
    ::= { afsEventObjects41 5 }

afs41_protocol OBJECT-TYPE
    SYNTAX DisplayString
    MAX-ACCESS accessible-for-notify
    STATUS current
    DESCRIPTION
        "Parameter 'protocol' in event AFS.41"
    ::= { afsEventObjects41 6 }

afs41_in-ifc OBJECT-TYPE
    SYNTAX DisplayString
    MAX-ACCESS accessible-for-notify
    STATUS current
    DESCRIPTION
        "Parameter 'in-ifc' in event AFS.41"
    ::= { afsEventObjects41 7 }

afsEventObjects42 OBJECT-IDENTITY
    STATUS current
    DESCRIPTION
        "Event AFS.42
        a local-in ipv6 packet has been accepted by a filter rule"
    ::= { afsEventsGroup 42 }

afs42_access-list OBJECT-TYPE
    SYNTAX Integer32
    MAX-ACCESS accessible-for-notify
    STATUS current
    DESCRIPTION
        "Parameter 'access-list' in event AFS.42"
    ::= { afsEventObjects42 1 }

afs42_entry OBJECT-TYPE
    SYNTAX Integer32
    MAX-ACCESS accessible-for-notify
    STATUS current
    DESCRIPTION
        "Parameter 'entry' in event AFS.42"
    ::= { afsEventObjects42 2 }

afs42_ip-source OBJECT-TYPE
    SYNTAX DisplayString
    MAX-ACCESS accessible-for-notify
    STATUS current
    DESCRIPTION
        "Parameter 'ip-source' in event AFS.42"
    ::= { afsEventObjects42 3 }

afs42_ip-destination OBJECT-TYPE
    SYNTAX DisplayString
    MAX-ACCESS accessible-for-notify
    STATUS current
    DESCRIPTION
        "Parameter 'ip-destination' in event AFS.42"
    ::= { afsEventObjects42 4 }

afs42_protocol OBJECT-TYPE
    SYNTAX DisplayString
    MAX-ACCESS accessible-for-notify
    STATUS current
    DESCRIPTION
        "Parameter 'protocol' in event AFS.42"
    ::= { afsEventObjects42 5 }

afs42_in-ifc OBJECT-TYPE
    SYNTAX DisplayString
    MAX-ACCESS accessible-for-notify
    STATUS current
    DESCRIPTION
        "Parameter 'in-ifc' in event AFS.42"
    ::= { afsEventObjects42 6 }

afsEventObjects43 OBJECT-IDENTITY
    STATUS current
    DESCRIPTION
        "Event AFS.43
        a local-in ipv6 packet has been discarded by a filter rule"
    ::= { afsEventsGroup 43 }

afs43_access-list OBJECT-TYPE
    SYNTAX Integer32
    MAX-ACCESS accessible-for-notify
    STATUS current
    DESCRIPTION
        "Parameter 'access-list' in event AFS.43"
    ::= { afsEventObjects43 1 }

afs43_entry OBJECT-TYPE
    SYNTAX Integer32
    MAX-ACCESS accessible-for-notify
    STATUS current
    DESCRIPTION
        "Parameter 'entry' in event AFS.43"
    ::= { afsEventObjects43 2 }

afs43_ip-source OBJECT-TYPE
    SYNTAX DisplayString
    MAX-ACCESS accessible-for-notify
    STATUS current
    DESCRIPTION
        "Parameter 'ip-source' in event AFS.43"
    ::= { afsEventObjects43 3 }

afs43_ip-destination OBJECT-TYPE
    SYNTAX DisplayString
    MAX-ACCESS accessible-for-notify
    STATUS current
    DESCRIPTION
        "Parameter 'ip-destination' in event AFS.43"
    ::= { afsEventObjects43 4 }

afs43_protocol OBJECT-TYPE
    SYNTAX DisplayString
    MAX-ACCESS accessible-for-notify
    STATUS current
    DESCRIPTION
        "Parameter 'protocol' in event AFS.43"
    ::= { afsEventObjects43 5 }

afs43_in-ifc OBJECT-TYPE
    SYNTAX DisplayString
    MAX-ACCESS accessible-for-notify
    STATUS current
    DESCRIPTION
        "Parameter 'in-ifc' in event AFS.43"
    ::= { afsEventObjects43 6 }

afsEventObjects44 OBJECT-IDENTITY
    STATUS current
    DESCRIPTION
        "Event AFS.44
        a local-out ipv6 packet has been accepted by a filter rule"
    ::= { afsEventsGroup 44 }

afs44_access-list OBJECT-TYPE
    SYNTAX Integer32
    MAX-ACCESS accessible-for-notify
    STATUS current
    DESCRIPTION
        "Parameter 'access-list' in event AFS.44"
    ::= { afsEventObjects44 1 }

afs44_entry OBJECT-TYPE
    SYNTAX Integer32
    MAX-ACCESS accessible-for-notify
    STATUS current
    DESCRIPTION
        "Parameter 'entry' in event AFS.44"
    ::= { afsEventObjects44 2 }

afs44_ip-source OBJECT-TYPE
    SYNTAX DisplayString
    MAX-ACCESS accessible-for-notify
    STATUS current
    DESCRIPTION
        "Parameter 'ip-source' in event AFS.44"
    ::= { afsEventObjects44 3 }

afs44_ip-destination OBJECT-TYPE
    SYNTAX DisplayString
    MAX-ACCESS accessible-for-notify
    STATUS current
    DESCRIPTION
        "Parameter 'ip-destination' in event AFS.44"
    ::= { afsEventObjects44 4 }

afs44_protocol OBJECT-TYPE
    SYNTAX DisplayString
    MAX-ACCESS accessible-for-notify
    STATUS current
    DESCRIPTION
        "Parameter 'protocol' in event AFS.44"
    ::= { afsEventObjects44 5 }

afs44_out-ifc OBJECT-TYPE
    SYNTAX DisplayString
    MAX-ACCESS accessible-for-notify
    STATUS current
    DESCRIPTION
        "Parameter 'out-ifc' in event AFS.44"
    ::= { afsEventObjects44 6 }

afsEventObjects45 OBJECT-IDENTITY
    STATUS current
    DESCRIPTION
        "Event AFS.45
        a local-out ipv6 packet has been discarded by a filter rule"
    ::= { afsEventsGroup 45 }

afs45_access-list OBJECT-TYPE
    SYNTAX Integer32
    MAX-ACCESS accessible-for-notify
    STATUS current
    DESCRIPTION
        "Parameter 'access-list' in event AFS.45"
    ::= { afsEventObjects45 1 }

afs45_entry OBJECT-TYPE
    SYNTAX Integer32
    MAX-ACCESS accessible-for-notify
    STATUS current
    DESCRIPTION
        "Parameter 'entry' in event AFS.45"
    ::= { afsEventObjects45 2 }

afs45_ip-source OBJECT-TYPE
    SYNTAX DisplayString
    MAX-ACCESS accessible-for-notify
    STATUS current
    DESCRIPTION
        "Parameter 'ip-source' in event AFS.45"
    ::= { afsEventObjects45 3 }

afs45_ip-destination OBJECT-TYPE
    SYNTAX DisplayString
    MAX-ACCESS accessible-for-notify
    STATUS current
    DESCRIPTION
        "Parameter 'ip-destination' in event AFS.45"
    ::= { afsEventObjects45 4 }

afs45_protocol OBJECT-TYPE
    SYNTAX DisplayString
    MAX-ACCESS accessible-for-notify
    STATUS current
    DESCRIPTION
        "Parameter 'protocol' in event AFS.45"
    ::= { afsEventObjects45 5 }

afs45_out-ifc OBJECT-TYPE
    SYNTAX DisplayString
    MAX-ACCESS accessible-for-notify
    STATUS current
    DESCRIPTION
        "Parameter 'out-ifc' in event AFS.45"
    ::= { afsEventObjects45 6 }

afsEventObjects46 OBJECT-IDENTITY
    STATUS current
    DESCRIPTION
        "Event AFS.46
        new connection event"
    ::= { afsEventsGroup 46 }

afs46_protocol OBJECT-TYPE
    SYNTAX DisplayString
    MAX-ACCESS accessible-for-notify
    STATUS current
    DESCRIPTION
        "Parameter 'protocol' in event AFS.46"
    ::= { afsEventObjects46 1 }

afs46_state OBJECT-TYPE
    SYNTAX DisplayString
    MAX-ACCESS accessible-for-notify
    STATUS current
    DESCRIPTION
        "Parameter 'state' in event AFS.46"
    ::= { afsEventObjects46 2 }

afs46_status OBJECT-TYPE
    SYNTAX DisplayString
    MAX-ACCESS accessible-for-notify
    STATUS current
    DESCRIPTION
        "Parameter 'status' in event AFS.46"
    ::= { afsEventObjects46 3 }

afs46_org_ip_src OBJECT-TYPE
    SYNTAX DisplayString
    MAX-ACCESS accessible-for-notify
    STATUS current
    DESCRIPTION
        "Parameter 'org_ip_src' in event AFS.46"
    ::= { afsEventObjects46 4 }

afs46_org_id_src OBJECT-TYPE
    SYNTAX Integer32
    MAX-ACCESS accessible-for-notify
    STATUS current
    DESCRIPTION
        "Parameter 'org_id_src' in event AFS.46"
    ::= { afsEventObjects46 5 }

afs46_org_ip_dst OBJECT-TYPE
    SYNTAX DisplayString
    MAX-ACCESS accessible-for-notify
    STATUS current
    DESCRIPTION
        "Parameter 'org_ip_dst' in event AFS.46"
    ::= { afsEventObjects46 6 }

afs46_org_id_dst OBJECT-TYPE
    SYNTAX Integer32
    MAX-ACCESS accessible-for-notify
    STATUS current
    DESCRIPTION
        "Parameter 'org_id_dst' in event AFS.46"
    ::= { afsEventObjects46 7 }

afs46_rply_ip_src OBJECT-TYPE
    SYNTAX DisplayString
    MAX-ACCESS accessible-for-notify
    STATUS current
    DESCRIPTION
        "Parameter 'rply_ip_src' in event AFS.46"
    ::= { afsEventObjects46 8 }

afs46_rply_id_src OBJECT-TYPE
    SYNTAX Integer32
    MAX-ACCESS accessible-for-notify
    STATUS current
    DESCRIPTION
        "Parameter 'rply_id_src' in event AFS.46"
    ::= { afsEventObjects46 9 }

afs46_rply_ip_dst OBJECT-TYPE
    SYNTAX DisplayString
    MAX-ACCESS accessible-for-notify
    STATUS current
    DESCRIPTION
        "Parameter 'rply_ip_dst' in event AFS.46"
    ::= { afsEventObjects46 10 }

afs46_rply_id_dst OBJECT-TYPE
    SYNTAX Integer32
    MAX-ACCESS accessible-for-notify
    STATUS current
    DESCRIPTION
        "Parameter 'rply_id_dst' in event AFS.46"
    ::= { afsEventObjects46 11 }

afsEventObjects47 OBJECT-IDENTITY
    STATUS current
    DESCRIPTION
        "Event AFS.47
        confirmed connection event"
    ::= { afsEventsGroup 47 }

afs47_protocol OBJECT-TYPE
    SYNTAX DisplayString
    MAX-ACCESS accessible-for-notify
    STATUS current
    DESCRIPTION
        "Parameter 'protocol' in event AFS.47"
    ::= { afsEventObjects47 1 }

afs47_state OBJECT-TYPE
    SYNTAX DisplayString
    MAX-ACCESS accessible-for-notify
    STATUS current
    DESCRIPTION
        "Parameter 'state' in event AFS.47"
    ::= { afsEventObjects47 2 }

afs47_status OBJECT-TYPE
    SYNTAX DisplayString
    MAX-ACCESS accessible-for-notify
    STATUS current
    DESCRIPTION
        "Parameter 'status' in event AFS.47"
    ::= { afsEventObjects47 3 }

afs47_org_ip_src OBJECT-TYPE
    SYNTAX DisplayString
    MAX-ACCESS accessible-for-notify
    STATUS current
    DESCRIPTION
        "Parameter 'org_ip_src' in event AFS.47"
    ::= { afsEventObjects47 4 }

afs47_org_id_src OBJECT-TYPE
    SYNTAX Integer32
    MAX-ACCESS accessible-for-notify
    STATUS current
    DESCRIPTION
        "Parameter 'org_id_src' in event AFS.47"
    ::= { afsEventObjects47 5 }

afs47_org_ip_dst OBJECT-TYPE
    SYNTAX DisplayString
    MAX-ACCESS accessible-for-notify
    STATUS current
    DESCRIPTION
        "Parameter 'org_ip_dst' in event AFS.47"
    ::= { afsEventObjects47 6 }

afs47_org_id_dst OBJECT-TYPE
    SYNTAX Integer32
    MAX-ACCESS accessible-for-notify
    STATUS current
    DESCRIPTION
        "Parameter 'org_id_dst' in event AFS.47"
    ::= { afsEventObjects47 7 }

afs47_rply_ip_src OBJECT-TYPE
    SYNTAX DisplayString
    MAX-ACCESS accessible-for-notify
    STATUS current
    DESCRIPTION
        "Parameter 'rply_ip_src' in event AFS.47"
    ::= { afsEventObjects47 8 }

afs47_rply_id_src OBJECT-TYPE
    SYNTAX Integer32
    MAX-ACCESS accessible-for-notify
    STATUS current
    DESCRIPTION
        "Parameter 'rply_id_src' in event AFS.47"
    ::= { afsEventObjects47 9 }

afs47_rply_ip_dst OBJECT-TYPE
    SYNTAX DisplayString
    MAX-ACCESS accessible-for-notify
    STATUS current
    DESCRIPTION
        "Parameter 'rply_ip_dst' in event AFS.47"
    ::= { afsEventObjects47 10 }

afs47_rply_id_dst OBJECT-TYPE
    SYNTAX Integer32
    MAX-ACCESS accessible-for-notify
    STATUS current
    DESCRIPTION
        "Parameter 'rply_id_dst' in event AFS.47"
    ::= { afsEventObjects47 11 }

afsEventObjects48 OBJECT-IDENTITY
    STATUS current
    DESCRIPTION
        "Event AFS.48
        deleted connection event"
    ::= { afsEventsGroup 48 }

afs48_protocol OBJECT-TYPE
    SYNTAX DisplayString
    MAX-ACCESS accessible-for-notify
    STATUS current
    DESCRIPTION
        "Parameter 'protocol' in event AFS.48"
    ::= { afsEventObjects48 1 }

afs48_state OBJECT-TYPE
    SYNTAX DisplayString
    MAX-ACCESS accessible-for-notify
    STATUS current
    DESCRIPTION
        "Parameter 'state' in event AFS.48"
    ::= { afsEventObjects48 2 }

afs48_status OBJECT-TYPE
    SYNTAX DisplayString
    MAX-ACCESS accessible-for-notify
    STATUS current
    DESCRIPTION
        "Parameter 'status' in event AFS.48"
    ::= { afsEventObjects48 3 }

afs48_org_ip_src OBJECT-TYPE
    SYNTAX DisplayString
    MAX-ACCESS accessible-for-notify
    STATUS current
    DESCRIPTION
        "Parameter 'org_ip_src' in event AFS.48"
    ::= { afsEventObjects48 4 }

afs48_org_id_src OBJECT-TYPE
    SYNTAX Integer32
    MAX-ACCESS accessible-for-notify
    STATUS current
    DESCRIPTION
        "Parameter 'org_id_src' in event AFS.48"
    ::= { afsEventObjects48 5 }

afs48_org_ip_dst OBJECT-TYPE
    SYNTAX DisplayString
    MAX-ACCESS accessible-for-notify
    STATUS current
    DESCRIPTION
        "Parameter 'org_ip_dst' in event AFS.48"
    ::= { afsEventObjects48 6 }

afs48_org_id_dst OBJECT-TYPE
    SYNTAX Integer32
    MAX-ACCESS accessible-for-notify
    STATUS current
    DESCRIPTION
        "Parameter 'org_id_dst' in event AFS.48"
    ::= { afsEventObjects48 7 }

afs48_rply_ip_src OBJECT-TYPE
    SYNTAX DisplayString
    MAX-ACCESS accessible-for-notify
    STATUS current
    DESCRIPTION
        "Parameter 'rply_ip_src' in event AFS.48"
    ::= { afsEventObjects48 8 }

afs48_rply_id_src OBJECT-TYPE
    SYNTAX Integer32
    MAX-ACCESS accessible-for-notify
    STATUS current
    DESCRIPTION
        "Parameter 'rply_id_src' in event AFS.48"
    ::= { afsEventObjects48 9 }

afs48_rply_ip_dst OBJECT-TYPE
    SYNTAX DisplayString
    MAX-ACCESS accessible-for-notify
    STATUS current
    DESCRIPTION
        "Parameter 'rply_ip_dst' in event AFS.48"
    ::= { afsEventObjects48 10 }

afs48_rply_id_dst OBJECT-TYPE
    SYNTAX Integer32
    MAX-ACCESS accessible-for-notify
    STATUS current
    DESCRIPTION
        "Parameter 'rply_id_dst' in event AFS.48"
    ::= { afsEventObjects48 11 }

afsEventObjects49 OBJECT-IDENTITY
    STATUS current
    DESCRIPTION
        "Event AFS.49
        failed confirmation connection event"
    ::= { afsEventsGroup 49 }

afs49_protocol OBJECT-TYPE
    SYNTAX DisplayString
    MAX-ACCESS accessible-for-notify
    STATUS current
    DESCRIPTION
        "Parameter 'protocol' in event AFS.49"
    ::= { afsEventObjects49 1 }

afs49_state OBJECT-TYPE
    SYNTAX DisplayString
    MAX-ACCESS accessible-for-notify
    STATUS current
    DESCRIPTION
        "Parameter 'state' in event AFS.49"
    ::= { afsEventObjects49 2 }

afs49_status OBJECT-TYPE
    SYNTAX DisplayString
    MAX-ACCESS accessible-for-notify
    STATUS current
    DESCRIPTION
        "Parameter 'status' in event AFS.49"
    ::= { afsEventObjects49 3 }

afs49_org_ip_src OBJECT-TYPE
    SYNTAX DisplayString
    MAX-ACCESS accessible-for-notify
    STATUS current
    DESCRIPTION
        "Parameter 'org_ip_src' in event AFS.49"
    ::= { afsEventObjects49 4 }

afs49_org_id_src OBJECT-TYPE
    SYNTAX Integer32
    MAX-ACCESS accessible-for-notify
    STATUS current
    DESCRIPTION
        "Parameter 'org_id_src' in event AFS.49"
    ::= { afsEventObjects49 5 }

afs49_org_ip_dst OBJECT-TYPE
    SYNTAX DisplayString
    MAX-ACCESS accessible-for-notify
    STATUS current
    DESCRIPTION
        "Parameter 'org_ip_dst' in event AFS.49"
    ::= { afsEventObjects49 6 }

afs49_org_id_dst OBJECT-TYPE
    SYNTAX Integer32
    MAX-ACCESS accessible-for-notify
    STATUS current
    DESCRIPTION
        "Parameter 'org_id_dst' in event AFS.49"
    ::= { afsEventObjects49 7 }

afs49_rply_ip_src OBJECT-TYPE
    SYNTAX DisplayString
    MAX-ACCESS accessible-for-notify
    STATUS current
    DESCRIPTION
        "Parameter 'rply_ip_src' in event AFS.49"
    ::= { afsEventObjects49 8 }

afs49_rply_id_src OBJECT-TYPE
    SYNTAX Integer32
    MAX-ACCESS accessible-for-notify
    STATUS current
    DESCRIPTION
        "Parameter 'rply_id_src' in event AFS.49"
    ::= { afsEventObjects49 9 }

afs49_rply_ip_dst OBJECT-TYPE
    SYNTAX DisplayString
    MAX-ACCESS accessible-for-notify
    STATUS current
    DESCRIPTION
        "Parameter 'rply_ip_dst' in event AFS.49"
    ::= { afsEventObjects49 10 }

afs49_rply_id_dst OBJECT-TYPE
    SYNTAX Integer32
    MAX-ACCESS accessible-for-notify
    STATUS current
    DESCRIPTION
        "Parameter 'rply_id_dst' in event AFS.49"
    ::= { afsEventObjects49 11 }

afsEventObjects50 OBJECT-IDENTITY
    STATUS current
    DESCRIPTION
        "Event AFS.50
        new expected connection added"
    ::= { afsEventsGroup 50 }

afs50_protocol OBJECT-TYPE
    SYNTAX DisplayString
    MAX-ACCESS accessible-for-notify
    STATUS current
    DESCRIPTION
        "Parameter 'protocol' in event AFS.50"
    ::= { afsEventObjects50 1 }

afs50_state OBJECT-TYPE
    SYNTAX DisplayString
    MAX-ACCESS accessible-for-notify
    STATUS current
    DESCRIPTION
        "Parameter 'state' in event AFS.50"
    ::= { afsEventObjects50 2 }

afs50_status OBJECT-TYPE
    SYNTAX DisplayString
    MAX-ACCESS accessible-for-notify
    STATUS current
    DESCRIPTION
        "Parameter 'status' in event AFS.50"
    ::= { afsEventObjects50 3 }

afs50_org_ip_src OBJECT-TYPE
    SYNTAX DisplayString
    MAX-ACCESS accessible-for-notify
    STATUS current
    DESCRIPTION
        "Parameter 'org_ip_src' in event AFS.50"
    ::= { afsEventObjects50 4 }

afs50_org_id_src OBJECT-TYPE
    SYNTAX Integer32
    MAX-ACCESS accessible-for-notify
    STATUS current
    DESCRIPTION
        "Parameter 'org_id_src' in event AFS.50"
    ::= { afsEventObjects50 5 }

afs50_org_ip_dst OBJECT-TYPE
    SYNTAX DisplayString
    MAX-ACCESS accessible-for-notify
    STATUS current
    DESCRIPTION
        "Parameter 'org_ip_dst' in event AFS.50"
    ::= { afsEventObjects50 6 }

afs50_org_id_dst OBJECT-TYPE
    SYNTAX Integer32
    MAX-ACCESS accessible-for-notify
    STATUS current
    DESCRIPTION
        "Parameter 'org_id_dst' in event AFS.50"
    ::= { afsEventObjects50 7 }

afs50_rply_ip_src OBJECT-TYPE
    SYNTAX DisplayString
    MAX-ACCESS accessible-for-notify
    STATUS current
    DESCRIPTION
        "Parameter 'rply_ip_src' in event AFS.50"
    ::= { afsEventObjects50 8 }

afs50_rply_id_src OBJECT-TYPE
    SYNTAX Integer32
    MAX-ACCESS accessible-for-notify
    STATUS current
    DESCRIPTION
        "Parameter 'rply_id_src' in event AFS.50"
    ::= { afsEventObjects50 9 }

afs50_rply_ip_dst OBJECT-TYPE
    SYNTAX DisplayString
    MAX-ACCESS accessible-for-notify
    STATUS current
    DESCRIPTION
        "Parameter 'rply_ip_dst' in event AFS.50"
    ::= { afsEventObjects50 10 }

afs50_rply_id_dst OBJECT-TYPE
    SYNTAX Integer32
    MAX-ACCESS accessible-for-notify
    STATUS current
    DESCRIPTION
        "Parameter 'rply_id_dst' in event AFS.50"
    ::= { afsEventObjects50 11 }

afsEventObjects51 OBJECT-IDENTITY
    STATUS current
    DESCRIPTION
        "Event AFS.51
        alg found event"
    ::= { afsEventsGroup 51 }

afs51_alg OBJECT-TYPE
    SYNTAX DisplayString
    MAX-ACCESS accessible-for-notify
    STATUS current
    DESCRIPTION
        "Parameter 'alg' in event AFS.51"
    ::= { afsEventObjects51 1 }

afs51_protocol OBJECT-TYPE
    SYNTAX DisplayString
    MAX-ACCESS accessible-for-notify
    STATUS current
    DESCRIPTION
        "Parameter 'protocol' in event AFS.51"
    ::= { afsEventObjects51 2 }

afs51_state OBJECT-TYPE
    SYNTAX DisplayString
    MAX-ACCESS accessible-for-notify
    STATUS current
    DESCRIPTION
        "Parameter 'state' in event AFS.51"
    ::= { afsEventObjects51 3 }

afs51_status OBJECT-TYPE
    SYNTAX DisplayString
    MAX-ACCESS accessible-for-notify
    STATUS current
    DESCRIPTION
        "Parameter 'status' in event AFS.51"
    ::= { afsEventObjects51 4 }

afs51_org_ip_src OBJECT-TYPE
    SYNTAX DisplayString
    MAX-ACCESS accessible-for-notify
    STATUS current
    DESCRIPTION
        "Parameter 'org_ip_src' in event AFS.51"
    ::= { afsEventObjects51 5 }

afs51_org_id_src OBJECT-TYPE
    SYNTAX Integer32
    MAX-ACCESS accessible-for-notify
    STATUS current
    DESCRIPTION
        "Parameter 'org_id_src' in event AFS.51"
    ::= { afsEventObjects51 6 }

afs51_org_ip_dst OBJECT-TYPE
    SYNTAX DisplayString
    MAX-ACCESS accessible-for-notify
    STATUS current
    DESCRIPTION
        "Parameter 'org_ip_dst' in event AFS.51"
    ::= { afsEventObjects51 7 }

afs51_org_id_dst OBJECT-TYPE
    SYNTAX Integer32
    MAX-ACCESS accessible-for-notify
    STATUS current
    DESCRIPTION
        "Parameter 'org_id_dst' in event AFS.51"
    ::= { afsEventObjects51 8 }

afs51_rply_ip_src OBJECT-TYPE
    SYNTAX DisplayString
    MAX-ACCESS accessible-for-notify
    STATUS current
    DESCRIPTION
        "Parameter 'rply_ip_src' in event AFS.51"
    ::= { afsEventObjects51 9 }

afs51_rply_id_src OBJECT-TYPE
    SYNTAX Integer32
    MAX-ACCESS accessible-for-notify
    STATUS current
    DESCRIPTION
        "Parameter 'rply_id_src' in event AFS.51"
    ::= { afsEventObjects51 10 }

afs51_rply_ip_dst OBJECT-TYPE
    SYNTAX DisplayString
    MAX-ACCESS accessible-for-notify
    STATUS current
    DESCRIPTION
        "Parameter 'rply_ip_dst' in event AFS.51"
    ::= { afsEventObjects51 11 }

afs51_rply_id_dst OBJECT-TYPE
    SYNTAX Integer32
    MAX-ACCESS accessible-for-notify
    STATUS current
    DESCRIPTION
        "Parameter 'rply_id_dst' in event AFS.51"
    ::= { afsEventObjects51 12 }

afsEventObjects52 OBJECT-IDENTITY
    STATUS current
    DESCRIPTION
        "Event AFS.52
        connection expected found event"
    ::= { afsEventsGroup 52 }

afs52_protocol OBJECT-TYPE
    SYNTAX DisplayString
    MAX-ACCESS accessible-for-notify
    STATUS current
    DESCRIPTION
        "Parameter 'protocol' in event AFS.52"
    ::= { afsEventObjects52 1 }

afs52_state OBJECT-TYPE
    SYNTAX DisplayString
    MAX-ACCESS accessible-for-notify
    STATUS current
    DESCRIPTION
        "Parameter 'state' in event AFS.52"
    ::= { afsEventObjects52 2 }

afs52_status OBJECT-TYPE
    SYNTAX DisplayString
    MAX-ACCESS accessible-for-notify
    STATUS current
    DESCRIPTION
        "Parameter 'status' in event AFS.52"
    ::= { afsEventObjects52 3 }

afs52_org_ip_src OBJECT-TYPE
    SYNTAX DisplayString
    MAX-ACCESS accessible-for-notify
    STATUS current
    DESCRIPTION
        "Parameter 'org_ip_src' in event AFS.52"
    ::= { afsEventObjects52 4 }

afs52_org_id_src OBJECT-TYPE
    SYNTAX Integer32
    MAX-ACCESS accessible-for-notify
    STATUS current
    DESCRIPTION
        "Parameter 'org_id_src' in event AFS.52"
    ::= { afsEventObjects52 5 }

afs52_org_ip_dst OBJECT-TYPE
    SYNTAX DisplayString
    MAX-ACCESS accessible-for-notify
    STATUS current
    DESCRIPTION
        "Parameter 'org_ip_dst' in event AFS.52"
    ::= { afsEventObjects52 6 }

afs52_org_id_dst OBJECT-TYPE
    SYNTAX Integer32
    MAX-ACCESS accessible-for-notify
    STATUS current
    DESCRIPTION
        "Parameter 'org_id_dst' in event AFS.52"
    ::= { afsEventObjects52 7 }

afs52_rply_ip_src OBJECT-TYPE
    SYNTAX DisplayString
    MAX-ACCESS accessible-for-notify
    STATUS current
    DESCRIPTION
        "Parameter 'rply_ip_src' in event AFS.52"
    ::= { afsEventObjects52 8 }

afs52_rply_id_src OBJECT-TYPE
    SYNTAX Integer32
    MAX-ACCESS accessible-for-notify
    STATUS current
    DESCRIPTION
        "Parameter 'rply_id_src' in event AFS.52"
    ::= { afsEventObjects52 9 }

afs52_rply_ip_dst OBJECT-TYPE
    SYNTAX DisplayString
    MAX-ACCESS accessible-for-notify
    STATUS current
    DESCRIPTION
        "Parameter 'rply_ip_dst' in event AFS.52"
    ::= { afsEventObjects52 10 }

afs52_rply_id_dst OBJECT-TYPE
    SYNTAX Integer32
    MAX-ACCESS accessible-for-notify
    STATUS current
    DESCRIPTION
        "Parameter 'rply_id_dst' in event AFS.52"
    ::= { afsEventObjects52 11 }

afsEventObjects53 OBJECT-IDENTITY
    STATUS current
    DESCRIPTION
        "Event AFS.53
        a connection has been matched by a packet"
    ::= { afsEventsGroup 53 }

afs53_protocol OBJECT-TYPE
    SYNTAX DisplayString
    MAX-ACCESS accessible-for-notify
    STATUS current
    DESCRIPTION
        "Parameter 'protocol' in event AFS.53"
    ::= { afsEventObjects53 1 }

afs53_state OBJECT-TYPE
    SYNTAX DisplayString
    MAX-ACCESS accessible-for-notify
    STATUS current
    DESCRIPTION
        "Parameter 'state' in event AFS.53"
    ::= { afsEventObjects53 2 }

afs53_status OBJECT-TYPE
    SYNTAX DisplayString
    MAX-ACCESS accessible-for-notify
    STATUS current
    DESCRIPTION
        "Parameter 'status' in event AFS.53"
    ::= { afsEventObjects53 3 }

afs53_org_ip_src OBJECT-TYPE
    SYNTAX DisplayString
    MAX-ACCESS accessible-for-notify
    STATUS current
    DESCRIPTION
        "Parameter 'org_ip_src' in event AFS.53"
    ::= { afsEventObjects53 4 }

afs53_org_id_src OBJECT-TYPE
    SYNTAX Integer32
    MAX-ACCESS accessible-for-notify
    STATUS current
    DESCRIPTION
        "Parameter 'org_id_src' in event AFS.53"
    ::= { afsEventObjects53 5 }

afs53_org_ip_dst OBJECT-TYPE
    SYNTAX DisplayString
    MAX-ACCESS accessible-for-notify
    STATUS current
    DESCRIPTION
        "Parameter 'org_ip_dst' in event AFS.53"
    ::= { afsEventObjects53 6 }

afs53_org_id_dst OBJECT-TYPE
    SYNTAX Integer32
    MAX-ACCESS accessible-for-notify
    STATUS current
    DESCRIPTION
        "Parameter 'org_id_dst' in event AFS.53"
    ::= { afsEventObjects53 7 }

afs53_rply_ip_src OBJECT-TYPE
    SYNTAX DisplayString
    MAX-ACCESS accessible-for-notify
    STATUS current
    DESCRIPTION
        "Parameter 'rply_ip_src' in event AFS.53"
    ::= { afsEventObjects53 8 }

afs53_rply_id_src OBJECT-TYPE
    SYNTAX Integer32
    MAX-ACCESS accessible-for-notify
    STATUS current
    DESCRIPTION
        "Parameter 'rply_id_src' in event AFS.53"
    ::= { afsEventObjects53 9 }

afs53_rply_ip_dst OBJECT-TYPE
    SYNTAX DisplayString
    MAX-ACCESS accessible-for-notify
    STATUS current
    DESCRIPTION
        "Parameter 'rply_ip_dst' in event AFS.53"
    ::= { afsEventObjects53 10 }

afs53_rply_id_dst OBJECT-TYPE
    SYNTAX Integer32
    MAX-ACCESS accessible-for-notify
    STATUS current
    DESCRIPTION
        "Parameter 'rply_id_dst' in event AFS.53"
    ::= { afsEventObjects53 11 }

afsEventObjects54 OBJECT-IDENTITY
    STATUS current
    DESCRIPTION
        "Event AFS.54
        an url filter has matched"
    ::= { afsEventsGroup 54 }

afs54_server_ip OBJECT-TYPE
    SYNTAX DisplayString
    MAX-ACCESS accessible-for-notify
    STATUS current
    DESCRIPTION
        "Parameter 'server_ip' in event AFS.54"
    ::= { afsEventObjects54 1 }

afs54_filename OBJECT-TYPE
    SYNTAX DisplayString
    MAX-ACCESS accessible-for-notify
    STATUS current
    DESCRIPTION
        "Parameter 'filename' in event AFS.54"
    ::= { afsEventObjects54 2 }

afs54_ev OBJECT-TYPE
    SYNTAX DisplayString
    MAX-ACCESS accessible-for-notify
    STATUS current
    DESCRIPTION
        "Parameter 'ev' in event AFS.54"
    ::= { afsEventObjects54 3 }

afs54_info OBJECT-TYPE
    SYNTAX DisplayString
    MAX-ACCESS accessible-for-notify
    STATUS current
    DESCRIPTION
        "Parameter 'info' in event AFS.54"
    ::= { afsEventObjects54 4 }

afsEventObjects55 OBJECT-IDENTITY
    STATUS current
    DESCRIPTION
        "Event AFS.55
        an internal error has arisen"
    ::= { afsEventsGroup 55 }

afs55_message OBJECT-TYPE
    SYNTAX DisplayString
    MAX-ACCESS accessible-for-notify
    STATUS current
    DESCRIPTION
        "Parameter 'message' in event AFS.55"
    ::= { afsEventObjects55 1 }

afsEventObjects56 OBJECT-IDENTITY
    STATUS current
    DESCRIPTION
        "Event AFS.56
        A routing change has been detected. The session will be dropped."
    ::= { afsEventsGroup 56 }

afs56_ip-source OBJECT-TYPE
    SYNTAX IpAddress
    MAX-ACCESS accessible-for-notify
    STATUS current
    DESCRIPTION
        "Parameter 'ip-source' in event AFS.56"
    ::= { afsEventObjects56 1 }

afs56_ip-destination OBJECT-TYPE
    SYNTAX IpAddress
    MAX-ACCESS accessible-for-notify
    STATUS current
    DESCRIPTION
        "Parameter 'ip-destination' in event AFS.56"
    ::= { afsEventObjects56 2 }

afs56_protocol OBJECT-TYPE
    SYNTAX DisplayString
    MAX-ACCESS accessible-for-notify
    STATUS current
    DESCRIPTION
        "Parameter 'protocol' in event AFS.56"
    ::= { afsEventObjects56 3 }

afs56_out-ifc OBJECT-TYPE
    SYNTAX DisplayString
    MAX-ACCESS accessible-for-notify
    STATUS current
    DESCRIPTION
        "Parameter 'out-ifc' in event AFS.56"
    ::= { afsEventObjects56 4 }

afsEventObjects57 OBJECT-IDENTITY
    STATUS current
    DESCRIPTION
        "Event AFS.57
        An invalid packet has been detected. The session will be dropped."
    ::= { afsEventsGroup 57 }

afs57_ip-source OBJECT-TYPE
    SYNTAX IpAddress
    MAX-ACCESS accessible-for-notify
    STATUS current
    DESCRIPTION
        "Parameter 'ip-source' in event AFS.57"
    ::= { afsEventObjects57 1 }

afs57_ip-destination OBJECT-TYPE
    SYNTAX IpAddress
    MAX-ACCESS accessible-for-notify
    STATUS current
    DESCRIPTION
        "Parameter 'ip-destination' in event AFS.57"
    ::= { afsEventObjects57 2 }

afs57_protocol OBJECT-TYPE
    SYNTAX DisplayString
    MAX-ACCESS accessible-for-notify
    STATUS current
    DESCRIPTION
        "Parameter 'protocol' in event AFS.57"
    ::= { afsEventObjects57 3 }


afsNotification1 NOTIFICATION-TYPE
    OBJECTS { 
              afs1_ip-source, 
              afs1_ip-destination,
              afs1_protocol,
              afs1_in-ifc 
            }
    STATUS current
    DESCRIPTION
        "Notification of Event AFS.1

        Message: 'IP packet filtered in IN source $1 destination $2 protocol $3 in interface $4 action ACCEPTED'

        Parameters list:
              $1: afs1_ip-source
              $2: afs1_ip-destination
              $3: afs1_protocol
              $4: afs1_in-ifc

        an in ip packet has been accepted"
    ::= { afsNotificationsPrefix 1 }

afsNotification2 NOTIFICATION-TYPE
    OBJECTS { 
              afs2_ip-source, 
              afs2_ip-destination,
              afs2_protocol,
              afs2_in-ifc 
            }
    STATUS current
    DESCRIPTION
        "Notification of Event AFS.2

        Message: 'IP packet filtered in IN source $1 destination $2 protocol $3 in interface $4 action DISCARDED'

        Parameters list:
              $1: afs2_ip-source
              $2: afs2_ip-destination
              $3: afs2_protocol
              $4: afs2_in-ifc

        an in ip packet has been discarded"
    ::= { afsNotificationsPrefix 2 }

afsNotification3 NOTIFICATION-TYPE
    OBJECTS { 
              afs3_ip-source, 
              afs3_ip-destination,
              afs3_protocol,
              afs3_in-ifc,
              afs3_out-ifc 
            }
    STATUS current
    DESCRIPTION
        "Notification of Event AFS.3

        Message: 'IP packet filtered in OUT source $1 destination $2 protocol $3 in interface $4 out interface $5 action ACCEPTED'

        Parameters list:
              $1: afs3_ip-source
              $2: afs3_ip-destination
              $3: afs3_protocol
              $4: afs3_in-ifc
              $5: afs3_out-ifc

        an out ip packet has been accepted"
    ::= { afsNotificationsPrefix 3 }

afsNotification4 NOTIFICATION-TYPE
    OBJECTS { 
              afs4_ip-source, 
              afs4_ip-destination,
              afs4_protocol,
              afs4_in-ifc,
              afs4_out-ifc 
            }
    STATUS current
    DESCRIPTION
        "Notification of Event AFS.4

        Message: 'IP packet filtered in OUT source $1 destination $2 protocol $3 in interface $4 out interface $5 action DISCARDED'

        Parameters list:
              $1: afs4_ip-source
              $2: afs4_ip-destination
              $3: afs4_protocol
              $4: afs4_in-ifc
              $5: afs4_out-ifc

        an out ip packet has been discarded"
    ::= { afsNotificationsPrefix 4 }

afsNotification5 NOTIFICATION-TYPE
    OBJECTS { 
              afs5_ip-source, 
              afs5_ip-destination,
              afs5_protocol,
              afs5_in-ifc 
            }
    STATUS current
    DESCRIPTION
        "Notification of Event AFS.5

        Message: 'IP packet filtered in LOCAL-IN source $1 destination $2 protocol $3 in interface $4 action ACCEPTED'

        Parameters list:
              $1: afs5_ip-source
              $2: afs5_ip-destination
              $3: afs5_protocol
              $4: afs5_in-ifc

        an local-in ip packet has been accepted"
    ::= { afsNotificationsPrefix 5 }

afsNotification6 NOTIFICATION-TYPE
    OBJECTS { 
              afs6_ip-source, 
              afs6_ip-destination,
              afs6_protocol,
              afs6_in-ifc 
            }
    STATUS current
    DESCRIPTION
        "Notification of Event AFS.6

        Message: 'IP packet filtered in LOCAL-IN source $1 destination $2 protocol $3 in interface $4 action DISCARDED'

        Parameters list:
              $1: afs6_ip-source
              $2: afs6_ip-destination
              $3: afs6_protocol
              $4: afs6_in-ifc

        a local-in ip packet has been discarded"
    ::= { afsNotificationsPrefix 6 }

afsNotification7 NOTIFICATION-TYPE
    OBJECTS { 
              afs7_ip-source, 
              afs7_ip-destination,
              afs7_protocol,
              afs7_out-ifc 
            }
    STATUS current
    DESCRIPTION
        "Notification of Event AFS.7

        Message: 'IP packet filtered in LOCAL-OUT source $1 destination $2 protocol $3 out interface $4 action ACCEPTED'

        Parameters list:
              $1: afs7_ip-source
              $2: afs7_ip-destination
              $3: afs7_protocol
              $4: afs7_out-ifc

        a local-out ip packet has been accepted"
    ::= { afsNotificationsPrefix 7 }

afsNotification8 NOTIFICATION-TYPE
    OBJECTS { 
              afs8_ip-source, 
              afs8_ip-destination,
              afs8_protocol,
              afs8_out-ifc 
            }
    STATUS current
    DESCRIPTION
        "Notification of Event AFS.8

        Message: 'IP packet filtered in LOCAL-OUT source $1 destination $2 protocol $3 out interface $4 action DISCARDED'

        Parameters list:
              $1: afs8_ip-source
              $2: afs8_ip-destination
              $3: afs8_protocol
              $4: afs8_out-ifc

        a local-out ip packet has been discarded"
    ::= { afsNotificationsPrefix 8 }

afsNotification9 NOTIFICATION-TYPE
    OBJECTS { 
              afs9_rule, 
              afs9_acc-list,
              afs9_entry,
              afs9_ip-source,
              afs9_ip-destination,
              afs9_protocol,
              afs9_in-ifc 
            }
    STATUS current
    DESCRIPTION
        "Notification of Event AFS.9

        Message: 'NAT IN rule $1 access-list $2 entry $3 source $4 destination $5 protocol $6 in interface $7'

        Parameters list:
              $1: afs9_rule
              $2: afs9_acc-list
              $3: afs9_entry
              $4: afs9_ip-source
              $5: afs9_ip-destination
              $6: afs9_protocol
              $7: afs9_in-ifc

        an incoming IP packet has matched a nat rule"
    ::= { afsNotificationsPrefix 9 }

afsNotification10 NOTIFICATION-TYPE
    OBJECTS { 
              afs10_rule, 
              afs10_acc-list,
              afs10_entry,
              afs10_ip-source,
              afs10_ip-destination,
              afs10_protocol,
              afs10_in-ifc,
              afs10_out-ifc 
            }
    STATUS current
    DESCRIPTION
        "Notification of Event AFS.10

        Message: 'NAT OUT rule $1 access-list $2 entry $3 source $4 destination $5 protocol $6 in interface $7 out interface $8'

        Parameters list:
              $1: afs10_rule
              $2: afs10_acc-list
              $3: afs10_entry
              $4: afs10_ip-source
              $5: afs10_ip-destination
              $6: afs10_protocol
              $7: afs10_in-ifc
              $8: afs10_out-ifc

        an outgoing IP packet has matched a nat rule"
    ::= { afsNotificationsPrefix 10 }

afsNotification11 NOTIFICATION-TYPE
    OBJECTS { 
              afs11_protocol, 
              afs11_ip-src,
              afs11_ip-dst,
              afs11_natip-src,
              afs11_natip-dst 
            }
    STATUS current
    DESCRIPTION
        "Notification of Event AFS.11

        Message: 'Pkt NAT $1 packet source $2 destination $3 to source $4 destination $5'

        Parameters list:
              $1: afs11_protocol
              $2: afs11_ip-src
              $3: afs11_ip-dst
              $4: afs11_natip-src
              $5: afs11_natip-dst

        an ip packet has been natted"
    ::= { afsNotificationsPrefix 11 }

afsNotification12 NOTIFICATION-TYPE
    OBJECTS { 
              afs12_in-ifc, 
              afs12_access-list,
              afs12_entry,
              afs12_ip-source,
              afs12_ip-destination,
              afs12_protocol 
            }
    STATUS current
    DESCRIPTION
        "Notification of Event AFS.12

        Message: 'IN $1 access-list $2 entry $3 matched source $4 destination $5 protocol $6 action ACCEPTED'

        Parameters list:
              $1: afs12_in-ifc
              $2: afs12_access-list
              $3: afs12_entry
              $4: afs12_ip-source
              $5: afs12_ip-destination
              $6: afs12_protocol

        an in ip packet has been accepted by a filter rule"
    ::= { afsNotificationsPrefix 12 }

afsNotification13 NOTIFICATION-TYPE
    OBJECTS { 
              afs13_in-ifc, 
              afs13_access-list,
              afs13_entry,
              afs13_ip-source,
              afs13_ip-destination,
              afs13_protocol 
            }
    STATUS current
    DESCRIPTION
        "Notification of Event AFS.13

        Message: 'IN $1 access-list $2 entry $3 matched source $4 destination $5 protocol $6 action DISCARDED'

        Parameters list:
              $1: afs13_in-ifc
              $2: afs13_access-list
              $3: afs13_entry
              $4: afs13_ip-source
              $5: afs13_ip-destination
              $6: afs13_protocol

        an in ip packet has been discarded by a filter rule"
    ::= { afsNotificationsPrefix 13 }

afsNotification14 NOTIFICATION-TYPE
    OBJECTS { 
              afs14_out-ifc, 
              afs14_access-list,
              afs14_entry,
              afs14_ip-source,
              afs14_ip-destination,
              afs14_protocol,
              afs14_in-ifc 
            }
    STATUS current
    DESCRIPTION
        "Notification of Event AFS.14

        Message: 'OUT $1 access-list $2 entry $3 matched source $4 destination $5 protocol $6 in interface $7 action ACCEPTED'

        Parameters list:
              $1: afs14_out-ifc
              $2: afs14_access-list
              $3: afs14_entry
              $4: afs14_ip-source
              $5: afs14_ip-destination
              $6: afs14_protocol
              $7: afs14_in-ifc

        an out ip packet has been accepted by a filter rule"
    ::= { afsNotificationsPrefix 14 }

afsNotification15 NOTIFICATION-TYPE
    OBJECTS { 
              afs15_out-ifc, 
              afs15_access-list,
              afs15_entry,
              afs15_ip-source,
              afs15_ip-destination,
              afs15_protocol,
              afs15_in-ifc 
            }
    STATUS current
    DESCRIPTION
        "Notification of Event AFS.15

        Message: 'OUT $1 access-list $2 entry $3 matched source $4 destination $5 protocol $6 in interface $7 action DISCARDED'

        Parameters list:
              $1: afs15_out-ifc
              $2: afs15_access-list
              $3: afs15_entry
              $4: afs15_ip-source
              $5: afs15_ip-destination
              $6: afs15_protocol
              $7: afs15_in-ifc

        an out ip packet has been discarded by a filter rule"
    ::= { afsNotificationsPrefix 15 }

afsNotification16 NOTIFICATION-TYPE
    OBJECTS { 
              afs16_access-list, 
              afs16_entry,
              afs16_ip-source,
              afs16_ip-destination,
              afs16_protocol,
              afs16_in-ifc 
            }
    STATUS current
    DESCRIPTION
        "Notification of Event AFS.16

        Message: 'LOCAL-IN access-list $1 entry $2 matched source $3 destination $4 protocol $5 in interface $6 action ACCEPTED'

        Parameters list:
              $1: afs16_access-list
              $2: afs16_entry
              $3: afs16_ip-source
              $4: afs16_ip-destination
              $5: afs16_protocol
              $6: afs16_in-ifc

        an local-in ip packet has been accepted by a filter rule"
    ::= { afsNotificationsPrefix 16 }

afsNotification17 NOTIFICATION-TYPE
    OBJECTS { 
              afs17_access-list, 
              afs17_entry,
              afs17_ip-source,
              afs17_ip-destination,
              afs17_protocol,
              afs17_in-ifc 
            }
    STATUS current
    DESCRIPTION
        "Notification of Event AFS.17

        Message: 'LOCAL-IN access-list $1 entry $2 matched source $3 destination $4 protocol $5 in interface $6 action DISCARDED'

        Parameters list:
              $1: afs17_access-list
              $2: afs17_entry
              $3: afs17_ip-source
              $4: afs17_ip-destination
              $5: afs17_protocol
              $6: afs17_in-ifc

        a local-in ip packet has been discarded by a filter rule"
    ::= { afsNotificationsPrefix 17 }

afsNotification18 NOTIFICATION-TYPE
    OBJECTS { 
              afs18_access-list, 
              afs18_entry,
              afs18_ip-source,
              afs18_ip-destination,
              afs18_protocol,
              afs18_out-ifc 
            }
    STATUS current
    DESCRIPTION
        "Notification of Event AFS.18

        Message: 'LOCAL-OUT access-list $1 entry $2 matched source $3 destination $4 protocol $5 out interface $6 action ACCEPTED'

        Parameters list:
              $1: afs18_access-list
              $2: afs18_entry
              $3: afs18_ip-source
              $4: afs18_ip-destination
              $5: afs18_protocol
              $6: afs18_out-ifc

        a local-out ip packet has been accepted by a filter rule"
    ::= { afsNotificationsPrefix 18 }

afsNotification19 NOTIFICATION-TYPE
    OBJECTS { 
              afs19_access-list, 
              afs19_entry,
              afs19_ip-source,
              afs19_ip-destination,
              afs19_protocol,
              afs19_out-ifc 
            }
    STATUS current
    DESCRIPTION
        "Notification of Event AFS.19

        Message: 'LOCAL-OUT access-list $1 entry $2 matched source $3 destination $4 protocol $5 out interface $6 action DISCARDED'

        Parameters list:
              $1: afs19_access-list
              $2: afs19_entry
              $3: afs19_ip-source
              $4: afs19_ip-destination
              $5: afs19_protocol
              $6: afs19_out-ifc

        a local-out ip packet has been discarded by a filter rule"
    ::= { afsNotificationsPrefix 19 }

afsNotification20 NOTIFICATION-TYPE
    OBJECTS { 
              afs20_protocol, 
              afs20_state,
              afs20_status,
              afs20_org_ip_src,
              afs20_org_id_src,
              afs20_org_ip_dst,
              afs20_org_id_dst,
              afs20_rply_ip_src,
              afs20_rply_id_src,
              afs20_rply_ip_dst,
              afs20_rply_id_dst 
            }
    STATUS current
    DESCRIPTION
        "Notification of Event AFS.20

        Message: 'New cnx prot $1 $2[$3] Original(source/destination) $4:$5/$6:$7 Reply(source/destination) $8:$9/$10:$11'

        Parameters list:
              $1: afs20_protocol
              $2: afs20_state
              $3: afs20_status
              $4: afs20_org_ip_src
              $5: afs20_org_id_src
              $6: afs20_org_ip_dst
              $7: afs20_org_id_dst
              $8: afs20_rply_ip_src
              $9: afs20_rply_id_src
              $10: afs20_rply_ip_dst
              $11: afs20_rply_id_dst

        new connection event"
    ::= { afsNotificationsPrefix 20 }

afsNotification21 NOTIFICATION-TYPE
    OBJECTS { 
              afs21_protocol, 
              afs21_state,
              afs21_status,
              afs21_org_ip_src,
              afs21_org_id_src,
              afs21_org_ip_dst,
              afs21_org_id_dst,
              afs21_rply_ip_src,
              afs21_rply_id_src,
              afs21_rply_ip_dst,
              afs21_rply_id_dst 
            }
    STATUS current
    DESCRIPTION
        "Notification of Event AFS.21

        Message: 'Confirmed cnx prot $1 $2[$3] Original(source/destination) $4:$5/$6:$7 Reply(source/destination) $8:$9/$10:$11'

        Parameters list:
              $1: afs21_protocol
              $2: afs21_state
              $3: afs21_status
              $4: afs21_org_ip_src
              $5: afs21_org_id_src
              $6: afs21_org_ip_dst
              $7: afs21_org_id_dst
              $8: afs21_rply_ip_src
              $9: afs21_rply_id_src
              $10: afs21_rply_ip_dst
              $11: afs21_rply_id_dst

        confirmed connection event"
    ::= { afsNotificationsPrefix 21 }

afsNotification22 NOTIFICATION-TYPE
    OBJECTS { 
              afs22_protocol, 
              afs22_state,
              afs22_status,
              afs22_org_ip_src,
              afs22_org_id_src,
              afs22_org_ip_dst,
              afs22_org_id_dst,
              afs22_rply_ip_src,
              afs22_rply_id_src,
              afs22_rply_ip_dst,
              afs22_rply_id_dst 
            }
    STATUS current
    DESCRIPTION
        "Notification of Event AFS.22

        Message: 'Deleted cnx prot $1 $2[$3] Original(source/destination) $4:$5/$6:$7 Reply(source/destination) $8:$9/$10:$11'

        Parameters list:
              $1: afs22_protocol
              $2: afs22_state
              $3: afs22_status
              $4: afs22_org_ip_src
              $5: afs22_org_id_src
              $6: afs22_org_ip_dst
              $7: afs22_org_id_dst
              $8: afs22_rply_ip_src
              $9: afs22_rply_id_src
              $10: afs22_rply_ip_dst
              $11: afs22_rply_id_dst

        deleted connection event"
    ::= { afsNotificationsPrefix 22 }

afsNotification23 NOTIFICATION-TYPE
    OBJECTS { 
              afs23_protocol, 
              afs23_state,
              afs23_status,
              afs23_org_ip_src,
              afs23_org_id_src,
              afs23_org_ip_dst,
              afs23_org_id_dst,
              afs23_rply_ip_src,
              afs23_rply_id_src,
              afs23_rply_ip_dst,
              afs23_rply_id_dst 
            }
    STATUS current
    DESCRIPTION
        "Notification of Event AFS.23

        Message: 'FAiled Confirmation cnx prot $1 $2[$3] Original(source/destination) $4:$5/$6:$7 Reply(source/destination) $8:$9/$10:$11'

        Parameters list:
              $1: afs23_protocol
              $2: afs23_state
              $3: afs23_status
              $4: afs23_org_ip_src
              $5: afs23_org_id_src
              $6: afs23_org_ip_dst
              $7: afs23_org_id_dst
              $8: afs23_rply_ip_src
              $9: afs23_rply_id_src
              $10: afs23_rply_ip_dst
              $11: afs23_rply_id_dst

        failed confirmation connection event"
    ::= { afsNotificationsPrefix 23 }

afsNotification24 NOTIFICATION-TYPE
    OBJECTS { 
              afs24_protocol, 
              afs24_state,
              afs24_status,
              afs24_org_ip_src,
              afs24_org_id_src,
              afs24_org_ip_dst,
              afs24_org_id_dst,
              afs24_rply_ip_src,
              afs24_rply_id_src,
              afs24_rply_ip_dst,
              afs24_rply_id_dst 
            }
    STATUS current
    DESCRIPTION
        "Notification of Event AFS.24

        Message: 'New expected cnx prot $1 $2[$3] Original(source/destination) $4:$5/$6:$7 Reply(source/destination) $8:$9/$10:$11'

        Parameters list:
              $1: afs24_protocol
              $2: afs24_state
              $3: afs24_status
              $4: afs24_org_ip_src
              $5: afs24_org_id_src
              $6: afs24_org_ip_dst
              $7: afs24_org_id_dst
              $8: afs24_rply_ip_src
              $9: afs24_rply_id_src
              $10: afs24_rply_ip_dst
              $11: afs24_rply_id_dst

        new expected connection added"
    ::= { afsNotificationsPrefix 24 }

afsNotification25 NOTIFICATION-TYPE
    OBJECTS { 
              afs25_alg, 
              afs25_protocol,
              afs25_state,
              afs25_status,
              afs25_org_ip_src,
              afs25_org_id_src,
              afs25_org_ip_dst,
              afs25_org_id_dst,
              afs25_rply_ip_src,
              afs25_rply_id_src,
              afs25_rply_ip_dst,
              afs25_rply_id_dst 
            }
    STATUS current
    DESCRIPTION
        "Notification of Event AFS.25

        Message: 'ALG $1 found cnx prot $2 $3[$4] Original(source/destination) $5:$6/$7:$8 Reply(source/destination) $9:$10/$11:$12'

        Parameters list:
              $1: afs25_alg
              $2: afs25_protocol
              $3: afs25_state
              $4: afs25_status
              $5: afs25_org_ip_src
              $6: afs25_org_id_src
              $7: afs25_org_ip_dst
              $8: afs25_org_id_dst
              $9: afs25_rply_ip_src
              $10: afs25_rply_id_src
              $11: afs25_rply_ip_dst
              $12: afs25_rply_id_dst

        alg found event"
    ::= { afsNotificationsPrefix 25 }

afsNotification26 NOTIFICATION-TYPE
    OBJECTS { 
              afs26_protocol, 
              afs26_state,
              afs26_status,
              afs26_org_ip_src,
              afs26_org_id_src,
              afs26_org_ip_dst,
              afs26_org_id_dst,
              afs26_rply_ip_src,
              afs26_rply_id_src,
              afs26_rply_ip_dst,
              afs26_rply_id_dst 
            }
    STATUS current
    DESCRIPTION
        "Notification of Event AFS.26

        Message: 'Expected connection found prot $1 $2[$3] Original(source/destination) $4:$5/$6:$7 Reply(source/destination) $8:$9/$10:$11'

        Parameters list:
              $1: afs26_protocol
              $2: afs26_state
              $3: afs26_status
              $4: afs26_org_ip_src
              $5: afs26_org_id_src
              $6: afs26_org_ip_dst
              $7: afs26_org_id_dst
              $8: afs26_rply_ip_src
              $9: afs26_rply_id_src
              $10: afs26_rply_ip_dst
              $11: afs26_rply_id_dst

        connection expected found event"
    ::= { afsNotificationsPrefix 26 }

afsNotification27 NOTIFICATION-TYPE
    OBJECTS { 
              afs27_event, 
              afs27_local-ip,
              afs27_global-ip 
            }
    STATUS current
    DESCRIPTION
        "Notification of Event AFS.27

        Message: 'Nat association $1 local IP $2 global IP $3'

        Parameters list:
              $1: afs27_event
              $2: afs27_local-ip
              $3: afs27_global-ip

        a non-overlapped nat association event has happened"
    ::= { afsNotificationsPrefix 27 }

afsNotification28 NOTIFICATION-TYPE
    OBJECTS { 
              afs28_protocol, 
              afs28_state,
              afs28_status,
              afs28_org_ip_src,
              afs28_org_id_src,
              afs28_org_ip_dst,
              afs28_org_id_dst,
              afs28_rply_ip_src,
              afs28_rply_id_src,
              afs28_rply_ip_dst,
              afs28_rply_id_dst 
            }
    STATUS current
    DESCRIPTION
        "Notification of Event AFS.28

        Message: 'Matched cnx prot $1 $2[$3] Original(source/destination) $4:$5/$6:$7 Reply(source/destination) $8:$9/$10:$11'

        Parameters list:
              $1: afs28_protocol
              $2: afs28_state
              $3: afs28_status
              $4: afs28_org_ip_src
              $5: afs28_org_id_src
              $6: afs28_org_ip_dst
              $7: afs28_org_id_dst
              $8: afs28_rply_ip_src
              $9: afs28_rply_id_src
              $10: afs28_rply_ip_dst
              $11: afs28_rply_id_dst

        a connection has been matched by a packet"
    ::= { afsNotificationsPrefix 28 }

afsNotification29 NOTIFICATION-TYPE
    OBJECTS { 
              afs29_server_ip, 
              afs29_filename,
              afs29_ev,
              afs29_info 
            }
    STATUS current
    DESCRIPTION
        "Notification of Event AFS.29

        Message: 'Url filter $1-$2 event $3  info $4'

        Parameters list:
              $1: afs29_server_ip
              $2: afs29_filename
              $3: afs29_ev
              $4: afs29_info

        an url filter has matched"
    ::= { afsNotificationsPrefix 29 }

afsNotification30 NOTIFICATION-TYPE
    OBJECTS { 
              afs30_ip-source, 
              afs30_ip-destination,
              afs30_protocol,
              afs30_in-ifc 
            }
    STATUS current
    DESCRIPTION
        "Notification of Event AFS.30

        Message: 'IPv6 packet filtered in IN source $1 destination $2 protocol $3 in interface $4 action ACCEPTED'

        Parameters list:
              $1: afs30_ip-source
              $2: afs30_ip-destination
              $3: afs30_protocol
              $4: afs30_in-ifc

        an in ipv6 packet has been accepted"
    ::= { afsNotificationsPrefix 30 }

afsNotification31 NOTIFICATION-TYPE
    OBJECTS { 
              afs31_ip-source, 
              afs31_ip-destination,
              afs31_protocol,
              afs31_in-ifc 
            }
    STATUS current
    DESCRIPTION
        "Notification of Event AFS.31

        Message: 'IPv6 packet filtered in IN source $1 destination $2 protocol $3 in interface $4 action DISCARDED'

        Parameters list:
              $1: afs31_ip-source
              $2: afs31_ip-destination
              $3: afs31_protocol
              $4: afs31_in-ifc

        an in ipv6 packet has been discarded"
    ::= { afsNotificationsPrefix 31 }

afsNotification32 NOTIFICATION-TYPE
    OBJECTS { 
              afs32_ip-source, 
              afs32_ip-destination,
              afs32_protocol,
              afs32_in-ifc,
              afs32_out-ifc 
            }
    STATUS current
    DESCRIPTION
        "Notification of Event AFS.32

        Message: 'IPv6 packet filtered in OUT source $1 destination $2 protocol $3 in interface $4 out interface $5 action ACCEPTED'

        Parameters list:
              $1: afs32_ip-source
              $2: afs32_ip-destination
              $3: afs32_protocol
              $4: afs32_in-ifc
              $5: afs32_out-ifc

        an out ipv6 packet has been accepted"
    ::= { afsNotificationsPrefix 32 }

afsNotification33 NOTIFICATION-TYPE
    OBJECTS { 
              afs33_ip-source, 
              afs33_ip-destination,
              afs33_protocol,
              afs33_in-ifc,
              afs33_out-ifc 
            }
    STATUS current
    DESCRIPTION
        "Notification of Event AFS.33

        Message: 'IPv6 packet filtered in OUT source $1 destination $2 protocol $3 in interface $4 out interface $5 action DISCARDED'

        Parameters list:
              $1: afs33_ip-source
              $2: afs33_ip-destination
              $3: afs33_protocol
              $4: afs33_in-ifc
              $5: afs33_out-ifc

        an out ipv6 packet has been discarded"
    ::= { afsNotificationsPrefix 33 }

afsNotification34 NOTIFICATION-TYPE
    OBJECTS { 
              afs34_ip-source, 
              afs34_ip-destination,
              afs34_protocol,
              afs34_in-ifc 
            }
    STATUS current
    DESCRIPTION
        "Notification of Event AFS.34

        Message: 'IPv6 packet filtered in LOCAL-IN source $1 destination $2 protocol $3 in interface $4 action ACCEPTED'

        Parameters list:
              $1: afs34_ip-source
              $2: afs34_ip-destination
              $3: afs34_protocol
              $4: afs34_in-ifc

        a local-in ipv6 packet has been accepted"
    ::= { afsNotificationsPrefix 34 }

afsNotification35 NOTIFICATION-TYPE
    OBJECTS { 
              afs35_ip-source, 
              afs35_ip-destination,
              afs35_protocol,
              afs35_in-ifc 
            }
    STATUS current
    DESCRIPTION
        "Notification of Event AFS.35

        Message: 'IPv6 packet filtered in LOCAL-IN source $1 destination $2 protocol $3 in interface $4 action DISCARDED'

        Parameters list:
              $1: afs35_ip-source
              $2: afs35_ip-destination
              $3: afs35_protocol
              $4: afs35_in-ifc

        a local-in ipv6 packet has been discarded"
    ::= { afsNotificationsPrefix 35 }

afsNotification36 NOTIFICATION-TYPE
    OBJECTS { 
              afs36_ip-source, 
              afs36_ip-destination,
              afs36_protocol,
              afs36_out-ifc 
            }
    STATUS current
    DESCRIPTION
        "Notification of Event AFS.36

        Message: 'IPv6 packet filtered in LOCAL-OUT source $1 destination $2 protocol $3 out interface $4 action ACCEPTED'

        Parameters list:
              $1: afs36_ip-source
              $2: afs36_ip-destination
              $3: afs36_protocol
              $4: afs36_out-ifc

        a local-out ipv6 packet has been accepted"
    ::= { afsNotificationsPrefix 36 }

afsNotification37 NOTIFICATION-TYPE
    OBJECTS { 
              afs37_ip-source, 
              afs37_ip-destination,
              afs37_protocol,
              afs37_out-ifc 
            }
    STATUS current
    DESCRIPTION
        "Notification of Event AFS.37

        Message: 'IPv6 packet filtered in LOCAL-OUT source $1 destination $2 protocol $3 out interface $4 action DISCARDED'

        Parameters list:
              $1: afs37_ip-source
              $2: afs37_ip-destination
              $3: afs37_protocol
              $4: afs37_out-ifc

        a local-out ipv6 packet has been discarded"
    ::= { afsNotificationsPrefix 37 }

afsNotification38 NOTIFICATION-TYPE
    OBJECTS { 
              afs38_in-ifc, 
              afs38_access-list,
              afs38_entry,
              afs38_ip-source,
              afs38_ip-destination,
              afs38_protocol 
            }
    STATUS current
    DESCRIPTION
        "Notification of Event AFS.38

        Message: 'IN $1 access-list $2 entry $3 matched source $4 destination $5 protocol $6 action ACCEPTED'

        Parameters list:
              $1: afs38_in-ifc
              $2: afs38_access-list
              $3: afs38_entry
              $4: afs38_ip-source
              $5: afs38_ip-destination
              $6: afs38_protocol

        an in ipv6 packet has been accepted by a filter rule"
    ::= { afsNotificationsPrefix 38 }

afsNotification39 NOTIFICATION-TYPE
    OBJECTS { 
              afs39_in-ifc, 
              afs39_access-list,
              afs39_entry,
              afs39_ip-source,
              afs39_ip-destination,
              afs39_protocol 
            }
    STATUS current
    DESCRIPTION
        "Notification of Event AFS.39

        Message: 'IN $1 access-list $2 entry $3 matched source $4 destination $5 protocol $6 action DISCARDED'

        Parameters list:
              $1: afs39_in-ifc
              $2: afs39_access-list
              $3: afs39_entry
              $4: afs39_ip-source
              $5: afs39_ip-destination
              $6: afs39_protocol

        an in ipv6 packet has been discarded by a filter rule"
    ::= { afsNotificationsPrefix 39 }

afsNotification40 NOTIFICATION-TYPE
    OBJECTS { 
              afs40_out-ifc, 
              afs40_access-list,
              afs40_entry,
              afs40_ip-source,
              afs40_ip-destination,
              afs40_protocol,
              afs40_in-ifc 
            }
    STATUS current
    DESCRIPTION
        "Notification of Event AFS.40

        Message: 'OUT $1 access-list $2 entry $3 matched source $4 destination $5 protocol $6 in interface $7 action ACCEPTED'

        Parameters list:
              $1: afs40_out-ifc
              $2: afs40_access-list
              $3: afs40_entry
              $4: afs40_ip-source
              $5: afs40_ip-destination
              $6: afs40_protocol
              $7: afs40_in-ifc

        an out ipv6 packet has been accepted by a filter rule"
    ::= { afsNotificationsPrefix 40 }

afsNotification41 NOTIFICATION-TYPE
    OBJECTS { 
              afs41_out-ifc, 
              afs41_access-list,
              afs41_entry,
              afs41_ip-source,
              afs41_ip-destination,
              afs41_protocol,
              afs41_in-ifc 
            }
    STATUS current
    DESCRIPTION
        "Notification of Event AFS.41

        Message: 'OUT $1 access-list $2 entry $3 matched source $4 destination $5 protocol $6 in interface $7 action DISCARDED'

        Parameters list:
              $1: afs41_out-ifc
              $2: afs41_access-list
              $3: afs41_entry
              $4: afs41_ip-source
              $5: afs41_ip-destination
              $6: afs41_protocol
              $7: afs41_in-ifc

        an out ipv6 packet has been discarded by a filter rule"
    ::= { afsNotificationsPrefix 41 }

afsNotification42 NOTIFICATION-TYPE
    OBJECTS { 
              afs42_access-list, 
              afs42_entry,
              afs42_ip-source,
              afs42_ip-destination,
              afs42_protocol,
              afs42_in-ifc 
            }
    STATUS current
    DESCRIPTION
        "Notification of Event AFS.42

        Message: 'LOCAL-IN access-list $1 entry $2 matched source $3 destination $4 protocol $5 in interface $6 action ACCEPTED'

        Parameters list:
              $1: afs42_access-list
              $2: afs42_entry
              $3: afs42_ip-source
              $4: afs42_ip-destination
              $5: afs42_protocol
              $6: afs42_in-ifc

        a local-in ipv6 packet has been accepted by a filter rule"
    ::= { afsNotificationsPrefix 42 }

afsNotification43 NOTIFICATION-TYPE
    OBJECTS { 
              afs43_access-list, 
              afs43_entry,
              afs43_ip-source,
              afs43_ip-destination,
              afs43_protocol,
              afs43_in-ifc 
            }
    STATUS current
    DESCRIPTION
        "Notification of Event AFS.43

        Message: 'LOCAL-IN access-list $1 entry $2 matched source $3 destination $4 protocol $5 in interface $6 action DISCARDED'

        Parameters list:
              $1: afs43_access-list
              $2: afs43_entry
              $3: afs43_ip-source
              $4: afs43_ip-destination
              $5: afs43_protocol
              $6: afs43_in-ifc

        a local-in ipv6 packet has been discarded by a filter rule"
    ::= { afsNotificationsPrefix 43 }

afsNotification44 NOTIFICATION-TYPE
    OBJECTS { 
              afs44_access-list, 
              afs44_entry,
              afs44_ip-source,
              afs44_ip-destination,
              afs44_protocol,
              afs44_out-ifc 
            }
    STATUS current
    DESCRIPTION
        "Notification of Event AFS.44

        Message: 'LOCAL-OUT access-list $1 entry $2 matched source $3 destination $4 protocol $5 out interface $6 action ACCEPTED'

        Parameters list:
              $1: afs44_access-list
              $2: afs44_entry
              $3: afs44_ip-source
              $4: afs44_ip-destination
              $5: afs44_protocol
              $6: afs44_out-ifc

        a local-out ipv6 packet has been accepted by a filter rule"
    ::= { afsNotificationsPrefix 44 }

afsNotification45 NOTIFICATION-TYPE
    OBJECTS { 
              afs45_access-list, 
              afs45_entry,
              afs45_ip-source,
              afs45_ip-destination,
              afs45_protocol,
              afs45_out-ifc 
            }
    STATUS current
    DESCRIPTION
        "Notification of Event AFS.45

        Message: 'LOCAL-OUT access-list $1 entry $2 matched source $3 destination $4 protocol $5 out interface $6 action DISCARDED'

        Parameters list:
              $1: afs45_access-list
              $2: afs45_entry
              $3: afs45_ip-source
              $4: afs45_ip-destination
              $5: afs45_protocol
              $6: afs45_out-ifc

        a local-out ipv6 packet has been discarded by a filter rule"
    ::= { afsNotificationsPrefix 45 }

afsNotification46 NOTIFICATION-TYPE
    OBJECTS { 
              afs46_protocol, 
              afs46_state,
              afs46_status,
              afs46_org_ip_src,
              afs46_org_id_src,
              afs46_org_ip_dst,
              afs46_org_id_dst,
              afs46_rply_ip_src,
              afs46_rply_id_src,
              afs46_rply_ip_dst,
              afs46_rply_id_dst 
            }
    STATUS current
    DESCRIPTION
        "Notification of Event AFS.46

        Message: 'New cnx prot $1 $2[$3] Original(source/destination) $4:$5/$6:$7 Reply(source/destination) $8:$9/$10:$11'

        Parameters list:
              $1: afs46_protocol
              $2: afs46_state
              $3: afs46_status
              $4: afs46_org_ip_src
              $5: afs46_org_id_src
              $6: afs46_org_ip_dst
              $7: afs46_org_id_dst
              $8: afs46_rply_ip_src
              $9: afs46_rply_id_src
              $10: afs46_rply_ip_dst
              $11: afs46_rply_id_dst

        new connection event"
    ::= { afsNotificationsPrefix 46 }

afsNotification47 NOTIFICATION-TYPE
    OBJECTS { 
              afs47_protocol, 
              afs47_state,
              afs47_status,
              afs47_org_ip_src,
              afs47_org_id_src,
              afs47_org_ip_dst,
              afs47_org_id_dst,
              afs47_rply_ip_src,
              afs47_rply_id_src,
              afs47_rply_ip_dst,
              afs47_rply_id_dst 
            }
    STATUS current
    DESCRIPTION
        "Notification of Event AFS.47

        Message: 'Confirmed cnx prot $1 $2[$3] Original(source/destination) $4:$5/$6:$7 Reply(source/destination) $8:$9/$10:$11'

        Parameters list:
              $1: afs47_protocol
              $2: afs47_state
              $3: afs47_status
              $4: afs47_org_ip_src
              $5: afs47_org_id_src
              $6: afs47_org_ip_dst
              $7: afs47_org_id_dst
              $8: afs47_rply_ip_src
              $9: afs47_rply_id_src
              $10: afs47_rply_ip_dst
              $11: afs47_rply_id_dst

        confirmed connection event"
    ::= { afsNotificationsPrefix 47 }

afsNotification48 NOTIFICATION-TYPE
    OBJECTS { 
              afs48_protocol, 
              afs48_state,
              afs48_status,
              afs48_org_ip_src,
              afs48_org_id_src,
              afs48_org_ip_dst,
              afs48_org_id_dst,
              afs48_rply_ip_src,
              afs48_rply_id_src,
              afs48_rply_ip_dst,
              afs48_rply_id_dst 
            }
    STATUS current
    DESCRIPTION
        "Notification of Event AFS.48

        Message: 'Deleted cnx prot $1 $2[$3] Original(source/destination) $4:$5/$6:$7 Reply(source/destination) $8:$9/$10:$11'

        Parameters list:
              $1: afs48_protocol
              $2: afs48_state
              $3: afs48_status
              $4: afs48_org_ip_src
              $5: afs48_org_id_src
              $6: afs48_org_ip_dst
              $7: afs48_org_id_dst
              $8: afs48_rply_ip_src
              $9: afs48_rply_id_src
              $10: afs48_rply_ip_dst
              $11: afs48_rply_id_dst

        deleted connection event"
    ::= { afsNotificationsPrefix 48 }

afsNotification49 NOTIFICATION-TYPE
    OBJECTS { 
              afs49_protocol, 
              afs49_state,
              afs49_status,
              afs49_org_ip_src,
              afs49_org_id_src,
              afs49_org_ip_dst,
              afs49_org_id_dst,
              afs49_rply_ip_src,
              afs49_rply_id_src,
              afs49_rply_ip_dst,
              afs49_rply_id_dst 
            }
    STATUS current
    DESCRIPTION
        "Notification of Event AFS.49

        Message: 'FAiled Confirmation cnx prot $1 $2[$3] Original(source/destination) $4:$5/$6:$7 Reply(source/destination) $8:$9/$10:$11'

        Parameters list:
              $1: afs49_protocol
              $2: afs49_state
              $3: afs49_status
              $4: afs49_org_ip_src
              $5: afs49_org_id_src
              $6: afs49_org_ip_dst
              $7: afs49_org_id_dst
              $8: afs49_rply_ip_src
              $9: afs49_rply_id_src
              $10: afs49_rply_ip_dst
              $11: afs49_rply_id_dst

        failed confirmation connection event"
    ::= { afsNotificationsPrefix 49 }

afsNotification50 NOTIFICATION-TYPE
    OBJECTS { 
              afs50_protocol, 
              afs50_state,
              afs50_status,
              afs50_org_ip_src,
              afs50_org_id_src,
              afs50_org_ip_dst,
              afs50_org_id_dst,
              afs50_rply_ip_src,
              afs50_rply_id_src,
              afs50_rply_ip_dst,
              afs50_rply_id_dst 
            }
    STATUS current
    DESCRIPTION
        "Notification of Event AFS.50

        Message: 'New expected cnx prot $1 $2[$3] Original(source/destination) $4:$5/$6:$7 Reply(source/destination) $8:$9/$10:$11'

        Parameters list:
              $1: afs50_protocol
              $2: afs50_state
              $3: afs50_status
              $4: afs50_org_ip_src
              $5: afs50_org_id_src
              $6: afs50_org_ip_dst
              $7: afs50_org_id_dst
              $8: afs50_rply_ip_src
              $9: afs50_rply_id_src
              $10: afs50_rply_ip_dst
              $11: afs50_rply_id_dst

        new expected connection added"
    ::= { afsNotificationsPrefix 50 }

afsNotification51 NOTIFICATION-TYPE
    OBJECTS { 
              afs51_alg, 
              afs51_protocol,
              afs51_state,
              afs51_status,
              afs51_org_ip_src,
              afs51_org_id_src,
              afs51_org_ip_dst,
              afs51_org_id_dst,
              afs51_rply_ip_src,
              afs51_rply_id_src,
              afs51_rply_ip_dst,
              afs51_rply_id_dst 
            }
    STATUS current
    DESCRIPTION
        "Notification of Event AFS.51

        Message: 'ALG $1 found cnx prot $2 $3[$4] Original(source/destination) $5:$6/$7:$8 Reply(source/destination) $9:$10/$11:$12'

        Parameters list:
              $1: afs51_alg
              $2: afs51_protocol
              $3: afs51_state
              $4: afs51_status
              $5: afs51_org_ip_src
              $6: afs51_org_id_src
              $7: afs51_org_ip_dst
              $8: afs51_org_id_dst
              $9: afs51_rply_ip_src
              $10: afs51_rply_id_src
              $11: afs51_rply_ip_dst
              $12: afs51_rply_id_dst

        alg found event"
    ::= { afsNotificationsPrefix 51 }

afsNotification52 NOTIFICATION-TYPE
    OBJECTS { 
              afs52_protocol, 
              afs52_state,
              afs52_status,
              afs52_org_ip_src,
              afs52_org_id_src,
              afs52_org_ip_dst,
              afs52_org_id_dst,
              afs52_rply_ip_src,
              afs52_rply_id_src,
              afs52_rply_ip_dst,
              afs52_rply_id_dst 
            }
    STATUS current
    DESCRIPTION
        "Notification of Event AFS.52

        Message: 'Expected connection found prot $1 $2[$3] Original(source/destination) $4:$5/$6:$7 Reply(source/destination) $8:$9/$10:$11'

        Parameters list:
              $1: afs52_protocol
              $2: afs52_state
              $3: afs52_status
              $4: afs52_org_ip_src
              $5: afs52_org_id_src
              $6: afs52_org_ip_dst
              $7: afs52_org_id_dst
              $8: afs52_rply_ip_src
              $9: afs52_rply_id_src
              $10: afs52_rply_ip_dst
              $11: afs52_rply_id_dst

        connection expected found event"
    ::= { afsNotificationsPrefix 52 }

afsNotification53 NOTIFICATION-TYPE
    OBJECTS { 
              afs53_protocol, 
              afs53_state,
              afs53_status,
              afs53_org_ip_src,
              afs53_org_id_src,
              afs53_org_ip_dst,
              afs53_org_id_dst,
              afs53_rply_ip_src,
              afs53_rply_id_src,
              afs53_rply_ip_dst,
              afs53_rply_id_dst 
            }
    STATUS current
    DESCRIPTION
        "Notification of Event AFS.53

        Message: 'Matched cnx prot $1 $2[$3] Original(source/destination) $4:$5/$6:$7 Reply(source/destination) $8:$9/$10:$11'

        Parameters list:
              $1: afs53_protocol
              $2: afs53_state
              $3: afs53_status
              $4: afs53_org_ip_src
              $5: afs53_org_id_src
              $6: afs53_org_ip_dst
              $7: afs53_org_id_dst
              $8: afs53_rply_ip_src
              $9: afs53_rply_id_src
              $10: afs53_rply_ip_dst
              $11: afs53_rply_id_dst

        a connection has been matched by a packet"
    ::= { afsNotificationsPrefix 53 }

afsNotification54 NOTIFICATION-TYPE
    OBJECTS { 
              afs54_server_ip, 
              afs54_filename,
              afs54_ev,
              afs54_info 
            }
    STATUS current
    DESCRIPTION
        "Notification of Event AFS.54

        Message: 'Url filter $1-$2 event $3  info $4'

        Parameters list:
              $1: afs54_server_ip
              $2: afs54_filename
              $3: afs54_ev
              $4: afs54_info

        an url filter has matched"
    ::= { afsNotificationsPrefix 54 }

afsNotification55 NOTIFICATION-TYPE
    OBJECTS { 
              afs55_message 
            }
    STATUS current
    DESCRIPTION
        "Notification of Event AFS.55

        Message: 'Internal error: $1'

        Parameters list:
              $1: afs55_message

        an internal error has arisen"
    ::= { afsNotificationsPrefix 55 }

afsNotification56 NOTIFICATION-TYPE
    OBJECTS { 
              afs56_ip-source, 
              afs56_ip-destination,
              afs56_protocol,
              afs56_out-ifc 
            }
    STATUS current
    DESCRIPTION
        "Notification of Event AFS.56

        Message: 'Routing change detected src $1 dst $2 prt $3 out-ifc $4 -> DISCARDED'

        Parameters list:
              $1: afs56_ip-source
              $2: afs56_ip-destination
              $3: afs56_protocol
              $4: afs56_out-ifc

        A routing change has been detected. The session will be dropped."
    ::= { afsNotificationsPrefix 56 }

afsNotification57 NOTIFICATION-TYPE
    OBJECTS { 
              afs57_ip-source, 
              afs57_ip-destination,
              afs57_protocol 
            }
    STATUS current
    DESCRIPTION
        "Notification of Event AFS.57

        Message: 'Invalid packet detected src $1 dst $2 prt $3 -> DISCARTED'

        Parameters list:
              $1: afs57_ip-source
              $2: afs57_ip-destination
              $3: afs57_protocol

        An invalid packet has been detected. The session will be dropped."
    ::= { afsNotificationsPrefix 57 }


END
