--
-- EXTREME-SUMMIT-WM-MIB.my
-- MIB generated by MG-SOFT Visual MIB Builder Version 4.0 Build 349
-- Friday, October 28, 2005 at 15:11:28
--

	EXTREME-SUMMIT-WM-MIB DEFINITIONS ::= BEGIN
 
		IMPORTS
			summitWMMgmt, summitWMModules			
				FROM EXTREME-SUMMIT-WM-SMI			
			WEPKeytype			
				FROM IEEE802dot11-MIB			
			ifIndex, InterfaceIndex			
				FROM IF-MIB			
			OBJECT-GROUP, MODULE-COMPLIANCE, NOTIFICATION-GROUP			
				FROM SNMPv2-CONF			
			TimeTicks, IpAddress, Integer32, Counter64, OBJECT-TYPE, 
			MODULE-IDENTITY, NOTIFICATION-TYPE			
				FROM SNMPv2-SMI			
			DisplayString, TruthValue, RowStatus, MacAddress, TEXTUAL-CONVENTION			
				FROM SNMPv2-TC;
	
	
--  September 01, 2005 at 02:37 GMT
-- September 01, 2005 at 02:37 GMT
		-- 1.3.6.1.4.1.1916.5.5.2
		summitWMMIB MODULE-IDENTITY 
			LAST-UPDATED "200510280311Z"		-- October 28, 2005 at 03:11 GMT
			ORGANIZATION 
				"Extreme Networks, Inc."
			CONTACT-INFO 
				"www.extremenetworks.com"
			DESCRIPTION 
				"Summit WM MIB definition"
			REVISION "200510280311Z"		-- October 28, 2005 at 03:11 GMT
			DESCRIPTION 
				"Initial revision."
			::= { summitWMModules 2 }

		
	
	
--
-- Textual conventions
--
	
		LogEventSeverity ::= TEXTUAL-CONVENTION
			STATUS current
			DESCRIPTION 
				"The log event severities used in the access controller."
			SYNTAX INTEGER
				{
				critical(1),
				major(2),
				minor(3),
				information(4),
				trace(5)
				}

	
--
-- Node definitions
--
	
		-- 1.3.6.1.4.1.1916.5.3.2
		summitWM OBJECT IDENTIFIER ::= { summitWMMgmt 2 }

		
		-- 1.3.6.1.4.1.1916.5.3.2.1
		systemObjects OBJECT IDENTIFIER ::= { summitWM 1 }

		
		-- 1.3.6.1.4.1.1916.5.3.2.1.1
		sysSoftwareVersion OBJECT-TYPE
			SYNTAX DisplayString
			MAX-ACCESS read-only
			STATUS current
			DESCRIPTION
				"System software version."
			::= { systemObjects 1 }

		
		-- 1.3.6.1.4.1.1916.5.3.2.1.2
		sysLogLevel OBJECT-TYPE
			SYNTAX LogEventSeverity
			MAX-ACCESS read-write
			STATUS current
			DESCRIPTION
				"Sets the level of events which are written to the system
				log."
			::= { systemObjects 2 }

		
		-- 1.3.6.1.4.1.1916.5.3.2.1.3
		sysSerialNo OBJECT-TYPE
			SYNTAX OCTET STRING (SIZE (0..64))
			MAX-ACCESS read-only
			STATUS current
			DESCRIPTION
				"System serial number."
			::= { systemObjects 3 }

		
		-- 1.3.6.1.4.1.1916.5.3.2.1.4
		sysLogSupport OBJECT IDENTIFIER ::= { systemObjects 4 }

		
		-- 1.3.6.1.4.1.1916.5.3.2.1.4.1
		summitWMAppLogFacility OBJECT-TYPE
			SYNTAX INTEGER
				{
				local0(0),
				local1(1),
				local2(2),
				local3(3),
				local4(4),
				local5(5),
				local6(6)
				}
			MAX-ACCESS read-write
			STATUS current
			DESCRIPTION
				"The application log facility level for syslog."
			::= { sysLogSupport 1 }

		
		-- 1.3.6.1.4.1.1916.5.3.2.1.4.2
		serviceLogFacility OBJECT-TYPE
			SYNTAX INTEGER
				{
				local0(0),
				local1(1),
				local2(2),
				local3(3),
				local4(4),
				local5(5),
				local6(6)
				}
			MAX-ACCESS read-write
			STATUS current
			DESCRIPTION
				"The service log facility level for syslog."
			::= { sysLogSupport 2 }

		
		-- 1.3.6.1.4.1.1916.5.3.2.1.4.3
		includeAllServiceMessages OBJECT-TYPE
			SYNTAX TruthValue
			MAX-ACCESS read-write
			STATUS current
			DESCRIPTION
				"Indicates if DHCP messages should also be forwarded to syslog."
			::= { sysLogSupport 3 }

		
		-- 1.3.6.1.4.1.1916.5.3.2.1.4.4
		sysLogServersTable OBJECT-TYPE
			SYNTAX SEQUENCE OF SysLogServersEntry
			MAX-ACCESS not-accessible
			STATUS current
			DESCRIPTION
				"Table of syslog servers to forward logging messages."
			::= { sysLogSupport 4 }

		
		-- 1.3.6.1.4.1.1916.5.3.2.1.4.4.1
		sysLogServersEntry OBJECT-TYPE
			SYNTAX SysLogServersEntry
			MAX-ACCESS not-accessible
			STATUS current
			DESCRIPTION
				"Configuration information for an external syslog server."
			INDEX { sysLogServerIndex }
			::= { sysLogServersTable 1 }

		
		SysLogServersEntry ::=
			SEQUENCE { 
				sysLogServerIndex
					Integer32,
				sysLogServerEnabled
					TruthValue,
				sysLogServerIP
					IpAddress,
				sysLogServerPort
					Integer32,
				sysLogServerRowStatus
					RowStatus
			 }

		-- 1.3.6.1.4.1.1916.5.3.2.1.4.4.1.1
		sysLogServerIndex OBJECT-TYPE
			SYNTAX Integer32 (1..2147483647)
			MAX-ACCESS read-write
			STATUS current
			DESCRIPTION
				"Table index for the syslog server."
			::= { sysLogServersEntry 1 }

		
		-- 1.3.6.1.4.1.1916.5.3.2.1.4.4.1.2
		sysLogServerEnabled OBJECT-TYPE
			SYNTAX TruthValue
			MAX-ACCESS read-write
			STATUS current
			DESCRIPTION
				"Indicates if messages are to be sent to the syslog server."
			::= { sysLogServersEntry 2 }

		
		-- 1.3.6.1.4.1.1916.5.3.2.1.4.4.1.3
		sysLogServerIP OBJECT-TYPE
			SYNTAX IpAddress
			MAX-ACCESS read-write
			STATUS current
			DESCRIPTION
				"syslog server IP address."
			::= { sysLogServersEntry 3 }

		
		-- 1.3.6.1.4.1.1916.5.3.2.1.4.4.1.4
		sysLogServerPort OBJECT-TYPE
			SYNTAX Integer32
			MAX-ACCESS read-write
			STATUS current
			DESCRIPTION
				"syslog server port number."
			::= { sysLogServersEntry 4 }

		
		-- 1.3.6.1.4.1.1916.5.3.2.1.4.4.1.5
		sysLogServerRowStatus OBJECT-TYPE
			SYNTAX RowStatus
			MAX-ACCESS read-write
			STATUS current
			DESCRIPTION
				"RowStatus for operating on syslogServersTable."
			::= { sysLogServersEntry 5 }

		
		-- 1.3.6.1.4.1.1916.5.3.2.3
		mgmtPortObjects OBJECT IDENTIFIER ::= { summitWM 3 }

		
		-- 1.3.6.1.4.1.1916.5.3.2.3.1
		mgmtPortIfIndex OBJECT-TYPE
			SYNTAX Integer32
			MAX-ACCESS read-only
			STATUS current
			DESCRIPTION
				"ifIndex of the management port."
			::= { mgmtPortObjects 1 }

		
		-- 1.3.6.1.4.1.1916.5.3.2.3.2
		mgmtPortHostname OBJECT-TYPE
			SYNTAX DisplayString
			MAX-ACCESS read-write
			STATUS current
			DESCRIPTION
				"Hostname of the management port."
			::= { mgmtPortObjects 2 }

		
		-- 1.3.6.1.4.1.1916.5.3.2.3.3
		mgmtPortPrimaryDNS OBJECT-TYPE
			SYNTAX IpAddress
			MAX-ACCESS read-write
			STATUS current
			DESCRIPTION
				"Primary domain server for the management port."
			::= { mgmtPortObjects 3 }

		
		-- 1.3.6.1.4.1.1916.5.3.2.3.4
		mgmtPortSecondaryDNS OBJECT-TYPE
			SYNTAX IpAddress
			MAX-ACCESS read-write
			STATUS current
			DESCRIPTION
				"Secondary domain server for the management port."
			::= { mgmtPortObjects 4 }

		
		-- 1.3.6.1.4.1.1916.5.3.2.3.5
		mgmtPortDomain OBJECT-TYPE
			SYNTAX DisplayString
			MAX-ACCESS read-write
			STATUS current
			DESCRIPTION
				"Domain of the management port."
			::= { mgmtPortObjects 5 }

		
		-- 1.3.6.1.4.1.1916.5.3.2.4
		physicalPortObjects OBJECT IDENTIFIER ::= { summitWM 4 }

		
		-- 1.3.6.1.4.1.1916.5.3.2.4.1
		physicalPortCount OBJECT-TYPE
			SYNTAX Integer32
			MAX-ACCESS read-only
			STATUS current
			DESCRIPTION
				"Number of rows in routerPortsTable."
			::= { physicalPortObjects 1 }

		
		-- 1.3.6.1.4.1.1916.5.3.2.4.2
		physicalPortsTable OBJECT-TYPE
			SYNTAX SEQUENCE OF PhysicalPortsEntry
			MAX-ACCESS not-accessible
			STATUS current
			DESCRIPTION
				"Table of router ports on the controller."
			::= { physicalPortObjects 2 }

		
		-- 1.3.6.1.4.1.1916.5.3.2.4.2.1
		physicalPortsEntry OBJECT-TYPE
			SYNTAX PhysicalPortsEntry
			MAX-ACCESS not-accessible
			STATUS current
			DESCRIPTION
				"An entry in routerPortsTable."
			INDEX { ifIndex }
			::= { physicalPortsTable 1 }

		
		PhysicalPortsEntry ::=
			SEQUENCE { 
				portMgmtTrafficEnable
					TruthValue,
				portDuplexMode
					INTEGER,
				portFunction
					INTEGER
			 }

		-- 1.3.6.1.4.1.1916.5.3.2.4.2.1.1
		portMgmtTrafficEnable OBJECT-TYPE
			SYNTAX TruthValue
			MAX-ACCESS read-write
			STATUS current
			DESCRIPTION
				"Determines whether controller management 
				network traffic is allowed over this interface."
			::= { physicalPortsEntry 1 }

		
		-- 1.3.6.1.4.1.1916.5.3.2.4.2.1.2
		portDuplexMode OBJECT-TYPE
			SYNTAX INTEGER
				{
				full(1),
				half(2),
				auto(3)
				}
			MAX-ACCESS read-write
			STATUS current
			DESCRIPTION
				"Duplex mode for the esa ports."
			::= { physicalPortsEntry 2 }

		
		-- 1.3.6.1.4.1.1916.5.3.2.4.2.1.3
		portFunction OBJECT-TYPE
			SYNTAX INTEGER
				{
				router(1),
				host(2),
				thirdPartyAP(3)
				}
			MAX-ACCESS read-write
			STATUS current
			DESCRIPTION
				"Specifies the behavior of the WM physical ports."
			::= { physicalPortsEntry 3 }

		
		-- 1.3.6.1.4.1.1916.5.3.2.5
		adManagerObjects OBJECT IDENTIFIER ::= { summitWM 5 }

		
		-- 1.3.6.1.4.1.1916.5.3.2.5.1
		adRole OBJECT-TYPE
			SYNTAX INTEGER
				{
				none(1),
				adMgr(2),
				adAgent(3)
				}
			MAX-ACCESS read-write
			STATUS current
			DESCRIPTION
				"Specifies the role of this WM in inter-WM mobility.  
				None indicates that mobile units cannot roam to or 
				from this WM.  In any WM cluster, only one WM should
				be specified as adMgr, all others should be have 
				adRole = adAgent ."
			::= { adManagerObjects 1 }

		
		-- 1.3.6.1.4.1.1916.5.3.2.5.2
		adIfIndex OBJECT-TYPE
			SYNTAX Integer32
			MAX-ACCESS read-write
			STATUS current
			DESCRIPTION
				"ifIndex of the physical port where inter-WM tunnels terminate."
			::= { adManagerObjects 2 }

		
		-- 1.3.6.1.4.1.1916.5.3.2.5.3
		adHeartBeatInterval OBJECT-TYPE
			SYNTAX Integer32
			MAX-ACCESS read-write
			STATUS current
			DESCRIPTION
				"The time interval between inter-WM polling messages."
			::= { adManagerObjects 3 }

		
		-- 1.3.6.1.4.1.1916.5.3.2.6
		ntpObjects OBJECT IDENTIFIER ::= { summitWM 6 }

		
		-- 1.3.6.1.4.1.1916.5.3.2.6.1
		ntpEnabled OBJECT-TYPE
			SYNTAX TruthValue
			MAX-ACCESS read-write
			STATUS current
			DESCRIPTION
				"Enable or disables support for the Network Time Protocol (NTP)."
			::= { ntpObjects 1 }

		
		-- 1.3.6.1.4.1.1916.5.3.2.6.2
		ntpTimezone OBJECT-TYPE
			SYNTAX DisplayString
			MAX-ACCESS read-write
			STATUS current
			DESCRIPTION
				"Specifies the time zone where this WM resides."
			::= { ntpObjects 2 }

		
		-- 1.3.6.1.4.1.1916.5.3.2.6.3
		ntpTimeServer1 OBJECT-TYPE
			SYNTAX DisplayString
			MAX-ACCESS read-write
			STATUS current
			DESCRIPTION
				"Primary NTP server."
			::= { ntpObjects 3 }

		
		-- 1.3.6.1.4.1.1916.5.3.2.6.4
		ntpTimeServer2 OBJECT-TYPE
			SYNTAX DisplayString
			MAX-ACCESS read-write
			STATUS current
			DESCRIPTION
				"Secondary NTP server."
			::= { ntpObjects 4 }

		
		-- 1.3.6.1.4.1.1916.5.3.2.6.5
		ntpTimeServer3 OBJECT-TYPE
			SYNTAX DisplayString
			MAX-ACCESS read-write
			STATUS current
			DESCRIPTION
				"Tertiary NTP server."
			::= { ntpObjects 5 }

		
		-- 1.3.6.1.4.1.1916.5.3.2.7
		controllerStats OBJECT IDENTIFIER ::= { summitWM 7 }

		
		-- 1.3.6.1.4.1.1916.5.3.2.7.6
		tunnelCount OBJECT-TYPE
			SYNTAX Integer32
			MAX-ACCESS read-only
			STATUS current
			DESCRIPTION
				"Number of connections to other summitWM controllers."
			::= { controllerStats 6 }

		
		-- 1.3.6.1.4.1.1916.5.3.2.7.7
		tunnelStatsTable OBJECT-TYPE
			SYNTAX SEQUENCE OF TunnelStatsEntry
			MAX-ACCESS not-accessible
			STATUS current
			DESCRIPTION
				"tunnelStatsTable contains a list of the IP tunnels connected 
				to this WM for use in inter-WM mobility."
			::= { controllerStats 7 }

		
		-- 1.3.6.1.4.1.1916.5.3.2.7.7.1
		tunnelStatsEntry OBJECT-TYPE
			SYNTAX TunnelStatsEntry
			MAX-ACCESS not-accessible
			STATUS current
			DESCRIPTION
				"Statistics for a mobility tunnel."
			INDEX { tunnelStartIP, tunnelEndIP }
			::= { tunnelStatsTable 1 }

		
		TunnelStatsEntry ::=
			SEQUENCE { 
				tunnelStartIP
					IpAddress,
				tunnelStartWM
					OCTET STRING,
				tunnelEndIP
					IpAddress,
				tunnelEndWM
					OCTET STRING,
				tunnelStatus
					INTEGER
			 }

		-- 1.3.6.1.4.1.1916.5.3.2.7.7.1.1
		tunnelStartIP OBJECT-TYPE
			SYNTAX IpAddress
			MAX-ACCESS read-write
			STATUS current
			DESCRIPTION
				"IP address for the start of the tunnel."
			::= { tunnelStatsEntry 1 }

		
		-- 1.3.6.1.4.1.1916.5.3.2.7.7.1.2
		tunnelStartWM OBJECT-TYPE
			SYNTAX OCTET STRING
			MAX-ACCESS read-write
			STATUS current
			DESCRIPTION
				"Name of the access controller for the start of the tunnel."
			::= { tunnelStatsEntry 2 }

		
		-- 1.3.6.1.4.1.1916.5.3.2.7.7.1.3
		tunnelEndIP OBJECT-TYPE
			SYNTAX IpAddress
			MAX-ACCESS read-write
			STATUS current
			DESCRIPTION
				"IP address for the end of the tunnel."
			::= { tunnelStatsEntry 3 }

		
		-- 1.3.6.1.4.1.1916.5.3.2.7.7.1.4
		tunnelEndWM OBJECT-TYPE
			SYNTAX OCTET STRING
			MAX-ACCESS read-write
			STATUS current
			DESCRIPTION
				"Name of the access controller for the end of the tunnel."
			::= { tunnelStatsEntry 4 }

		
		-- 1.3.6.1.4.1.1916.5.3.2.7.7.1.5
		tunnelStatus OBJECT-TYPE
			SYNTAX INTEGER
				{
				disconnected(1),
				connected(2)
				}
			MAX-ACCESS read-write
			STATUS current
			DESCRIPTION
				"Indicates if the mobility tunnel is up or down."
			::= { tunnelStatsEntry 5 }

		
		-- 1.3.6.1.4.1.1916.5.3.3
		accessDomains OBJECT IDENTIFIER ::= { summitWMMgmt 3 }

		
		-- 1.3.6.1.4.1.1916.5.3.3.1
		wmadConfigObjects OBJECT IDENTIFIER ::= { accessDomains 1 }

		
		-- 1.3.6.1.4.1.1916.5.3.3.1.1
		wmadCount OBJECT-TYPE
			SYNTAX Integer32
			MAX-ACCESS read-only
			STATUS current
			DESCRIPTION
				"Number of WMADs defined in wmadConfigTable."
			::= { wmadConfigObjects 1 }

		
		-- 1.3.6.1.4.1.1916.5.3.3.1.2
		wmadConfigTable OBJECT-TYPE
			SYNTAX SEQUENCE OF WmadConfigEntry
			MAX-ACCESS not-accessible
			STATUS current
			DESCRIPTION
				"Contains definitions of the Access Domain Segments 
				defined on this SummitWM."
			::= { wmadConfigObjects 2 }

		
		-- 1.3.6.1.4.1.1916.5.3.3.1.2.1
		wmadConfigEntry OBJECT-TYPE
			SYNTAX WmadConfigEntry
			MAX-ACCESS not-accessible
			STATUS current
			DESCRIPTION
				"Configuration elements for a specific Access Domain Segment."
			INDEX { wmadIfIndex }
			::= { wmadConfigTable 1 }

		
		WmadConfigEntry ::=
			SEQUENCE { 
				wmadDescription
					DisplayString,
				wmadAssignmentMode
					INTEGER,
				wmadMUSessionTimeout
					Integer32,
				wmadAllowMulticast
					TruthValue,
				wmadSSID
					DisplayString,
				wmadDomain
					DisplayString,
				wmadDNSServers
					DisplayString,
				wmadWINSServers
					DisplayString,
				wmadAuthModel
					INTEGER,
				wmadParentIfIndex
					Integer32,
				wmadMgmtTrafficEnable
					TruthValue,
				wmadUseDHCPRelay
					TruthValue,
				wmad3rdPartyAP
					TruthValue,
				wmadStatus
					RowStatus
			 }

		-- 1.3.6.1.4.1.1916.5.3.3.1.2.1.1
		wmadDescription OBJECT-TYPE
			SYNTAX DisplayString
			MAX-ACCESS read-write
			STATUS current
			DESCRIPTION
				"Textual description of the WMAD."
			::= { wmadConfigEntry 1 }

		
		-- 1.3.6.1.4.1.1916.5.3.3.1.2.1.2
		wmadAssignmentMode OBJECT-TYPE
			SYNTAX INTEGER
				{
				ssid(1),
				aaa(2)
				}
			MAX-ACCESS read-write
			STATUS current
			DESCRIPTION
				"Determines the method by which mobile units are assigned an 
				address within this WMAD.  If wmadAssignmentMode = ssid, any 
				client with an SSID matching the WMAD will be assigned an 
				address from this WMAD.  If wmadAssignmentMode == aaa, then
				address assignment is not completed until after the user is
				authenticated."
			::= { wmadConfigEntry 2 }

		
		-- 1.3.6.1.4.1.1916.5.3.3.1.2.1.3
		wmadMUSessionTimeout OBJECT-TYPE
			SYNTAX Integer32
			MAX-ACCESS read-write
			STATUS current
			DESCRIPTION
				"Client session idle time out, in seconds."
			::= { wmadConfigEntry 3 }

		
		-- 1.3.6.1.4.1.1916.5.3.3.1.2.1.4
		wmadAllowMulticast OBJECT-TYPE
			SYNTAX TruthValue
			MAX-ACCESS read-write
			STATUS current
			DESCRIPTION
				"When true, allows IP multicast packets to be broadcast 
				to the clients on this WMAD."
			::= { wmadConfigEntry 4 }

		
		-- 1.3.6.1.4.1.1916.5.3.3.1.2.1.5
		wmadSSID OBJECT-TYPE
			SYNTAX DisplayString
			MAX-ACCESS read-write
			STATUS current
			DESCRIPTION
				"Service Set Identifier (i.e. Network Name) that will be 
				configured on the Altitudes associated with this WMAD."
			::= { wmadConfigEntry 5 }

		
		-- 1.3.6.1.4.1.1916.5.3.3.1.2.1.6
		wmadDomain OBJECT-TYPE
			SYNTAX DisplayString
			MAX-ACCESS read-write
			STATUS current
			DESCRIPTION
				"Domain name to be supplied to the wireless clients if internal DHCP address assignment."
			::= { wmadConfigEntry 6 }

		
		-- 1.3.6.1.4.1.1916.5.3.3.1.2.1.7
		wmadDNSServers OBJECT-TYPE
			SYNTAX DisplayString
			MAX-ACCESS read-write
			STATUS current
			DESCRIPTION
				"List of DNSs to be supplied to the wireless clients if internal DHCP address assignment."
			::= { wmadConfigEntry 7 }

		
		-- 1.3.6.1.4.1.1916.5.3.3.1.2.1.8
		wmadWINSServers OBJECT-TYPE
			SYNTAX DisplayString
			MAX-ACCESS read-write
			STATUS current
			DESCRIPTION
				"List of WINSs to be supplied to the wireless clients if internal DHCP address assignment."
			::= { wmadConfigEntry 8 }

		
		-- 1.3.6.1.4.1.1916.5.3.3.1.2.1.9
		wmadAuthModel OBJECT-TYPE
			SYNTAX INTEGER
				{
				none(1),
				captivePortal(2),
				dot1X(3)
				}
			MAX-ACCESS read-write
			STATUS current
			DESCRIPTION
				"wmadAuthModel specifies the authentication method used 
				for clients in the WMAD.  None indicates that the WMAD is
				open, and no authentication is required.
				
				wmadAuthModel=captivePortal may only be specified for 
				a WMAD with wmadAssignmentMode=ssid.  Likewise, 
				wmadAuthModel=dot1X may only be specified for a WMAD with
				wmadAssignmentMode=aaa."
			::= { wmadConfigEntry 9 }

		
		-- 1.3.6.1.4.1.1916.5.3.3.1.2.1.10
		wmadParentIfIndex OBJECT-TYPE
			SYNTAX Integer32
			MAX-ACCESS read-write
			STATUS current
			DESCRIPTION
				"Specifies the ifIndex of the parent WMAD, if this WMAD
				is a child.  This only applies for a WMAD where 
				wmadAssignmentMode=aaa.
				
				If this is a top level WMAD, wmadParentIfIndex will return 
				null or 0."
			::= { wmadConfigEntry 10 }

		
		-- 1.3.6.1.4.1.1916.5.3.3.1.2.1.11
		wmadMgmtTrafficEnable OBJECT-TYPE
			SYNTAX TruthValue
			MAX-ACCESS read-write
			STATUS current
			DESCRIPTION
				"Specifies whether clients in the WMAD have access 
				to WM management elements."
			::= { wmadConfigEntry 11 }

		
		-- 1.3.6.1.4.1.1916.5.3.3.1.2.1.12
		wmadUseDHCPRelay OBJECT-TYPE
			SYNTAX TruthValue
			MAX-ACCESS read-write
			STATUS current
			DESCRIPTION
				"When true, specifies that DHCP Relay is enabled on the WMAD."
			::= { wmadConfigEntry 12 }

		
		-- 1.3.6.1.4.1.1916.5.3.3.1.2.1.13
		wmad3rdPartyAP OBJECT-TYPE
			SYNTAX TruthValue
			MAX-ACCESS read-write
			STATUS current
			DESCRIPTION
				"When true, specifies that the WMAD contains 3rd party 
				access points.  Only one such WMAD may be defined for
				a summitWM."
			::= { wmadConfigEntry 13 }

		
		-- 1.3.6.1.4.1.1916.5.3.3.1.2.1.14
		wmadStatus OBJECT-TYPE
			SYNTAX RowStatus
			MAX-ACCESS read-write
			STATUS current
			DESCRIPTION
				"RowStatus variable for performing row operations on 
				wmadConfigTable."
			::= { wmadConfigEntry 14 }

		
		-- 1.3.6.1.4.1.1916.5.3.3.1.3
		wmadDHCPRangeTable OBJECT-TYPE
			SYNTAX SEQUENCE OF WmadDHCPRangeEntry
			MAX-ACCESS not-accessible
			STATUS current
			DESCRIPTION
				"wmadDHCPRangeTable contains the IP address ranges that DHCP
				will serve to clients associated with this WMAD."
			::= { wmadConfigObjects 3 }

		
		-- 1.3.6.1.4.1.1916.5.3.3.1.3.1
		wmadDHCPRangeEntry OBJECT-TYPE
			SYNTAX WmadDHCPRangeEntry
			MAX-ACCESS not-accessible
			STATUS current
			DESCRIPTION
				"Configuration information for a DHCP range."
			INDEX { ifIndex, wmadDHCPRangeIndex }
			::= { wmadDHCPRangeTable 1 }

		
		WmadDHCPRangeEntry ::=
			SEQUENCE { 
				wmadDHCPRangeIndex
					Integer32,
				wmadDHCPRangeStart
					IpAddress,
				wmadDHCPRangeEnd
					IpAddress,
				wmadDHCPRangeType
					INTEGER,
				wmadDHCPRangeStatus
					RowStatus
			 }

		-- 1.3.6.1.4.1.1916.5.3.3.1.3.1.1
		wmadDHCPRangeIndex OBJECT-TYPE
			SYNTAX Integer32 (1..2147483647)
			MAX-ACCESS read-write
			STATUS current
			DESCRIPTION
				"Index for the DHCP row element."
			::= { wmadDHCPRangeEntry 1 }

		
		-- 1.3.6.1.4.1.1916.5.3.3.1.3.1.2
		wmadDHCPRangeStart OBJECT-TYPE
			SYNTAX IpAddress
			MAX-ACCESS read-write
			STATUS current
			DESCRIPTION
				"First IP address in the range."
			::= { wmadDHCPRangeEntry 2 }

		
		-- 1.3.6.1.4.1.1916.5.3.3.1.3.1.3
		wmadDHCPRangeEnd OBJECT-TYPE
			SYNTAX IpAddress
			MAX-ACCESS read-write
			STATUS current
			DESCRIPTION
				"Last IP address in the range."
			::= { wmadDHCPRangeEntry 3 }

		
		-- 1.3.6.1.4.1.1916.5.3.3.1.3.1.4
		wmadDHCPRangeType OBJECT-TYPE
			SYNTAX INTEGER
				{
				inclusion(1),
				exclusion(2)
				}
			MAX-ACCESS read-write
			STATUS current
			DESCRIPTION
				"Determines whether addresses in the specified range will 
				be included, or excluded by the DHCP server."
			::= { wmadDHCPRangeEntry 4 }

		
		-- 1.3.6.1.4.1.1916.5.3.3.1.3.1.5
		wmadDHCPRangeStatus OBJECT-TYPE
			SYNTAX RowStatus
			MAX-ACCESS read-write
			STATUS current
			DESCRIPTION
				"Row status variable for row operations on the wmadDHCPRangeTable"
			::= { wmadDHCPRangeEntry 5 }

		
		-- 1.3.6.1.4.1.1916.5.3.3.1.4
		wmadCaptivePortalTable OBJECT-TYPE
			SYNTAX SEQUENCE OF WmadCaptivePortalEntry
			MAX-ACCESS not-accessible
			STATUS current
			DESCRIPTION
				"Details of the Captive Portal login page for 
				WMADs that have wmadAssignment=ssid and 
				wmadAuthModel=captivePortal."
			::= { wmadConfigObjects 4 }

		
		-- 1.3.6.1.4.1.1916.5.3.3.1.4.1
		wmadCaptivePortalEntry OBJECT-TYPE
			SYNTAX WmadCaptivePortalEntry
			MAX-ACCESS not-accessible
			STATUS current
			DESCRIPTION
				"Captive Portal Information for the WMAD."
			INDEX { ifIndex }
			::= { wmadCaptivePortalTable 1 }

		
		WmadCaptivePortalEntry ::=
			SEQUENCE { 
				cpURL
					DisplayString,
				cpLoginLabel
					DisplayString,
				cpPasswordLabel
					DisplayString,
				cpHeaderURL
					DisplayString,
				cpFooterURL
					DisplayString,
				cpMessage
					DisplayString
			 }

		-- 1.3.6.1.4.1.1916.5.3.3.1.4.1.1
		cpURL OBJECT-TYPE
			SYNTAX DisplayString
			MAX-ACCESS read-write
			STATUS current
			DESCRIPTION
				"Redirect URL of the Captive Portal login page."
			::= { wmadCaptivePortalEntry 1 }

		
		-- 1.3.6.1.4.1.1916.5.3.3.1.4.1.2
		cpLoginLabel OBJECT-TYPE
			SYNTAX DisplayString
			MAX-ACCESS read-write
			STATUS current
			DESCRIPTION
				"Label that appears in front of the login field
				on the Captive Portal login page."
			::= { wmadCaptivePortalEntry 2 }

		
		-- 1.3.6.1.4.1.1916.5.3.3.1.4.1.3
		cpPasswordLabel OBJECT-TYPE
			SYNTAX DisplayString
			MAX-ACCESS read-write
			STATUS current
			DESCRIPTION
				"Label that appears in front of the password field
				on the Captive Portal login page."
			::= { wmadCaptivePortalEntry 3 }

		
		-- 1.3.6.1.4.1.1916.5.3.3.1.4.1.4
		cpHeaderURL OBJECT-TYPE
			SYNTAX DisplayString
			MAX-ACCESS read-write
			STATUS current
			DESCRIPTION
				"URL of the Captive Portal header."
			::= { wmadCaptivePortalEntry 4 }

		
		-- 1.3.6.1.4.1.1916.5.3.3.1.4.1.5
		cpFooterURL OBJECT-TYPE
			SYNTAX DisplayString
			MAX-ACCESS read-write
			STATUS current
			DESCRIPTION
				"URL of the Captive Portal footer."
			::= { wmadCaptivePortalEntry 5 }

		
		-- 1.3.6.1.4.1.1916.5.3.3.1.4.1.6
		cpMessage OBJECT-TYPE
			SYNTAX DisplayString
			MAX-ACCESS read-write
			STATUS current
			DESCRIPTION
				"A welcome message, or set of instructions that is to 
				appear on the Captive Portal login page."
			::= { wmadCaptivePortalEntry 6 }

		
		-- 1.3.6.1.4.1.1916.5.3.3.1.5
		wmadRadiusServerTable OBJECT-TYPE
			SYNTAX SEQUENCE OF WmadRadiusServerEntry
			MAX-ACCESS not-accessible
			STATUS current
			DESCRIPTION
				"List of RADIUS servers to be utilized for authentication in the WMAD."
			::= { wmadConfigObjects 5 }

		
		-- 1.3.6.1.4.1.1916.5.3.3.1.5.1
		wmadRadiusServerEntry OBJECT-TYPE
			SYNTAX WmadRadiusServerEntry
			MAX-ACCESS not-accessible
			STATUS current
			DESCRIPTION
				"Configuration information for a RADIUS server."
			INDEX { ifIndex, wmadRadiusServerIP }
			::= { wmadRadiusServerTable 1 }

		
		WmadRadiusServerEntry ::=
			SEQUENCE { 
				wmadRadiusServerIP
					IpAddress,
				wmadRadiusServerPort
					Integer32,
				wmadRadiusServerRetries
					Integer32,
				wmadRadiusServerTimeout
					Integer32,
				wmadRadiusServerSharedSecret
					DisplayString,
				wmadRadiusServerNASIdentifier
					DisplayString,
				wmadRadiusServerAuthType
					INTEGER,
				wmadRadiusServerRowStatus
					RowStatus
			 }

		-- 1.3.6.1.4.1.1916.5.3.3.1.5.1.1
		wmadRadiusServerIP OBJECT-TYPE
			SYNTAX IpAddress
			MAX-ACCESS read-write
			STATUS current
			DESCRIPTION
				"IP address of the RADIUS server."
			::= { wmadRadiusServerEntry 1 }

		
		-- 1.3.6.1.4.1.1916.5.3.3.1.5.1.2
		wmadRadiusServerPort OBJECT-TYPE
			SYNTAX Integer32
			MAX-ACCESS read-write
			STATUS current
			DESCRIPTION
				"Port number for the RADIUS server."
			::= { wmadRadiusServerEntry 2 }

		
		-- 1.3.6.1.4.1.1916.5.3.3.1.5.1.3
		wmadRadiusServerRetries OBJECT-TYPE
			SYNTAX Integer32
			MAX-ACCESS read-write
			STATUS current
			DESCRIPTION
				"Number of retries for a RADIUS authentication request."
			::= { wmadRadiusServerEntry 3 }

		
		-- 1.3.6.1.4.1.1916.5.3.3.1.5.1.4
		wmadRadiusServerTimeout OBJECT-TYPE
			SYNTAX Integer32
			MAX-ACCESS read-write
			STATUS current
			DESCRIPTION
				"Delay between requests."
			::= { wmadRadiusServerEntry 4 }

		
		-- 1.3.6.1.4.1.1916.5.3.3.1.5.1.5
		wmadRadiusServerSharedSecret OBJECT-TYPE
			SYNTAX DisplayString
			MAX-ACCESS read-write
			STATUS current
			DESCRIPTION
				"Shared secret to be used between the NAS and RADIUS server."
			::= { wmadRadiusServerEntry 5 }

		
		-- 1.3.6.1.4.1.1916.5.3.3.1.5.1.6
		wmadRadiusServerNASIdentifier OBJECT-TYPE
			SYNTAX DisplayString
			MAX-ACCESS read-write
			STATUS current
			DESCRIPTION
				"NAS identifier to be include in RADIUS request."
			::= { wmadRadiusServerEntry 6 }

		
		-- 1.3.6.1.4.1.1916.5.3.3.1.5.1.7
		wmadRadiusServerAuthType OBJECT-TYPE
			SYNTAX INTEGER
				{
				pap(0),
				chap(1),
				msChap(2),
				msChapV2(3),
				notApplicable(4)
				}
			MAX-ACCESS read-write
			STATUS current
			DESCRIPTION
				"Challenge mechanism for the request."
			::= { wmadRadiusServerEntry 7 }

		
		-- 1.3.6.1.4.1.1916.5.3.3.1.5.1.8
		wmadRadiusServerRowStatus OBJECT-TYPE
			SYNTAX RowStatus
			MAX-ACCESS read-write
			STATUS current
			DESCRIPTION
				"RowStatus value for manipulating wmadRADIUSServerTable."
			::= { wmadRadiusServerEntry 8 }

		
		-- 1.3.6.1.4.1.1916.5.3.3.1.6
		wmadFilterIDTable OBJECT-TYPE
			SYNTAX SEQUENCE OF WmadFilterIDEntry
			MAX-ACCESS not-accessible
			STATUS current
			DESCRIPTION
				"Table of names filters for a WMAD."
			::= { wmadConfigObjects 6 }

		
		-- 1.3.6.1.4.1.1916.5.3.3.1.6.1
		wmadFilterIDEntry OBJECT-TYPE
			SYNTAX WmadFilterIDEntry
			MAX-ACCESS not-accessible
			STATUS current
			DESCRIPTION
				"Name of a specific filter in the WMAD."
			INDEX { ifIndex, wmadFilterID }
			::= { wmadFilterIDTable 1 }

		
		WmadFilterIDEntry ::=
			SEQUENCE { 
				wmadFilterID
					DisplayString,
				wmadFilterIDStatus
					RowStatus
			 }

		-- 1.3.6.1.4.1.1916.5.3.3.1.6.1.1
		wmadFilterID OBJECT-TYPE
			SYNTAX DisplayString
			MAX-ACCESS read-write
			STATUS current
			DESCRIPTION
				"Filter names."
			::= { wmadFilterIDEntry 1 }

		
		-- 1.3.6.1.4.1.1916.5.3.3.1.6.1.2
		wmadFilterIDStatus OBJECT-TYPE
			SYNTAX RowStatus
			MAX-ACCESS read-write
			STATUS current
			DESCRIPTION
				"RowStatus for operating on wmadFilterIDTable."
			::= { wmadFilterIDEntry 2 }

		
		-- 1.3.6.1.4.1.1916.5.3.3.1.7
		wmadFilterRuleTable OBJECT-TYPE
			SYNTAX SEQUENCE OF WmadFilterRuleEntry
			MAX-ACCESS not-accessible
			STATUS current
			DESCRIPTION
				"Table containing specific filters for a named filter."
			::= { wmadConfigObjects 7 }

		
		-- 1.3.6.1.4.1.1916.5.3.3.1.7.1
		wmadFilterRuleEntry OBJECT-TYPE
			SYNTAX WmadFilterRuleEntry
			MAX-ACCESS not-accessible
			STATUS current
			DESCRIPTION
				"Filter elements for an individual WMAD filter."
			INDEX { ifIndex, wmadFilterID, wmadFilterRuleOrder }
			::= { wmadFilterRuleTable 1 }

		
		WmadFilterRuleEntry ::=
			SEQUENCE { 
				wmadFilterRuleOrder
					Integer32,
				wmadFilterRuleDirection
					INTEGER,
				wmadFilterRuleAction
					INTEGER,
				wmadFilterRuleIPAddress
					IpAddress,
				wmadFilterRulePortLow
					Integer32,
				wmadFilterRulePortHigh
					Integer32,
				wmadFilterRuleProtocol
					INTEGER,
				wmadFilterRuleEtherType
					INTEGER,
				wmadFilterRuleStatus
					RowStatus
			 }

		-- 1.3.6.1.4.1.1916.5.3.3.1.7.1.1
		wmadFilterRuleOrder OBJECT-TYPE
			SYNTAX Integer32 (1..65532)
			MAX-ACCESS read-write
			STATUS current
			DESCRIPTION
				"Position of the filter in the filter list."
			::= { wmadFilterRuleEntry 1 }

		
		-- 1.3.6.1.4.1.1916.5.3.3.1.7.1.2
		wmadFilterRuleDirection OBJECT-TYPE
			SYNTAX INTEGER
				{
				in(1),
				out(2),
				both(3)
				}
			MAX-ACCESS read-write
			STATUS current
			DESCRIPTION
				"Traffic direction to apply the rule."
			::= { wmadFilterRuleEntry 2 }

		
		-- 1.3.6.1.4.1.1916.5.3.3.1.7.1.3
		wmadFilterRuleAction OBJECT-TYPE
			SYNTAX INTEGER
				{
				allow(1),
				disallow(2)
				}
			MAX-ACCESS read-write
			STATUS current
			DESCRIPTION
				"Allow or deny traffic for the filter."
			::= { wmadFilterRuleEntry 3 }

		
		-- 1.3.6.1.4.1.1916.5.3.3.1.7.1.4
		wmadFilterRuleIPAddress OBJECT-TYPE
			SYNTAX IpAddress
			MAX-ACCESS read-write
			STATUS current
			DESCRIPTION
				"IP address to apply the filter."
			::= { wmadFilterRuleEntry 4 }

		
		-- 1.3.6.1.4.1.1916.5.3.3.1.7.1.5
		wmadFilterRulePortLow OBJECT-TYPE
			SYNTAX Integer32
			MAX-ACCESS read-write
			STATUS current
			DESCRIPTION
				"Low port number for the filter."
			::= { wmadFilterRuleEntry 5 }

		
		-- 1.3.6.1.4.1.1916.5.3.3.1.7.1.6
		wmadFilterRulePortHigh OBJECT-TYPE
			SYNTAX Integer32
			MAX-ACCESS read-write
			STATUS current
			DESCRIPTION
				"High port number for the filter."
			::= { wmadFilterRuleEntry 6 }

		
		-- 1.3.6.1.4.1.1916.5.3.3.1.7.1.7
		wmadFilterRuleProtocol OBJECT-TYPE
			SYNTAX INTEGER
				{
				notApplicable(1),
				tcp(2)
				}
			MAX-ACCESS read-write
			STATUS current
			DESCRIPTION
				"Specific protocol to filter."
			::= { wmadFilterRuleEntry 7 }

		
		-- 1.3.6.1.4.1.1916.5.3.3.1.7.1.8
		wmadFilterRuleEtherType OBJECT-TYPE
			SYNTAX INTEGER
				{
				ip(1),
				arp(2),
				rarp(3)
				}
			MAX-ACCESS read-write
			STATUS current
			DESCRIPTION
				"Specific ethertype to filter."
			::= { wmadFilterRuleEntry 8 }

		
		-- 1.3.6.1.4.1.1916.5.3.3.1.7.1.9
		wmadFilterRuleStatus OBJECT-TYPE
			SYNTAX RowStatus
			MAX-ACCESS read-write
			STATUS current
			DESCRIPTION
				"RowStatus value for the wmadFilterRuleTable."
			::= { wmadFilterRuleEntry 9 }

		
		-- 1.3.6.1.4.1.1916.5.3.3.1.8
		wmadPrivacyTable OBJECT-TYPE
			SYNTAX SEQUENCE OF WmadPrivacyEntry
			MAX-ACCESS not-accessible
			STATUS current
			DESCRIPTION
				"Table of privacy settings for the WMAD."
			::= { wmadConfigObjects 8 }

		
		-- 1.3.6.1.4.1.1916.5.3.3.1.8.1
		wmadPrivacyEntry OBJECT-TYPE
			SYNTAX WmadPrivacyEntry
			MAX-ACCESS not-accessible
			STATUS current
			DESCRIPTION
				"Configuration values for a specific privacy setting."
			INDEX { ifIndex }
			::= { wmadPrivacyTable 1 }

		
		WmadPrivacyEntry ::=
			SEQUENCE { 
				wmadPrivWEPKeyType
					INTEGER,
				wmadPrivDynamicRekeyFrequency
					Integer32,
				wmadPrivWEPKeyLength
					Integer32,
				wmadPrivWPA1Enabled
					TruthValue,
				wmadPrivUseSharedKey
					TruthValue,
				wmadPrivWPASharedKey
					DisplayString,
				wmadPrivWPA2Enabled
					TruthValue
			 }

		-- 1.3.6.1.4.1.1916.5.3.3.1.8.1.1
		wmadPrivWEPKeyType OBJECT-TYPE
			SYNTAX INTEGER
				{
				none(1),
				wepstatic(2),
				wpapsk(3),
				dynamic(4),
				wpa(5)
				}
			MAX-ACCESS read-write
			STATUS current
			DESCRIPTION
				"Type of key in use. 
				none(1) = not cofigured, 
				wepstatic(2) = static WEP, 
				wpapsk(3) = WPA Pre-Shared Key,
				dynamic(4) = dynamically assigned,
				wpa(5) = WPA."
			::= { wmadPrivacyEntry 1 }

		
		-- 1.3.6.1.4.1.1916.5.3.3.1.8.1.2
		wmadPrivDynamicRekeyFrequency OBJECT-TYPE
			SYNTAX Integer32
			MAX-ACCESS read-write
			STATUS current
			DESCRIPTION
				"Dynamic WEP re-keying frequency, in seconds.  Setting this 
				value to 0 disables rekeying.
				
				This value is only meaningful if wmadPrivWEPKeyType == dynamic.
				For any other values of wmadPrivWEPKeyType, reading or setting 
				this value will return an unsuccessful status and will return 
				a value of null or zero."
			::= { wmadPrivacyEntry 2 }

		
		-- 1.3.6.1.4.1.1916.5.3.3.1.8.1.3
		wmadPrivWEPKeyLength OBJECT-TYPE
			SYNTAX Integer32
			MAX-ACCESS read-write
			STATUS current
			DESCRIPTION
				"WEP key length, either 40 or 104 bit.  If wmadPrivWEPKeyType
				is none, reading or setting this value will return an 
				unsuccessful status and will return a value of null or zero."
			::= { wmadPrivacyEntry 3 }

		
		-- 1.3.6.1.4.1.1916.5.3.3.1.8.1.4
		wmadPrivWPA1Enabled OBJECT-TYPE
			SYNTAX TruthValue
			MAX-ACCESS read-write
			STATUS current
			DESCRIPTION
				"Enables WPA.1 (Wi-Fi Protected Access)."
			::= { wmadPrivacyEntry 4 }

		
		-- 1.3.6.1.4.1.1916.5.3.3.1.8.1.5
		wmadPrivUseSharedKey OBJECT-TYPE
			SYNTAX TruthValue
			MAX-ACCESS read-write
			STATUS current
			DESCRIPTION
				"Enables the use of WPA shared key for this WMAD."
			::= { wmadPrivacyEntry 5 }

		
		-- 1.3.6.1.4.1.1916.5.3.3.1.8.1.6
		wmadPrivWPASharedKey OBJECT-TYPE
			SYNTAX DisplayString
			MAX-ACCESS read-write
			STATUS current
			DESCRIPTION
				"The value of the WPA shared key for this WMAD.  
				
				This value is logically WRITE ONLY.  Attempts 
				to read this value shall return unsuccessful 
				status and values of null or zero."
			::= { wmadPrivacyEntry 6 }

		
		-- 1.3.6.1.4.1.4329.15.3.3.1.8.1.7
		wmadPrivWPA2Enabled OBJECT-TYPE
			SYNTAX TruthValue
			MAX-ACCESS read-write
			STATUS current
			DESCRIPTION
				"When true, WPA v.2 support is enabled."
			::= { wmadPrivacyEntry 7 }

		
		-- 1.3.6.1.4.1.1916.5.3.3.1.9
		wmadWEPKeyTable OBJECT-TYPE
			SYNTAX SEQUENCE OF WmadWEPKeyEntry
			MAX-ACCESS not-accessible
			STATUS current
			DESCRIPTION
				"Table of WEP key entries for a static WEP definition."
			::= { wmadConfigObjects 9 }

		
		-- 1.3.6.1.4.1.1916.5.3.3.1.9.1
		wmadWEPKeyEntry OBJECT-TYPE
			SYNTAX WmadWEPKeyEntry
			MAX-ACCESS not-accessible
			STATUS current
			DESCRIPTION
				"WEP key for a single entry in the table."
			INDEX { ifIndex, wmadWEPKeyIndex }
			::= { wmadWEPKeyTable 1 }

		
		WmadWEPKeyEntry ::=
			SEQUENCE { 
				wmadWEPKeyIndex
					Integer32,
				wmadWEPKeyValue
					WEPKeytype
			 }

		-- 1.3.6.1.4.1.1916.5.3.3.1.9.1.1
		wmadWEPKeyIndex OBJECT-TYPE
			SYNTAX Integer32 (1..4)
			MAX-ACCESS read-write
			STATUS current
			DESCRIPTION
				"Table index for the WEP key."
			::= { wmadWEPKeyEntry 1 }

		
		-- 1.3.6.1.4.1.1916.5.3.3.1.9.1.2
		wmadWEPKeyValue OBJECT-TYPE
			SYNTAX WEPKeytype
			MAX-ACCESS read-write
			STATUS current
			DESCRIPTION
				"Value of a WEP key for this WMAD.
				
				This value is logically WRITE ONLY.  Attempts 
				to read this value shall return unsuccessful 
				status and values of null or zero."
			::= { wmadWEPKeyEntry 2 }

		
		-- 1.3.6.1.4.1.1916.5.3.3.1.10
		wmad3rdPartyAPTable OBJECT-TYPE
			SYNTAX SEQUENCE OF Wmad3rdPartyAPEntry
			MAX-ACCESS not-accessible
			STATUS current
			DESCRIPTION
				"Contains a list of 3rd Party access points for 
				the WM."
			::= { wmadConfigObjects 10 }

		
		-- 1.3.6.1.4.1.1916.5.3.3.1.10.1
		wmad3rdPartyAPEntry OBJECT-TYPE
			SYNTAX Wmad3rdPartyAPEntry
			MAX-ACCESS not-accessible
			STATUS current
			DESCRIPTION
				"Configuration information for a 3rd party access point."
			INDEX { ifIndex, apMacAddress }
			::= { wmad3rdPartyAPTable 1 }

		
		Wmad3rdPartyAPEntry ::=
			SEQUENCE { 
				apMacAddress
					MacAddress,
				apIpAddress
					IpAddress
			 }

		-- 1.3.6.1.4.1.1916.5.3.3.1.10.1.1
		apMacAddress OBJECT-TYPE
			SYNTAX MacAddress
			MAX-ACCESS read-write
			STATUS current
			DESCRIPTION
				"Ethernet MAC address of the 3rd party access point."
			::= { wmad3rdPartyAPEntry 1 }

		
		-- 1.3.6.1.4.1.1916.5.3.3.1.10.1.2
		apIpAddress OBJECT-TYPE
			SYNTAX IpAddress
			MAX-ACCESS read-write
			STATUS current
			DESCRIPTION
				"IP address of the 3rd party access point."
			::= { wmad3rdPartyAPEntry 2 }

		
		-- 1.3.6.1.4.1.1916.5.3.3.2
		wmadStatsObjects OBJECT IDENTIFIER ::= { accessDomains 2 }

		
		-- 1.3.6.1.4.1.1916.5.3.3.2.1
		activeWMADSessionCount OBJECT-TYPE
			SYNTAX Integer32
			MAX-ACCESS read-write
			STATUS current
			DESCRIPTION
				"Number of active WMADs."
			::= { wmadStatsObjects 1 }

		
		-- 1.3.6.1.4.1.1916.5.3.5
		altitude OBJECT IDENTIFIER ::= { summitWMMgmt 5 }

		
		-- 1.3.6.1.4.1.1916.5.3.5.1
		altitudeConfigObjects OBJECT IDENTIFIER ::= { altitude 1 }

		
		-- 1.3.6.1.4.1.1916.5.3.5.1.1
		altitudeCount OBJECT-TYPE
			SYNTAX Integer32
			MAX-ACCESS read-only
			STATUS current
			DESCRIPTION
				"The count of currently configured Altitudes associated with this summitWM."
			::= { altitudeConfigObjects 1 }

		
		-- 1.3.6.1.4.1.1916.5.3.5.1.2
		altitudeTable OBJECT-TYPE
			SYNTAX SEQUENCE OF AltitudeEntry
			MAX-ACCESS not-accessible
			STATUS current
			DESCRIPTION
				"Contains a list of all configured Altitudes associated with the summitWM."
			::= { altitudeConfigObjects 2 }

		
		-- 1.3.6.1.4.1.1916.5.3.5.1.2.1
		altitudeEntry OBJECT-TYPE
			SYNTAX AltitudeEntry
			MAX-ACCESS not-accessible
			STATUS current
			DESCRIPTION
				"Configuration information for an access point."
			INDEX { altitudeIndex }
			::= { altitudeTable 1 }

		
		AltitudeEntry ::=
			SEQUENCE { 
				altitudeIndex
					Integer32,
				altitudeName
					DisplayString,
				altitudeDesc
					DisplayString,
				altitudeSerialNumber
					OCTET STRING,
				altitudePortifIndex
					InterfaceIndex,
				altitudeWiredIfIndex
					InterfaceIndex,
				altitudeSoftwareVersion
					OCTET STRING,
				altitudeSpecific
					OBJECT IDENTIFIER,
				altitudeBroadcastDisassociate
					TruthValue,
				altitudeRowStatus
					RowStatus
			 }

		-- 1.3.6.1.4.1.1916.5.3.5.1.2.1.1
		altitudeIndex OBJECT-TYPE
			SYNTAX Integer32 (1..2147483647)
			MAX-ACCESS read-write
			STATUS current
			DESCRIPTION
				"Table index for the access point."
			::= { altitudeEntry 1 }

		
		-- 1.3.6.1.4.1.1916.5.3.5.1.2.1.2
		altitudeName OBJECT-TYPE
			SYNTAX DisplayString
			MAX-ACCESS read-write
			STATUS current
			DESCRIPTION
				"Altitude's name."
			::= { altitudeEntry 2 }

		
		-- 1.3.6.1.4.1.1916.5.3.5.1.2.1.3
		altitudeDesc OBJECT-TYPE
			SYNTAX DisplayString
			MAX-ACCESS read-write
			STATUS current
			DESCRIPTION
				"Text description of the Altitude."
			::= { altitudeEntry 3 }

		
		-- 1.3.6.1.4.1.1916.5.3.5.1.2.1.4
		altitudeSerialNumber OBJECT-TYPE
			SYNTAX OCTET STRING (SIZE (16))
			MAX-ACCESS read-only
			STATUS current
			DESCRIPTION
				"16-character serial number of the Altitude."
			::= { altitudeEntry 4 }

		
		-- 1.3.6.1.4.1.1916.5.3.5.1.2.1.5
		altitudePortifIndex OBJECT-TYPE
			SYNTAX InterfaceIndex
			MAX-ACCESS read-write
			STATUS current
			DESCRIPTION
				"ifIndex of the physical port to which this Altitude is assigned."
			::= { altitudeEntry 5 }

		
		-- 1.3.6.1.4.1.1916.5.3.5.1.2.1.6
		altitudeWiredIfIndex OBJECT-TYPE
			SYNTAX InterfaceIndex
			MAX-ACCESS read-write
			STATUS current
			DESCRIPTION
				"ifIndex of the wired interface on the Altitude."
			::= { altitudeEntry 6 }

		
		-- 1.3.6.1.4.1.1916.5.3.5.1.2.1.7
		altitudeSoftwareVersion OBJECT-TYPE
			SYNTAX OCTET STRING
			MAX-ACCESS read-only
			STATUS current
			DESCRIPTION
				"Software version currently installed on the Altitude."
			::= { altitudeEntry 7 }

		
		-- 1.3.6.1.4.1.1916.5.3.5.1.2.1.8
		altitudeSpecific OBJECT-TYPE
			SYNTAX OBJECT IDENTIFIER
			MAX-ACCESS read-only
			STATUS current
			DESCRIPTION
				"A link back to the OID under the summitWMProducts
				branch that identifies the specific version of this Altitude."
			::= { altitudeEntry 8 }

		
		-- 1.3.6.1.4.1.1916.5.3.5.1.2.1.9
		altitudeBroadcastDisassociate OBJECT-TYPE
			SYNTAX TruthValue
			MAX-ACCESS read-write
			STATUS current
			DESCRIPTION
				"True indicates that the Altitude should broadcast
				disassociation requests, False indicates unicast."
			::= { altitudeEntry 9 }

		
		-- 1.3.6.1.4.1.1916.5.3.5.1.2.1.10
		altitudeRowStatus OBJECT-TYPE
			SYNTAX RowStatus
			MAX-ACCESS read-write
			STATUS current
			DESCRIPTION
				"RowStatus for the altitudeTable."
			::= { altitudeEntry 10 }

		
		-- 1.3.6.1.4.1.1916.5.3.5.1.3
		altitudeRadioTable OBJECT-TYPE
			SYNTAX SEQUENCE OF AltitudeRadioEntry
			MAX-ACCESS not-accessible
			STATUS current
			DESCRIPTION
				"Table access point radio configuration information."
			::= { altitudeConfigObjects 3 }

		
		-- 1.3.6.1.4.1.1916.5.3.5.1.3.1
		altitudeRadioEntry OBJECT-TYPE
			SYNTAX AltitudeRadioEntry
			MAX-ACCESS not-accessible
			STATUS current
			DESCRIPTION
				"Configuration information for a radio on the access point."
			INDEX { altitudeIndex, ifIndex }
			::= { altitudeRadioTable 1 }

		
		AltitudeRadioEntry ::=
			SEQUENCE { 
				altitudeRadioFrequency
					INTEGER
			 }

		-- 1.3.6.1.4.1.1916.5.3.5.1.3.1.1
		altitudeRadioFrequency OBJECT-TYPE
			SYNTAX INTEGER
				{
				freq50GHz(1),
				freq24GHz(2)
				}
			MAX-ACCESS read-only
			STATUS current
			DESCRIPTION
				"Indicates the type of radio (a or b/g)."
			::= { altitudeRadioEntry 1 }

		
		-- 1.3.6.1.4.1.1916.5.3.5.1.4
		radioWMADTable OBJECT-TYPE
			SYNTAX SEQUENCE OF RadioWMADEntry
			MAX-ACCESS not-accessible
			STATUS current
			DESCRIPTION
				"Table of WMADs the radio is participating in."
			::= { altitudeConfigObjects 4 }

		
		-- 1.3.6.1.4.1.1916.5.3.5.1.4.1
		radioWMADEntry OBJECT-TYPE
			SYNTAX RadioWMADEntry
			MAX-ACCESS not-accessible
			STATUS current
			DESCRIPTION
				"Information for a single WMAD entry."
			INDEX { radioIfIndex, wmadIfIndex }
			::= { radioWMADTable 1 }

		
		RadioWMADEntry ::=
			SEQUENCE { 
				radioIfIndex
					InterfaceIndex,
				wmadIfIndex
					InterfaceIndex,
				radioWMADRowStatus
					RowStatus
			 }

		-- 1.3.6.1.4.1.1916.5.3.5.1.4.1.1
		radioIfIndex OBJECT-TYPE
			SYNTAX InterfaceIndex
			MAX-ACCESS read-write
			STATUS current
			DESCRIPTION
				"Radio participating in the WMAD."
			::= { radioWMADEntry 1 }

		
		-- 1.3.6.1.4.1.1916.5.3.5.1.4.1.2
		wmadIfIndex OBJECT-TYPE
			SYNTAX InterfaceIndex
			MAX-ACCESS read-write
			STATUS current
			DESCRIPTION
				"ifIndex for the WMAD the radio is participating."
			::= { radioWMADEntry 2 }

		
		-- 1.3.6.1.4.1.1916.5.3.5.1.4.1.3
		radioWMADRowStatus OBJECT-TYPE
			SYNTAX RowStatus
			MAX-ACCESS read-write
			STATUS current
			DESCRIPTION
				"RowStatus for the radioWMADTable."
			::= { radioWMADEntry 3 }

		
		-- 1.3.6.1.4.1.1916.5.3.5.2
		altitudeStatsObjects OBJECT IDENTIFIER ::= { altitude 2 }

		
		-- 1.3.6.1.4.1.1916.5.3.5.2.1
		altitudeActiveCount OBJECT-TYPE
			SYNTAX Integer32
			MAX-ACCESS read-only
			STATUS current
			DESCRIPTION
				"The count of active Altitude associated with this summitWM."
			::= { altitudeStatsObjects 1 }

		
		-- 1.3.6.1.4.1.1916.5.3.5.2.2
		altitudeStatsTable OBJECT-TYPE
			SYNTAX SEQUENCE OF AltitudeStatsEntry
			MAX-ACCESS not-accessible
			STATUS current
			DESCRIPTION
				"Table of statistics for the access points."
			::= { altitudeStatsObjects 2 }

		
		-- 1.3.6.1.4.1.1916.5.3.5.2.2.1
		altitudeStatsEntry OBJECT-TYPE
			SYNTAX AltitudeStatsEntry
			MAX-ACCESS not-accessible
			STATUS current
			DESCRIPTION
				"Statistics for an access point."
			INDEX { altitudeIndex }
			::= { altitudeStatsTable 1 }

		
		AltitudeStatsEntry ::=
			SEQUENCE { 
				altitudeInUcastPkts
					Counter64,
				altitudeInNUcastPkts
					Counter64,
				altitudeInOctets
					Counter64,
				altitudeInErrors
					Counter64,
				altitudeInDiscards
					Counter64,
				altitudeOutUcastPkts
					Counter64,
				altitudeOutNUcastPkts
					Counter64,
				altitudeOutOctets
					Counter64,
				altitudeOutErrors
					Counter64,
				altitudeOutDiscards
					Counter64,
				altitudeUpTime
					TimeTicks
			 }

		-- 1.3.6.1.4.1.1916.5.3.5.2.2.1.1
		altitudeInUcastPkts OBJECT-TYPE
			SYNTAX Counter64
			MAX-ACCESS read-only
			STATUS current
			DESCRIPTION
				"Number of unicast packets from wireless-to-wired network."
			::= { altitudeStatsEntry 1 }

		
		-- 1.3.6.1.4.1.1916.5.3.5.2.2.1.2
		altitudeInNUcastPkts OBJECT-TYPE
			SYNTAX Counter64
			MAX-ACCESS read-only
			STATUS current
			DESCRIPTION
				"Number of non-unicast packets from wireless-to-wired network."
			::= { altitudeStatsEntry 2 }

		
		-- 1.3.6.1.4.1.1916.5.3.5.2.2.1.3
		altitudeInOctets OBJECT-TYPE
			SYNTAX Counter64
			MAX-ACCESS read-only
			STATUS current
			DESCRIPTION
				"Number of octets from wireless-to-wired network."
			::= { altitudeStatsEntry 3 }

		
		-- 1.3.6.1.4.1.1916.5.3.5.2.2.1.4
		altitudeInErrors OBJECT-TYPE
			SYNTAX Counter64
			MAX-ACCESS read-only
			STATUS current
			DESCRIPTION
				"Number of error packets from wireless-to-wired network."
			::= { altitudeStatsEntry 4 }

		
		-- 1.3.6.1.4.1.1916.5.3.5.2.2.1.5
		altitudeInDiscards OBJECT-TYPE
			SYNTAX Counter64
			MAX-ACCESS read-only
			STATUS current
			DESCRIPTION
				"Number of discarded packets from wireless-to-wired network."
			::= { altitudeStatsEntry 5 }

		
		-- 1.3.6.1.4.1.1916.5.3.5.2.2.1.6
		altitudeOutUcastPkts OBJECT-TYPE
			SYNTAX Counter64
			MAX-ACCESS read-only
			STATUS current
			DESCRIPTION
				"Number of unicast packets from wired-to-wireless network."
			::= { altitudeStatsEntry 6 }

		
		-- 1.3.6.1.4.1.1916.5.3.5.2.2.1.7
		altitudeOutNUcastPkts OBJECT-TYPE
			SYNTAX Counter64
			MAX-ACCESS read-only
			STATUS current
			DESCRIPTION
				"Number of non-unicast packets from wired-to-wireless network."
			::= { altitudeStatsEntry 7 }

		
		-- 1.3.6.1.4.1.1916.5.3.5.2.2.1.8
		altitudeOutOctets OBJECT-TYPE
			SYNTAX Counter64
			MAX-ACCESS read-only
			STATUS current
			DESCRIPTION
				"Number of octets from wired-to-wireless network."
			::= { altitudeStatsEntry 8 }

		
		-- 1.3.6.1.4.1.1916.5.3.5.2.2.1.9
		altitudeOutErrors OBJECT-TYPE
			SYNTAX Counter64
			MAX-ACCESS read-only
			STATUS current
			DESCRIPTION
				"Number of error packets from wired-to-wireless network."
			::= { altitudeStatsEntry 9 }

		
		-- 1.3.6.1.4.1.1916.5.3.5.2.2.1.10
		altitudeOutDiscards OBJECT-TYPE
			SYNTAX Counter64
			MAX-ACCESS read-only
			STATUS current
			DESCRIPTION
				"Number of discarded packets from wired-to-wireless network."
			::= { altitudeStatsEntry 10 }

		
		-- 1.3.6.1.4.1.1916.5.3.5.2.2.1.11
		altitudeUpTime OBJECT-TYPE
			SYNTAX TimeTicks
			MAX-ACCESS read-only
			STATUS current
			DESCRIPTION
				"Description."
			::= { altitudeStatsEntry 11 }

		
		-- 1.3.6.1.4.1.1916.5.3.6
		mobileUnits OBJECT IDENTIFIER ::= { summitWMMgmt 6 }

		
		-- 1.3.6.1.4.1.1916.5.3.6.1
		mobileUnitCount OBJECT-TYPE
			SYNTAX Integer32
			MAX-ACCESS read-write
			STATUS current
			DESCRIPTION
				"Number of clients associated with the access point."
			::= { mobileUnits 1 }

		
		-- 1.3.6.1.4.1.1916.5.3.6.2
		muTable OBJECT-TYPE
			SYNTAX SEQUENCE OF MuEntry
			MAX-ACCESS not-accessible
			STATUS current
			DESCRIPTION
				"Table of information for clients associated with the WM."
			::= { mobileUnits 2 }

		
		-- 1.3.6.1.4.1.1916.5.3.6.2.1
		muEntry OBJECT-TYPE
			SYNTAX MuEntry
			MAX-ACCESS not-accessible
			STATUS current
			DESCRIPTION
				"Information for a client associated with the WM."
			INDEX { muMACAddress }
			::= { muTable 1 }

		
		MuEntry ::=
			SEQUENCE { 
				muMACAddress
					MacAddress,
				muIPAddress
					IpAddress,
				muUser
					OCTET STRING,
				muState
					TruthValue,
				muAltitudeSerialNo
					OCTET STRING,
				muWmadSSID
					OCTET STRING,
				muTxPackets
					Counter64,
				muRxPackets
					Counter64,
				muTxOctets
					Counter64,
				muRxOctets
					Counter64,
				muDuration
					Counter64
			 }

		-- 1.3.6.1.4.1.1916.5.3.6.2.1.1
		muMACAddress OBJECT-TYPE
			SYNTAX MacAddress
			MAX-ACCESS read-only
			STATUS current
			DESCRIPTION
				"Client MAC address."
			::= { muEntry 1 }

		
		-- 1.3.6.1.4.1.1916.5.3.6.2.1.2
		muIPAddress OBJECT-TYPE
			SYNTAX IpAddress
			MAX-ACCESS read-only
			STATUS current
			DESCRIPTION
				"Client IP Address."
			::= { muEntry 2 }

		
		-- 1.3.6.1.4.1.1916.5.3.6.2.1.3
		muUser OBJECT-TYPE
			SYNTAX OCTET STRING
			MAX-ACCESS read-only
			STATUS current
			DESCRIPTION
				"Client login name."
			::= { muEntry 3 }

		
		-- 1.3.6.1.4.1.1916.5.3.6.2.1.4
		muState OBJECT-TYPE
			SYNTAX TruthValue
			MAX-ACCESS read-only
			STATUS current
			DESCRIPTION
				"True if the client is authenticated."
			::= { muEntry 4 }

		
		-- 1.3.6.1.4.1.1916.5.3.6.2.1.5
		muAltitudeSerialNo OBJECT-TYPE
			SYNTAX OCTET STRING
			MAX-ACCESS read-only
			STATUS current
			DESCRIPTION
				"Serial Number of the Altitude the client is associated with."
			::= { muEntry 5 }

		
		-- 1.3.6.1.4.1.1916.5.3.6.2.1.6
		muWmadSSID OBJECT-TYPE
			SYNTAX OCTET STRING
			MAX-ACCESS read-only
			STATUS current
			DESCRIPTION
				"SSID of the WMAD the client is associated with."
			::= { muEntry 6 }

		
		-- 1.3.6.1.4.1.1916.5.3.6.2.1.7
		muTxPackets OBJECT-TYPE
			SYNTAX Counter64
			MAX-ACCESS read-only
			STATUS current
			DESCRIPTION
				"Number of packets trasmitted to the client."
			::= { muEntry 7 }

		
		-- 1.3.6.1.4.1.1916.5.3.6.2.1.8
		muRxPackets OBJECT-TYPE
			SYNTAX Counter64
			MAX-ACCESS read-only
			STATUS current
			DESCRIPTION
				"Number of packets received from the client."
			::= { muEntry 8 }

		
		-- 1.3.6.1.4.1.1916.5.3.6.2.1.9
		muTxOctets OBJECT-TYPE
			SYNTAX Counter64
			MAX-ACCESS read-only
			STATUS current
			DESCRIPTION
				"Number of octets transmitted to the client."
			::= { muEntry 9 }

		
		-- 1.3.6.1.4.1.1916.5.3.6.2.1.10
		muRxOctets OBJECT-TYPE
			SYNTAX Counter64
			MAX-ACCESS read-only
			STATUS current
			DESCRIPTION
				"Number of octets received from the client."
			::= { muEntry 10 }

		
		-- 1.3.6.1.4.1.1916.5.3.6.2.1.11
		muDuration OBJECT-TYPE
			SYNTAX Counter64
			MAX-ACCESS read-only
			STATUS current
			DESCRIPTION
				"Time client has been associated with the WM."
			::= { muEntry 11 }

		
		-- 1.3.6.1.4.1.1916.5.3.7
		associations OBJECT IDENTIFIER ::= { summitWMMgmt 7 }

		
		-- 1.3.6.1.4.1.1916.5.3.7.1
		assocCount OBJECT-TYPE
			SYNTAX Integer32
			MAX-ACCESS read-write
			STATUS current
			DESCRIPTION
				"Total number of current client associations to the access point."
			::= { associations 1 }

		
		-- 1.3.6.1.4.1.1916.5.3.7.2
		assocTable OBJECT-TYPE
			SYNTAX SEQUENCE OF AssocEntry
			MAX-ACCESS not-accessible
			STATUS current
			DESCRIPTION
				"Table of information about clients associated with the access point."
			::= { associations 2 }

		
		-- 1.3.6.1.4.1.1916.5.3.7.2.1
		assocEntry OBJECT-TYPE
			SYNTAX AssocEntry
			MAX-ACCESS not-accessible
			STATUS current
			DESCRIPTION
				"Information for a single client in the association table."
			INDEX { assocMUMacAddress, altitudeIndex, assocStartSysUpTime }
			::= { assocTable 1 }

		
		AssocEntry ::=
			SEQUENCE { 
				assocMUMacAddress
					MacAddress,
				assocStartSysUpTime
					TimeTicks,
				assocTxPackets
					Counter64,
				assocRxPackets
					Counter64,
				assocTxOctets
					Counter64,
				assocRxOctets
					Counter64,
				assocDuration
					Integer32,
				assocWmadIfIndex
					InterfaceIndex
			 }

		-- 1.3.6.1.4.1.1916.5.3.7.2.1.1
		assocMUMacAddress OBJECT-TYPE
			SYNTAX MacAddress
			MAX-ACCESS read-only
			STATUS current
			DESCRIPTION
				"MAC address of the client."
			::= { assocEntry 1 }

		
		-- 1.3.6.1.4.1.1916.5.3.7.2.1.2
		assocStartSysUpTime OBJECT-TYPE
			SYNTAX TimeTicks
			MAX-ACCESS read-only
			STATUS current
			DESCRIPTION
				"How long the client has been associated to the access point."
			::= { assocEntry 2 }

		
		-- 1.3.6.1.4.1.1916.5.3.7.2.1.3
		assocTxPackets OBJECT-TYPE
			SYNTAX Counter64
			MAX-ACCESS read-only
			STATUS current
			DESCRIPTION
				"Nubmer of tx packets to the client."
			::= { assocEntry 3 }

		
		-- 1.3.6.1.4.1.1916.5.3.7.2.1.4
		assocRxPackets OBJECT-TYPE
			SYNTAX Counter64
			MAX-ACCESS read-only
			STATUS current
			DESCRIPTION
				"Number of received packets from the client."
			::= { assocEntry 4 }

		
		-- 1.3.6.1.4.1.1916.5.3.7.2.1.5
		assocTxOctets OBJECT-TYPE
			SYNTAX Counter64
			MAX-ACCESS read-only
			STATUS current
			DESCRIPTION
				"Number of octets sent to the client."
			::= { assocEntry 5 }

		
		-- 1.3.6.1.4.1.1916.5.3.7.2.1.6
		assocRxOctets OBJECT-TYPE
			SYNTAX Counter64
			MAX-ACCESS read-only
			STATUS current
			DESCRIPTION
				"Number of octets received from the client."
			::= { assocEntry 6 }

		
		-- 1.3.6.1.4.1.1916.5.3.7.2.1.7
		assocDuration OBJECT-TYPE
			SYNTAX Integer32
			MAX-ACCESS read-write
			STATUS current
			DESCRIPTION
				"Length of time since last association."
			::= { assocEntry 7 }

		
		-- 1.3.6.1.4.1.1916.5.3.7.2.1.8
		assocWmadIfIndex OBJECT-TYPE
			SYNTAX InterfaceIndex
			MAX-ACCESS read-only
			STATUS current
			DESCRIPTION
				"Index of WMAD to which the MU is associated with."
			::= { assocEntry 8 }

		
		-- 1.3.6.1.4.1.1916.5.3.8
		protocols OBJECT IDENTIFIER ::= { summitWMMgmt 8 }

		
		-- 1.3.6.1.4.1.1916.5.3.8.1
		wmadc OBJECT IDENTIFIER ::= { protocols 1 }

		
		-- 1.3.6.1.4.1.1916.5.3.9
		logNotifications OBJECT IDENTIFIER ::= { summitWMMgmt 9 }

		
		-- 1.3.6.1.4.1.1916.5.3.9.1
		logEventSeverityThreshold OBJECT-TYPE
			SYNTAX LogEventSeverity
			MAX-ACCESS read-write
			STATUS current
			DESCRIPTION
				"Specifies the minimum level at which the SNMP agent will 
				send notifications for log events.  I.e., setting this
				value to 'major' will send notifcations for critical and
				major log events.  Setting the threshold to minor will 
				trap critical, major, and minor events.
				"
			::= { logNotifications 1 }

		
		-- 1.3.6.1.4.1.1916.5.3.9.3
		logEventSeverity OBJECT-TYPE
			SYNTAX LogEventSeverity
			MAX-ACCESS read-only
			STATUS current
			DESCRIPTION
				"Contains the severity of the most recently trapped summitWMLogAlarm notification."
			::= { logNotifications 3 }

		
		-- 1.3.6.1.4.1.1916.5.3.9.4
		logEventComponent OBJECT-TYPE
			SYNTAX OCTET STRING
			MAX-ACCESS read-write
			STATUS current
			DESCRIPTION
				"Contains the component which sent the most
				recently trapped summitWMLogAlarm notification."
			::= { logNotifications 4 }

		
		-- 1.3.6.1.4.1.1916.5.3.9.5
		logEventDescription OBJECT-TYPE
			SYNTAX OCTET STRING
			MAX-ACCESS read-only
			STATUS current
			DESCRIPTION
				"Contains the description of the most recently trapped 
				summitWMLogAlarm."
			::= { logNotifications 5 }

		
		-- 1.3.6.1.4.1.1916.5.3.9.6
		summitWMLogAlarm NOTIFICATION-TYPE
			OBJECTS { logEventSeverity, logEventComponent, logEventDescription }
			STATUS current
			DESCRIPTION 
				"Components of an alarm."
			::= { logNotifications 6 }

		
		-- 1.3.6.1.4.1.1916.5.3.19
		altitudeNotifications OBJECT IDENTIFIER ::= { summitWMMgmt 19 }

		
		-- 1.3.6.1.4.1.1916.5.3.19.1
		altitudeEventId OBJECT-TYPE
			SYNTAX INTEGER { altitudePollTimeout(1) }
			MAX-ACCESS read-write
			STATUS current
			DESCRIPTION
				"Identifies event associated with Altitude or Altitude tunnel:
				
				altitudePollTimeout - an event triggered when Altitude disconnects from WM"
			::= { altitudeNotifications 1 }

		
		-- 1.3.6.1.4.1.1916.5.3.19.2
		altitudeEventDescription OBJECT-TYPE
			SYNTAX OCTET STRING
			MAX-ACCESS read-only
			STATUS current
			DESCRIPTION
				"Contains the description of the most recently triggered event."
			::= { altitudeNotifications 2 }

		
		-- 1.3.6.1.4.1.1916.5.3.19.3
		altitudeEventSerialNumber OBJECT-TYPE
			SYNTAX OCTET STRING (SIZE (16))
			MAX-ACCESS read-only
			STATUS current
			DESCRIPTION
				"16-character serial number of the Altitude."
			::= { altitudeNotifications 3 }

		
		-- 1.3.6.1.4.1.1916.5.3.19.4
		altitudeTunnelAlarm NOTIFICATION-TYPE
			OBJECTS { altitudeEventId, altitudeEventDescription, altitudeEventSerialNumber }
			STATUS current
			DESCRIPTION 
				"alarm associated with Altitude and Altitude interface."
			::= { altitudeNotifications 4 }

		
		-- 1.3.6.1.4.1.1916.5.3.30
		summitWMConformance OBJECT IDENTIFIER ::= { summitWMMgmt 30 }

		
--  this module
		-- 1.3.6.1.4.1.1916.5.3.30.1
		summitWMModule MODULE-COMPLIANCE
			STATUS current
			DESCRIPTION 
				"Conformance definition for the WM MIB."
			MODULE -- this module
				MANDATORY-GROUPS { summitWMGroup }
			::= { summitWMConformance 1 }

		
		-- 1.3.6.1.4.1.1916.5.3.30.2
		summitWMGroup OBJECT-GROUP
			OBJECTS { sysSoftwareVersion, sysLogLevel, logEventSeverityThreshold, logEventSeverity, logEventComponent, 
				logEventDescription, altitudeEventId, altitudeEventDescription, altitudeEventSerialNumber, assocTxPackets, 
				assocRxPackets, assocTxOctets, assocRxOctets, assocDuration, assocCount, 
				assocMUMacAddress, assocStartSysUpTime, muTxPackets, muRxPackets, muTxOctets, 
				muRxOctets, muDuration, mobileUnitCount, muMACAddress, wmadIfIndex, 
				radioWMADRowStatus, altitudeSpecific, altitudeRowStatus, radioIfIndex, altitudeDesc, 
				altitudeSerialNumber, altitudePortifIndex, wmadFilterRulePortLow, wmadFilterRulePortHigh, altitudeInUcastPkts, 
				altitudeInNUcastPkts, altitudeInOctets, altitudeInErrors, altitudeInDiscards, altitudeOutUcastPkts, 
				altitudeOutNUcastPkts, altitudeOutOctets, altitudeOutErrors, altitudeOutDiscards, cpPasswordLabel, 
				cpLoginLabel, cpURL, wmadDHCPRangeIndex, wmad3rdPartyAP, wmadUseDHCPRelay, 
				wmadMgmtTrafficEnable, wmadAuthModel, physicalPortCount, altitudeSoftwareVersion, mgmtPortIfIndex, 
				mgmtPortHostname, mgmtPortPrimaryDNS, mgmtPortSecondaryDNS, mgmtPortDomain, portMgmtTrafficEnable, 
				portDuplexMode, portFunction, adRole, adIfIndex, adHeartBeatInterval, 
				ntpEnabled, ntpTimezone, ntpTimeServer1, ntpTimeServer2, ntpTimeServer3, 
				tunnelCount, wmadCount, wmadDescription, wmadAssignmentMode, wmadMUSessionTimeout, 
				wmadAllowMulticast, wmadSSID, wmadDomain, wmadDNSServers, wmadWINSServers, 
				wmadParentIfIndex, wmadStatus, wmadDHCPRangeStart, wmadDHCPRangeEnd, wmadDHCPRangeType, 
				wmadDHCPRangeStatus, wmadRadiusServerIP, wmadRadiusServerPort, wmadRadiusServerRetries, wmadRadiusServerTimeout, 
				wmadRadiusServerSharedSecret, wmadRadiusServerNASIdentifier, wmadRadiusServerAuthType, wmadRadiusServerRowStatus, wmadFilterID, 
				wmadFilterIDStatus, wmadFilterRuleOrder, wmadFilterRuleDirection, wmadFilterRuleAction, wmadFilterRuleIPAddress, 
				wmadFilterRuleProtocol, wmadFilterRuleEtherType, wmadFilterRuleStatus, wmadPrivWEPKeyType, wmadPrivDynamicRekeyFrequency, 
				wmadPrivWEPKeyLength, wmadPrivWPA1Enabled, wmadPrivUseSharedKey, wmadPrivWPASharedKey, wmadWEPKeyIndex, 
				wmadWEPKeyValue, activeWMADSessionCount, altitudeCount, altitudeIndex, cpHeaderURL, 
				cpFooterURL, cpMessage, apMacAddress, apIpAddress, summitWMAppLogFacility, 
				serviceLogFacility, sysLogServerIP, sysLogServerPort, sysLogServerRowStatus, sysLogServerIndex, 
				altitudeActiveCount, altitudeWiredIfIndex, sysLogServerEnabled, altitudeUpTime, assocWmadIfIndex, 
				muIPAddress, muUser, muState, muAltitudeSerialNo, muWmadSSID, 
				altitudeBroadcastDisassociate, altitudeName, sysSerialNo, wmadPrivWPA2Enabled, 
				altitudeRadioFrequency, includeAllServiceMessages, 
				tunnelStartIP, tunnelStartWM, tunnelEndIP, tunnelEndWM, tunnelStatus
				 }
			STATUS current
			DESCRIPTION 
				"Conformance groups."
			::= { summitWMConformance 2 }

		
		-- 1.3.6.1.4.1.1916.5.3.30.3
		summitWMAlarms NOTIFICATION-GROUP
			NOTIFICATIONS { summitWMLogAlarm, altitudeTunnelAlarm }
			STATUS current
			DESCRIPTION 
				"Conformance information for the alarm groups."
			::= { summitWMConformance 3 }

		
	
	END

--
-- EXTREME-SUMMIT-WM-MIB.my
--
