--
-- IEEE-802DOT17-RPR-MIB.mib extracted from IEEE 802.17/D3.3
--

IEEE-802DOT17-RPR-MIB DEFINITIONS ::= BEGIN

    IMPORTS
        HCPerfCurrentCount, HCPerfIntervalCount, HCPerfTotalCount
            FROM HC-PerfHist-TC-MIB
        InterfaceIndex, InterfaceIndexOrZero
            FROM IF-MIB
        InetAddressType, InetAddress
            FROM INET-ADDRESS-MIB
        SnmpAdminString
            FROM SNMP-FRAMEWORK-MIB
        OBJECT-GROUP, MODULE-COMPLIANCE
            FROM SNMPv2-CONF
        Integer32, Unsigned32, Counter32, Counter64,
        OBJECT-TYPE, MODULE-IDENTITY
            FROM SNMPv2-SMI
        TruthValue, TimeStamp, MacAddress, DateAndTime, TEXTUAL-CONVENTION
            FROM SNMPv2-TC;


    -- Revision history
    -- 21 Apr 2004 12:00:00 UTC
    ieee802dot17rprMIB MODULE-IDENTITY
        LAST-UPDATED "200404211200Z"    -- April 21, 2004 at 12:00 GMT
        ORGANIZATION
            "IEEE 802.17 Working Group"
        CONTACT-INFO
            "stds-802-17@ieee.org"
        DESCRIPTION
            "The resilient packet ring MIB for IEEE 802.17.
            Copyright (C) IEEE802.17.
            This version of this MIB module is part of IEEE802.17;
            see the draft itself for full legal notices."
        REVISION "200404211200Z"    -- April 21, 2004 at 12:00 GMT
        DESCRIPTION
            "First published version."
        ::= { iso std(0) iso8802(8802) ieee802dot17(17) ieee802dot17mibs(1) 1 }


    --
    -- Textual Conventions used in this MIB
    --
    RprSpan ::= TEXTUAL-CONVENTION
        STATUS current
        DESCRIPTION
            "Indicates the span interface of the RPR MAC. Each RPR
            span is connected to both ringlet0 and ringlet1.
            The east span receives from ringlet1 and transmits through
            ringlet0.
            The west span receives from ringlet0 and transmits through
            ringlet1."
        SYNTAX INTEGER
            {
            east(1),
            west(2)
            }

    RprProtectionStatus ::= TEXTUAL-CONVENTION
        STATUS current
        DESCRIPTION
            "Indicates the current protection status of the RPR MAC
            span.
            The status values are (arranged in ascending priority
            order) :
            noRequest
            No protection request on the span, the protection
            status is idle.
            waitToRestore
            The condition for an automatic protection was cleared and
            the span is engaged in a wait to restore period.
            manualSwitch
            A user initiated manual switch (via the
            rprSpanProtectionCommand) on the span.
            signalDegraded
            An automatically-detected status which causes protection on
            a span when a media signal degrade is detected due to
            excessive BER.
            signalFailed
            An automatically-detected status which causes protection on
            a span when a media signal failure is detected.
            forcedSwitch
            A user initiated forced switch (via the
            rprSpanProtectionCommand) on the span."
        SYNTAX BITS
            {
            noRequest(0),
            waitToRestore(1),
            manualSwitch(2),
            signalDegraded(3),
            signalFailed(4),
            forcedSwitch(5)
            }

    RprOamRinglet ::= TEXTUAL-CONVENTION
        STATUS current
        DESCRIPTION
            "Indicates the ringlet on which the OAM action
            request/response is sent/replied.
            The valid values for this object are:
            (1) Default (2) ringlet0 (3) ringlet1 (4) Reverse ringlet.
            The value (4) is applicable only for OAM response action."
        SYNTAX INTEGER
            {
            default(1),
            ringlet0(2),
            ringlet1(3),
            reverseRinglet(4)
            }


    --
    -- Node definitions
    --
    -- Object groups
    --
    -- 1.0.8802.17.1.1.1
    rprObjects OBJECT IDENTIFIER ::= { ieee802dot17rprMIB 1 }

    -- 1.0.8802.17.1.1.1.1
    rprGeneral OBJECT IDENTIFIER ::= { rprObjects 1 }

    -- RPR interface table
    --
    -- 1.0.8802.17.1.1.1.1.1
    rprIfTable OBJECT-TYPE
        SYNTAX SEQUENCE OF RprIfEntry
        MAX-ACCESS not-accessible
        STATUS current
        DESCRIPTION
            "The RPR interface table, extension to the ifTable.
            All read-write attributes in this table are non-volatile,
            i.e. will be retained across system reset."
        ::= { rprGeneral 1 }

    -- 1.0.8802.17.1.1.1.1.1.1
    rprIfEntry OBJECT-TYPE
        SYNTAX RprIfEntry
        MAX-ACCESS not-accessible
        STATUS current
        DESCRIPTION
            "One such entry for every interface in the ifTable which
            has an ifType of RPR interface."
        INDEX { rprIfIndex }
        ::= { rprIfTable 1 }

    RprIfEntry ::=
        SEQUENCE {
            rprIfIndex
                InterfaceIndex,
            rprIfStationsOnRing
                Unsigned32,
            rprIfReversionMode
                TruthValue,
            rprIfProtectionWTR
                Unsigned32,
            rprIfProtectionFastTimer
                Unsigned32,
            rprIfProtectionSlowTimer
                Unsigned32,
            rprIfAtdTimer
                Unsigned32,
            rprIfKeepaliveTimeout
                Unsigned32,
            rprIfFairnessAggressive
                TruthValue,
            rprIfPtqSize
                Unsigned32,
            rprIfStqSize
                Unsigned32,
            rprIfSTQFullThreshold
                Unsigned32,
            rprIfIdleThreshold
                Unsigned32,
            rprIfSesThreshold
                Unsigned32,
            rprIfWrapConfig
                TruthValue,
            rprIfJumboFramePreferred
                TruthValue,
            rprIfMacOperModes
                BITS,
            rprIfRingOperModes
                BITS,
            rprIfCurrentStatus
                BITS,
            rprIfLastChange
                TimeStamp,
            rprIfChanges
                Counter32
         }

    -- 1.0.8802.17.1.1.1.1.1.1.1
    rprIfIndex OBJECT-TYPE
        SYNTAX InterfaceIndex
        MAX-ACCESS not-accessible
        STATUS current
        DESCRIPTION
            "The ifIndex of this RPR interface."
        REFERENCE
            "RFC 2863, ifIndex"
        ::= { rprIfEntry 1 }

    -- 1.0.8802.17.1.1.1.1.1.1.2
    rprIfStationsOnRing OBJECT-TYPE
        SYNTAX Unsigned32 (1..255)
        MAX-ACCESS read-only
        STATUS current
        DESCRIPTION
            "The number of stations on the RPR ring.
            When the operStatus of the interface is down the value is 1."
        REFERENCE
            "IEEE 802.17 Subclause 11.2.4, numStations"
        ::= { rprIfEntry 2 }

    -- 1.0.8802.17.1.1.1.1.1.1.3
    rprIfReversionMode OBJECT-TYPE
        SYNTAX TruthValue
        MAX-ACCESS read-write
        STATUS current
        DESCRIPTION
            "The reversion mode of the MAC,
            False for non-revertive
            True for revertive.
            Revertive station will return to idle state after
            WTR interval expires.
            Default value for reversion mode is true."
        REFERENCE
            "IEEE 802.17 Subclause 11.2.3, revertive"
        DEFVAL { true }
        ::= { rprIfEntry 3 }

    -- 1.0.8802.17.1.1.1.1.1.1.4
    rprIfProtectionWTR OBJECT-TYPE
        SYNTAX Unsigned32 (0..1440)
        UNITS "Seconds"
        MAX-ACCESS read-write
        STATUS current
        DESCRIPTION
            "Indicates the length of time in seconds, to remain in the
            protection state, after the cause of an automatic
            protection is removed. This mechanism prevents protection
            switch oscillations.
            Default value for WTR is 10 seconds."
        REFERENCE
            "IEEE 802.17 Subclause 11.2.3, wtr"
        DEFVAL { 10 }
        ::= { rprIfEntry 4 }

    -- 1.0.8802.17.1.1.1.1.1.1.5
    rprIfProtectionFastTimer OBJECT-TYPE
        SYNTAX Unsigned32 (1..20)
        UNITS "milliseconds"
        MAX-ACCESS read-write
        STATUS current
        DESCRIPTION
            "Indicates the protection messages fast timer value in 1 ms units.
            The fast timer is used for protection protocols.
            Default value for fast timer protection messages is 10 ms."
        REFERENCE
            "IEEE 802.17 Subclause 11.2.3, txFastTimeout"
        DEFVAL { 10 }
        ::= { rprIfEntry 5 }

    -- 1.0.8802.17.1.1.1.1.1.1.6
    rprIfProtectionSlowTimer OBJECT-TYPE
        SYNTAX Unsigned32 (1..200)
        UNITS "50 milliseconds"
        MAX-ACCESS read-write
        STATUS current
        DESCRIPTION
            "Indicates the protection slow timer value in 50 ms units.
            The slow timer is used for topology and protection protocols.
            Default value for slow timer protection and topology messages
            is 20 units of 50 ms, i.e. 1sec."
        REFERENCE
            "IEEE 802.17 Subclause 11.2.3, txSlowTimeout"
        DEFVAL { 20 }
        ::= { rprIfEntry 6 }

    -- 1.0.8802.17.1.1.1.1.1.1.7
    rprIfAtdTimer OBJECT-TYPE
        SYNTAX Unsigned32 (1..200)
        UNITS "50 milliseconds"
        MAX-ACCESS read-write
        STATUS current
        DESCRIPTION
            "Indicates the timer period for ATD message transmissions.
            Default value is 20 units of 50 ms, i.e. 1sec."
        REFERENCE
            "IEEE 802.17 Subclause 11.2.3, atdTimerTimeout"
        DEFVAL { 20 }
        ::= { rprIfEntry 7 }

    -- 1.0.8802.17.1.1.1.1.1.1.8
    rprIfKeepaliveTimeout OBJECT-TYPE
        SYNTAX Unsigned32 (2..50)
        UNITS "milliseconds"
        MAX-ACCESS read-write
        STATUS current
        DESCRIPTION
            "Indicates the timer to declare keepalive timeout, multiples
            of 1 millisecond.
            Default value for keepalive timeout is 3 ms."
        REFERENCE
            "IEEE 802.17 Subclause 11.2.3, keepaliveTime"
        DEFVAL { 3 }
        ::= { rprIfEntry 8 }

    -- 1.0.8802.17.1.1.1.1.1.1.9
    rprIfFairnessAggressive OBJECT-TYPE
        SYNTAX TruthValue
        MAX-ACCESS read-write
        STATUS current
        DESCRIPTION
            "Indicates whether the selected RPR fairness algorithm is
            aggressive or conservative.
            If true, the selected fairness mode is aggressive.
            If false, the selected fairness mode is conservative.
            The default value for fairness aggressive is true."
        REFERENCE
            "IEEE 802.17 Subclause 11.2.5, conservativeMode"
        DEFVAL { true }
        ::= { rprIfEntry 9 }

    -- 1.0.8802.17.1.1.1.1.1.1.10
    rprIfPtqSize OBJECT-TYPE
        SYNTAX Unsigned32
        UNITS "Bytes"
        MAX-ACCESS read-only
        STATUS current
        DESCRIPTION
            "The size in bytes of the Primary Transit Queue per ringlet
            supported by this RPR MAC."
        REFERENCE
            "IEEE 802.17 Subclause 7.2.2, sizePtq"
        ::= { rprIfEntry 10 }

    -- 1.0.8802.17.1.1.1.1.1.1.11
    rprIfStqSize OBJECT-TYPE
        SYNTAX Unsigned32
        UNITS "Bytes"
        MAX-ACCESS read-only
        STATUS current
        DESCRIPTION
            "The size in bytes of the Secondary Transit Queue per ringlet
            supported by this RPR MAC."
        REFERENCE
            "IEEE 802.17 Subclause 7.2.2, size Stq"
        ::= { rprIfEntry 11 }

    -- 1.0.8802.17.1.1.1.1.1.1.12
    rprIfSTQFullThreshold OBJECT-TYPE
        SYNTAX Unsigned32
        UNITS "MTUs"
        MAX-ACCESS read-write
        STATUS current
        DESCRIPTION
            "A level of STQ occupancy at or above which the STQ
            is almost full.
            This attribute specifies the full threshold location
            in MTU units below the STQ size.
            The range is [stqHighThreshold + mtuSize, sizeSTQ - mtuSize].
            The default value for stqFullThreshold is sizeSTQ - 2*mtuSize."
        REFERENCE
            "IEEE 802.17 Subclause 7.2.2, stqFullThreshold"
        DEFVAL { 2 }
        ::= { rprIfEntry 12 }

    -- 1.0.8802.17.1.1.1.1.1.1.13
    rprIfIdleThreshold OBJECT-TYPE
        SYNTAX Unsigned32
        UNITS "MTUs"
        MAX-ACCESS read-write
        STATUS current
        DESCRIPTION
            "Indicates that a MAC is experiencing an adverse rate
            mismatch. When the PTQ depth exceeds this value,
            the incoming link is considered adversely rate mismatched.
            This attribute specifies the idle-threshold location
            from the top of the PTQ buffer, in MTU size.
            Default value should be 1, which means (sizePTQ - mtuSize)"
        REFERENCE
            "IEEE 802.17 Subclause 7.5.3.2, idleThreshold"
        DEFVAL { 1 }
        ::= { rprIfEntry 13 }

    -- 1.0.8802.17.1.1.1.1.1.1.14
    rprIfSesThreshold OBJECT-TYPE
        SYNTAX Unsigned32 (1..512)
        MAX-ACCESS read-write
        STATUS current
        DESCRIPTION
            "Indicates the number of E-RPR errors to declare
            a second as SES-RPR
            The default value is the rounded integer of
            0.000001 * (lineRate * advertisementRatio)."
        REFERENCE
            "IEEE 802.17 Subclause 12.2.2, sesThreshold"
        ::= { rprIfEntry 14 }

    -- 1.0.8802.17.1.1.1.1.1.1.15
    rprIfWrapConfig OBJECT-TYPE
        SYNTAX TruthValue
        MAX-ACCESS read-write
        STATUS current
        DESCRIPTION
            "Indicates the configured protection mode,
            steering or wrapping, in a MAC that supports both modes.
            If wrap configured bit is set, the station will
            perform wrap protection during ring failures.
            If the station detects another station on the ring that
            has a protection configuration that conflicts with its own,
            the station will generate a defect to higher layers.
            Default value for wrap preferred is false for steering
            only stations, and true for stations that implement wrapping."
        REFERENCE
            "IEEE 802.17 Subclause 11.2.5, protConfig"
        ::= { rprIfEntry 15 }

    -- 1.0.8802.17.1.1.1.1.1.1.16
    rprIfJumboFramePreferred OBJECT-TYPE
        SYNTAX TruthValue
        MAX-ACCESS read-write
        STATUS current
        DESCRIPTION
            "Indicates the preference of the manager to support jumbo frame
            in a MAC that supports jumbo frame.
            The station advertises the 'logical and' of rprIfJumboFramePreferred
            and jumbo capable bit in the rprIfMacCapability.
            Default value for jumbo frame preferred is true. i.e. station
            supports jumbo frame."
        REFERENCE
            "IEEE 802.17 Subclause 11.2.5, jumboPrefer"
        DEFVAL { true }
        ::= { rprIfEntry 16 }

    -- 1.0.8802.17.1.1.1.1.1.1.17
    rprIfMacOperModes OBJECT-TYPE
        SYNTAX BITS
            {
            strictOrder(0),
            dropBadFcs(1)
            }
        MAX-ACCESS read-only
        STATUS current
        DESCRIPTION
            "The summary of the Mac operational modes.
            if strictOrder is set, the MAC operates in strict order mode.
            if dropBadFcs is set, frames with bad FCS are dropped."
        REFERENCE
            "IEEE 802.17 Subclause 6.2, forceStrict and copyBadFcs"
        ::= { rprIfEntry 17 }

    -- 1.0.8802.17.1.1.1.1.1.1.18
    rprIfRingOperModes OBJECT-TYPE
        SYNTAX BITS
            {
            jumboFrames(0),
            wrapProtection(1),
            openRing(2)
            }
        MAX-ACCESS read-only
        STATUS current
        DESCRIPTION
            "The summary of the ring operational modes
            collected through the topology discovery protocol.
            If at least one station doesn't support jumbo frames,
            the jumboFrame bit in this attribute is set to false.
            Only if all stations support jumbo frames, the bit is true.
            If at least one station wasn't configured to wrap,
            the wrap bit in this attribute is set to false.
            Only if all stations configured to wrap, the bit is true.
            If the ring doesn't complete full loop, the ring is considered
            openRing, with at least one detected edge."
        REFERENCE
            "IEEE 802.17 Subclause 11.2.4, jumboType and topoType"
        ::= { rprIfEntry 18 }

    -- 1.0.8802.17.1.1.1.1.1.1.19
    rprIfCurrentStatus OBJECT-TYPE
        SYNTAX BITS
            {
            neighborInconsistency(0),
            duplicateMac(1),
            exceedMaxStations(2)
            }
        MAX-ACCESS read-only
        STATUS current
        DESCRIPTION
            "Indicates the current status of the RPR interface.
            this attribute is used to generate alarm to the management system."
        REFERENCE
            "IEEE 802.17 Subclause 11.2.9, topoInconsistencyDefect,
            duplicateSecMacAddressDefect, and maxStationsDefect"
        ::= { rprIfEntry 19 }

    -- 1.0.8802.17.1.1.1.1.1.1.20
    rprIfLastChange OBJECT-TYPE
        SYNTAX TimeStamp
        MAX-ACCESS read-only
        STATUS current
        DESCRIPTION
            "The value of sysUpTime at the time when any of the following
            attributes changes:
            rprIfStationsOnRing, rprIfReversionMode, rprIfProtectionWTR,
            rprIfProtectionFastTimer, rprIfProtectionSlowTimer, rprIfAtdTimer,
            rprIfKeepaliveTimeout, rprIfFairnessAggressive,
            rprIfSTQFullThreshold, rprIfIdleThreshold,
            rprIfSesThreshold, rprIfWrapConfig, rprIfJumboFramePreferred,
            rprIfMacOperModes, rprIfRingOperModes, rprIfCurrentStatus
            contents of the rprTopoImageEntry."
        ::= { rprIfEntry 20 }

    -- 1.0.8802.17.1.1.1.1.1.1.21
    rprIfChanges OBJECT-TYPE
        SYNTAX Counter32
        MAX-ACCESS read-only
        STATUS current
        DESCRIPTION
            "Indicates number of times rprIfLastChange changed.
            The discontinued counter value is indicated
            by the ifCounterDiscontinuityTime value."
        ::= { rprIfEntry 21 }

    -- RPR statistics management table
    --
    -- 1.0.8802.17.1.1.1.1.2
    rprIfStatsControlTable OBJECT-TYPE
        SYNTAX SEQUENCE OF RprIfStatsControlEntry
        MAX-ACCESS not-accessible
        STATUS current
        DESCRIPTION
            "The RPR statistics management table,
            controls the collection, duration, clearance, and status
            of the MAC statistics.
            The usage of this table is as follows:
            1. In order to clear period of counters (or all periods) of
            specific counting point (or all counting points) of the
            RPR MAC, the user should first set the
            rprIfStatsControlPeriodClear item to specify the period
            that he would like to clear, and the
            rprIfStatsControlCountPointClear item to specify the
            counting point on which he would like to perform the
            statistics clearance.
            In case that the user specified 'clearSpecificInterval'
            in the rprIfStatsControlPeriodClear item, the user should
            also set the specific interval to clear by setting
            rprIfStatsControlIntervalClear.
            After setting these items, the user can activate the
            clear operation by setting rprIfStatsControlCommitClear
            item to 'commit'.
            The status of the clear operation (done of failed) is
            indicated by the returned value of rprIfStatsControlCommitClear
            item.
            2. Setting rprIfStatsControlPeriodClear to 'clearAllIntervals' and
            rprIfStatsControlCountPointClear to 'clearWest' (for example)
            will clear all current and previous intervals, and day
            counters of the west side of the RPR MAC.
            3. The IntervalValidData of cleared interval should be set to false.
            All read-write attributes in this table are volatile,
            i.e. will be cleared on system reset."
        ::= { rprGeneral 2 }

    -- 1.0.8802.17.1.1.1.1.2.1
    rprIfStatsControlEntry OBJECT-TYPE
        SYNTAX RprIfStatsControlEntry
        MAX-ACCESS not-accessible
        STATUS current
        DESCRIPTION
            "One such entry for every interface in the ifTable which
            has an ifType of RPR interface."
        INDEX { rprIfStatsControlIfIndex }
        ::= { rprIfStatsControlTable 1 }

    RprIfStatsControlEntry ::=
        SEQUENCE {
            rprIfStatsControlIfIndex
                InterfaceIndex,
            rprIfStatsControlPeriodClear
                INTEGER,
            rprIfStatsControlCountPointClear
                INTEGER,
            rprIfStatsControlIntervalClear
                Unsigned32,
            rprIfStatsControlCommitClear
                INTEGER,
            rprIfStatsControlTimeElapsed
                Unsigned32,
            rprIfStatsControlValidIntervals
                Unsigned32
         }

    -- 1.0.8802.17.1.1.1.1.2.1.1
    rprIfStatsControlIfIndex OBJECT-TYPE
        SYNTAX InterfaceIndex
        MAX-ACCESS not-accessible
        STATUS current
        DESCRIPTION
            "The ifIndex of this RPR interface."
        REFERENCE
            "RFC 2863, ifIndex"
        ::= { rprIfStatsControlEntry 1 }

    -- 1.0.8802.17.1.1.1.1.2.1.2
    rprIfStatsControlPeriodClear OBJECT-TYPE
        SYNTAX INTEGER
            {
            idle(1),
            clearAllIntervals(2),
            clearCurrent(3),
            clearIntervals(4),
            clearSpecificInterval(5)
            }
        MAX-ACCESS read-write
        STATUS current
        DESCRIPTION
            "This attribute allows for some or all of the
            interval statistics for this RPR MAC to be cleared.
            It does not affect the values of the running counters
            or the counter values reported through the interface MIB.
            clearSpecificInterval clears the interval indicated by
            rprIfStatsControlIntervalClear.
            Default value for period clear is idle."
        DEFVAL { idle }
        ::= { rprIfStatsControlEntry 2 }

    -- 1.0.8802.17.1.1.1.1.2.1.3
    rprIfStatsControlCountPointClear OBJECT-TYPE
        SYNTAX INTEGER
            {
            clearAll(1),
            clearWest(2),
            clearEast(3),
            clearClient(4)
            }
        MAX-ACCESS read-write
        STATUS current
        DESCRIPTION
            "This attribute allows for a specific counting point of the
            RPR MAC or all of the RPR MAC counting points to be cleared
            on rprIfStatsControlPeriodClear request.
            Default value for Interface to clear is clearAll, i.e.
            clear statistics of all interfaces."
        DEFVAL { clearAll }
        ::= { rprIfStatsControlEntry 3 }

    -- 1.0.8802.17.1.1.1.1.2.1.4
    rprIfStatsControlIntervalClear OBJECT-TYPE
        SYNTAX Unsigned32 (1..96)
        MAX-ACCESS read-write
        STATUS current
        DESCRIPTION
            "The statistics interval number to clear.
            The interval identified by 1 is the most recently completed
            15 minute interval, and interval identified by N is the
            interval immediately preceding the one identified by N-1.
            Setting rprIfStatsControlPeriodClear to clearSpecificInterval will
            clear the interval that is indicated by this object."
        ::= { rprIfStatsControlEntry 4 }

    -- write only
    -- read only
    -- read only
    -- 1.0.8802.17.1.1.1.1.2.1.5
    rprIfStatsControlCommitClear OBJECT-TYPE
        SYNTAX INTEGER
            {
            commit(1),
            commitDone(2),
            commitFailed(3)
            }
        MAX-ACCESS read-write
        STATUS current
        DESCRIPTION
            "Sends a commit with input parameters to specify the
            Period (rprIfStatsControlPeriodClear),
            count point (rprIfStatsControlCountPointClear) and
            specific interval (rprIfStatsControlIntervalClear) to clear.
            If the clear operation succeeds this attribute will have
            the value commitDone(2) when read.
            If the clear operation fails this attribute will have
            the value commitFailed(3) when read."
        ::= { rprIfStatsControlEntry 5 }

    -- 1.0.8802.17.1.1.1.1.2.1.6
    rprIfStatsControlTimeElapsed OBJECT-TYPE
        SYNTAX Unsigned32 (0..899)
        UNITS "Seconds"
        MAX-ACCESS read-only
        STATUS current
        DESCRIPTION
            "The number of seconds, including partial seconds, that
            have elapsed since the beginning of the current
            measurement interval. If, for some reason, such as an
            adjustment in the system's time-of-day clock, the current
            interval exceeds the maximum value, the agent will return
            the maximum value."
        ::= { rprIfStatsControlEntry 6 }

    -- 1.0.8802.17.1.1.1.1.2.1.7
    rprIfStatsControlValidIntervals OBJECT-TYPE
        SYNTAX Unsigned32 (0..96)
        MAX-ACCESS read-only
        STATUS current
        DESCRIPTION
            "The number of previous 15-minute intervals for
            which data was collected.
            An RPR interface must be capable of supporting at least n
            intervals.
            The minimum value of n is 4. The default of n is 32.
            The maximum value of n is 96.
            The value will be <n> unless the measurement was
            (re-)started within the last (<n>*15) minutes, in which
            case the value will be the number of complete 15
            minute intervals for which the agent has at least
            some data. In certain cases (e.g., in the case
            where the agent is a proxy) it is possible that some
            intervals are unavailable. In this case, this
            interval is the maximum interval number for
            which data is available. "
        ::= { rprIfStatsControlEntry 7 }

    -- RPR span table
    --
    -- 1.0.8802.17.1.1.1.1.3
    rprSpanTable OBJECT-TYPE
        SYNTAX SEQUENCE OF RprSpanEntry
        MAX-ACCESS not-accessible
        STATUS current
        DESCRIPTION
            "The RPR interface Span table.
            All read-write attributes in this table are non-volatile,
            i.e. will be retained across system reset."
        ::= { rprGeneral 3 }

    -- 1.0.8802.17.1.1.1.1.3.1
    rprSpanEntry OBJECT-TYPE
        SYNTAX RprSpanEntry
        MAX-ACCESS not-accessible
        STATUS current
        DESCRIPTION
            "One such entry for every span of an RPR interface."
        INDEX { rprSpanIfIndex, rprSpanId }
        ::= { rprSpanTable 1 }

    RprSpanEntry ::=
        SEQUENCE {
            rprSpanIfIndex
                InterfaceIndex,
            rprSpanId
                RprSpan,
            rprSpanLowerLayerIfIndex
                InterfaceIndexOrZero,
            rprSpanTotalRingletReservedRate
                Unsigned32,
            rprSpanCurrentStatus
                BITS,
            rprSpanLastChange
                TimeStamp,
            rprSpanChanges
                Counter32
         }

    -- 1.0.8802.17.1.1.1.1.3.1.1
    rprSpanIfIndex OBJECT-TYPE
        SYNTAX InterfaceIndex
        MAX-ACCESS not-accessible
        STATUS current
        DESCRIPTION
            "The ifIndex of this RPR interface."
        REFERENCE
            "RFC 2863, ifIndex"
        ::= { rprSpanEntry 1 }

    -- 1.0.8802.17.1.1.1.1.3.1.2
    rprSpanId OBJECT-TYPE
        SYNTAX RprSpan
        MAX-ACCESS not-accessible
        STATUS current
        DESCRIPTION
            "Indicates the span interface of the RPR MAC. Each RPR
            span is connected to both ringlet0 and ringlet1.
            The east span receives from ringlet1 and transmits through
            ringlet0.
            The west span receives from ringlet0 and transmits through
            ringlet1."
        REFERENCE
            "IEEE 802.17 Subclause 7.2.2, myRi"
        ::= { rprSpanEntry 2 }

    -- 1.0.8802.17.1.1.1.1.3.1.3
    rprSpanLowerLayerIfIndex OBJECT-TYPE
        SYNTAX InterfaceIndexOrZero
        MAX-ACCESS read-only
        STATUS current
        DESCRIPTION
            "The ifIndex of interface which is below the RPR layer in this
            span. A value of zero indicates an interface index that has
            yet to be determined"
        REFERENCE
            "RFC 2863, ifIndex"
        ::= { rprSpanEntry 3 }

    -- 1.0.8802.17.1.1.1.1.3.1.4
    rprSpanTotalRingletReservedRate OBJECT-TYPE
        SYNTAX Unsigned32
        UNITS "Mb/s"
        MAX-ACCESS read-only
        STATUS current
        DESCRIPTION
            "The total reserved subclassA0 bandwidth on the ringlet.
            This variable is used by the fairness module
            to determine the total reclaimable bandwidth."
        REFERENCE
            "IEEE 802.17 Subclause 11.2.4, unreservedRate"
        ::= { rprSpanEntry 4 }

    -- 1.0.8802.17.1.1.1.1.3.1.5
    rprSpanCurrentStatus OBJECT-TYPE
        SYNTAX BITS
            {
            keepAliveTimeout(0),
            miscabling(1),
            phyLinkDegrade(2),
            phyLinkFail(3)
            }
        MAX-ACCESS read-only
        STATUS current
        DESCRIPTION
            "Indicates the current status of the RPR span.
            this attribute is used to generate alarm to the management system."
        REFERENCE
            "IEEE 802.17 Subclause 11.2.3, keepaliveTime, 11.2.9, miscablingDefect,
            and 8.2.3.2, LINK_STATUS"
        ::= { rprSpanEntry 5 }

    -- 1.0.8802.17.1.1.1.1.3.1.6
    rprSpanLastChange OBJECT-TYPE
        SYNTAX TimeStamp
        MAX-ACCESS read-only
        STATUS current
        DESCRIPTION
            "The value of sysUpTime at the time when any of the following
            attributes changes:
            rprSpanCurrentStatus,
            rprSpanProtectionNeighborValid, rprSpanProtectionHoldOffTimer,
            rprSpanProtectionCommand, rprSpanProtectionCount."
        ::= { rprSpanEntry 6 }

    -- 1.0.8802.17.1.1.1.1.3.1.7
    rprSpanChanges OBJECT-TYPE
        SYNTAX Counter32
        MAX-ACCESS read-only
        STATUS current
        DESCRIPTION
            "Indicates number of times rprSpanLastChange changed.
            The discontinued counter value is indicated
            by the ifCounterDiscontinuityTime value."
        ::= { rprSpanEntry 7 }

    -- RPR span protection table
    --
    -- 1.0.8802.17.1.1.1.1.4
    rprSpanProtectionTable OBJECT-TYPE
        SYNTAX SEQUENCE OF RprSpanProtectionEntry
        MAX-ACCESS not-accessible
        STATUS current
        DESCRIPTION
            "The RPR interface Span protection management table.
            All read-write attributes in this table are non-volatile,
            i.e. will be retained across system reset."
        ::= { rprGeneral 4 }

    -- 1.0.8802.17.1.1.1.1.4.1
    rprSpanProtectionEntry OBJECT-TYPE
        SYNTAX RprSpanProtectionEntry
        MAX-ACCESS not-accessible
        STATUS current
        DESCRIPTION
            "One such entry for every span of an RPR interface."
        INDEX { rprSpanProtectionIfIndex, rprSpanProtectionSpan }
        ::= { rprSpanProtectionTable 1 }

    RprSpanProtectionEntry ::=
        SEQUENCE {
            rprSpanProtectionIfIndex
                InterfaceIndex,
            rprSpanProtectionSpan
                RprSpan,
            rprSpanProtectionNeighborValid
                TruthValue,
            rprSpanProtectionHoldOffTimer
                Unsigned32,
            rprSpanProtectionCommand
                INTEGER,
            rprSpanProtectionCount
                Counter32,
            rprSpanProtectionDuration
                Counter32,
            rprSpanProtectionLastActivationTime
                TimeStamp
         }

    -- 1.0.8802.17.1.1.1.1.4.1.1
    rprSpanProtectionIfIndex OBJECT-TYPE
        SYNTAX InterfaceIndex
        MAX-ACCESS not-accessible
        STATUS current
        DESCRIPTION
            "The ifIndex of this RPR interface."
        REFERENCE
            "RFC 2863, ifIndex"
        ::= { rprSpanProtectionEntry 1 }

    -- 1.0.8802.17.1.1.1.1.4.1.2
    rprSpanProtectionSpan OBJECT-TYPE
        SYNTAX RprSpan
        MAX-ACCESS not-accessible
        STATUS current
        DESCRIPTION
            "The Span for this entry."
        REFERENCE
            "IEEE 802.17 Subclause 7.2.2. myRi"
        ::= { rprSpanProtectionEntry 2 }

    -- 1.0.8802.17.1.1.1.1.4.1.3
    rprSpanProtectionNeighborValid OBJECT-TYPE
        SYNTAX TruthValue
        MAX-ACCESS read-only
        STATUS current
        DESCRIPTION
            "Indicates whether the neighbor address is active or former.
            true value for active, false for former"
        REFERENCE
            "IEEE 802.17 Subclause 11.2.5, lastNeighborMac"
        ::= { rprSpanProtectionEntry 3 }

    -- 1.0.8802.17.1.1.1.1.4.1.4
    rprSpanProtectionHoldOffTimer OBJECT-TYPE
        SYNTAX Unsigned32 (0..500)
        UNITS "milliseconds"
        MAX-ACCESS read-write
        STATUS current
        DESCRIPTION
            "The period that RPR gives to lower layer to perform
            protection, before it activates its protection mechanism.
            Default value of hold off timer is 0."
        REFERENCE
            "IEEE 802.17 Subclause 11.2.3, holdOffTimeout"
        DEFVAL { 0 }
        ::= { rprSpanProtectionEntry 4 }

    -- 1.0.8802.17.1.1.1.1.4.1.5
    rprSpanProtectionCommand OBJECT-TYPE
        SYNTAX INTEGER
            {
            idle(1),
            manualSwitch(2),
            forcedSwitch(3)
            }
        MAX-ACCESS read-write
        STATUS current
        DESCRIPTION
            "The protection mode requested by management for the local
            station that can affect the protection status of the RPR
            station, according to the set of rules describing the RPR
            protection.
            When read, this object returns the last command written
            unless it has been preempted, or idle if no command has been
            written to this interface span since initialization.
            There is no pending of commands, that is if a command has
            been preempted by a failure, when the failure clears the
            command is not executed.
            If the command cannot be executed because an equal or \
            higher priority request is in effect, an error is returned.
            writing idle to a span that has no pending protection
            command, has no affect. An idle clears an active WTR state.
            The protection commands (arranged in ascending priority
            order) are:
            idle
            This command clears the protection for the specified
            interface span.
            This value should be returned by a read request when no
            protection command has been written to the object.
            manualSwitch
            A protection command on each end of a specified span. This
            command doesn't have precedence over automatic protection,
            and therefore it can't preempt
            an existing automatic protection request.
            forcedSwitch
            A command on each end of a specified span. This command has
            precedence over automatic protection, and therefore it can
            preempt an existing automatic protection request.
            Default value of protection command is idle."
        REFERENCE
            "IEEE 802.17 Subclause 11.2.3, adminRequestProtection"
        DEFVAL { idle }
        ::= { rprSpanProtectionEntry 5 }

    -- 1.0.8802.17.1.1.1.1.4.1.6
    rprSpanProtectionCount OBJECT-TYPE
        SYNTAX Counter32
        MAX-ACCESS read-only
        STATUS current
        DESCRIPTION
            "The number of transitions from idle state to active
            protection state.
            The discontinued counter value is indicated
            by the ifCounterDiscontinuityTime value."
        REFERENCE
            "IEEE 802.17 Subclause 11.6.5.5, IndicateEdgeState()"
        ::= { rprSpanProtectionEntry 6 }

    -- 1.0.8802.17.1.1.1.1.4.1.7
    rprSpanProtectionDuration OBJECT-TYPE
        SYNTAX Counter32
        UNITS "seconds"
        MAX-ACCESS read-only
        STATUS current
        DESCRIPTION
            "The total amount of time protection was active on the
            span interface.
            The discontinued counter value is indicated
            by the ifCounterDiscontinuityTime value."
        REFERENCE
            "IEEE 802.17 Subclause 11.6.5.5, IndicateEdgeState()"
        ::= { rprSpanProtectionEntry 7 }

    -- 1.0.8802.17.1.1.1.1.4.1.8
    rprSpanProtectionLastActivationTime OBJECT-TYPE
        SYNTAX TimeStamp
        MAX-ACCESS read-only
        STATUS current
        DESCRIPTION
            "The value of sysUpTime at the time of the last protection
            activation."
        REFERENCE
            "IEEE 802.17 Subclause 11.6.5.5, IndicateEdgeState()"
        ::= { rprSpanProtectionEntry 8 }

    -- RPR changes summary group
    --
    -- 1.0.8802.17.1.1.1.1.5
    rprIfChangeSummaryObject OBJECT IDENTIFIER ::= { rprGeneral 5 }

    -- 1.0.8802.17.1.1.1.1.5.1
    rprIfChangeSummaryNumInterfaces OBJECT-TYPE
        SYNTAX Unsigned32
        MAX-ACCESS read-only
        STATUS current
        DESCRIPTION
            "Number of RPR interfaces on this device."
        ::= { rprIfChangeSummaryObject 1 }

    -- 1.0.8802.17.1.1.1.1.5.2
    rprIfChangeSummaryIfLastChange OBJECT-TYPE
        SYNTAX TimeStamp
        MAX-ACCESS read-only
        STATUS current
        DESCRIPTION
            "Latest timestamp when any instance of rprIfLastChange changed."
        ::= { rprIfChangeSummaryObject 2 }

    -- 1.0.8802.17.1.1.1.1.5.3
    rprIfChangeSummaryIfChanges OBJECT-TYPE
        SYNTAX Counter32
        MAX-ACCESS read-only
        STATUS current
        DESCRIPTION
            "Number of times any instance of rprIfChanges changed.
            The discontinued counter value is indicated
            by the ifCounterDiscontinuityTime value."
        ::= { rprIfChangeSummaryObject 3 }

    -- 1.0.8802.17.1.1.1.1.5.4
    rprIfChangeSummarySpanLastChange OBJECT-TYPE
        SYNTAX TimeStamp
        MAX-ACCESS read-only
        STATUS current
        DESCRIPTION
            "Latest timestamp when any instance of rprSpanLastChange changed."
        ::= { rprIfChangeSummaryObject 4 }

    -- 1.0.8802.17.1.1.1.1.5.5
    rprIfChangeSummarySpanChanges OBJECT-TYPE
        SYNTAX Counter32
        MAX-ACCESS read-only
        STATUS current
        DESCRIPTION
            "Number of times any instance of rprSpanChanges changed.
            The discontinued counter value is indicated
            by the ifCounterDiscontinuityTime value."
        ::= { rprIfChangeSummaryObject 5 }

    -- 1.0.8802.17.1.1.1.1.5.6
    rprIfChangeSummaryFairnessLastChange OBJECT-TYPE
        SYNTAX TimeStamp
        MAX-ACCESS read-only
        STATUS current
        DESCRIPTION
            "Latest timestamp when any instance of rprFairnessLastChange changed."
        ::= { rprIfChangeSummaryObject 6 }

    -- 1.0.8802.17.1.1.1.1.5.7
    rprIfChangeSummaryFairnessChanges OBJECT-TYPE
        SYNTAX Counter32
        MAX-ACCESS read-only
        STATUS current
        DESCRIPTION
            "Number of times any instance of rprFairnessChanges changed.
            The discontinued counter value is indicated
            by the ifCounterDiscontinuityTime value."
        ::= { rprIfChangeSummaryObject 7 }

    -- 1.0.8802.17.1.1.1.2
    rprProtocols OBJECT IDENTIFIER ::= { rprObjects 2 }

    -- RPR topology table
    --
    -- 1.0.8802.17.1.1.1.2.1
    rprTopoImageTable OBJECT-TYPE
        SYNTAX SEQUENCE OF RprTopoImageEntry
        MAX-ACCESS not-accessible
        STATUS current
        DESCRIPTION
            "A topology map that details the list of stations on the RPR
            ringlets.
            All attributes in this table are volatile,
            i.e. will be cleared on system reset."
        ::= { rprProtocols 1 }

    -- 1.0.8802.17.1.1.1.2.1.1
    rprTopoImageEntry OBJECT-TYPE
        SYNTAX RprTopoImageEntry
        MAX-ACCESS not-accessible
        STATUS current
        DESCRIPTION
            "Each entry contains information specific to a particular
            station on the ring.
            The table has at least one entry for the station itself,
            this entry indicates zero hops on each ringlet."
        INDEX { rprTopoImageIfIndex, rprTopoImageMacAddress }
        ::= { rprTopoImageTable 1 }

    RprTopoImageEntry ::=
        SEQUENCE {
            rprTopoImageIfIndex
                InterfaceIndex,
            rprTopoImageMacAddress
                MacAddress,
            rprTopoImageSecMacAddress1
                MacAddress,
            rprTopoImageSecMacAddress2
                MacAddress,
            rprTopoImageStationIfIndex
                InterfaceIndex,
            rprTopoImageStationName
                SnmpAdminString,
            rprTopoImageInetAddressType
                InetAddressType,
            rprTopoImageInetAddress
                InetAddress,
            rprTopoImageCapability
                BITS,
            rprTopoImageRinglet0Hops
                Integer32,
            rprTopoImageRinglet0ReservedRate
                Unsigned32,
            rprTopoImageRinglet1Hops
                Integer32,
            rprTopoImageRinglet1ReservedRate
                Unsigned32,
            rprTopoImageWestProtectionStatus
                RprProtectionStatus,
            rprTopoImageWestWeight
                Unsigned32,
            rprTopoImageEastProtectionStatus
                RprProtectionStatus,
            rprTopoImageEastWeight
                Unsigned32,
            rprTopoImageStatus
                BITS
         }

    -- 1.0.8802.17.1.1.1.2.1.1.1
    rprTopoImageIfIndex OBJECT-TYPE
        SYNTAX InterfaceIndex
        MAX-ACCESS not-accessible
        STATUS current
        DESCRIPTION
            "The ifIndex of this RPR interface."
        REFERENCE
            "RFC 2863, ifIndex"
        ::= { rprTopoImageEntry 1 }

    -- 1.0.8802.17.1.1.1.2.1.1.2
    rprTopoImageMacAddress OBJECT-TYPE
        SYNTAX MacAddress
        MAX-ACCESS not-accessible
        STATUS current
        DESCRIPTION
            "The 48-bit MAC address of the station."
        REFERENCE
            "IEEE 802.17 Subclause 11.2.6, macAddress"
        ::= { rprTopoImageEntry 2 }

    -- 1.0.8802.17.1.1.1.2.1.1.3
    rprTopoImageSecMacAddress1 OBJECT-TYPE
        SYNTAX MacAddress
        MAX-ACCESS read-only
        STATUS current
        DESCRIPTION
            "The 48-bit first secondary MAC address of the station.
            Default and unused value is FF:FF:FF:FF:FF:FF"
        REFERENCE
            "IEEE 802.17 Subclause 11.2.6, secMac"
        ::= { rprTopoImageEntry 3 }

    -- 1.0.8802.17.1.1.1.2.1.1.4
    rprTopoImageSecMacAddress2 OBJECT-TYPE
        SYNTAX MacAddress
        MAX-ACCESS read-only
        STATUS current
        DESCRIPTION
            "The 48-bit second secondary MAC address of the station.
            Default and unused value is FF:FF:FF:FF:FF:FF"
        REFERENCE
            "IEEE 802.17 Subclause 11.2.6, secMac"
        ::= { rprTopoImageEntry 4 }

    -- 1.0.8802.17.1.1.1.2.1.1.5
    rprTopoImageStationIfIndex OBJECT-TYPE
        SYNTAX InterfaceIndex
        MAX-ACCESS read-only
        STATUS current
        DESCRIPTION
            "The station ifIndex."
        REFERENCE
            "IEEE 802.17 Subclause 11.2.6, interfaceIndex"
        ::= { rprTopoImageEntry 5 }

    -- 1.0.8802.17.1.1.1.2.1.1.6
    rprTopoImageStationName OBJECT-TYPE
        SYNTAX SnmpAdminString
        MAX-ACCESS read-only
        STATUS current
        DESCRIPTION
            "The operator assigned station name."
        REFERENCE
            "IEEE 802.17 Subclause 11.2.6, stationName"
        ::= { rprTopoImageEntry 6 }

    -- 1.0.8802.17.1.1.1.2.1.1.7
    rprTopoImageInetAddressType OBJECT-TYPE
        SYNTAX InetAddressType
        MAX-ACCESS read-only
        STATUS current
        DESCRIPTION
            "Denotes the address type of the station INET address
            It should be set to 'unknown' if station INET address
            is not known."
        REFERENCE
            "IEEE 802.17 Subclause 11.2.6, managementAddressType"
        ::= { rprTopoImageEntry 7 }

    -- 1.0.8802.17.1.1.1.2.1.1.8
    rprTopoImageInetAddress OBJECT-TYPE
        SYNTAX InetAddress
        MAX-ACCESS read-only
        STATUS current
        DESCRIPTION
            "This object contains the value of of the station
            IP (v4 or V6) address.
            The format of this address is specified by the value
            of the corresponding rprTopoImageInetAddressType object.
            If the address type is unknown, then this object contains the
            zero-length OCTET-STRING."
        REFERENCE
            "IEEE 802.17 Subclause 11.2.6, managementIpAddr"
        ::= { rprTopoImageEntry 8 }

    -- 1.0.8802.17.1.1.1.2.1.1.9
    rprTopoImageCapability OBJECT-TYPE
        SYNTAX BITS
            {
            jumboFrames(0),
            wrapProtection(1),
            supportsConservativeFairness(2)
            }
        MAX-ACCESS read-only
        STATUS current
        DESCRIPTION
            "Indicates the capabilities that the MAC supports.
            jumboFrames - Indicates whether the MAC capable of receiving,
            transmitting and transiting jumbo frames.
            wrapProtection - Indicates whether the MAC configured to wrap
            protection.
            supportsConservativeFairness - indicates the MAC supports
            conservative fairness algorithm."
        REFERENCE
            "IEEE 802.17 Subclause 11.2.6, jumboPrefer, protConfig, and
            conservativeMode"
        ::= { rprTopoImageEntry 9 }

    -- 1.0.8802.17.1.1.1.2.1.1.10
    rprTopoImageRinglet0Hops OBJECT-TYPE
        SYNTAX Integer32
        MAX-ACCESS read-only
        STATUS current
        DESCRIPTION
            "The number of hops to this station through ringlet0.
            The self station is indicated with zero hops.
            A non reachable station is indicated with -1 value."
        REFERENCE
            "IEEE 802.17 Subclause 11.2.6, hops"
        ::= { rprTopoImageEntry 10 }

    -- 1.0.8802.17.1.1.1.2.1.1.11
    rprTopoImageRinglet0ReservedRate OBJECT-TYPE
        SYNTAX Unsigned32
        UNITS "Mb/s"
        MAX-ACCESS read-only
        STATUS current
        DESCRIPTION
            "The amount of A0 traffic that this station adds on ringlet0,
            in Mb/s units."
        REFERENCE
            "IEEE 802.17 Subclause 11.2.6, reservedRate"
        ::= { rprTopoImageEntry 11 }

    -- 1.0.8802.17.1.1.1.2.1.1.12
    rprTopoImageRinglet1Hops OBJECT-TYPE
        SYNTAX Integer32
        MAX-ACCESS read-only
        STATUS current
        DESCRIPTION
            "The number of hops to this station through ringlet1.
            The self station is indicated with zero hops.
            A non reachable station is indicated with -1 value."
        REFERENCE
            "IEEE 802.17 Subclause 11.2.6, hops"
        ::= { rprTopoImageEntry 12 }

    -- 1.0.8802.17.1.1.1.2.1.1.13
    rprTopoImageRinglet1ReservedRate OBJECT-TYPE
        SYNTAX Unsigned32
        UNITS "Mb/s"
        MAX-ACCESS read-only
        STATUS current
        DESCRIPTION
            "The amount of A0 traffic that this station adds on ringlet1,
            in Mb/s units."
        REFERENCE
            "IEEE 802.17 Subclause 11.2.6, reservedRate"
        ::= { rprTopoImageEntry 13 }

    -- 1.0.8802.17.1.1.1.2.1.1.14
    rprTopoImageWestProtectionStatus OBJECT-TYPE
        SYNTAX RprProtectionStatus
        MAX-ACCESS read-only
        STATUS current
        DESCRIPTION
            "The current protection status of the West span."
        REFERENCE
            "IEEE 802.17 Subclause 11.2.6, spanProtState"
        ::= { rprTopoImageEntry 14 }

    -- 1.0.8802.17.1.1.1.2.1.1.15
    rprTopoImageWestWeight OBJECT-TYPE
        SYNTAX Unsigned32 (1..255)
        MAX-ACCESS read-only
        STATUS current
        DESCRIPTION
            "The weight of the station on the west span.
            used for weighted fairness."
        REFERENCE
            "IEEE 802.17 Subclause 11.2.6, weight"
        ::= { rprTopoImageEntry 15 }

    -- 1.0.8802.17.1.1.1.2.1.1.16
    rprTopoImageEastProtectionStatus OBJECT-TYPE
        SYNTAX RprProtectionStatus
        MAX-ACCESS read-only
        STATUS current
        DESCRIPTION
            "The current protection status of the east span."
        REFERENCE
            "IEEE 802.17 Subclause 11.2.6, spanProtState"
        ::= { rprTopoImageEntry 16 }

    -- 1.0.8802.17.1.1.1.2.1.1.17
    rprTopoImageEastWeight OBJECT-TYPE
        SYNTAX Unsigned32 (1..255)
        MAX-ACCESS read-only
        STATUS current
        DESCRIPTION
            "The weight of the station on the east span.
            Used for weighted fairness."
        REFERENCE
            "IEEE 802.17 Subclause 11.2.6, weight"
        ::= { rprTopoImageEntry 17 }

    -- 1.0.8802.17.1.1.1.2.1.1.18
    rprTopoImageStatus OBJECT-TYPE
        SYNTAX BITS
            {
            reachableRinglet0(0),
            reachableRinglet1(1),
            wrapActiveWest(2),
            wrapActiveEast(3),
            receivedBadFcs(4),
            receivedMultichokeFairness(5)
            }
        MAX-ACCESS read-only
        STATUS current
        DESCRIPTION
            "Status of the station,
            the reachability of station through ringlet0 and ringlet1,
            wrap active on the station spans,
            events of reception frames with bad FCS,
            events of reception multichoke fairness frames."
        REFERENCE
            "IEEE 802.17 Subclause 11.2.6, reachable, protConfig, spanProtState,
            badFcsUser, and multichokeUser"
        ::= { rprTopoImageEntry 18 }

    -- The RPR Fairness table
    --
    -- 1.0.8802.17.1.1.1.2.2
    rprFairnessTable OBJECT-TYPE
        SYNTAX SEQUENCE OF RprFairnessEntry
        MAX-ACCESS not-accessible
        STATUS current
        DESCRIPTION
            "A table of RPR Fairness per RPR span.
            All read-write attributes in this table are non-volatile,
            i.e. will be retained across system reset."
        ::= { rprProtocols 2 }

    -- 1.0.8802.17.1.1.1.2.2.1
    rprFairnessEntry OBJECT-TYPE
        SYNTAX RprFairnessEntry
        MAX-ACCESS not-accessible
        STATUS current
        DESCRIPTION
            "A fairness parameters for a particular ringlet of the
            an RPR interface."
        INDEX { rprFairnessIfIndex, rprFairnessRinglet }
        ::= { rprFairnessTable 1 }

    RprFairnessEntry ::=
        SEQUENCE {
            rprFairnessIfIndex
                InterfaceIndex,
            rprFairnessRinglet
                INTEGER,
            rprFairnessRingletWeight
                Unsigned32,
            rprFairnessReservedRate
                Unsigned32,
            rprFairnessMaxAllowed
                Unsigned32,
            rprFairnessAgeCoef
                Unsigned32,
            rprFairnessRampCoef
                Unsigned32,
            rprFairnessLpCoef
                Unsigned32,
            rprFairnessAdvertisementRatio
                Unsigned32,
            rprFairnessMcffReportCoef
                Unsigned32,
            rprFairnessActiveWeightsCoef
                Unsigned32,
            rprFairnessSTQHighThreshold
                Unsigned32,
            rprFairnessSTQMedThreshold
                Unsigned32,
            rprFairnessSTQLowThreshold
                Unsigned32,
            rprFairnessRateHighThreshold
                Unsigned32,
            rprFairnessRateLowThreshold
                Unsigned32,
            rprFairnessResetWaterMarks
                INTEGER,
            rprFairnessSTQHighWaterMark
                Unsigned32,
            rprFairnessSTQLowWaterMark
                Unsigned32,
            rprFairnessLastChange
                TimeStamp,
            rprFairnessChanges
                Counter32
         }

    -- 1.0.8802.17.1.1.1.2.2.1.1
    rprFairnessIfIndex OBJECT-TYPE
        SYNTAX InterfaceIndex
        MAX-ACCESS not-accessible
        STATUS current
        DESCRIPTION
            "The ifIndex of this RPR interface."
        REFERENCE
            "RFC 2863, ifIndex"
        ::= { rprFairnessEntry 1 }

    -- 1.0.8802.17.1.1.1.2.2.1.2
    rprFairnessRinglet OBJECT-TYPE
        SYNTAX INTEGER
            {
            ringlet0(1),
            ringlet1(2)
            }
        MAX-ACCESS not-accessible
        STATUS current
        DESCRIPTION
            "The ringlet for which this row contains information.
            ringlet0 is the transmission of the east span and the
            reception of the west span,
            ringlet1 is the transmission of the west span and the
            reception of the east span"
        REFERENCE
            "IEEE 802.17 Subclause 7.2.2, myRi"
        ::= { rprFairnessEntry 2 }

    -- 1.0.8802.17.1.1.1.2.2.1.3
    rprFairnessRingletWeight OBJECT-TYPE
        SYNTAX Unsigned32 (1..255)
        MAX-ACCESS read-write
        STATUS current
        DESCRIPTION
            "Weight assigned to fairness to permit the scaling of
            fair rate values among stations on the ringlet.
            This allows one station to use a larger share of available
            capacity than another station without violating fairness
            principles.
            The allowed range is [1, 255]. The default value is 1."
        REFERENCE
            "IEEE 802.17 Subclause 10.2.2, localWeight"
        DEFVAL { 1 }
        ::= { rprFairnessEntry 3 }

    -- 1.0.8802.17.1.1.1.2.2.1.4
    rprFairnessReservedRate OBJECT-TYPE
        SYNTAX Unsigned32
        UNITS "Mb/s"
        MAX-ACCESS read-write
        STATUS current
        DESCRIPTION
            "The amount of A0 traffic that this station adds that ringlet,
            in Mb/s units.
            Default value for A0 reserved rate is 0 Mb/s."
        REFERENCE
            "IEEE 802.17 Subclause 11.2.4, reservedRate"
        DEFVAL { 0 }
        ::= { rprFairnessEntry 4 }

    -- 1.0.8802.17.1.1.1.2.2.1.5
    rprFairnessMaxAllowed OBJECT-TYPE
        SYNTAX Unsigned32
        UNITS "Mb/s"
        MAX-ACCESS read-write
        STATUS current
        DESCRIPTION
            "The maximum value that the station is allowed to transmit
            local excess traffic to the ringlet. The default value
            is the physical ring rate."
        REFERENCE
            "IEEE 802.17 Subclause 10.2.2, maxAllowedRate"
        ::= { rprFairnessEntry 5 }

    -- 1.0.8802.17.1.1.1.2.2.1.6
    rprFairnessAgeCoef OBJECT-TYPE
        SYNTAX Unsigned32 (0..4)
        MAX-ACCESS read-write
        STATUS current
        DESCRIPTION
            "The coefficient used by the aging procedure to specify
            the relative weights assigned to
            (a) the change in the value of a rate-counter during
            the most recent agingInterval and
            (b) the value of the rate-counter at the end of the previous
            agingInterval.
            The value is interpreted as 2 raised to the power
            specified by this attribute.
            The default value is 2, giving an aging coefficient
            of 2**2, or 4."
        REFERENCE
            "IEEE 802.17 Subclause 10.2.2, ageCoef"
        DEFVAL { 2 }
        ::= { rprFairnessEntry 6 }

    -- 1.0.8802.17.1.1.1.2.2.1.7
    rprFairnessRampCoef OBJECT-TYPE
        SYNTAX Unsigned32 (4..9)
        MAX-ACCESS read-write
        STATUS current
        DESCRIPTION
            "The coefficient used for ramping a rate.
            The value is interpreted as 2 raised to the power
            specified by this attribute.
            The default value is 6, giving a low-pass coefficient
            of 2**6, or 64."
        REFERENCE
            "IEEE 802.17 Subclause 10.2.2, rampUpCoef"
        DEFVAL { 6 }
        ::= { rprFairnessEntry 7 }

    -- 1.0.8802.17.1.1.1.2.2.1.8
    rprFairnessLpCoef OBJECT-TYPE
        SYNTAX Unsigned32 (4..9)
        MAX-ACCESS read-write
        STATUS current
        DESCRIPTION
            "The coefficient used by the low-pass filter procedure
            to specify the relative weights applied to
            (a) the increase in the rate-count value during the most
            recent agingInterval and
            (b) the previous low-pass filtered rate.
            The former is assigned a weight of 1 and the latter a
            weight of (lpCoef-1).
            The value is interpreted as 2 raised to the power
            specified by this attribute.
            The default value is 6, giving a low-pass coefficient
            of 2**6, or 64."
        REFERENCE
            "IEEE 802.17 Subclause 10.2.2, lpCoef"
        DEFVAL { 6 }
        ::= { rprFairnessEntry 8 }

    -- 1.0.8802.17.1.1.1.2.2.1.9
    rprFairnessAdvertisementRatio OBJECT-TYPE
        SYNTAX Unsigned32 (1..40)
        UNITS "0.00025"
        MAX-ACCESS read-write
        STATUS current
        DESCRIPTION
            "The ratio between the link capacity reserved for fairness
            control messages and the total link capacity.
            Default value of fairness advertisement ratio is 5 units
            of 0.00025, i.e 0.00125."
        REFERENCE
            "IEEE 802.17 Subclause 10.2.2, advertisementRatio"
        DEFVAL { 5 }
        ::= { rprFairnessEntry 9 }

    -- 1.0.8802.17.1.1.1.2.2.1.10
    rprFairnessMcffReportCoef OBJECT-TYPE
        SYNTAX Unsigned32 (8..512)
        MAX-ACCESS read-write
        STATUS current
        DESCRIPTION
            "Indicates the number of SCFF advertisingIntervals that
            elapse between the sending of successive MCFFs,
            This value allows the interval between sending MCFFs
            to be established as MCFF_reportingInterval =
            rprFairnessMcffReportCoef * SCFF_avertisingInterval.
            The default value is 10."
        REFERENCE
            "IEEE 802.17 Subclause 10.2.2, reportCoef"
        DEFVAL { 10 }
        ::= { rprFairnessEntry 10 }

    -- 1.0.8802.17.1.1.1.2.2.1.11
    rprFairnessActiveWeightsCoef OBJECT-TYPE
        SYNTAX Unsigned32 (8..512)
        MAX-ACCESS read-write
        STATUS current
        DESCRIPTION
            "Indicates the number of agingIntervals that elapse between
            successive computations of activeWeights.
            This value allows the interval between computations of
            activeWeights to be established as
            activeWeightsInterval = activeWeightsCoef * agingInterval.
            The default value is 64."
        REFERENCE
            "IEEE 802.17 Subclause 10.2.2, activeWeightsCoef"
        DEFVAL { 64 }
        ::= { rprFairnessEntry 11 }

    -- 1.0.8802.17.1.1.1.2.2.1.12
    rprFairnessSTQHighThreshold OBJECT-TYPE
        SYNTAX Unsigned32 (0..1000)
        UNITS "Tenth of percent"
        MAX-ACCESS read-write
        STATUS current
        DESCRIPTION
            "A level of STQ occupancy at or above which CSFE frames are no
            longer admitted. Defined only for a dual transit-queue
            implementation.
            This attribute specifies the high threshold location
            in percentage of the STQ size.
            The allowed range is [2*mtuSize, stqFullThreshold -mtuSize].
            The default value is 0.25*stqFullThreshold."
        REFERENCE
            "IEEE 802.17 Subclause 10.2.2, stqHighThreshold"
        DEFVAL { 250 }
        ::= { rprFairnessEntry 12 }

    -- 1.0.8802.17.1.1.1.2.2.1.13
    rprFairnessSTQMedThreshold OBJECT-TYPE
        SYNTAX Unsigned32 (0..1000)
        UNITS "Tenth of percent"
        MAX-ACCESS read-write
        STATUS current
        DESCRIPTION
            "A level of buffer occupancy in a dual-queue deployment,
            at or above which congestion on the outbound link is declared.
            This attribute specifies the medium threshold location
            in percentage of the STQ size.
            The allowed range is [stqLowThreshold + mtuSize,
            stqHighThreshold - mtuSize].
            The default value is 0.5 * (stqHighThreshold + stqLowThreshold)."
        REFERENCE
            "IEEE 802.17 Subclause 10.2.2, stqMedThreshold"
        DEFVAL { 187 }
        ::= { rprFairnessEntry 13 }

    -- 1.0.8802.17.1.1.1.2.2.1.14
    rprFairnessSTQLowThreshold OBJECT-TYPE
        SYNTAX Unsigned32 (0..1000)
        UNITS "Tenth of percent"
        MAX-ACCESS read-write
        STATUS current
        DESCRIPTION
            "A level of STQ occupancy at or above which congestion on
            the outbound link is imminent.
            Defined only for dual transit-queue implementations.
            This attribute specifies the low threshold location
            in percentage of the STQ size.
            The range is [mtuSize, stqHighThreshold -mtuSize].
            The default value is 0.5*stqHighThreshold."
        REFERENCE
            "IEEE 802.17 Subclause 10.2.2, stqLowThreshold"
        DEFVAL { 125 }
        ::= { rprFairnessEntry 14 }

    -- 1.0.8802.17.1.1.1.2.2.1.15
    rprFairnessRateHighThreshold OBJECT-TYPE
        SYNTAX Unsigned32 (400..990)
        UNITS "Tenth of percent"
        MAX-ACCESS read-write
        STATUS current
        DESCRIPTION
            "Rate at or above which congestion on the outbound link
            is declared.
            The range is [0.4 * unreservedRate, 0.99 * unreservedRate].
            The default value is 0.95 * unreservedRate."
        REFERENCE
            "IEEE 802.17 Subclause 10.2.2, rateHighThreshold"
        DEFVAL { 950 }
        ::= { rprFairnessEntry 15 }

    -- 1.0.8802.17.1.1.1.2.2.1.16
    rprFairnessRateLowThreshold OBJECT-TYPE
        SYNTAX Unsigned32 (500..990)
        UNITS "Tenth of percent"
        MAX-ACCESS read-write
        STATUS current
        DESCRIPTION
            "Rate at or above which congestion on the outbound link
            is imminent.
            The range is [0.5 * rateHighThreshold, 0.99 * rateHighThreshold].
            The default value is 0.9 * rateHighThreshold"
        REFERENCE
            "IEEE 802.17 Subclause 10.2.2, rateLowThreshold"
        DEFVAL { 900 }
        ::= { rprFairnessEntry 16 }

    -- 1.0.8802.17.1.1.1.2.2.1.17
    rprFairnessResetWaterMarks OBJECT-TYPE
        SYNTAX INTEGER
            {
            idle(1),
            resetWaterMarks(2)
            }
        MAX-ACCESS read-write
        STATUS current
        DESCRIPTION
            "Write resetWaterMarks to this attribute to reset
            the STQ water marks to the current occupancy.
            Default value is idle"
        DEFVAL { idle }
        ::= { rprFairnessEntry 17 }

    -- 1.0.8802.17.1.1.1.2.2.1.18
    rprFairnessSTQHighWaterMark OBJECT-TYPE
        SYNTAX Unsigned32 (0..1000)
        UNITS "Tenth of percent"
        MAX-ACCESS read-only
        STATUS current
        DESCRIPTION
            "The highest level of STQ occupancy since the last reset
            of this value, in percentage of the STQ size."
        REFERENCE
            "IEEE 802.17 Subclause 10.2.2, stqHighWatermark"
        ::= { rprFairnessEntry 18 }

    -- 1.0.8802.17.1.1.1.2.2.1.19
    rprFairnessSTQLowWaterMark OBJECT-TYPE
        SYNTAX Unsigned32 (0..1000)
        UNITS "Tenth of percent"
        MAX-ACCESS read-only
        STATUS current
        DESCRIPTION
            "The lowest level of STQ occupancy since the last reset of
            this value, in percentage of the STQ size."
        REFERENCE
            "IEEE 802.17 Subclause 10.2.2, stqLowWatermark"
        ::= { rprFairnessEntry 19 }

    -- 1.0.8802.17.1.1.1.2.2.1.20
    rprFairnessLastChange OBJECT-TYPE
        SYNTAX TimeStamp
        MAX-ACCESS read-only
        STATUS current
        DESCRIPTION
            "The value of sysUpTime at the time when any of the following
            attributes changes:
            rprFairnessRingletWeight, rprFairnessReservedRate,
            rprFairnessMaxAllowed, rprFairnessAgeCoef, rprFairnessRampCoef,
            rprFairnessLpCoef, rprFairnessAdvertisementRatio,
            rprFairnessSTQHighThreshold, rprFairnessSTQLowThreshold
            rprFairnessResetWaterMarks."
        ::= { rprFairnessEntry 20 }

    -- 1.0.8802.17.1.1.1.2.2.1.21
    rprFairnessChanges OBJECT-TYPE
        SYNTAX Counter32
        MAX-ACCESS read-only
        STATUS current
        DESCRIPTION
            "Indicates number of times rprFairnessLastChange changed.
            The discontinued counter value is indicated
            by the ifCounterDiscontinuityTime value."
        ::= { rprFairnessEntry 21 }

    -- The RPR OAM actions table
    --
    -- 1.0.8802.17.1.1.1.2.3
    rprOamTable OBJECT-TYPE
        SYNTAX SEQUENCE OF RprOamEntry
        MAX-ACCESS not-accessible
        STATUS current
        DESCRIPTION
            "A table of RPR OAM actions.
            The table is designed to support a one action at a time
            on an RPR interface.
            All read-write attributes in this table are volatile,
            i.e. will be cleared on system reset."
        ::= { rprProtocols 3 }

    -- 1.0.8802.17.1.1.1.2.3.1
    rprOamEntry OBJECT-TYPE
        SYNTAX RprOamEntry
        MAX-ACCESS not-accessible
        STATUS current
        DESCRIPTION
            "OAM Echo and Flush control for an RPR interface"
        INDEX { rprOamIfIndex }
        ::= { rprOamTable 1 }

    RprOamEntry ::=
        SEQUENCE {
            rprOamIfIndex
                InterfaceIndex,
            rprOamActionType
                INTEGER,
            rprOamDestAddress
                MacAddress,
            rprOamRequestRinglet
                RprOamRinglet,
            rprOamResponseRinglet
                RprOamRinglet,
            rprOamClassOfService
                INTEGER,
            rprOamUserData
                OCTET STRING,
            rprOamProtected
                TruthValue,
            rprOamRequestCount
                Unsigned32,
            rprOamTimeout
                Unsigned32,
            rprOamControl
                INTEGER,
            rprOamResponseCount
                Unsigned32,
            rprOamAvResponseTime
                Unsigned32,
            rprOamResponseStatus
                INTEGER
         }

    -- 1.0.8802.17.1.1.1.2.3.1.1
    rprOamIfIndex OBJECT-TYPE
        SYNTAX InterfaceIndex
        MAX-ACCESS not-accessible
        STATUS current
        DESCRIPTION
            "The ifIndex of this RPR interface."
        REFERENCE
            "RFC 2863, ifIndex"
        ::= { rprOamEntry 1 }

    -- 1.0.8802.17.1.1.1.2.3.1.2
    rprOamActionType OBJECT-TYPE
        SYNTAX INTEGER
            {
            echo(1),
            flush(2)
            }
        MAX-ACCESS read-write
        STATUS current
        DESCRIPTION
            "The type of OAM action.
            The valid values for this object are:
            (1) echo (2) flush."
        REFERENCE
            "IEEE 802.17 Subclause 12.4.1, OAM_ECHO_REQ, and 12.4.3, OAM_FLUSH_REQ"
        DEFVAL { echo }
        ::= { rprOamEntry 2 }

    -- 1.0.8802.17.1.1.1.2.3.1.3
    rprOamDestAddress OBJECT-TYPE
        SYNTAX MacAddress
        MAX-ACCESS read-write
        STATUS current
        DESCRIPTION
            "The 48-bit MAC address of the destination station of OAM
            session."
        REFERENCE
            "IEEE 802.17 Subclause 12.4.1 and 12.4.3, destination_address"
        ::= { rprOamEntry 3 }

    -- 1.0.8802.17.1.1.1.2.3.1.4
    rprOamRequestRinglet OBJECT-TYPE
        SYNTAX RprOamRinglet
        MAX-ACCESS read-write
        STATUS current
        DESCRIPTION
            "The ringlet ID on which the OAM request should be sent."
        REFERENCE
            "IEEE 802.17 Subclause 12.4.1 and 12.4.3, ringlet_id"
        DEFVAL { default }
        ::= { rprOamEntry 4 }

    -- 1.0.8802.17.1.1.1.2.3.1.5
    rprOamResponseRinglet OBJECT-TYPE
        SYNTAX RprOamRinglet
        MAX-ACCESS read-write
        STATUS current
        DESCRIPTION
            "The ringlet ID on which the OAM response should be replied."
        REFERENCE
            "IEEE 802.17 Subclause 12.4.1, response_ringlet"
        DEFVAL { default }
        ::= { rprOamEntry 5 }

    -- 1.0.8802.17.1.1.1.2.3.1.6
    rprOamClassOfService OBJECT-TYPE
        SYNTAX INTEGER
            {
            classA(1),
            classB(2),
            classC(3)
            }
        MAX-ACCESS read-write
        STATUS current
        DESCRIPTION
            "The class-of-service of OAM session frames"
        REFERENCE
            "IEEE 802.17 Subclause 12.4.1 and 12.4.3, service_class"
        DEFVAL { classC }
        ::= { rprOamEntry 6 }

    -- 1.0.8802.17.1.1.1.2.3.1.7
    rprOamUserData OBJECT-TYPE
        SYNTAX OCTET STRING (SIZE (0..1024))
        MAX-ACCESS read-write
        STATUS current
        DESCRIPTION
            "The operator assigned user specific data."
        REFERENCE
            "IEEE 802.17 Subclause 12.4.1 and 12.4.3, user_data"
        DEFVAL { "" }
        ::= { rprOamEntry 7 }

    -- 1.0.8802.17.1.1.1.2.3.1.8
    rprOamProtected OBJECT-TYPE
        SYNTAX TruthValue
        MAX-ACCESS read-write
        STATUS current
        DESCRIPTION
            "Indicates whether the OAM action should be protected.
            In a wrapping ring,
            If true, the WE (wrap eligible) bit of the OAM action
            frame is set to 1.
            Otherwise, the WE bit is set to 0.
            In steering ring,
            If true, in case of failure on the requested ringlet between
            the source and the destination stations, the OAM action frame
            will be steered to the alternative ringlet.
            Otherwise, the OAM action frame will be sent through the requested
            ringlet regardless of its protection state."
        REFERENCE
            "IEEE 802.17 Subclause 12.4.1 and 12.4.3, mac_protection"
        DEFVAL { false }
        ::= { rprOamEntry 8 }

    -- 1.0.8802.17.1.1.1.2.3.1.9
    rprOamRequestCount OBJECT-TYPE
        SYNTAX Unsigned32 (0..65535)
        MAX-ACCESS read-write
        STATUS current
        DESCRIPTION
            "Indicates the number of OAM requests to send.
            Default value of OAM request action is 1."
        DEFVAL { 1 }
        ::= { rprOamEntry 9 }

    -- 1.0.8802.17.1.1.1.2.3.1.10
    rprOamTimeout OBJECT-TYPE
        SYNTAX Unsigned32 (1..10000)
        UNITS "10usec"
        MAX-ACCESS read-write
        STATUS current
        DESCRIPTION
            "Indicates the timer to declare OAM action timeout,
            in 10usec units.
            Default value of OAM timeout is 500 units of 10usec (i.e. 5 ms)"
        DEFVAL { 500 }
        ::= { rprOamEntry 10 }

    -- 1.0.8802.17.1.1.1.2.3.1.11
    rprOamControl OBJECT-TYPE
        SYNTAX INTEGER
            {
            idle(1),
            active(2),
            abort(3)
            }
        MAX-ACCESS read-write
        STATUS current
        DESCRIPTION
            "Control of an OAM action.
            The valid values for this object are:
            (1) idle (2) active (3) abort.
            Default value of OAM control is idle."
        DEFVAL { idle }
        ::= { rprOamEntry 11 }

    -- 1.0.8802.17.1.1.1.2.3.1.12
    rprOamResponseCount OBJECT-TYPE
        SYNTAX Unsigned32 (0..65535)
        MAX-ACCESS read-only
        STATUS current
        DESCRIPTION
            "Indicates the number of OAM actions responses received."
        ::= { rprOamEntry 12 }

    -- 1.0.8802.17.1.1.1.2.3.1.13
    rprOamAvResponseTime OBJECT-TYPE
        SYNTAX Unsigned32 (0..65535)
        UNITS "10usec"
        MAX-ACCESS read-only
        STATUS current
        DESCRIPTION
            "Average response time to receive the OAM reply."
        ::= { rprOamEntry 13 }

    -- 1.0.8802.17.1.1.1.2.3.1.14
    rprOamResponseStatus OBJECT-TYPE
        SYNTAX INTEGER
            {
            unknown(1),
            inProcess(2),
            error(3),
            success(4)
            }
        MAX-ACCESS read-only
        STATUS current
        DESCRIPTION
            "Status of an OAM action.
            The valid values for this object are:
            (1) unknown (2) inProcess (3) error (4) success.
            The action status is success if at least 90% of the responses
            were received till timeout."
        ::= { rprOamEntry 14 }

    -- 1.0.8802.17.1.1.1.3
    rprSpanCounters OBJECT IDENTIFIER ::= { rprObjects 3 }

    -- RPR ring interface current counters table
    --
    -- 1.0.8802.17.1.1.1.3.1
    rprSpanCountersCurrentTable OBJECT-TYPE
        SYNTAX SEQUENCE OF RprSpanCountersCurrentEntry
        MAX-ACCESS not-accessible
        STATUS current
        DESCRIPTION
            "The RPR MAC Span interface current counters table.
            All attributes in this table are volatile,
            i.e. will be cleared on system reset."
        ::= { rprSpanCounters 1 }

    -- 1.0.8802.17.1.1.1.3.1.1
    rprSpanCountersCurrentEntry OBJECT-TYPE
        SYNTAX RprSpanCountersCurrentEntry
        MAX-ACCESS not-accessible
        STATUS current
        DESCRIPTION
            "Frames and octets statistics for the current interval for
            the RPR MAC Span interface.
            The corresponding instance of rprIfStatsControlTimeElapsed
            indicates the number of seconds which have elapsed
            so far in the current interval."
        INDEX { rprSpanCurrentIfIndex, rprSpanCurrentSpan }
        ::= { rprSpanCountersCurrentTable 1 }

    RprSpanCountersCurrentEntry ::=
        SEQUENCE {
            rprSpanCurrentIfIndex
                InterfaceIndex,
            rprSpanCurrentSpan
                RprSpan,
            rprSpanCurrentInUcastClassAFrames
                HCPerfCurrentCount,
            rprSpanCurrentInUcastClassAOctets
                HCPerfCurrentCount,
            rprSpanCurrentInUcastClassBCirFrames
                HCPerfCurrentCount,
            rprSpanCurrentInUcastClassBCirOctets
                HCPerfCurrentCount,
            rprSpanCurrentInUcastClassBEirFrames
                HCPerfCurrentCount,
            rprSpanCurrentInUcastClassBEirOctets
                HCPerfCurrentCount,
            rprSpanCurrentInUcastClassCFrames
                HCPerfCurrentCount,
            rprSpanCurrentInUcastClassCOctets
                HCPerfCurrentCount,
            rprSpanCurrentInMcastClassAFrames
                HCPerfCurrentCount,
            rprSpanCurrentInMcastClassAOctets
                HCPerfCurrentCount,
            rprSpanCurrentInMcastClassBCirFrames
                HCPerfCurrentCount,
            rprSpanCurrentInMcastClassBCirOctets
                HCPerfCurrentCount,
            rprSpanCurrentInMcastClassBEirFrames
                HCPerfCurrentCount,
            rprSpanCurrentInMcastClassBEirOctets
                HCPerfCurrentCount,
            rprSpanCurrentInMcastClassCFrames
                HCPerfCurrentCount,
            rprSpanCurrentInMcastClassCOctets
                HCPerfCurrentCount,
            rprSpanCurrentOutUcastClassAFrames
                HCPerfCurrentCount,
            rprSpanCurrentOutUcastClassAOctets
                HCPerfCurrentCount,
            rprSpanCurrentOutUcastClassBCirFrames
                HCPerfCurrentCount,
            rprSpanCurrentOutUcastClassBCirOctets
                HCPerfCurrentCount,
            rprSpanCurrentOutUcastClassBEirFrames
                HCPerfCurrentCount,
            rprSpanCurrentOutUcastClassBEirOctets
                HCPerfCurrentCount,
            rprSpanCurrentOutUcastClassCFrames
                HCPerfCurrentCount,
            rprSpanCurrentOutUcastClassCOctets
                HCPerfCurrentCount,
            rprSpanCurrentOutMcastClassAFrames
                HCPerfCurrentCount,
            rprSpanCurrentOutMcastClassAOctets
                HCPerfCurrentCount,
            rprSpanCurrentOutMcastClassBCirFrames
                HCPerfCurrentCount,
            rprSpanCurrentOutMcastClassBCirOctets
                HCPerfCurrentCount,
            rprSpanCurrentOutMcastClassBEirFrames
                HCPerfCurrentCount,
            rprSpanCurrentOutMcastClassBEirOctets
                HCPerfCurrentCount,
            rprSpanCurrentOutMcastClassCFrames
                HCPerfCurrentCount,
            rprSpanCurrentOutMcastClassCOctets
                HCPerfCurrentCount
         }

    -- 1.0.8802.17.1.1.1.3.1.1.1
    rprSpanCurrentIfIndex OBJECT-TYPE
        SYNTAX InterfaceIndex
        MAX-ACCESS not-accessible
        STATUS current
        DESCRIPTION
            "The ifIndex of this RPR interface."
        REFERENCE
            "RFC 2863, ifIndex"
        ::= { rprSpanCountersCurrentEntry 1 }

    -- 1.0.8802.17.1.1.1.3.1.1.2
    rprSpanCurrentSpan OBJECT-TYPE
        SYNTAX RprSpan
        MAX-ACCESS not-accessible
        STATUS current
        DESCRIPTION
            "An indication of the span of the interface for which this
            row contains information."
        ::= { rprSpanCountersCurrentEntry 2 }

    -- 1.0.8802.17.1.1.1.3.1.1.3
    rprSpanCurrentInUcastClassAFrames OBJECT-TYPE
        SYNTAX HCPerfCurrentCount
        MAX-ACCESS read-only
        STATUS current
        DESCRIPTION
            "The number of received (PHY to MAC) classA unicast frames
            in the current interval."
        ::= { rprSpanCountersCurrentEntry 3 }

    -- 1.0.8802.17.1.1.1.3.1.1.4
    rprSpanCurrentInUcastClassAOctets OBJECT-TYPE
        SYNTAX HCPerfCurrentCount
        MAX-ACCESS read-only
        STATUS current
        DESCRIPTION
            "The number of received (PHY to MAC) classA unicast octets,
            in the current interval."
        ::= { rprSpanCountersCurrentEntry 4 }

    -- 1.0.8802.17.1.1.1.3.1.1.5
    rprSpanCurrentInUcastClassBCirFrames OBJECT-TYPE
        SYNTAX HCPerfCurrentCount
        MAX-ACCESS read-only
        STATUS current
        DESCRIPTION
            "The number of received (PHY to MAC) classB CIR unicast frames
            in the current interval."
        ::= { rprSpanCountersCurrentEntry 5 }

    -- 1.0.8802.17.1.1.1.3.1.1.6
    rprSpanCurrentInUcastClassBCirOctets OBJECT-TYPE
        SYNTAX HCPerfCurrentCount
        MAX-ACCESS read-only
        STATUS current
        DESCRIPTION
            "The number of received (PHY to MAC) classB CIR unicast octets
            in the current interval."
        ::= { rprSpanCountersCurrentEntry 6 }

    -- 1.0.8802.17.1.1.1.3.1.1.7
    rprSpanCurrentInUcastClassBEirFrames OBJECT-TYPE
        SYNTAX HCPerfCurrentCount
        MAX-ACCESS read-only
        STATUS current
        DESCRIPTION
            "The number of received (PHY to MAC) classB EIR unicast frames
            in the current interval."
        ::= { rprSpanCountersCurrentEntry 7 }

    -- 1.0.8802.17.1.1.1.3.1.1.8
    rprSpanCurrentInUcastClassBEirOctets OBJECT-TYPE
        SYNTAX HCPerfCurrentCount
        MAX-ACCESS read-only
        STATUS current
        DESCRIPTION
            "The number of received (PHY to MAC) classB EIR unicast octets
            in the current interval."
        ::= { rprSpanCountersCurrentEntry 8 }

    -- 1.0.8802.17.1.1.1.3.1.1.9
    rprSpanCurrentInUcastClassCFrames OBJECT-TYPE
        SYNTAX HCPerfCurrentCount
        MAX-ACCESS read-only
        STATUS current
        DESCRIPTION
            "The number of received (PHY to MAC) classC unicast frames
            in the current interval."
        ::= { rprSpanCountersCurrentEntry 9 }

    -- 1.0.8802.17.1.1.1.3.1.1.10
    rprSpanCurrentInUcastClassCOctets OBJECT-TYPE
        SYNTAX HCPerfCurrentCount
        MAX-ACCESS read-only
        STATUS current
        DESCRIPTION
            "The number of received (PHY to MAC) classC unicast octets
            in the current interval."
        ::= { rprSpanCountersCurrentEntry 10 }

    -- 1.0.8802.17.1.1.1.3.1.1.11
    rprSpanCurrentInMcastClassAFrames OBJECT-TYPE
        SYNTAX HCPerfCurrentCount
        MAX-ACCESS read-only
        STATUS current
        DESCRIPTION
            "The number of received (PHY to MAC) classA multicast and
            broadcast frames in the current interval."
        ::= { rprSpanCountersCurrentEntry 11 }

    -- 1.0.8802.17.1.1.1.3.1.1.12
    rprSpanCurrentInMcastClassAOctets OBJECT-TYPE
        SYNTAX HCPerfCurrentCount
        MAX-ACCESS read-only
        STATUS current
        DESCRIPTION
            "The number of received (PHY to MAC) classA multicast and
            broadcast octets in the current interval."
        ::= { rprSpanCountersCurrentEntry 12 }

    -- 1.0.8802.17.1.1.1.3.1.1.13
    rprSpanCurrentInMcastClassBCirFrames OBJECT-TYPE
        SYNTAX HCPerfCurrentCount
        MAX-ACCESS read-only
        STATUS current
        DESCRIPTION
            "The number of received (PHY to MAC) classB CIR multicast and
            broadcast frames in the current interval."
        ::= { rprSpanCountersCurrentEntry 13 }

    -- 1.0.8802.17.1.1.1.3.1.1.14
    rprSpanCurrentInMcastClassBCirOctets OBJECT-TYPE
        SYNTAX HCPerfCurrentCount
        MAX-ACCESS read-only
        STATUS current
        DESCRIPTION
            "The number of received (PHY to MAC) classB CIR multicast and
            broadcast octets in the current interval."
        ::= { rprSpanCountersCurrentEntry 14 }

    -- 1.0.8802.17.1.1.1.3.1.1.15
    rprSpanCurrentInMcastClassBEirFrames OBJECT-TYPE
        SYNTAX HCPerfCurrentCount
        MAX-ACCESS read-only
        STATUS current
        DESCRIPTION
            "The number of received (PHY to MAC) classB EIR multicast and
            broadcast frames in the current interval."
        ::= { rprSpanCountersCurrentEntry 15 }

    -- 1.0.8802.17.1.1.1.3.1.1.16
    rprSpanCurrentInMcastClassBEirOctets OBJECT-TYPE
        SYNTAX HCPerfCurrentCount
        MAX-ACCESS read-only
        STATUS current
        DESCRIPTION
            "The number of received (PHY to MAC) classB EIR multicast and
            broadcast octets in the current interval."
        ::= { rprSpanCountersCurrentEntry 16 }

    -- 1.0.8802.17.1.1.1.3.1.1.17
    rprSpanCurrentInMcastClassCFrames OBJECT-TYPE
        SYNTAX HCPerfCurrentCount
        MAX-ACCESS read-only
        STATUS current
        DESCRIPTION
            "The number of received (PHY to MAC) classC multicast and
            broadcast frames in the current interval."
        ::= { rprSpanCountersCurrentEntry 17 }

    -- 1.0.8802.17.1.1.1.3.1.1.18
    rprSpanCurrentInMcastClassCOctets OBJECT-TYPE
        SYNTAX HCPerfCurrentCount
        MAX-ACCESS read-only
        STATUS current
        DESCRIPTION
            "The number of received (PHY to MAC) classC multicast and
            broadcast octets in the current interval."
        ::= { rprSpanCountersCurrentEntry 18 }

    -- 1.0.8802.17.1.1.1.3.1.1.19
    rprSpanCurrentOutUcastClassAFrames OBJECT-TYPE
        SYNTAX HCPerfCurrentCount
        MAX-ACCESS read-only
        STATUS current
        DESCRIPTION
            "The number of transmitted (MAC to PHY) classA unicast frames
            in the current interval."
        ::= { rprSpanCountersCurrentEntry 19 }

    -- 1.0.8802.17.1.1.1.3.1.1.20
    rprSpanCurrentOutUcastClassAOctets OBJECT-TYPE
        SYNTAX HCPerfCurrentCount
        MAX-ACCESS read-only
        STATUS current
        DESCRIPTION
            "The number of transmitted (MAC to PHY) classA unicast octets
            in the current interval."
        ::= { rprSpanCountersCurrentEntry 20 }

    -- 1.0.8802.17.1.1.1.3.1.1.21
    rprSpanCurrentOutUcastClassBCirFrames OBJECT-TYPE
        SYNTAX HCPerfCurrentCount
        MAX-ACCESS read-only
        STATUS current
        DESCRIPTION
            "The number of transmitted (MAC to PHY) classB CIR unicast frames
            in the current interval."
        ::= { rprSpanCountersCurrentEntry 21 }

    -- 1.0.8802.17.1.1.1.3.1.1.22
    rprSpanCurrentOutUcastClassBCirOctets OBJECT-TYPE
        SYNTAX HCPerfCurrentCount
        MAX-ACCESS read-only
        STATUS current
        DESCRIPTION
            "The number of transmitted (MAC to PHY) classB CIR unicast octets
            in the current interval."
        ::= { rprSpanCountersCurrentEntry 22 }

    -- 1.0.8802.17.1.1.1.3.1.1.23
    rprSpanCurrentOutUcastClassBEirFrames OBJECT-TYPE
        SYNTAX HCPerfCurrentCount
        MAX-ACCESS read-only
        STATUS current
        DESCRIPTION
            "The number of transmitted (MAC to PHY) classB EIR unicast frames
            in the current interval."
        ::= { rprSpanCountersCurrentEntry 23 }

    -- 1.0.8802.17.1.1.1.3.1.1.24
    rprSpanCurrentOutUcastClassBEirOctets OBJECT-TYPE
        SYNTAX HCPerfCurrentCount
        MAX-ACCESS read-only
        STATUS current
        DESCRIPTION
            "The number of transmitted (MAC to PHY) classB EIR unicast octets
            in the current interval."
        ::= { rprSpanCountersCurrentEntry 24 }

    -- 1.0.8802.17.1.1.1.3.1.1.25
    rprSpanCurrentOutUcastClassCFrames OBJECT-TYPE
        SYNTAX HCPerfCurrentCount
        MAX-ACCESS read-only
        STATUS current
        DESCRIPTION
            "The number of transmitted (MAC to PHY) classC unicast frames
            in the current interval."
        ::= { rprSpanCountersCurrentEntry 25 }

    -- 1.0.8802.17.1.1.1.3.1.1.26
    rprSpanCurrentOutUcastClassCOctets OBJECT-TYPE
        SYNTAX HCPerfCurrentCount
        MAX-ACCESS read-only
        STATUS current
        DESCRIPTION
            "The number of transmitted (MAC to PHY) classC unicast octets
            in the current interval."
        ::= { rprSpanCountersCurrentEntry 26 }

    -- 1.0.8802.17.1.1.1.3.1.1.27
    rprSpanCurrentOutMcastClassAFrames OBJECT-TYPE
        SYNTAX HCPerfCurrentCount
        MAX-ACCESS read-only
        STATUS current
        DESCRIPTION
            "The number of transmitted (MAC to PHY) classA multicast and
            broadcast frames in the current interval."
        ::= { rprSpanCountersCurrentEntry 27 }

    -- 1.0.8802.17.1.1.1.3.1.1.28
    rprSpanCurrentOutMcastClassAOctets OBJECT-TYPE
        SYNTAX HCPerfCurrentCount
        MAX-ACCESS read-only
        STATUS current
        DESCRIPTION
            "The number of transmitted (MAC to PHY) classA multicast and
            broadcast octets in the current interval."
        ::= { rprSpanCountersCurrentEntry 28 }

    -- 1.0.8802.17.1.1.1.3.1.1.29
    rprSpanCurrentOutMcastClassBCirFrames OBJECT-TYPE
        SYNTAX HCPerfCurrentCount
        MAX-ACCESS read-only
        STATUS current
        DESCRIPTION
            "The number of transmitted (MAC to PHY) classB CIR multicast and
            broadcast frames in the current interval."
        ::= { rprSpanCountersCurrentEntry 29 }

    -- 1.0.8802.17.1.1.1.3.1.1.30
    rprSpanCurrentOutMcastClassBCirOctets OBJECT-TYPE
        SYNTAX HCPerfCurrentCount
        MAX-ACCESS read-only
        STATUS current
        DESCRIPTION
            "The number of transmitted (MAC to PHY) classB CIR multicast and
            broadcast octets in the current interval."
        ::= { rprSpanCountersCurrentEntry 30 }

    -- 1.0.8802.17.1.1.1.3.1.1.31
    rprSpanCurrentOutMcastClassBEirFrames OBJECT-TYPE
        SYNTAX HCPerfCurrentCount
        MAX-ACCESS read-only
        STATUS current
        DESCRIPTION
            "The number of transmitted (MAC to PHY) classB EIR multicast and
            broadcast frames in the current interval."
        ::= { rprSpanCountersCurrentEntry 31 }

    -- 1.0.8802.17.1.1.1.3.1.1.32
    rprSpanCurrentOutMcastClassBEirOctets OBJECT-TYPE
        SYNTAX HCPerfCurrentCount
        MAX-ACCESS read-only
        STATUS current
        DESCRIPTION
            "The number of transmitted (MAC to PHY) classB EIR multicast and
            broadcast octets in the current interval."
        ::= { rprSpanCountersCurrentEntry 32 }

    -- 1.0.8802.17.1.1.1.3.1.1.33
    rprSpanCurrentOutMcastClassCFrames OBJECT-TYPE
        SYNTAX HCPerfCurrentCount
        MAX-ACCESS read-only
        STATUS current
        DESCRIPTION
            "The number of transmitted (MAC to PHY) classC multicast and
            broadcast frames in the current interval."
        ::= { rprSpanCountersCurrentEntry 33 }

    -- 1.0.8802.17.1.1.1.3.1.1.34
    rprSpanCurrentOutMcastClassCOctets OBJECT-TYPE
        SYNTAX HCPerfCurrentCount
        MAX-ACCESS read-only
        STATUS current
        DESCRIPTION
            "The number of transmitted (MAC to PHY) classC multicast and
            broadcast octets in the current interval."
        ::= { rprSpanCountersCurrentEntry 34 }

    -- RPR ring interface interval counters
    --
    -- 1.0.8802.17.1.1.1.3.2
    rprSpanCountersIntervalTable OBJECT-TYPE
        SYNTAX SEQUENCE OF RprSpanCountersIntervalEntry
        MAX-ACCESS not-accessible
        STATUS current
        DESCRIPTION
            "The RPR MAC Span interface interval counters table.
            All attributes in this table are volatile,
            i.e. will be cleared on system reset."
        ::= { rprSpanCounters 2 }

    -- 1.0.8802.17.1.1.1.3.2.1
    rprSpanCountersIntervalEntry OBJECT-TYPE
        SYNTAX RprSpanCountersIntervalEntry
        MAX-ACCESS not-accessible
        STATUS current
        DESCRIPTION
            "Frames and octets statistics collected for a particular
            interval for the RPR MAC Span interface of a
            particular span of a particular RPR interface.
            The corresponding instance of rprIfValidIntervals
            indicates the number of intervals for which the set of
            statistics is available."
        INDEX { rprSpanIntervalIfIndex, rprSpanIntervalSpan, rprSpanIntervalNumber }
        ::= { rprSpanCountersIntervalTable 1 }

    RprSpanCountersIntervalEntry ::=
        SEQUENCE {
            rprSpanIntervalIfIndex
                InterfaceIndex,
            rprSpanIntervalSpan
                RprSpan,
            rprSpanIntervalNumber
                Unsigned32,
            rprSpanIntervalValidData
                TruthValue,
            rprSpanIntervalTimeElapsed
                Unsigned32,
            rprSpanIntervalStartTime
                DateAndTime,
            rprSpanIntervalInUcastClassAFrames
                HCPerfIntervalCount,
            rprSpanIntervalInUcastClassAOctets
                HCPerfIntervalCount,
            rprSpanIntervalInUcastClassBCirFrames
                HCPerfIntervalCount,
            rprSpanIntervalInUcastClassBCirOctets
                HCPerfIntervalCount,
            rprSpanIntervalInUcastClassBEirFrames
                HCPerfIntervalCount,
            rprSpanIntervalInUcastClassBEirOctets
                HCPerfIntervalCount,
            rprSpanIntervalInUcastClassCFrames
                HCPerfIntervalCount,
            rprSpanIntervalInUcastClassCOctets
                HCPerfIntervalCount,
            rprSpanIntervalInMcastClassAFrames
                HCPerfIntervalCount,
            rprSpanIntervalInMcastClassAOctets
                HCPerfIntervalCount,
            rprSpanIntervalInMcastClassBCirFrames
                HCPerfIntervalCount,
            rprSpanIntervalInMcastClassBCirOctets
                HCPerfIntervalCount,
            rprSpanIntervalInMcastClassBEirFrames
                HCPerfIntervalCount,
            rprSpanIntervalInMcastClassBEirOctets
                HCPerfIntervalCount,
            rprSpanIntervalInMcastClassCFrames
                HCPerfIntervalCount,
            rprSpanIntervalInMcastClassCOctets
                HCPerfIntervalCount,
            rprSpanIntervalOutUcastClassAFrames
                HCPerfIntervalCount,
            rprSpanIntervalOutUcastClassAOctets
                HCPerfIntervalCount,
            rprSpanIntervalOutUcastClassBCirFrames
                HCPerfIntervalCount,
            rprSpanIntervalOutUcastClassBCirOctets
                HCPerfIntervalCount,
            rprSpanIntervalOutUcastClassBEirFrames
                HCPerfIntervalCount,
            rprSpanIntervalOutUcastClassBEirOctets
                HCPerfIntervalCount,
            rprSpanIntervalOutUcastClassCFrames
                HCPerfIntervalCount,
            rprSpanIntervalOutUcastClassCOctets
                HCPerfIntervalCount,
            rprSpanIntervalOutMcastClassAFrames
                HCPerfIntervalCount,
            rprSpanIntervalOutMcastClassAOctets
                HCPerfIntervalCount,
            rprSpanIntervalOutMcastClassBCirFrames
                HCPerfIntervalCount,
            rprSpanIntervalOutMcastClassBCirOctets
                HCPerfIntervalCount,
            rprSpanIntervalOutMcastClassBEirFrames
                HCPerfIntervalCount,
            rprSpanIntervalOutMcastClassBEirOctets
                HCPerfIntervalCount,
            rprSpanIntervalOutMcastClassCFrames
                HCPerfIntervalCount,
            rprSpanIntervalOutMcastClassCOctets
                HCPerfIntervalCount
         }

    -- 1.0.8802.17.1.1.1.3.2.1.1
    rprSpanIntervalIfIndex OBJECT-TYPE
        SYNTAX InterfaceIndex
        MAX-ACCESS not-accessible
        STATUS current
        DESCRIPTION
            "The ifIndex of this RPR interface."
        ::= { rprSpanCountersIntervalEntry 1 }

    -- 1.0.8802.17.1.1.1.3.2.1.2
    rprSpanIntervalSpan OBJECT-TYPE
        SYNTAX RprSpan
        MAX-ACCESS not-accessible
        STATUS current
        DESCRIPTION
            "An indication of the span of the interface for which this
            row contains information."
        ::= { rprSpanCountersIntervalEntry 2 }

    -- 1.0.8802.17.1.1.1.3.2.1.3
    rprSpanIntervalNumber OBJECT-TYPE
        SYNTAX Unsigned32 (1..96)
        MAX-ACCESS not-accessible
        STATUS current
        DESCRIPTION
            "A number between 1 and 96, which identifies the intervals
            for which the set of statistics is available. The interval
            identified by 1 is the most recently completed 15 minute
            interval, and interval identified by N is the interval
            immediately preceding the one identified by N-1."
        ::= { rprSpanCountersIntervalEntry 3 }

    -- 1.0.8802.17.1.1.1.3.2.1.4
    rprSpanIntervalValidData OBJECT-TYPE
        SYNTAX TruthValue
        MAX-ACCESS read-only
        STATUS current
        DESCRIPTION
            "This variable indicates if the data for this interval
            is valid.
            It will be valid if it contains data for 900 seconds
            plus or minus 10 seconds."
        ::= { rprSpanCountersIntervalEntry 4 }

    -- 1.0.8802.17.1.1.1.3.2.1.5
    rprSpanIntervalTimeElapsed OBJECT-TYPE
        SYNTAX Unsigned32 (0..899)
        UNITS "Seconds"
        MAX-ACCESS read-only
        STATUS current
        DESCRIPTION
            "The duration of a particular interval in seconds.
            If, for some reason, such as an adjustment in the system's
            time-of-day clock, the current interval exceeds the maximum
            value, the agent will return the maximum value."
        ::= { rprSpanCountersIntervalEntry 5 }

    -- 1.0.8802.17.1.1.1.3.2.1.6
    rprSpanIntervalStartTime OBJECT-TYPE
        SYNTAX DateAndTime
        MAX-ACCESS read-only
        STATUS current
        DESCRIPTION
            "Indicates the wall clock time that this interval started."
        ::= { rprSpanCountersIntervalEntry 6 }

    -- 1.0.8802.17.1.1.1.3.2.1.7
    rprSpanIntervalInUcastClassAFrames OBJECT-TYPE
        SYNTAX HCPerfIntervalCount
        MAX-ACCESS read-only
        STATUS current
        DESCRIPTION
            "The number of received (PHY to MAC) classA unicast frames
            in a particular interval in the past 24 hours."
        ::= { rprSpanCountersIntervalEntry 7 }

    -- 1.0.8802.17.1.1.1.3.2.1.8
    rprSpanIntervalInUcastClassAOctets OBJECT-TYPE
        SYNTAX HCPerfIntervalCount
        MAX-ACCESS read-only
        STATUS current
        DESCRIPTION
            "The number of received (PHY to MAC) classA unicast octets
            in a particular interval in the past 24 hours."
        ::= { rprSpanCountersIntervalEntry 8 }

    -- 1.0.8802.17.1.1.1.3.2.1.9
    rprSpanIntervalInUcastClassBCirFrames OBJECT-TYPE
        SYNTAX HCPerfIntervalCount
        MAX-ACCESS read-only
        STATUS current
        DESCRIPTION
            "The number of received (PHY to MAC) classB CIR unicast frames
            in a particular interval in the past 24 hours."
        ::= { rprSpanCountersIntervalEntry 9 }

    -- 1.0.8802.17.1.1.1.3.2.1.10
    rprSpanIntervalInUcastClassBCirOctets OBJECT-TYPE
        SYNTAX HCPerfIntervalCount
        MAX-ACCESS read-only
        STATUS current
        DESCRIPTION
            "The number of received (PHY to MAC) classB CIR unicast octets
            in a particular interval in the past 24 hours."
        ::= { rprSpanCountersIntervalEntry 10 }

    -- 1.0.8802.17.1.1.1.3.2.1.11
    rprSpanIntervalInUcastClassBEirFrames OBJECT-TYPE
        SYNTAX HCPerfIntervalCount
        MAX-ACCESS read-only
        STATUS current
        DESCRIPTION
            "The number of received (PHY to MAC) classB EIR unicast
            frames in a particular interval in the past 24 hours."
        ::= { rprSpanCountersIntervalEntry 11 }

    -- 1.0.8802.17.1.1.1.3.2.1.12
    rprSpanIntervalInUcastClassBEirOctets OBJECT-TYPE
        SYNTAX HCPerfIntervalCount
        MAX-ACCESS read-only
        STATUS current
        DESCRIPTION
            "The number of received (PHY to MAC) classB EIR unicast
            octets in a particular interval in the past 24 hours."
        ::= { rprSpanCountersIntervalEntry 12 }

    -- 1.0.8802.17.1.1.1.3.2.1.13
    rprSpanIntervalInUcastClassCFrames OBJECT-TYPE
        SYNTAX HCPerfIntervalCount
        MAX-ACCESS read-only
        STATUS current
        DESCRIPTION
            "The number of received (PHY to MAC) classC unicast
            frames in a particular interval in the past 24 hours."
        ::= { rprSpanCountersIntervalEntry 13 }

    -- 1.0.8802.17.1.1.1.3.2.1.14
    rprSpanIntervalInUcastClassCOctets OBJECT-TYPE
        SYNTAX HCPerfIntervalCount
        MAX-ACCESS read-only
        STATUS current
        DESCRIPTION
            "The number of received (PHY to MAC) classC unicast
            octets in a particular interval in the past 24 hours."
        ::= { rprSpanCountersIntervalEntry 14 }

    -- 1.0.8802.17.1.1.1.3.2.1.15
    rprSpanIntervalInMcastClassAFrames OBJECT-TYPE
        SYNTAX HCPerfIntervalCount
        MAX-ACCESS read-only
        STATUS current
        DESCRIPTION
            "The number of received (PHY to MAC) classA multicast and
            broadcast frames in a particular interval in the past 24 hours."
        ::= { rprSpanCountersIntervalEntry 15 }

    -- 1.0.8802.17.1.1.1.3.2.1.16
    rprSpanIntervalInMcastClassAOctets OBJECT-TYPE
        SYNTAX HCPerfIntervalCount
        MAX-ACCESS read-only
        STATUS current
        DESCRIPTION
            "The number of received (PHY to MAC) classA multicast and
            broadcast octets in a particular interval in the past 24 hours."
        ::= { rprSpanCountersIntervalEntry 16 }

    -- 1.0.8802.17.1.1.1.3.2.1.17
    rprSpanIntervalInMcastClassBCirFrames OBJECT-TYPE
        SYNTAX HCPerfIntervalCount
        MAX-ACCESS read-only
        STATUS current
        DESCRIPTION
            "The number of received (PHY to MAC) classB CIR multicast and
            broadcast frames in a particular interval in the past 24 hours."
        ::= { rprSpanCountersIntervalEntry 17 }

    -- 1.0.8802.17.1.1.1.3.2.1.18
    rprSpanIntervalInMcastClassBCirOctets OBJECT-TYPE
        SYNTAX HCPerfIntervalCount
        MAX-ACCESS read-only
        STATUS current
        DESCRIPTION
            "The number of received (PHY to MAC) classB CIR multicast and
            broadcast octets in a particular interval in the past 24 hours."
        ::= { rprSpanCountersIntervalEntry 18 }

    -- 1.0.8802.17.1.1.1.3.2.1.19
    rprSpanIntervalInMcastClassBEirFrames OBJECT-TYPE
        SYNTAX HCPerfIntervalCount
        MAX-ACCESS read-only
        STATUS current
        DESCRIPTION
            "The number of received (PHY to MAC) classB EIR multicast and
            broadcast frames in a particular interval in the past 24 hours."
        ::= { rprSpanCountersIntervalEntry 19 }

    -- 1.0.8802.17.1.1.1.3.2.1.20
    rprSpanIntervalInMcastClassBEirOctets OBJECT-TYPE
        SYNTAX HCPerfIntervalCount
        MAX-ACCESS read-only
        STATUS current
        DESCRIPTION
            "The number of received (PHY to MAC) classB EIR multicast and
            broadcast octets in a particular interval in the past 24 hours."
        ::= { rprSpanCountersIntervalEntry 20 }

    -- 1.0.8802.17.1.1.1.3.2.1.21
    rprSpanIntervalInMcastClassCFrames OBJECT-TYPE
        SYNTAX HCPerfIntervalCount
        MAX-ACCESS read-only
        STATUS current
        DESCRIPTION
            "The number of received (PHY to MAC) classC multicast and
            broadcast frames in a particular interval in the past 24 hours."
        ::= { rprSpanCountersIntervalEntry 21 }

    -- 1.0.8802.17.1.1.1.3.2.1.22
    rprSpanIntervalInMcastClassCOctets OBJECT-TYPE
        SYNTAX HCPerfIntervalCount
        MAX-ACCESS read-only
        STATUS current
        DESCRIPTION
            "The number of received (PHY to MAC) classC multicast and
            broadcast octets in a particular interval in the past 24 hours."
        ::= { rprSpanCountersIntervalEntry 22 }

    -- 1.0.8802.17.1.1.1.3.2.1.23
    rprSpanIntervalOutUcastClassAFrames OBJECT-TYPE
        SYNTAX HCPerfIntervalCount
        MAX-ACCESS read-only
        STATUS current
        DESCRIPTION
            "The number of transmitted (MAC to PHY) classA unicast frames
            in a particular interval in the past 24 hours."
        ::= { rprSpanCountersIntervalEntry 23 }

    -- 1.0.8802.17.1.1.1.3.2.1.24
    rprSpanIntervalOutUcastClassAOctets OBJECT-TYPE
        SYNTAX HCPerfIntervalCount
        MAX-ACCESS read-only
        STATUS current
        DESCRIPTION
            "The number of transmitted (MAC to PHY) classA unicast octets
            in a particular interval in the past 24 hours."
        ::= { rprSpanCountersIntervalEntry 24 }

    -- 1.0.8802.17.1.1.1.3.2.1.25
    rprSpanIntervalOutUcastClassBCirFrames OBJECT-TYPE
        SYNTAX HCPerfIntervalCount
        MAX-ACCESS read-only
        STATUS current
        DESCRIPTION
            "The number of transmitted (MAC to PHY) classB CIR unicast frames,
            in a particular interval in the past 24 hours."
        ::= { rprSpanCountersIntervalEntry 25 }

    -- 1.0.8802.17.1.1.1.3.2.1.26
    rprSpanIntervalOutUcastClassBCirOctets OBJECT-TYPE
        SYNTAX HCPerfIntervalCount
        MAX-ACCESS read-only
        STATUS current
        DESCRIPTION
            "The number of transmitted (MAC to PHY) classB CIR unicast octets
            in a particular interval in the past 24 hours."
        ::= { rprSpanCountersIntervalEntry 26 }

    -- 1.0.8802.17.1.1.1.3.2.1.27
    rprSpanIntervalOutUcastClassBEirFrames OBJECT-TYPE
        SYNTAX HCPerfIntervalCount
        MAX-ACCESS read-only
        STATUS current
        DESCRIPTION
            "The number of transmitted (MAC to PHY) classB EIR unicast frames
            in a particular interval in the past 24 hours."
        ::= { rprSpanCountersIntervalEntry 27 }

    -- 1.0.8802.17.1.1.1.3.2.1.28
    rprSpanIntervalOutUcastClassBEirOctets OBJECT-TYPE
        SYNTAX HCPerfIntervalCount
        MAX-ACCESS read-only
        STATUS current
        DESCRIPTION
            "The number of transmitted (MAC to PHY) classB EIR unicast octets
            in a particular interval in the past 24 hours."
        ::= { rprSpanCountersIntervalEntry 28 }

    -- 1.0.8802.17.1.1.1.3.2.1.29
    rprSpanIntervalOutUcastClassCFrames OBJECT-TYPE
        SYNTAX HCPerfIntervalCount
        MAX-ACCESS read-only
        STATUS current
        DESCRIPTION
            "The number of transmitted (MAC to PHY) classC unicast frames
            in a particular interval in the past 24 hours."
        ::= { rprSpanCountersIntervalEntry 29 }

    -- 1.0.8802.17.1.1.1.3.2.1.30
    rprSpanIntervalOutUcastClassCOctets OBJECT-TYPE
        SYNTAX HCPerfIntervalCount
        MAX-ACCESS read-only
        STATUS current
        DESCRIPTION
            "The number of transmitted (MAC to PHY) classC unicast octets
            in a particular interval in the past 24 hours."
        ::= { rprSpanCountersIntervalEntry 30 }

    -- 1.0.8802.17.1.1.1.3.2.1.31
    rprSpanIntervalOutMcastClassAFrames OBJECT-TYPE
        SYNTAX HCPerfIntervalCount
        MAX-ACCESS read-only
        STATUS current
        DESCRIPTION
            "The number of transmitted (MAC to PHY) classA multicast and
            broadcast frames in a particular interval in the past 24 hours."
        ::= { rprSpanCountersIntervalEntry 31 }

    -- 1.0.8802.17.1.1.1.3.2.1.32
    rprSpanIntervalOutMcastClassAOctets OBJECT-TYPE
        SYNTAX HCPerfIntervalCount
        MAX-ACCESS read-only
        STATUS current
        DESCRIPTION
            "The number of transmitted (MAC to PHY) classA multicast and
            broadcast octets in a particular interval in the past 24 hours."
        ::= { rprSpanCountersIntervalEntry 32 }

    -- 1.0.8802.17.1.1.1.3.2.1.33
    rprSpanIntervalOutMcastClassBCirFrames OBJECT-TYPE
        SYNTAX HCPerfIntervalCount
        MAX-ACCESS read-only
        STATUS current
        DESCRIPTION
            "The number of transmitted (MAC to PHY) classB CIR multicast and
            broadcast frames in a particular interval in the past 24 hours."
        ::= { rprSpanCountersIntervalEntry 33 }

    -- 1.0.8802.17.1.1.1.3.2.1.34
    rprSpanIntervalOutMcastClassBCirOctets OBJECT-TYPE
        SYNTAX HCPerfIntervalCount
        MAX-ACCESS read-only
        STATUS current
        DESCRIPTION
            "The number of transmitted (MAC to PHY) classB CIR multicast and
            broadcast octets in a particular interval in the past 24 hours."
        ::= { rprSpanCountersIntervalEntry 34 }

    -- 1.0.8802.17.1.1.1.3.2.1.35
    rprSpanIntervalOutMcastClassBEirFrames OBJECT-TYPE
        SYNTAX HCPerfIntervalCount
        MAX-ACCESS read-only
        STATUS current
        DESCRIPTION
            "The number of transmitted (MAC to PHY) classB EIR multicast and
            broadcast frames in a particular interval in the past 24 hours."
        ::= { rprSpanCountersIntervalEntry 35 }

    -- 1.0.8802.17.1.1.1.3.2.1.36
    rprSpanIntervalOutMcastClassBEirOctets OBJECT-TYPE
        SYNTAX HCPerfIntervalCount
        MAX-ACCESS read-only
        STATUS current
        DESCRIPTION
            "The number of transmitted (MAC to PHY) classB EIR multicast and
            broadcast octets in a particular interval in the past 24 hours."
        ::= { rprSpanCountersIntervalEntry 36 }

    -- 1.0.8802.17.1.1.1.3.2.1.37
    rprSpanIntervalOutMcastClassCFrames OBJECT-TYPE
        SYNTAX HCPerfIntervalCount
        MAX-ACCESS read-only
        STATUS current
        DESCRIPTION
            "The number of transmitted (MAC to PHY) classC multicast and
            broadcast frames in a particular interval in the past 24 hours."
        ::= { rprSpanCountersIntervalEntry 37 }

    -- 1.0.8802.17.1.1.1.3.2.1.38
    rprSpanIntervalOutMcastClassCOctets OBJECT-TYPE
        SYNTAX HCPerfIntervalCount
        MAX-ACCESS read-only
        STATUS current
        DESCRIPTION
            "The number of transmitted (MAC to PHY) classC multicast and
            broadcast octets in a particular interval in the past 24 hours."
        ::= { rprSpanCountersIntervalEntry 38 }

    -- RPR ring interface day (24 hour summaries) counters
    --
    -- 1.0.8802.17.1.1.1.3.3
    rprSpanCountersDayTable OBJECT-TYPE
        SYNTAX SEQUENCE OF RprSpanCountersDayEntry
        MAX-ACCESS not-accessible
        STATUS current
        DESCRIPTION
            "The RPR Mac Span Day Table contains the cumulative sum
            of the various statistics for the 24 hour period
            preceding the current interval.
            All attributes in this table are volatile,
            i.e. will be cleared on system reset."
        ::= { rprSpanCounters 3 }

    -- 1.0.8802.17.1.1.1.3.3.1
    rprSpanCountersDayEntry OBJECT-TYPE
        SYNTAX RprSpanCountersDayEntry
        MAX-ACCESS not-accessible
        STATUS current
        DESCRIPTION
            "An entry in the RPR Span Day table."
        INDEX { rprSpanDayIfIndex, rprSpanDaySpan }
        ::= { rprSpanCountersDayTable 1 }

    RprSpanCountersDayEntry ::=
        SEQUENCE {
            rprSpanDayIfIndex
                InterfaceIndex,
            rprSpanDaySpan
                RprSpan,
            rprSpanDayInUcastClassAFrames
                HCPerfTotalCount,
            rprSpanDayInUcastClassAOctets
                HCPerfTotalCount,
            rprSpanDayInUcastClassBCirFrames
                HCPerfTotalCount,
            rprSpanDayInUcastClassBCirOctets
                HCPerfTotalCount,
            rprSpanDayInUcastClassBEirFrames
                HCPerfTotalCount,
            rprSpanDayInUcastClassBEirOctets
                HCPerfTotalCount,
            rprSpanDayInUcastClassCFrames
                HCPerfTotalCount,
            rprSpanDayInUcastClassCOctets
                HCPerfTotalCount,
            rprSpanDayInMcastClassAFrames
                HCPerfTotalCount,
            rprSpanDayInMcastClassAOctets
                HCPerfTotalCount,
            rprSpanDayInMcastClassBCirFrames
                HCPerfTotalCount,
            rprSpanDayInMcastClassBCirOctets
                HCPerfTotalCount,
            rprSpanDayInMcastClassBEirFrames
                HCPerfTotalCount,
            rprSpanDayInMcastClassBEirOctets
                HCPerfTotalCount,
            rprSpanDayInMcastClassCFrames
                HCPerfTotalCount,
            rprSpanDayInMcastClassCOctets
                HCPerfTotalCount,
            rprSpanDayOutUcastClassAFrames
                HCPerfTotalCount,
            rprSpanDayOutUcastClassAOctets
                HCPerfTotalCount,
            rprSpanDayOutUcastClassBCirFrames
                HCPerfTotalCount,
            rprSpanDayOutUcastClassBCirOctets
                HCPerfTotalCount,
            rprSpanDayOutUcastClassBEirFrames
                HCPerfTotalCount,
            rprSpanDayOutUcastClassBEirOctets
                HCPerfTotalCount,
            rprSpanDayOutUcastClassCFrames
                HCPerfTotalCount,
            rprSpanDayOutUcastClassCOctets
                HCPerfTotalCount,
            rprSpanDayOutMcastClassAFrames
                HCPerfTotalCount,
            rprSpanDayOutMcastClassAOctets
                HCPerfTotalCount,
            rprSpanDayOutMcastClassBCirFrames
                HCPerfTotalCount,
            rprSpanDayOutMcastClassBCirOctets
                HCPerfTotalCount,
            rprSpanDayOutMcastClassBEirFrames
                HCPerfTotalCount,
            rprSpanDayOutMcastClassBEirOctets
                HCPerfTotalCount,
            rprSpanDayOutMcastClassCFrames
                HCPerfTotalCount,
            rprSpanDayOutMcastClassCOctets
                HCPerfTotalCount
         }

    -- 1.0.8802.17.1.1.1.3.3.1.1
    rprSpanDayIfIndex OBJECT-TYPE
        SYNTAX InterfaceIndex
        MAX-ACCESS not-accessible
        STATUS current
        DESCRIPTION
            "The ifIndex of this RPR interface."
        ::= { rprSpanCountersDayEntry 1 }

    -- 1.0.8802.17.1.1.1.3.3.1.2
    rprSpanDaySpan OBJECT-TYPE
        SYNTAX RprSpan
        MAX-ACCESS not-accessible
        STATUS current
        DESCRIPTION
            "An indication of the span of the interface for which this
            row contains information."
        ::= { rprSpanCountersDayEntry 2 }

    -- 1.0.8802.17.1.1.1.3.3.1.3
    rprSpanDayInUcastClassAFrames OBJECT-TYPE
        SYNTAX HCPerfTotalCount
        MAX-ACCESS read-only
        STATUS current
        DESCRIPTION
            "The number of received (PHY to MAC) classA unicast frames."
        ::= { rprSpanCountersDayEntry 3 }

    -- 1.0.8802.17.1.1.1.3.3.1.4
    rprSpanDayInUcastClassAOctets OBJECT-TYPE
        SYNTAX HCPerfTotalCount
        MAX-ACCESS read-only
        STATUS current
        DESCRIPTION
            "The number of received (PHY to MAC) classA unicast octets."
        ::= { rprSpanCountersDayEntry 4 }

    -- 1.0.8802.17.1.1.1.3.3.1.5
    rprSpanDayInUcastClassBCirFrames OBJECT-TYPE
        SYNTAX HCPerfTotalCount
        MAX-ACCESS read-only
        STATUS current
        DESCRIPTION
            "The number of received (PHY to MAC) classB CIR unicast frames."
        ::= { rprSpanCountersDayEntry 5 }

    -- 1.0.8802.17.1.1.1.3.3.1.6
    rprSpanDayInUcastClassBCirOctets OBJECT-TYPE
        SYNTAX HCPerfTotalCount
        MAX-ACCESS read-only
        STATUS current
        DESCRIPTION
            "The number of received (PHY to MAC) classB CIR unicast octets."
        ::= { rprSpanCountersDayEntry 6 }

    -- 1.0.8802.17.1.1.1.3.3.1.7
    rprSpanDayInUcastClassBEirFrames OBJECT-TYPE
        SYNTAX HCPerfTotalCount
        MAX-ACCESS read-only
        STATUS current
        DESCRIPTION
            "The number of received (PHY to MAC) classB EIR unicast frames."
        ::= { rprSpanCountersDayEntry 7 }

    -- 1.0.8802.17.1.1.1.3.3.1.8
    rprSpanDayInUcastClassBEirOctets OBJECT-TYPE
        SYNTAX HCPerfTotalCount
        MAX-ACCESS read-only
        STATUS current
        DESCRIPTION
            "The number of received (PHY to MAC) classB EIR unicast octets."
        ::= { rprSpanCountersDayEntry 8 }

    -- 1.0.8802.17.1.1.1.3.3.1.9
    rprSpanDayInUcastClassCFrames OBJECT-TYPE
        SYNTAX HCPerfTotalCount
        MAX-ACCESS read-only
        STATUS current
        DESCRIPTION
            "The number of received (PHY to MAC) classC unicast frames."
        ::= { rprSpanCountersDayEntry 9 }

    -- 1.0.8802.17.1.1.1.3.3.1.10
    rprSpanDayInUcastClassCOctets OBJECT-TYPE
        SYNTAX HCPerfTotalCount
        MAX-ACCESS read-only
        STATUS current
        DESCRIPTION
            "The number of received (PHY to MAC) classC unicast octets."
        ::= { rprSpanCountersDayEntry 10 }

    -- 1.0.8802.17.1.1.1.3.3.1.11
    rprSpanDayInMcastClassAFrames OBJECT-TYPE
        SYNTAX HCPerfTotalCount
        MAX-ACCESS read-only
        STATUS current
        DESCRIPTION
            "The number of received (PHY to MAC) classA multicast
            and broadcast frames"
        ::= { rprSpanCountersDayEntry 11 }

    -- 1.0.8802.17.1.1.1.3.3.1.12
    rprSpanDayInMcastClassAOctets OBJECT-TYPE
        SYNTAX HCPerfTotalCount
        MAX-ACCESS read-only
        STATUS current
        DESCRIPTION
            "The number of received (PHY to MAC) classA multicast
            and broadcast octets"
        ::= { rprSpanCountersDayEntry 12 }

    -- 1.0.8802.17.1.1.1.3.3.1.13
    rprSpanDayInMcastClassBCirFrames OBJECT-TYPE
        SYNTAX HCPerfTotalCount
        MAX-ACCESS read-only
        STATUS current
        DESCRIPTION
            "The number of received (PHY to MAC) classB CIR multicast
            and broadcast frames"
        ::= { rprSpanCountersDayEntry 13 }

    -- 1.0.8802.17.1.1.1.3.3.1.14
    rprSpanDayInMcastClassBCirOctets OBJECT-TYPE
        SYNTAX HCPerfTotalCount
        MAX-ACCESS read-only
        STATUS current
        DESCRIPTION
            "The number of received (PHY to MAC) classB CIR multicast
            and broadcast octets"
        ::= { rprSpanCountersDayEntry 14 }

    -- 1.0.8802.17.1.1.1.3.3.1.15
    rprSpanDayInMcastClassBEirFrames OBJECT-TYPE
        SYNTAX HCPerfTotalCount
        MAX-ACCESS read-only
        STATUS current
        DESCRIPTION
            "The number of received (PHY to MAC) classB EIR multicast
            and broadcast frames"
        ::= { rprSpanCountersDayEntry 15 }

    -- 1.0.8802.17.1.1.1.3.3.1.16
    rprSpanDayInMcastClassBEirOctets OBJECT-TYPE
        SYNTAX HCPerfTotalCount
        MAX-ACCESS read-only
        STATUS current
        DESCRIPTION
            "The number of received (PHY to MAC) classB EIR multicast
            and broadcast octets"
        ::= { rprSpanCountersDayEntry 16 }

    -- 1.0.8802.17.1.1.1.3.3.1.17
    rprSpanDayInMcastClassCFrames OBJECT-TYPE
        SYNTAX HCPerfTotalCount
        MAX-ACCESS read-only
        STATUS current
        DESCRIPTION
            "The number of received (PHY to MAC) classC multicast
            and broadcast frames"
        ::= { rprSpanCountersDayEntry 17 }

    -- 1.0.8802.17.1.1.1.3.3.1.18
    rprSpanDayInMcastClassCOctets OBJECT-TYPE
        SYNTAX HCPerfTotalCount
        MAX-ACCESS read-only
        STATUS current
        DESCRIPTION
            "The number of received (PHY to MAC) classC multicast
            and broadcast octets"
        ::= { rprSpanCountersDayEntry 18 }

    -- 1.0.8802.17.1.1.1.3.3.1.19
    rprSpanDayOutUcastClassAFrames OBJECT-TYPE
        SYNTAX HCPerfTotalCount
        MAX-ACCESS read-only
        STATUS current
        DESCRIPTION
            "The number of transmitted (MAC to PHY) classA unicast frames."
        ::= { rprSpanCountersDayEntry 19 }

    -- 1.0.8802.17.1.1.1.3.3.1.20
    rprSpanDayOutUcastClassAOctets OBJECT-TYPE
        SYNTAX HCPerfTotalCount
        MAX-ACCESS read-only
        STATUS current
        DESCRIPTION
            "The number of transmitted (MAC to PHY) classA unicast octets."
        ::= { rprSpanCountersDayEntry 20 }

    -- 1.0.8802.17.1.1.1.3.3.1.21
    rprSpanDayOutUcastClassBCirFrames OBJECT-TYPE
        SYNTAX HCPerfTotalCount
        MAX-ACCESS read-only
        STATUS current
        DESCRIPTION
            "The number of transmitted (MAC to PHY) classB CIR unicast frames."
        ::= { rprSpanCountersDayEntry 21 }

    -- 1.0.8802.17.1.1.1.3.3.1.22
    rprSpanDayOutUcastClassBCirOctets OBJECT-TYPE
        SYNTAX HCPerfTotalCount
        MAX-ACCESS read-only
        STATUS current
        DESCRIPTION
            "The number of transmitted (MAC to PHY) classB CIR unicast octets."
        ::= { rprSpanCountersDayEntry 22 }

    -- 1.0.8802.17.1.1.1.3.3.1.23
    rprSpanDayOutUcastClassBEirFrames OBJECT-TYPE
        SYNTAX HCPerfTotalCount
        MAX-ACCESS read-only
        STATUS current
        DESCRIPTION
            "The number of transmitted (MAC to PHY) classB EIR unicast
            frames"
        ::= { rprSpanCountersDayEntry 23 }

    -- 1.0.8802.17.1.1.1.3.3.1.24
    rprSpanDayOutUcastClassBEirOctets OBJECT-TYPE
        SYNTAX HCPerfTotalCount
        MAX-ACCESS read-only
        STATUS current
        DESCRIPTION
            "The number of transmitted (MAC to PHY) classB EIR unicast
            octets"
        ::= { rprSpanCountersDayEntry 24 }

    -- 1.0.8802.17.1.1.1.3.3.1.25
    rprSpanDayOutUcastClassCFrames OBJECT-TYPE
        SYNTAX HCPerfTotalCount
        MAX-ACCESS read-only
        STATUS current
        DESCRIPTION
            "The number of transmitted (MAC to PHY) classC unicast frames"
        ::= { rprSpanCountersDayEntry 25 }

    -- 1.0.8802.17.1.1.1.3.3.1.26
    rprSpanDayOutUcastClassCOctets OBJECT-TYPE
        SYNTAX HCPerfTotalCount
        MAX-ACCESS read-only
        STATUS current
        DESCRIPTION
            "The number of transmitted (MAC to PHY) classC unicast octets"
        ::= { rprSpanCountersDayEntry 26 }

    -- 1.0.8802.17.1.1.1.3.3.1.27
    rprSpanDayOutMcastClassAFrames OBJECT-TYPE
        SYNTAX HCPerfTotalCount
        MAX-ACCESS read-only
        STATUS current
        DESCRIPTION
            "The number of transmitted (MAC to PHY) classA multicast and broadcast
            frames."
        ::= { rprSpanCountersDayEntry 27 }

    -- 1.0.8802.17.1.1.1.3.3.1.28
    rprSpanDayOutMcastClassAOctets OBJECT-TYPE
        SYNTAX HCPerfTotalCount
        MAX-ACCESS read-only
        STATUS current
        DESCRIPTION
            "The number of transmitted (MAC to PHY) classA multicast and broadcast
            octets."
        ::= { rprSpanCountersDayEntry 28 }

    -- 1.0.8802.17.1.1.1.3.3.1.29
    rprSpanDayOutMcastClassBCirFrames OBJECT-TYPE
        SYNTAX HCPerfTotalCount
        MAX-ACCESS read-only
        STATUS current
        DESCRIPTION
            "The number of transmitted (MAC to PHY) classB CIR
            multicast and broadcast frames."
        ::= { rprSpanCountersDayEntry 29 }

    -- 1.0.8802.17.1.1.1.3.3.1.30
    rprSpanDayOutMcastClassBCirOctets OBJECT-TYPE
        SYNTAX HCPerfTotalCount
        MAX-ACCESS read-only
        STATUS current
        DESCRIPTION
            "The number of transmitted (MAC to PHY) classB CIR
            multicast and broadcast octets."
        ::= { rprSpanCountersDayEntry 30 }

    -- 1.0.8802.17.1.1.1.3.3.1.31
    rprSpanDayOutMcastClassBEirFrames OBJECT-TYPE
        SYNTAX HCPerfTotalCount
        MAX-ACCESS read-only
        STATUS current
        DESCRIPTION
            "The number of transmitted (MAC to PHY) classB EIR
            multicast and broadcast frames."
        ::= { rprSpanCountersDayEntry 31 }

    -- 1.0.8802.17.1.1.1.3.3.1.32
    rprSpanDayOutMcastClassBEirOctets OBJECT-TYPE
        SYNTAX HCPerfTotalCount
        MAX-ACCESS read-only
        STATUS current
        DESCRIPTION
            "The number of transmitted (MAC to PHY) classB EIR
            multicast and broadcast octets."
        ::= { rprSpanCountersDayEntry 32 }

    -- 1.0.8802.17.1.1.1.3.3.1.33
    rprSpanDayOutMcastClassCFrames OBJECT-TYPE
        SYNTAX HCPerfTotalCount
        MAX-ACCESS read-only
        STATUS current
        DESCRIPTION
            "The number of transmitted (MAC to PHY) classC multicast and broadcast
            frames."
        ::= { rprSpanCountersDayEntry 33 }

    -- 1.0.8802.17.1.1.1.3.3.1.34
    rprSpanDayOutMcastClassCOctets OBJECT-TYPE
        SYNTAX HCPerfTotalCount
        MAX-ACCESS read-only
        STATUS current
        DESCRIPTION
            "The number of transmitted (MAC to PHY) classC multicast and broadcast
            octets."
        ::= { rprSpanCountersDayEntry 34 }

    -- RPR ring interface continuously running counters
    --
    -- 1.0.8802.17.1.1.1.3.4
    rprSpanCountersStatsTable OBJECT-TYPE
        SYNTAX SEQUENCE OF RprSpanCountersStatsEntry
        MAX-ACCESS not-accessible
        STATUS current
        DESCRIPTION
            "The RPR Mac Span interface total counters table.
            The DiscontinuityTime for this table is indicated by
            ifCounterDiscontinuityTime defined in ifXTable.
            All attributes in this table are volatile,
            i.e. will be cleared on system reset."
        ::= { rprSpanCounters 4 }

    -- 1.0.8802.17.1.1.1.3.4.1
    rprSpanCountersStatsEntry OBJECT-TYPE
        SYNTAX RprSpanCountersStatsEntry
        MAX-ACCESS not-accessible
        STATUS current
        DESCRIPTION
            "An entry in the span stats table."
        INDEX { rprSpanStatsIfIndex, rprSpanStatsSpan }
        ::= { rprSpanCountersStatsTable 1 }

    RprSpanCountersStatsEntry ::=
        SEQUENCE {
            rprSpanStatsIfIndex
                InterfaceIndex,
            rprSpanStatsSpan
                RprSpan,
            rprSpanStatsInUcastClassAFrames
                Counter64,
            rprSpanStatsInUcastClassAOctets
                Counter64,
            rprSpanStatsInUcastClassBCirFrames
                Counter64,
            rprSpanStatsInUcastClassBCirOctets
                Counter64,
            rprSpanStatsInUcastClassBEirFrames
                Counter64,
            rprSpanStatsInUcastClassBEirOctets
                Counter64,
            rprSpanStatsInUcastClassCFrames
                Counter64,
            rprSpanStatsInUcastClassCOctets
                Counter64,
            rprSpanStatsInMcastClassAFrames
                Counter64,
            rprSpanStatsInMcastClassAOctets
                Counter64,
            rprSpanStatsInMcastClassBCirFrames
                Counter64,
            rprSpanStatsInMcastClassBCirOctets
                Counter64,
            rprSpanStatsInMcastClassBEirFrames
                Counter64,
            rprSpanStatsInMcastClassBEirOctets
                Counter64,
            rprSpanStatsInMcastClassCFrames
                Counter64,
            rprSpanStatsInMcastClassCOctets
                Counter64,
            rprSpanStatsInCtrlFrames
                Counter64,
            rprSpanStatsInOamEchoFrames
                Counter64,
            rprSpanStatsInOamFlushFrames
                Counter64,
            rprSpanStatsInOamOrgFrames
                Counter64,
            rprSpanStatsInTopoAtdFrames
                Counter64,
            rprSpanStatsInTopoChkSumFrames
                Counter64,
            rprSpanStatsInTopoTpFrames
                Counter64,
            rprSpanStatsOutUcastClassAFrames
                Counter64,
            rprSpanStatsOutUcastClassAOctets
                Counter64,
            rprSpanStatsOutUcastClassBCirFrames
                Counter64,
            rprSpanStatsOutUcastClassBCirOctets
                Counter64,
            rprSpanStatsOutUcastClassBEirFrames
                Counter64,
            rprSpanStatsOutUcastClassBEirOctets
                Counter64,
            rprSpanStatsOutUcastClassCFrames
                Counter64,
            rprSpanStatsOutUcastClassCOctets
                Counter64,
            rprSpanStatsOutMcastClassAFrames
                Counter64,
            rprSpanStatsOutMcastClassAOctets
                Counter64,
            rprSpanStatsOutMcastClassBCirFrames
                Counter64,
            rprSpanStatsOutMcastClassBCirOctets
                Counter64,
            rprSpanStatsOutMcastClassBEirFrames
                Counter64,
            rprSpanStatsOutMcastClassBEirOctets
                Counter64,
            rprSpanStatsOutMcastClassCFrames
                Counter64,
            rprSpanStatsOutMcastClassCOctets
                Counter64,
            rprSpanStatsOutCtrlFrames
                Counter64,
            rprSpanStatsOutOamEchoFrames
                Counter64,
            rprSpanStatsOutOamFlushFrames
                Counter64,
            rprSpanStatsOutOamOrgFrames
                Counter64,
            rprSpanStatsOutTopoAtdFrames
                Counter64,
            rprSpanStatsOutTopoChkSumFrames
                Counter64,
            rprSpanStatsOutTopoTpFrames
                Counter64
         }

    -- 1.0.8802.17.1.1.1.3.4.1.1
    rprSpanStatsIfIndex OBJECT-TYPE
        SYNTAX InterfaceIndex
        MAX-ACCESS not-accessible
        STATUS current
        DESCRIPTION
            "The ifIndex of this RPR interface."
        ::= { rprSpanCountersStatsEntry 1 }

    -- 1.0.8802.17.1.1.1.3.4.1.2
    rprSpanStatsSpan OBJECT-TYPE
        SYNTAX RprSpan
        MAX-ACCESS not-accessible
        STATUS current
        DESCRIPTION
            "An indication of the span of the interface for which this
            row contains information."
        REFERENCE
            "IEEE 802.17 Subclause 7.2.2, myRi"
        ::= { rprSpanCountersStatsEntry 2 }

    -- 1.0.8802.17.1.1.1.3.4.1.3
    rprSpanStatsInUcastClassAFrames OBJECT-TYPE
        SYNTAX Counter64
        MAX-ACCESS read-only
        STATUS current
        DESCRIPTION
            "The number of received (PHY to MAC) classA unicast frames."
        REFERENCE
            "IEEE 802.17 Subclause 7.2.5, rxUcastClassAFrames"
        ::= { rprSpanCountersStatsEntry 3 }

    -- 1.0.8802.17.1.1.1.3.4.1.4
    rprSpanStatsInUcastClassAOctets OBJECT-TYPE
        SYNTAX Counter64
        MAX-ACCESS read-only
        STATUS current
        DESCRIPTION
            "The number of received (PHY to MAC) classA unicast octets."
        REFERENCE
            "IEEE 802.17 Subclause 7.2.5, rxUcastClassABytes"
        ::= { rprSpanCountersStatsEntry 4 }

    -- 1.0.8802.17.1.1.1.3.4.1.5
    rprSpanStatsInUcastClassBCirFrames OBJECT-TYPE
        SYNTAX Counter64
        MAX-ACCESS read-only
        STATUS current
        DESCRIPTION
            "The number of received (PHY to MAC) classB CIR unicast frames."
        REFERENCE
            "IEEE 802.17 Subclause 7.2.5, rxUcastClassBCirFrames"
        ::= { rprSpanCountersStatsEntry 5 }

    -- 1.0.8802.17.1.1.1.3.4.1.6
    rprSpanStatsInUcastClassBCirOctets OBJECT-TYPE
        SYNTAX Counter64
        MAX-ACCESS read-only
        STATUS current
        DESCRIPTION
            "The number of received (PHY to MAC) classB CIR unicast octets."
        REFERENCE
            "IEEE 802.17 Subclause 7.2.5, rxUcastClassBCirBytes"
        ::= { rprSpanCountersStatsEntry 6 }

    -- 1.0.8802.17.1.1.1.3.4.1.7
    rprSpanStatsInUcastClassBEirFrames OBJECT-TYPE
        SYNTAX Counter64
        MAX-ACCESS read-only
        STATUS current
        DESCRIPTION
            "The number of received (PHY to MAC) classB EIR unicast frames."
        REFERENCE
            "IEEE 802.17 Subclause 7.2.5, rxUcastClassBEirFrames"
        ::= { rprSpanCountersStatsEntry 7 }

    -- 1.0.8802.17.1.1.1.3.4.1.8
    rprSpanStatsInUcastClassBEirOctets OBJECT-TYPE
        SYNTAX Counter64
        MAX-ACCESS read-only
        STATUS current
        DESCRIPTION
            "The number of received (PHY to MAC) classB EIR unicast octets."
        REFERENCE
            "IEEE 802.17 Subclause 7.2.5, rxUcastClassBEirBytes"
        ::= { rprSpanCountersStatsEntry 8 }

    -- 1.0.8802.17.1.1.1.3.4.1.9
    rprSpanStatsInUcastClassCFrames OBJECT-TYPE
        SYNTAX Counter64
        MAX-ACCESS read-only
        STATUS current
        DESCRIPTION
            "The number of received (PHY to MAC) classC unicast frames."
        REFERENCE
            "IEEE 802.17 Subclause 7.2.5, rxUcastClassCFrames"
        ::= { rprSpanCountersStatsEntry 9 }

    -- 1.0.8802.17.1.1.1.3.4.1.10
    rprSpanStatsInUcastClassCOctets OBJECT-TYPE
        SYNTAX Counter64
        MAX-ACCESS read-only
        STATUS current
        DESCRIPTION
            "The number of received (PHY to MAC) classC unicast octets."
        REFERENCE
            "IEEE 802.17 Subclause 7.2.5, rxUcastClassCBytes"
        ::= { rprSpanCountersStatsEntry 10 }

    -- 1.0.8802.17.1.1.1.3.4.1.11
    rprSpanStatsInMcastClassAFrames OBJECT-TYPE
        SYNTAX Counter64
        MAX-ACCESS read-only
        STATUS current
        DESCRIPTION
            "The number of received (PHY to MAC) classA multicast and
            broadcast frames"
        REFERENCE
            "IEEE 802.17 Subclause 7.2.5, rxMcastClassAFrames"
        ::= { rprSpanCountersStatsEntry 11 }

    -- 1.0.8802.17.1.1.1.3.4.1.12
    rprSpanStatsInMcastClassAOctets OBJECT-TYPE
        SYNTAX Counter64
        MAX-ACCESS read-only
        STATUS current
        DESCRIPTION
            "The number of received (PHY to MAC) classA multicast and
            broadcast octets"
        REFERENCE
            "IEEE 802.17 Subclause 7.2.5, rxMcastClassABytes"
        ::= { rprSpanCountersStatsEntry 12 }

    -- 1.0.8802.17.1.1.1.3.4.1.13
    rprSpanStatsInMcastClassBCirFrames OBJECT-TYPE
        SYNTAX Counter64
        MAX-ACCESS read-only
        STATUS current
        DESCRIPTION
            "The number of received (PHY to MAC) classB CIR multicast
            and broadcast frames"
        REFERENCE
            "IEEE 802.17 Subclause 7.2.5, rxMcastClassBCirFrames"
        ::= { rprSpanCountersStatsEntry 13 }

    -- 1.0.8802.17.1.1.1.3.4.1.14
    rprSpanStatsInMcastClassBCirOctets OBJECT-TYPE
        SYNTAX Counter64
        MAX-ACCESS read-only
        STATUS current
        DESCRIPTION
            "The number of received (PHY to MAC) classB CIR multicast
            and broadcast octets"
        REFERENCE
            "IEEE 802.17 Subclause 7.2.5, rxMcastClassBCirBytes"
        ::= { rprSpanCountersStatsEntry 14 }

    -- 1.0.8802.17.1.1.1.3.4.1.15
    rprSpanStatsInMcastClassBEirFrames OBJECT-TYPE
        SYNTAX Counter64
        MAX-ACCESS read-only
        STATUS current
        DESCRIPTION
            "The number of received (PHY to MAC) classB EIR multicast
            and broadcast frames"
        REFERENCE
            "IEEE 802.17 Subclause 7.2.5, rxMcastClassBEirFrames"
        ::= { rprSpanCountersStatsEntry 15 }

    -- 1.0.8802.17.1.1.1.3.4.1.16
    rprSpanStatsInMcastClassBEirOctets OBJECT-TYPE
        SYNTAX Counter64
        MAX-ACCESS read-only
        STATUS current
        DESCRIPTION
            "The number of received (PHY to MAC) classB EIR multicast
            and broadcast octets"
        REFERENCE
            "IEEE 802.17 Subclause 7.2.5, rxMcastClassBEirBytes"
        ::= { rprSpanCountersStatsEntry 16 }

    -- 1.0.8802.17.1.1.1.3.4.1.17
    rprSpanStatsInMcastClassCFrames OBJECT-TYPE
        SYNTAX Counter64
        MAX-ACCESS read-only
        STATUS current
        DESCRIPTION
            "The number of received (PHY to MAC) classC multicast and
            broadcast frames"
        REFERENCE
            "IEEE 802.17 Subclause 7.2.5, rxMcastClassCFrames"
        ::= { rprSpanCountersStatsEntry 17 }

    -- 1.0.8802.17.1.1.1.3.4.1.18
    rprSpanStatsInMcastClassCOctets OBJECT-TYPE
        SYNTAX Counter64
        MAX-ACCESS read-only
        STATUS current
        DESCRIPTION
            "The number of received (PHY to MAC) classC multicast and
            broadcast octets"
        REFERENCE
            "IEEE 802.17 Subclause 7.2.5, rxMcastClassCBytes"
        ::= { rprSpanCountersStatsEntry 18 }

    -- 1.0.8802.17.1.1.1.3.4.1.19
    rprSpanStatsInCtrlFrames OBJECT-TYPE
        SYNTAX Counter64
        MAX-ACCESS read-only
        STATUS current
        DESCRIPTION
            "The number of received (PHY to MAC) control frames
            processed by this MAC.
            This does not include control frames in transit,
            i.e. a multicast control frame received from a ringlet
            will be counted as In but not Out.
            This does not include Fairness or idle frames."
        REFERENCE
            "IEEE 802.17 Subclause 7.2.5, toCtrlFrames"
        ::= { rprSpanCountersStatsEntry 19 }

    -- 1.0.8802.17.1.1.1.3.4.1.20
    rprSpanStatsInOamEchoFrames OBJECT-TYPE
        SYNTAX Counter64
        MAX-ACCESS read-only
        STATUS current
        DESCRIPTION
            "The number of received (PHY to MAC) OAM echo
            frames processed by this MAC."
        REFERENCE
            "IEEE 802.17 Subclause 7.2.5, toCtrlOamEchoFrames"
        ::= { rprSpanCountersStatsEntry 20 }

    -- 1.0.8802.17.1.1.1.3.4.1.21
    rprSpanStatsInOamFlushFrames OBJECT-TYPE
        SYNTAX Counter64
        MAX-ACCESS read-only
        STATUS current
        DESCRIPTION
            "The number of received (PHY to MAC) OAM flush
            frames processed by this MAC."
        REFERENCE
            "IEEE 802.17 Subclause 7.2.5, toCtrlOamFlushFrames"
        ::= { rprSpanCountersStatsEntry 21 }

    -- 1.0.8802.17.1.1.1.3.4.1.22
    rprSpanStatsInOamOrgFrames OBJECT-TYPE
        SYNTAX Counter64
        MAX-ACCESS read-only
        STATUS current
        DESCRIPTION
            "The number of received (PHY to MAC) OAM Org
            frames processed by this MAC."
        REFERENCE
            "IEEE 802.17 Subclause 7.2.5, toCtrlOamOrgFrames"
        ::= { rprSpanCountersStatsEntry 22 }

    -- 1.0.8802.17.1.1.1.3.4.1.23
    rprSpanStatsInTopoAtdFrames OBJECT-TYPE
        SYNTAX Counter64
        MAX-ACCESS read-only
        STATUS current
        DESCRIPTION
            "The number of received (PHY to MAC) Topology ATD
            frames processed by this MAC."
        REFERENCE
            "IEEE 802.17 Subclause 7.2.5, toCtrlTopoATDFrames"
        ::= { rprSpanCountersStatsEntry 23 }

    -- 1.0.8802.17.1.1.1.3.4.1.24
    rprSpanStatsInTopoChkSumFrames OBJECT-TYPE
        SYNTAX Counter64
        MAX-ACCESS read-only
        STATUS current
        DESCRIPTION
            "The number of received (PHY to MAC) topology
            checksum frames processed by this MAC."
        REFERENCE
            "IEEE 802.17 Subclause 7.2.5, toCtrlTopoSumFrames"
        ::= { rprSpanCountersStatsEntry 24 }

    -- 1.0.8802.17.1.1.1.3.4.1.25
    rprSpanStatsInTopoTpFrames OBJECT-TYPE
        SYNTAX Counter64
        MAX-ACCESS read-only
        STATUS current
        DESCRIPTION
            "The number of received (PHY to MAC) topology TP
            frames processed by this MAC."
        REFERENCE
            "IEEE 802.17 Subclause 7.2.5, toCtrlTopoTPFrames"
        ::= { rprSpanCountersStatsEntry 25 }

    -- 1.0.8802.17.1.1.1.3.4.1.26
    rprSpanStatsOutUcastClassAFrames OBJECT-TYPE
        SYNTAX Counter64
        MAX-ACCESS read-only
        STATUS current
        DESCRIPTION
            "The number of transmitted (MAC to PHY) classA unicast frames."
        REFERENCE
            "IEEE 802.17 Subclause 7.2.5, txUcastClassAFrames"
        ::= { rprSpanCountersStatsEntry 26 }

    -- 1.0.8802.17.1.1.1.3.4.1.27
    rprSpanStatsOutUcastClassAOctets OBJECT-TYPE
        SYNTAX Counter64
        MAX-ACCESS read-only
        STATUS current
        DESCRIPTION
            "The number of transmitted (MAC to PHY) classA unicast octets."
        REFERENCE
            "IEEE 802.17 Subclause 7.2.5, txUcastClassABytes"
        ::= { rprSpanCountersStatsEntry 27 }

    -- 1.0.8802.17.1.1.1.3.4.1.28
    rprSpanStatsOutUcastClassBCirFrames OBJECT-TYPE
        SYNTAX Counter64
        MAX-ACCESS read-only
        STATUS current
        DESCRIPTION
            "The number of transmitted (MAC to PHY) classB CIR unicast frames."
        REFERENCE
            "IEEE 802.17 Subclause 7.2.5, txUcastClassBCirFrames"
        ::= { rprSpanCountersStatsEntry 28 }

    -- 1.0.8802.17.1.1.1.3.4.1.29
    rprSpanStatsOutUcastClassBCirOctets OBJECT-TYPE
        SYNTAX Counter64
        MAX-ACCESS read-only
        STATUS current
        DESCRIPTION
            "The number of transmitted (MAC to PHY) classB CIR unicast octets."
        REFERENCE
            "IEEE 802.17 Subclause 7.2.5, txUcastClassBCirBytes"
        ::= { rprSpanCountersStatsEntry 29 }

    -- 1.0.8802.17.1.1.1.3.4.1.30
    rprSpanStatsOutUcastClassBEirFrames OBJECT-TYPE
        SYNTAX Counter64
        MAX-ACCESS read-only
        STATUS current
        DESCRIPTION
            "The number of transmitted (MAC to PHY) classB EIR unicast frames"
        REFERENCE
            "IEEE 802.17 Subclause 7.2.5, txUcastClassBEirFrames"
        ::= { rprSpanCountersStatsEntry 30 }

    -- 1.0.8802.17.1.1.1.3.4.1.31
    rprSpanStatsOutUcastClassBEirOctets OBJECT-TYPE
        SYNTAX Counter64
        MAX-ACCESS read-only
        STATUS current
        DESCRIPTION
            "The number of transmitted (MAC to PHY) classB EIR unicast octets"
        REFERENCE
            "IEEE 802.17 Subclause 7.2.5, txUcastClassBEirBytes"
        ::= { rprSpanCountersStatsEntry 31 }

    -- 1.0.8802.17.1.1.1.3.4.1.32
    rprSpanStatsOutUcastClassCFrames OBJECT-TYPE
        SYNTAX Counter64
        MAX-ACCESS read-only
        STATUS current
        DESCRIPTION
            "The number of transmitted (MAC to PHY) classC unicast frames"
        REFERENCE
            "IEEE 802.17 Subclause 7.2.5, txUcastClassCFrames"
        ::= { rprSpanCountersStatsEntry 32 }

    -- 1.0.8802.17.1.1.1.3.4.1.33
    rprSpanStatsOutUcastClassCOctets OBJECT-TYPE
        SYNTAX Counter64
        MAX-ACCESS read-only
        STATUS current
        DESCRIPTION
            "The number of transmitted (MAC to PHY) classC unicast octets"
        REFERENCE
            "IEEE 802.17 Subclause 7.2.5, txUcastClassCBytes"
        ::= { rprSpanCountersStatsEntry 33 }

    -- 1.0.8802.17.1.1.1.3.4.1.34
    rprSpanStatsOutMcastClassAFrames OBJECT-TYPE
        SYNTAX Counter64
        MAX-ACCESS read-only
        STATUS current
        DESCRIPTION
            "The number of transmitted (MAC to PHY) classA multicast and
            broadcast frames."
        REFERENCE
            "IEEE 802.17 Subclause 7.2.5, txMcastClassAFrames"
        ::= { rprSpanCountersStatsEntry 34 }

    -- 1.0.8802.17.1.1.1.3.4.1.35
    rprSpanStatsOutMcastClassAOctets OBJECT-TYPE
        SYNTAX Counter64
        MAX-ACCESS read-only
        STATUS current
        DESCRIPTION
            "The number of transmitted (MAC to PHY) classA multicast and
            broadcast octets."
        REFERENCE
            "IEEE 802.17 Subclause 7.2.5, txMcastClassABytes"
        ::= { rprSpanCountersStatsEntry 35 }

    -- 1.0.8802.17.1.1.1.3.4.1.36
    rprSpanStatsOutMcastClassBCirFrames OBJECT-TYPE
        SYNTAX Counter64
        MAX-ACCESS read-only
        STATUS current
        DESCRIPTION
            "The number of transmitted (MAC to PHY) classB CIR
            multicast and broadcast frames."
        REFERENCE
            "IEEE 802.17 Subclause 7.2.5, txMcastClassBCirFrames"
        ::= { rprSpanCountersStatsEntry 36 }

    -- 1.0.8802.17.1.1.1.3.4.1.37
    rprSpanStatsOutMcastClassBCirOctets OBJECT-TYPE
        SYNTAX Counter64
        MAX-ACCESS read-only
        STATUS current
        DESCRIPTION
            "The number of transmitted (MAC to PHY) classB CIR
            multicast and broadcast octets."
        REFERENCE
            "IEEE 802.17 Subclause 7.2.5, txMcastClassBCirBytes"
        ::= { rprSpanCountersStatsEntry 37 }

    -- 1.0.8802.17.1.1.1.3.4.1.38
    rprSpanStatsOutMcastClassBEirFrames OBJECT-TYPE
        SYNTAX Counter64
        MAX-ACCESS read-only
        STATUS current
        DESCRIPTION
            "The number of transmitted (MAC to PHY) classB EIR
            multicast and broadcast frames."
        REFERENCE
            "IEEE 802.17 Subclause 7.2.5, txMcastClassBEirFrames"
        ::= { rprSpanCountersStatsEntry 38 }

    -- 1.0.8802.17.1.1.1.3.4.1.39
    rprSpanStatsOutMcastClassBEirOctets OBJECT-TYPE
        SYNTAX Counter64
        MAX-ACCESS read-only
        STATUS current
        DESCRIPTION
            "The number of transmitted (MAC to PHY) classB EIR
            multicast and broadcast octets."
        REFERENCE
            "IEEE 802.17 Subclause 7.2.5, txMcastClassBEirBytes"
        ::= { rprSpanCountersStatsEntry 39 }

    -- 1.0.8802.17.1.1.1.3.4.1.40
    rprSpanStatsOutMcastClassCFrames OBJECT-TYPE
        SYNTAX Counter64
        MAX-ACCESS read-only
        STATUS current
        DESCRIPTION
            "The number of transmitted (MAC to PHY) classC multicast and
            broadcast frames."
        REFERENCE
            "IEEE 802.17 Subclause 7.2.5, txMcastClassCFrames"
        ::= { rprSpanCountersStatsEntry 40 }

    -- 1.0.8802.17.1.1.1.3.4.1.41
    rprSpanStatsOutMcastClassCOctets OBJECT-TYPE
        SYNTAX Counter64
        MAX-ACCESS read-only
        STATUS current
        DESCRIPTION
            "The number of transmitted (MAC to PHY) classC multicast and
            broadcast octets."
        REFERENCE
            "IEEE 802.17 Subclause 7.2.5, txMcastClassCBytes"
        ::= { rprSpanCountersStatsEntry 41 }

    -- 1.0.8802.17.1.1.1.3.4.1.42
    rprSpanStatsOutCtrlFrames OBJECT-TYPE
        SYNTAX Counter64
        MAX-ACCESS read-only
        STATUS current
        DESCRIPTION
            "The number of transmitted (MAC to PHY) control frames
            generated by this MAC.
            This does not include control frames in transit,
            i.e. a multicast control frame received from a ringlet
            will be counted as In but not Out.
            This does not include Fairness or idle frames."
        REFERENCE
            "IEEE 802.17 Subclause 7.2.5, fromCtrlFrames"
        ::= { rprSpanCountersStatsEntry 42 }

    -- 1.0.8802.17.1.1.1.3.4.1.43
    rprSpanStatsOutOamEchoFrames OBJECT-TYPE
        SYNTAX Counter64
        MAX-ACCESS read-only
        STATUS current
        DESCRIPTION
            "The number of transmitted (MAC to PHY) OAM echo
            frames generated by this MAC."
        REFERENCE
            "IEEE 802.17 Subclause 7.2.5, fromCtrlOamEchoFrames"
        ::= { rprSpanCountersStatsEntry 43 }

    -- 1.0.8802.17.1.1.1.3.4.1.44
    rprSpanStatsOutOamFlushFrames OBJECT-TYPE
        SYNTAX Counter64
        MAX-ACCESS read-only
        STATUS current
        DESCRIPTION
            "The number of transmitted (MAC to PHY) OAM flush
            frames generated by this MAC."
        REFERENCE
            "IEEE 802.17 Subclause 7.2.5, fromCtrlOamFlushFrames"
        ::= { rprSpanCountersStatsEntry 44 }

    -- 1.0.8802.17.1.1.1.3.4.1.45
    rprSpanStatsOutOamOrgFrames OBJECT-TYPE
        SYNTAX Counter64
        MAX-ACCESS read-only
        STATUS current
        DESCRIPTION
            "The number of transmitted (MAC to PHY) OAM Org
            frames generated by this MAC."
        REFERENCE
            "IEEE 802.17 Subclause 7.2.5, fromCtrlOamOrgFrames"
        ::= { rprSpanCountersStatsEntry 45 }

    -- 1.0.8802.17.1.1.1.3.4.1.46
    rprSpanStatsOutTopoAtdFrames OBJECT-TYPE
        SYNTAX Counter64
        MAX-ACCESS read-only
        STATUS current
        DESCRIPTION
            "The number of transmitted (MAC to PHY) topology
            ATD frames generated by this MAC."
        REFERENCE
            "IEEE 802.17 Subclause 7.2.5, fromCtrlTopoATDFrames"
        ::= { rprSpanCountersStatsEntry 46 }

    -- 1.0.8802.17.1.1.1.3.4.1.47
    rprSpanStatsOutTopoChkSumFrames OBJECT-TYPE
        SYNTAX Counter64
        MAX-ACCESS read-only
        STATUS current
        DESCRIPTION
            "The number of transmitted (MAC to PHY) topology
            checksum frames generated by this MAC."
        REFERENCE
            "IEEE 802.17 Subclause 7.2.5, fromCtrlTopoSumFrames"
        ::= { rprSpanCountersStatsEntry 47 }

    -- 1.0.8802.17.1.1.1.3.4.1.48
    rprSpanStatsOutTopoTpFrames OBJECT-TYPE
        SYNTAX Counter64
        MAX-ACCESS read-only
        STATUS current
        DESCRIPTION
            "The number of transmitted (MAC to PHY) topology
            TP frames generated by this MAC."
        REFERENCE
            "IEEE 802.17 Subclause 7.2.5, fromCtrlTopoTPFrames"
        ::= { rprSpanCountersStatsEntry 48 }

    -- 1.0.8802.17.1.1.1.4
    rprClientCounters OBJECT IDENTIFIER ::= { rprObjects 4 }

    -- RPR Client interface current counters table
    --
    -- 1.0.8802.17.1.1.1.4.1
    rprClientCountersCurrentTable OBJECT-TYPE
        SYNTAX SEQUENCE OF RprClientCountersCurrentEntry
        MAX-ACCESS not-accessible
        STATUS current
        DESCRIPTION
            "The local station traffic current counters table.
            All attributes in this table are volatile,
            i.e. will be cleared on system reset."
        ::= { rprClientCounters 1 }

    -- 1.0.8802.17.1.1.1.4.1.1
    rprClientCountersCurrentEntry OBJECT-TYPE
        SYNTAX RprClientCountersCurrentEntry
        MAX-ACCESS not-accessible
        STATUS current
        DESCRIPTION
            "Frames and octets statistics for the current interval for
            the local station traffic of a particular RPR client interface.
            The corresponding instance of rprIfTimeElapsed indicates
            the number of seconds which have elapsed so far in the
            current interval."
        INDEX { rprClientCurrentIfIndex }
        ::= { rprClientCountersCurrentTable 1 }

    RprClientCountersCurrentEntry ::=
        SEQUENCE {
            rprClientCurrentIfIndex
                InterfaceIndex,
            rprClientCurrentInUcastClassAFrames
                HCPerfCurrentCount,
            rprClientCurrentInUcastClassAOctets
                HCPerfCurrentCount,
            rprClientCurrentInUcastClassBCirFrames
                HCPerfCurrentCount,
            rprClientCurrentInUcastClassBCirOctets
                HCPerfCurrentCount,
            rprClientCurrentInUcastClassBEirFrames
                HCPerfCurrentCount,
            rprClientCurrentInUcastClassBEirOctets
                HCPerfCurrentCount,
            rprClientCurrentInUcastClassCFrames
                HCPerfCurrentCount,
            rprClientCurrentInUcastClassCOctets
                HCPerfCurrentCount,
            rprClientCurrentInMcastClassAFrames
                HCPerfCurrentCount,
            rprClientCurrentInMcastClassAOctets
                HCPerfCurrentCount,
            rprClientCurrentInMcastClassBCirFrames
                HCPerfCurrentCount,
            rprClientCurrentInMcastClassBCirOctets
                HCPerfCurrentCount,
            rprClientCurrentInMcastClassBEirFrames
                HCPerfCurrentCount,
            rprClientCurrentInMcastClassBEirOctets
                HCPerfCurrentCount,
            rprClientCurrentInMcastClassCFrames
                HCPerfCurrentCount,
            rprClientCurrentInMcastClassCOctets
                HCPerfCurrentCount,
            rprClientCurrentOutUcastClassAFrames
                HCPerfCurrentCount,
            rprClientCurrentOutUcastClassAOctets
                HCPerfCurrentCount,
            rprClientCurrentOutUcastClassBCirFrames
                HCPerfCurrentCount,
            rprClientCurrentOutUcastClassBCirOctets
                HCPerfCurrentCount,
            rprClientCurrentOutUcastClassBEirFrames
                HCPerfCurrentCount,
            rprClientCurrentOutUcastClassBEirOctets
                HCPerfCurrentCount,
            rprClientCurrentOutUcastClassCFrames
                HCPerfCurrentCount,
            rprClientCurrentOutUcastClassCOctets
                HCPerfCurrentCount,
            rprClientCurrentOutMcastClassAFrames
                HCPerfCurrentCount,
            rprClientCurrentOutMcastClassAOctets
                HCPerfCurrentCount,
            rprClientCurrentOutMcastClassBCirFrames
                HCPerfCurrentCount,
            rprClientCurrentOutMcastClassBCirOctets
                HCPerfCurrentCount,
            rprClientCurrentOutMcastClassBEirFrames
                HCPerfCurrentCount,
            rprClientCurrentOutMcastClassBEirOctets
                HCPerfCurrentCount,
            rprClientCurrentOutMcastClassCFrames
                HCPerfCurrentCount,
            rprClientCurrentOutMcastClassCOctets
                HCPerfCurrentCount
         }

    -- 1.0.8802.17.1.1.1.4.1.1.1
    rprClientCurrentIfIndex OBJECT-TYPE
        SYNTAX InterfaceIndex
        MAX-ACCESS not-accessible
        STATUS current
        DESCRIPTION
            "The ifIndex of this RPR interface."
        REFERENCE
            "RFC 2863, ifIndex"
        ::= { rprClientCountersCurrentEntry 1 }

    -- 1.0.8802.17.1.1.1.4.1.1.2
    rprClientCurrentInUcastClassAFrames OBJECT-TYPE
        SYNTAX HCPerfCurrentCount
        MAX-ACCESS read-only
        STATUS current
        DESCRIPTION
            "The number of MAC to client classA unicast frames in
            the current interval."
        ::= { rprClientCountersCurrentEntry 2 }

    -- 1.0.8802.17.1.1.1.4.1.1.3
    rprClientCurrentInUcastClassAOctets OBJECT-TYPE
        SYNTAX HCPerfCurrentCount
        MAX-ACCESS read-only
        STATUS current
        DESCRIPTION
            "The number of MAC to client classA unicast octets in
            the current interval."
        ::= { rprClientCountersCurrentEntry 3 }

    -- 1.0.8802.17.1.1.1.4.1.1.4
    rprClientCurrentInUcastClassBCirFrames OBJECT-TYPE
        SYNTAX HCPerfCurrentCount
        MAX-ACCESS read-only
        STATUS current
        DESCRIPTION
            "The number of MAC to client classB CIR unicast frames in
            the current interval."
        ::= { rprClientCountersCurrentEntry 4 }

    -- 1.0.8802.17.1.1.1.4.1.1.5
    rprClientCurrentInUcastClassBCirOctets OBJECT-TYPE
        SYNTAX HCPerfCurrentCount
        MAX-ACCESS read-only
        STATUS current
        DESCRIPTION
            "The number of MAC to client classB CIR unicast octets
            in the current interval."
        ::= { rprClientCountersCurrentEntry 5 }

    -- 1.0.8802.17.1.1.1.4.1.1.6
    rprClientCurrentInUcastClassBEirFrames OBJECT-TYPE
        SYNTAX HCPerfCurrentCount
        MAX-ACCESS read-only
        STATUS current
        DESCRIPTION
            "The number of MAC to client classB EIR unicast
            frames in the current interval."
        ::= { rprClientCountersCurrentEntry 6 }

    -- 1.0.8802.17.1.1.1.4.1.1.7
    rprClientCurrentInUcastClassBEirOctets OBJECT-TYPE
        SYNTAX HCPerfCurrentCount
        MAX-ACCESS read-only
        STATUS current
        DESCRIPTION
            "The number of MAC to client classB EIR unicast
            octets in the current interval."
        ::= { rprClientCountersCurrentEntry 7 }

    -- 1.0.8802.17.1.1.1.4.1.1.8
    rprClientCurrentInUcastClassCFrames OBJECT-TYPE
        SYNTAX HCPerfCurrentCount
        MAX-ACCESS read-only
        STATUS current
        DESCRIPTION
            "The number of MAC to client classC unicast frames in the
            current interval."
        ::= { rprClientCountersCurrentEntry 8 }

    -- 1.0.8802.17.1.1.1.4.1.1.9
    rprClientCurrentInUcastClassCOctets OBJECT-TYPE
        SYNTAX HCPerfCurrentCount
        MAX-ACCESS read-only
        STATUS current
        DESCRIPTION
            "The number of MAC to client classC unicast octets in the
            current interval."
        ::= { rprClientCountersCurrentEntry 9 }

    -- 1.0.8802.17.1.1.1.4.1.1.10
    rprClientCurrentInMcastClassAFrames OBJECT-TYPE
        SYNTAX HCPerfCurrentCount
        MAX-ACCESS read-only
        STATUS current
        DESCRIPTION
            "The number of MAC to client classA multicast and broadcast
            frames in the current interval."
        ::= { rprClientCountersCurrentEntry 10 }

    -- 1.0.8802.17.1.1.1.4.1.1.11
    rprClientCurrentInMcastClassAOctets OBJECT-TYPE
        SYNTAX HCPerfCurrentCount
        MAX-ACCESS read-only
        STATUS current
        DESCRIPTION
            "The number of MAC to client classA multicast and broadcast
            octets in the current interval."
        ::= { rprClientCountersCurrentEntry 11 }

    -- 1.0.8802.17.1.1.1.4.1.1.12
    rprClientCurrentInMcastClassBCirFrames OBJECT-TYPE
        SYNTAX HCPerfCurrentCount
        MAX-ACCESS read-only
        STATUS current
        DESCRIPTION
            "The number of MAC to client classB CIR
            multicast and broadcast frames in the current interval."
        ::= { rprClientCountersCurrentEntry 12 }

    -- 1.0.8802.17.1.1.1.4.1.1.13
    rprClientCurrentInMcastClassBCirOctets OBJECT-TYPE
        SYNTAX HCPerfCurrentCount
        MAX-ACCESS read-only
        STATUS current
        DESCRIPTION
            "The number of MAC to client classB CIR
            multicast and broadcast octets in the current interval."
        ::= { rprClientCountersCurrentEntry 13 }

    -- 1.0.8802.17.1.1.1.4.1.1.14
    rprClientCurrentInMcastClassBEirFrames OBJECT-TYPE
        SYNTAX HCPerfCurrentCount
        MAX-ACCESS read-only
        STATUS current
        DESCRIPTION
            "The number of MAC to client classB EIR
            multicast and broadcast frames in the current interval."
        ::= { rprClientCountersCurrentEntry 14 }

    -- 1.0.8802.17.1.1.1.4.1.1.15
    rprClientCurrentInMcastClassBEirOctets OBJECT-TYPE
        SYNTAX HCPerfCurrentCount
        MAX-ACCESS read-only
        STATUS current
        DESCRIPTION
            "The number of MAC to client classB EIR
            multicast and broadcast octets in the current interval."
        ::= { rprClientCountersCurrentEntry 15 }

    -- 1.0.8802.17.1.1.1.4.1.1.16
    rprClientCurrentInMcastClassCFrames OBJECT-TYPE
        SYNTAX HCPerfCurrentCount
        MAX-ACCESS read-only
        STATUS current
        DESCRIPTION
            "The number of MAC to client classC multicast and broadcast
            frames in the current interval."
        ::= { rprClientCountersCurrentEntry 16 }

    -- 1.0.8802.17.1.1.1.4.1.1.17
    rprClientCurrentInMcastClassCOctets OBJECT-TYPE
        SYNTAX HCPerfCurrentCount
        MAX-ACCESS read-only
        STATUS current
        DESCRIPTION
            "The number of MAC to client classC multicast and broadcast
            octets in the current interval."
        ::= { rprClientCountersCurrentEntry 17 }

    -- 1.0.8802.17.1.1.1.4.1.1.18
    rprClientCurrentOutUcastClassAFrames OBJECT-TYPE
        SYNTAX HCPerfCurrentCount
        MAX-ACCESS read-only
        STATUS current
        DESCRIPTION
            "The number of client to MAC classA unicast frames
            in the current interval."
        ::= { rprClientCountersCurrentEntry 18 }

    -- 1.0.8802.17.1.1.1.4.1.1.19
    rprClientCurrentOutUcastClassAOctets OBJECT-TYPE
        SYNTAX HCPerfCurrentCount
        MAX-ACCESS read-only
        STATUS current
        DESCRIPTION
            "The number of client to MAC classA unicast octets
            in the current interval."
        ::= { rprClientCountersCurrentEntry 19 }

    -- 1.0.8802.17.1.1.1.4.1.1.20
    rprClientCurrentOutUcastClassBCirFrames OBJECT-TYPE
        SYNTAX HCPerfCurrentCount
        MAX-ACCESS read-only
        STATUS current
        DESCRIPTION
            "The number of client to MAC classB CIR unicast
            frames in the current interval."
        ::= { rprClientCountersCurrentEntry 20 }

    -- 1.0.8802.17.1.1.1.4.1.1.21
    rprClientCurrentOutUcastClassBCirOctets OBJECT-TYPE
        SYNTAX HCPerfCurrentCount
        MAX-ACCESS read-only
        STATUS current
        DESCRIPTION
            "The number of client to MAC classB CIR unicast
            octets in the current interval."
        ::= { rprClientCountersCurrentEntry 21 }

    -- 1.0.8802.17.1.1.1.4.1.1.22
    rprClientCurrentOutUcastClassBEirFrames OBJECT-TYPE
        SYNTAX HCPerfCurrentCount
        MAX-ACCESS read-only
        STATUS current
        DESCRIPTION
            "The number of client to MAC classB EIR unicast
            frames in the current interval."
        ::= { rprClientCountersCurrentEntry 22 }

    -- 1.0.8802.17.1.1.1.4.1.1.23
    rprClientCurrentOutUcastClassBEirOctets OBJECT-TYPE
        SYNTAX HCPerfCurrentCount
        MAX-ACCESS read-only
        STATUS current
        DESCRIPTION
            "The number of client to MAC classB EIR unicast
            octets in the current interval."
        ::= { rprClientCountersCurrentEntry 23 }

    -- 1.0.8802.17.1.1.1.4.1.1.24
    rprClientCurrentOutUcastClassCFrames OBJECT-TYPE
        SYNTAX HCPerfCurrentCount
        MAX-ACCESS read-only
        STATUS current
        DESCRIPTION
            "The number of client to MAC classC unicast frames
            in the current interval."
        ::= { rprClientCountersCurrentEntry 24 }

    -- 1.0.8802.17.1.1.1.4.1.1.25
    rprClientCurrentOutUcastClassCOctets OBJECT-TYPE
        SYNTAX HCPerfCurrentCount
        MAX-ACCESS read-only
        STATUS current
        DESCRIPTION
            "The number of client to MAC classC unicast octets
            in the current interval."
        ::= { rprClientCountersCurrentEntry 25 }

    -- 1.0.8802.17.1.1.1.4.1.1.26
    rprClientCurrentOutMcastClassAFrames OBJECT-TYPE
        SYNTAX HCPerfCurrentCount
        MAX-ACCESS read-only
        STATUS current
        DESCRIPTION
            "The number of client to MAC classA multicast and broadcast
            frames in the current interval."
        ::= { rprClientCountersCurrentEntry 26 }

    -- 1.0.8802.17.1.1.1.4.1.1.27
    rprClientCurrentOutMcastClassAOctets OBJECT-TYPE
        SYNTAX HCPerfCurrentCount
        MAX-ACCESS read-only
        STATUS current
        DESCRIPTION
            "The number of client to MAC classA multicast and broadcast
            octets in the current interval."
        ::= { rprClientCountersCurrentEntry 27 }

    -- 1.0.8802.17.1.1.1.4.1.1.28
    rprClientCurrentOutMcastClassBCirFrames OBJECT-TYPE
        SYNTAX HCPerfCurrentCount
        MAX-ACCESS read-only
        STATUS current
        DESCRIPTION
            "The number of client to MAC classB CIR
            multicast and broadcast frames in the current interval."
        ::= { rprClientCountersCurrentEntry 28 }

    -- 1.0.8802.17.1.1.1.4.1.1.29
    rprClientCurrentOutMcastClassBCirOctets OBJECT-TYPE
        SYNTAX HCPerfCurrentCount
        MAX-ACCESS read-only
        STATUS current
        DESCRIPTION
            "The number of client to MAC classB CIR
            multicast and broadcast octets in the current interval."
        ::= { rprClientCountersCurrentEntry 29 }

    -- 1.0.8802.17.1.1.1.4.1.1.30
    rprClientCurrentOutMcastClassBEirFrames OBJECT-TYPE
        SYNTAX HCPerfCurrentCount
        MAX-ACCESS read-only
        STATUS current
        DESCRIPTION
            "The number of client to MAC classB EIR
            multicast and broadcast frames in the current interval."
        ::= { rprClientCountersCurrentEntry 30 }

    -- 1.0.8802.17.1.1.1.4.1.1.31
    rprClientCurrentOutMcastClassBEirOctets OBJECT-TYPE
        SYNTAX HCPerfCurrentCount
        MAX-ACCESS read-only
        STATUS current
        DESCRIPTION
            "The number of client to MAC classB EIR
            multicast and broadcast octets in the current interval."
        ::= { rprClientCountersCurrentEntry 31 }

    -- 1.0.8802.17.1.1.1.4.1.1.32
    rprClientCurrentOutMcastClassCFrames OBJECT-TYPE
        SYNTAX HCPerfCurrentCount
        MAX-ACCESS read-only
        STATUS current
        DESCRIPTION
            "The number of client to MAC classC multicast and broadcast
            frames in the current interval."
        ::= { rprClientCountersCurrentEntry 32 }

    -- 1.0.8802.17.1.1.1.4.1.1.33
    rprClientCurrentOutMcastClassCOctets OBJECT-TYPE
        SYNTAX HCPerfCurrentCount
        MAX-ACCESS read-only
        STATUS current
        DESCRIPTION
            "The number of client to MAC classC multicast and broadcast
            octets in the current interval."
        ::= { rprClientCountersCurrentEntry 33 }

    -- RPR client interface interval counters table
    --
    -- 1.0.8802.17.1.1.1.4.2
    rprClientCountersIntervalTable OBJECT-TYPE
        SYNTAX SEQUENCE OF RprClientCountersIntervalEntry
        MAX-ACCESS not-accessible
        STATUS current
        DESCRIPTION
            "The local station traffic interval counters table.
            All attributes in this table are volatile,
            i.e. will be cleared on system reset."
        ::= { rprClientCounters 2 }

    -- 1.0.8802.17.1.1.1.4.2.1
    rprClientCountersIntervalEntry OBJECT-TYPE
        SYNTAX RprClientCountersIntervalEntry
        MAX-ACCESS not-accessible
        STATUS current
        DESCRIPTION
            "Frames and octets statistics collected for a particular
            interval for local station traffic of a particular RPR
            interface.
            The corresponding instance of rprIfValidIntervals indicates
            the number of intervals for which the set of statistics is
            available."
        INDEX { rprClientIntervalIfIndex, rprClientIntervalNumber }
        ::= { rprClientCountersIntervalTable 1 }

    RprClientCountersIntervalEntry ::=
        SEQUENCE {
            rprClientIntervalIfIndex
                InterfaceIndex,
            rprClientIntervalNumber
                Unsigned32,
            rprClientIntervalValidData
                TruthValue,
            rprClientIntervalTimeElapsed
                Unsigned32,
            rprClientIntervalInUcastClassAFrames
                HCPerfIntervalCount,
            rprClientIntervalInUcastClassAOctets
                HCPerfIntervalCount,
            rprClientIntervalInUcastClassBCirFrames
                HCPerfIntervalCount,
            rprClientIntervalInUcastClassBCirOctets
                HCPerfIntervalCount,
            rprClientIntervalInUcastClassBEirFrames
                HCPerfIntervalCount,
            rprClientIntervalInUcastClassBEirOctets
                HCPerfIntervalCount,
            rprClientIntervalInUcastClassCFrames
                HCPerfIntervalCount,
            rprClientIntervalInUcastClassCOctets
                HCPerfIntervalCount,
            rprClientIntervalInMcastClassAFrames
                HCPerfIntervalCount,
            rprClientIntervalInMcastClassAOctets
                HCPerfIntervalCount,
            rprClientIntervalInMcastClassBCirFrames
                HCPerfIntervalCount,
            rprClientIntervalInMcastClassBCirOctets
                HCPerfIntervalCount,
            rprClientIntervalInMcastClassBEirFrames
                HCPerfIntervalCount,
            rprClientIntervalInMcastClassBEirOctets
                HCPerfIntervalCount,
            rprClientIntervalInMcastClassCFrames
                HCPerfIntervalCount,
            rprClientIntervalInMcastClassCOctets
                HCPerfIntervalCount,
            rprClientIntervalOutUcastClassAFrames
                HCPerfIntervalCount,
            rprClientIntervalOutUcastClassAOctets
                HCPerfIntervalCount,
            rprClientIntervalOutUcastClassBCirFrames
                HCPerfIntervalCount,
            rprClientIntervalOutUcastClassBCirOctets
                HCPerfIntervalCount,
            rprClientIntervalOutUcastClassBEirFrames
                HCPerfIntervalCount,
            rprClientIntervalOutUcastClassBEirOctets
                HCPerfIntervalCount,
            rprClientIntervalOutUcastClassCFrames
                HCPerfIntervalCount,
            rprClientIntervalOutUcastClassCOctets
                HCPerfIntervalCount,
            rprClientIntervalOutMcastClassAFrames
                HCPerfIntervalCount,
            rprClientIntervalOutMcastClassAOctets
                HCPerfIntervalCount,
            rprClientIntervalOutMcastClassBCirFrames
                HCPerfIntervalCount,
            rprClientIntervalOutMcastClassBCirOctets
                HCPerfIntervalCount,
            rprClientIntervalOutMcastClassBEirFrames
                HCPerfIntervalCount,
            rprClientIntervalOutMcastClassBEirOctets
                HCPerfIntervalCount,
            rprClientIntervalOutMcastClassCFrames
                HCPerfIntervalCount,
            rprClientIntervalOutMcastClassCOctets
                HCPerfIntervalCount
         }

    -- 1.0.8802.17.1.1.1.4.2.1.1
    rprClientIntervalIfIndex OBJECT-TYPE
        SYNTAX InterfaceIndex
        MAX-ACCESS not-accessible
        STATUS current
        DESCRIPTION
            "The ifIndex of this RPR interface."
        ::= { rprClientCountersIntervalEntry 1 }

    -- 1.0.8802.17.1.1.1.4.2.1.2
    rprClientIntervalNumber OBJECT-TYPE
        SYNTAX Unsigned32 (1..96)
        MAX-ACCESS not-accessible
        STATUS current
        DESCRIPTION
            "A number between 1 and 96, which identifies the interval
            for which the set of statistics is available. The interval
            identified by 1 is the most recently completed 15 minute
            interval, and interval identified by N is the interval
            immediately preceding the one identified by N-1."
        ::= { rprClientCountersIntervalEntry 2 }

    -- 1.0.8802.17.1.1.1.4.2.1.3
    rprClientIntervalValidData OBJECT-TYPE
        SYNTAX TruthValue
        MAX-ACCESS read-only
        STATUS current
        DESCRIPTION
            "This variable indicates if the data for this interval
            is valid.
            It will be valid if it contains data for 900 seconds
            plus or minus 10 seconds."
        ::= { rprClientCountersIntervalEntry 3 }

    -- 1.0.8802.17.1.1.1.4.2.1.4
    rprClientIntervalTimeElapsed OBJECT-TYPE
        SYNTAX Unsigned32 (0..899)
        UNITS "Seconds"
        MAX-ACCESS read-only
        STATUS current
        DESCRIPTION
            "The duration of a particular interval in seconds.
            If, for some reason, such as an adjustment in the system's
            time-of-day clock, the current interval exceeds the maximum
            value, the agent will return the maximum value."
        ::= { rprClientCountersIntervalEntry 4 }

    -- 1.0.8802.17.1.1.1.4.2.1.5
    rprClientIntervalInUcastClassAFrames OBJECT-TYPE
        SYNTAX HCPerfIntervalCount
        MAX-ACCESS read-only
        STATUS current
        DESCRIPTION
            "The number of MAC to client classA unicast frames
            in a particular interval in the past 24 hours."
        ::= { rprClientCountersIntervalEntry 5 }

    -- 1.0.8802.17.1.1.1.4.2.1.6
    rprClientIntervalInUcastClassAOctets OBJECT-TYPE
        SYNTAX HCPerfIntervalCount
        MAX-ACCESS read-only
        STATUS current
        DESCRIPTION
            "The number of MAC to client classA unicast octets
            in a particular interval in the past 24 hours."
        ::= { rprClientCountersIntervalEntry 6 }

    -- 1.0.8802.17.1.1.1.4.2.1.7
    rprClientIntervalInUcastClassBCirFrames OBJECT-TYPE
        SYNTAX HCPerfIntervalCount
        MAX-ACCESS read-only
        STATUS current
        DESCRIPTION
            "The number of MAC to client classB CIR unicast frames
            in a particular interval in the past 24 hours."
        ::= { rprClientCountersIntervalEntry 7 }

    -- 1.0.8802.17.1.1.1.4.2.1.8
    rprClientIntervalInUcastClassBCirOctets OBJECT-TYPE
        SYNTAX HCPerfIntervalCount
        MAX-ACCESS read-only
        STATUS current
        DESCRIPTION
            "The number of MAC to client classB CIR unicast octets
            in a particular interval in the past 24 hours."
        ::= { rprClientCountersIntervalEntry 8 }

    -- 1.0.8802.17.1.1.1.4.2.1.9
    rprClientIntervalInUcastClassBEirFrames OBJECT-TYPE
        SYNTAX HCPerfIntervalCount
        MAX-ACCESS read-only
        STATUS current
        DESCRIPTION
            "The number of MAC to client classB EIR unicast
            frames in a particular interval in the past 24 hours."
        ::= { rprClientCountersIntervalEntry 9 }

    -- 1.0.8802.17.1.1.1.4.2.1.10
    rprClientIntervalInUcastClassBEirOctets OBJECT-TYPE
        SYNTAX HCPerfIntervalCount
        MAX-ACCESS read-only
        STATUS current
        DESCRIPTION
            "The number of MAC to client classB EIR unicast
            octets in a particular interval in the past 24 hours."
        ::= { rprClientCountersIntervalEntry 10 }

    -- 1.0.8802.17.1.1.1.4.2.1.11
    rprClientIntervalInUcastClassCFrames OBJECT-TYPE
        SYNTAX HCPerfIntervalCount
        MAX-ACCESS read-only
        STATUS current
        DESCRIPTION
            "The number of MAC to client classC unicast
            frames in a particular interval in the past 24 hours."
        ::= { rprClientCountersIntervalEntry 11 }

    -- 1.0.8802.17.1.1.1.4.2.1.12
    rprClientIntervalInUcastClassCOctets OBJECT-TYPE
        SYNTAX HCPerfIntervalCount
        MAX-ACCESS read-only
        STATUS current
        DESCRIPTION
            "The number of MAC to client classC unicast
            octets in a particular interval in the past 24 hours."
        ::= { rprClientCountersIntervalEntry 12 }

    -- 1.0.8802.17.1.1.1.4.2.1.13
    rprClientIntervalInMcastClassAFrames OBJECT-TYPE
        SYNTAX HCPerfIntervalCount
        MAX-ACCESS read-only
        STATUS current
        DESCRIPTION
            "The number of MAC to client classA multicast and broadcast
            frames in a particular interval in the past 24 hours."
        ::= { rprClientCountersIntervalEntry 13 }

    -- 1.0.8802.17.1.1.1.4.2.1.14
    rprClientIntervalInMcastClassAOctets OBJECT-TYPE
        SYNTAX HCPerfIntervalCount
        MAX-ACCESS read-only
        STATUS current
        DESCRIPTION
            "The number of MAC to client classA multicast and broadcast
            octets in a particular interval in the past 24 hours."
        ::= { rprClientCountersIntervalEntry 14 }

    -- 1.0.8802.17.1.1.1.4.2.1.15
    rprClientIntervalInMcastClassBCirFrames OBJECT-TYPE
        SYNTAX HCPerfIntervalCount
        MAX-ACCESS read-only
        STATUS current
        DESCRIPTION
            "The number of MAC to client classB CIR multicast and
            broadcast frames in a particular interval in the past
            24 hours."
        ::= { rprClientCountersIntervalEntry 15 }

    -- 1.0.8802.17.1.1.1.4.2.1.16
    rprClientIntervalInMcastClassBCirOctets OBJECT-TYPE
        SYNTAX HCPerfIntervalCount
        MAX-ACCESS read-only
        STATUS current
        DESCRIPTION
            "The number of MAC to client classB CIR multicast and
            broadcast octets in a particular interval in the past
            24 hours."
        ::= { rprClientCountersIntervalEntry 16 }

    -- 1.0.8802.17.1.1.1.4.2.1.17
    rprClientIntervalInMcastClassBEirFrames OBJECT-TYPE
        SYNTAX HCPerfIntervalCount
        MAX-ACCESS read-only
        STATUS current
        DESCRIPTION
            "The number of MAC to client classB EIR multicast and
            broadcast frames in a particular interval in the past
            24 hours."
        ::= { rprClientCountersIntervalEntry 17 }

    -- 1.0.8802.17.1.1.1.4.2.1.18
    rprClientIntervalInMcastClassBEirOctets OBJECT-TYPE
        SYNTAX HCPerfIntervalCount
        MAX-ACCESS read-only
        STATUS current
        DESCRIPTION
            "The number of MAC to client classB EIR multicast and
            broadcast octets in a particular interval in the past
            24 hours."
        ::= { rprClientCountersIntervalEntry 18 }

    -- 1.0.8802.17.1.1.1.4.2.1.19
    rprClientIntervalInMcastClassCFrames OBJECT-TYPE
        SYNTAX HCPerfIntervalCount
        MAX-ACCESS read-only
        STATUS current
        DESCRIPTION
            "The number of MAC to client classC multicast and broadcast
            frames in a particular interval in the past 24 hours."
        ::= { rprClientCountersIntervalEntry 19 }

    -- 1.0.8802.17.1.1.1.4.2.1.20
    rprClientIntervalInMcastClassCOctets OBJECT-TYPE
        SYNTAX HCPerfIntervalCount
        MAX-ACCESS read-only
        STATUS current
        DESCRIPTION
            "The number of MAC to client classC multicast and broadcast
            octets in a particular interval in the past 24 hours."
        ::= { rprClientCountersIntervalEntry 20 }

    -- 1.0.8802.17.1.1.1.4.2.1.21
    rprClientIntervalOutUcastClassAFrames OBJECT-TYPE
        SYNTAX HCPerfIntervalCount
        MAX-ACCESS read-only
        STATUS current
        DESCRIPTION
            "The number of client to MAC classA unicast frames
            in a particular interval in the past 24 hours."
        ::= { rprClientCountersIntervalEntry 21 }

    -- 1.0.8802.17.1.1.1.4.2.1.22
    rprClientIntervalOutUcastClassAOctets OBJECT-TYPE
        SYNTAX HCPerfIntervalCount
        MAX-ACCESS read-only
        STATUS current
        DESCRIPTION
            "The number of client to MAC classA unicast octets
            in a particular interval in the past 24 hours."
        ::= { rprClientCountersIntervalEntry 22 }

    -- 1.0.8802.17.1.1.1.4.2.1.23
    rprClientIntervalOutUcastClassBCirFrames OBJECT-TYPE
        SYNTAX HCPerfIntervalCount
        MAX-ACCESS read-only
        STATUS current
        DESCRIPTION
            "The number of client to MAC classB CIR unicast frames
            in a particular interval in the past 24 hours."
        ::= { rprClientCountersIntervalEntry 23 }

    -- 1.0.8802.17.1.1.1.4.2.1.24
    rprClientIntervalOutUcastClassBCirOctets OBJECT-TYPE
        SYNTAX HCPerfIntervalCount
        MAX-ACCESS read-only
        STATUS current
        DESCRIPTION
            "The number of client to MAC classB CIR unicast octets
            in a particular interval in the past 24 hours."
        ::= { rprClientCountersIntervalEntry 24 }

    -- 1.0.8802.17.1.1.1.4.2.1.25
    rprClientIntervalOutUcastClassBEirFrames OBJECT-TYPE
        SYNTAX HCPerfIntervalCount
        MAX-ACCESS read-only
        STATUS current
        DESCRIPTION
            "The number of client to MAC classB EIR unicast
            frames in a particular interval in the past 24 hours."
        ::= { rprClientCountersIntervalEntry 25 }

    -- 1.0.8802.17.1.1.1.4.2.1.26
    rprClientIntervalOutUcastClassBEirOctets OBJECT-TYPE
        SYNTAX HCPerfIntervalCount
        MAX-ACCESS read-only
        STATUS current
        DESCRIPTION
            "The number of client to MAC classB EIR unicast
            octets in a particular interval in the past 24 hours."
        ::= { rprClientCountersIntervalEntry 26 }

    -- 1.0.8802.17.1.1.1.4.2.1.27
    rprClientIntervalOutUcastClassCFrames OBJECT-TYPE
        SYNTAX HCPerfIntervalCount
        MAX-ACCESS read-only
        STATUS current
        DESCRIPTION
            "The number of client to MAC classC unicast
            frames in a particular interval in the past 24 hours."
        ::= { rprClientCountersIntervalEntry 27 }

    -- 1.0.8802.17.1.1.1.4.2.1.28
    rprClientIntervalOutUcastClassCOctets OBJECT-TYPE
        SYNTAX HCPerfIntervalCount
        MAX-ACCESS read-only
        STATUS current
        DESCRIPTION
            "The number of client to MAC classC unicast
            octets in a particular interval in the past 24 hours."
        ::= { rprClientCountersIntervalEntry 28 }

    -- 1.0.8802.17.1.1.1.4.2.1.29
    rprClientIntervalOutMcastClassAFrames OBJECT-TYPE
        SYNTAX HCPerfIntervalCount
        MAX-ACCESS read-only
        STATUS current
        DESCRIPTION
            "The number of client to MAC classA multicast and broadcast
            frames in a particular interval in the past 24 hours."
        ::= { rprClientCountersIntervalEntry 29 }

    -- 1.0.8802.17.1.1.1.4.2.1.30
    rprClientIntervalOutMcastClassAOctets OBJECT-TYPE
        SYNTAX HCPerfIntervalCount
        MAX-ACCESS read-only
        STATUS current
        DESCRIPTION
            "The number of client to MAC classA multicast and broadcast
            octets in a particular interval in the past 24 hours."
        ::= { rprClientCountersIntervalEntry 30 }

    -- 1.0.8802.17.1.1.1.4.2.1.31
    rprClientIntervalOutMcastClassBCirFrames OBJECT-TYPE
        SYNTAX HCPerfIntervalCount
        MAX-ACCESS read-only
        STATUS current
        DESCRIPTION
            "The number of client to MAC classB CIR multicast
            and broadcast frames in a particular interval in the
            past 24 hours."
        ::= { rprClientCountersIntervalEntry 31 }

    -- 1.0.8802.17.1.1.1.4.2.1.32
    rprClientIntervalOutMcastClassBCirOctets OBJECT-TYPE
        SYNTAX HCPerfIntervalCount
        MAX-ACCESS read-only
        STATUS current
        DESCRIPTION
            "The number of client to MAC classB CIR multicast
            and broadcast octets in a particular interval in the
            past 24 hours."
        ::= { rprClientCountersIntervalEntry 32 }

    -- 1.0.8802.17.1.1.1.4.2.1.33
    rprClientIntervalOutMcastClassBEirFrames OBJECT-TYPE
        SYNTAX HCPerfIntervalCount
        MAX-ACCESS read-only
        STATUS current
        DESCRIPTION
            "The number of client to MAC classB EIR multicast
            and broadcast frames in a particular interval in the
            past 24 hours."
        ::= { rprClientCountersIntervalEntry 33 }

    -- 1.0.8802.17.1.1.1.4.2.1.34
    rprClientIntervalOutMcastClassBEirOctets OBJECT-TYPE
        SYNTAX HCPerfIntervalCount
        MAX-ACCESS read-only
        STATUS current
        DESCRIPTION
            "The number of client to MAC classB EIR multicast
            and broadcast octets in a particular interval in the
            past 24 hours."
        ::= { rprClientCountersIntervalEntry 34 }

    -- 1.0.8802.17.1.1.1.4.2.1.35
    rprClientIntervalOutMcastClassCFrames OBJECT-TYPE
        SYNTAX HCPerfIntervalCount
        MAX-ACCESS read-only
        STATUS current
        DESCRIPTION
            "The number of client to MAC classC multicast and broadcast
            frames in a particular interval in the past 24 hours."
        ::= { rprClientCountersIntervalEntry 35 }

    -- 1.0.8802.17.1.1.1.4.2.1.36
    rprClientIntervalOutMcastClassCOctets OBJECT-TYPE
        SYNTAX HCPerfIntervalCount
        MAX-ACCESS read-only
        STATUS current
        DESCRIPTION
            "The number of client to MAC classC multicast and broadcast
            octets in a particular interval in the past 24 hours."
        ::= { rprClientCountersIntervalEntry 36 }

    -- RPR client interface day (24 hour summaries) counters table
    --
    -- 1.0.8802.17.1.1.1.4.3
    rprClientCountersDayTable OBJECT-TYPE
        SYNTAX SEQUENCE OF RprClientCountersDayEntry
        MAX-ACCESS not-accessible
        STATUS current
        DESCRIPTION
            "The RPR Mac Client Day Table contains the cumulative sum
            of the various statistics for the 24 hour period
            preceding the current interval.
            All attributes in this table are volatile,
            i.e. will be cleared on system reset."
        ::= { rprClientCounters 3 }

    -- 1.0.8802.17.1.1.1.4.3.1
    rprClientCountersDayEntry OBJECT-TYPE
        SYNTAX RprClientCountersDayEntry
        MAX-ACCESS not-accessible
        STATUS current
        DESCRIPTION
            "An entry in the RPR Client Day table."
        INDEX { rprClientDayIfIndex }
        ::= { rprClientCountersDayTable 1 }

    RprClientCountersDayEntry ::=
        SEQUENCE {
            rprClientDayIfIndex
                InterfaceIndex,
            rprClientDayInUcastClassAFrames
                HCPerfTotalCount,
            rprClientDayInUcastClassAOctets
                HCPerfTotalCount,
            rprClientDayInUcastClassBCirFrames
                HCPerfTotalCount,
            rprClientDayInUcastClassBCirOctets
                HCPerfTotalCount,
            rprClientDayInUcastClassBEirFrames
                HCPerfTotalCount,
            rprClientDayInUcastClassBEirOctets
                HCPerfTotalCount,
            rprClientDayInUcastClassCFrames
                HCPerfTotalCount,
            rprClientDayInUcastClassCOctets
                HCPerfTotalCount,
            rprClientDayInMcastClassAFrames
                HCPerfTotalCount,
            rprClientDayInMcastClassAOctets
                HCPerfTotalCount,
            rprClientDayInMcastClassBCirFrames
                HCPerfTotalCount,
            rprClientDayInMcastClassBCirOctets
                HCPerfTotalCount,
            rprClientDayInMcastClassBEirFrames
                HCPerfTotalCount,
            rprClientDayInMcastClassBEirOctets
                HCPerfTotalCount,
            rprClientDayInMcastClassCFrames
                HCPerfTotalCount,
            rprClientDayInMcastClassCOctets
                HCPerfTotalCount,
            rprClientDayOutUcastClassAFrames
                HCPerfTotalCount,
            rprClientDayOutUcastClassAOctets
                HCPerfTotalCount,
            rprClientDayOutUcastClassBCirFrames
                HCPerfTotalCount,
            rprClientDayOutUcastClassBCirOctets
                HCPerfTotalCount,
            rprClientDayOutUcastClassBEirFrames
                HCPerfTotalCount,
            rprClientDayOutUcastClassBEirOctets
                HCPerfTotalCount,
            rprClientDayOutUcastClassCFrames
                HCPerfTotalCount,
            rprClientDayOutUcastClassCOctets
                HCPerfTotalCount,
            rprClientDayOutMcastClassAFrames
                HCPerfTotalCount,
            rprClientDayOutMcastClassAOctets
                HCPerfTotalCount,
            rprClientDayOutMcastClassBCirFrames
                HCPerfTotalCount,
            rprClientDayOutMcastClassBCirOctets
                HCPerfTotalCount,
            rprClientDayOutMcastClassBEirFrames
                HCPerfTotalCount,
            rprClientDayOutMcastClassBEirOctets
                HCPerfTotalCount,
            rprClientDayOutMcastClassCFrames
                HCPerfTotalCount,
            rprClientDayOutMcastClassCOctets
                HCPerfTotalCount
         }

    -- 1.0.8802.17.1.1.1.4.3.1.1
    rprClientDayIfIndex OBJECT-TYPE
        SYNTAX InterfaceIndex
        MAX-ACCESS not-accessible
        STATUS current
        DESCRIPTION
            "The ifIndex of this RPR interface."
        ::= { rprClientCountersDayEntry 1 }

    -- 1.0.8802.17.1.1.1.4.3.1.2
    rprClientDayInUcastClassAFrames OBJECT-TYPE
        SYNTAX HCPerfTotalCount
        MAX-ACCESS read-only
        STATUS current
        DESCRIPTION
            "The number of MAC to client classA unicast frames."
        ::= { rprClientCountersDayEntry 2 }

    -- 1.0.8802.17.1.1.1.4.3.1.3
    rprClientDayInUcastClassAOctets OBJECT-TYPE
        SYNTAX HCPerfTotalCount
        MAX-ACCESS read-only
        STATUS current
        DESCRIPTION
            "The number of MAC to client classA unicast octets."
        ::= { rprClientCountersDayEntry 3 }

    -- 1.0.8802.17.1.1.1.4.3.1.4
    rprClientDayInUcastClassBCirFrames OBJECT-TYPE
        SYNTAX HCPerfTotalCount
        MAX-ACCESS read-only
        STATUS current
        DESCRIPTION
            "The number of MAC to client classB CIR unicast frames."
        ::= { rprClientCountersDayEntry 4 }

    -- 1.0.8802.17.1.1.1.4.3.1.5
    rprClientDayInUcastClassBCirOctets OBJECT-TYPE
        SYNTAX HCPerfTotalCount
        MAX-ACCESS read-only
        STATUS current
        DESCRIPTION
            "The number of MAC to client classB CIR unicast octets."
        ::= { rprClientCountersDayEntry 5 }

    -- 1.0.8802.17.1.1.1.4.3.1.6
    rprClientDayInUcastClassBEirFrames OBJECT-TYPE
        SYNTAX HCPerfTotalCount
        MAX-ACCESS read-only
        STATUS current
        DESCRIPTION
            "The number of MAC to client classB EIR unicast frames."
        ::= { rprClientCountersDayEntry 6 }

    -- 1.0.8802.17.1.1.1.4.3.1.7
    rprClientDayInUcastClassBEirOctets OBJECT-TYPE
        SYNTAX HCPerfTotalCount
        MAX-ACCESS read-only
        STATUS current
        DESCRIPTION
            "The number of MAC to client classB EIR unicast octets."
        ::= { rprClientCountersDayEntry 7 }

    -- 1.0.8802.17.1.1.1.4.3.1.8
    rprClientDayInUcastClassCFrames OBJECT-TYPE
        SYNTAX HCPerfTotalCount
        MAX-ACCESS read-only
        STATUS current
        DESCRIPTION
            "The number of MAC to client classC unicast frames."
        ::= { rprClientCountersDayEntry 8 }

    -- 1.0.8802.17.1.1.1.4.3.1.9
    rprClientDayInUcastClassCOctets OBJECT-TYPE
        SYNTAX HCPerfTotalCount
        MAX-ACCESS read-only
        STATUS current
        DESCRIPTION
            "The number of MAC to client classC unicast octets."
        ::= { rprClientCountersDayEntry 9 }

    -- 1.0.8802.17.1.1.1.4.3.1.10
    rprClientDayInMcastClassAFrames OBJECT-TYPE
        SYNTAX HCPerfTotalCount
        MAX-ACCESS read-only
        STATUS current
        DESCRIPTION
            "The number of MAC to client classA multicast and broadcast frames"
        ::= { rprClientCountersDayEntry 10 }

    -- 1.0.8802.17.1.1.1.4.3.1.11
    rprClientDayInMcastClassAOctets OBJECT-TYPE
        SYNTAX HCPerfTotalCount
        MAX-ACCESS read-only
        STATUS current
        DESCRIPTION
            "The number of MAC to client classA multicast and broadcast octets"
        ::= { rprClientCountersDayEntry 11 }

    -- 1.0.8802.17.1.1.1.4.3.1.12
    rprClientDayInMcastClassBCirFrames OBJECT-TYPE
        SYNTAX HCPerfTotalCount
        MAX-ACCESS read-only
        STATUS current
        DESCRIPTION
            "The number of MAC to client classB CIR multicast
            and broadcast frames"
        ::= { rprClientCountersDayEntry 12 }

    -- 1.0.8802.17.1.1.1.4.3.1.13
    rprClientDayInMcastClassBCirOctets OBJECT-TYPE
        SYNTAX HCPerfTotalCount
        MAX-ACCESS read-only
        STATUS current
        DESCRIPTION
            "The number of MAC to client classB CIR multicast
            and broadcast octets"
        ::= { rprClientCountersDayEntry 13 }

    -- 1.0.8802.17.1.1.1.4.3.1.14
    rprClientDayInMcastClassBEirFrames OBJECT-TYPE
        SYNTAX HCPerfTotalCount
        MAX-ACCESS read-only
        STATUS current
        DESCRIPTION
            "The number of MAC to client classB EIR multicast
            and broadcast frames"
        ::= { rprClientCountersDayEntry 14 }

    -- 1.0.8802.17.1.1.1.4.3.1.15
    rprClientDayInMcastClassBEirOctets OBJECT-TYPE
        SYNTAX HCPerfTotalCount
        MAX-ACCESS read-only
        STATUS current
        DESCRIPTION
            "The number of MAC to client classB EIR multicast
            and broadcast octets"
        ::= { rprClientCountersDayEntry 15 }

    -- 1.0.8802.17.1.1.1.4.3.1.16
    rprClientDayInMcastClassCFrames OBJECT-TYPE
        SYNTAX HCPerfTotalCount
        MAX-ACCESS read-only
        STATUS current
        DESCRIPTION
            "The number of MAC to client classC multicast and broadcast frames"
        ::= { rprClientCountersDayEntry 16 }

    -- 1.0.8802.17.1.1.1.4.3.1.17
    rprClientDayInMcastClassCOctets OBJECT-TYPE
        SYNTAX HCPerfTotalCount
        MAX-ACCESS read-only
        STATUS current
        DESCRIPTION
            "The number of MAC to client classC multicast and broadcast octets"
        ::= { rprClientCountersDayEntry 17 }

    -- 1.0.8802.17.1.1.1.4.3.1.18
    rprClientDayOutUcastClassAFrames OBJECT-TYPE
        SYNTAX HCPerfTotalCount
        MAX-ACCESS read-only
        STATUS current
        DESCRIPTION
            "The number of client to MAC classA unicast frames."
        ::= { rprClientCountersDayEntry 18 }

    -- 1.0.8802.17.1.1.1.4.3.1.19
    rprClientDayOutUcastClassAOctets OBJECT-TYPE
        SYNTAX HCPerfTotalCount
        MAX-ACCESS read-only
        STATUS current
        DESCRIPTION
            "The number of client to MAC classA unicast octets."
        ::= { rprClientCountersDayEntry 19 }

    -- 1.0.8802.17.1.1.1.4.3.1.20
    rprClientDayOutUcastClassBCirFrames OBJECT-TYPE
        SYNTAX HCPerfTotalCount
        MAX-ACCESS read-only
        STATUS current
        DESCRIPTION
            "The number of client to MAC classB CIR unicast frames."
        ::= { rprClientCountersDayEntry 20 }

    -- 1.0.8802.17.1.1.1.4.3.1.21
    rprClientDayOutUcastClassBCirOctets OBJECT-TYPE
        SYNTAX HCPerfTotalCount
        MAX-ACCESS read-only
        STATUS current
        DESCRIPTION
            "The number of client to MAC classB CIR unicast octets."
        ::= { rprClientCountersDayEntry 21 }

    -- 1.0.8802.17.1.1.1.4.3.1.22
    rprClientDayOutUcastClassBEirFrames OBJECT-TYPE
        SYNTAX HCPerfTotalCount
        MAX-ACCESS read-only
        STATUS current
        DESCRIPTION
            "The number of client to MAC classB EIR unicast
            frames"
        ::= { rprClientCountersDayEntry 22 }

    -- 1.0.8802.17.1.1.1.4.3.1.23
    rprClientDayOutUcastClassBEirOctets OBJECT-TYPE
        SYNTAX HCPerfTotalCount
        MAX-ACCESS read-only
        STATUS current
        DESCRIPTION
            "The number of client to MAC classB EIR unicast
            octets"
        ::= { rprClientCountersDayEntry 23 }

    -- 1.0.8802.17.1.1.1.4.3.1.24
    rprClientDayOutUcastClassCFrames OBJECT-TYPE
        SYNTAX HCPerfTotalCount
        MAX-ACCESS read-only
        STATUS current
        DESCRIPTION
            "The number of client to MAC classC unicast frames"
        ::= { rprClientCountersDayEntry 24 }

    -- 1.0.8802.17.1.1.1.4.3.1.25
    rprClientDayOutUcastClassCOctets OBJECT-TYPE
        SYNTAX HCPerfTotalCount
        MAX-ACCESS read-only
        STATUS current
        DESCRIPTION
            "The number of client to MAC classC unicast octets"
        ::= { rprClientCountersDayEntry 25 }

    -- 1.0.8802.17.1.1.1.4.3.1.26
    rprClientDayOutMcastClassAFrames OBJECT-TYPE
        SYNTAX HCPerfTotalCount
        MAX-ACCESS read-only
        STATUS current
        DESCRIPTION
            "The number of client to MAC classA multicast and broadcast
            frames."
        ::= { rprClientCountersDayEntry 26 }

    -- 1.0.8802.17.1.1.1.4.3.1.27
    rprClientDayOutMcastClassAOctets OBJECT-TYPE
        SYNTAX HCPerfTotalCount
        MAX-ACCESS read-only
        STATUS current
        DESCRIPTION
            "The number of client to MAC classA multicast and broadcast
            octets."
        ::= { rprClientCountersDayEntry 27 }

    -- 1.0.8802.17.1.1.1.4.3.1.28
    rprClientDayOutMcastClassBCirFrames OBJECT-TYPE
        SYNTAX HCPerfTotalCount
        MAX-ACCESS read-only
        STATUS current
        DESCRIPTION
            "The number of client to MAC classB CIR
            multicast and broadcast frames."
        ::= { rprClientCountersDayEntry 28 }

    -- 1.0.8802.17.1.1.1.4.3.1.29
    rprClientDayOutMcastClassBCirOctets OBJECT-TYPE
        SYNTAX HCPerfTotalCount
        MAX-ACCESS read-only
        STATUS current
        DESCRIPTION
            "The number of client to MAC classB CIR
            multicast and broadcast octets."
        ::= { rprClientCountersDayEntry 29 }

    -- 1.0.8802.17.1.1.1.4.3.1.30
    rprClientDayOutMcastClassBEirFrames OBJECT-TYPE
        SYNTAX HCPerfTotalCount
        MAX-ACCESS read-only
        STATUS current
        DESCRIPTION
            "The number of client to MAC classB EIR
            multicast and broadcast frames."
        ::= { rprClientCountersDayEntry 30 }

    -- 1.0.8802.17.1.1.1.4.3.1.31
    rprClientDayOutMcastClassBEirOctets OBJECT-TYPE
        SYNTAX HCPerfTotalCount
        MAX-ACCESS read-only
        STATUS current
        DESCRIPTION
            "The number of client to MAC classB EIR
            multicast and broadcast octets."
        ::= { rprClientCountersDayEntry 31 }

    -- 1.0.8802.17.1.1.1.4.3.1.32
    rprClientDayOutMcastClassCFrames OBJECT-TYPE
        SYNTAX HCPerfTotalCount
        MAX-ACCESS read-only
        STATUS current
        DESCRIPTION
            "The number of client to MAC classC multicast and broadcast
            frames."
        ::= { rprClientCountersDayEntry 32 }

    -- 1.0.8802.17.1.1.1.4.3.1.33
    rprClientDayOutMcastClassCOctets OBJECT-TYPE
        SYNTAX HCPerfTotalCount
        MAX-ACCESS read-only
        STATUS current
        DESCRIPTION
            "The number of client to MAC classC multicast and broadcast
            octets."
        ::= { rprClientCountersDayEntry 33 }

    -- RPR client interface continuously running counters table
    --
    -- 1.0.8802.17.1.1.1.4.4
    rprClientCountersStatsTable OBJECT-TYPE
        SYNTAX SEQUENCE OF RprClientCountersStatsEntry
        MAX-ACCESS not-accessible
        STATUS current
        DESCRIPTION
            "The local station traffic total counters table.
            The DiscontinuityTime for this table is indicated by
            ifCounterDiscontinuityTime defined in ifXTable.
            All attributes in this table are volatile,
            i.e. will be cleared on system reset."
        ::= { rprClientCounters 4 }

    -- 1.0.8802.17.1.1.1.4.4.1
    rprClientCountersStatsEntry OBJECT-TYPE
        SYNTAX RprClientCountersStatsEntry
        MAX-ACCESS not-accessible
        STATUS current
        DESCRIPTION
            "An entry in the span stats table."
        INDEX { rprClientStatsIfIndex }
        ::= { rprClientCountersStatsTable 1 }

    RprClientCountersStatsEntry ::=
        SEQUENCE {
            rprClientStatsIfIndex
                InterfaceIndex,
            rprClientStatsInUcastClassAFrames
                Counter64,
            rprClientStatsInUcastClassAOctets
                Counter64,
            rprClientStatsInUcastClassBCirFrames
                Counter64,
            rprClientStatsInUcastClassBCirOctets
                Counter64,
            rprClientStatsInUcastClassBEirFrames
                Counter64,
            rprClientStatsInUcastClassBEirOctets
                Counter64,
            rprClientStatsInUcastClassCFrames
                Counter64,
            rprClientStatsInUcastClassCOctets
                Counter64,
            rprClientStatsInMcastClassAFrames
                Counter64,
            rprClientStatsInMcastClassAOctets
                Counter64,
            rprClientStatsInMcastClassBCirFrames
                Counter64,
            rprClientStatsInMcastClassBCirOctets
                Counter64,
            rprClientStatsInMcastClassBEirFrames
                Counter64,
            rprClientStatsInMcastClassBEirOctets
                Counter64,
            rprClientStatsInMcastClassCFrames
                Counter64,
            rprClientStatsInMcastClassCOctets
                Counter64,
            rprClientStatsInBcastFrames
                Counter64,
            rprClientStatsOutUcastClassAFrames
                Counter64,
            rprClientStatsOutUcastClassAOctets
                Counter64,
            rprClientStatsOutUcastClassBCirFrames
                Counter64,
            rprClientStatsOutUcastClassBCirOctets
                Counter64,
            rprClientStatsOutUcastClassBEirFrames
                Counter64,
            rprClientStatsOutUcastClassBEirOctets
                Counter64,
            rprClientStatsOutUcastClassCFrames
                Counter64,
            rprClientStatsOutUcastClassCOctets
                Counter64,
            rprClientStatsOutMcastClassAFrames
                Counter64,
            rprClientStatsOutMcastClassAOctets
                Counter64,
            rprClientStatsOutMcastClassBCirFrames
                Counter64,
            rprClientStatsOutMcastClassBCirOctets
                Counter64,
            rprClientStatsOutMcastClassBEirFrames
                Counter64,
            rprClientStatsOutMcastClassBEirOctets
                Counter64,
            rprClientStatsOutMcastClassCFrames
                Counter64,
            rprClientStatsOutMcastClassCOctets
                Counter64,
            rprClientStatsOutBcastFrames
                Counter64
         }

    -- 1.0.8802.17.1.1.1.4.4.1.1
    rprClientStatsIfIndex OBJECT-TYPE
        SYNTAX InterfaceIndex
        MAX-ACCESS not-accessible
        STATUS current
        DESCRIPTION
            "The ifIndex of this RPR interface."
        ::= { rprClientCountersStatsEntry 1 }

    -- 1.0.8802.17.1.1.1.4.4.1.2
    rprClientStatsInUcastClassAFrames OBJECT-TYPE
        SYNTAX Counter64
        MAX-ACCESS read-only
        STATUS current
        DESCRIPTION
            "The number of MAC to client classA unicast frames."
        REFERENCE
            "IEEE 802.17 Subclause 7.2.5, toClientUcastClassAFrames"
        ::= { rprClientCountersStatsEntry 2 }

    -- 1.0.8802.17.1.1.1.4.4.1.3
    rprClientStatsInUcastClassAOctets OBJECT-TYPE
        SYNTAX Counter64
        MAX-ACCESS read-only
        STATUS current
        DESCRIPTION
            "The number of MAC to client classA unicast octets."
        REFERENCE
            "IEEE 802.17 Subclause 7.2.5, toClientUcastClassABytes"
        ::= { rprClientCountersStatsEntry 3 }

    -- 1.0.8802.17.1.1.1.4.4.1.4
    rprClientStatsInUcastClassBCirFrames OBJECT-TYPE
        SYNTAX Counter64
        MAX-ACCESS read-only
        STATUS current
        DESCRIPTION
            "The number of MAC to client classB CIR unicast frames."
        REFERENCE
            "IEEE 802.17 Subclause 7.2.5, toClientUcastClassBCirAFrames"
        ::= { rprClientCountersStatsEntry 4 }

    -- 1.0.8802.17.1.1.1.4.4.1.5
    rprClientStatsInUcastClassBCirOctets OBJECT-TYPE
        SYNTAX Counter64
        MAX-ACCESS read-only
        STATUS current
        DESCRIPTION
            "The number of MAC to client classB CIR unicast octets."
        REFERENCE
            "IEEE 802.17 Subclause 7.2.5, toClientUcastClassBCirBytes"
        ::= { rprClientCountersStatsEntry 5 }

    -- 1.0.8802.17.1.1.1.4.4.1.6
    rprClientStatsInUcastClassBEirFrames OBJECT-TYPE
        SYNTAX Counter64
        MAX-ACCESS read-only
        STATUS current
        DESCRIPTION
            "The number of MAC to client classB EIR unicast frames."
        REFERENCE
            "IEEE 802.17 Subclause 7.2.5, toClientUcastClassBEirFrames"
        ::= { rprClientCountersStatsEntry 6 }

    -- 1.0.8802.17.1.1.1.4.4.1.7
    rprClientStatsInUcastClassBEirOctets OBJECT-TYPE
        SYNTAX Counter64
        MAX-ACCESS read-only
        STATUS current
        DESCRIPTION
            "The number of MAC to client classB EIR unicast octets."
        REFERENCE
            "IEEE 802.17 Subclause 7.2.5, toClientUcastClassBEirBytes"
        ::= { rprClientCountersStatsEntry 7 }

    -- 1.0.8802.17.1.1.1.4.4.1.8
    rprClientStatsInUcastClassCFrames OBJECT-TYPE
        SYNTAX Counter64
        MAX-ACCESS read-only
        STATUS current
        DESCRIPTION
            "The number of MAC to client classC unicast frames."
        REFERENCE
            "IEEE 802.17 Subclause 7.2.5, toClientUcastClassCFrames"
        ::= { rprClientCountersStatsEntry 8 }

    -- 1.0.8802.17.1.1.1.4.4.1.9
    rprClientStatsInUcastClassCOctets OBJECT-TYPE
        SYNTAX Counter64
        MAX-ACCESS read-only
        STATUS current
        DESCRIPTION
            "The number of MAC to client classC unicast octets."
        REFERENCE
            "IEEE 802.17 Subclause 7.2.5, toClientUcastClassCBytes"
        ::= { rprClientCountersStatsEntry 9 }

    -- 1.0.8802.17.1.1.1.4.4.1.10
    rprClientStatsInMcastClassAFrames OBJECT-TYPE
        SYNTAX Counter64
        MAX-ACCESS read-only
        STATUS current
        DESCRIPTION
            "The number of MAC to client classA multicast and broadcast frames"
        REFERENCE
            "IEEE 802.17 Subclause 7.2.5, toClientMcastClassAFrames"
        ::= { rprClientCountersStatsEntry 10 }

    -- 1.0.8802.17.1.1.1.4.4.1.11
    rprClientStatsInMcastClassAOctets OBJECT-TYPE
        SYNTAX Counter64
        MAX-ACCESS read-only
        STATUS current
        DESCRIPTION
            "The number of MAC to client classA multicast and broadcast octets"
        REFERENCE
            "IEEE 802.17 Subclause 7.2.5, toClientMcastClassABytes"
        ::= { rprClientCountersStatsEntry 11 }

    -- 1.0.8802.17.1.1.1.4.4.1.12
    rprClientStatsInMcastClassBCirFrames OBJECT-TYPE
        SYNTAX Counter64
        MAX-ACCESS read-only
        STATUS current
        DESCRIPTION
            "The number of MAC to client classB CIR multicast
            and broadcast frames"
        REFERENCE
            "IEEE 802.17 Subclause 7.2.5, toClientMcastClassBCirFrames"
        ::= { rprClientCountersStatsEntry 12 }

    -- 1.0.8802.17.1.1.1.4.4.1.13
    rprClientStatsInMcastClassBCirOctets OBJECT-TYPE
        SYNTAX Counter64
        MAX-ACCESS read-only
        STATUS current
        DESCRIPTION
            "The number of MAC to client classB CIR multicast
            and broadcast octets"
        REFERENCE
            "IEEE 802.17 Subclause 7.2.5, toClientMcastClassBCirBytes"
        ::= { rprClientCountersStatsEntry 13 }

    -- 1.0.8802.17.1.1.1.4.4.1.14
    rprClientStatsInMcastClassBEirFrames OBJECT-TYPE
        SYNTAX Counter64
        MAX-ACCESS read-only
        STATUS current
        DESCRIPTION
            "The number of MAC to client classB EIR multicast
            and broadcast frames"
        REFERENCE
            "IEEE 802.17 Subclause 7.2.5, toClientMcastClassBEirFrames"
        ::= { rprClientCountersStatsEntry 14 }

    -- 1.0.8802.17.1.1.1.4.4.1.15
    rprClientStatsInMcastClassBEirOctets OBJECT-TYPE
        SYNTAX Counter64
        MAX-ACCESS read-only
        STATUS current
        DESCRIPTION
            "The number of MAC to client classB EIR multicast
            and broadcast octets"
        REFERENCE
            "IEEE 802.17 Subclause 7.2.5, toClientMcastClassBEirBytes"
        ::= { rprClientCountersStatsEntry 15 }

    -- 1.0.8802.17.1.1.1.4.4.1.16
    rprClientStatsInMcastClassCFrames OBJECT-TYPE
        SYNTAX Counter64
        MAX-ACCESS read-only
        STATUS current
        DESCRIPTION
            "The number of MAC to client classC multicast and broadcast frames"
        REFERENCE
            "IEEE 802.17 Subclause 7.2.5, toClientMcastClassCFrames"
        ::= { rprClientCountersStatsEntry 16 }

    -- 1.0.8802.17.1.1.1.4.4.1.17
    rprClientStatsInMcastClassCOctets OBJECT-TYPE
        SYNTAX Counter64
        MAX-ACCESS read-only
        STATUS current
        DESCRIPTION
            "The number of MAC to client classC multicast and broadcast octets"
        REFERENCE
            "IEEE 802.17 Subclause 7.2.5, toClientMcastClassCBytes"
        ::= { rprClientCountersStatsEntry 17 }

    -- 1.0.8802.17.1.1.1.4.4.1.18
    rprClientStatsInBcastFrames OBJECT-TYPE
        SYNTAX Counter64
        MAX-ACCESS read-only
        STATUS current
        DESCRIPTION
            "The number of MAC to client broadcast frames.
            This is used only when deriving the multicast
            and broadcast packet counters for the interface MIB."
        REFERENCE
            "IEEE 802.17 Subclause 7.2.5, toClientBcastFrames"
        ::= { rprClientCountersStatsEntry 18 }

    -- 1.0.8802.17.1.1.1.4.4.1.19
    rprClientStatsOutUcastClassAFrames OBJECT-TYPE
        SYNTAX Counter64
        MAX-ACCESS read-only
        STATUS current
        DESCRIPTION
            "The number of client to MAC classA unicast frames."
        REFERENCE
            "IEEE 802.17 Subclause 7.2.5, fromClientUcastClassAFrames"
        ::= { rprClientCountersStatsEntry 19 }

    -- 1.0.8802.17.1.1.1.4.4.1.20
    rprClientStatsOutUcastClassAOctets OBJECT-TYPE
        SYNTAX Counter64
        MAX-ACCESS read-only
        STATUS current
        DESCRIPTION
            "The number of client to MAC classA unicast octets."
        REFERENCE
            "IEEE 802.17 Subclause 7.2.5, fromClientUcastClassABytes"
        ::= { rprClientCountersStatsEntry 20 }

    -- 1.0.8802.17.1.1.1.4.4.1.21
    rprClientStatsOutUcastClassBCirFrames OBJECT-TYPE
        SYNTAX Counter64
        MAX-ACCESS read-only
        STATUS current
        DESCRIPTION
            "The number of client to MAC classB CIR unicast frames."
        REFERENCE
            "IEEE 802.17 Subclause 7.2.5, fromClientUcastClassBCirFrames"
        ::= { rprClientCountersStatsEntry 21 }

    -- 1.0.8802.17.1.1.1.4.4.1.22
    rprClientStatsOutUcastClassBCirOctets OBJECT-TYPE
        SYNTAX Counter64
        MAX-ACCESS read-only
        STATUS current
        DESCRIPTION
            "The number of client to MAC classB CIR unicast octets."
        REFERENCE
            "IEEE 802.17 Subclause 7.2.5, fromClientUcastClassBCirBytes"
        ::= { rprClientCountersStatsEntry 22 }

    -- 1.0.8802.17.1.1.1.4.4.1.23
    rprClientStatsOutUcastClassBEirFrames OBJECT-TYPE
        SYNTAX Counter64
        MAX-ACCESS read-only
        STATUS current
        DESCRIPTION
            "The number of client to MAC classB EIR unicast
            frames"
        REFERENCE
            "IEEE 802.17 Subclause 7.2.5, fromClientUcastClassBEirFrames"
        ::= { rprClientCountersStatsEntry 23 }

    -- 1.0.8802.17.1.1.1.4.4.1.24
    rprClientStatsOutUcastClassBEirOctets OBJECT-TYPE
        SYNTAX Counter64
        MAX-ACCESS read-only
        STATUS current
        DESCRIPTION
            "The number of client to MAC classB EIR unicast
            octets"
        REFERENCE
            "IEEE 802.17 Subclause 7.2.5, fromClientUcastClassBEirBytes"
        ::= { rprClientCountersStatsEntry 24 }

    -- 1.0.8802.17.1.1.1.4.4.1.25
    rprClientStatsOutUcastClassCFrames OBJECT-TYPE
        SYNTAX Counter64
        MAX-ACCESS read-only
        STATUS current
        DESCRIPTION
            "The number of client to MAC classC unicast frames"
        REFERENCE
            "IEEE 802.17 Subclause 7.2.5, fromClientUcastClassCFrames"
        ::= { rprClientCountersStatsEntry 25 }

    -- 1.0.8802.17.1.1.1.4.4.1.26
    rprClientStatsOutUcastClassCOctets OBJECT-TYPE
        SYNTAX Counter64
        MAX-ACCESS read-only
        STATUS current
        DESCRIPTION
            "The number of client to MAC classC unicast octets"
        REFERENCE
            "IEEE 802.17 Subclause 7.2.5, fromClientUcastClassCBytes"
        ::= { rprClientCountersStatsEntry 26 }

    -- 1.0.8802.17.1.1.1.4.4.1.27
    rprClientStatsOutMcastClassAFrames OBJECT-TYPE
        SYNTAX Counter64
        MAX-ACCESS read-only
        STATUS current
        DESCRIPTION
            "The number of client to MAC classA multicast and broadcast
            frames."
        REFERENCE
            "IEEE 802.17 Subclause 7.2.5, fromClientMcastClassAFrames"
        ::= { rprClientCountersStatsEntry 27 }

    -- 1.0.8802.17.1.1.1.4.4.1.28
    rprClientStatsOutMcastClassAOctets OBJECT-TYPE
        SYNTAX Counter64
        MAX-ACCESS read-only
        STATUS current
        DESCRIPTION
            "The number of client to MAC classA multicast and broadcast
            octets."
        REFERENCE
            "IEEE 802.17 Subclause 7.2.5, fromClientMcastClassABytes"
        ::= { rprClientCountersStatsEntry 28 }

    -- 1.0.8802.17.1.1.1.4.4.1.29
    rprClientStatsOutMcastClassBCirFrames OBJECT-TYPE
        SYNTAX Counter64
        MAX-ACCESS read-only
        STATUS current
        DESCRIPTION
            "The number of client to MAC classB CIR
            multicast and broadcast frames."
        REFERENCE
            "IEEE 802.17 Subclause 7.2.5, fromClientMcastClassBCirFrames"
        ::= { rprClientCountersStatsEntry 29 }

    -- 1.0.8802.17.1.1.1.4.4.1.30
    rprClientStatsOutMcastClassBCirOctets OBJECT-TYPE
        SYNTAX Counter64
        MAX-ACCESS read-only
        STATUS current
        DESCRIPTION
            "The number of client to MAC classB CIR
            multicast and broadcast octets."
        REFERENCE
            "IEEE 802.17 Subclause 7.2.5, fromClientMcastClassBCirBytes"
        ::= { rprClientCountersStatsEntry 30 }

    -- 1.0.8802.17.1.1.1.4.4.1.31
    rprClientStatsOutMcastClassBEirFrames OBJECT-TYPE
        SYNTAX Counter64
        MAX-ACCESS read-only
        STATUS current
        DESCRIPTION
            "The number of client to MAC classB EIR
            multicast and broadcast frames."
        REFERENCE
            "IEEE 802.17 Subclause 7.2.5, fromClientMcastClassBEirFrames"
        ::= { rprClientCountersStatsEntry 31 }

    -- 1.0.8802.17.1.1.1.4.4.1.32
    rprClientStatsOutMcastClassBEirOctets OBJECT-TYPE
        SYNTAX Counter64
        MAX-ACCESS read-only
        STATUS current
        DESCRIPTION
            "The number of client to MAC classB EIR
            multicast and broadcast octets."
        REFERENCE
            "IEEE 802.17 Subclause 7.2.5, fromClientMcastClassBEirBytes"
        ::= { rprClientCountersStatsEntry 32 }

    -- 1.0.8802.17.1.1.1.4.4.1.33
    rprClientStatsOutMcastClassCFrames OBJECT-TYPE
        SYNTAX Counter64
        MAX-ACCESS read-only
        STATUS current
        DESCRIPTION
            "The number of client to MAC classC multicast and broadcast
            frames."
        REFERENCE
            "IEEE 802.17 Subclause 7.2.5, fromClientMcastClassCFrames"
        ::= { rprClientCountersStatsEntry 33 }

    -- 1.0.8802.17.1.1.1.4.4.1.34
    rprClientStatsOutMcastClassCOctets OBJECT-TYPE
        SYNTAX Counter64
        MAX-ACCESS read-only
        STATUS current
        DESCRIPTION
            "The number of client to MAC classC multicast and broadcast
            octets."
        REFERENCE
            "IEEE 802.17 Subclause 7.2.5, fromClientMcastClassCBytes"
        ::= { rprClientCountersStatsEntry 34 }

    -- 1.0.8802.17.1.1.1.4.4.1.35
    rprClientStatsOutBcastFrames OBJECT-TYPE
        SYNTAX Counter64
        MAX-ACCESS read-only
        STATUS current
        DESCRIPTION
            "The number of client to MAC broadcast frames.
            This is used only when deriving the multicast
            and broadcast packet counters for the interface MIB."
        REFERENCE
            "IEEE 802.17 Subclause 7.2.5, fromClientBcastFrames"
        ::= { rprClientCountersStatsEntry 35 }

    -- 1.0.8802.17.1.1.1.5
    rprSpanErrorCounters OBJECT IDENTIFIER ::= { rprObjects 5 }

    -- RPR error current counters
    --
    -- 1.0.8802.17.1.1.1.5.1
    rprSpanErrorCountersCurrentTable OBJECT-TYPE
        SYNTAX SEQUENCE OF RprSpanErrorCountersCurrentEntry
        MAX-ACCESS not-accessible
        STATUS current
        DESCRIPTION
            "The RPR Errors Current counters table.
            All attributes in this table are volatile,
            i.e. will be cleared on system reset."
        ::= { rprSpanErrorCounters 1 }

    -- 1.0.8802.17.1.1.1.5.1.1
    rprSpanErrorCountersCurrentEntry OBJECT-TYPE
        SYNTAX RprSpanErrorCountersCurrentEntry
        MAX-ACCESS not-accessible
        STATUS current
        DESCRIPTION
            "Errors statistics for the current interval of a particular
            span of a particular RPR interface.
            The corresponding instance of rprIfTimeElapsed indicates
            the number of seconds which have elapsed so far in the
            current interval."
        INDEX { rprSpanErrorCurrentIfIndex, rprSpanErrorCurrentSpan }
        ::= { rprSpanErrorCountersCurrentTable 1 }

    RprSpanErrorCountersCurrentEntry ::=
        SEQUENCE {
            rprSpanErrorCurrentIfIndex
                InterfaceIndex,
            rprSpanErrorCurrentSpan
                RprSpan,
            rprSpanErrorCurrentTtlExpFrames
                HCPerfCurrentCount,
            rprSpanErrorCurrentTooLongFrames
                HCPerfCurrentCount,
            rprSpanErrorCurrentTooShortFrames
                HCPerfCurrentCount,
            rprSpanErrorCurrentBadHecFrames
                HCPerfCurrentCount,
            rprSpanErrorCurrentBadFcsFrames
                HCPerfCurrentCount,
            rprSpanErrorCurrentSelfSrcUcastFrames
                HCPerfCurrentCount,
            rprSpanErrorCurrentPmdAbortFrames
                HCPerfCurrentCount,
            rprSpanErrorCurrentBadAddrFrames
                HCPerfCurrentCount,
            rprSpanErrorCurrentBadParityFrames
                HCPerfCurrentCount,
            rprSpanErrorCurrentContainedFrames
                HCPerfCurrentCount,
            rprSpanErrorCurrentScffErrors
                HCPerfCurrentCount,
            rprSpanErrorCurrentErroredSeconds
                HCPerfCurrentCount,
            rprSpanErrorCurrentSeverelyErroredSeconds
                HCPerfCurrentCount,
            rprSpanErrorCurrentUnavailableSeconds
                HCPerfCurrentCount
         }

    -- 1.0.8802.17.1.1.1.5.1.1.1
    rprSpanErrorCurrentIfIndex OBJECT-TYPE
        SYNTAX InterfaceIndex
        MAX-ACCESS not-accessible
        STATUS current
        DESCRIPTION
            "The ifIndex of this RPR interface."
        REFERENCE
            "RFC 2863, ifIndex"
        ::= { rprSpanErrorCountersCurrentEntry 1 }

    -- 1.0.8802.17.1.1.1.5.1.1.2
    rprSpanErrorCurrentSpan OBJECT-TYPE
        SYNTAX RprSpan
        MAX-ACCESS not-accessible
        STATUS current
        DESCRIPTION
            "An indication of the span of the interface for which this
            row contains information."
        ::= { rprSpanErrorCountersCurrentEntry 2 }

    -- 1.0.8802.17.1.1.1.5.1.1.3
    rprSpanErrorCurrentTtlExpFrames OBJECT-TYPE
        SYNTAX HCPerfCurrentCount
        MAX-ACCESS read-only
        STATUS current
        DESCRIPTION
            "The number of received (PHY to MAC) data frames that were dropped
            due to zero Time To Live (TTL)."
        ::= { rprSpanErrorCountersCurrentEntry 3 }

    -- 1.0.8802.17.1.1.1.5.1.1.4
    rprSpanErrorCurrentTooLongFrames OBJECT-TYPE
        SYNTAX HCPerfCurrentCount
        MAX-ACCESS read-only
        STATUS current
        DESCRIPTION
            "The number of received (PHY to MAC) frames that exceed the
            maximum permitted frame size."
        ::= { rprSpanErrorCountersCurrentEntry 4 }

    -- 1.0.8802.17.1.1.1.5.1.1.5
    rprSpanErrorCurrentTooShortFrames OBJECT-TYPE
        SYNTAX HCPerfCurrentCount
        MAX-ACCESS read-only
        STATUS current
        DESCRIPTION
            "The number of received (PHY to MAC) frames shortest than the
            minimum permitted frame size."
        ::= { rprSpanErrorCountersCurrentEntry 5 }

    -- 1.0.8802.17.1.1.1.5.1.1.6
    rprSpanErrorCurrentBadHecFrames OBJECT-TYPE
        SYNTAX HCPerfCurrentCount
        MAX-ACCESS read-only
        STATUS current
        DESCRIPTION
            "The number of received (PHY to MAC) frames with HEC error."
        ::= { rprSpanErrorCountersCurrentEntry 6 }

    -- 1.0.8802.17.1.1.1.5.1.1.7
    rprSpanErrorCurrentBadFcsFrames OBJECT-TYPE
        SYNTAX HCPerfCurrentCount
        MAX-ACCESS read-only
        STATUS current
        DESCRIPTION
            "The number of received (PHY to MAC) data and control frames
            where the fcs value did not match the expected fcs value.
            This includes data frames passed to the client as a result of
            rprIfMacOperModes being not set to dropBadFcs."
        ::= { rprSpanErrorCountersCurrentEntry 7 }

    -- 1.0.8802.17.1.1.1.5.1.1.8
    rprSpanErrorCurrentSelfSrcUcastFrames OBJECT-TYPE
        SYNTAX HCPerfCurrentCount
        MAX-ACCESS read-only
        STATUS current
        DESCRIPTION
            "The number of received (PHY to MAC) unicast frames that were
            transmitted by the station itself i.e.
            the source MAC is equal to the interface MAC."
        ::= { rprSpanErrorCountersCurrentEntry 8 }

    -- 1.0.8802.17.1.1.1.5.1.1.9
    rprSpanErrorCurrentPmdAbortFrames OBJECT-TYPE
        SYNTAX HCPerfCurrentCount
        MAX-ACCESS read-only
        STATUS current
        DESCRIPTION
            "The number of received (PHY to MAC) frames that were
            aborted by the PMD."
        ::= { rprSpanErrorCountersCurrentEntry 9 }

    -- 1.0.8802.17.1.1.1.5.1.1.10
    rprSpanErrorCurrentBadAddrFrames OBJECT-TYPE
        SYNTAX HCPerfCurrentCount
        MAX-ACCESS read-only
        STATUS current
        DESCRIPTION
            "The number of received (PHY to MAC) frames
            with invalid SA value."
        ::= { rprSpanErrorCountersCurrentEntry 10 }

    -- 1.0.8802.17.1.1.1.5.1.1.11
    rprSpanErrorCurrentBadParityFrames OBJECT-TYPE
        SYNTAX HCPerfCurrentCount
        MAX-ACCESS read-only
        STATUS current
        DESCRIPTION
            "The number of received (PHY to MAC) frames
            parity value not matching the expected parity value"
        ::= { rprSpanErrorCountersCurrentEntry 11 }

    -- 1.0.8802.17.1.1.1.5.1.1.12
    rprSpanErrorCurrentContainedFrames OBJECT-TYPE
        SYNTAX HCPerfCurrentCount
        MAX-ACCESS read-only
        STATUS current
        DESCRIPTION
            "The number of received (PHY to MAC) frames
            that were removed due to context containment"
        ::= { rprSpanErrorCountersCurrentEntry 12 }

    -- 1.0.8802.17.1.1.1.5.1.1.13
    rprSpanErrorCurrentScffErrors OBJECT-TYPE
        SYNTAX HCPerfCurrentCount
        MAX-ACCESS read-only
        STATUS current
        DESCRIPTION
            "The number of received (PHY to MAC) errored SCFF,
            with bad parity, bad FCS, or both."
        ::= { rprSpanErrorCountersCurrentEntry 13 }

    -- 1.0.8802.17.1.1.1.5.1.1.14
    rprSpanErrorCurrentErroredSeconds OBJECT-TYPE
        SYNTAX HCPerfCurrentCount
        MAX-ACCESS read-only
        STATUS current
        DESCRIPTION
            "The number of errored seconds."
        ::= { rprSpanErrorCountersCurrentEntry 14 }

    -- 1.0.8802.17.1.1.1.5.1.1.15
    rprSpanErrorCurrentSeverelyErroredSeconds OBJECT-TYPE
        SYNTAX HCPerfCurrentCount
        MAX-ACCESS read-only
        STATUS current
        DESCRIPTION
            "The number of severely errored seconds."
        ::= { rprSpanErrorCountersCurrentEntry 15 }

    -- 1.0.8802.17.1.1.1.5.1.1.16
    rprSpanErrorCurrentUnavailableSeconds OBJECT-TYPE
        SYNTAX HCPerfCurrentCount
        MAX-ACCESS read-only
        STATUS current
        DESCRIPTION
            "The number of unavailable seconds."
        ::= { rprSpanErrorCountersCurrentEntry 16 }

    -- RPR error interval counters table
    --
    -- 1.0.8802.17.1.1.1.5.2
    rprSpanErrorCountersIntervalTable OBJECT-TYPE
        SYNTAX SEQUENCE OF RprSpanErrorCountersIntervalEntry
        MAX-ACCESS not-accessible
        STATUS current
        DESCRIPTION
            "The RPR Errors Interval counters table.
            All attributes in this table are volatile,
            i.e. will be cleared on system reset."
        ::= { rprSpanErrorCounters 2 }

    -- 1.0.8802.17.1.1.1.5.2.1
    rprSpanErrorCountersIntervalEntry OBJECT-TYPE
        SYNTAX RprSpanErrorCountersIntervalEntry
        MAX-ACCESS not-accessible
        STATUS current
        DESCRIPTION
            "Error statistics collected for a particular interval of a
            particular span of a particular RPR interface.
            The corresponding instance of rprIfValidIntervals indicates
            the number of intervals for which the set of statistics is
            available."
        INDEX { rprSpanErrorIntervalIfIndex, rprSpanErrorIntervalSpan, rprSpanErrorIntervalNumber }
        ::= { rprSpanErrorCountersIntervalTable 1 }

    RprSpanErrorCountersIntervalEntry ::=
        SEQUENCE {
            rprSpanErrorIntervalIfIndex
                InterfaceIndex,
            rprSpanErrorIntervalSpan
                RprSpan,
            rprSpanErrorIntervalNumber
                Unsigned32,
            rprSpanErrorIntervalValidData
                TruthValue,
            rprSpanErrorIntervalTimeElapsed
                Unsigned32,
            rprSpanErrorIntervalTtlExpFrames
                HCPerfIntervalCount,
            rprSpanErrorIntervalTooLongFrames
                HCPerfIntervalCount,
            rprSpanErrorIntervalTooShortFrames
                HCPerfIntervalCount,
            rprSpanErrorIntervalBadHecFrames
                HCPerfIntervalCount,
            rprSpanErrorIntervalBadFcsFrames
                HCPerfIntervalCount,
            rprSpanErrorIntervalSelfSrcUcastFrames
                HCPerfIntervalCount,
            rprSpanErrorIntervalPmdAbortFrames
                HCPerfIntervalCount,
            rprSpanErrorIntervalBadAddrFrames
                HCPerfIntervalCount,
            rprSpanErrorIntervalBadParityFrames
                HCPerfIntervalCount,
            rprSpanErrorIntervalContainedFrames
                HCPerfIntervalCount,
            rprSpanErrorIntervalScffErrors
                HCPerfIntervalCount,
            rprSpanErrorIntervalErroredSeconds
                HCPerfIntervalCount,
            rprSpanErrorIntervalSeverelyErroredSeconds
                HCPerfIntervalCount,
            rprSpanErrorIntervalUnavailableSeconds
                HCPerfIntervalCount
         }

    -- 1.0.8802.17.1.1.1.5.2.1.1
    rprSpanErrorIntervalIfIndex OBJECT-TYPE
        SYNTAX InterfaceIndex
        MAX-ACCESS not-accessible
        STATUS current
        DESCRIPTION
            "The ifIndex of this RPR interface."
        ::= { rprSpanErrorCountersIntervalEntry 1 }

    -- 1.0.8802.17.1.1.1.5.2.1.2
    rprSpanErrorIntervalSpan OBJECT-TYPE
        SYNTAX RprSpan
        MAX-ACCESS not-accessible
        STATUS current
        DESCRIPTION
            "An indication of the span of the interface for which this
            row contains information."
        ::= { rprSpanErrorCountersIntervalEntry 2 }

    -- 1.0.8802.17.1.1.1.5.2.1.3
    rprSpanErrorIntervalNumber OBJECT-TYPE
        SYNTAX Unsigned32 (1..96)
        MAX-ACCESS not-accessible
        STATUS current
        DESCRIPTION
            "A number between 1 and 96, which identifies the interval
            for which the set of statistics is available. The interval
            identified by 1 is the most recently completed 15 minute
            interval, and interval identified by N is the interval
            immediately preceding the one identified by N-1."
        ::= { rprSpanErrorCountersIntervalEntry 3 }

    -- 1.0.8802.17.1.1.1.5.2.1.4
    rprSpanErrorIntervalValidData OBJECT-TYPE
        SYNTAX TruthValue
        MAX-ACCESS read-only
        STATUS current
        DESCRIPTION
            "This variable indicates if the data for this interval
            is valid.
            It will be valid if it contains data for 900 seconds
            plus or minus 10 seconds."
        ::= { rprSpanErrorCountersIntervalEntry 4 }

    -- 1.0.8802.17.1.1.1.5.2.1.5
    rprSpanErrorIntervalTimeElapsed OBJECT-TYPE
        SYNTAX Unsigned32 (0..899)
        UNITS "Seconds"
        MAX-ACCESS read-only
        STATUS current
        DESCRIPTION
            "The duration of a particular interval in seconds.
            If, for some reason, such as an adjustment in the system's
            time-of-day clock, the current interval exceeds the maximum
            value, the agent will return the maximum value."
        ::= { rprSpanErrorCountersIntervalEntry 5 }

    -- 1.0.8802.17.1.1.1.5.2.1.6
    rprSpanErrorIntervalTtlExpFrames OBJECT-TYPE
        SYNTAX HCPerfIntervalCount
        MAX-ACCESS read-only
        STATUS current
        DESCRIPTION
            "The number of received (PHY to MAC) frames that were dropped due to
            zero Time To Live (TTL) in a particular interval in the
            past 24 hours"
        ::= { rprSpanErrorCountersIntervalEntry 6 }

    -- 1.0.8802.17.1.1.1.5.2.1.7
    rprSpanErrorIntervalTooLongFrames OBJECT-TYPE
        SYNTAX HCPerfIntervalCount
        MAX-ACCESS read-only
        STATUS current
        DESCRIPTION
            "The number of received (PHY to MAC) frames that exceed the maximum
            permitted frame size in a particular interval in the
            past 24 hours"
        ::= { rprSpanErrorCountersIntervalEntry 7 }

    -- 1.0.8802.17.1.1.1.5.2.1.8
    rprSpanErrorIntervalTooShortFrames OBJECT-TYPE
        SYNTAX HCPerfIntervalCount
        MAX-ACCESS read-only
        STATUS current
        DESCRIPTION
            "The number of received (PHY to MAC) frames shortest than the
            minimum permitted frame size in a particular interval
            in the past 24 hours."
        ::= { rprSpanErrorCountersIntervalEntry 8 }

    -- 1.0.8802.17.1.1.1.5.2.1.9
    rprSpanErrorIntervalBadHecFrames OBJECT-TYPE
        SYNTAX HCPerfIntervalCount
        MAX-ACCESS read-only
        STATUS current
        DESCRIPTION
            "The number of received (PHY to MAC) frames with HEC error in a
            particular interval in the past 24 hours"
        ::= { rprSpanErrorCountersIntervalEntry 9 }

    -- 1.0.8802.17.1.1.1.5.2.1.10
    rprSpanErrorIntervalBadFcsFrames OBJECT-TYPE
        SYNTAX HCPerfIntervalCount
        MAX-ACCESS read-only
        STATUS current
        DESCRIPTION
            "The number of received (PHY to MAC) data and control frames
            where the fcs value did not match the expected fcs value.
            This includes data frames passed to the client as a result of
            rprIfMacOperModes being not set to dropBadFcs."
        ::= { rprSpanErrorCountersIntervalEntry 10 }

    -- 1.0.8802.17.1.1.1.5.2.1.11
    rprSpanErrorIntervalSelfSrcUcastFrames OBJECT-TYPE
        SYNTAX HCPerfIntervalCount
        MAX-ACCESS read-only
        STATUS current
        DESCRIPTION
            "The number of received (PHY to MAC) unicast frames that were transmitted
            by the station itself i.e. the source MAC is equal to the
            interface MAC, in a particular interval in the past 24 hours"
        ::= { rprSpanErrorCountersIntervalEntry 11 }

    -- 1.0.8802.17.1.1.1.5.2.1.12
    rprSpanErrorIntervalPmdAbortFrames OBJECT-TYPE
        SYNTAX HCPerfIntervalCount
        MAX-ACCESS read-only
        STATUS current
        DESCRIPTION
            "The number of received (PHY to MAC) unicast frames that were aborted
            by the PMD layer, in a particular interval in the past
            24 hours"
        ::= { rprSpanErrorCountersIntervalEntry 12 }

    -- 1.0.8802.17.1.1.1.5.2.1.13
    rprSpanErrorIntervalBadAddrFrames OBJECT-TYPE
        SYNTAX HCPerfIntervalCount
        MAX-ACCESS read-only
        STATUS current
        DESCRIPTION
            "The number of received (PHY to MAC) frames
            with invalid SA value."
        ::= { rprSpanErrorCountersIntervalEntry 13 }

    -- 1.0.8802.17.1.1.1.5.2.1.14
    rprSpanErrorIntervalBadParityFrames OBJECT-TYPE
        SYNTAX HCPerfIntervalCount
        MAX-ACCESS read-only
        STATUS current
        DESCRIPTION
            "The number of received (PHY to MAC) frames
            parity value not matching the expected parity value"
        ::= { rprSpanErrorCountersIntervalEntry 14 }

    -- 1.0.8802.17.1.1.1.5.2.1.15
    rprSpanErrorIntervalContainedFrames OBJECT-TYPE
        SYNTAX HCPerfIntervalCount
        MAX-ACCESS read-only
        STATUS current
        DESCRIPTION
            "The number of received (PHY to MAC) frames
            that were removed due to context containment"
        ::= { rprSpanErrorCountersIntervalEntry 15 }

    -- 1.0.8802.17.1.1.1.5.2.1.16
    rprSpanErrorIntervalScffErrors OBJECT-TYPE
        SYNTAX HCPerfIntervalCount
        MAX-ACCESS read-only
        STATUS current
        DESCRIPTION
            "The number of received (PHY to MAC) errored SCFF,
            with bad parity, bad FCS, or both."
        ::= { rprSpanErrorCountersIntervalEntry 16 }

    -- 1.0.8802.17.1.1.1.5.2.1.17
    rprSpanErrorIntervalErroredSeconds OBJECT-TYPE
        SYNTAX HCPerfIntervalCount
        MAX-ACCESS read-only
        STATUS current
        DESCRIPTION
            "The number of errored seconds."
        ::= { rprSpanErrorCountersIntervalEntry 17 }

    -- 1.0.8802.17.1.1.1.5.2.1.18
    rprSpanErrorIntervalSeverelyErroredSeconds OBJECT-TYPE
        SYNTAX HCPerfIntervalCount
        MAX-ACCESS read-only
        STATUS current
        DESCRIPTION
            "The number of severely errored seconds."
        ::= { rprSpanErrorCountersIntervalEntry 18 }

    -- 1.0.8802.17.1.1.1.5.2.1.19
    rprSpanErrorIntervalUnavailableSeconds OBJECT-TYPE
        SYNTAX HCPerfIntervalCount
        MAX-ACCESS read-only
        STATUS current
        DESCRIPTION
            "The number of unavailable seconds."
        ::= { rprSpanErrorCountersIntervalEntry 19 }

    -- RPR error day (24 hour summaries) counters table
    --
    -- 1.0.8802.17.1.1.1.5.3
    rprSpanErrorCountersDayTable OBJECT-TYPE
        SYNTAX SEQUENCE OF RprSpanErrorCountersDayEntry
        MAX-ACCESS not-accessible
        STATUS current
        DESCRIPTION
            "The RPR Mac Error Day Table contains the cumulative sum
            of the various statistics for the 24 hour period
            preceding the current interval.
            All attributes in this table are volatile,
            i.e. will be cleared on system reset."
        ::= { rprSpanErrorCounters 3 }

    -- 1.0.8802.17.1.1.1.5.3.1
    rprSpanErrorCountersDayEntry OBJECT-TYPE
        SYNTAX RprSpanErrorCountersDayEntry
        MAX-ACCESS not-accessible
        STATUS current
        DESCRIPTION
            "An entry in the RPR Error Day table."
        INDEX { rprSpanErrorDayIfIndex, rprSpanErrorDaySpan }
        ::= { rprSpanErrorCountersDayTable 1 }

    RprSpanErrorCountersDayEntry ::=
        SEQUENCE {
            rprSpanErrorDayIfIndex
                InterfaceIndex,
            rprSpanErrorDaySpan
                RprSpan,
            rprSpanErrorDayTtlExpFrames
                HCPerfTotalCount,
            rprSpanErrorDayTooLongFrames
                HCPerfTotalCount,
            rprSpanErrorDayTooShortFrames
                HCPerfTotalCount,
            rprSpanErrorDayBadHecFrames
                HCPerfTotalCount,
            rprSpanErrorDayBadFcsFrames
                HCPerfTotalCount,
            rprSpanErrorDaySelfSrcUcastFrames
                HCPerfTotalCount,
            rprSpanErrorDayPmdAbortFrames
                HCPerfTotalCount,
            rprSpanErrorDayBadAddrFrames
                HCPerfTotalCount,
            rprSpanErrorDayBadParityFrames
                HCPerfTotalCount,
            rprSpanErrorDayContainedFrames
                HCPerfTotalCount,
            rprSpanErrorDayScffErrors
                HCPerfTotalCount,
            rprSpanErrorDayErroredSeconds
                HCPerfTotalCount,
            rprSpanErrorDaySeverelyErroredSeconds
                HCPerfTotalCount,
            rprSpanErrorDayUnavailableSeconds
                HCPerfTotalCount
         }

    -- 1.0.8802.17.1.1.1.5.3.1.1
    rprSpanErrorDayIfIndex OBJECT-TYPE
        SYNTAX InterfaceIndex
        MAX-ACCESS not-accessible
        STATUS current
        DESCRIPTION
            "The ifIndex of this RPR interface."
        ::= { rprSpanErrorCountersDayEntry 1 }

    -- 1.0.8802.17.1.1.1.5.3.1.2
    rprSpanErrorDaySpan OBJECT-TYPE
        SYNTAX RprSpan
        MAX-ACCESS not-accessible
        STATUS current
        DESCRIPTION
            "An indication of the span of the interface for which this
            row contains information."
        ::= { rprSpanErrorCountersDayEntry 2 }

    -- 1.0.8802.17.1.1.1.5.3.1.3
    rprSpanErrorDayTtlExpFrames OBJECT-TYPE
        SYNTAX HCPerfTotalCount
        MAX-ACCESS read-only
        STATUS current
        DESCRIPTION
            "The number of received (PHY to MAC) frames that were dropped
            due to zero Time To Live (TTL)."
        ::= { rprSpanErrorCountersDayEntry 3 }

    -- 1.0.8802.17.1.1.1.5.3.1.4
    rprSpanErrorDayTooLongFrames OBJECT-TYPE
        SYNTAX HCPerfTotalCount
        MAX-ACCESS read-only
        STATUS current
        DESCRIPTION
            "The number of received (PHY to MAC) frames that exceed the
            maximum permitted frame size."
        ::= { rprSpanErrorCountersDayEntry 4 }

    -- 1.0.8802.17.1.1.1.5.3.1.5
    rprSpanErrorDayTooShortFrames OBJECT-TYPE
        SYNTAX HCPerfTotalCount
        MAX-ACCESS read-only
        STATUS current
        DESCRIPTION
            "The number of received (PHY to MAC) frames shortest than the
            minimum permitted frame size."
        ::= { rprSpanErrorCountersDayEntry 5 }

    -- 1.0.8802.17.1.1.1.5.3.1.6
    rprSpanErrorDayBadHecFrames OBJECT-TYPE
        SYNTAX HCPerfTotalCount
        MAX-ACCESS read-only
        STATUS current
        DESCRIPTION
            "The number of received (PHY to MAC) frames with HEC error."
        ::= { rprSpanErrorCountersDayEntry 6 }

    -- 1.0.8802.17.1.1.1.5.3.1.7
    rprSpanErrorDayBadFcsFrames OBJECT-TYPE
        SYNTAX HCPerfTotalCount
        MAX-ACCESS read-only
        STATUS current
        DESCRIPTION
            "The number of received (PHY to MAC) data and control frames
            where the fcs value did not match the expected fcs value.
            This includes data frames passed to the client as a result of
            rprIfMacOperModes being not set to dropBadFcs."
        ::= { rprSpanErrorCountersDayEntry 7 }

    -- 1.0.8802.17.1.1.1.5.3.1.8
    rprSpanErrorDaySelfSrcUcastFrames OBJECT-TYPE
        SYNTAX HCPerfTotalCount
        MAX-ACCESS read-only
        STATUS current
        DESCRIPTION
            "The number of received (PHY to MAC) unicast frames that were
            transmitted by the station itself i.e.
            the source MAC is equal to the interface MAC."
        ::= { rprSpanErrorCountersDayEntry 8 }

    -- 1.0.8802.17.1.1.1.5.3.1.9
    rprSpanErrorDayPmdAbortFrames OBJECT-TYPE
        SYNTAX HCPerfTotalCount
        MAX-ACCESS read-only
        STATUS current
        DESCRIPTION
            "The number of received (PHY to MAC) frames that were
            aborted by the PMD"
        ::= { rprSpanErrorCountersDayEntry 9 }

    -- 1.0.8802.17.1.1.1.5.3.1.10
    rprSpanErrorDayBadAddrFrames OBJECT-TYPE
        SYNTAX HCPerfTotalCount
        MAX-ACCESS read-only
        STATUS current
        DESCRIPTION
            "The number of received (PHY to MAC) frames
            with invalid SA value."
        ::= { rprSpanErrorCountersDayEntry 10 }

    -- 1.0.8802.17.1.1.1.5.3.1.11
    rprSpanErrorDayBadParityFrames OBJECT-TYPE
        SYNTAX HCPerfTotalCount
        MAX-ACCESS read-only
        STATUS current
        DESCRIPTION
            "The number of received (PHY to MAC) frames
            parity value not matching the expected parity value"
        ::= { rprSpanErrorCountersDayEntry 11 }

    -- 1.0.8802.17.1.1.1.5.3.1.12
    rprSpanErrorDayContainedFrames OBJECT-TYPE
        SYNTAX HCPerfTotalCount
        MAX-ACCESS read-only
        STATUS current
        DESCRIPTION
            "The number of received (PHY to MAC) frames
            that were removed due to context containment"
        ::= { rprSpanErrorCountersDayEntry 12 }

    -- 1.0.8802.17.1.1.1.5.3.1.13
    rprSpanErrorDayScffErrors OBJECT-TYPE
        SYNTAX HCPerfTotalCount
        MAX-ACCESS read-only
        STATUS current
        DESCRIPTION
            "The number of received (PHY to MAC) errored SCFF,
            with bad parity, bad FCS, or both."
        ::= { rprSpanErrorCountersDayEntry 13 }

    -- 1.0.8802.17.1.1.1.5.3.1.14
    rprSpanErrorDayErroredSeconds OBJECT-TYPE
        SYNTAX HCPerfTotalCount
        MAX-ACCESS read-only
        STATUS current
        DESCRIPTION
            "The number of errored seconds."
        ::= { rprSpanErrorCountersDayEntry 14 }

    -- 1.0.8802.17.1.1.1.5.3.1.15
    rprSpanErrorDaySeverelyErroredSeconds OBJECT-TYPE
        SYNTAX HCPerfTotalCount
        MAX-ACCESS read-only
        STATUS current
        DESCRIPTION
            "The number of severely errored seconds."
        ::= { rprSpanErrorCountersDayEntry 15 }

    -- 1.0.8802.17.1.1.1.5.3.1.16
    rprSpanErrorDayUnavailableSeconds OBJECT-TYPE
        SYNTAX HCPerfTotalCount
        MAX-ACCESS read-only
        STATUS current
        DESCRIPTION
            "The number of unavailable seconds."
        ::= { rprSpanErrorCountersDayEntry 16 }

    -- RPR error total continuously running counters table
    --
    -- 1.0.8802.17.1.1.1.5.4
    rprSpanErrorCountersStatsTable OBJECT-TYPE
        SYNTAX SEQUENCE OF RprSpanErrorCountersStatsEntry
        MAX-ACCESS not-accessible
        STATUS current
        DESCRIPTION
            "The RPR Errors total counters table.
            The DiscontinuityTime for this table is indicated by
            ifCounterDiscontinuityTime defined in ifXTable.
            All attributes in this table are volatile,
            i.e. will be cleared on system reset."
        ::= { rprSpanErrorCounters 4 }

    -- 1.0.8802.17.1.1.1.5.4.1
    rprSpanErrorCountersStatsEntry OBJECT-TYPE
        SYNTAX RprSpanErrorCountersStatsEntry
        MAX-ACCESS not-accessible
        STATUS current
        DESCRIPTION
            "An entry in the span error counter table."
        INDEX { rprSpanErrorStatsIfIndex, rprSpanErrorStatsSpan }
        ::= { rprSpanErrorCountersStatsTable 1 }

    RprSpanErrorCountersStatsEntry ::=
        SEQUENCE {
            rprSpanErrorStatsIfIndex
                InterfaceIndex,
            rprSpanErrorStatsSpan
                RprSpan,
            rprSpanErrorStatsTtlExpFrames
                Counter64,
            rprSpanErrorStatsTooLongFrames
                Counter64,
            rprSpanErrorStatsTooShortFrames
                Counter64,
            rprSpanErrorStatsBadHecFrames
                Counter64,
            rprSpanErrorStatsBadFcsFrames
                Counter64,
            rprSpanErrorStatsSelfSrcUcastFrames
                Counter64,
            rprSpanErrorStatsPmdAbortFrames
                Counter64,
            rprSpanErrorStatsBadAddrFrames
                Counter64,
            rprSpanErrorStatsBadParityFrames
                Counter64,
            rprSpanErrorStatsContainedFrames
                Counter64,
            rprSpanErrorStatsScffErrors
                Counter64
         }

    -- 1.0.8802.17.1.1.1.5.4.1.1
    rprSpanErrorStatsIfIndex OBJECT-TYPE
        SYNTAX InterfaceIndex
        MAX-ACCESS not-accessible
        STATUS current
        DESCRIPTION
            "The ifIndex of this RPR interface."
        ::= { rprSpanErrorCountersStatsEntry 1 }

    -- 1.0.8802.17.1.1.1.5.4.1.2
    rprSpanErrorStatsSpan OBJECT-TYPE
        SYNTAX RprSpan
        MAX-ACCESS not-accessible
        STATUS current
        DESCRIPTION
            "An indication of the span of the interface for which this
            row contains information."
        REFERENCE
            "IEEE 802.17 Subclause 7.2.2, myRi"
        ::= { rprSpanErrorCountersStatsEntry 2 }

    -- 1.0.8802.17.1.1.1.5.4.1.3
    rprSpanErrorStatsTtlExpFrames OBJECT-TYPE
        SYNTAX Counter64
        MAX-ACCESS read-only
        STATUS current
        DESCRIPTION
            "The number of received (PHY to MAC) frames that were dropped
            due to zero Time To Live (TTL)."
        REFERENCE
            "IEEE 802.17 Subclause 7.6.3.6.2, ttlExpiredFrames"
        ::= { rprSpanErrorCountersStatsEntry 3 }

    -- 1.0.8802.17.1.1.1.5.4.1.4
    rprSpanErrorStatsTooLongFrames OBJECT-TYPE
        SYNTAX Counter64
        MAX-ACCESS read-only
        STATUS current
        DESCRIPTION
            "The number of received (PHY to MAC) frames that exceed the
            maximum permitted frame size."
        REFERENCE
            "IEEE 802.17 Subclause 7.6.3.6.2, tooLongFrames"
        ::= { rprSpanErrorCountersStatsEntry 4 }

    -- 1.0.8802.17.1.1.1.5.4.1.5
    rprSpanErrorStatsTooShortFrames OBJECT-TYPE
        SYNTAX Counter64
        MAX-ACCESS read-only
        STATUS current
        DESCRIPTION
            "The number of received (PHY to MAC) frames shortest than the
            minimum permitted frame size."
        REFERENCE
            "IEEE 802.17 Subclause 7.6.3.6.2, tooShortFrames"
        ::= { rprSpanErrorCountersStatsEntry 5 }

    -- 1.0.8802.17.1.1.1.5.4.1.6
    rprSpanErrorStatsBadHecFrames OBJECT-TYPE
        SYNTAX Counter64
        MAX-ACCESS read-only
        STATUS current
        DESCRIPTION
            "The number of received (PHY to MAC) frames with HEC error."
        REFERENCE
            "IEEE 802.17 Subclause 7.6.3.6.2, badHecFrames"
        ::= { rprSpanErrorCountersStatsEntry 6 }

    -- 1.0.8802.17.1.1.1.5.4.1.7
    rprSpanErrorStatsBadFcsFrames OBJECT-TYPE
        SYNTAX Counter64
        MAX-ACCESS read-only
        STATUS current
        DESCRIPTION
            "The number of received (PHY to MAC) data and control frames
            where the fcs value did not match the expected fcs value.
            This includes data frames passed to the client as a result of
            rprIfMacOperModes being not set to dropBadFcs."
        REFERENCE
            "IEEE 802.17 Subclause 7.6.3.6.2, badFcsFrames"
        ::= { rprSpanErrorCountersStatsEntry 7 }

    -- 1.0.8802.17.1.1.1.5.4.1.8
    rprSpanErrorStatsSelfSrcUcastFrames OBJECT-TYPE
        SYNTAX Counter64
        MAX-ACCESS read-only
        STATUS current
        DESCRIPTION
            "The number of received (PHY to MAC) unicast frames that were
            transmitted by the station itself i.e.
            the source MAC is equal to the interface MAC."
        REFERENCE
            "IEEE 802.17 Subclause 7.6.3.8.2, selfSourcedFrames"
        ::= { rprSpanErrorCountersStatsEntry 8 }

    -- 1.0.8802.17.1.1.1.5.4.1.9
    rprSpanErrorStatsPmdAbortFrames OBJECT-TYPE
        SYNTAX Counter64
        MAX-ACCESS read-only
        STATUS current
        DESCRIPTION
            "The number of received (PHY to MAC) frames that
            were aborted by the PMD"
        REFERENCE
            "IEEE 802.17 Subclause 8.2.2, STATUS"
        ::= { rprSpanErrorCountersStatsEntry 9 }

    -- 1.0.8802.17.1.1.1.5.4.1.10
    rprSpanErrorStatsBadAddrFrames OBJECT-TYPE
        SYNTAX Counter64
        MAX-ACCESS read-only
        STATUS current
        DESCRIPTION
            "The number of received (PHY to MAC) frames
            with invalid SA value."
        REFERENCE
            "IEEE 802.17 Subclause 7.6.3.6.2, badAddressFrames"
        ::= { rprSpanErrorCountersStatsEntry 10 }

    -- 1.0.8802.17.1.1.1.5.4.1.11
    rprSpanErrorStatsBadParityFrames OBJECT-TYPE
        SYNTAX Counter64
        MAX-ACCESS read-only
        STATUS current
        DESCRIPTION
            "The number of received (PHY to MAC) frames
            parity value not matching the expected parity value"
        REFERENCE
            "IEEE 802.17 Subclause 7.6.3.6.2, badParityFrames"
        ::= { rprSpanErrorCountersStatsEntry 11 }

    -- 1.0.8802.17.1.1.1.5.4.1.12
    rprSpanErrorStatsContainedFrames OBJECT-TYPE
        SYNTAX Counter64
        MAX-ACCESS read-only
        STATUS current
        DESCRIPTION
            "The number of received (PHY to MAC) frames
            that were removed due to context containment"
        REFERENCE
            "IEEE 802.17 Subclause , containedFrames"
        ::= { rprSpanErrorCountersStatsEntry 12 }

    -- 1.0.8802.17.1.1.1.5.4.1.13
    rprSpanErrorStatsScffErrors OBJECT-TYPE
        SYNTAX Counter64
        MAX-ACCESS read-only
        STATUS current
        DESCRIPTION
            "The number of received (PHY to MAC) errored SCFF,
            with bad parity, bad FCS, or both."
        REFERENCE
            "IEEE 802.17 Subclause 12.5.1.2, scffErrors"
        ::= { rprSpanErrorCountersStatsEntry 13 }

    -- Conformance
    --
    -- 1.0.8802.17.1.1.2
    rprConformance OBJECT IDENTIFIER ::= { ieee802dot17rprMIB 2 }

    -- conformance information
    --
    -- 1.0.8802.17.1.1.2.1
    rprGroups OBJECT IDENTIFIER ::= { rprConformance 1 }

    -- Units of conformance.
    --
    -- 1.0.8802.17.1.1.2.1.1
    rprIfGroup OBJECT-GROUP
        OBJECTS { rprIfStationsOnRing, rprIfReversionMode, rprIfProtectionWTR, rprIfProtectionFastTimer, rprIfProtectionSlowTimer,
            rprIfAtdTimer, rprIfKeepaliveTimeout, rprIfFairnessAggressive, rprIfPtqSize, rprIfStqSize,
            rprIfSTQFullThreshold, rprIfIdleThreshold, rprIfSesThreshold, rprIfWrapConfig, rprIfJumboFramePreferred,
            rprIfMacOperModes, rprIfRingOperModes, rprIfCurrentStatus }
        STATUS current
        DESCRIPTION
            "Collection of objects needed for RPR MAC
            configuration."
        ::= { rprGroups 1 }

    -- 1.0.8802.17.1.1.2.1.2
    rprIfGroupOpt OBJECT-GROUP
        OBJECTS { rprIfLastChange, rprIfChanges }
        STATUS current
        DESCRIPTION
            "Collection of objects for RPR MAC."
        ::= { rprGroups 2 }

    -- 1.0.8802.17.1.1.2.1.3
    rprIfStatsControlGroup OBJECT-GROUP
        OBJECTS { rprIfStatsControlPeriodClear, rprIfStatsControlCountPointClear, rprIfStatsControlIntervalClear, rprIfStatsControlCommitClear, rprIfStatsControlTimeElapsed,
            rprIfStatsControlValidIntervals }
        STATUS current
        DESCRIPTION
            "Collection of objects needed for RPR MAC
            statistics management."
        ::= { rprGroups 3 }

    -- 1.0.8802.17.1.1.2.1.4
    rprSpanGroup OBJECT-GROUP
        OBJECTS { rprSpanLowerLayerIfIndex, rprSpanTotalRingletReservedRate, rprSpanCurrentStatus }
        STATUS current
        DESCRIPTION
            "Collection of objects needed for RPR Span
            configuration."
        ::= { rprGroups 4 }

    -- 1.0.8802.17.1.1.2.1.5
    rprSpanGroupOpt OBJECT-GROUP
        OBJECTS { rprSpanLastChange, rprSpanChanges }
        STATUS current
        DESCRIPTION
            "Collection of objects for RPR Span."
        ::= { rprGroups 5 }

    -- 1.0.8802.17.1.1.2.1.6
    rprSpanProtectionGroup OBJECT-GROUP
        OBJECTS { rprSpanProtectionNeighborValid, rprSpanProtectionHoldOffTimer, rprSpanProtectionCommand, rprSpanProtectionCount, rprSpanProtectionDuration,
            rprSpanProtectionLastActivationTime }
        STATUS current
        DESCRIPTION
            "Collection of objects needed for RPR Span
            Protection monitoring."
        ::= { rprGroups 6 }

    -- 1.0.8802.17.1.1.2.1.7
    rprTopoGroup OBJECT-GROUP
        OBJECTS { rprTopoImageSecMacAddress1, rprTopoImageSecMacAddress2, rprTopoImageStationIfIndex, rprTopoImageStationName, rprTopoImageInetAddressType,
            rprTopoImageInetAddress, rprTopoImageCapability, rprTopoImageRinglet0Hops, rprTopoImageRinglet0ReservedRate, rprTopoImageRinglet1Hops,
            rprTopoImageRinglet1ReservedRate, rprTopoImageWestProtectionStatus, rprTopoImageWestWeight, rprTopoImageEastProtectionStatus, rprTopoImageEastWeight,
            rprTopoImageStatus }
        STATUS current
        DESCRIPTION
            "Collection of objects needed for RPR Topology
            discovery."
        ::= { rprGroups 7 }

    -- 1.0.8802.17.1.1.2.1.8
    rprFairnessGroup OBJECT-GROUP
        OBJECTS { rprFairnessRingletWeight, rprFairnessReservedRate, rprFairnessMaxAllowed, rprFairnessAgeCoef, rprFairnessRampCoef,
            rprFairnessLpCoef, rprFairnessAdvertisementRatio, rprFairnessMcffReportCoef, rprFairnessActiveWeightsCoef, rprFairnessSTQHighThreshold,
            rprFairnessSTQMedThreshold, rprFairnessSTQLowThreshold, rprFairnessRateHighThreshold, rprFairnessRateLowThreshold, rprFairnessResetWaterMarks,
            rprFairnessSTQHighWaterMark, rprFairnessSTQLowWaterMark }
        STATUS current
        DESCRIPTION
            "Collection of objects needed for RPR Fairness
            configuration."
        ::= { rprGroups 8 }

    -- 1.0.8802.17.1.1.2.1.9
    rprFairnessGroupOpt OBJECT-GROUP
        OBJECTS { rprFairnessLastChange, rprFairnessChanges }
        STATUS current
        DESCRIPTION
            "Collection of objects for RPR Fairness."
        ::= { rprGroups 9 }

    -- 1.0.8802.17.1.1.2.1.10
    rprOamGroup OBJECT-GROUP
        OBJECTS { rprOamActionType, rprOamDestAddress, rprOamRequestRinglet, rprOamResponseRinglet, rprOamClassOfService,
            rprOamUserData, rprOamProtected, rprOamRequestCount, rprOamTimeout, rprOamControl,
            rprOamResponseCount, rprOamAvResponseTime, rprOamResponseStatus }
        STATUS current
        DESCRIPTION
            "Collection of objects needed for RPR OAM
            configuration."
        ::= { rprGroups 10 }

    -- 1.0.8802.17.1.1.2.1.11
    rprIfChangeSummaryGroup OBJECT-GROUP
        OBJECTS { rprIfChangeSummaryNumInterfaces, rprIfChangeSummaryIfLastChange, rprIfChangeSummaryIfChanges, rprIfChangeSummarySpanLastChange, rprIfChangeSummarySpanChanges,
            rprIfChangeSummaryFairnessLastChange, rprIfChangeSummaryFairnessChanges }
        STATUS current
        DESCRIPTION
            "Collection of objects summarizes changes on
            the RPR interfaces."
        ::= { rprGroups 11 }

    -- 1.0.8802.17.1.1.2.1.12
    rprSpanCurrentGroup OBJECT-GROUP
        OBJECTS { rprSpanCurrentInUcastClassAFrames, rprSpanCurrentInUcastClassAOctets, rprSpanCurrentInUcastClassBCirFrames, rprSpanCurrentInUcastClassBCirOctets, rprSpanCurrentInUcastClassBEirFrames,
            rprSpanCurrentInUcastClassBEirOctets, rprSpanCurrentInUcastClassCFrames, rprSpanCurrentInUcastClassCOctets, rprSpanCurrentInMcastClassAFrames, rprSpanCurrentInMcastClassAOctets,
            rprSpanCurrentInMcastClassBCirFrames, rprSpanCurrentInMcastClassBCirOctets, rprSpanCurrentInMcastClassBEirFrames, rprSpanCurrentInMcastClassBEirOctets, rprSpanCurrentInMcastClassCFrames,
            rprSpanCurrentInMcastClassCOctets, rprSpanCurrentOutUcastClassAFrames, rprSpanCurrentOutUcastClassAOctets, rprSpanCurrentOutUcastClassBCirFrames, rprSpanCurrentOutUcastClassBCirOctets,
            rprSpanCurrentOutUcastClassBEirFrames, rprSpanCurrentOutUcastClassBEirOctets, rprSpanCurrentOutUcastClassCFrames, rprSpanCurrentOutUcastClassCOctets, rprSpanCurrentOutMcastClassAFrames,
            rprSpanCurrentOutMcastClassAOctets, rprSpanCurrentOutMcastClassBCirFrames, rprSpanCurrentOutMcastClassBCirOctets, rprSpanCurrentOutMcastClassBEirFrames, rprSpanCurrentOutMcastClassBEirOctets,
            rprSpanCurrentOutMcastClassCFrames, rprSpanCurrentOutMcastClassCOctets }
        STATUS current
        DESCRIPTION
            "Collection of objects counting MAC span current
            statistics."
        ::= { rprGroups 12 }

    -- 1.0.8802.17.1.1.2.1.13
    rprSpanIntervalGroup OBJECT-GROUP
        OBJECTS { rprSpanIntervalValidData, rprSpanIntervalTimeElapsed, rprSpanIntervalStartTime, rprSpanIntervalInUcastClassAFrames, rprSpanIntervalInUcastClassAOctets,
            rprSpanIntervalInUcastClassBCirFrames, rprSpanIntervalInUcastClassBCirOctets, rprSpanIntervalInUcastClassBEirFrames, rprSpanIntervalInUcastClassBEirOctets, rprSpanIntervalInUcastClassCFrames,
            rprSpanIntervalInUcastClassCOctets, rprSpanIntervalInMcastClassAFrames, rprSpanIntervalInMcastClassAOctets, rprSpanIntervalInMcastClassBCirFrames, rprSpanIntervalInMcastClassBCirOctets,
            rprSpanIntervalInMcastClassBEirFrames, rprSpanIntervalInMcastClassBEirOctets, rprSpanIntervalInMcastClassCFrames, rprSpanIntervalInMcastClassCOctets, rprSpanIntervalOutUcastClassAFrames,
            rprSpanIntervalOutUcastClassAOctets, rprSpanIntervalOutUcastClassBCirFrames, rprSpanIntervalOutUcastClassBCirOctets, rprSpanIntervalOutUcastClassBEirFrames, rprSpanIntervalOutUcastClassBEirOctets,
            rprSpanIntervalOutUcastClassCFrames, rprSpanIntervalOutUcastClassCOctets, rprSpanIntervalOutMcastClassAFrames, rprSpanIntervalOutMcastClassAOctets, rprSpanIntervalOutMcastClassBCirFrames,
            rprSpanIntervalOutMcastClassBCirOctets, rprSpanIntervalOutMcastClassBEirFrames, rprSpanIntervalOutMcastClassBEirOctets, rprSpanIntervalOutMcastClassCFrames, rprSpanIntervalOutMcastClassCOctets
             }
        STATUS current
        DESCRIPTION
            "Collection of objects counting MAC span intervals
            statistics."
        ::= { rprGroups 13 }

    -- 1.0.8802.17.1.1.2.1.14
    rprSpanDayGroup OBJECT-GROUP
        OBJECTS { rprSpanDayInUcastClassAFrames, rprSpanDayInUcastClassAOctets, rprSpanDayInUcastClassBCirFrames, rprSpanDayInUcastClassBCirOctets, rprSpanDayInUcastClassBEirFrames,
            rprSpanDayInUcastClassBEirOctets, rprSpanDayInUcastClassCFrames, rprSpanDayInUcastClassCOctets, rprSpanDayInMcastClassAFrames, rprSpanDayInMcastClassAOctets,
            rprSpanDayInMcastClassBCirFrames, rprSpanDayInMcastClassBCirOctets, rprSpanDayInMcastClassBEirFrames, rprSpanDayInMcastClassBEirOctets, rprSpanDayInMcastClassCFrames,
            rprSpanDayInMcastClassCOctets, rprSpanDayOutUcastClassAFrames, rprSpanDayOutUcastClassAOctets, rprSpanDayOutUcastClassBCirFrames, rprSpanDayOutUcastClassBCirOctets,
            rprSpanDayOutUcastClassBEirFrames, rprSpanDayOutUcastClassBEirOctets, rprSpanDayOutUcastClassCFrames, rprSpanDayOutUcastClassCOctets, rprSpanDayOutMcastClassAFrames,
            rprSpanDayOutMcastClassAOctets, rprSpanDayOutMcastClassBCirFrames, rprSpanDayOutMcastClassBCirOctets, rprSpanDayOutMcastClassBEirFrames, rprSpanDayOutMcastClassBEirOctets,
            rprSpanDayOutMcastClassCFrames, rprSpanDayOutMcastClassCOctets }
        STATUS current
        DESCRIPTION
            "Collection of objects counting MAC span 24 hours
            statistics."
        ::= { rprGroups 14 }

    -- 1.0.8802.17.1.1.2.1.15
    rprSpanStatsGroup OBJECT-GROUP
        OBJECTS { rprSpanStatsInUcastClassAFrames, rprSpanStatsInUcastClassAOctets, rprSpanStatsInUcastClassBCirFrames, rprSpanStatsInUcastClassBCirOctets, rprSpanStatsInUcastClassBEirFrames,
            rprSpanStatsInUcastClassBEirOctets, rprSpanStatsInUcastClassCFrames, rprSpanStatsInUcastClassCOctets, rprSpanStatsInMcastClassAFrames, rprSpanStatsInMcastClassAOctets,
            rprSpanStatsInMcastClassBCirFrames, rprSpanStatsInMcastClassBCirOctets, rprSpanStatsInMcastClassBEirFrames, rprSpanStatsInMcastClassBEirOctets, rprSpanStatsInMcastClassCFrames,
            rprSpanStatsInMcastClassCOctets, rprSpanStatsInCtrlFrames, rprSpanStatsInOamEchoFrames, rprSpanStatsInOamFlushFrames, rprSpanStatsInOamOrgFrames,
            rprSpanStatsInTopoAtdFrames, rprSpanStatsInTopoChkSumFrames, rprSpanStatsInTopoTpFrames, rprSpanStatsOutUcastClassAFrames, rprSpanStatsOutUcastClassAOctets,
            rprSpanStatsOutUcastClassBCirFrames, rprSpanStatsOutUcastClassBCirOctets, rprSpanStatsOutUcastClassBEirFrames, rprSpanStatsOutUcastClassBEirOctets, rprSpanStatsOutUcastClassCFrames,
            rprSpanStatsOutUcastClassCOctets, rprSpanStatsOutMcastClassAFrames, rprSpanStatsOutMcastClassAOctets, rprSpanStatsOutMcastClassBCirFrames, rprSpanStatsOutMcastClassBCirOctets,
            rprSpanStatsOutMcastClassBEirFrames, rprSpanStatsOutMcastClassBEirOctets, rprSpanStatsOutMcastClassCFrames, rprSpanStatsOutMcastClassCOctets, rprSpanStatsOutCtrlFrames,
            rprSpanStatsOutOamEchoFrames, rprSpanStatsOutOamFlushFrames, rprSpanStatsOutOamOrgFrames, rprSpanStatsOutTopoAtdFrames, rprSpanStatsOutTopoChkSumFrames,
            rprSpanStatsOutTopoTpFrames }
        STATUS current
        DESCRIPTION
            "Collection of objects counting MAC span total
            statistics."
        ::= { rprGroups 15 }

    -- 1.0.8802.17.1.1.2.1.16
    rprClientCurrentGroup OBJECT-GROUP
        OBJECTS { rprClientCurrentInUcastClassAFrames, rprClientCurrentInUcastClassAOctets, rprClientCurrentInUcastClassBCirFrames, rprClientCurrentInUcastClassBCirOctets, rprClientCurrentInUcastClassBEirFrames,
            rprClientCurrentInUcastClassBEirOctets, rprClientCurrentInUcastClassCFrames, rprClientCurrentInUcastClassCOctets, rprClientCurrentInMcastClassAFrames, rprClientCurrentInMcastClassAOctets,
            rprClientCurrentInMcastClassBCirFrames, rprClientCurrentInMcastClassBCirOctets, rprClientCurrentInMcastClassBEirFrames, rprClientCurrentInMcastClassBEirOctets, rprClientCurrentInMcastClassCFrames,
            rprClientCurrentInMcastClassCOctets, rprClientCurrentOutUcastClassAFrames, rprClientCurrentOutUcastClassAOctets, rprClientCurrentOutUcastClassBCirFrames, rprClientCurrentOutUcastClassBCirOctets,
            rprClientCurrentOutUcastClassBEirFrames, rprClientCurrentOutUcastClassBEirOctets, rprClientCurrentOutUcastClassCFrames, rprClientCurrentOutUcastClassCOctets, rprClientCurrentOutMcastClassAFrames,
            rprClientCurrentOutMcastClassAOctets, rprClientCurrentOutMcastClassBCirFrames, rprClientCurrentOutMcastClassBCirOctets, rprClientCurrentOutMcastClassBEirFrames, rprClientCurrentOutMcastClassBEirOctets,
            rprClientCurrentOutMcastClassCFrames, rprClientCurrentOutMcastClassCOctets }
        STATUS current
        DESCRIPTION
            "Collection of objects counting MAC client interface
            current statistics."
        ::= { rprGroups 16 }

    -- 1.0.8802.17.1.1.2.1.17
    rprClientIntervalGroup OBJECT-GROUP
        OBJECTS { rprClientIntervalValidData, rprClientIntervalTimeElapsed, rprClientIntervalInUcastClassAFrames, rprClientIntervalInUcastClassAOctets, rprClientIntervalInUcastClassBCirFrames,
            rprClientIntervalInUcastClassBCirOctets, rprClientIntervalInUcastClassBEirFrames, rprClientIntervalInUcastClassBEirOctets, rprClientIntervalInUcastClassCFrames, rprClientIntervalInUcastClassCOctets,
            rprClientIntervalInMcastClassAFrames, rprClientIntervalInMcastClassAOctets, rprClientIntervalInMcastClassBCirFrames, rprClientIntervalInMcastClassBCirOctets, rprClientIntervalInMcastClassBEirFrames,
            rprClientIntervalInMcastClassBEirOctets, rprClientIntervalInMcastClassCFrames, rprClientIntervalInMcastClassCOctets, rprClientIntervalOutUcastClassAFrames, rprClientIntervalOutUcastClassAOctets,
            rprClientIntervalOutUcastClassBCirFrames, rprClientIntervalOutUcastClassBCirOctets, rprClientIntervalOutUcastClassBEirFrames, rprClientIntervalOutUcastClassBEirOctets, rprClientIntervalOutUcastClassCFrames,
            rprClientIntervalOutUcastClassCOctets, rprClientIntervalOutMcastClassAFrames, rprClientIntervalOutMcastClassAOctets, rprClientIntervalOutMcastClassBCirFrames, rprClientIntervalOutMcastClassBCirOctets,
            rprClientIntervalOutMcastClassBEirFrames, rprClientIntervalOutMcastClassBEirOctets, rprClientIntervalOutMcastClassCFrames, rprClientIntervalOutMcastClassCOctets }
        STATUS current
        DESCRIPTION
            "Collection of objects counting MAC client interface
            intervals statistics."
        ::= { rprGroups 17 }

    -- 1.0.8802.17.1.1.2.1.18
    rprClientDayGroup OBJECT-GROUP
        OBJECTS { rprClientDayInUcastClassAFrames, rprClientDayInUcastClassAOctets, rprClientDayInUcastClassBCirFrames, rprClientDayInUcastClassBCirOctets, rprClientDayInUcastClassBEirFrames,
            rprClientDayInUcastClassBEirOctets, rprClientDayInUcastClassCFrames, rprClientDayInUcastClassCOctets, rprClientDayInMcastClassAFrames, rprClientDayInMcastClassAOctets,
            rprClientDayInMcastClassBCirFrames, rprClientDayInMcastClassBCirOctets, rprClientDayInMcastClassBEirFrames, rprClientDayInMcastClassBEirOctets, rprClientDayInMcastClassCFrames,
            rprClientDayInMcastClassCOctets, rprClientDayOutUcastClassAFrames, rprClientDayOutUcastClassAOctets, rprClientDayOutUcastClassBCirFrames, rprClientDayOutUcastClassBCirOctets,
            rprClientDayOutUcastClassBEirFrames, rprClientDayOutUcastClassBEirOctets, rprClientDayOutUcastClassCFrames, rprClientDayOutUcastClassCOctets, rprClientDayOutMcastClassAFrames,
            rprClientDayOutMcastClassAOctets, rprClientDayOutMcastClassBCirFrames, rprClientDayOutMcastClassBCirOctets, rprClientDayOutMcastClassBEirFrames, rprClientDayOutMcastClassBEirOctets,
            rprClientDayOutMcastClassCFrames, rprClientDayOutMcastClassCOctets }
        STATUS current
        DESCRIPTION
            "Collection of objects counting MAC client interface
            24 hours statistics."
        ::= { rprGroups 18 }

    -- 1.0.8802.17.1.1.2.1.19
    rprClientStatsGroup OBJECT-GROUP
        OBJECTS { rprClientStatsInUcastClassAFrames, rprClientStatsInUcastClassAOctets, rprClientStatsInUcastClassBCirFrames, rprClientStatsInUcastClassBCirOctets, rprClientStatsInUcastClassBEirFrames,
            rprClientStatsInUcastClassBEirOctets, rprClientStatsInUcastClassCFrames, rprClientStatsInUcastClassCOctets, rprClientStatsInMcastClassAFrames, rprClientStatsInMcastClassAOctets,
            rprClientStatsInMcastClassBCirFrames, rprClientStatsInMcastClassBCirOctets, rprClientStatsInMcastClassBEirFrames, rprClientStatsInMcastClassBEirOctets, rprClientStatsInMcastClassCFrames,
            rprClientStatsInMcastClassCOctets, rprClientStatsInBcastFrames, rprClientStatsOutUcastClassAFrames, rprClientStatsOutUcastClassAOctets, rprClientStatsOutUcastClassBCirFrames,
            rprClientStatsOutUcastClassBCirOctets, rprClientStatsOutUcastClassBEirFrames, rprClientStatsOutUcastClassBEirOctets, rprClientStatsOutUcastClassCFrames, rprClientStatsOutUcastClassCOctets,
            rprClientStatsOutMcastClassAFrames, rprClientStatsOutMcastClassAOctets, rprClientStatsOutMcastClassBCirFrames, rprClientStatsOutMcastClassBCirOctets, rprClientStatsOutMcastClassBEirFrames,
            rprClientStatsOutMcastClassBEirOctets, rprClientStatsOutMcastClassCFrames, rprClientStatsOutMcastClassCOctets, rprClientStatsOutBcastFrames }
        STATUS current
        DESCRIPTION
            "Collection of objects counting MAC client interface
            total statistics."
        ::= { rprGroups 19 }

    -- 1.0.8802.17.1.1.2.1.20
    rprErrorCurrentGroup OBJECT-GROUP
        OBJECTS { rprSpanErrorCurrentTtlExpFrames, rprSpanErrorCurrentTooLongFrames, rprSpanErrorCurrentTooShortFrames, rprSpanErrorCurrentBadHecFrames, rprSpanErrorCurrentBadFcsFrames,
            rprSpanErrorCurrentSelfSrcUcastFrames, rprSpanErrorCurrentPmdAbortFrames, rprSpanErrorCurrentBadAddrFrames, rprSpanErrorCurrentBadParityFrames, rprSpanErrorCurrentContainedFrames,
            rprSpanErrorCurrentScffErrors, rprSpanErrorCurrentErroredSeconds, rprSpanErrorCurrentSeverelyErroredSeconds, rprSpanErrorCurrentUnavailableSeconds }
        STATUS current
        DESCRIPTION
            "Collection of objects counting MAC span error
            current statistics."
        ::= { rprGroups 20 }

    -- 1.0.8802.17.1.1.2.1.21
    rprErrorIntervalGroup OBJECT-GROUP
        OBJECTS { rprSpanErrorIntervalValidData, rprSpanErrorIntervalTimeElapsed, rprSpanErrorIntervalTtlExpFrames, rprSpanErrorIntervalTooLongFrames, rprSpanErrorIntervalTooShortFrames,
            rprSpanErrorIntervalBadHecFrames, rprSpanErrorIntervalBadFcsFrames, rprSpanErrorIntervalSelfSrcUcastFrames, rprSpanErrorIntervalPmdAbortFrames, rprSpanErrorIntervalBadAddrFrames,
            rprSpanErrorIntervalBadParityFrames, rprSpanErrorIntervalContainedFrames, rprSpanErrorIntervalScffErrors, rprSpanErrorIntervalErroredSeconds, rprSpanErrorIntervalSeverelyErroredSeconds,
            rprSpanErrorIntervalUnavailableSeconds }
        STATUS current
        DESCRIPTION
            "Collection of objects counting MAC span error
            intervals statistics."
        ::= { rprGroups 21 }

    -- 1.0.8802.17.1.1.2.1.22
    rprErrorDayGroup OBJECT-GROUP
        OBJECTS { rprSpanErrorDayTtlExpFrames, rprSpanErrorDayTooLongFrames, rprSpanErrorDayTooShortFrames, rprSpanErrorDayBadHecFrames, rprSpanErrorDayBadFcsFrames,
            rprSpanErrorDaySelfSrcUcastFrames, rprSpanErrorDayPmdAbortFrames, rprSpanErrorDayBadAddrFrames, rprSpanErrorDayBadParityFrames, rprSpanErrorDayContainedFrames,
            rprSpanErrorDayScffErrors, rprSpanErrorDayErroredSeconds, rprSpanErrorDaySeverelyErroredSeconds, rprSpanErrorDayUnavailableSeconds }
        STATUS current
        DESCRIPTION
            "Collection of objects counting MAC span error
            24 hours statistics."
        ::= { rprGroups 22 }

    -- 1.0.8802.17.1.1.2.1.23
    rprErrorStatsGroup OBJECT-GROUP
        OBJECTS { rprSpanErrorStatsTtlExpFrames, rprSpanErrorStatsTooLongFrames, rprSpanErrorStatsTooShortFrames, rprSpanErrorStatsBadHecFrames, rprSpanErrorStatsBadFcsFrames,
            rprSpanErrorStatsSelfSrcUcastFrames, rprSpanErrorStatsPmdAbortFrames, rprSpanErrorStatsBadAddrFrames, rprSpanErrorStatsBadParityFrames, rprSpanErrorStatsContainedFrames,
            rprSpanErrorStatsScffErrors }
        STATUS current
        DESCRIPTION
            "Collection of objects counting MAC span error
            total statistics."
        ::= { rprGroups 23 }

    -- 1.0.8802.17.1.1.2.2
    rprCompliances OBJECT IDENTIFIER ::= { rprConformance 2 }

    -- this module
    -- 1.0.8802.17.1.1.2.2.1
    rprModuleTotalStatsCompliance MODULE-COMPLIANCE
        STATUS current
        DESCRIPTION
            "The compliance statement for agent that support RPR operation
            with total statistics collections."
        MODULE    -- this module
            MANDATORY-GROUPS { rprIfGroup, rprSpanGroup, rprSpanProtectionGroup, rprTopoGroup, rprFairnessGroup,
                rprSpanStatsGroup, rprClientStatsGroup, rprErrorStatsGroup }
            GROUP rprIfGroupOpt
                DESCRIPTION
                    "Collection of objects for RPR MAC.
                    This group is optional."
            GROUP rprSpanGroupOpt
                DESCRIPTION
                    "Collection of objects for RPR span.
                    This group is optional."
            GROUP rprIfStatsControlGroup
                DESCRIPTION
                    "Current, interval, total intervals and running counters management.
                    This group is optional."
            GROUP rprFairnessGroupOpt
                DESCRIPTION
                    "Collection of objects for RPR fairness.
                    This group is optional."
            GROUP rprOamGroup
                DESCRIPTION
                    "OAM Echo and Flush control and status table.
                    This group is optional."
            GROUP rprIfChangeSummaryGroup
                DESCRIPTION
                    "RPR interfaces changes summry group.
                    This group is optional."
            GROUP rprSpanCurrentGroup
                DESCRIPTION
                    "Collection of RPR MAC Span current interval counters.
                    This group is optional."
            GROUP rprSpanIntervalGroup
                DESCRIPTION
                    "Collection of RPR MAC Span counters during specific 15min
                    interval. This group is optional."
            GROUP rprSpanDayGroup
                DESCRIPTION
                    "Collection of RPR MAC Span Day counters, contains the
                    cumulative sum of the span statistics for the 24 hour period
                    preceding the current interval.
                    This group is optional, the Span Day statistics can be
                    calculated from the 96 15min Intervals table."
            GROUP rprClientCurrentGroup
                DESCRIPTION
                    "Collection of RPR MAC client interface current interval counters.
                    This group is optional."
            GROUP rprClientIntervalGroup
                DESCRIPTION
                    "Collection of RPR MAC client interface counters during
                    specific 15min interval. This group is optional."
            GROUP rprClientDayGroup
                DESCRIPTION
                    "Collection of RPR MAC Client Day counters, contains the
                    cumulative sum of the client interface statistics for the 24
                    hour period preceding the current interval.
                    This group is optional, the client Day statistics can be
                    calculated from the 96 15min Intervals table."
            GROUP rprErrorCurrentGroup
                DESCRIPTION
                    "Collection of RPR MAC span error current interval counters.
                    This group is optional."
            GROUP rprErrorIntervalGroup
                DESCRIPTION
                    "Collection of RPR MAC span error counters during
                    specific 15min interval. This group is optional."
            GROUP rprErrorDayGroup
                DESCRIPTION
                    "Collection of RPR MAC Error Day counters, contains the
                    cumulative sum of the span error statistics for the 24
                    hour period preceding the current interval.
                    This group is optional, the error Day statistics can be
                    calculated from the 96 15min Intervals table."
        ::= { rprCompliances 1 }


END

--
-- IEEE-802DOT17-RPR-MIB.mib
--
