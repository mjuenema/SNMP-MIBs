-- =============================================================================
-- Copyright (C) 2002-2003 by  H3C TECHNOLOGIES. All rights reserved.
--
-- Description:MPLS-BGP-VPN-MIB 
-- Reference:This MIB was extracted from Draft-ietf-mpls-ldp-mib-01
-- Version: V1.6
-- History:
--  VERSION    AUTHOR/          Change Description
--  OLD/NEW     DATE
--                                                  
--  #/1.1     Lingesh M        + Initial create. 
--             27/08/99
--  #/1.2     27/09/99         + Replaced the MIB objects
--                                  - hh3cMplsLdpLsrMaxIngressCrlspTnls
--                                  - hh3cMplsLdpLsrMaxInbetwnCrlspTnls
--                               with hh3cMplsLdpLsrMaxCrlspTnls
--  1.2/1.3   19/10/99         + Added hh3cMplsLdpPeerType in Peer Table.
--            04/10/99         + Added hh3cMplsLdpEntityIfTable.
--  1.3/1.4   23/11/99         + Added MIB object for Hello Hold Time in Entity
--                               Table, modified Cr-lsp Tnl index of type
--                               read-create to not-accessible.
--                             + Removed hh3cMplsLdpSessionRowStatus mib-object.
--  
--   1.1      03/01/2k         + H3C MPLS Release 1.0.0.0
--             Naren             
-- 
--   1.2      27/01/2k         + Modified for MPLS Implementation for H3C
--             Naren             Following objects are added in the Incarnation table
--                                 hh3cMplsLdpLsrMaxVcmCapability                  
--                                 hh3cMplsLdpLsrVcmPathVecInAllLblMapPresent      
--                                 hh3cMplsLdpLsrRequestRetrytimerValue            
--                                 hh3cMplsLdpLsrNumOfRequestRetryAttempts         
--                               Following Notifications are added
--                                 hh3cMplsLdpIncarnUpEventFailure
--                                 hh3cMplsLdpIncarnDownEventFailure
--                                 hh3cMplsLdpEntityUpEventFailure
--                                 hh3cMplsLdpEntityDownEventFailure
-- 
--   1.3      03/04/2k         + Changed FS related identification to hh3c 
--             David             related identification.	
--   1.4      03/14/2003       add hh3cMplsLdpSessionUpEventFailure and hh3cMplsLdpSessionDownEventFailure
--   V1.5 2004-10-12 updated by gaolong
--        Change SYNTAX clause value from INTEGER to Unsigned because the value range is (1..4294967295).
--        Change MAX-ACCESS clause value of hh3cMplsLdpCrlspTnlIndex to accessible-for-notify
--        because this index node is used when sending notification.
--   V1.6 2004-11-5  updated by liuxiaolong
--        Change DEFVAL clause value of hh3cMplsLdpLsrHopCountLimit to 32.
-- ====================================================================================
--
-- Full Copyright Notice of the MIB that was extracted from Draft-ietf-mpls-ldp-mib-01 as followsú¦
--
--Copyright (C) The Internet Society (1999). All Rights Reserved.
--
--
--   This document and translations of it may be copied and furnished to
--   others, and derivative works that comment on or otherwise explain it
--   or assist in its implementation may be prepared, copied, published
--   and distributed, in whole or in part, without restriction of any
--   kind, provided that the above copyright notice and this paragraph are
--   included on all such copies and derivative works.  However, this
--   document itself may not be modified in any way, such as by removing
--   the copyright notice or references to the Internet Society or other
--   Internet organizations, except as needed for the  purpose of
--   developing Internet standards in which case the procedures for
--   copyrights defined in the Internet Standards process must be
--   followed, or as required to translate it into languages other than
--   English.
--
--   The limited permissions granted above are perpetual and will not be
--   revoked by the Internet Society or its successors or assigns.
--
--   This document and the information contained herein is provided on an
--   "AS IS" basis and THE INTERNET SOCIETY AND THE INTERNET ENGINEERING
--   TASK FORCE DISCLAIMS ALL WARRANTIES, EXPRESS OR IMPLIED, INCLUDING
--   BUT NOT LIMITED TO ANY WARRANTY THAT THE USE OF THE INFORMATION
--   HEREIN WILL NOT INFRINGE ANY RIGHTS OR ANY IMPLIED WARRANTIES OF
--   MERCHANTABILITY OR FITNESS FOR A PARTICULAR PURPOSE.
--
--  H3CMPLS Label Distribution Protocol MIB Definitions
HH3C-MPLS-LDP-MIB DEFINITIONS ::= BEGIN

     IMPORTS                  
         hh3cMpls
             FROM HH3C-OID-MIB
         OBJECT-TYPE, MODULE-IDENTITY, NOTIFICATION-TYPE,
         Integer32, Counter32, Unsigned32,IpAddress
             FROM SNMPv2-SMI
         MODULE-COMPLIANCE, OBJECT-GROUP, NOTIFICATION-GROUP
             FROM SNMPv2-CONF
         TEXTUAL-CONVENTION, TruthValue, RowStatus, TimeInterval
             FROM SNMPv2-TC;
             
     hh3cMplsLdp MODULE-IDENTITY
         LAST-UPDATED "9906301200Z"     -- June 30, 1999 at 12:00 GMT
         ORGANIZATION
             "Hangzhou H3C Tech. Co., Ltd."
         CONTACT-INFO
             "Platform Team Hangzhou H3C Tech. Co., Ltd.
             Hai-Dian District Beijing P.R. China
             http://www.h3c.com
             Zip:100085
             "
         DESCRIPTION  "All rights reserved"
         REVISION     "9611082155Z"
         DESCRIPTION  "The MIB for H3CMPLS LDP module.
                       This MIB has been derived from the MPLS Working 
                       group LDP MIB <drst-ietf-mpls-ldp-mib-01.txt> and
                       MPLS Working group TE MIB <draft-ietf-mpls-te-mib
                       -01.txt>."

         ::= { hh3cMpls 2 }

     --********************************************************************
     -- MPLS LDP Textual Conventions
     --********************************************************************
     --

           DisplayString ::=
               OCTET STRING
          -- This data type is used to model textual information taken
          -- from the NVT ASCII character set.  By convention, objects
          -- with this syntax are declared as having
          --
                (SIZE (0..255))

           PhysAddress ::=
               OCTET STRING
          -- This data type is used to model media addresses.  For many
          -- types of media, this will be in a binary representation.
          -- For example, an ethernet address would be represented as
          -- a string of 6 octets.

	BitRate ::= INTEGER
	
	BurstSize ::= INTEGER
	
	
     MplsLsrIdentifier ::= TEXTUAL-CONVENTION
         STATUS      current
         DESCRIPTION
             "The Label Switch Router (LSR) identifier
             is the first 4 bytes or the IP Address component
             of the Label Distribution Protocol (LDP) identifier."
         SYNTAX      OCTET STRING (SIZE (4))

     MplsLdpGenAddr ::= TEXTUAL-CONVENTION
         STATUS      current
         DESCRIPTION
             "The value of an network layer or data link layer address."
         SYNTAX      OCTET STRING (SIZE (0..64))

     MplsLdpIdentifier ::= TEXTUAL-CONVENTION
         STATUS      current
         DESCRIPTION
             "The LDP identifier is a six octet quantity
             which is used to identify an Label Switch Router
             (LSR) label space.

             The first four octets encode an IP address
             assigned to the LSR, and the last two octets
             identify a specific label space within the LSR."
         SYNTAX      OCTET STRING (SIZE (6))

     AtmVpIdentifier ::= TEXTUAL-CONVENTION
          STATUS      current
          DESCRIPTION
              "The VPI value for a VPL. The value VPI=0 is not
              used for a VPL not associated with a VCL. For ATM
              UNIs supporting VPCs the VPI value ranges from 1
              to 255. For ATM UNIs supporting VCCs the VPI value
              ranges from 0 to 255.  The maximum VPI value
              cannot exceed the value allowable by
              atmInterfaceMaxVpiBits defined in ATM-MIB."
          SYNTAX INTEGER (0..4095)

     AtmVcIdentifier ::= TEXTUAL-CONVENTION
          STATUS      current
          DESCRIPTION
              "The VCI value for a VCL. The maximum VCI value
              cannot exceed the value allowable by
              atmInterfaceMaxVciBits defined in ATM-MIB."
          SYNTAX INTEGER (0..65535)

     AddressFamilyNumbers ::= TEXTUAL-CONVENTION
        STATUS        current
        DESCRIPTION
            "An address family.  Values are defined in RFC 1700 -
             Assigned Numbers.  All values may not be relevant in
             all contexts when used in this MIB, but are included
             for completeness."
        REFERENCE
            "RFC  1700   Assigned Numbers, Reynolds and  Postel,
             Oct. 1994"
        SYNTAX        INTEGER {
                        other(0),
                         ipv4(1),
                         ipv6(2),
                         nsap(3),
                         hdlc(4),
                         bbn1822(5),
                         ieee802(6),
                         e163(7),
                         e164(8),
                         f69(9),
                         x121(10),
                         ipx(11),
                         appleTalk(12),
                         decnetIV(13),
                         banyanVines(14),
                         e164WithNsap(15)
                     }


     MplsLabel ::= TEXTUAL-CONVENTION
        STATUS        current
        DESCRIPTION
            "Represents an MPLS label.  Note that the contents of
             a  label  field are interpreted in an interface-type
             specific fashion.  For example, the label carried in
             the MPLS shim header is 20 bits wide and the top  12
             bits  must  be zero.  The frame relay label  can  be
             either 10, 17 or 23 bits wide depending on the  size
             of the DLCI field size and the top 22, 15, or 9 bits
             must  be  zero, respectively.  For an ATM interface,
             the  lowermost 16 bits are interpreted as  the  VCI,
             the  next  8 bits as the VPI and the remaining  bits
             must  be  zero.   Also  note the  permissible  label
             values  are  also a function of the interface  type.
             For  example,  the value 3 has special semantics  in
             the  control plane for an MPLS shim header label and
             is not a valid label value in the datapath."
        REFERENCE
            "1.  MPLS  Label Stack Encoding, Rosen et al,  draft-
             ietf-mpls-label-encaps-04.txt, April 1999.
            2.  Use  of  Label Switching on Frame Relay Networks,
             Conta et al, draft-ietf-mpls-fr-03.txt, Nov. 1998."
        SYNTAX INTEGER
     
     MplsTunnelIndex ::= TEXTUAL-CONVENTION
        STATUS        current
        DESCRIPTION
            "Index into mplsTunnelTable."
        SYNTAX        INTEGER (0..65535)
     
     hh3cMplsLdpObjects       OBJECT IDENTIFIER ::= { hh3cMplsLdp 1 }
     hh3cMplsLdpNotifications OBJECT IDENTIFIER ::= { hh3cMplsLdp 2 }

     --****************************************************************
     -- MPLS LDP Objects
     --****************************************************************

     hh3cMplsLdpLsrObjects            OBJECT IDENTIFIER ::= { hh3cMplsLdpObjects 1 }
     hh3cMplsLdpEntityObjects         OBJECT IDENTIFIER ::= { hh3cMplsLdpObjects 2 }
     hh3cMplsLdpPeerObjects           OBJECT IDENTIFIER ::= { hh3cMplsLdpObjects 3 }
     hh3cMplsLdpSessionObjects        OBJECT IDENTIFIER ::= { hh3cMplsLdpObjects 4 }
     hh3cMplsLdpHelloAdjacencyObjects OBJECT IDENTIFIER ::= { hh3cMplsLdpObjects 5 }
     hh3cMplsLdpCrlspTnlObjects       OBJECT IDENTIFIER ::= { hh3cMplsLdpObjects 6 }

     --
     -- The MPLS Label Distribution Protocol Label Switch Router Objects
     --
     hh3cMplsLdpLsrIncarnTable OBJECT-TYPE
         SYNTAX      SEQUENCE OF Hh3cMplsLdpLsrIncarnEntry
         MAX-ACCESS  not-accessible
         STATUS      current
         DESCRIPTION
             "H3CMPLS provides support for multiple incarnations of the 
              MPLS Stack in a target. The LSR defined in the standard <IETF
              DRAFT> MIB is treated as an incarnation in this MIB. Using a
              local policy the Network administrator must group the LDP Entities
              that should be placed in an incarnation."
         ::= { hh3cMplsLdpLsrObjects 1 }

     hh3cMplsLdpLsrIncarnEntry OBJECT-TYPE
         SYNTAX      Hh3cMplsLdpLsrIncarnEntry
         MAX-ACCESS  not-accessible
         STATUS      current
         DESCRIPTION
             "An entry in this table represents an LSR incarnation.
              All the entries in this table are created initially when the 
              LDP is initiated. The row status of each entry will be in 
              'notInService' state initially. The row status must be set to
              'active' after the necessary configurations are complete with
              respect to an incarnation.

              Currenlty the LSR ID of the incarnation is the only mandatory
              parameter that must be set before the rowStatus is set to 
              'active'.

              An LSR Incarnation Entity is uniquely indexed by its Incarnation
              Identifier."
         INDEX       {  hh3cMplsLdpLsrIncarnID }
         ::= { hh3cMplsLdpLsrIncarnTable 1 }

     Hh3cMplsLdpLsrIncarnEntry ::= SEQUENCE {
         hh3cMplsLdpLsrID                                MplsLsrIdentifier,
         hh3cMplsLdpLsrLoopDetectionPresent              TruthValue,
         hh3cMplsLdpLsrLoopDetectionAdminStatus          INTEGER,
         hh3cMplsLdpLsrPathVectorLimit                   INTEGER,
         hh3cMplsLdpLsrHopCountLimit                     INTEGER,
         hh3cMplsLdpLsrLoopPreventionPresent             TruthValue,
         hh3cMplsLdpLsrLoopPreventionAdminStatus         INTEGER,
         hh3cMplsLdpLsrLabelRetentionMode                INTEGER,
         hh3cMplsLdpLsrIncarnID                          INTEGER,
         hh3cMplsLdpLsrMaxLdpEntities                    INTEGER,
         hh3cMplsLdpLsrMaxLocalPeers                     INTEGER,
         hh3cMplsLdpLsrMaxRemotePeers                    INTEGER,
         hh3cMplsLdpLsrMaxIfaces                         INTEGER,
         hh3cMplsLdpLsrMaxLsps                           INTEGER,
         hh3cMplsLdpLsrMaxCrlspTnls                      INTEGER,
         hh3cMplsLdpLsrMaxErhopPerCrlspTnl               INTEGER,
         hh3cMplsLdpLsrRowStatus                         RowStatus,
         hh3cMplsLdpLsrMaxVcmCapability                  INTEGER,  
         hh3cMplsLdpLsrVcmPathVecInAllLblMapPresent      TruthValue,
         hh3cMplsLdpLsrRequestRetrytimerValue            INTEGER,
         hh3cMplsLdpLsrNumOfRequestRetryAttempts         INTEGER
    }

     hh3cMplsLdpLsrID OBJECT-TYPE
         SYNTAX      MplsLsrIdentifier
         MAX-ACCESS  read-write   
         STATUS      current
         DESCRIPTION
             "The LSR's Identifier."
         ::= { hh3cMplsLdpLsrIncarnEntry 1 }

     hh3cMplsLdpLsrLoopDetectionPresent OBJECT-TYPE
         SYNTAX      TruthValue
         MAX-ACCESS  read-only
         STATUS      current
         DESCRIPTION
             "A indication of whether this LSR supports loop detection.  A 
             value of 'true' indicates this LSR does support loop detection.  
             A value of 'false' indicates this LSR does not support
             loop detection."
         DEFVAL  { true }
         ::= { hh3cMplsLdpLsrIncarnEntry 2 }

     hh3cMplsLdpLsrLoopDetectionAdminStatus OBJECT-TYPE
         SYNTAX      INTEGER {
                         enabled(1),
                         disabled(2)
                     }
         MAX-ACCESS  read-write
         STATUS      current
         DESCRIPTION
             "To enable loop detection the value of this object should be 
             'enabled(1)'.  Otherwise, to turn off loop detection, set this 
             value to 'disabled(2)'."
         DEFVAL  { enabled }
         ::= { hh3cMplsLdpLsrIncarnEntry 3 }

     hh3cMplsLdpLsrPathVectorLimit OBJECT-TYPE
         SYNTAX      INTEGER
         MAX-ACCESS  read-write
         STATUS      current
         DESCRIPTION
             "This object only has meaning if hh3cMplsLdpLsrLoopDetectionPresent 
             has the value of 'true'.

             The value of this object represents the limit of path vectors which
             this LSR uses to treat the message as if it had traversed a loop."
         DEFVAL  { 32 }
         ::= { hh3cMplsLdpLsrIncarnEntry 4 }

     hh3cMplsLdpLsrHopCountLimit OBJECT-TYPE
         SYNTAX      INTEGER
         MAX-ACCESS  read-write
         STATUS      current
         DESCRIPTION
             "This object only has meaning if hh3cMplsLdpLsrLoopDetectionPresent 
             has the value of 'true'.

             The value of this object represents the limit on the Hop Count 
             which this LSR uses to treat the message as if it had traversed a 
             loop."
         DEFVAL  { 32 }
         ::= { hh3cMplsLdpLsrIncarnEntry 5 }

     hh3cMplsLdpLsrLoopPreventionPresent OBJECT-TYPE
         SYNTAX      TruthValue
         MAX-ACCESS  read-only
         STATUS      current
         DESCRIPTION
             "A indication of whether this LSR supports loop prevention.  A 
             value of 'true' indicates this LSR does support loop prevention.  
             A value of 'false' indicates this LSR does not support loop 
             prevention.

             Current release of H3CMPLS does not provide support to assign
             this MIB object with a value 'true'."
         DEFVAL  { false }
         ::= { hh3cMplsLdpLsrIncarnEntry 6 }

     hh3cMplsLdpLsrLoopPreventionAdminStatus OBJECT-TYPE
         SYNTAX      INTEGER {
                         enabled(1),
                         disabled(2)
                     }
         MAX-ACCESS  read-write
         STATUS      current
         DESCRIPTION
             "To enable loop prevention the value of this object should be 
             'enabled(1)'.  Otherwise, to turn off loop prevention, set this 
             value to 'disabled(2)'.

             Current release of H3CMPLS does not provide support to assign
             this MIB object with a value 'enabled'."
         DEFVAL  { disabled }
         ::= { hh3cMplsLdpLsrIncarnEntry 7 }

     hh3cMplsLdpLsrLabelRetentionMode OBJECT-TYPE
         SYNTAX      INTEGER {
                         conservative(1),
                         liberal(2)
                     }
         MAX-ACCESS  read-write
         STATUS      current
         DESCRIPTION
             "The LSR can be configured to use either conservative or liberal 
              label retention mode.

             If the value of this object is conservative(1) then advertized 
             label mappings are retained only if they will be used to forward 
             packets, i.e. if label came from a valid next hop.  If the value of
             this object is liberal(2) then all advertized label mappings are 
             retained whether they are from a valid next hop or not.

             Current release of H3CMPLS does not provide support to assign
             this MIB object with a value 'liberal'."
         DEFVAL  { conservative }
         ::= { hh3cMplsLdpLsrIncarnEntry 8 }

     hh3cMplsLdpLsrIncarnID   OBJECT-TYPE
         SYNTAX     INTEGER
         MAX-ACCESS read-only
         STATUS     current
         DESCRIPTION 
             "The incarnation acts as index to all the elements in this
              table."
         ::= { hh3cMplsLdpLsrIncarnEntry  9 }
 
     hh3cMplsLdpLsrMaxLdpEntities OBJECT-TYPE
         SYNTAX      INTEGER (1..1024)
         MAX-ACCESS  read-write
         STATUS      current
         DESCRIPTION
             "The maximum number of LDP entities that can be supported by this
              Incarnation."
         ::= { hh3cMplsLdpLsrIncarnEntry 10 }

     hh3cMplsLdpLsrMaxLocalPeers OBJECT-TYPE
         SYNTAX      INTEGER (1..1024)
         MAX-ACCESS  read-write
         STATUS      current
         DESCRIPTION
             "The maximum number of Local LDP peers that can be supported by 
              this Incarnation."
         ::= { hh3cMplsLdpLsrIncarnEntry 11 }

     hh3cMplsLdpLsrMaxRemotePeers OBJECT-TYPE
         SYNTAX      INTEGER (1..1024)
         MAX-ACCESS  read-write
         STATUS      current
         DESCRIPTION
             "The maximum number of Remote LDP peers that can be supported by 
              this Incarnation."
         ::= { hh3cMplsLdpLsrIncarnEntry 12 }

     hh3cMplsLdpLsrMaxIfaces OBJECT-TYPE
         SYNTAX      INTEGER
         MAX-ACCESS  read-write
         STATUS      current
         DESCRIPTION
             "The maximum number of Label enabled Interfaces that can be 
              supported by this Incarnation."
         ::= { hh3cMplsLdpLsrIncarnEntry 13 }

     hh3cMplsLdpLsrMaxLsps OBJECT-TYPE
         SYNTAX      INTEGER
         MAX-ACCESS  read-write
         STATUS      current
         DESCRIPTION
             "The maximum number of Label Switched Paths that can be 
              supported by this Incarnation."
         ::= { hh3cMplsLdpLsrIncarnEntry 14 }

     hh3cMplsLdpLsrMaxCrlspTnls OBJECT-TYPE
         SYNTAX      INTEGER
         MAX-ACCESS  read-write
         STATUS      current
         DESCRIPTION
             "The maximum number of CRLSPs that can be supported by this
             Incarnation."
         ::= { hh3cMplsLdpLsrIncarnEntry 15 }


     hh3cMplsLdpLsrMaxErhopPerCrlspTnl OBJECT-TYPE
         SYNTAX      INTEGER
         MAX-ACCESS  read-write
         STATUS      current
         DESCRIPTION
             " The maximum number of ER-Hops that can be supported in a 
              CRLSP tunnel."
         ::= { hh3cMplsLdpLsrIncarnEntry 16 }

     hh3cMplsLdpLsrRowStatus OBJECT-TYPE
         SYNTAX      RowStatus
         MAX-ACCESS  read-create
         STATUS      current
              DESCRIPTION
                  "An object that allows entries in this table to
                  be created and deleted using the
                  RowStatus convention."
         ::= { hh3cMplsLdpLsrIncarnEntry 17 }

     hh3cMplsLdpLsrMaxVcmCapability OBJECT-TYPE
         SYNTAX      INTEGER
         MAX-ACCESS  read-write
         STATUS      current
         DESCRIPTION
                  "  "
         ::= { hh3cMplsLdpLsrIncarnEntry 18 }

     hh3cMplsLdpLsrVcmPathVecInAllLblMapPresent OBJECT-TYPE
         SYNTAX      TruthValue
         MAX-ACCESS  read-write
         STATUS      current
         DESCRIPTION
                  "  "
         ::= { hh3cMplsLdpLsrIncarnEntry 19 }

     hh3cMplsLdpLsrRequestRetrytimerValue  OBJECT-TYPE
         SYNTAX      INTEGER
         MAX-ACCESS  read-write
         STATUS      current
         DESCRIPTION
                  "  "
         ::= { hh3cMplsLdpLsrIncarnEntry 20 }

     hh3cMplsLdpLsrNumOfRequestRetryAttempts OBJECT-TYPE
         SYNTAX      INTEGER
         MAX-ACCESS  read-write
         STATUS      current
         DESCRIPTION
                  "  "
         ::= { hh3cMplsLdpLsrIncarnEntry 21 }


     --
     -- The MPLS Label Distribution Protocol Entity Table
     --

     hh3cMplsLdpEntityTable OBJECT-TYPE
         SYNTAX      SEQUENCE OF Hh3cMplsLdpEntityEntry
         MAX-ACCESS  not-accessible
         STATUS      current
         DESCRIPTION
             "This table contains information about the
             MPLS Label Distribution Protocol Entities which
             exist on this Label Switch Router (LSR)."
         ::= { hh3cMplsLdpEntityObjects 1 }

     hh3cMplsLdpEntityEntry OBJECT-TYPE
         SYNTAX      Hh3cMplsLdpEntityEntry
         MAX-ACCESS  not-accessible
         STATUS      current
         DESCRIPTION
             "An entry in this table represents an LDP entity.
             An entry can be created by a network administrator
             or by an SNMP agent as instructed by LDP.

             An LPD Entity is uniquely indexed by its LPD
             Identifier."
         INDEX       {   hh3cMplsLdpLsrIncarnID, hh3cMplsLdpEntityIfIndex  }
         ::= { hh3cMplsLdpEntityTable 1 }

     Hh3cMplsLdpEntityEntry ::= SEQUENCE {
         hh3cMplsLdpEntityID                            MplsLdpIdentifier,
         hh3cMplsLdpEntityLabelSpaceType                INTEGER,
         hh3cMplsLdpEntityDefVpi                        AtmVpIdentifier,
         hh3cMplsLdpEntityDefVci                        AtmVcIdentifier,
         hh3cMplsLdpEntityUnlabTrafVpi                  AtmVpIdentifier,
         hh3cMplsLdpEntityUnlabTrafVci                  AtmVcIdentifier,
         hh3cMplsLdpEntityMergeCapability               INTEGER,
         hh3cMplsLdpEntityVcDirectionality              INTEGER,
         hh3cMplsLdpEntityWellKnownDiscoveryPort        INTEGER,
         hh3cMplsLdpEntityMtu                           INTEGER,
         hh3cMplsLdpEntityKeepAliveHoldTimer            INTEGER,
         hh3cMplsLdpEntityFailedInitSessionThreshold    INTEGER,
         hh3cMplsLdpEntityLabelDistributionMethod       INTEGER,
         hh3cMplsLdpEntityLabelAllocationMethod         INTEGER,
         hh3cMplsLdpEntityHelloHoldTimer                INTEGER,
         hh3cMplsLdpEntityRowStatus                     RowStatus
     }

     hh3cMplsLdpEntityID OBJECT-TYPE
         SYNTAX      MplsLdpIdentifier
         MAX-ACCESS  accessible-for-notify
         STATUS      current
         DESCRIPTION
             "The LDP identifier which uniquely identifies
             the LDP Entity.  This is s six octet quantity
             which is used to identify an Label Switch Router
             (LSR) label space.

             The first four octets encode an IP address
             assigned to the LSR, and the last two octets
             identify a specific label space within the
             LSR."
         REFERENCE
             "LDP Specification, Section on LDP Identifiers."
         ::= { hh3cMplsLdpEntityEntry 1 }


     hh3cMplsLdpEntityLabelSpaceType OBJECT-TYPE
         SYNTAX      INTEGER {
                         unknown(1),
                         perInterface(2),
                         perPlatform(3)
                         }
         MAX-ACCESS  read-create
         STATUS      current
         DESCRIPTION
             "The type of label spaces associated with this
             LDP Entity.  The values are

                'unknown(1)'        The type of label space is
                                    not known.

                'perInterface(2)'   The type of label space is
                                    tied to an interface.
                'perPlatform(3)'    The type of label space is
                                    tied to the platform."
         REFERENCE
             "LDP Specification, Section on Label Spaces."
         ::= { hh3cMplsLdpEntityEntry 2 }

     hh3cMplsLdpEntityDefVpi OBJECT-TYPE
         SYNTAX      AtmVpIdentifier
         MAX-ACCESS  read-create
         STATUS      current
         DESCRIPTION
             "The Default VPI value used in the label for the default
             VPI."
         ::= { hh3cMplsLdpEntityEntry 3 }

     hh3cMplsLdpEntityDefVci OBJECT-TYPE
         SYNTAX      AtmVcIdentifier
         MAX-ACCESS  read-create
         STATUS      current
         DESCRIPTION
             "The Default VCI value used in the label for the default
             VCI."
         ::= { hh3cMplsLdpEntityEntry  4 }

     hh3cMplsLdpEntityUnlabTrafVpi OBJECT-TYPE
         SYNTAX      AtmVpIdentifier
         MAX-ACCESS  read-create
         STATUS      current
         DESCRIPTION
             "VPI value of the VCC supporting unlabeled traffic."
         DEFVAL  { 0 }
         ::= { hh3cMplsLdpEntityEntry 5 }

     hh3cMplsLdpEntityUnlabTrafVci OBJECT-TYPE
         SYNTAX      AtmVcIdentifier
         MAX-ACCESS  read-create
         STATUS      current
         DESCRIPTION
             "VCI value of the VCC supporting unlabeled traffic."
         DEFVAL  { 32 }
         ::= { hh3cMplsLdpEntityEntry 6 }

     hh3cMplsLdpEntityMergeCapability OBJECT-TYPE
         SYNTAX      INTEGER {
                         noMerge(0),
                         vpMerge(1),
                         vcMerge(2),
                         vpVcMerge(3)
                      }
         MAX-ACCESS  read-create
         STATUS      current
         DESCRIPTION
             "Sets the merge capability for this LDP entity.

              Current Release of H3CMPLS does not provide support for
              any kind of Merge."
         REFERENCE
             "draft-ietf-mpls-ldp-04.txt, Section 3.5.3"
         ::= { hh3cMplsLdpEntityEntry 7 }

     hh3cMplsLdpEntityVcDirectionality OBJECT-TYPE
         SYNTAX      INTEGER {
                         bidirectional(1),
                         unidirectional(2)
                     }
         MAX-ACCESS  read-create
         STATUS      current
         DESCRIPTION
             "Sets the VC directionality for this LDP entity."
         REFERENCE
             "draft-ietf-mpls-ldp-04.txt, Section 3.5.3"
         ::= { hh3cMplsLdpEntityEntry 8 }

     hh3cMplsLdpEntityWellKnownDiscoveryPort OBJECT-TYPE
         SYNTAX      INTEGER
         MAX-ACCESS  read-create
         STATUS      current
         DESCRIPTION
             "The well known LDP Discovery Port."
         ::= { hh3cMplsLdpEntityEntry 9 }

     hh3cMplsLdpEntityMtu OBJECT-TYPE
         SYNTAX      INTEGER (0..65535)
         MAX-ACCESS  read-create
         STATUS      current
         DESCRIPTION
             "The maximum transmission unit (MTU) that was configured
             for this entity."
         ::= { hh3cMplsLdpEntityEntry 10 }

     hh3cMplsLdpEntityKeepAliveHoldTimer OBJECT-TYPE
         SYNTAX      INTEGER (1..65535)
         UNITS       "seconds"
         MAX-ACCESS  read-create
         STATUS      current
         DESCRIPTION
             "The two octet value which is the proposed keep alive hold
             timer for this LDP Entity."
         ::= { hh3cMplsLdpEntityEntry 11 }

     hh3cMplsLdpEntityFailedInitSessionThreshold OBJECT-TYPE
         SYNTAX      INTEGER
         MAX-ACCESS  read-create
         STATUS      current
         DESCRIPTION
             "When attempting to establish a session with a
             given Peer, the given LDP Entity should
             send out a notification when exceeding this threshold.
             A value of 0 (zero) for this object
             indicates that the threshold is infinity.
             In other words, a notification will not
             be sent if the value of this object is 0 (zero)."
         ::= { hh3cMplsLdpEntityEntry 12 }


     hh3cMplsLdpEntityLabelDistributionMethod OBJECT-TYPE
         SYNTAX      INTEGER {
                        downstreamOnDemand(1),
                        downstreamUnsolicited(2)
                     }
         MAX-ACCESS  read-create
         STATUS      current
         DESCRIPTION
             "For any given LDP session, the method of
             label distribution must be specified.
 
             Current release of H3CMPLS does not provide support for
             'downstreamUnsolicited'."
         REFERENCE
             "draft-ietf-mpls-arch-04.txt [20]."
         ::= { hh3cMplsLdpEntityEntry 13 }

     hh3cMplsLdpEntityLabelAllocationMethod OBJECT-TYPE
         SYNTAX      INTEGER {
                        ordered(1),
                        independent(2)
                     }
         MAX-ACCESS  read-create
         STATUS      current
         DESCRIPTION
             "For any given LDP session, the method of
             label allocation must be specified. Label can be allocated
             in either ordered mode or in the independent mode."
         DEFVAL  { ordered }
         ::= { hh3cMplsLdpEntityEntry 14 }

     hh3cMplsLdpEntityHelloHoldTimer OBJECT-TYPE
         SYNTAX      INTEGER (1..65535)
         UNITS       "seconds"
         MAX-ACCESS  read-create
         STATUS      current
         DESCRIPTION
             "The two octet value which is the proposed hello hold
             timer for this LDP Entity."
         ::= { hh3cMplsLdpEntityEntry 15 }
     
     hh3cMplsLdpEntityRowStatus OBJECT-TYPE
         SYNTAX      RowStatus
         MAX-ACCESS  read-create
         STATUS      current
              DESCRIPTION
                  "An object that allows entries in this table to
                  be created and deleted using the
                  RowStatus convention."
         ::= { hh3cMplsLdpEntityEntry 16 }

     --
     -- The MPLS LDP Entity Interface Table
     --

     hh3cMplsLdpEntityIfTable OBJECT-TYPE
         SYNTAX      SEQUENCE OF Hh3cMplsLdpEntityIfEntry
         MAX-ACCESS  not-accessible
         STATUS      current
         DESCRIPTION
             "This table contains information about the
             interfaces that are associated with an LDP Entity.
             There should be atleast one interface associated with
             each LDP Entity. If the LDP Entity supports 'per interface
             based label space' label type then, atmost one interface can be 
             associated with the LDP entity. If the LDP Entity supports
             'per platform based label space' label type then, more than one
             interface can be associated with the LDP Entity."
         ::= { hh3cMplsLdpEntityObjects 2 }

     hh3cMplsLdpEntityIfEntry OBJECT-TYPE
         SYNTAX      Hh3cMplsLdpEntityIfEntry
         MAX-ACCESS  not-accessible
         STATUS      current
         DESCRIPTION
             "An entry in this table represents an Interface that is
             associated with a LDP entity.

             An entry can be created by a network administrator
             or by an SNMP agent as instructed by LDP.

             An interface (row in this table) can be created/deleted only when 
             the associted LDP Entity row status has the value notInService 
             or notReady."
         INDEX       {   hh3cMplsLdpLsrIncarnID, hh3cMplsLdpEntityIfIndex }
         ::= { hh3cMplsLdpEntityIfTable 1 }

     Hh3cMplsLdpEntityIfEntry ::= SEQUENCE {
         hh3cMplsLdpEntityIfIndex                       Unsigned32,
         hh3cMplsLdpEntityIfIpv4Address                 IpAddress,
         hh3cMplsLdpEntityIfRowStatus                   RowStatus
     }

     hh3cMplsLdpEntityIfIndex OBJECT-TYPE
         SYNTAX      Unsigned32 (1..4294967295)
         MAX-ACCESS  not-accessible
         STATUS      current
         DESCRIPTION
             "Identifier that uniquely identifies the Interface with 
             respect to an LDP Entity.
             
             The ifIndex value corresponds to the IfIndex value of the
             MIB-II"
         ::= { hh3cMplsLdpEntityIfEntry 1 }

     hh3cMplsLdpEntityIfIpv4Address OBJECT-TYPE
        SYNTAX        IpAddress
        MAX-ACCESS    read-create
        STATUS        current
        DESCRIPTION
            "The IPv4 address associated with the interface."
        ::= { hh3cMplsLdpEntityIfEntry 2 }

     hh3cMplsLdpEntityIfRowStatus OBJECT-TYPE
         SYNTAX      RowStatus
         MAX-ACCESS  read-create
         STATUS      current
              DESCRIPTION
                  "An object that allows entries in this table to
                  be created and deleted using the
                  RowStatus convention."
         ::= { hh3cMplsLdpEntityIfEntry 3 }

     --
     -- The MPLS LDP Entity Configurable ATM Label Range Table
     --

     hh3cMplsLdpEntityConfAtmLabelRangeTable OBJECT-TYPE
         SYNTAX SEQUENCE OF Hh3cMplsLdpEntityConfAtmLabelRangeEntry
         MAX-ACCESS not-accessible
         STATUS current
         DESCRIPTION
             "The MPLS LDP Entity Configurable ATM Label Range Table.
             The purpose of this table is to provide a mechanism
             for specifying a contiguous range of vpi's
             with a contiguous range of vci's, or a 'label range'
             for LDP Entities.

             LDP Entities which use ATM must have at least one
             entry in this table."
         ::= { hh3cMplsLdpEntityObjects 3 }

     hh3cMplsLdpEntityConfAtmLabelRangeEntry OBJECT-TYPE
         SYNTAX Hh3cMplsLdpEntityConfAtmLabelRangeEntry
         MAX-ACCESS not-accessible
         STATUS current
         DESCRIPTION
             "A row in the LDP Entity Configurable ATM Label
             Range Table.  One entry in this table contains
             information on a single range of labels
             represented by the configured Upper and Lower
             Bounds VPI/VCI pairs.
             NOTE:  The ranges for a specific LDP Entity
             are UNIQUE and non-overlapping.  For example,
             for a specific LDP Entity index, there could
             be one entry having ConfLowerBound vpi/vci == 0/32, and
             ConfUpperBound vpi/vci == 0/100, and a second entry for this
             same interface with ConfLowerBound vpi/vci == 0/101 and
             ConfUpperBound vpi/vci == 0/200.  However, there could not be
             a third entry with ConfLowerBound vpi/vci == 0/200 and
             ConfUpperBound vpi/vci == 0/300 because this label range overlaps
             with the second entry (i.e. both entries now have 0/200).

             A row will not be created unless a unique and non-overlapping
             range is specified.  Thus, row creation implies a one-shot
             row creation of LDP EntityID and ConfLowerBound vpi/vci and
             ConfUpperBound vpi/vci.  At least one label range entry
             for a specific LDP Entity MUST include the default VPI/VCI
             values denoted in the LDP Entity Table."
         INDEX { hh3cMplsLdpLsrIncarnID, hh3cMplsLdpEntityIfIndex,
                 hh3cMplsLdpEntityConfAtmLabelRangeLowerBoundVPI,
                 hh3cMplsLdpEntityConfAtmLabelRangeLowerBoundVCI  }
         ::= { hh3cMplsLdpEntityConfAtmLabelRangeTable 1 }

     Hh3cMplsLdpEntityConfAtmLabelRangeEntry ::= SEQUENCE {
         hh3cMplsLdpEntityConfAtmLabelRangeLowerBoundVPI  AtmVpIdentifier,
         hh3cMplsLdpEntityConfAtmLabelRangeLowerBoundVCI  AtmVcIdentifier,
         hh3cMplsLdpEntityConfAtmLabelRangeUpperBoundVPI  AtmVpIdentifier,
         hh3cMplsLdpEntityConfAtmLabelRangeUpperBoundVCI  AtmVcIdentifier,
         hh3cMplsLdpEntityConfAtmLabelRangeRowStatus      RowStatus
     }

     hh3cMplsLdpEntityConfAtmLabelRangeLowerBoundVPI OBJECT-TYPE
         SYNTAX AtmVpIdentifier
         MAX-ACCESS not-accessible
         STATUS current
         DESCRIPTION
             "The minimum VPI number configured for this range."
         ::= { hh3cMplsLdpEntityConfAtmLabelRangeEntry 1 }

     hh3cMplsLdpEntityConfAtmLabelRangeLowerBoundVCI OBJECT-TYPE
         SYNTAX AtmVcIdentifier
         MAX-ACCESS not-accessible
         STATUS current
         DESCRIPTION
             "The minimum VCI number configured for this range."
         ::= { hh3cMplsLdpEntityConfAtmLabelRangeEntry 2 }

     hh3cMplsLdpEntityConfAtmLabelRangeUpperBoundVPI OBJECT-TYPE
         SYNTAX AtmVpIdentifier
         MAX-ACCESS read-create
         STATUS current
         DESCRIPTION
             "The maximum VPI number configured for this range."
         ::= { hh3cMplsLdpEntityConfAtmLabelRangeEntry 3 }

     hh3cMplsLdpEntityConfAtmLabelRangeUpperBoundVCI OBJECT-TYPE
         SYNTAX AtmVcIdentifier
         MAX-ACCESS read-create
         STATUS current
         DESCRIPTION
             "The maximum VCI number configured for this range."
        ::= { hh3cMplsLdpEntityConfAtmLabelRangeEntry 4 }

     hh3cMplsLdpEntityConfAtmLabelRangeRowStatus OBJECT-TYPE
         SYNTAX RowStatus
         MAX-ACCESS read-create
         STATUS current
              DESCRIPTION
                  "An object that allows entries in this
                  table to be created and deleted using
                  the RowStatus convention."
         ::= { hh3cMplsLdpEntityConfAtmLabelRangeEntry 5 }


     --
     -- The MPLS LDP Entity Statistics Table
     --

     hh3cMplsLdpEntityStatsTable OBJECT-TYPE
         SYNTAX      SEQUENCE OF Hh3cMplsLdpEntityStatsEntry
         MAX-ACCESS  not-accessible
         STATUS      current
         DESCRIPTION
             "This table is a read-only table which augments
             the MplsLdpConfEntityTable.  The purpose of this
             table is to keep statistical information about
             the LDP Entities on the LSR."
         ::= { hh3cMplsLdpEntityObjects 4 }

     hh3cMplsLdpEntityStatsEntry OBJECT-TYPE
         SYNTAX      Hh3cMplsLdpEntityStatsEntry
         MAX-ACCESS  not-accessible
         STATUS      current
         DESCRIPTION
             "A row in this table contains statistical information
             about an LDP Entity."
         AUGMENTS       {   hh3cMplsLdpEntityEntry  }
         ::= { hh3cMplsLdpEntityStatsTable 1 }

     Hh3cMplsLdpEntityStatsEntry ::= SEQUENCE {
         hh3cMplsLdpAttemptedSessions      Counter32
     }

     hh3cMplsLdpAttemptedSessions OBJECT-TYPE
         SYNTAX      Counter32
         MAX-ACCESS  read-only
         STATUS      current
         DESCRIPTION
             "A count of the total attempted sessions for
             this LDP Entity."
         ::= { hh3cMplsLdpEntityStatsEntry 1 }


     --
     -- The MPLS LDP Peer Table
     --


     hh3cMplsLdpPeerTable OBJECT-TYPE
         SYNTAX      SEQUENCE OF Hh3cMplsLdpPeerEntry
         MAX-ACCESS  not-accessible
         STATUS      current
         DESCRIPTION
             "Information about LDP peers which have been discovered
             by the LDP Entities that are managed by this agent."
         ::= { hh3cMplsLdpPeerObjects 1 }

     hh3cMplsLdpPeerEntry OBJECT-TYPE
         SYNTAX      Hh3cMplsLdpPeerEntry
         MAX-ACCESS  not-accessible
         STATUS      current
         DESCRIPTION
             "Information about a single Peer."
         INDEX       { hh3cMplsLdpLsrIncarnID, hh3cMplsLdpEntityIfIndex,
                       hh3cMplsLdpPeerIndex }
         ::= { hh3cMplsLdpPeerTable 1 }

     Hh3cMplsLdpPeerEntry ::= SEQUENCE {
         hh3cMplsLdpPeerIndex                      Unsigned32,
         hh3cMplsLdpPeerID                         MplsLdpIdentifier,
         hh3cMplsLdpPeerInternetworkAddrType       AddressFamilyNumbers,
         hh3cMplsLdpPeerInternetworkAddr           MplsLdpGenAddr,
         hh3cMplsLdpPeerDefaultMtu                 INTEGER,
         hh3cMplsLdpPeerKeepAliveHoldTimer         INTEGER,
         hh3cMplsLdpPeerLabelDistributionMethod    INTEGER,
         hh3cMplsLdpPeerType                       INTEGER,
         hh3cMplsLdpPeerRowStatus                  RowStatus
     }

     hh3cMplsLdpPeerIndex OBJECT-TYPE
         SYNTAX      Unsigned32 (1..4294967295)
         MAX-ACCESS  not-accessible
         STATUS      current
         DESCRIPTION
             "An identifier for the LDP peer that is unique within the
              scope of this agent."
         ::= { hh3cMplsLdpPeerEntry 1 }

     hh3cMplsLdpPeerID OBJECT-TYPE
         SYNTAX      MplsLdpIdentifier
         MAX-ACCESS  read-create
         STATUS      current
         DESCRIPTION
             "The LDP identifier of this LDP Peer."
         ::= { hh3cMplsLdpPeerEntry 2 }

     hh3cMplsLdpPeerInternetworkAddrType OBJECT-TYPE
         SYNTAX      AddressFamilyNumbers
         MAX-ACCESS  read-create
         STATUS      current
         DESCRIPTION
             "The type of the internetwork layer address of this
             LDP peer. This object indicates how the value of
             hh3cMplsLdpPeerInternetworkAddr is to be interpreted."
         ::= { hh3cMplsLdpPeerEntry 3 }

     hh3cMplsLdpPeerInternetworkAddr OBJECT-TYPE
         SYNTAX      MplsLdpGenAddr
         MAX-ACCESS  read-create
         STATUS      current
         DESCRIPTION
             "The value of the internetwork layer address of this LDP peer."
         ::= { hh3cMplsLdpPeerEntry 4 }

     hh3cMplsLdpPeerDefaultMtu OBJECT-TYPE
         SYNTAX      INTEGER (0..65535)
         MAX-ACCESS  read-create
         STATUS      current
         DESCRIPTION
             "The default maximum transmission unit (MTU) of the
             LDP Peer."
         DEFVAL      { 9180 }
         ::= { hh3cMplsLdpPeerEntry 5 }

     hh3cMplsLdpPeerKeepAliveHoldTimer OBJECT-TYPE
         SYNTAX      INTEGER (1..65535)
         UNITS       "seconds"
         MAX-ACCESS  read-create
         STATUS      current
         DESCRIPTION
             "The two octet unsigned non zero INTEGER that indicates
             the number of seconds that this Peer proposes for the
             value of the KeepAlive Interval."
         ::= { hh3cMplsLdpPeerEntry 6 }

     hh3cMplsLdpPeerLabelDistributionMethod OBJECT-TYPE
         SYNTAX      INTEGER {
                        downstreamOnDemand(1),
                        downstreamUnsolicited(2)
                     }
         MAX-ACCESS  read-create
         STATUS      current
         DESCRIPTION
             "For any given LDP session, the method of
             label distribution must be specified."
         REFERENCE
             "draft-ietf-mpls-arch-05.txt [20]."
         ::= { hh3cMplsLdpPeerEntry 7 }

     hh3cMplsLdpPeerType OBJECT-TYPE
         SYNTAX      INTEGER {
                        local(1),
                        remote(2)
                     }
         MAX-ACCESS  read-create
         STATUS      current
         DESCRIPTION
             "Indicates whether a peer is a local peer or a remote peer"
         ::= { hh3cMplsLdpPeerEntry 8 } 
     
     hh3cMplsLdpPeerRowStatus OBJECT-TYPE
         SYNTAX      RowStatus
         MAX-ACCESS  read-create
         STATUS      current
         DESCRIPTION
             "An object that allows entries in this table to be created
             and deleted using the RowStatus convention."
         ::= { hh3cMplsLdpPeerEntry 9 }

     --
     -- The MPLS LDP Peer Configurable ATM Label Range Table
     --

     hh3cMplsLdpPeerConfAtmLabelRangeTable OBJECT-TYPE
         SYNTAX SEQUENCE OF Hh3cMplsLdpPeerConfAtmLabelRangeEntry
         MAX-ACCESS not-accessible
         STATUS current
         DESCRIPTION
             "The MPLS LDP Peer Configurable ATM Label Range Table.
             The purpose of this table is to provide a mechanism
             for specifying a contiguous range of vpi's with a contiguous
             range of vci's, or a 'label range' for LDP Peers.
             LDP Peers which use ATM must have at least one
             entry in this table."
         ::= { hh3cMplsLdpPeerObjects 2 }

     hh3cMplsLdpPeerConfAtmLabelRangeEntry OBJECT-TYPE
         SYNTAX Hh3cMplsLdpPeerConfAtmLabelRangeEntry
         MAX-ACCESS not-accessible
         STATUS current
         DESCRIPTION
             "A row in the LDP Peer Configurable ATM Label Range Table.
             One entry in this table contains information
             on a single range of labels represented by
             the configured Upper and Lower Bounds VPI/VCI pairs.

             NOTE:  The ranges for a specific LDP Peer
             are UNIQUE and non-overlapping.  For example,
             for a specific LDP Peer index, there could
             be one entry having ConfLowerBound vpi/vci == 0/32, and
             ConfUpperBound vpi/vci == 0/100, and a second entry for this
             same interface with ConfLowerBound vpi/vci == 0/101 and
             ConfUpperBound vpi/vci == 0/200.  However, there could not be
             a third entry with ConfLowerBound vpi/vci == 0/200 and
             ConfUpperBound vpi/vci == 0/300 because this label range overlaps
             with the second entry (i.e. both entries now have 0/200).

             A row will not be created unless a unique and non-overlapping
             range is specified.  Thus, row creation implies a one-shot
             row creation of LDP PeerIndex and ConfLowerBound vpi/vci and
             ConfUpperBound vpi/vci.  At least one label range entry
             for a specific LDP Peer MUST include the default VPI/VCI
             values denoted in the LDP Peer Table."
         INDEX { hh3cMplsLdpLsrIncarnID, hh3cMplsLdpEntityIfIndex,
                 hh3cMplsLdpPeerIndex,
                 hh3cMplsLdpPeerConfAtmLabelRangeLowerBoundVPI,
                 hh3cMplsLdpPeerConfAtmLabelRangeLowerBoundVCI  }
         ::= { hh3cMplsLdpPeerConfAtmLabelRangeTable 1 }

     Hh3cMplsLdpPeerConfAtmLabelRangeEntry ::= SEQUENCE {
         hh3cMplsLdpPeerConfAtmLabelRangeLowerBoundVPI      AtmVpIdentifier,
         hh3cMplsLdpPeerConfAtmLabelRangeLowerBoundVCI      AtmVcIdentifier,
         hh3cMplsLdpPeerConfAtmLabelRangeUpperBoundVPI      AtmVpIdentifier,
         hh3cMplsLdpPeerConfAtmLabelRangeUpperBoundVCI      AtmVcIdentifier
     }

     hh3cMplsLdpPeerConfAtmLabelRangeLowerBoundVPI OBJECT-TYPE
         SYNTAX AtmVpIdentifier
         MAX-ACCESS not-accessible
         STATUS current
         DESCRIPTION
             "The minimum VPI number configured for this range."
         ::= { hh3cMplsLdpPeerConfAtmLabelRangeEntry 1 }

     hh3cMplsLdpPeerConfAtmLabelRangeLowerBoundVCI OBJECT-TYPE
         SYNTAX AtmVcIdentifier
         MAX-ACCESS not-accessible
         STATUS current
         DESCRIPTION
             "The minimum VCI number configured for this range."
         ::= { hh3cMplsLdpPeerConfAtmLabelRangeEntry 2 }

     hh3cMplsLdpPeerConfAtmLabelRangeUpperBoundVPI OBJECT-TYPE
         SYNTAX AtmVpIdentifier
         MAX-ACCESS read-only  
         STATUS current
         DESCRIPTION
             "The maximum VPI number configured for this range."
         ::= { hh3cMplsLdpPeerConfAtmLabelRangeEntry 3 }

     hh3cMplsLdpPeerConfAtmLabelRangeUpperBoundVCI OBJECT-TYPE
         SYNTAX AtmVcIdentifier
         MAX-ACCESS read-only  
         STATUS current
         DESCRIPTION
             "The maximum VCI number configured for this range."
        ::= { hh3cMplsLdpPeerConfAtmLabelRangeEntry 4 }

     --
     -- The MPLS LDP Sessions Table
     --


     hh3cMplsLdpSessionTable OBJECT-TYPE
         SYNTAX      SEQUENCE OF Hh3cMplsLdpSessionEntry
         MAX-ACCESS  not-accessible
         STATUS      current
         DESCRIPTION
             "A table of Sessions between the LDP Entities and
             LDP Peers."
         ::= { hh3cMplsLdpSessionObjects 1 }

     hh3cMplsLdpSessionEntry OBJECT-TYPE
         SYNTAX      Hh3cMplsLdpSessionEntry
         MAX-ACCESS  not-accessible
         STATUS      current
         DESCRIPTION
             "An entry in this table represents information on a
             single session between an LDP Entity and LDP Peer."
         INDEX       { hh3cMplsLdpLsrIncarnID,
                       hh3cMplsLdpEntityIfIndex,
                       hh3cMplsLdpPeerIndex,
                       hh3cMplsLdpSessionIndex
                     }
         ::= { hh3cMplsLdpSessionTable 1 }

     Hh3cMplsLdpSessionEntry ::= SEQUENCE {
         hh3cMplsLdpSessionIndex                          Unsigned32,
         hh3cMplsLdpSessionID                             MplsLdpIdentifier,
         hh3cMplsLdpSessionProtocolVersion                INTEGER,
         hh3cMplsLdpSessionKeepAliveHoldTimeRemaining     TimeInterval,
         hh3cMplsLdpSessionRole                           INTEGER,
         hh3cMplsLdpSessionState                          INTEGER,
         hh3cMplsLdpSessionAtmLabelRangeLowerBoundVPI     AtmVpIdentifier,
         hh3cMplsLdpSessionAtmLabelRangeLowerBoundVCI     AtmVcIdentifier,
         hh3cMplsLdpSessionAtmLabelRangeUpperBoundVPI     AtmVpIdentifier,
         hh3cMplsLdpSessionAtmLabelRangeUpperBoundVCI     AtmVcIdentifier
     }

     hh3cMplsLdpSessionIndex OBJECT-TYPE
         SYNTAX      Unsigned32 (1..4294967295)
         MAX-ACCESS  not-accessible
         STATUS      current
         DESCRIPTION
             "An unique identifier for this entry such that it
             identifies a specific LDP Session."
         ::= { hh3cMplsLdpSessionEntry 1 }

     hh3cMplsLdpSessionID OBJECT-TYPE
         SYNTAX      MplsLdpIdentifier
         MAX-ACCESS  read-only
         STATUS      current
         DESCRIPTION
             "The LDP Session identifier."
         ::= { hh3cMplsLdpSessionEntry 2 }

     hh3cMplsLdpSessionProtocolVersion OBJECT-TYPE
              SYNTAX      INTEGER(0..65535)
              MAX-ACCESS  read-only
              STATUS      current
              DESCRIPTION
                  "The version of the LDP Protocol which
                  this session is using."
              ::= { hh3cMplsLdpSessionEntry 3 }

     hh3cMplsLdpSessionKeepAliveHoldTimeRemaining OBJECT-TYPE
         SYNTAX      TimeInterval
         MAX-ACCESS  read-only
         STATUS      current
         DESCRIPTION
             "The keep alive hold time remaining for this session."
         ::= { hh3cMplsLdpSessionEntry 4 }

     hh3cMplsLdpSessionRole OBJECT-TYPE
         SYNTAX      INTEGER {
                        active(1),
                        passive(2)
                     }
         MAX-ACCESS  read-only
         STATUS      current
         DESCRIPTION
             "An indication of whether the LDP Entity associated with
             this session is acting in an 'active' role or
             a 'passive' role."
         ::= { hh3cMplsLdpSessionEntry 5 }

     hh3cMplsLdpSessionState OBJECT-TYPE
         SYNTAX      INTEGER {
                        nonexistent(1),
                        initialized(2),
                        openrec(3),
                        opensent(4),
                        operational(5)
                     }
         MAX-ACCESS  read-only
         STATUS      current
         DESCRIPTION
             "The current state of the session, all of the
             states 1 - 5 are based on the state machine for
             session negotiation behavior."
         ::= { hh3cMplsLdpSessionEntry 6 }

     hh3cMplsLdpSessionAtmLabelRangeLowerBoundVPI OBJECT-TYPE
         SYNTAX AtmVpIdentifier
         MAX-ACCESS read-only
         STATUS current
         DESCRIPTION
             "The minimum VPI number for this range."
         ::= { hh3cMplsLdpSessionEntry 7 }

     hh3cMplsLdpSessionAtmLabelRangeLowerBoundVCI OBJECT-TYPE
         SYNTAX AtmVcIdentifier
         MAX-ACCESS read-only
         STATUS current
         DESCRIPTION
             "The minimum VCI number for this range."
         ::= { hh3cMplsLdpSessionEntry 8 }

     hh3cMplsLdpSessionAtmLabelRangeUpperBoundVPI OBJECT-TYPE
         SYNTAX AtmVpIdentifier
         MAX-ACCESS read-only
         STATUS current
         DESCRIPTION
             "The maximum VPI number for this range."
         ::= { hh3cMplsLdpSessionEntry 9 }

     hh3cMplsLdpSessionAtmLabelRangeUpperBoundVCI OBJECT-TYPE
         SYNTAX AtmVcIdentifier
         MAX-ACCESS read-only
         STATUS current
         DESCRIPTION
             "The maximum VCI number for this range."
         ::= { hh3cMplsLdpSessionEntry 10 }



     --
     -- The MPLS LDP Hello Adjacency Table
     --


     hh3cMplsLdpHelloAdjacencyTable OBJECT-TYPE
         SYNTAX      SEQUENCE OF Hh3cMplsLdpHelloAdjacencyEntry
         MAX-ACCESS  not-accessible
         STATUS      current
         DESCRIPTION
             "A table of Hello Adjacencies for Sessions."
         ::= { hh3cMplsLdpHelloAdjacencyObjects 1 }

     hh3cMplsLdpHelloAdjacencyEntry OBJECT-TYPE
         SYNTAX      Hh3cMplsLdpHelloAdjacencyEntry
         MAX-ACCESS  not-accessible
         STATUS      current
         DESCRIPTION
             "Each row represents a single LDP Hello Adjacency.
             An LDP Session can have one or more Hello adjacencies."
         INDEX       { hh3cMplsLdpLsrIncarnID,
                       hh3cMplsLdpEntityIfIndex, 
                       hh3cMplsLdpPeerIndex,
                       hh3cMplsLdpSessionIndex,
                       hh3cMplsLdpHelloAdjacencyIndex }
         ::= { hh3cMplsLdpHelloAdjacencyTable 1 }

     Hh3cMplsLdpHelloAdjacencyEntry ::= SEQUENCE {
         hh3cMplsLdpHelloAdjacencyIndex                  Unsigned32,
         hh3cMplsLdpHelloAdjacencyHoldTimeRemaining      TimeInterval
     }

     hh3cMplsLdpHelloAdjacencyIndex OBJECT-TYPE
         SYNTAX      Unsigned32 (1..4294967295)
         MAX-ACCESS  not-accessible
         STATUS      current
         DESCRIPTION
             "An identifier for the adjacency."
         ::= { hh3cMplsLdpHelloAdjacencyEntry 1 }

     hh3cMplsLdpHelloAdjacencyHoldTimeRemaining OBJECT-TYPE
         SYNTAX      TimeInterval
         MAX-ACCESS  read-only
         STATUS      current
         DESCRIPTION
             "The time remaining for this Hello Adjacency."
         ::= { hh3cMplsLdpHelloAdjacencyEntry 2 }

     --
     -- FSMPLS- CRLSP Table
     --

     hh3cMplsLdpCrlspTnlTable OBJECT-TYPE
        SYNTAX        SEQUENCE OF Hh3cMplsLdpCrlspTnlEntry
        MAX-ACCESS    not-accessible
        STATUS        current
        DESCRIPTION
            "The hh3cMplsLdpCrlspTnlTable allows new CRLSP MPLS tunnels
             to be created. The ER hops associated with a CRLSP tunnel
             are to be configured using the hh3cMplsLdpCrlspErHopTable."
        ::= { hh3cMplsLdpCrlspTnlObjects 1 }
     
     hh3cMplsLdpCrlspTnlEntry OBJECT-TYPE
        SYNTAX        Hh3cMplsLdpCrlspTnlEntry
        MAX-ACCESS    not-accessible
        STATUS        current
        DESCRIPTION
            "An  entry  in this table represents an CRLSP MPLS  tunnel.
             An  entry  can be created by a network administrator."
        INDEX  {  hh3cMplsLdpLsrIncarnID,  hh3cMplsLdpCrlspTnlIndex  }
           ::= { hh3cMplsLdpCrlspTnlTable 1 }
     
     Hh3cMplsLdpCrlspTnlEntry ::= SEQUENCE {
           hh3cMplsLdpCrlspTnlIndex                 MplsTunnelIndex,
           hh3cMplsLdpCrlspTnlName                  DisplayString,
           hh3cMplsLdpCrlspTnlDirection             INTEGER,
           hh3cMplsLdpCrlspTnlSignallingProto       INTEGER,
           hh3cMplsLdpCrlspTnlSetupPrio             INTEGER,
           hh3cMplsLdpCrlspTnlHoldingPrio           INTEGER,
           hh3cMplsLdpCrlspTnlPeakDataRate          BitRate,
           hh3cMplsLdpCrlspTnlPeakBurstSize         BurstSize,
           hh3cMplsLdpCrlspTnlCommittedDataRate     BitRate,
           hh3cMplsLdpCrlspTnlCommittedBurstSize    BurstSize,
           hh3cMplsLdpCrlspTnlExcessBurstSize       BurstSize,
           hh3cMplsLdpCrlspTnlIsPinned              TruthValue,
           hh3cMplsLdpCrlspTnlFrequency             INTEGER,
           hh3cMplsLdpCrlspTnlWeight                INTEGER,
           hh3cMplsLdpCrlspTnlRowStatus             RowStatus
        }
     
     hh3cMplsLdpCrlspTnlIndex OBJECT-TYPE
        SYNTAX        MplsTunnelIndex
        MAX-ACCESS    accessible-for-notify
        STATUS        current
        DESCRIPTION
            "Uniquely identifies this row."
        ::= { hh3cMplsLdpCrlspTnlEntry 1 }
     
     hh3cMplsLdpCrlspTnlName OBJECT-TYPE
        SYNTAX        DisplayString
        MAX-ACCESS    read-create
        STATUS        current
        DESCRIPTION
            "The 'canonical' name assigned to the tunnel that can
             be  used  to refer to it on the 'console' port."
        ::= { hh3cMplsLdpCrlspTnlEntry 2 }
     
     
     hh3cMplsLdpCrlspTnlDirection OBJECT-TYPE
        SYNTAX        INTEGER { in(1), out(2), inOut(3) }
        MAX-ACCESS    read-create
        STATUS        current
        DESCRIPTION
            "Whether   this  tunnel  is  unidirectional-incoming,
             unidirectional-outgoing, or bidirectional."
        ::= { hh3cMplsLdpCrlspTnlEntry 3 }
     
     
     hh3cMplsLdpCrlspTnlSignallingProto OBJECT-TYPE
        SYNTAX        INTEGER { none(1), ldp(2), rsvp(3) }
        MAX-ACCESS    read-create
        STATUS        current
        DESCRIPTION
            "The  signaling protocol, if any, that  set  up  this
             tunnel."
        DEFVAL        { none }
        ::= { hh3cMplsLdpCrlspTnlEntry 4 }
     
     hh3cMplsLdpCrlspTnlSetupPrio OBJECT-TYPE
        SYNTAX        INTEGER (0..7)
        MAX-ACCESS    read-create
        STATUS        current
        DESCRIPTION
            "The setup priority of this tunnel."
        REFERENCE
            "Extensions to RSVP for LSP Tunnels, Awduche  et  al,
             Internet  Draft <draft-mpls-rsvp-lsp-tunnel-02.txt>,
             March  1999., Constraint-Based LSP Setup using  LDP,
             Jamoussi,  Internet  Draft  <draft-ietf-mpls-cr-ldp-
             01.txt>, Feb. 1999."
        ::= { hh3cMplsLdpCrlspTnlEntry 5 }
     
     hh3cMplsLdpCrlspTnlHoldingPrio OBJECT-TYPE
        SYNTAX        INTEGER (0..7)
        MAX-ACCESS    read-create
        STATUS        current
        DESCRIPTION
            "The holding priority for this tunnel."
        REFERENCE
            "  Extensions to RSVP for LSP Tunnels, Awduche et al,
             Internet  Draft <draft-mpls-rsvp-lsp-tunnel-02.txt>,
             March  1999., Constraint-Based LSP Setup using  LDP,
             Jamoussi,  Internet  Draft  <draft-ietf-mpls-cr-ldp-
             01.txt>, Feb. 1999."
        ::= { hh3cMplsLdpCrlspTnlEntry 6 }
     
     hh3cMplsLdpCrlspTnlPeakDataRate OBJECT-TYPE
        SYNTAX        BitRate
        UNITS         "bits per second"
        MAX-ACCESS    read-create
        STATUS        current
        DESCRIPTION
            "The peak rate - the maximum rate at which traffic will be sent on the
             CRLSP."
        REFERENCE
            "Section 4.3.1.2, Constraint-Based LSP Setup using LDP, Jamoussi, et.
             al, <draft-ietf-mpls-crldp-02.txt>, August 1999."
        DEFVAL        { 0 }
        ::= { hh3cMplsLdpCrlspTnlEntry 7 }
     
     hh3cMplsLdpCrlspTnlPeakBurstSize OBJECT-TYPE
        SYNTAX        BurstSize
        UNITS         "bytes"
        MAX-ACCESS    read-create
        STATUS        current
        DESCRIPTION
            "The peak burst size - the maximum burst size of the traffic that can 
             occur in the established CRLSP."
        REFERENCE
            "Section 4.3, Constraint-Based LSP Setup using LDP, Jamoussi, et.
             al, <draft-ietf-mpls-crldp-02.txt>, August 1999."
        DEFVAL        { 0 }
        ::= { hh3cMplsLdpCrlspTnlEntry 8 }
     
     hh3cMplsLdpCrlspTnlCommittedDataRate OBJECT-TYPE
        SYNTAX        BitRate
        UNITS         "bits per second"
        MAX-ACCESS    read-create
        STATUS        current
        DESCRIPTION
            "The committed rate - the committed rate at which traffic will be sent on the
             CRLSP."
        REFERENCE
            "Section 4.3.1.3, Constraint-Based LSP Setup using LDP, Jamoussi, et.
             al, <draft-ietf-mpls-crldp-02.txt>, August 1999."
        DEFVAL        { 0 }
        ::= { hh3cMplsLdpCrlspTnlEntry 9 }
     
     hh3cMplsLdpCrlspTnlCommittedBurstSize OBJECT-TYPE
        SYNTAX        BurstSize
        UNITS         "bytes"
        MAX-ACCESS    read-create
        STATUS        current
        DESCRIPTION
            "The committed burst size - the committed burst size of the traffic 
             that will be handled in the established CRLSP."
        REFERENCE
            "Section 4.3, Constraint-Based LSP Setup using LDP, Jamoussi, et.
             al, <draft-ietf-mpls-crldp-02.txt>, August 1999."
        DEFVAL        { 0 }
        ::= { hh3cMplsLdpCrlspTnlEntry 10 }
     
     hh3cMplsLdpCrlspTnlExcessBurstSize OBJECT-TYPE
        SYNTAX        BurstSize
        UNITS         "bytes"
        MAX-ACCESS    read-create
        STATUS        current
        DESCRIPTION
            "The Excess burst size - the excess burst size limit to be used
             for traffic conditioning at the ingress of the CRLSP."
        REFERENCE
            "Section 4.3.1.4, Constraint-Based LSP Setup using LDP, Jamoussi, et.
             al, <draft-ietf-mpls-crldp-02.txt>, August 1999."
        DEFVAL        { 0 }
        ::= { hh3cMplsLdpCrlspTnlEntry 11 }
     
     hh3cMplsLdpCrlspTnlIsPinned OBJECT-TYPE
        SYNTAX        TruthValue
        MAX-ACCESS    read-create
        STATUS        current
        DESCRIPTION
            "Indicates  whether  the loose-routed  hops  of  this
             tunnel are to be pinned."
        DEFVAL        { false }
        ::= { hh3cMplsLdpCrlspTnlEntry 12 }
     
     hh3cMplsLdpCrlspTnlFrequency OBJECT-TYPE
        SYNTAX        INTEGER (0..2)
        MAX-ACCESS    read-create
        STATUS        current
        DESCRIPTION
            "Indicates the frequency of usage of the established CRLSP."
        REFERENCE
            "Section 4.3.1.1, Constraint-Based LSP Setup using LDP, Jamoussi, et.
             al, <draft-ietf-mpls-crldp-02.txt>, August 1999."
        ::= { hh3cMplsLdpCrlspTnlEntry 13 }
     
     hh3cMplsLdpCrlspTnlWeight OBJECT-TYPE
        SYNTAX        INTEGER (0..255)
        MAX-ACCESS    read-create
        STATUS        current
        DESCRIPTION
            "Indicates the weight that is the established CRLSP."
        REFERENCE
            "Section 4.3, Constraint-Based LSP Setup using LDP, Jamoussi, et.
             al, <draft-ietf-mpls-crldp-02.txt>, August 1999."
        ::= { hh3cMplsLdpCrlspTnlEntry 14 }
     
     hh3cMplsLdpCrlspTnlRowStatus OBJECT-TYPE
        SYNTAX        RowStatus
        MAX-ACCESS    read-create
        STATUS        current
        DESCRIPTION
            "For controlling the state of this row.
             The status can be set to 'active' only when atleast one ERHOP
             is created in the hh3cMplsLdpErHopTable, associated with this
             tunnel."
        ::= { hh3cMplsLdpCrlspTnlEntry 15 }

    -- 
    -- Er-Hop Table
    --

     hh3cMplsLdpCrlspErHopTable  OBJECT-TYPE
        SYNTAX        SEQUENCE OF Hh3cMplsLdpCrlspErHopEntry
        MAX-ACCESS    not-accessible
        STATUS        current
        DESCRIPTION
            "The hh3cMplsLdpCrlspErHopTable is used to indicate the hops,
             strict  or  loose,  for an MPLS  CRLSP tunnel  defined  in
             hh3cMplsLdpCrlspTnlTable. 
     
             There must be atleast one entry in this table for each CRLSP tunnel 
             that is supported in the hh3cMplsLdpCrlspTnlTable.
             
             The first row in the table  is  the
             first hop after the origination point of the tunnel."
        ::= { hh3cMplsLdpCrlspTnlObjects 2 }
     
     hh3cMplsLdpCrlspErHopEntry  OBJECT-TYPE
        SYNTAX        Hh3cMplsLdpCrlspErHopEntry
        MAX-ACCESS    not-accessible
        STATUS        current
        DESCRIPTION
            "An  entry in this table represents a tunnel hop.  An
             entry  is  created  by a network  administrator  for
             signalled ERLSP set up by LDP or RSVP."
        INDEX  {  hh3cMplsLdpLsrIncarnID, 
                  hh3cMplsLdpCrlspTnlIndex, hh3cMplsLdpCrlspErHopIndex  }
           ::= { hh3cMplsLdpCrlspErHopTable 1 }
     
     Hh3cMplsLdpCrlspErHopEntry ::= SEQUENCE {
           hh3cMplsLdpCrlspErHopIndex              INTEGER,
           hh3cMplsLdpCrlspErHopAddrType           INTEGER,
           hh3cMplsLdpCrlspErHopIpv4Addr           IpAddress,
           hh3cMplsLdpCrlspErHopIpv4PrefixLen      INTEGER,
           hh3cMplsLdpCrlspErHopStrictOrLoose      INTEGER,
           hh3cMplsLdpCrlspErHopRowStatus          RowStatus
        }
     
     hh3cMplsLdpCrlspErHopIndex OBJECT-TYPE
        SYNTAX        INTEGER
        MAX-ACCESS    not-accessible
        STATUS        current
        DESCRIPTION
            "Secondary  index  into  this table  identifying  the
             particular hop."
        ::= { hh3cMplsLdpCrlspErHopEntry 1 }
     
     hh3cMplsLdpCrlspErHopAddrType OBJECT-TYPE
        SYNTAX        INTEGER { ipV4(1) }
        MAX-ACCESS    read-create
        STATUS        current
        DESCRIPTION
            "Address type of this hop."
        DEFVAL        { ipV4 }
        ::= { hh3cMplsLdpCrlspErHopEntry 2 }
     
     hh3cMplsLdpCrlspErHopIpv4Addr OBJECT-TYPE
        SYNTAX        IpAddress
        MAX-ACCESS    read-create
        STATUS        current
        DESCRIPTION
            "If hh3cMplsLdpCrlspErHopAddrType is ipV4(1), IPv4 address of
             this  hop.  This object is not significant otherwise
             and should return a value of 0."
        ::= { hh3cMplsLdpCrlspErHopEntry 3 }
     
     hh3cMplsLdpCrlspErHopIpv4PrefixLen OBJECT-TYPE
        SYNTAX        INTEGER (1..32)
        MAX-ACCESS    read-create
        STATUS        current
        DESCRIPTION
            "If  hh3cMplsLdpCrlspErHopAddrType is ipV4(1), prefix  length
             for  this  hop's IPv4 address.  This object  is  not
             significant otherwise and should return a  value  of
             0."
        ::= { hh3cMplsLdpCrlspErHopEntry 4 }
     
     hh3cMplsLdpCrlspErHopStrictOrLoose OBJECT-TYPE
        SYNTAX        INTEGER { strict(1), loose(2) }
        MAX-ACCESS    read-create
        STATUS        current
        DESCRIPTION
            "Whether this is a strict or loose hop."
        ::= { hh3cMplsLdpCrlspErHopEntry 5 }
     
     hh3cMplsLdpCrlspErHopRowStatus OBJECT-TYPE
        SYNTAX        RowStatus
        MAX-ACCESS    read-create
        STATUS        current
        DESCRIPTION
            "For creating, modifying and deleting this row."
        ::= { hh3cMplsLdpCrlspErHopEntry 6 }

     ---
     --- Notifications
     ---

     hh3cMplsLdpNotificationPrefix   OBJECT IDENTIFIER ::=
                                      { hh3cMplsLdpNotifications 0 }

     hh3cMplsLdpFailedInitSessionThresholdExceeded NOTIFICATION-TYPE
     OBJECTS     {
			hh3cMplsLdpLsrIncarnID, hh3cMplsLdpEntityID,
                        hh3cMplsLdpEntityFailedInitSessionThreshold
                 }
     STATUS      current
   DESCRIPTION   "This notification is generated whenever the value
             of hh3cMplsLdpEntityFailedInitSessionThreshold is
             exceeded."
   ::= { hh3cMplsLdpNotificationPrefix 1 }

--          OBJECTS     { hh3cMplsLdpLsrIncarnID, hh3cMplsLdpEntityID,
--                        hh3cMplsLdpEntityFailedInitSessionThreshold
--                      }
--          STATUS      current
--          DESCRIPTION
--             "This notification is generated whenever the value
--             of hh3cMplsLdpEntityFailedInitSessionThreshold is
--             exceeded."
--          ::= { hh3cMplsLdpNotificationPrefix 1 }

     hh3cMplsLdpCrlspTunnelUp NOTIFICATION-TYPE
     OBJECTS     {
			hh3cMplsLdpLsrIncarnID, hh3cMplsLdpEntityID,
                  hh3cMplsLdpCrlspTnlIndex 
                 }
        STATUS      current
        DESCRIPTION
            "This notification is generated by the Ingress LSR of the CRLSP tunnel
             on the receipt of Label mapping message from the downstream LSR for
             the LAbel request sent for the CRLSP tunnel."
        ::= { hh3cMplsLdpNotificationPrefix 2 }
  
     hh3cMplsLdpCrlspTunnelDown NOTIFICATION-TYPE
     OBJECTS     {
		hh3cMplsLdpLsrIncarnID, hh3cMplsLdpEntityID,
                  hh3cMplsLdpCrlspTnlIndex }
        STATUS      current
        DESCRIPTION
            "This notification is generated when a CRLSP Row status is modified
             to destroy the CRLSP tunnel.  - due to pre-emption etc.,"
        ::= { hh3cMplsLdpNotificationPrefix 3 }
     
     hh3cMplsLdpCrlspTunnelSetupFailure NOTIFICATION-TYPE
     OBJECTS     { hh3cMplsLdpLsrIncarnID, hh3cMplsLdpEntityID,
                  hh3cMplsLdpCrlspTnlIndex }
        STATUS      current
        DESCRIPTION
            "This notification is generated by the Ingress LSR of the CRLSP tunnel
             on the receipt of Nak message from the downstream LSR for
             the Label request sent for the CRLSP tunnel. This can occur due to
             improper ER hop values being set, or Traffic resources not available
             etc.,"
        ::=  { hh3cMplsLdpNotificationPrefix 4 } 


     hh3cMplsLdpIncarnUpEventFailure  NOTIFICATION-TYPE
     OBJECTS     { hh3cMplsLdpLsrIncarnID}
        STATUS      current
        DESCRIPTION
            "This notification is generated by LDP to notify 
             the Incarnation UP Event failure"
        ::= { hh3cMplsLdpNotificationPrefix 11 } 

     hh3cMplsLdpIncarnDownEventFailure NOTIFICATION-TYPE
     OBJECTS     { hh3cMplsLdpLsrIncarnID }
        STATUS      current
        DESCRIPTION
            "This notification is generated by LDP to notify 
             the Incarnation DOWN Event failure"
        ::= { hh3cMplsLdpNotificationPrefix 12 } 

     hh3cMplsLdpEntityUpEventFailure NOTIFICATION-TYPE
     OBJECTS     { hh3cMplsLdpLsrIncarnID, hh3cMplsLdpEntityID}
        STATUS      current
        DESCRIPTION
            "This notification is generated by LDP to notify 
             the ENTITY UP Event failure"
        ::= { hh3cMplsLdpNotificationPrefix 13 }


     hh3cMplsLdpEntityDownEventFailure NOTIFICATION-TYPE
     OBJECTS     { hh3cMplsLdpLsrIncarnID, hh3cMplsLdpEntityID }
        STATUS      current
        DESCRIPTION
            "This notification is generated by LDP to notify 
             the ENTITY  DOWN Event failure"
        ::= { hh3cMplsLdpNotificationPrefix 14 }
        hh3cMplsLdpSessionUpEventFailure NOTIFICATION-TYPE
     OBJECTS     { hh3cMplsLdpSessionID, hh3cMplsLdpSessionState }
        STATUS      current
        DESCRIPTION
            "Generation of this trap occurs when the 
            value of 'hh3cMplsLdpSessionState' enters
             the 'operational(5)' state."
        ::= { hh3cMplsLdpNotificationPrefix 15 }  
        
     hh3cMplsLdpSessionDownEventFailure NOTIFICATION-TYPE
     OBJECTS     { hh3cMplsLdpSessionID, hh3cMplsLdpSessionState }
        STATUS      current
        DESCRIPTION
            "Generation of this trap occurs when the 
            value of 'hh3cMplsLdpSessionState' leaves 
            the 'operational(5)' state."
        ::= { hh3cMplsLdpNotificationPrefix 16 }      

-- End of notifications.
END
