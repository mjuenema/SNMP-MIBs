-- ============================================================================
-- Copyright (C) by  HUAWEI TECHNOLOGIES. All rights reserved.
-- 
-- Description:  
-- Reference:  
-- Version: V1.0
-- History:
-- Created by hexingjian 61140 2008-12-30 
-- modified by xuxuguang 00107864    2009-12-10
-- ============================================================================
         
HUAWEI-L2MULTICAST-MIB DEFINITIONS ::= BEGIN

IMPORTS     
    MODULE-IDENTITY,OBJECT-TYPE, 
    Counter32,Integer32,Unsigned32,IpAddress,Counter64
        FROM SNMPv2-SMI

    TruthValue,TEXTUAL-CONVENTION,
    RowStatus,MacAddress,DisplayString
        FROM SNMPv2-TC

    MODULE-COMPLIANCE, OBJECT-GROUP
        FROM SNMPv2-CONF
    
    EnabledStatus    
        FROM P-BRIDGE-MIB
        
    VlanIdOrAny    
        FROM Q-BRIDGE-MIB
    
    InterfaceIndex,InterfaceIndexOrZero
        FROM IF-MIB
        
    hwDatacomm
            FROM HUAWEI-MIB;
            
VlanIdOrAnyOrNone ::= TEXTUAL-CONVENTION
    DISPLAY-HINT "d"
    STATUS       current
    DESCRIPTION
        "The VLAN-ID that uniquely identifies a specific VLAN,
        any VLAN, or no VLAN.  The special values 0 and 4095
        have the same meaning as described in the VlanIdOrAny
        and VlanIdOrNone TEXTUAL-CONVENTIONs.

        Note that a MIB object that is defined using this
        TEXTUAL-CONVENTION should clarify the meaning of
        'any VLAN' and 'no VLAN' (i.e., the special values
        0 and 4095)."
    SYNTAX       Integer32 (0 | 1..4094 | 4095)
    
hwL2MultiCastMIB MODULE-IDENTITY 
    LAST-UPDATED "200812300000Z" 
    ORGANIZATION "Huawei Technologies co.,Ltd."
    CONTACT-INFO 
            " R&D BeiJing, Huawei Technologies co.,Ltd.
            Huawei Bld.,NO.3 Xinxi Rd., 
            Shang-Di Information Industry Base,
            Hai-Dian District Beijing P.R. China
            Zip:100085 
            Http://www.huawei.com                                       
            E-mail:support@huawei.com "
    DESCRIPTION 
        "The MIB module for IGMP Snooping feature. 

         Internet Group Management Protocol (IGMP) is the protocol used 
         by IPv4 end hosts to indicate their interest in receiving 
         multicast traffic for certain multicast groups to neighboring 
         multicast routers. 
         IGMP Snooping is a switch protocol. A switch that implements 
         IGMP Snooping listens to the IGMP messages exchanged between 
         the hosts and router, then provides selective transmission of 
         multicast traffic based on multicast mac destination address
         or multicast group address."      
    ::= { hwDatacomm 181 }

-- Textual Convention
   
HWPortType ::= TEXTUAL-CONVENTION
     STATUS  current
     DESCRIPTION 
        "type of port :
                 invalid(1):invalid type,       
                 pw(2) :  pw type,
                 switchport(3) :  switchport type,
                 dot1q(4): dot1q sub-interface type,
                 termination(5): termination sub-interface type,
                 board(6): interface board number,
                 VlanPort(7): Vlanif port,
                 qinq-batch-config(9): batch config qinq port ce VLAN ID,
                 dot1q-termination-batch-config(10): batch config dot1q termination port ce VLAN ID"
     SYNTAX   INTEGER
     {   
         invalid(1),     
         pw(2),
         switchport(3),
         dot1q(4),
         termination(5),
         board(6),
         vlanPort(7),
         qinq-batch-config(9),
         dot1q-termination-batch-config(10)
     }
     
     
     
            

 
hwIgspMibObject   OBJECT IDENTIFIER ::= { hwL2MultiCastMIB 1 } 

       
--
--  The hwIgspSystemInfo group.
--
hwIgspSystemInfo     
        OBJECT IDENTIFIER ::= { hwIgspMibObject 1 }
 
hwIgmpSnoopingEnabled OBJECT-TYPE
    SYNTAX       EnabledStatus
    MAX-ACCESS   read-write
    STATUS       current
    DESCRIPTION
        "IGMP snooping is enabled or disabled in the global view:
                        1: enabled
                        2: disabled
                        The default value is 2.
                "
    ::= { hwIgspSystemInfo 1 }     

hwSendQueryEnabled              OBJECT-TYPE
    SYNTAX       EnabledStatus
    MAX-ACCESS   read-write
    STATUS       current
    DESCRIPTION
        "The sending of query packets is enabled or disabled:
                        1: enabled
                        2: disabled
                The default value is 2.
                Note: Ensure that you query and configure this object after hwIgmpSnoopingEnabled is configured.
                "
    ::= { hwIgspSystemInfo 2 } 

hwSendQuerySourceIpAddr OBJECT-TYPE
    SYNTAX       IpAddress  
    MAX-ACCESS   read-write
    STATUS       current
    DESCRIPTION  
        "The source IP addresses of the Query messages sent by a device.
                The value ranges from 0.0.0.1 to 223.255.255.255.
                The default value is 192.168.0.1.
                "
    ::= { hwIgspSystemInfo  3}


hwL2mcCacTrapInterval OBJECT-TYPE
    SYNTAX       Integer32(0..1200) 
    MAX-ACCESS   read-write
    STATUS       current
    DESCRIPTION  
        "The CAC trap interval. The default is zero."
    ::= { hwIgspSystemInfo  4}

hwL2mcPerformanceStatisticsInterval OBJECT-TYPE
    SYNTAX       Integer32(5 |15 | 30 | 60)
    MAX-ACCESS   read-write
    STATUS       current
    DESCRIPTION  
        "The Performance statistic interval. The default is 15 minute."
    ::= { hwIgspSystemInfo  5}


    
--
--  The hwL2mcCfgInfo group.
--
hwL2mcCfgInfo     
        OBJECT IDENTIFIER ::= { hwIgspMibObject 2 }

hwL2mcCfgTable OBJECT-TYPE
    SYNTAX       SEQUENCE OF HWL2mcCfgEntry
    MAX-ACCESS   not-accessible
    STATUS       current
    DESCRIPTION
        "This table describes the configurations of IGMP snooping in a VLAN or a VSI."
    ::= { hwL2mcCfgInfo 1 }
    
hwL2mcCfgEntry OBJECT-TYPE
    SYNTAX       HWL2mcCfgEntry
    MAX-ACCESS   not-accessible
    STATUS       current
    DESCRIPTION
        "An entry is created for each active VLAN or VSI in the device 
         and deleted when the VLAN or VSI becomes inactive."
    INDEX { hwL2mcVlanIndex, hwL2mcVsiName }
    ::= { hwL2mcCfgTable 1 } 
     
HWL2mcCfgEntry ::= SEQUENCE { 
    hwL2mcVlanIndex            VlanIdOrAny,
    hwL2mcVsiName              DisplayString,
    hwL2mcEnabled              EnabledStatus,
    hwL2mcRouterAgingTime      Integer32,
    hwL2mcMaxQueryRespTime     Integer32,
    hwL2mcLastMemQueryInterval Integer32,
    hwL2mcQueryInterval        Integer32,
    hwL2mcRobustCount          Integer32,
    hwL2mcCheckRouterAlert     TruthValue,
    hwL2mcSendRouterAlert      TruthValue,  
    hwL2mcIgmpVersion          INTEGER ,
    hwL2mcFwdMode              INTEGER, 
    hwL2mcPromptLeaveEnable    EnabledStatus,
    hwL2mcPromptLeaveAclNum    Integer32,
    hwL2mcRouterPortLearningEnable    EnabledStatus,
    hwL2mcReportSuppressEnable    EnabledStatus,
    hwL2mcIgmpQuerierEnable       EnabledStatus,
    hwL2mcIgmpSsmMappingEnable    EnabledStatus,
    hwL2mcSsmAclNum               Integer32,
    hwL2mcProxyRouterProtocolPass TruthValue,
    hwL2mcAsmSsmFlag              Integer32,
    hwL2mcSrcLifeTime             Integer32,
    hwL2mcPerformanceStatistics   EnabledStatus,
    hwL2mcQuerierElection         EnabledStatus,
    hwETrackEnable                EnabledStatus,
    hwL2mcBackupQueryFwd          Integer32,
    hwL2mcBackupReportFwd         Integer32,
    hwL2mcQuerySuppress           Integer32,
    hwL2mcRtLearnRingLinkage      TruthValue,
    hwL2mcRowStatus               RowStatus
    }
   

hwL2mcVlanIndex  OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcCfgEntry 1 }
    
hwL2mcVsiName OBJECT-TYPE
    SYNTAX       DisplayString(SIZE (0..31))
    MAX-ACCESS   not-accessible
    STATUS       current
    DESCRIPTION
        "The name of a VSI. If a VLAN is specified, the value is 32."
    ::= { hwL2mcCfgEntry 2 }    
    
hwL2mcEnabled OBJECT-TYPE
    SYNTAX       EnabledStatus
    MAX-ACCESS   read-create
    STATUS       current
    DESCRIPTION
        "Whether IGMP snooping is enabled in a VLAN or a VSI:
                        1:enabled
                        2:disabled
                The default value is 2.
                "
    ::= { hwL2mcCfgEntry 3 }

hwL2mcRouterAgingTime OBJECT-TYPE
    SYNTAX       Integer32(1..1000)
    MAX-ACCESS   read-create
    STATUS       current
    DESCRIPTION
        "The aging time of an interface on a router.
                The value ranges from 1 to 1000, in seconds.
                The default value is 180, which router port is created by Igmp Query message.
                And when it is created by PIM hello messge, the default value is the time of Holdtime in the message.
                "
    ::= { hwL2mcCfgEntry 4 }  
    
hwL2mcMaxQueryRespTime OBJECT-TYPE
    SYNTAX       Integer32(1..25)
    MAX-ACCESS   read-create
    STATUS       current
    DESCRIPTION
        "The maximum response time.
                The value ranges from 1 to 25, in seconds.
                The default value is 10, in seconds.
                "
    ::= { hwL2mcCfgEntry 5 }
      
hwL2mcLastMemQueryInterval OBJECT-TYPE
    SYNTAX       Integer32(1..5)
    MAX-ACCESS   read-create
    STATUS       current
    DESCRIPTION
        "The last member query interval.
                The value ranges from 1 to 5, in seconds.
                The default value is 1, in seconds.
                "
    ::= { hwL2mcCfgEntry 6 }
    
hwL2mcQueryInterval OBJECT-TYPE
    SYNTAX       Integer32(1..65535)
    MAX-ACCESS   read-create
    STATUS       current
    DESCRIPTION
        "The query interval.
                The value ranges from 1 to 65535, in seconds.
                The default value is 60, in seconds.
                "
    ::= { hwL2mcCfgEntry 7 }
    
hwL2mcRobustCount OBJECT-TYPE
    SYNTAX       Integer32(2..5)
    MAX-ACCESS   read-create
    STATUS       current
    DESCRIPTION
        "The robustness variable.
                The value ranges from 2 to 5.
                The default value is 2.
                "
    ::= { hwL2mcCfgEntry 8 }
    
hwL2mcCheckRouterAlert OBJECT-TYPE
    SYNTAX       TruthValue
    MAX-ACCESS   read-create
    STATUS       current
    DESCRIPTION
        "Whether to check the router-alert of a packet.
                The default value is false.
                "
    ::= { hwL2mcCfgEntry 9 }
    
hwL2mcSendRouterAlert OBJECT-TYPE
    SYNTAX       TruthValue
    MAX-ACCESS   read-create
    STATUS       current
    DESCRIPTION
        "Whether to send the router-alert of a packet.
                The default value is true.
                "
    ::= { hwL2mcCfgEntry 10 }    
    
hwL2mcIgmpVersion OBJECT-TYPE
    SYNTAX       INTEGER
            {
            version1(1),
            version2(2),
            version3(3)
            }
    MAX-ACCESS   read-create
    STATUS       current
    DESCRIPTION
        "The version of the IGMP packets.
                The value ranges from 1 to 3.
                The default value is 2.
                "
    ::= { hwL2mcCfgEntry 11 }    
    
hwL2mcFwdMode OBJECT-TYPE
    SYNTAX       INTEGER
            {
            ip(1),
            mac(2)
            }
    MAX-ACCESS   read-create
    STATUS       current
    DESCRIPTION
        "The forwarding mode:
                        1: IP
                        2: MAC
                The default value is 1.
                "
    ::= { hwL2mcCfgEntry 12 }    
    
hwL2mcPromptLeaveEnable OBJECT-TYPE
    SYNTAX       EnabledStatus
    MAX-ACCESS   read-create
    STATUS       current
    DESCRIPTION
        "Whether the prompt leave is enabled:
                        1: enabled
                        2: disabled
                The default value is 2.
                "
    ::= { hwL2mcCfgEntry 13 }    
    
hwL2mcPromptLeaveAclNum OBJECT-TYPE
    SYNTAX       Integer32(0|2000..3999)
    MAX-ACCESS   read-create
    STATUS       current
    DESCRIPTION
        "Whether the prompt leave complies with the ACL rules. The ACL number can be set.
                The ACL number ranges from 2000 to 3999.
                The default value is 0, indicating that no ACL number is set.
                "
    ::= { hwL2mcCfgEntry 14 }    
    
hwL2mcRouterPortLearningEnable OBJECT-TYPE
    SYNTAX       EnabledStatus
    MAX-ACCESS   read-create
    STATUS       current
    DESCRIPTION
        "Whether interface learning is enabled or not in a VLAN:
                        1: enabled
                        2: disabled
                The default value is 1.
                "
    ::= { hwL2mcCfgEntry 15 }    
    
hwL2mcReportSuppressEnable OBJECT-TYPE
    SYNTAX       EnabledStatus
    MAX-ACCESS   read-create
    STATUS       current
    DESCRIPTION
        "Whether the suppression of the IGMP Report message (proxy) is enabled:
                        1: enabled
                        2: disabled
                The default value is 2.
                "
    ::= { hwL2mcCfgEntry 16 }
    
hwL2mcIgmpQuerierEnable OBJECT-TYPE
    SYNTAX       EnabledStatus
    MAX-ACCESS   read-create
    STATUS       current
    DESCRIPTION
        "Whether the querier is enabled:
                        1: enabled
                        2: disabled
                The default value is 2.
                "
    ::= { hwL2mcCfgEntry 17 }    
    
hwL2mcIgmpSsmMappingEnable OBJECT-TYPE
    SYNTAX       EnabledStatus
    MAX-ACCESS   read-create
    STATUS       current
    DESCRIPTION
        "Whether Ssm-Mapping is enabled:
                        1: enabled
                        2: disabled
                The default value is 2.
                "
    ::= { hwL2mcCfgEntry 18 }    
    
hwL2mcSsmAclNum OBJECT-TYPE
    SYNTAX       Integer32(0|2000..2999)
    MAX-ACCESS   read-create
    STATUS       current
    DESCRIPTION
        "That SSM complies with the ACL number.
                The ACL number ranges from 2000 to 2999.
                The default value is 0, indicating that no ACL number is set.
                "
    ::= { hwL2mcCfgEntry 19 }    
    
hwL2mcProxyRouterProtocolPass OBJECT-TYPE
    SYNTAX       TruthValue
    MAX-ACCESS   read-create
    STATUS       current
    DESCRIPTION
        "Whether protocol packets are allowed to pass a router port when proxy is enabled.
                The default value is false.
                "
    ::= { hwL2mcCfgEntry 20 }
    
hwL2mcAsmSsmFlag    OBJECT-TYPE
    SYNTAX       Integer32(1..3)
    MAX-ACCESS   read-create
    STATUS       current
    DESCRIPTION
        "That restric study:
                1: asm-ssm
                2: asm-only
                3: ssm-only
                The default value is 1.
                "
    ::= { hwL2mcCfgEntry 21 }

hwL2mcSrcLifeTime  OBJECT-TYPE
    SYNTAX       Integer32(60..1000)
    MAX-ACCESS   read-create
    STATUS       current
    DESCRIPTION
        "That source aging time:
                range from 60 to 1000
                The default value is 210.
                "
    ::= { hwL2mcCfgEntry 22 }
    
hwL2mcPerformanceStatistics OBJECT-TYPE
    SYNTAX       EnabledStatus
    MAX-ACCESS   read-create
    STATUS       current
    DESCRIPTION
        "That performance statistic is enabled:
                1: enabled
                2: disabled
                The default value is 2.
                "
    ::= { hwL2mcCfgEntry 23 }
    
hwL2mcQuerierElection OBJECT-TYPE
    SYNTAX       EnabledStatus
    MAX-ACCESS   read-create
    STATUS       current
    DESCRIPTION
        "That querier election is enabled:
                1: enabled
                2: disabled
                The default value is 2.
                "
    ::= { hwL2mcCfgEntry 24 }    

hwETrackEnable OBJECT-TYPE
    SYNTAX       EnabledStatus
    MAX-ACCESS   read-create
    STATUS       current
    DESCRIPTION
        "The host explicity track is enabled:
                1: enabled
                2: disabled
                The default value is 2.
                "
    ::= { hwL2mcCfgEntry 25 }
    
hwL2mcBackupQueryFwd OBJECT-TYPE
    SYNTAX       Integer32(1..3)
    MAX-ACCESS   read-create
    STATUS       current
    DESCRIPTION
        "That IGMP query forward :
        	1: Do not forward;
        	2: Forward without replace source MAC address;
        	3: Forward with replace source MAC address;
                The default value is 1.
                "
    ::= { hwL2mcCfgEntry 26 }

hwL2mcBackupReportFwd OBJECT-TYPE
    SYNTAX       Integer32(1..3)
    MAX-ACCESS   read-create
    STATUS       current
    DESCRIPTION
        "That IGMP report forward :
        	1: Do not forward;
        	2: Forward without replace source MAC address;
        	3: Forward with replace source MAC address;
                The default value is 1.
                "
    ::= { hwL2mcCfgEntry 27 }

hwL2mcQuerySuppress OBJECT-TYPE
    SYNTAX       Integer32
    MAX-ACCESS   read-create
    STATUS       current
    DESCRIPTION
        "Whether supress IGMP query packet or time of suppress interval.
                "
    ::= { hwL2mcCfgEntry 28 }

hwL2mcRtLearnRingLinkage OBJECT-TYPE
    SYNTAX       TruthValue
    MAX-ACCESS   read-create
    STATUS       current
    DESCRIPTION
        "Whether responed to link state for SEP.
                "
    ::= { hwL2mcCfgEntry 29 }

hwL2mcRowStatus OBJECT-TYPE
    SYNTAX       RowStatus
    MAX-ACCESS   read-create
    STATUS       current
    DESCRIPTION
        "The row status."
    ::= { hwL2mcCfgEntry 100 }    
    


--
--  The hwL2mcStatisticsInfo group.
--
hwL2mcStatisticsInfo     
        OBJECT IDENTIFIER ::= { hwIgspMibObject 3 }
        
hwL2mcStatisticsTable OBJECT-TYPE
    SYNTAX       SEQUENCE OF HWL2mcStatisticsEntry
    MAX-ACCESS   not-accessible
    STATUS       current
    DESCRIPTION
        "Table contains VLAN or VSI statistics information
         for IGMP Snooping."
    ::= { hwL2mcStatisticsInfo 1 }

hwL2mcStatisticsEntry OBJECT-TYPE
    SYNTAX       HWL2mcStatisticsEntry
    MAX-ACCESS   not-accessible
    STATUS       current
    DESCRIPTION
        "An entry is created for each active VLAN or VSI in the device 
         and deleted when the VLAN or VSI becomes inactive."
    INDEX { hwL2mcStatsVlanIndex, hwL2mcStatsVsiName }
    ::= { hwL2mcStatisticsTable 1 } 
     
HWL2mcStatisticsEntry ::= SEQUENCE { 
    hwL2mcStatsVlanIndex        VlanIdOrAny,
    hwL2mcStatsVsiName          DisplayString,
    hwL2mcRecvIgmpV1ReportNum   Counter32,
    hwL2mcRecvIgmpV2ReportNum   Counter32,
    hwL2mcRecvIgmpV3ReportNum   Counter32,
    hwL2mcRecvIgmpLeaveNum      Counter32,
    hwL2mcRecvIgmpV1QueryNum    Counter32,
    hwL2mcRecvIgmpV2QueryNum    Counter32,
    hwL2mcRecvIgmpV3QueryNum    Counter32,
    hwL2mcRecvPimHelloNum       Counter32,  
    hwL2mcSendQueryNum          Counter32 ,
    hwL2mcSendQuerySourceNum    Counter32, 
    hwL2mcProxyGenQueryNum      Counter32,
    hwL2mcProxyGroupQueryNum    Counter32,
    hwL2mcProxyGroupSourceQueryNum   Counter32,
    hwL2mcIgmpPacketClearStats  TruthValue
    }                                                                                                                                      

hwL2mcStatsVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcStatisticsEntry 1 }

hwL2mcStatsVsiName OBJECT-TYPE
    SYNTAX       DisplayString(SIZE (0..31))
    MAX-ACCESS   not-accessible
    STATUS       current
    DESCRIPTION
        "The name of a VSI. If a VLAN is specified, the value is 32."
    ::= { hwL2mcStatisticsEntry 2 }
 
hwL2mcRecvIgmpV1ReportNum OBJECT-TYPE
    SYNTAX       Counter32
    MAX-ACCESS   read-only
    STATUS       current
    DESCRIPTION
        "The number of IGMPv1 Report messages received in a VLAN or a VSI."
    ::= { hwL2mcStatisticsEntry 3 }
    
hwL2mcRecvIgmpV2ReportNum OBJECT-TYPE
    SYNTAX       Counter32
    MAX-ACCESS   read-only
    STATUS       current
    DESCRIPTION
        "The number of IGMPv2 Report messages received in a VLAN or a VSI."
    ::= { hwL2mcStatisticsEntry 4 }
    
hwL2mcRecvIgmpV3ReportNum OBJECT-TYPE
    SYNTAX       Counter32
    MAX-ACCESS   read-only
    STATUS       current
    DESCRIPTION
        "The number of IGMPv3 Report messages received in a VLAN or a VSI."
    ::= { hwL2mcStatisticsEntry 5 }
    
hwL2mcRecvIgmpLeaveNum OBJECT-TYPE
    SYNTAX       Counter32
    MAX-ACCESS   read-only
    STATUS       current
    DESCRIPTION
        "The number of IGMP Leave messages received in a VLAN or a VSI."
    ::= { hwL2mcStatisticsEntry 6 } 
    
hwL2mcRecvIgmpV1QueryNum OBJECT-TYPE
    SYNTAX       Counter32
    MAX-ACCESS   read-only
    STATUS       current
    DESCRIPTION
        "The number of IGMPv1 Query messages received in a VLAN or a VSI."
    ::= { hwL2mcStatisticsEntry 7 }
 
hwL2mcRecvIgmpV2QueryNum OBJECT-TYPE
    SYNTAX       Counter32
    MAX-ACCESS   read-only
    STATUS       current
    DESCRIPTION
        "The number of IGMPv2 Query messages received in a VLAN or a VSI."
    ::= { hwL2mcStatisticsEntry 8 }
    
hwL2mcRecvIgmpV3QueryNum OBJECT-TYPE
    SYNTAX       Counter32
    MAX-ACCESS   read-only
    STATUS       current
    DESCRIPTION
        "The number of IGMPv3 Query messages received in a VLAN or a VSI."
    ::= { hwL2mcStatisticsEntry 9 }
    
hwL2mcRecvPimHelloNum OBJECT-TYPE
    SYNTAX       Counter32
    MAX-ACCESS   read-only
    STATUS       current
    DESCRIPTION
        "The number of PIM Hello messages received in a VLAN or a VSI."
    ::= { hwL2mcStatisticsEntry 10 }
    
hwL2mcSendQueryNum OBJECT-TYPE
    SYNTAX       Counter32
    MAX-ACCESS   read-only
    STATUS       current
    DESCRIPTION
        "The number of IGMP Query messages (the source address is 0) in a VLAN or a VSI."
    ::= { hwL2mcStatisticsEntry 11 }
    
hwL2mcSendQuerySourceNum OBJECT-TYPE
    SYNTAX       Counter32
    MAX-ACCESS   read-only
    STATUS       current
    DESCRIPTION
        "The number of IGMP Query messages (the source address is not 0) in a VLAN or a VSI."
    ::= { hwL2mcStatisticsEntry 12 }
 
hwL2mcProxyGenQueryNum OBJECT-TYPE
    SYNTAX       Counter32
    MAX-ACCESS   read-only
    STATUS       current
    DESCRIPTION
        "The number of Query messages sent by the proxy in a VLAN or a VSI."
    ::= { hwL2mcStatisticsEntry 13 }
    
hwL2mcProxyGroupQueryNum OBJECT-TYPE
    SYNTAX       Counter32
    MAX-ACCESS   read-only
    STATUS       current
    DESCRIPTION
        "The number of Query messages sent by the proxy in a VLAN or a VSI to a specified group."
    ::= { hwL2mcStatisticsEntry 14 }
    
hwL2mcProxyGroupSourceQueryNum OBJECT-TYPE
    SYNTAX       Counter32
    MAX-ACCESS   read-only
    STATUS       current
    DESCRIPTION
        "The number of Query messages sent by the proxy in a VLAN or a VSI to a specified source group."
    ::= { hwL2mcStatisticsEntry 15 }
    
hwL2mcIgmpPacketClearStats OBJECT-TYPE
    SYNTAX       TruthValue
    MAX-ACCESS   read-write
    STATUS       current
    DESCRIPTION
        "Whether to clear the statistics of IGMP snooping. If the value is 1, it indicates that the statistics need to be cleared."
    ::= { hwL2mcStatisticsEntry 30 }                    
   
   
--
--  The hwL2mcFwdInfo group.
--
hwL2mcFwdInfo     
        OBJECT IDENTIFIER ::= { hwIgspMibObject 4 }

hwL2mcFwdTable OBJECT-TYPE
    SYNTAX       SEQUENCE OF HWL2mcFwdEntry
    MAX-ACCESS   not-accessible
    STATUS       current
    DESCRIPTION
        "Table contains l2 multicast forward information
         for IGMP Snooping."
    ::= { hwL2mcFwdInfo 1 }
    
hwL2mcFwdEntry OBJECT-TYPE
    SYNTAX       HWL2mcFwdEntry
    MAX-ACCESS   not-accessible
    STATUS       current
    DESCRIPTION
        "An entry is created for each active VLAN or VSI in the device create a forwarding table entry and delete when 
        a forwarding table entry deleted."
    INDEX { hwL2mcFwdVlanIndex, hwL2mcFwdVsiName, hwL2mcFwdGroupAddress, hwL2mcFwdSourceAddress, hwL2mcFwdPortType,
            hwL2mcFwdPortIfIndex, hwL2mcFwdPortPeId, hwL2mcFwdPortCeId, 
            hwL2mcFwdPeerAddress, hwL2mcFwdVcOrSiteId }
    ::= { hwL2mcFwdTable 1 } 
     
HWL2mcFwdEntry ::= SEQUENCE { 
    hwL2mcFwdVlanIndex      VlanIdOrAny,
    hwL2mcFwdVsiName        DisplayString,
    hwL2mcFwdGroupAddress   IpAddress,
    hwL2mcFwdSourceAddress  IpAddress,      
    hwL2mcFwdPortType       HWPortType,
    hwL2mcFwdPortIfIndex    InterfaceIndexOrZero,
    hwL2mcFwdPortPeId       VlanIdOrAny,
    hwL2mcFwdPortCeId       VlanIdOrAny,
    hwL2mcFwdPeerAddress    IpAddress,
    hwL2mcFwdVcOrSiteId     Unsigned32,
    hwL2mcFwdAddressType    INTEGER,
    hwL2mcFwdHostFlag1      INTEGER, 
    hwL2mcFwdHostFlag2      INTEGER,
    hwL2mcFwdHostFlag3      INTEGER,
    hwL2mcFwdHostFlag4      INTEGER
    }
    
hwL2mcFwdVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcFwdEntry 1 }
    
hwL2mcFwdVsiName OBJECT-TYPE
    SYNTAX       DisplayString(SIZE (0..31))
    MAX-ACCESS   not-accessible
    STATUS       current
    DESCRIPTION
        "The name of a VSI. If a VLAN is specified, the value is 32."
    ::= { hwL2mcFwdEntry 2 }
    
hwL2mcFwdGroupAddress OBJECT-TYPE
    SYNTAX       IpAddress
    MAX-ACCESS   not-accessible
    STATUS       current
    DESCRIPTION
        "The group address of a multicast group. In the case of MAC forwarding, the group address is the smallest of 32 IP addresses."
    ::= { hwL2mcFwdEntry 3 }    

hwL2mcFwdSourceAddress OBJECT-TYPE
    SYNTAX       IpAddress
    MAX-ACCESS   not-accessible
    STATUS       current
    DESCRIPTION
        "The source IP address of a multicast group."
    ::= { hwL2mcFwdEntry 4 }
        
hwL2mcFwdPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcFwdEntry 5 }

hwL2mcFwdPortIfIndex OBJECT-TYPE
    SYNTAX       InterfaceIndexOrZero
    MAX-ACCESS   not-accessible
    STATUS       current
    DESCRIPTION
        "The interface index. The value 0 indicates that the interface index is invalid."
    ::= { hwL2mcFwdEntry 6 }
 
hwL2mcFwdPortPeId OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcFwdEntry 7 }
    
hwL2mcFwdPortCeId OBJECT-TYPE
    SYNTAX       VlanIdOrAny
    MAX-ACCESS   not-accessible
    STATUS       current
    DESCRIPTION
        "The CE VID of an interface.
                The value ranges from 1 to 4095.
                The value 4095 indicates that the CE VID is invalid.
                "
    ::= { hwL2mcFwdEntry 8 }
    
hwL2mcFwdPeerAddress OBJECT-TYPE
    SYNTAX       IpAddress
    MAX-ACCESS   not-accessible
    STATUS       current
    DESCRIPTION
        "The peer IP address of a PW interface. The value 0.0.0.0 indicates that the IP address is invalid."
    ::= { hwL2mcFwdEntry 9 }
    
hwL2mcFwdVcOrSiteId OBJECT-TYPE
    SYNTAX       Unsigned32(1..4294967295) 
    MAX-ACCESS   not-accessible
    STATUS       current
    DESCRIPTION
        "The VC ID or SITE ID of a PW interface."
    ::= { hwL2mcFwdEntry 10 }
 
hwL2mcFwdAddressType OBJECT-TYPE
    SYNTAX       INTEGER
            {
            ip(1),
            mac(2)
            } 
    MAX-ACCESS   read-only
    STATUS       current
    DESCRIPTION
        "The address type of an entry:
                1: IP
                2: MAC
                The default value is 1.
                "
    ::= { hwL2mcFwdEntry 11 }

hwL2mcFwdHostFlag1 OBJECT-TYPE
    SYNTAX       INTEGER
            {
            static(1),
            dynamic(2),
            staticDynamic(3),
            invalid(4)
            } 
    MAX-ACCESS   read-only
    STATUS       current
    DESCRIPTION
        "The mode to create an interface on the host:
                1: static
                2: dynamic
                3: static and dynamic
                4: invalid
                "
    ::= { hwL2mcFwdEntry 18 }
    
hwL2mcFwdHostFlag2 OBJECT-TYPE
    SYNTAX       INTEGER
            {
            nonMapping(1),
            mapping(2)
            }
    MAX-ACCESS   read-only
    STATUS       current
    DESCRIPTION
        "Whether an interface on the host is created through SSM-mapping:
                1: non-mapping
                2: mapping
                "
    ::= { hwL2mcFwdEntry 19 }
    
hwL2mcFwdHostFlag3 OBJECT-TYPE
    SYNTAX       INTEGER
            {
            host(1),
            router(2)
            }
    MAX-ACCESS   read-only
    STATUS       current
    DESCRIPTION
        "The type of an interface created on a router:
                1: Interface connected to the host
                2: Router interface that replicates multicast data flows
                "
    ::= { hwL2mcFwdEntry 20 }
    
hwL2mcFwdHostFlag4 OBJECT-TYPE
    SYNTAX       INTEGER
            {
            port(1),
            static(2),
            both(3)
            }
    MAX-ACCESS   read-only
    STATUS       current
    DESCRIPTION
        "Indicates (S, G) table created :
                1: from port;
                2: from static;
                3: from both
                the default value is 1
                "
    ::= { hwL2mcFwdEntry 21 }    
    
    
--
--  The hwGroupInfo group.
--
hwL2mcGroupInfo     
        OBJECT IDENTIFIER ::= { hwIgspMibObject 5 }

hwL2mcGroupInfoTable OBJECT-TYPE
    SYNTAX       SEQUENCE OF HWL2mcGroupInfoEntry
    MAX-ACCESS   not-accessible
    STATUS       current
    DESCRIPTION
        "Table contains l2 multicast group information
         for IGMP Snooping."
    ::= { hwL2mcGroupInfo 1 }
    
hwL2mcGroupInfoEntry OBJECT-TYPE
    SYNTAX       HWL2mcGroupInfoEntry
    MAX-ACCESS   not-accessible
    STATUS       current
    DESCRIPTION
        "An entry is created for each active VLAN or VSI in the device create a forwarding table entry and delete when 
        a forwarding table entry deleted."
    INDEX { hwL2mcGroupVlanIndex, hwL2mcGroupVsiName, hwL2mcGroupGroupAddress, hwL2mcGroupSourceAddress, hwL2mcPortType,
            hwL2mcGroupPortIfIndex, hwL2mcGroupPortPeId, hwL2mcGroupPortCeId, 
            hwL2mcGroupPeerAddress, hwL2mcGroupVcOrSiteId }
    ::= { hwL2mcGroupInfoTable 1 } 
     
HWL2mcGroupInfoEntry ::= SEQUENCE { 
    hwL2mcGroupVlanIndex      VlanIdOrAny,
    hwL2mcGroupVsiName        DisplayString,
    hwL2mcGroupGroupAddress   IpAddress,  
    hwL2mcGroupSourceAddress  IpAddress,
    hwL2mcPortType            HWPortType,
    hwL2mcGroupPortIfIndex    InterfaceIndexOrZero,
    hwL2mcGroupPortPeId       VlanIdOrAny,
    hwL2mcGroupPortCeId       VlanIdOrAny,
    hwL2mcGroupPeerAddress    IpAddress,
    hwL2mcGroupVcOrSiteId     Unsigned32,
    hwL2mcSourceUpTime        Counter32, 
    hwL2mcSourceExpires       Counter32,
    hwL2mcGroupUpTime         Counter32,
    hwL2mcGroupExpires        Counter32,
    hwL2mcGroupFilterFlag     INTEGER,
    hwL2mcGroupHostFlag1      INTEGER,
    hwL2mcGroupHostFlag2      INTEGER,
    hwL2mcGroupRowStatus      RowStatus
    }
    
hwL2mcGroupVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcGroupInfoEntry 1 }

hwL2mcGroupVsiName OBJECT-TYPE
    SYNTAX       DisplayString(SIZE (0..31))
    MAX-ACCESS   not-accessible
    STATUS       current
    DESCRIPTION
        "The name of a VSI. If a VLAN is specified, the value is 32."
    ::= { hwL2mcGroupInfoEntry 2 }

hwL2mcGroupGroupAddress OBJECT-TYPE
    SYNTAX       IpAddress
    MAX-ACCESS   not-accessible
    STATUS       current
    DESCRIPTION
        "The IP address of a multicast group."
    ::= { hwL2mcGroupInfoEntry 3 }

hwL2mcGroupSourceAddress OBJECT-TYPE
    SYNTAX       IpAddress
    MAX-ACCESS   not-accessible
    STATUS       current
    DESCRIPTION
        "The source IP address of a multicast group."
    ::= { hwL2mcGroupInfoEntry 4 }
    
hwL2mcPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcGroupInfoEntry 5 }

hwL2mcGroupPortIfIndex OBJECT-TYPE
    SYNTAX       InterfaceIndexOrZero
    MAX-ACCESS   not-accessible
    STATUS       current
    DESCRIPTION
        "The interface index. The value 0 indicates that the interface index is invalid."
    ::= { hwL2mcGroupInfoEntry 6 }

hwL2mcGroupPortPeId OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcGroupInfoEntry 7 }

hwL2mcGroupPortCeId OBJECT-TYPE
    SYNTAX       VlanIdOrAny
    MAX-ACCESS   not-accessible
    STATUS       current
    DESCRIPTION
        "The CE VID of an interface.
                The value ranges from 1 to 4095.
                The value 0 indicates that the PE VID is invalid.
                "
    ::= { hwL2mcGroupInfoEntry 8 }

hwL2mcGroupPeerAddress OBJECT-TYPE
    SYNTAX       IpAddress
    MAX-ACCESS   not-accessible
    STATUS       current
    DESCRIPTION
        "The peer IP address of a PW interface. The value 0.0.0.0 indicates that the IP address is invalid."
    ::= { hwL2mcGroupInfoEntry 9 }

hwL2mcGroupVcOrSiteId OBJECT-TYPE
    SYNTAX       Unsigned32(1..4294967295) 
    MAX-ACCESS   not-accessible
    STATUS       current
    DESCRIPTION
        "The VC ID or SITE ID of a PW interface."
    ::= { hwL2mcGroupInfoEntry 10 }

hwL2mcSourceUpTime OBJECT-TYPE
    SYNTAX       Counter32
    MAX-ACCESS   read-only
    STATUS       current
    DESCRIPTION
        "How long the source group exists in the forwarding entry."
    ::= { hwL2mcGroupInfoEntry 14 }

hwL2mcSourceExpires OBJECT-TYPE
    SYNTAX       Counter32
    MAX-ACCESS   read-only
    STATUS       current
    DESCRIPTION
        "The timeout period of the source group in the forwarding entry, that is, the aging time of the source group."
    ::= { hwL2mcGroupInfoEntry 15 }
    
hwL2mcGroupUpTime OBJECT-TYPE
    SYNTAX       Counter32
    MAX-ACCESS   read-only
    STATUS       current
    DESCRIPTION
        "How long the group exists in the forwarding entry."
    ::= { hwL2mcGroupInfoEntry 16 }
    
hwL2mcGroupExpires OBJECT-TYPE
    SYNTAX       Counter32
    MAX-ACCESS   read-only
    STATUS       current
    DESCRIPTION
        "When the group expires in the forwarding entry, that is, the aging time of the source group."
    ::= { hwL2mcGroupInfoEntry 17 }
    
hwL2mcGroupFilterFlag OBJECT-TYPE
    SYNTAX       INTEGER
            {
            include(1),
            exclude(2),
            invalid(3)
            }
    MAX-ACCESS   read-only
    STATUS       current
    DESCRIPTION
        "The filtering mode:
                1: include
                2: exclude
                3: invalid 
                "
    ::= { hwL2mcGroupInfoEntry 18 }
    
hwL2mcGroupHostFlag1 OBJECT-TYPE
    SYNTAX       INTEGER
            {
            static(1),
            dynamic(2),
            staticDynamic(3),
            invalid(4)
            } 
    MAX-ACCESS   read-only
    STATUS       current
    DESCRIPTION
        "The mode to create an interface on the host:
                1: static
                2: dynamic
                3: static and dynamic
                4: invalid
                "
    ::= { hwL2mcGroupInfoEntry 19 }
    
hwL2mcGroupHostFlag2 OBJECT-TYPE
    SYNTAX       INTEGER
         {
         nonMapping(1),
         mapping(2)
         }
    MAX-ACCESS   read-only
    STATUS       current
    DESCRIPTION
        "Whether an interface on the host is created through SSM-mapping:
                1: non-mapping
                2: mapping
                "
    ::= { hwL2mcGroupInfoEntry 20 }
    
hwL2mcGroupRowStatus OBJECT-TYPE
    SYNTAX       RowStatus
    MAX-ACCESS   read-only
    STATUS       current
    DESCRIPTION
        "The row status."
    ::= { hwL2mcGroupInfoEntry 100 }
 
    
    
--
--  The hwL2mcGroupCfgInfo group.
--
hwL2mcGroupCfgInfo     
        OBJECT IDENTIFIER ::= { hwIgspMibObject 6 }

hwL2mcGroupCfgTable OBJECT-TYPE
    SYNTAX       SEQUENCE OF HWL2mcGroupCfgEntry
    MAX-ACCESS   not-accessible
    STATUS       current
    DESCRIPTION
        "Table contains l2 multicast static group information
         for IGMP Snooping."
    ::= { hwL2mcGroupCfgInfo 1 }
    
hwL2mcGroupCfgEntry OBJECT-TYPE
    SYNTAX       HWL2mcGroupCfgEntry
    MAX-ACCESS   not-accessible
    STATUS       current
    DESCRIPTION
        "An entry is created for each active VLAN or VSI in the device create a static group entry and delete when 
        a static group entry deleted."
    INDEX { hwGroupCfgPortType, hwGroupCfgPortIfIndex, hwGroupCfgPortPeId, hwGroupCfgPortCeId, 
            hwGroupCfgPeerAddress, hwGroupCfgVcOrSiteId, hwGroupCfgVlanIndex, hwGroupCfgVsiName,
            hwGroupCfgGroupAddress, hwGroupCfgSourceAddress }
    ::= { hwL2mcGroupCfgTable 1 } 
     
HWL2mcGroupCfgEntry ::= SEQUENCE { 
    hwGroupCfgPortType       HWPortType,
    hwGroupCfgPortIfIndex    InterfaceIndexOrZero,
    hwGroupCfgPortPeId       VlanIdOrAny,
    hwGroupCfgPortCeId       VlanIdOrAny,
    hwGroupCfgPeerAddress    IpAddress,
    hwGroupCfgVcOrSiteId     Unsigned32,
    hwGroupCfgVlanIndex      VlanIdOrAny,
    hwGroupCfgVsiName        DisplayString,
    hwGroupCfgGroupAddress   IpAddress,
    hwGroupCfgSourceAddress  IpAddress,     
    hwGroupCfgRowStatus      RowStatus
    }

hwGroupCfgPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcGroupCfgEntry 1 }
    
hwGroupCfgPortIfIndex OBJECT-TYPE
    SYNTAX       InterfaceIndexOrZero
    MAX-ACCESS   not-accessible
    STATUS       current
    DESCRIPTION
        "The interface index. The value 0 indicates that the interface index is invalid."
    ::= { hwL2mcGroupCfgEntry 2 }
    
hwGroupCfgPortPeId OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcGroupCfgEntry 3 }
    
hwGroupCfgPortCeId OBJECT-TYPE
    SYNTAX       VlanIdOrAny
    MAX-ACCESS   not-accessible
    STATUS       current
    DESCRIPTION
        "The CE VID of an interface.
                The value ranges from 1 to 4095.
                The value 0 indicates that the PE VID is invalid.
                "
    ::= { hwL2mcGroupCfgEntry 4 }
    
hwGroupCfgPeerAddress OBJECT-TYPE
    SYNTAX       IpAddress
    MAX-ACCESS   not-accessible
    STATUS       current
    DESCRIPTION
        "The peer IP address of a PW interface. The value 0.0.0.0 indicates that the IP address is invalid."
    ::= { hwL2mcGroupCfgEntry 5 }
    
hwGroupCfgVcOrSiteId OBJECT-TYPE
    SYNTAX       Unsigned32(1..4294967295) 
    MAX-ACCESS   not-accessible
    STATUS       current
    DESCRIPTION
        "The VC ID or SITE ID of a PW interface."
    ::= { hwL2mcGroupCfgEntry 6 }
    
hwGroupCfgVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcGroupCfgEntry 7 }
    
hwGroupCfgVsiName OBJECT-TYPE
    SYNTAX       DisplayString(SIZE (0..31))
    MAX-ACCESS   not-accessible
    STATUS       current
    DESCRIPTION
        "The name of a VSI. If a VLAN is specified, the value is 32."
    ::= { hwL2mcGroupCfgEntry 8 }    
    
hwGroupCfgGroupAddress OBJECT-TYPE
    SYNTAX       IpAddress
    MAX-ACCESS   not-accessible
    STATUS       current
    DESCRIPTION
        "The group address of a multicast group. In the case of MAC forwarding, the group address is the smallest of 32 IP addresses."
    ::= { hwL2mcGroupCfgEntry 9 }  
        
hwGroupCfgSourceAddress OBJECT-TYPE
    SYNTAX       IpAddress
    MAX-ACCESS   not-accessible
    STATUS       current
    DESCRIPTION
        "The source IP address of a multicast group."
    ::= { hwL2mcGroupCfgEntry 10 }

hwGroupCfgRowStatus OBJECT-TYPE
    SYNTAX       RowStatus
    MAX-ACCESS   read-create
    STATUS       current
    DESCRIPTION
        "The row status."
    ::= { hwL2mcGroupCfgEntry 100 }    
    
    
--
--  The hwL2mcSsmSourceInfo group.
--
hwL2mcSsmSourceInfo     
        OBJECT IDENTIFIER ::= { hwIgspMibObject 7 }
        
hwL2mcSsmSourceTable OBJECT-TYPE
    SYNTAX       SEQUENCE OF HWL2mcSsmSourceEntry
    MAX-ACCESS   not-accessible
    STATUS       current
    DESCRIPTION
        "This table contains the configuration of the source address list of SSM-Mapping."
    ::= { hwL2mcSsmSourceInfo 1 }
    
hwL2mcSsmSourceEntry OBJECT-TYPE
    SYNTAX       HWL2mcSsmSourceEntry
    MAX-ACCESS   not-accessible
    STATUS       current
    DESCRIPTION
        "An entry is created for each active VLAN or VSI in the device add an entry for SSM-Mapping."
    INDEX { hwL2mcSsmSourceVlanIndex, hwL2mcSsmSourceVsiName, 
            hwL2mcSsmGroupAddress, hwL2mcSsmGroupLen, hwL2mcSsmSourceAddress
            }
    ::= { hwL2mcSsmSourceTable 1 } 
     
HWL2mcSsmSourceEntry ::= SEQUENCE { 
    hwL2mcSsmSourceVlanIndex      VlanIdOrAny,
    hwL2mcSsmSourceVsiName        DisplayString,
    hwL2mcSsmGroupAddress        IpAddress,
    hwL2mcSsmGroupLen            Integer32,
    hwL2mcSsmSourceAddress        IpAddress,
    hwL2mcSsmSourceRowStatus      RowStatus
    }

hwL2mcSsmSourceVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcSsmSourceEntry 1 }
    
hwL2mcSsmSourceVsiName OBJECT-TYPE
    SYNTAX       DisplayString(SIZE (0..31))
    MAX-ACCESS   not-accessible
    STATUS       current
    DESCRIPTION
        "The name of a VSI. If a VLAN is specified, the value is 32."
    ::= { hwL2mcSsmSourceEntry 2 }

hwL2mcSsmGroupAddress OBJECT-TYPE
    SYNTAX       IpAddress
    MAX-ACCESS   not-accessible
    STATUS       current
    DESCRIPTION
        "The IP address of a multicast group. "
    ::= { hwL2mcSsmSourceEntry 3 }
    
hwL2mcSsmGroupLen OBJECT-TYPE
    SYNTAX       Integer32(4..32) 
    MAX-ACCESS   not-accessible
    STATUS       current
    DESCRIPTION
        "The mask length of a multicast group."
    ::= { hwL2mcSsmSourceEntry 4 }
    
hwL2mcSsmSourceAddress OBJECT-TYPE
    SYNTAX       IpAddress
    MAX-ACCESS   not-accessible
    STATUS       current
    DESCRIPTION
        "The source address of SSM-Mapping, which serves as an index of this table."
    ::= { hwL2mcSsmSourceEntry 5 }
    
hwL2mcSsmSourceRowStatus OBJECT-TYPE
    SYNTAX       RowStatus
    MAX-ACCESS   read-create
    STATUS       current
    DESCRIPTION
        "The row status."
    ::= { hwL2mcSsmSourceEntry 100 }   
    
    
--
--  The hwL2mcPortGroupPolicyCfgInfo group.
--
hwL2mcPortGroupPolicyCfgInfo     
        OBJECT IDENTIFIER ::= { hwIgspMibObject 8 }

hwL2mcPortGroupPolicyCfgTable OBJECT-TYPE
    SYNTAX       SEQUENCE OF HWL2mcPortGroupPolicyCfgEntry
    MAX-ACCESS   not-accessible
    STATUS       current
    DESCRIPTION
        "In this table, you can query or configure a group policy to filter entries on a port."
    ::= { hwL2mcPortGroupPolicyCfgInfo 1 }
    
hwL2mcPortGroupPolicyCfgEntry OBJECT-TYPE
    SYNTAX       HWL2mcPortGroupPolicyCfgEntry
    MAX-ACCESS   not-accessible
    STATUS       current
    DESCRIPTION
        "An entry is created for each active VLAN or VSI in the device when a group policy added."
    INDEX {  hwPortGroupPolicyPortType, hwPortGroupPolicyPortIfIndex, hwPortGroupPolicyPortPeId, hwPortGroupPolicyPortCeId,
            hwPortGroupPolicyPeerAddress, hwPortGroupPolicyVcOrSiteId,hwPortGroupPolicyVlanIndex, hwPortGroupPolicyVsiName
            }
    ::= { hwL2mcPortGroupPolicyCfgTable 1 } 
     
HWL2mcPortGroupPolicyCfgEntry ::= SEQUENCE { 
    hwPortGroupPolicyPortType       HWPortType,
    hwPortGroupPolicyPortIfIndex    InterfaceIndexOrZero,
    hwPortGroupPolicyPortPeId       VlanIdOrAny,
    hwPortGroupPolicyPortCeId       VlanIdOrAny,
    hwPortGroupPolicyPeerAddress    IpAddress,
    hwPortGroupPolicyVcOrSiteId     Unsigned32, 
    hwPortGroupPolicyVlanIndex      VlanIdOrAny,
    hwPortGroupPolicyVsiName        DisplayString,
    hwPortGroupPolicyAclNum         Integer32, 
    hwPortGroupPolicyIgmpVersion    INTEGER, 
    hwPortGroupPolicyRowStatus      RowStatus
    }
    
    
hwPortGroupPolicyPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                9: batch config qinq port ce VLAN ID
                10: batch config dot1q termination port ce VLAN ID
                "
    ::= { hwL2mcPortGroupPolicyCfgEntry 1 }
    
hwPortGroupPolicyPortIfIndex OBJECT-TYPE
    SYNTAX       InterfaceIndexOrZero
    MAX-ACCESS   not-accessible
    STATUS       current
    DESCRIPTION
        "The interface index. The value 0 indicates that the interface index is invalid."
    ::= { hwL2mcPortGroupPolicyCfgEntry 2 }
    
hwPortGroupPolicyPortPeId OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcPortGroupPolicyCfgEntry 3 }
    
hwPortGroupPolicyPortCeId OBJECT-TYPE
    SYNTAX       VlanIdOrAny
    MAX-ACCESS   not-accessible
    STATUS       current
    DESCRIPTION
        "The CE VID of an interface.
                The value ranges from 1 to 4095.
                The value 4095 indicates that the PE VID is invalid.
                "
    ::= { hwL2mcPortGroupPolicyCfgEntry 4 }
    
hwPortGroupPolicyPeerAddress OBJECT-TYPE
    SYNTAX       IpAddress
    MAX-ACCESS   not-accessible
    STATUS       current
    DESCRIPTION
        "The peer IP address of a PW interface. The value 0.0.0.0 indicates that the IP address is invalid."
    ::= { hwL2mcPortGroupPolicyCfgEntry 5 }
    
hwPortGroupPolicyVcOrSiteId OBJECT-TYPE
    SYNTAX       Unsigned32(1..4294967295) 
    MAX-ACCESS   not-accessible
    STATUS       current
    DESCRIPTION
        "The VC ID or SITE ID of a PW interface."
    ::= { hwL2mcPortGroupPolicyCfgEntry 6 }
    
hwPortGroupPolicyVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcPortGroupPolicyCfgEntry 7 }
    
hwPortGroupPolicyVsiName OBJECT-TYPE
    SYNTAX       DisplayString(SIZE (0..31))
    MAX-ACCESS   not-accessible
    STATUS       current
    DESCRIPTION
        "The name of a VSI. If a VLAN is specified, the value is 32."
    ::= { hwL2mcPortGroupPolicyCfgEntry 8 }    
    
hwPortGroupPolicyAclNum OBJECT-TYPE
    SYNTAX       Integer32(0|2000..3999)
    MAX-ACCESS   read-create
    STATUS       current
    DESCRIPTION
        "The number of a basic ACL.
                The ACL number ranges from 2000 to 3999.
                The default value is 0, indicating that the value is invalid.
                "
    ::= { hwL2mcPortGroupPolicyCfgEntry 9 }
    
hwPortGroupPolicyIgmpVersion OBJECT-TYPE
    SYNTAX       INTEGER
            {
            version1(1),
            version2(2),
            version3(3),
            versionAll(4)
            }
    MAX-ACCESS   read-create
    STATUS       current
    DESCRIPTION
        "The IGMP version.
                The value ranges from 1 to 4.
                The default is 4, indicating that no version is specified.
                "
    ::= { hwL2mcPortGroupPolicyCfgEntry 10 }
    
hwPortGroupPolicyRowStatus OBJECT-TYPE
    SYNTAX       RowStatus
    MAX-ACCESS   read-create
    STATUS       current
    DESCRIPTION
        "The row status."
    ::= { hwL2mcPortGroupPolicyCfgEntry 100 }  
    
    
--
--  The hwL2mcChnlCfgInfo group.
--
hwL2mcChnlCfgInfo     
        OBJECT IDENTIFIER ::= { hwIgspMibObject 9 }

hwL2mcChnlCfgTable OBJECT-TYPE
    SYNTAX       SEQUENCE OF HWL2mcChnlCfgEntry
    MAX-ACCESS   not-accessible
    STATUS       current
    DESCRIPTION
        "This table describes the configurations of a channel."
    ::= { hwL2mcChnlCfgInfo 1 }
    
hwL2mcChnlCfgEntry OBJECT-TYPE
    SYNTAX       HWL2mcChnlCfgEntry
    MAX-ACCESS   not-accessible
    STATUS       current
    DESCRIPTION
        "An entry of channel is created for each VLAN or VSI in the device create an channel."
    INDEX { hwChnlCfgVlanIndex, hwChnlCfgVsiName, hwChnlCfgChnlName
          }
    ::= { hwL2mcChnlCfgTable 1 } 
     
HWL2mcChnlCfgEntry ::= SEQUENCE { 
    hwChnlCfgVlanIndex      VlanIdOrAny,
    hwChnlCfgVsiName        DisplayString,
    hwChnlCfgChnlName       DisplayString,
    hwChnlCfgChnlType       INTEGER, 
    hwChnlCfgRowStatus      RowStatus
    }
    
hwChnlCfgVlanIndex OBJECT-TYPE
    SYNTAX       VlanIdOrAny
    MAX-ACCESS   not-accessible
    STATUS       current
    DESCRIPTION
        "The VLAN ID, which is the configuration index in a VLAN. 
        If a VSI is specified, the value is 4095. If both hwChnlCfgVlanIndex and hwChnlCfgVSIName are invalid, the configuration is global.
                The value ranges from 1 to 4095.
                "
    ::= { hwL2mcChnlCfgEntry 1 }
    
hwChnlCfgVsiName OBJECT-TYPE
    SYNTAX       DisplayString(SIZE (0..31))
    MAX-ACCESS   not-accessible
    STATUS       current
    DESCRIPTION
        "The name of a VSI. 
        If a VLAN is specified, the value is 32. If both hwChnlCfgVlanIndex and hwChnlCfgVSIName are invalid, the configuration is global."
    ::= { hwL2mcChnlCfgEntry 2 }
    
hwChnlCfgChnlName OBJECT-TYPE
    SYNTAX       DisplayString(SIZE (0..31))
    MAX-ACCESS   not-accessible
    STATUS       current
    DESCRIPTION
        "The channel name."
    ::= { hwL2mcChnlCfgEntry 3 }
  
hwChnlCfgChnlType OBJECT-TYPE
    SYNTAX       INTEGER
            {
            ssm(1),
            asm(2)
            }
    MAX-ACCESS   read-create
    STATUS       current
    DESCRIPTION
        "The channel type:
                1: SSM
                2: ASM
                "
    ::= { hwL2mcChnlCfgEntry 9 }
    

    
hwChnlCfgRowStatus OBJECT-TYPE
    SYNTAX       RowStatus
    MAX-ACCESS   read-create
    STATUS       current
    DESCRIPTION
        "The row status."
    ::= { hwL2mcChnlCfgEntry 100 } 
    
    
--
--  The hwL2mcLimitInfo group.
--
hwL2mcLimitInfo     
        OBJECT IDENTIFIER ::= { hwIgspMibObject 10 }

hwL2mcLimitTable OBJECT-TYPE
    SYNTAX       SEQUENCE OF HWL2mcLimitEntry
    MAX-ACCESS   not-accessible
    STATUS       current
    DESCRIPTION
        "This table describes the configurations of IGMP snooping CAC in a VLAN or a VSI."
    ::= { hwL2mcLimitInfo 1 }
    
hwL2mcLimitEntry OBJECT-TYPE
    SYNTAX       HWL2mcLimitEntry
    MAX-ACCESS   not-accessible
    STATUS       current
    DESCRIPTION
        "An entry is created for each IGMP snooping CAC in a VLAN or a VSI."
    INDEX { hwL2mcLimitVlanIndex, hwL2mcLimitVsiName, hwL2mcLimitChnlName }
    ::= { hwL2mcLimitTable 1 } 
     
HWL2mcLimitEntry ::= SEQUENCE { 
    hwL2mcLimitVlanIndex      VlanIdOrAny,
    hwL2mcLimitVsiName        DisplayString,
    hwL2mcLimitChnlName       DisplayString,
    hwL2mcLimitMaxEntry       Integer32,
    hwL2mcLimitEntryCnt       Counter32,
    hwL2mcLimitMaxBandWidth   Integer32,
    hwL2mcLimitBandWidth      Counter32,
    hwL2mcLimitAcl            Integer32, 
    hwL2mcLimitCfgRowStatus   RowStatus
    }
    
hwL2mcLimitVlanIndex OBJECT-TYPE
    SYNTAX       VlanIdOrAny
    MAX-ACCESS   not-accessible
    STATUS       current
    DESCRIPTION
        "The VLAN ID, which is the configuration index in a VLAN. 
        If a VSI is specified, the value is 4095. If both hwVlanLimitVlanIndex and hwVlanLimitVSIName are invalid, the configuration is global.
                The value ranges from 1 to 4095.
                "
    ::= { hwL2mcLimitEntry 1 }
    
hwL2mcLimitVsiName OBJECT-TYPE
    SYNTAX       DisplayString(SIZE (0..31))
    MAX-ACCESS   not-accessible
    STATUS       current
    DESCRIPTION
        "The name of a VSI. If a VLAN is specified, the value is 32. 
        If both hwVlanLimitVlanIndex and hwVlanLimitVSIName are invalid, the configuration is global."
    ::= { hwL2mcLimitEntry 2 }
    
hwL2mcLimitChnlName OBJECT-TYPE
    SYNTAX       DisplayString(SIZE (0..31))
    MAX-ACCESS   not-accessible
    STATUS       current
    DESCRIPTION
        "The channel name."
    ::= { hwL2mcLimitEntry 3 }
    
hwL2mcLimitMaxEntry OBJECT-TYPE
    SYNTAX       Integer32(0..16384)
    MAX-ACCESS   read-create
    STATUS       current
    DESCRIPTION
        "The maximum number of forwarding entries. The value 0 indicates that the number is invalid."
    ::= { hwL2mcLimitEntry 4 }
    
hwL2mcLimitEntryCnt OBJECT-TYPE
    SYNTAX       Counter32 
    MAX-ACCESS   read-only
    STATUS       current
    DESCRIPTION
        "The number of current forwarding entries."
    ::= { hwL2mcLimitEntry 5 }
    
hwL2mcLimitMaxBandWidth OBJECT-TYPE
    SYNTAX       Integer32(0..4194304)
    MAX-ACCESS   read-create
    STATUS       current
    DESCRIPTION
        "The maximum bandwidth. The value 0 indicates that the bandwidth is invalid."
    ::= { hwL2mcLimitEntry 6 }
    
hwL2mcLimitBandWidth OBJECT-TYPE
    SYNTAX       Counter32 
    MAX-ACCESS   read-only
    STATUS       current
    DESCRIPTION
        "The current bandwidth."
    ::= { hwL2mcLimitEntry 7 }
    
hwL2mcLimitAcl OBJECT-TYPE
    SYNTAX       Integer32(0|2000..3999)
    MAX-ACCESS   read-create
    STATUS       current
    DESCRIPTION
        "The number of ACL for the multicast groups that do not need to be configured with CAC limit.
                The ACL number ranges from 2000 to 3999.
                The default value is 0, indicating that the number is invalid.
                "
    ::= { hwL2mcLimitEntry 8 }
    
hwL2mcLimitCfgRowStatus OBJECT-TYPE
    SYNTAX       RowStatus
    MAX-ACCESS   read-create
    STATUS       current
    DESCRIPTION
        "The row status."
    ::= { hwL2mcLimitEntry 100 }   
    
    
--
--  The hwL2mcPortLimitInfo group.
--
hwL2mcPortLimitInfo     
        OBJECT IDENTIFIER ::= { hwIgspMibObject 11 }

hwL2mcPortLimitTable OBJECT-TYPE
    SYNTAX       SEQUENCE OF HWL2mcPortLimitEntry
    MAX-ACCESS   not-accessible
    STATUS       current
    DESCRIPTION
        "This table describes the configurations of IGMP snooping CAC on an interface."
    ::= { hwL2mcPortLimitInfo 1 }
    
hwL2mcPortLimitEntry OBJECT-TYPE
    SYNTAX       HWL2mcPortLimitEntry
    MAX-ACCESS   not-accessible
    STATUS       current
    DESCRIPTION
        "An entry is created for each IGMP snooping CAC on an interface."
    INDEX { hwPortLimitVlanIndex, hwPortLimitVsiName, hwPortLimitPortType,
            hwPortLimitIfIndex, hwPortLimitPeId, hwPortLimitCeId, 
            hwPortLimitPeerAddress, hwPortLimitVcOrSiteId, hwPortLimitChnlName }
    ::= { hwL2mcPortLimitTable 1 } 
     
HWL2mcPortLimitEntry ::= SEQUENCE { 
    hwPortLimitVlanIndex      VlanIdOrAny,
    hwPortLimitVsiName        DisplayString,
    hwPortLimitPortType       HWPortType,
    hwPortLimitIfIndex        InterfaceIndexOrZero,
    hwPortLimitPeId           VlanIdOrAny,
    hwPortLimitCeId           VlanIdOrAny,
    hwPortLimitPeerAddress    IpAddress,
    hwPortLimitVcOrSiteId     Unsigned32, 
    hwPortLimitChnlName       DisplayString,
    hwPortLimitAcl            Integer32, 
    hwPortLimitMaxEntry       Integer32, 
    hwPortLimitEntryCnt       Counter32, 
    hwPortLimitMaxBandWidth   Integer32, 
    hwPortLimitBandWidth      Counter32, 
    hwPortLimitCfgRowStatus   RowStatus
    }
    
    
hwPortLimitVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcPortLimitEntry 1 }
    
hwPortLimitVsiName OBJECT-TYPE
    SYNTAX       DisplayString(SIZE (0..31))
    MAX-ACCESS   not-accessible
    STATUS       current
    DESCRIPTION
        "The name of a VSI. If a VLAN is specified, the value is 32."
    ::= { hwL2mcPortLimitEntry 2 }
    
hwPortLimitPortType OBJECT-TYPE
    SYNTAX       HWPortType
    MAX-ACCESS   not-accessible
    STATUS       current
    DESCRIPTION
        "The interface type:
                1: Invalid
                2: PW interface
                3: L2 interface
                4: Encapsulation sub-interface
                5: Termination sub-interface
                9: batch config qinq port ce VLAN ID
                10: batch config dot1q termination port ce VLAN ID
                "
    ::= { hwL2mcPortLimitEntry 3 }
    
hwPortLimitIfIndex OBJECT-TYPE
    SYNTAX       InterfaceIndexOrZero
    MAX-ACCESS   not-accessible
    STATUS       current
    DESCRIPTION
        "The interface index. The value 0 indicates that the interface index is invalid."
    ::= { hwL2mcPortLimitEntry 4 }
    
hwPortLimitPeId OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcPortLimitEntry 5 }
    
hwPortLimitCeId OBJECT-TYPE
    SYNTAX       VlanIdOrAny
    MAX-ACCESS   not-accessible
    STATUS       current
    DESCRIPTION
        "The CE VID of an interface.
                The value ranges from 1 to 4095.
                The value 4095 indicates that the PE VID is invalid.
                "
    ::= { hwL2mcPortLimitEntry 6 }
    
hwPortLimitPeerAddress OBJECT-TYPE
    SYNTAX       IpAddress
    MAX-ACCESS   not-accessible
    STATUS       current
    DESCRIPTION
        "The peer IP address of a PW interface. The value 0.0.0.0 indicates that the IP address is invalid."
    ::= { hwL2mcPortLimitEntry 7 }
    
hwPortLimitVcOrSiteId OBJECT-TYPE
    SYNTAX       Unsigned32(1..4294967295) 
    MAX-ACCESS   not-accessible
    STATUS       current
    DESCRIPTION
        "The VC ID or SITE ID of a PW interface."
    ::= { hwL2mcPortLimitEntry 8 }
    
hwPortLimitChnlName OBJECT-TYPE
    SYNTAX       DisplayString(SIZE (0..31))
    MAX-ACCESS   not-accessible
    STATUS       current
    DESCRIPTION
        "The channel name."
    ::= { hwL2mcPortLimitEntry 9 }
    
hwPortLimitAcl OBJECT-TYPE
    SYNTAX       Integer32(0|2000..3999)
    MAX-ACCESS   read-create
    STATUS       current
    DESCRIPTION
        "The number of ACL for the multicast groups that do not need to be configured with CAC limit.
                The ACL number ranges from 2000 to 3999.
                The default value is 0, indicating that the number is invalid.
                "
    ::= { hwL2mcPortLimitEntry 10 }
    
hwPortLimitMaxEntry OBJECT-TYPE
    SYNTAX       Integer32(0..16384) 
    MAX-ACCESS   read-create
    STATUS       current
    DESCRIPTION
        "The maximum number of forwarding entries. The value 0 indicates that the number is invalid."
    ::= { hwL2mcPortLimitEntry 11 }
    
hwPortLimitEntryCnt OBJECT-TYPE
    SYNTAX       Counter32 
    MAX-ACCESS   read-only
    STATUS       current
    DESCRIPTION
        "The number of current forwarding entries."
    ::= { hwL2mcPortLimitEntry 12 }
    
hwPortLimitMaxBandWidth OBJECT-TYPE
    SYNTAX       Integer32(0..4194304)
    MAX-ACCESS   read-create
    STATUS       current
    DESCRIPTION
        "The maximum bandwidth. The value 0 indicates that the bandwidth is invalid."
    ::= { hwL2mcPortLimitEntry 13 }
    
hwPortLimitBandWidth OBJECT-TYPE
    SYNTAX       Counter32 
    MAX-ACCESS   read-only
    STATUS       current
    DESCRIPTION
        "The current bandwidth."
    ::= { hwL2mcPortLimitEntry 14 }
    
hwPortLimitCfgRowStatus OBJECT-TYPE
    SYNTAX       RowStatus
    MAX-ACCESS   read-create
    STATUS       current
    DESCRIPTION
        "The row status."
    ::= { hwL2mcPortLimitEntry 100 } 
    


--
--  The hwL2mcFastChnlCfgInfo group.
--
hwL2mcFastChnlCfgInfo     
        OBJECT IDENTIFIER ::= { hwIgspMibObject 12 }

hwL2mcFastChnlCfgTable OBJECT-TYPE
    SYNTAX       SEQUENCE OF HWL2mcFastChnlCfgEntry
    MAX-ACCESS   not-accessible
    STATUS       current
    DESCRIPTION
        "Table contains l2 multicast fast forward information for IGMP Snooping."
    ::= { hwL2mcFastChnlCfgInfo 1 }
    
hwL2mcFastChnlCfgEntry OBJECT-TYPE
    SYNTAX       HWL2mcFastChnlCfgEntry
    MAX-ACCESS   not-accessible
    STATUS       current
    DESCRIPTION
        "An entry is created for each IGMP snooping fast channel."
    INDEX { hwL2mcFastChnlCfgVlanIndex, hwL2mcFastChnlCfgVsiName, 
            hwL2mcFastChnlCfgGroupAddress, hwL2mcFastChnlCfgGroupLen,
            hwL2mcFastChnlCfgSourceAddress, hwL2mcFastChnlCfgSourceLen
             }
    ::= { hwL2mcFastChnlCfgTable 1 } 
     
HWL2mcFastChnlCfgEntry ::= SEQUENCE { 
    hwL2mcFastChnlCfgVlanIndex           VlanIdOrAny,
    hwL2mcFastChnlCfgVsiName            DisplayString,
    hwL2mcFastChnlCfgGroupAddress       IpAddress,  
    hwL2mcFastChnlCfgGroupLen           Integer32,
    hwL2mcFastChnlCfgSourceAddress      IpAddress ,
    hwL2mcFastChnlCfgSourceLen          Integer32 ,
    hwL2mcFastChnlCfgRowStatus           RowStatus
    }
    
hwL2mcFastChnlCfgVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcFastChnlCfgEntry 1 }
    
hwL2mcFastChnlCfgVsiName OBJECT-TYPE
    SYNTAX       DisplayString(SIZE (0..31))
    MAX-ACCESS   not-accessible
    STATUS       current
    DESCRIPTION
        "The name of a VSI. If a VLAN is specified, the value is 32."
    ::= { hwL2mcFastChnlCfgEntry 2 }
    
hwL2mcFastChnlCfgGroupAddress OBJECT-TYPE
    SYNTAX       IpAddress
    MAX-ACCESS   not-accessible
    STATUS       current
    DESCRIPTION
        "The group address of a multicast group. In the case of MAC forwarding, the group address is the smallest of 32 IP addresses."
    ::= { hwL2mcFastChnlCfgEntry 3 }
    
hwL2mcFastChnlCfgGroupLen OBJECT-TYPE
    SYNTAX       Integer32(16..32) 
    MAX-ACCESS   not-accessible
    STATUS       current
    DESCRIPTION
        "The mask length of a multicast group address."
    ::= { hwL2mcFastChnlCfgEntry 4 }
    
hwL2mcFastChnlCfgSourceAddress OBJECT-TYPE
    SYNTAX       IpAddress
    MAX-ACCESS   not-accessible
    STATUS       current
    DESCRIPTION
        "The source IP address of a multicast group."
    ::= { hwL2mcFastChnlCfgEntry 5 }
    
hwL2mcFastChnlCfgSourceLen OBJECT-TYPE
    SYNTAX       Integer32(0|16..32) 
    MAX-ACCESS   not-accessible
    STATUS       current
    DESCRIPTION
        "The mask length of a multicast source address."
    ::= { hwL2mcFastChnlCfgEntry 6 }    
    
hwL2mcFastChnlCfgRowStatus OBJECT-TYPE
    SYNTAX       RowStatus
    MAX-ACCESS   read-create
    STATUS       current
    DESCRIPTION
        "The row status."
    ::= { hwL2mcFastChnlCfgEntry 100 }
    
    
--
--  The hwL2mcRouterPortInfo group.
--
hwL2mcRouterPortInfo    
        OBJECT IDENTIFIER ::= { hwIgspMibObject 13 }

hwL2mcRouterPortInfoTable OBJECT-TYPE
    SYNTAX       SEQUENCE OF HWL2mcRouterPortInfoEntry
    MAX-ACCESS   not-accessible
    STATUS       current
    DESCRIPTION
        "Table contains l2 multicast router port information for IGMP Snooping."
    ::= { hwL2mcRouterPortInfo 1 }
    
hwL2mcRouterPortInfoEntry OBJECT-TYPE
    SYNTAX       HWL2mcRouterPortInfoEntry
    MAX-ACCESS   not-accessible
    STATUS       current
    DESCRIPTION
        "An entry is created for each IGMP snooping router port on an interface."
    INDEX { hwL2mcRouterPortVlanIndex, hwL2mcRouterPortVsiName, hwL2mcRouterPortType, hwL2mcRouterPortIfIndex,
     hwL2mcRouterPortPeId, hwL2mcRouterPortCeId, hwL2mcRouterPortPeerAddress, hwL2mcRouterPortVcOrSiteId }
    ::= { hwL2mcRouterPortInfoTable 1 } 
     
HWL2mcRouterPortInfoEntry ::= SEQUENCE { 
    hwL2mcRouterPortVlanIndex       VlanIdOrAny,
    hwL2mcRouterPortVsiName         DisplayString,
    hwL2mcRouterPortType            HWPortType ,
    hwL2mcRouterPortIfIndex         InterfaceIndexOrZero ,
    hwL2mcRouterPortPeId            VlanIdOrAny,  
    hwL2mcRouterPortCeId            VlanIdOrAny,
    hwL2mcRouterPortPeerAddress     IpAddress,
    hwL2mcRouterPortVcOrSiteId      Unsigned32,
    hwL2mcRouterPortGroupUpTime     Counter32,
    hwL2mcRouterPortGroupExpires    Counter32,
    hwL2mcRouterPortGroupHostFlag1  INTEGER    
    }
    
hwL2mcRouterPortVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcRouterPortInfoEntry 1 }
    
hwL2mcRouterPortVsiName OBJECT-TYPE
    SYNTAX       DisplayString(SIZE (0..31))
    MAX-ACCESS   not-accessible
    STATUS       current
    DESCRIPTION
        "The name of a VSI. If a VLAN is specified, the value is 32."
    ::= { hwL2mcRouterPortInfoEntry 2 }
    
hwL2mcRouterPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcRouterPortInfoEntry 3 }
    
hwL2mcRouterPortIfIndex  OBJECT-TYPE
    SYNTAX       InterfaceIndexOrZero
    MAX-ACCESS   not-accessible
    STATUS       current
    DESCRIPTION
        "The interface index. The value 0 indicates that the interface index is invalid."
    ::= { hwL2mcRouterPortInfoEntry 4 }  
    
hwL2mcRouterPortPeId  OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcRouterPortInfoEntry 5 }   
    
hwL2mcRouterPortCeId  OBJECT-TYPE
    SYNTAX       VlanIdOrAny
    MAX-ACCESS   not-accessible
    STATUS       current
    DESCRIPTION
        "The CE VID of an interface.
                The value ranges from 1 to 4095.
                The value 4095 indicates that the PE VID is invalid.
                "
    ::= { hwL2mcRouterPortInfoEntry 6 }
    
hwL2mcRouterPortPeerAddress  OBJECT-TYPE
    SYNTAX       IpAddress
    MAX-ACCESS   not-accessible
    STATUS       current
    DESCRIPTION
        "The peer IP address of a PW interface. The value 0.0.0.0 indicates that the IP address is invalid."
    ::= { hwL2mcRouterPortInfoEntry 7 }   
    
hwL2mcRouterPortVcOrSiteId   OBJECT-TYPE
    SYNTAX       Unsigned32(1..4294967295) 
    MAX-ACCESS   not-accessible
    STATUS       current
    DESCRIPTION
        "The VC ID or SITE ID of a PW interface."
    ::= { hwL2mcRouterPortInfoEntry 8 }  
    
hwL2mcRouterPortGroupUpTime OBJECT-TYPE
    SYNTAX       Counter32
    MAX-ACCESS   read-only
    STATUS       current
    DESCRIPTION
        "How long the group exists in the forwarding entry."
    ::= { hwL2mcRouterPortInfoEntry 16 }  

hwL2mcRouterPortGroupExpires  OBJECT-TYPE
    SYNTAX       Counter32
    MAX-ACCESS   read-only
    STATUS       current
    DESCRIPTION
        "The timeout period of the router port, that is, the aging time of the router port."
    ::= { hwL2mcRouterPortInfoEntry 17 }   
    
hwL2mcRouterPortGroupHostFlag1  OBJECT-TYPE
    SYNTAX       INTEGER
            {
            static(1),
            dynamic(2),
            staticDynamic(3)
            }
    MAX-ACCESS   read-only
    STATUS       current
    DESCRIPTION
        "The mode to create an interface on the host:
                1: static
                2: dynamic
                3: static and dynamic
                "    
    ::= { hwL2mcRouterPortInfoEntry 19 }                
   


--  
--
--  The hwL2mcRouterPortCfgInfo group.
--
hwL2mcRouterPortCfgInfo    
        OBJECT IDENTIFIER ::= { hwIgspMibObject 14 }

hwL2mcRouterPortCfgTable OBJECT-TYPE
    SYNTAX       SEQUENCE OF HWL2mcRouterPortCfgEntry
    MAX-ACCESS   not-accessible
    STATUS       current
    DESCRIPTION
        "Table contains l2 multicast configuration of router port for IGMP Snooping."
    ::= { hwL2mcRouterPortCfgInfo 1 }
    
hwL2mcRouterPortCfgEntry OBJECT-TYPE
    SYNTAX       HWL2mcRouterPortCfgEntry
    MAX-ACCESS   not-accessible
    STATUS       current
    DESCRIPTION
        "An entry is created for each IGMP snooping static router port on an interface."
    INDEX { hwL2mcRouterPortCfgPortType, hwL2mcRouterPortCfgPortIfIndex, hwL2mcRouterPortCfgPortPeId , hwL2mcRouterPortCfgPortCeId ,
     hwL2mcRouterPortCfgPeerAddress , hwL2mcRouterPortCfgVcOrSiteId, hwL2mcRouterPortCfgVlanIndex, hwL2mcRouterPortCfgVsiName }
    ::= { hwL2mcRouterPortCfgTable 1 } 
     
HWL2mcRouterPortCfgEntry ::= SEQUENCE { 
    hwL2mcRouterPortCfgPortType     HWPortType ,
    hwL2mcRouterPortCfgPortIfIndex  InterfaceIndexOrZero ,
    hwL2mcRouterPortCfgPortPeId     VlanIdOrAny,  
    hwL2mcRouterPortCfgPortCeId     VlanIdOrAny,
    hwL2mcRouterPortCfgPeerAddress  IpAddress,
    hwL2mcRouterPortCfgVcOrSiteId   Unsigned32,
    hwL2mcRouterPortCfgVlanIndex    VlanIdOrAny,
    hwL2mcRouterPortCfgVsiName      DisplayString,
    hwL2mcRouterPortCfgRowStatus    RowStatus
    }
    
hwL2mcRouterPortCfgPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcRouterPortCfgEntry 1 }
    
hwL2mcRouterPortCfgPortIfIndex  OBJECT-TYPE
    SYNTAX       InterfaceIndexOrZero
    MAX-ACCESS   not-accessible
    STATUS       current
    DESCRIPTION
        "The interface index. The value 0 indicates that the interface index is invalid."
    ::= { hwL2mcRouterPortCfgEntry 2 }  
    
hwL2mcRouterPortCfgPortPeId  OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcRouterPortCfgEntry 3 }   
    
hwL2mcRouterPortCfgPortCeId  OBJECT-TYPE
    SYNTAX       VlanIdOrAny
    MAX-ACCESS   not-accessible
    STATUS       current
    DESCRIPTION
        "The CE VID of an interface.
                The value ranges from 1 to 4095.
                The value 4095 indicates that the PE VID is invalid.
                "
    ::= { hwL2mcRouterPortCfgEntry 4 }
    
hwL2mcRouterPortCfgPeerAddress  OBJECT-TYPE
    SYNTAX       IpAddress
    MAX-ACCESS   not-accessible
    STATUS       current
    DESCRIPTION
        "The peer IP address of a PW interface. The value 0.0.0.0 indicates that the IP address is invalid."
    ::= { hwL2mcRouterPortCfgEntry 5 }   
    
hwL2mcRouterPortCfgVcOrSiteId   OBJECT-TYPE
    SYNTAX       Unsigned32(1..4294967295) 
    MAX-ACCESS   not-accessible
    STATUS       current
    DESCRIPTION
        "The VC ID or SITE ID of a PW interface."
    ::= { hwL2mcRouterPortCfgEntry 6 }  

hwL2mcRouterPortCfgVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcRouterPortCfgEntry 7 }
    
hwL2mcRouterPortCfgVsiName OBJECT-TYPE
    SYNTAX       DisplayString(SIZE (0..31))
    MAX-ACCESS   not-accessible
    STATUS       current
    DESCRIPTION
        "The name of a VSI. If a VLAN is specified, the value is 32."
    ::= { hwL2mcRouterPortCfgEntry 8 }    
    
hwL2mcRouterPortCfgRowStatus   OBJECT-TYPE
    SYNTAX       RowStatus
    MAX-ACCESS   read-create
    STATUS       current
    DESCRIPTION
        "The row status."
    ::= { hwL2mcRouterPortCfgEntry 100 }    


--
--  The hwL2mcChnlGroupCfgInfo group.
--
hwL2mcChnlGroupCfgInfo     
        OBJECT IDENTIFIER ::= { hwIgspMibObject 15 }

hwL2mcChnlGroupCfgTable OBJECT-TYPE
    SYNTAX       SEQUENCE OF HWL2mcChnlGroupCfgEntry
    MAX-ACCESS   not-accessible
    STATUS       current
    DESCRIPTION
        "This table describes the group configurations of a channel."
    ::= { hwL2mcChnlGroupCfgInfo 1 }
    
hwL2mcChnlGroupCfgEntry OBJECT-TYPE
    SYNTAX       HWL2mcChnlGroupCfgEntry
    MAX-ACCESS   not-accessible
    STATUS       current
    DESCRIPTION
        "An entry of channel is created for each VLAN or VSI in the device create an channel."
    INDEX { hwChnlGroupCfgVlanIndex , hwChnlGroupCfgVsiName , hwChnlCfgGroupChnlName, hwChnlGroupCfgGroupAddress ,
           hwChnlGroupCfgGroupLen, hwChnlGroupCfgSourceAddress , hwChnlGroupCfgSourceLen  
          }
    ::= { hwL2mcChnlGroupCfgTable 1 } 
     
HWL2mcChnlGroupCfgEntry ::= SEQUENCE { 
    hwChnlGroupCfgVlanIndex       VlanIdOrAny,
    hwChnlGroupCfgVsiName         DisplayString,
    hwChnlCfgGroupChnlName        DisplayString,
    hwChnlGroupCfgGroupAddress       IpAddress,
    hwChnlGroupCfgGroupLen       Integer32,
    hwChnlGroupCfgSourceAddress   IpAddress,
    hwChnlGroupCfgSourceLen       Integer32,
    hwChnlGroupCfgPerBand       Integer32, 
    hwChnlGroupCfgRowStatus       RowStatus
    }
    
hwChnlGroupCfgVlanIndex OBJECT-TYPE
    SYNTAX       VlanIdOrAny
    MAX-ACCESS   not-accessible
    STATUS       current
    DESCRIPTION
        "The VLAN ID, which is the configuration index in a VLAN. 
        If a VSI is specified, the value is 4095. If both hwChnlCfgVlanIndex and hwChnlCfgVSIName are invalid, the configuration is global.
                The value ranges from 1 to 4095.
                "
    ::= { hwL2mcChnlGroupCfgEntry 1 }
    
hwChnlGroupCfgVsiName OBJECT-TYPE
    SYNTAX       DisplayString(SIZE (0..31))
    MAX-ACCESS   not-accessible
    STATUS       current
    DESCRIPTION
        "The name of a VSI. 
        If a VLAN is specified, the value is 32. If both hwChnlCfgVlanIndex and hwChnlCfgVSIName are invalid, the configuration is global."
    ::= { hwL2mcChnlGroupCfgEntry 2 }
    
hwChnlCfgGroupChnlName OBJECT-TYPE
    SYNTAX       DisplayString(SIZE (0..31))
    MAX-ACCESS   not-accessible
    STATUS       current
    DESCRIPTION
        "The channel name."
    ::= { hwL2mcChnlGroupCfgEntry 3 }
    
    
hwChnlGroupCfgGroupAddress OBJECT-TYPE
    SYNTAX       IpAddress
    MAX-ACCESS   not-accessible
    STATUS       current
    DESCRIPTION
        "The group address of a multicast group. In the case of MAC forwarding, the group address is the smallest of 32 IP addresses."
    ::= { hwL2mcChnlGroupCfgEntry 4 }    


hwChnlGroupCfgGroupLen   OBJECT-TYPE
    SYNTAX       Integer32(4..32) 
    MAX-ACCESS   not-accessible
    STATUS       current
    DESCRIPTION
        "The mask length of a multicast group."
    ::= { hwL2mcChnlGroupCfgEntry 5 }
    
hwChnlGroupCfgSourceAddress  OBJECT-TYPE
    SYNTAX       IpAddress
    MAX-ACCESS   not-accessible
    STATUS       current
    DESCRIPTION
        "The source IP address of a multicast group."
    ::= { hwL2mcChnlGroupCfgEntry 6 }   
    
hwChnlGroupCfgSourceLen   OBJECT-TYPE
    SYNTAX       Integer32(0|8..32) 
    MAX-ACCESS   not-accessible
    STATUS       current
    DESCRIPTION
        "The mask length of a multicast source address."
    ::= { hwL2mcChnlGroupCfgEntry 7 }     

hwChnlGroupCfgPerBand OBJECT-TYPE
    SYNTAX       Integer32(0..131072) 
    MAX-ACCESS   read-create
    STATUS       current
    DESCRIPTION
        "The bandwidth of a multicast group."
    ::= { hwL2mcChnlGroupCfgEntry 9 }     
    
hwChnlGroupCfgRowStatus  OBJECT-TYPE
    SYNTAX       RowStatus
    MAX-ACCESS   read-create
    STATUS       current
    DESCRIPTION
        "The row status."
    ::= { hwL2mcChnlGroupCfgEntry 100 } 
    
    
--
--  The hwL2mcGroupPolicyCfgInfo group.
--
hwL2mcGroupPolicyCfgInfo     
        OBJECT IDENTIFIER ::= { hwIgspMibObject 16 }

hwL2mcGroupPolicyCfgTable OBJECT-TYPE
    SYNTAX       SEQUENCE OF HWL2mcGroupPolicyCfgEntry
    MAX-ACCESS   not-accessible
    STATUS       current
    DESCRIPTION
        "In this table, you can query or configure a group policy to filter entries on a port."
    ::= { hwL2mcGroupPolicyCfgInfo 1 }
    
hwL2mcGroupPolicyCfgEntry OBJECT-TYPE
    SYNTAX       HWL2mcGroupPolicyCfgEntry
    MAX-ACCESS   not-accessible
    STATUS       current
    DESCRIPTION
        "An entry is created for each active VLAN or VSI in the device when a group policy added."
    INDEX {  hwGroupPolicyVlanIndex, hwGroupPolicyVsiName
            }
    ::= { hwL2mcGroupPolicyCfgTable 1 } 
     
HWL2mcGroupPolicyCfgEntry ::= SEQUENCE { 
    hwGroupPolicyVlanIndex    VlanIdOrAny,
    hwGroupPolicyVsiName    DisplayString,
    hwGroupPolicyAclNum        Integer32,
    hwGroupPolicyIgmpVersion    INTEGER,
    hwGroupPolicyRowStatus    RowStatus
    }

hwGroupPolicyVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcGroupPolicyCfgEntry 1 }
    
hwGroupPolicyVsiName OBJECT-TYPE
    SYNTAX       DisplayString(SIZE (0..31))
    MAX-ACCESS   not-accessible
    STATUS       current
    DESCRIPTION
        "The name of a VSI. If a VLAN is specified, the value is 32."
    ::= { hwL2mcGroupPolicyCfgEntry 2 }        
    
    
hwGroupPolicyAclNum OBJECT-TYPE
    SYNTAX       Integer32(0|2000..3999) 
    MAX-ACCESS   read-create
    STATUS       current
    DESCRIPTION
        "The number of a basic ACL.
                The ACL number ranges from 2000 to 3999.
                The default value is 0, indicating that the value is invalid.
                "
    ::= { hwL2mcGroupPolicyCfgEntry 3 }
    
hwGroupPolicyIgmpVersion OBJECT-TYPE
    SYNTAX       INTEGER
            {
            version1(1),
            version2(2),
            version3(3),
            versionAll(4)
            }
    MAX-ACCESS   read-create
    STATUS       current
    DESCRIPTION
        "The IGMP version.
                The value ranges from 1 to 4.
                The default is 4, indicating that no version is specified.
                "
    ::= { hwL2mcGroupPolicyCfgEntry 4 }
    
hwGroupPolicyRowStatus OBJECT-TYPE
    SYNTAX       RowStatus
    MAX-ACCESS   read-create
    STATUS       current
    DESCRIPTION
        "The row status."
    ::= { hwL2mcGroupPolicyCfgEntry 100 }
    
--
--  The hwL2mcChnlDenyCfgInfo group.
--
hwL2mcChnlDenyCfgInfo     
        OBJECT IDENTIFIER ::= { hwIgspMibObject 17 }

hwL2mcChnlDenyCfgTable OBJECT-TYPE
    SYNTAX       SEQUENCE OF HWL2mcChnlDenyCfgEntry
    MAX-ACCESS   not-accessible
    STATUS       current
    DESCRIPTION
        "This table describes the configurations of deny unspecified group for each VLAN or VSI, or in global."
    ::= { hwL2mcChnlDenyCfgInfo 1 }
    
hwL2mcChnlDenyCfgEntry OBJECT-TYPE
    SYNTAX       HWL2mcChnlDenyCfgEntry
    MAX-ACCESS   not-accessible
    STATUS       current
    DESCRIPTION
        "An entry of channel deny is created for each VLAN or VSI in the device create an channel."
    INDEX { hwChnlDenyCfgVlanIndex, hwChnlDenyCfgVsiName
          }
    ::= { hwL2mcChnlDenyCfgTable 1 } 
     
HWL2mcChnlDenyCfgEntry ::= SEQUENCE { 
    hwChnlDenyCfgVlanIndex      VlanIdOrAny,
    hwChnlDenyCfgVsiName        DisplayString,
    hwChnlDenyCfg            INTEGER, 
    hwChnlDenyCfgRowStatus      RowStatus
    }
    
hwChnlDenyCfgVlanIndex OBJECT-TYPE
    SYNTAX       VlanIdOrAny
    MAX-ACCESS   not-accessible
    STATUS       current
    DESCRIPTION
        "The VLAN ID, which is the configuration index in a VLAN. 
        If a VSI is specified, the value is 4095. If both hwChnlCfgVlanIndex and hwChnlCfgVSIName are invalid, the configuration is global.
                The value ranges from 1 to 4095.
                "
    ::= { hwL2mcChnlDenyCfgEntry 1 }
    
hwChnlDenyCfgVsiName OBJECT-TYPE
    SYNTAX       DisplayString(SIZE (0..31))
    MAX-ACCESS   not-accessible
    STATUS       current
    DESCRIPTION
        "The name of a VSI. 
        If a VLAN is specified, the value is 32. If both hwChnlCfgVlanIndex and hwChnlCfgVSIName are invalid, the configuration is global."
    ::= { hwL2mcChnlDenyCfgEntry 2 }
    
  
hwChnlDenyCfg  OBJECT-TYPE
    SYNTAX       INTEGER
            {
            forward(1),
            discard(2)
            }
    MAX-ACCESS   read-create
    STATUS       current
    DESCRIPTION
        "Whether discard unspecified channel:
                1: not discard
                2: discard
                "
    ::= { hwL2mcChnlDenyCfgEntry 3 }
    
    
hwChnlDenyCfgRowStatus OBJECT-TYPE
    SYNTAX       RowStatus
    MAX-ACCESS   read-create
    STATUS       current
    DESCRIPTION
        "The row status."
    ::= { hwL2mcChnlDenyCfgEntry 100 } 

    
--
--  The hwL2mcQinQPortTable  group.
--
hwL2mcQinQPortInfo     
        OBJECT IDENTIFIER ::= { hwIgspMibObject 18 }

hwL2mcQinQPortTable OBJECT-TYPE
    SYNTAX       SEQUENCE OF HWL2mcQinQPortEntry
    MAX-ACCESS   not-accessible
    STATUS       current
    DESCRIPTION
        "This table describes the specific port statistic of QinQ table of protol."
    ::= { hwL2mcQinQPortInfo 1 }
    
hwL2mcQinQPortEntry OBJECT-TYPE
    SYNTAX       HWL2mcQinQPortEntry
    MAX-ACCESS   not-accessible
    STATUS       current
    DESCRIPTION
        "An entry of the specific port statistic of QinQ table of protol."
    INDEX { hwQinQPortVlanIndex, hwQinQPortVsiName, hwL2mcQinQPortIfIndex, hwQinQPortGroupAddr,
            hwQinQPortSourceAddr, hwQinQPortPe, hwQinQPortCe
          }
    ::= { hwL2mcQinQPortTable 1 } 
     
HWL2mcQinQPortEntry ::= SEQUENCE { 
    hwQinQPortVlanIndex      VlanIdOrAny,
    hwQinQPortVsiName        DisplayString,
    hwL2mcQinQPortIfIndex    InterfaceIndexOrZero, 
    hwQinQPortGroupAddr      IpAddress,
    hwQinQPortSourceAddr     IpAddress,
    hwQinQPortPe             VlanIdOrAny,
    hwQinQPortCe             VlanIdOrAny,
    hwQinQPortTime           Counter32,
    hwQinQPortFlag           Integer32
    }
    
hwQinQPortVlanIndex OBJECT-TYPE
    SYNTAX       VlanIdOrAny
    MAX-ACCESS   not-accessible
    STATUS       current
    DESCRIPTION
        "The VLAN ID, which is the configuration index in a VLAN. 
        If a VSI is specified, the value is 4095. If both hwChnlCfgVlanIndex and hwChnlCfgVSIName are invalid, the configuration is global.
                The value ranges from 1 to 4095.
                "
    ::= { hwL2mcQinQPortEntry 1 }
    
hwQinQPortVsiName OBJECT-TYPE
    SYNTAX       DisplayString(SIZE (0..31))
    MAX-ACCESS   not-accessible
    STATUS       current
    DESCRIPTION
        "The name of a VSI. 
        If a VLAN is specified, the value is 32. If both hwChnlCfgVlanIndex and hwChnlCfgVSIName are invalid, the configuration is global."
    ::= { hwL2mcQinQPortEntry 2 }

hwL2mcQinQPortIfIndex OBJECT-TYPE
    SYNTAX       InterfaceIndexOrZero
    MAX-ACCESS   not-accessible
    STATUS       current
    DESCRIPTION
        "The interface index. The value 0 indicates that the interface index is invalid."
    ::= { hwL2mcQinQPortEntry 3 }
  
hwQinQPortGroupAddr  OBJECT-TYPE
    SYNTAX       IpAddress
    MAX-ACCESS   not-accessible
    STATUS       current
    DESCRIPTION
        "The group address of a multicast group. In the case of MAC forwarding, the group address is the smallest of 32 IP addresses."
    ::= { hwL2mcQinQPortEntry 4 }
  
hwQinQPortSourceAddr OBJECT-TYPE
    SYNTAX       IpAddress
    MAX-ACCESS   not-accessible
    STATUS       current
    DESCRIPTION
        "The source IP address of a multicast group."
    ::= { hwL2mcQinQPortEntry 5 }
  
hwQinQPortPe  OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcQinQPortEntry 6 }
    
hwQinQPortCe OBJECT-TYPE
    SYNTAX       VlanIdOrAny
    MAX-ACCESS   not-accessible
    STATUS       current
    DESCRIPTION
        "The CE VID of an interface.
                The value ranges from 1 to 4095.
                The value 4095 indicates that the CE VID is invalid.
                "
    ::= { hwL2mcQinQPortEntry 7 }
  
hwQinQPortTime OBJECT-TYPE
    SYNTAX       Counter32
    MAX-ACCESS   read-only
    STATUS       current
    DESCRIPTION
        "The number of QinQ Port entry live time in second."
    ::= { hwL2mcQinQPortEntry 20 }
    
hwQinQPortFlag OBJECT-TYPE
    SYNTAX       Integer32(1..4)
    MAX-ACCESS   read-only
    STATUS       current
    DESCRIPTION
        "The port flag:
            1 static
            2 dynamic
            3 static and dynamic
            4 invalid
            "
    ::= { hwL2mcQinQPortEntry 21 }

--
--  The hwL2mcETrackingInfoTable   group.
--
hwL2mcETrackingInfoInfo
        OBJECT IDENTIFIER ::= { hwIgspMibObject 19 }

hwL2mcETrackingInfoTable OBJECT-TYPE
    SYNTAX       SEQUENCE OF HWL2mcETrackingInfoEntry
    MAX-ACCESS   not-accessible
    STATUS       current
    DESCRIPTION
        "This table describes the host explicit tracking."
    ::= { hwL2mcETrackingInfoInfo 1 }
    
hwL2mcETrackingInfoEntry OBJECT-TYPE
    SYNTAX       HWL2mcETrackingInfoEntry
    MAX-ACCESS   not-accessible
    STATUS       current
    DESCRIPTION
        "An entry of the host explicit tracking."
    INDEX { hwETrackInfoSlotIndex, hwETrackInfoVlanIndex, hwETrackInfoVsiName, hwETrackInfoGroupAddr, hwETrackInfoSourceAddr,
            hwETrackInfoPortType, hwETrackInfoPortIfIndex, hwETrackInfoPortPeId, hwETrackInfoPortCeId,
            hwETrackInfoPeerAddress, hwETrackInfoVcOrSiteId,hwETrackInfoBoardNum, hwETrackInfoReportAddr
          }
    ::= { hwL2mcETrackingInfoTable 1 } 
     
HWL2mcETrackingInfoEntry ::= SEQUENCE {
    hwETrackInfoSlotIndex    Integer32,
    hwETrackInfoVlanIndex    VlanIdOrAny,
    hwETrackInfoVsiName      DisplayString,
    hwETrackInfoGroupAddr    IpAddress, 
    hwETrackInfoSourceAddr   IpAddress,
    hwETrackInfoPortType     HWPortType,
    hwETrackInfoPortIfIndex  InterfaceIndexOrZero,
    hwETrackInfoPortPeId     VlanIdOrAny,
    hwETrackInfoPortCeId     VlanIdOrAny,
    hwETrackInfoPeerAddress  IpAddress,
    hwETrackInfoVcOrSiteId   Unsigned32,
    hwETrackInfoBoardNum     Integer32,
    hwETrackInfoReportAddr   IpAddress,
    hwETrackInfoFlag         Integer32
    }

hwETrackInfoSlotIndex OBJECT-TYPE
    SYNTAX       Integer32
    MAX-ACCESS   not-accessible
    STATUS       current
    DESCRIPTION
        "The slot index, which is interface board number. "
    ::= { hwL2mcETrackingInfoEntry 1 }
    
hwETrackInfoVlanIndex OBJECT-TYPE
    SYNTAX       VlanIdOrAny
    MAX-ACCESS   not-accessible
    STATUS       current
    DESCRIPTION
        "The VLAN ID, which is the configuration index in a VLAN. 
        If a VSI is specified, the value is 4095. If both hwETrackInfoVlanIndex and hwETrackInfoVsiName are invalid, the configuration is global.
                The value ranges from 1 to 4095.
                "
    ::= { hwL2mcETrackingInfoEntry 2 }
    
hwETrackInfoVsiName OBJECT-TYPE
    SYNTAX       DisplayString(SIZE (0..31))
    MAX-ACCESS   not-accessible
    STATUS       current
    DESCRIPTION
        "The name of a VSI. 
        If a VLAN is specified, the value is 32. If both hwETrackInfoVlanIndex and hwETrackInfoVsiName are invalid, the configuration is global."
    ::= { hwL2mcETrackingInfoEntry 3 }
    
hwETrackInfoGroupAddr  OBJECT-TYPE
    SYNTAX       IpAddress
    MAX-ACCESS   not-accessible
    STATUS       current
    DESCRIPTION
        "The group address of a multicast group. In the case of MAC forwarding, the group address is the smallest of 32 IP addresses."
    ::= { hwL2mcETrackingInfoEntry 4 }  
    
hwETrackInfoSourceAddr  OBJECT-TYPE
    SYNTAX       IpAddress
    MAX-ACCESS   not-accessible
    STATUS       current
    DESCRIPTION
        "The source IP address of a multicast group."
    ::= { hwL2mcETrackingInfoEntry 5 }  
    
hwETrackInfoPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcETrackingInfoEntry 6 }

hwETrackInfoPortIfIndex OBJECT-TYPE
    SYNTAX       InterfaceIndexOrZero
    MAX-ACCESS   not-accessible
    STATUS       current
    DESCRIPTION
        "The interface index. The value 0 indicates that the interface index is invalid."
    ::= { hwL2mcETrackingInfoEntry 7 }
  
hwETrackInfoPortPeId  OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcETrackingInfoEntry 8 }
    
hwETrackInfoPortCeId OBJECT-TYPE
    SYNTAX       VlanIdOrAny
    MAX-ACCESS   not-accessible
    STATUS       current
    DESCRIPTION
        "The CE VID of an interface.
                The value ranges from 1 to 4095.
                The value 4095 indicates that the CE VID is invalid.
                "
    ::= { hwL2mcETrackingInfoEntry 9 }
  
hwETrackInfoPeerAddress OBJECT-TYPE
    SYNTAX       IpAddress
    MAX-ACCESS   not-accessible
    STATUS       current
    DESCRIPTION
        "The peer IP address of a PW interface. The value 0.0.0.0 indicates that the IP address is invalid."
    ::= { hwL2mcETrackingInfoEntry 10 }
    
hwETrackInfoVcOrSiteId OBJECT-TYPE
    SYNTAX       Unsigned32(1..4294967295) 
    MAX-ACCESS   not-accessible
    STATUS       current
    DESCRIPTION
        "The VC ID or SITE ID of a PW interface."
    ::= { hwL2mcETrackingInfoEntry 11 }

hwETrackInfoBoardNum OBJECT-TYPE
    SYNTAX       Integer32
    MAX-ACCESS   not-accessible
    STATUS       current
    DESCRIPTION
        "The interface board number."
    ::= { hwL2mcETrackingInfoEntry 12 }
    
hwETrackInfoReportAddr  OBJECT-TYPE
    SYNTAX       IpAddress
    MAX-ACCESS   not-accessible
    STATUS       current
    DESCRIPTION
        "The source IP address of a user."
    ::= { hwL2mcETrackingInfoEntry 13 } 
    
hwETrackInfoFlag  OBJECT-TYPE
    SYNTAX       Integer32(1..4)
    MAX-ACCESS   read-only
    STATUS       current
    DESCRIPTION
        "The port filter mode:
            1 include
            2 exclude
            "
    ::= { hwL2mcETrackingInfoEntry 20 }   

--
--  The hwL2mcSourceGroupTable  group.
--
hwL2mcSourceGroupInfo     
        OBJECT IDENTIFIER ::= { hwIgspMibObject 22 }
        
hwL2mcSourceGroupTable OBJECT-TYPE
    SYNTAX       SEQUENCE OF HWL2mcSourceGroupEntry
    MAX-ACCESS   not-accessible
    STATUS       current
    DESCRIPTION
        "Table contains VLAN or VSI performance statistics information
         for IGMP Snooping."
    ::= { hwL2mcSourceGroupInfo 1 }

hwL2mcSourceGroupEntry OBJECT-TYPE
    SYNTAX       HWL2mcSourceGroupEntry
    MAX-ACCESS   not-accessible
    STATUS       current
    DESCRIPTION
        "An entry is created for each active VLAN or VSI in the device 
         and deleted when the VLAN or VSI becomes inactive."
    INDEX { hwL2mcSourceGroupVlanIndex, hwL2mcSourceGroupVsiName, 
        hwL2mcSourceGroupGroupAddress, hwL2mcSourceGroupSourceAddress}
    ::= { hwL2mcSourceGroupTable 1 } 
     
HWL2mcSourceGroupEntry ::= SEQUENCE { 
    hwL2mcSourceGroupVlanIndex VlanIdOrAny,
    hwL2mcSourceGroupVsiName    DisplayString,
    hwL2mcSourceGroupGroupAddress   IpAddress,
    hwL2mcSourceGroupSourceAddress  IpAddress,
    hwL2mcSourceGroupStat Counter64
    }                                                                                                                                      

hwL2mcSourceGroupVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcSourceGroupEntry 1 }

hwL2mcSourceGroupVsiName OBJECT-TYPE
    SYNTAX       DisplayString(SIZE (0..31))
    MAX-ACCESS   not-accessible
    STATUS       current
    DESCRIPTION
        "The name of a VSI. If a VLAN is specified, the value is 32."
    ::= { hwL2mcSourceGroupEntry 2 }
 
hwL2mcSourceGroupGroupAddress OBJECT-TYPE
    SYNTAX       IpAddress
    MAX-ACCESS   not-accessible
    STATUS       current
    DESCRIPTION
        "The group address of a multicast group. 
        In the case of MAC forwarding, the group address is the smallest of 32 IP addresses."
    ::= { hwL2mcSourceGroupEntry 3 }
    
hwL2mcSourceGroupSourceAddress OBJECT-TYPE
    SYNTAX       IpAddress
    MAX-ACCESS   not-accessible
    STATUS       current
    DESCRIPTION
        "The source IP address of a multicast group."
    ::= { hwL2mcSourceGroupEntry 4 }

hwL2mcSourceGroupStat  OBJECT-TYPE
    SYNTAX       Counter64
    MAX-ACCESS   read-only
    STATUS       current
    DESCRIPTION
        "the packet statistic of (S,G) group."
    ::= { hwL2mcSourceGroupEntry 10 }
        
--
--  The hwL2mcDTFwdInfo group.
--
hwL2mcDTFwdInfo     
        OBJECT IDENTIFIER ::= { hwIgspMibObject 23 }

hwL2mcDTFwdTable OBJECT-TYPE
    SYNTAX       SEQUENCE OF HWL2mcDTFwdEntry
    MAX-ACCESS   not-accessible
    STATUS       current
    DESCRIPTION
        "Table contains l2 multicast forward information
         for IGMP Snooping."
    ::= { hwL2mcDTFwdInfo 1 }
    
hwL2mcDTFwdEntry OBJECT-TYPE
    SYNTAX       HWL2mcDTFwdEntry
    MAX-ACCESS   not-accessible
    STATUS       current
    DESCRIPTION
        "An entry is created for each active VLAN or VSI in the device create a forwarding table entry and delete when 
        a forwarding table entry deleted."
    INDEX { hwL2mcDTFwdSlotIndex, hwL2mcDTFwdVlanIndex, hwL2mcDTFwdVsiName, hwL2mcDTFwdGroupAddress, hwL2mcDTFwdSourceAddress, hwL2mcDTFwdPortType,
            hwL2mcDTFwdPortIfIndex, hwL2mcDTFwdPortPeId, hwL2mcDTFwdPortCeId, 
            hwL2mcDTFwdPeerAddress, hwL2mcDTFwdVcOrSiteId, hwL2mcDTFwdBoardNum }
    ::= { hwL2mcDTFwdTable 1 } 
     
HWL2mcDTFwdEntry ::= SEQUENCE { 
    hwL2mcDTFwdSlotIndex      Integer32,
    hwL2mcDTFwdVlanIndex      VlanIdOrAny,
    hwL2mcDTFwdVsiName        DisplayString,
    hwL2mcDTFwdGroupAddress   IpAddress,
    hwL2mcDTFwdSourceAddress  IpAddress,      
    hwL2mcDTFwdPortType       HWPortType,
    hwL2mcDTFwdPortIfIndex    InterfaceIndexOrZero,
    hwL2mcDTFwdPortPeId       VlanIdOrAny,
    hwL2mcDTFwdPortCeId       VlanIdOrAny,
    hwL2mcDTFwdPeerAddress    IpAddress,
    hwL2mcDTFwdVcOrSiteId     Unsigned32,
    hwL2mcDTFwdBoardNum       Integer32,
    hwL2mcDTFwdAddressType    INTEGER,
    hwL2mcDTFwdHostFlag1      INTEGER, 
    hwL2mcDTFwdHostFlag2      INTEGER,
    hwL2mcDTFwdHostFlag3      INTEGER,
    hwL2mcDTFwdHostFlag4      INTEGER
    }

hwL2mcDTFwdSlotIndex OBJECT-TYPE
    SYNTAX       Integer32
    MAX-ACCESS   not-accessible
    STATUS       current
    DESCRIPTION
        "The slot index, which is interface board number. "
    ::= { hwL2mcDTFwdEntry 1 }
    
hwL2mcDTFwdVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcDTFwdEntry 2 }
    
hwL2mcDTFwdVsiName OBJECT-TYPE
    SYNTAX       DisplayString(SIZE (0..31))
    MAX-ACCESS   not-accessible
    STATUS       current
    DESCRIPTION
        "The name of a VSI. If a VLAN is specified, the value is 32."
    ::= { hwL2mcDTFwdEntry 3 }
    
hwL2mcDTFwdGroupAddress OBJECT-TYPE
    SYNTAX       IpAddress
    MAX-ACCESS   not-accessible
    STATUS       current
    DESCRIPTION
        "The group address of a multicast group. In the case of MAC forwarding, the group address is the smallest of 32 IP addresses."
    ::= { hwL2mcDTFwdEntry 4 }    

hwL2mcDTFwdSourceAddress OBJECT-TYPE
    SYNTAX       IpAddress
    MAX-ACCESS   not-accessible
    STATUS       current
    DESCRIPTION
        "The source IP address of a multicast group."
    ::= { hwL2mcDTFwdEntry 5 }
        
hwL2mcDTFwdPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcDTFwdEntry 6 }

hwL2mcDTFwdPortIfIndex OBJECT-TYPE
    SYNTAX       InterfaceIndexOrZero
    MAX-ACCESS   not-accessible
    STATUS       current
    DESCRIPTION
        "The interface index. The value 0 indicates that the interface index is invalid."
    ::= { hwL2mcDTFwdEntry 7 }
 
hwL2mcDTFwdPortPeId OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcDTFwdEntry 8 }
    
hwL2mcDTFwdPortCeId OBJECT-TYPE
    SYNTAX       VlanIdOrAny
    MAX-ACCESS   not-accessible
    STATUS       current
    DESCRIPTION
        "The CE VID of an interface.
                The value ranges from 1 to 4095.
                The value 4095 indicates that the CE VID is invalid.
                "
    ::= { hwL2mcDTFwdEntry 9 }
    
hwL2mcDTFwdPeerAddress OBJECT-TYPE
    SYNTAX       IpAddress
    MAX-ACCESS   not-accessible
    STATUS       current
    DESCRIPTION
        "The peer IP address of a PW interface. The value 0.0.0.0 indicates that the IP address is invalid."
    ::= { hwL2mcDTFwdEntry 10 }
    
hwL2mcDTFwdVcOrSiteId OBJECT-TYPE
    SYNTAX       Unsigned32(1..4294967295) 
    MAX-ACCESS   not-accessible
    STATUS       current
    DESCRIPTION
        "The VC ID or SITE ID of a PW interface."
    ::= { hwL2mcDTFwdEntry 11 }
 
hwL2mcDTFwdBoardNum OBJECT-TYPE
    SYNTAX       Integer32
    MAX-ACCESS   not-accessible
    STATUS       current
    DESCRIPTION
        "The interface board number."
    ::= { hwL2mcDTFwdEntry 12 }
    
hwL2mcDTFwdAddressType OBJECT-TYPE
    SYNTAX       INTEGER
            {
            ip(1),
            mac(2)
            } 
    MAX-ACCESS   read-only
    STATUS       current
    DESCRIPTION
        "The address type of an entry:
                1: IP
                2: MAC
                The default value is 1.
                "
    ::= { hwL2mcDTFwdEntry 21 }

hwL2mcDTFwdHostFlag1 OBJECT-TYPE
    SYNTAX       INTEGER
            {
            static(1),
            dynamic(2),
            staticDynamic(3),
            invalid(4)
            } 
    MAX-ACCESS   read-only
    STATUS       current
    DESCRIPTION
        "The mode to create an interface on the host:
                1: static
                2: dynamic
                3: static and dynamic
                4: invalid
                "
    ::= { hwL2mcDTFwdEntry 22 }
    
hwL2mcDTFwdHostFlag2 OBJECT-TYPE
    SYNTAX       INTEGER
            {
            nonMapping(1),
            mapping(2)
            }
    MAX-ACCESS   read-only
    STATUS       current
    DESCRIPTION
        "Whether an interface on the host is created through SSM-mapping:
                1: non-mapping
                2: mapping
                "
    ::= { hwL2mcDTFwdEntry 23 }
    
hwL2mcDTFwdHostFlag3 OBJECT-TYPE
    SYNTAX       INTEGER
            {
            host(1),
            router(2)
            }
    MAX-ACCESS   read-only
    STATUS       current
    DESCRIPTION
        "The type of an interface created on a router:
                1: Interface connected to the host
                2: Router interface that replicates multicast data flows
                "
    ::= { hwL2mcDTFwdEntry 24 }
    
hwL2mcDTFwdHostFlag4 OBJECT-TYPE
    SYNTAX       INTEGER
            {
            port(1),
            static(2),
            both(3)
            }
    MAX-ACCESS   read-only
    STATUS       current
    DESCRIPTION
        "Indicates (S, G) table created :
                1: from port;
                2: from static;
                3: from both
                the default falue is 1
                "
    ::= { hwL2mcDTFwdEntry 25 }    
    
    
--
--  The hwDTGroupInfo group.
--
hwL2mcDTGroupInfo     
        OBJECT IDENTIFIER ::= { hwIgspMibObject 24 }

hwL2mcDTGroupInfoTable OBJECT-TYPE
    SYNTAX       SEQUENCE OF HWL2mcDTGroupInfoEntry
    MAX-ACCESS   not-accessible
    STATUS       current
    DESCRIPTION
        "Table contains l2 multicast group information
         for IGMP Snooping."
    ::= { hwL2mcDTGroupInfo 1 }
    
hwL2mcDTGroupInfoEntry OBJECT-TYPE
    SYNTAX       HWL2mcDTGroupInfoEntry
    MAX-ACCESS   not-accessible
    STATUS       current
    DESCRIPTION
        "An entry is created for each active VLAN or VSI in the device create a forwarding table entry and delete when 
        a forwarding table entry deleted."
    INDEX { hwL2mcDTGroupSlotIndex, hwL2mcDTGroupVlanIndex, hwL2mcDTGroupVsiName, hwL2mcDTGroupGroupAddress, hwL2mcDTGroupSourceAddress, 
    		hwL2mcDTGroupFilterFlag, hwL2mcDTPortType, hwL2mcDTGroupPortIfIndex, hwL2mcDTGroupPortPeId, 
    		hwL2mcDTGroupPortCeId, hwL2mcDTGroupPeerAddress, hwL2mcDTGroupVcOrSiteId, hwL2mcDTGroupBoardNum }
    ::= { hwL2mcDTGroupInfoTable 1 } 
     
HWL2mcDTGroupInfoEntry ::= SEQUENCE {
    hwL2mcDTGroupSlotIndex      Integer32, 
    hwL2mcDTGroupVlanIndex      VlanIdOrAny,
    hwL2mcDTGroupVsiName        DisplayString,
    hwL2mcDTGroupGroupAddress   IpAddress,  
    hwL2mcDTGroupSourceAddress  IpAddress,
    hwL2mcDTGroupFilterFlag     INTEGER,
    hwL2mcDTPortType            HWPortType,
    hwL2mcDTGroupPortIfIndex    InterfaceIndexOrZero,
    hwL2mcDTGroupPortPeId       VlanIdOrAny,
    hwL2mcDTGroupPortCeId       VlanIdOrAny,
    hwL2mcDTGroupPeerAddress    IpAddress,
    hwL2mcDTGroupVcOrSiteId     Unsigned32,
    hwL2mcDTGroupBoardNum       Integer32,
    hwL2mcDTSourceUpTime        Counter32, 
    hwL2mcDTSourceExpires       Counter32,
    hwL2mcDTGroupUpTime         Counter32,
    hwL2mcDTGroupExpires        Counter32,    
    hwL2mcDTGroupHostFlag1      INTEGER,
    hwL2mcDTGroupHostFlag2      INTEGER,
    hwL2mcDTGroupRowStatus      RowStatus
    }
    
hwL2mcDTGroupSlotIndex OBJECT-TYPE
    SYNTAX       Integer32
    MAX-ACCESS   not-accessible
    STATUS       current
    DESCRIPTION
        "The slot index, which is interface board number. "
    ::= { hwL2mcDTGroupInfoEntry 1 }    
    
hwL2mcDTGroupVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcDTGroupInfoEntry 2 }

hwL2mcDTGroupVsiName OBJECT-TYPE
    SYNTAX       DisplayString(SIZE (0..31))
    MAX-ACCESS   not-accessible
    STATUS       current
    DESCRIPTION
        "The name of a VSI. If a VLAN is specified, the value is 32."
    ::= { hwL2mcDTGroupInfoEntry 3 }

hwL2mcDTGroupGroupAddress OBJECT-TYPE
    SYNTAX       IpAddress
    MAX-ACCESS   not-accessible
    STATUS       current
    DESCRIPTION
        "The IP address of a multicast group."
    ::= { hwL2mcDTGroupInfoEntry 4 }

hwL2mcDTGroupSourceAddress OBJECT-TYPE
    SYNTAX       IpAddress
    MAX-ACCESS   not-accessible
    STATUS       current
    DESCRIPTION
        "The source IP address of a multicast group."
    ::= { hwL2mcDTGroupInfoEntry 5 }
    
hwL2mcDTGroupFilterFlag OBJECT-TYPE
    SYNTAX       INTEGER
            {
            include(1),
            exclude(2),
            invalid(3)
            }
    MAX-ACCESS   not-accessible
    STATUS       current
    DESCRIPTION
        "The filtering mode:
                1: include
                2: exclude
                3: invalid 
                "
    ::= { hwL2mcDTGroupInfoEntry 6 }    
    
hwL2mcDTPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcDTGroupInfoEntry 7 }

hwL2mcDTGroupPortIfIndex OBJECT-TYPE
    SYNTAX       InterfaceIndexOrZero
    MAX-ACCESS   not-accessible
    STATUS       current
    DESCRIPTION
        "The interface index. The value 0 indicates that the interface index is invalid."
    ::= { hwL2mcDTGroupInfoEntry 8 }

hwL2mcDTGroupPortPeId OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcDTGroupInfoEntry 9 }

hwL2mcDTGroupPortCeId OBJECT-TYPE
    SYNTAX       VlanIdOrAny
    MAX-ACCESS   not-accessible
    STATUS       current
    DESCRIPTION
        "The CE VID of an interface.
                The value ranges from 1 to 4095.
                The value 0 indicates that the PE VID is invalid.
                "
    ::= { hwL2mcDTGroupInfoEntry 10 }

hwL2mcDTGroupPeerAddress OBJECT-TYPE
    SYNTAX       IpAddress
    MAX-ACCESS   not-accessible
    STATUS       current
    DESCRIPTION
        "The peer IP address of a PW interface. The value 0.0.0.0 indicates that the IP address is invalid."
    ::= { hwL2mcDTGroupInfoEntry 11 }

hwL2mcDTGroupVcOrSiteId OBJECT-TYPE
    SYNTAX       Unsigned32(1..4294967295) 
    MAX-ACCESS   not-accessible
    STATUS       current
    DESCRIPTION
        "The VC ID or SITE ID of a PW interface."
    ::= { hwL2mcDTGroupInfoEntry 12 }
    
hwL2mcDTGroupBoardNum OBJECT-TYPE
    SYNTAX       Integer32
    MAX-ACCESS   not-accessible
    STATUS       current
    DESCRIPTION
        "The interface board number."
    ::= { hwL2mcDTGroupInfoEntry 13 }    

hwL2mcDTSourceUpTime OBJECT-TYPE
    SYNTAX       Counter32
    MAX-ACCESS   read-only
    STATUS       current
    DESCRIPTION
        "How long the source group exists in the forwarding entry."
    ::= { hwL2mcDTGroupInfoEntry 21 }

hwL2mcDTSourceExpires OBJECT-TYPE
    SYNTAX       Counter32
    MAX-ACCESS   read-only
    STATUS       current
    DESCRIPTION
        "The timeout period of the source group in the forwarding entry, that is, the aging time of the source group."
    ::= { hwL2mcDTGroupInfoEntry 22 }
    
hwL2mcDTGroupUpTime OBJECT-TYPE
    SYNTAX       Counter32
    MAX-ACCESS   read-only
    STATUS       current
    DESCRIPTION
        "How long the group exists in the forwarding entry."
    ::= { hwL2mcDTGroupInfoEntry 23 }
    
hwL2mcDTGroupExpires OBJECT-TYPE
    SYNTAX       Counter32
    MAX-ACCESS   read-only
    STATUS       current
    DESCRIPTION
        "When the group expires in the forwarding entry, that is, the aging time of the source group."
    ::= { hwL2mcDTGroupInfoEntry 24 }
    

    
hwL2mcDTGroupHostFlag1 OBJECT-TYPE
    SYNTAX       INTEGER
            {
            static(1),
            dynamic(2),
            staticDynamic(3),
            invalid(4)
            } 
    MAX-ACCESS   read-only
    STATUS       current
    DESCRIPTION
        "The mode to create an interface on the host:
                1: static
                2: dynamic
                3: static and dynamic
                4: invalid
                "
    ::= { hwL2mcDTGroupInfoEntry 26 }
    
hwL2mcDTGroupHostFlag2 OBJECT-TYPE
    SYNTAX       INTEGER
         {
         nonMapping(1),
         mapping(2)
         }
    MAX-ACCESS   read-only
    STATUS       current
    DESCRIPTION
        "Whether an interface on the host is created through SSM-mapping:
                1: non-mapping
                2: mapping
                "
    ::= { hwL2mcDTGroupInfoEntry 27 }
    
hwL2mcDTGroupRowStatus OBJECT-TYPE
    SYNTAX       RowStatus
    MAX-ACCESS   read-only
    STATUS       current
    DESCRIPTION
        "The row status."
    ::= { hwL2mcDTGroupInfoEntry 100 }

--
--  The hwL2mcMulticastTrafficPolicyCfgInfo group.
--
hwL2mcMulticastTrafficPolicyCfgInfo     
        OBJECT IDENTIFIER ::= { hwIgspMibObject 25 }

hwL2mcMulticastTrafficPolicyCfgTable OBJECT-TYPE
    SYNTAX       SEQUENCE OF HWL2mcMulticastTrafficPolicyCfgEntry
    MAX-ACCESS   not-accessible
    STATUS       current
    DESCRIPTION
        "In this table, you can query or configure whether to disable receive multicast traffic on a port."
    ::= { hwL2mcMulticastTrafficPolicyCfgInfo 1 }
    
hwL2mcMulticastTrafficPolicyCfgEntry OBJECT-TYPE
    SYNTAX       HWL2mcMulticastTrafficPolicyCfgEntry
    MAX-ACCESS   not-accessible
    STATUS       current
    DESCRIPTION
        "An entry is created for each active VLAN or VSI in the device when disable receive multicast traffic on a port."
    INDEX {  hwMulticastTrafficPolicyPortType, hwMulticastTrafficPolicyPortIfIndex, hwMulticastTrafficPolicyPortPeId, hwMulticastTrafficPolicyPortCeId,
            hwMulticastTrafficPolicyPortEndCeId,
            hwMulticastTrafficPolicyPeerAddress, hwMulticastTrafficPolicyVcOrSiteId,hwMulticastTrafficPolicyVlanIndex, hwMulticastTrafficPolicyVsiName,
            hwMulticastTrafficPolicyEndVlanIndex
            }
    ::= { hwL2mcMulticastTrafficPolicyCfgTable 1 } 
     
HWL2mcMulticastTrafficPolicyCfgEntry ::= SEQUENCE { 
    hwMulticastTrafficPolicyPortType       HWPortType,
    hwMulticastTrafficPolicyPortIfIndex    InterfaceIndexOrZero,
    hwMulticastTrafficPolicyPortPeId       VlanIdOrAny,
    hwMulticastTrafficPolicyPortCeId       VlanIdOrAny,
    hwMulticastTrafficPolicyPortEndCeId    VlanIdOrAny,
    hwMulticastTrafficPolicyPeerAddress    IpAddress,
    hwMulticastTrafficPolicyVcOrSiteId     Unsigned32, 
    hwMulticastTrafficPolicyVlanIndex      VlanIdOrAny,
    hwMulticastTrafficPolicyEndVlanIndex   VlanIdOrAny,
    hwMulticastTrafficPolicyVsiName        DisplayString,
    hwMulticastTrafficPolicyRowStatus      RowStatus
    }
    
    
hwMulticastTrafficPolicyPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcMulticastTrafficPolicyCfgEntry 1 }
    
hwMulticastTrafficPolicyPortIfIndex OBJECT-TYPE
    SYNTAX       InterfaceIndexOrZero
    MAX-ACCESS   not-accessible
    STATUS       current
    DESCRIPTION
        "The interface index. The value 0 indicates that the interface index is invalid."
    ::= { hwL2mcMulticastTrafficPolicyCfgEntry 2 }
    
hwMulticastTrafficPolicyPortPeId OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcMulticastTrafficPolicyCfgEntry 3 }
    
hwMulticastTrafficPolicyPortCeId OBJECT-TYPE
    SYNTAX       VlanIdOrAny
    MAX-ACCESS   not-accessible
    STATUS       current
    DESCRIPTION
        "The CE VID of an interface.
                The value ranges from 1 to 4095.
                The value 4095 indicates that the PE VID is invalid.
                "
    ::= { hwL2mcMulticastTrafficPolicyCfgEntry 4 }
    
hwMulticastTrafficPolicyPortEndCeId OBJECT-TYPE
    SYNTAX       VlanIdOrAny
    MAX-ACCESS   not-accessible
    STATUS       current
    DESCRIPTION
        "The CE VID of an interface.
                The value ranges from 1 to 4095.
                The value 4095 indicates that the PE VID is invalid.
                "
    ::= { hwL2mcMulticastTrafficPolicyCfgEntry 5 }

hwMulticastTrafficPolicyPeerAddress OBJECT-TYPE
    SYNTAX       IpAddress
    MAX-ACCESS   not-accessible
    STATUS       current
    DESCRIPTION
        "The peer IP address of a PW interface. The value 0.0.0.0 indicates that the IP address is invalid."
    ::= { hwL2mcMulticastTrafficPolicyCfgEntry 6 }
    
hwMulticastTrafficPolicyVcOrSiteId OBJECT-TYPE
    SYNTAX       Unsigned32(1..4294967295) 
    MAX-ACCESS   not-accessible
    STATUS       current
    DESCRIPTION
        "The VC ID or SITE ID of a PW interface."
    ::= { hwL2mcMulticastTrafficPolicyCfgEntry 7 }
    
hwMulticastTrafficPolicyVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcMulticastTrafficPolicyCfgEntry 8 }
    
hwMulticastTrafficPolicyEndVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcMulticastTrafficPolicyCfgEntry 9 }

hwMulticastTrafficPolicyVsiName OBJECT-TYPE
    SYNTAX       DisplayString(SIZE (0..31))
    MAX-ACCESS   not-accessible
    STATUS       current
    DESCRIPTION
        "The name of a VSI. If a VLAN is specified, the value is 32."
    ::= { hwL2mcMulticastTrafficPolicyCfgEntry 10 }    
    
hwMulticastTrafficPolicyRowStatus OBJECT-TYPE
    SYNTAX       RowStatus
    MAX-ACCESS   read-create
    STATUS       current
    DESCRIPTION
        "The row status."
    ::= { hwL2mcMulticastTrafficPolicyCfgEntry 100 }  
    

--
--  The hwL2mcRouteLearnDisablePolicyCfgInfo group.
--
hwL2mcRouteLearnDisablePolicyCfgInfo     
        OBJECT IDENTIFIER ::= { hwIgspMibObject 26 }

hwL2mcRouteLearnDisablePolicyCfgTable OBJECT-TYPE
    SYNTAX       SEQUENCE OF HWL2mcRouteLearnDisablePolicyCfgEntry
    MAX-ACCESS   not-accessible
    STATUS       current
    DESCRIPTION
        "In this table, you can query or configure whether to disable router port learning on a port."
    ::= { hwL2mcRouteLearnDisablePolicyCfgInfo 1 }
    
hwL2mcRouteLearnDisablePolicyCfgEntry OBJECT-TYPE
    SYNTAX       HWL2mcRouteLearnDisablePolicyCfgEntry
    MAX-ACCESS   not-accessible
    STATUS       current
    DESCRIPTION
        "An entry is created for each active VLAN or VSI in the device when disable router port learning on a port."
    INDEX { hwRouteLearnDisablePolicyPortType, hwRouteLearnDisablePolicyPortIfIndex, hwRouteLearnDisablePolicyPortPeId, hwRouteLearnDisablePolicyPortCeId,
            hwRouteLearnDisablePolicyPortEndCeId, hwRouteLearnDisablePolicyPeerAddress, hwRouteLearnDisablePolicyVcOrSiteId,hwRouteLearnDisablePolicyVlanIndex, 
            hwRouteLearnDisablePolicyEndVlanIndex, hwRouteLearnDisablePolicyVsiName
            }
    ::= { hwL2mcRouteLearnDisablePolicyCfgTable 1 } 
     
HWL2mcRouteLearnDisablePolicyCfgEntry ::= SEQUENCE { 
    hwRouteLearnDisablePolicyPortType       HWPortType,
    hwRouteLearnDisablePolicyPortIfIndex    InterfaceIndexOrZero,
    hwRouteLearnDisablePolicyPortPeId       VlanIdOrAny,
    hwRouteLearnDisablePolicyPortCeId       VlanIdOrAny,
    hwRouteLearnDisablePolicyPortEndCeId    VlanIdOrAny,
    hwRouteLearnDisablePolicyPeerAddress    IpAddress,
    hwRouteLearnDisablePolicyVcOrSiteId     Unsigned32, 
    hwRouteLearnDisablePolicyVlanIndex      VlanIdOrAny,
    hwRouteLearnDisablePolicyEndVlanIndex   VlanIdOrAny,
    hwRouteLearnDisablePolicyVsiName        DisplayString,
    hwRouteLearnDisablePolicyRowStatus      RowStatus
    }
    
    
hwRouteLearnDisablePolicyPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcRouteLearnDisablePolicyCfgEntry 1 }
    
hwRouteLearnDisablePolicyPortIfIndex OBJECT-TYPE
    SYNTAX       InterfaceIndexOrZero
    MAX-ACCESS   not-accessible
    STATUS       current
    DESCRIPTION
        "The interface index. The value 0 indicates that the interface index is invalid."
    ::= { hwL2mcRouteLearnDisablePolicyCfgEntry 2 }
    
hwRouteLearnDisablePolicyPortPeId OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcRouteLearnDisablePolicyCfgEntry 3 }
    
hwRouteLearnDisablePolicyPortCeId OBJECT-TYPE
    SYNTAX       VlanIdOrAny
    MAX-ACCESS   not-accessible
    STATUS       current
    DESCRIPTION
        "The CE VID of an interface.
                The value ranges from 1 to 4095.
                The value 4095 indicates that the CE VID is invalid.
                "
    ::= { hwL2mcRouteLearnDisablePolicyCfgEntry 4 }

hwRouteLearnDisablePolicyPortEndCeId OBJECT-TYPE
    SYNTAX       VlanIdOrAny
    MAX-ACCESS   not-accessible
    STATUS       current
    DESCRIPTION
        "The CE VID of an interface.
                The value ranges from 1 to 4095.
                The value 4095 indicates that the CE VID is invalid.
                "
    ::= { hwL2mcRouteLearnDisablePolicyCfgEntry 5 }

hwRouteLearnDisablePolicyPeerAddress OBJECT-TYPE
    SYNTAX       IpAddress
    MAX-ACCESS   not-accessible
    STATUS       current
    DESCRIPTION
        "The peer IP address of a PW interface. The value 0.0.0.0 indicates that the IP address is invalid."
    ::= { hwL2mcRouteLearnDisablePolicyCfgEntry 6 }
    
hwRouteLearnDisablePolicyVcOrSiteId OBJECT-TYPE
    SYNTAX       Unsigned32(1..4294967295) 
    MAX-ACCESS   not-accessible
    STATUS       current
    DESCRIPTION
        "The VC ID or SITE ID of a PW interface."
    ::= { hwL2mcRouteLearnDisablePolicyCfgEntry 7 }
    
hwRouteLearnDisablePolicyVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcRouteLearnDisablePolicyCfgEntry 8 }
    
hwRouteLearnDisablePolicyEndVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcRouteLearnDisablePolicyCfgEntry 9 }

hwRouteLearnDisablePolicyVsiName OBJECT-TYPE
    SYNTAX       DisplayString(SIZE (0..31))
    MAX-ACCESS   not-accessible
    STATUS       current
    DESCRIPTION
        "The name of a VSI. If a VLAN is specified, the value is 32."
    ::= { hwL2mcRouteLearnDisablePolicyCfgEntry 10 }    
    
hwRouteLearnDisablePolicyRowStatus OBJECT-TYPE
    SYNTAX       RowStatus
    MAX-ACCESS   read-create
    STATUS       current
    DESCRIPTION
        "The row status."
    ::= { hwL2mcRouteLearnDisablePolicyCfgEntry 100 }  
    


--
--  The hwL2mcTrackVRRPCfgInfo group.
--
hwL2mcTrackVRRPCfgInfo     
        OBJECT IDENTIFIER ::= { hwIgspMibObject 27 }

hwL2mcTrackVRRPCfgTable OBJECT-TYPE
    SYNTAX       SEQUENCE OF HWL2mcTrackVRRPCfgEntry
    MAX-ACCESS   not-accessible
    STATUS       current
    DESCRIPTION
        "In this table, you can query or configure a port to track VRRP."
    ::= { hwL2mcTrackVRRPCfgInfo 1 }
    
hwL2mcTrackVRRPCfgEntry OBJECT-TYPE
    SYNTAX       HWL2mcTrackVRRPCfgEntry
    MAX-ACCESS   not-accessible
    STATUS       current
    DESCRIPTION
        "An entry is created for each active VLAN or VSI in the device when configure a port to track VRRP."
    INDEX {  hwTrackVRRPPortType, hwTrackVRRPPortIfIndex, hwTrackVRRPPortPeId, hwTrackVRRPPortCeId,
            hwTrackVRRPPortEndCeId, hwTrackVRRPVlanIndex, hwTrackVRRPEndVlanIndex, hwTrackVRRPVsiName
            }
    ::= { hwL2mcTrackVRRPCfgTable 1 } 
     
HWL2mcTrackVRRPCfgEntry ::= SEQUENCE { 
    hwTrackVRRPPortType       HWPortType,
    hwTrackVRRPPortIfIndex    InterfaceIndexOrZero,
    hwTrackVRRPPortPeId       VlanIdOrAny,
    hwTrackVRRPPortCeId       VlanIdOrAny,
    hwTrackVRRPPortEndCeId    VlanIdOrAny,
    hwTrackVRRPVlanIndex      VlanIdOrAny,
    hwTrackVRRPEndVlanIndex   VlanIdOrAny,
    hwTrackVRRPVsiName        DisplayString,
    hwTrackVRRPVridIfIndex    InterfaceIndexOrZero,
    hwTrackVRRPVridID         Unsigned32,
    hwTrackVRRPRowStatus      RowStatus
    }
    
    
hwTrackVRRPPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcTrackVRRPCfgEntry 1 }
    
hwTrackVRRPPortIfIndex OBJECT-TYPE
    SYNTAX       InterfaceIndexOrZero
    MAX-ACCESS   not-accessible
    STATUS       current
    DESCRIPTION
        "The interface index. The value 0 indicates that the interface index is invalid."
    ::= { hwL2mcTrackVRRPCfgEntry 2 }
    
hwTrackVRRPPortPeId OBJECT-TYPE
    SYNTAX       VlanIdOrAny
    MAX-ACCESS   not-accessible
    STATUS       current
    DESCRIPTION
        "The PE VID of an interface.
                The value ranges from 1 to 4095.
                The value 4095 indicates that the PE VID is invalid.
                "
    ::= { hwL2mcTrackVRRPCfgEntry 3 }
    
hwTrackVRRPPortCeId OBJECT-TYPE
    SYNTAX       VlanIdOrAny
    MAX-ACCESS   not-accessible
    STATUS       current
    DESCRIPTION
        "The CE VID of an interface.
                The value ranges from 1 to 4095.
                The value 4095 indicates that the CE VID is invalid.
                "
    ::= { hwL2mcTrackVRRPCfgEntry 4 }

hwTrackVRRPPortEndCeId OBJECT-TYPE
    SYNTAX       VlanIdOrAny
    MAX-ACCESS   not-accessible
    STATUS       current
    DESCRIPTION
        "The CE VID of an interface.
                The value ranges from 1 to 4095.
                The value 4095 indicates that the CE VID is invalid.
                "
    ::= { hwL2mcTrackVRRPCfgEntry 5 }

hwTrackVRRPVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcTrackVRRPCfgEntry 6 }
    
hwTrackVRRPEndVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcTrackVRRPCfgEntry 7 }

hwTrackVRRPVsiName OBJECT-TYPE
    SYNTAX       DisplayString(SIZE (0..31))
    MAX-ACCESS   not-accessible
    STATUS       current
    DESCRIPTION
        "The name of a VSI. If a VLAN is specified, the value is 32."
    ::= { hwL2mcTrackVRRPCfgEntry 8 }

hwTrackVRRPVridIfIndex OBJECT-TYPE
    SYNTAX       InterfaceIndexOrZero
    MAX-ACCESS   read-create
    STATUS       current
    DESCRIPTION
        "The interface index. The value 0 indicates that the interface index is invalid."
    ::= { hwL2mcTrackVRRPCfgEntry 9 }

hwTrackVRRPVridID OBJECT-TYPE
    SYNTAX       Unsigned32
    MAX-ACCESS   read-create
    STATUS       current
    DESCRIPTION
        "The VRRP VRID."
    ::= { hwL2mcTrackVRRPCfgEntry 10 }

hwTrackVRRPRowStatus OBJECT-TYPE
    SYNTAX       RowStatus
    MAX-ACCESS   read-create
    STATUS       current
    DESCRIPTION
        "The row status."
    ::= { hwL2mcTrackVRRPCfgEntry 100 }  
    

--
--  The hwL2mcMInstCfgInfo group.
--
hwL2mcMInstCfgInfo     
        OBJECT IDENTIFIER ::= { hwIgspMibObject 28 }

hwL2mcMInstCfgTable OBJECT-TYPE
    SYNTAX       SEQUENCE OF HWL2mcMInstCfgEntry
    MAX-ACCESS   not-accessible
    STATUS       current
    DESCRIPTION
        "This table create or modified multicast Instance."
    ::= { hwL2mcMInstCfgInfo 1 }
    
hwL2mcMInstCfgEntry OBJECT-TYPE
    SYNTAX       HWL2mcMInstCfgEntry
    MAX-ACCESS   not-accessible
    STATUS       current
    DESCRIPTION
        "An entry is created for each active VLAN or VSI in the device when disable router port learning on a port."
    INDEX {  hwL2mcMInstId
            }
    ::= { hwL2mcMInstCfgTable 1 } 
     
HWL2mcMInstCfgEntry ::= SEQUENCE { 
    hwL2mcMInstId             Unsigned32,
    hwL2mcMInstVlanIndex      VlanIdOrAnyOrNone,
    hwL2mcMInstVsiName        DisplayString,
    hwL2mcMInstProtectInst    Unsigned32,
    hwL2mcMInstRowStatus      RowStatus
    }
    
hwL2mcMInstId OBJECT-TYPE
    SYNTAX       Unsigned32(1..32)
    MAX-ACCESS   not-accessible
    STATUS       current
    DESCRIPTION
        "L2 multicast instance ID"
    ::= { hwL2mcMInstCfgEntry 1 }
    
hwL2mcMInstVlanIndex OBJECT-TYPE
    SYNTAX       VlanIdOrAnyOrNone
    MAX-ACCESS   read-create
    STATUS       current
    DESCRIPTION
        "Multicast-VLAN ID"
    ::= { hwL2mcMInstCfgEntry 2 }
    
hwL2mcMInstVsiName OBJECT-TYPE
    SYNTAX       DisplayString(SIZE (0..31))
    MAX-ACCESS   read-create
    STATUS       current
    DESCRIPTION
        "Multicast-VSI name"
    ::= { hwL2mcMInstCfgEntry 3 }

hwL2mcMInstProtectInst OBJECT-TYPE
    SYNTAX       Unsigned32(1..32)
    MAX-ACCESS   read-create
    STATUS       current
    DESCRIPTION
        "L2 multicast protect instance ID"
    ::= { hwL2mcMInstCfgEntry 4 }
    
hwL2mcMInstRowStatus OBJECT-TYPE
    SYNTAX       RowStatus
    MAX-ACCESS   read-create
    STATUS       current
    DESCRIPTION
        "The row status."
    ::= { hwL2mcMInstCfgEntry 100 }


hwL2mcMInstGroupCfgTable OBJECT-TYPE
    SYNTAX       SEQUENCE OF HWL2mcMInstGroupCfgEntry
    MAX-ACCESS   not-accessible
    STATUS       current
    DESCRIPTION
        "Thist table configure multicast instance mulitcast group infomation."
    ::= { hwL2mcMInstCfgInfo 2 }
    
hwL2mcMInstGroupCfgEntry OBJECT-TYPE
    SYNTAX       HWL2mcMInstGroupCfgEntry
    MAX-ACCESS   not-accessible
    STATUS       current
    DESCRIPTION
        "."
    INDEX {  hwL2mcMInstGroupId, hwL2mcMInstGroupAddress, hwL2mcMinstGroupAddressMask
            }
    ::= { hwL2mcMInstGroupCfgTable 1 } 

HWL2mcMInstGroupCfgEntry ::= SEQUENCE { 
    hwL2mcMInstGroupId        Unsigned32,
    hwL2mcMInstGroupAddress   IpAddress,
    hwL2mcMinstGroupAddressMask IpAddress,
    hwL2mcMInstGroupRowStatus RowStatus
    }
    
hwL2mcMInstGroupId OBJECT-TYPE
    SYNTAX       Unsigned32(1..32)
    MAX-ACCESS   not-accessible
    STATUS       current
    DESCRIPTION
        "L2 multicast instance ID"
    ::= { hwL2mcMInstGroupCfgEntry 1 }
    
hwL2mcMInstGroupAddress OBJECT-TYPE
    SYNTAX       IpAddress
    MAX-ACCESS   not-accessible
    STATUS       current
    DESCRIPTION
        "Group address."
    ::= { hwL2mcMInstGroupCfgEntry 2 }
    
hwL2mcMinstGroupAddressMask OBJECT-TYPE
    SYNTAX       IpAddress
    MAX-ACCESS   not-accessible
    STATUS       current
    DESCRIPTION
        "Group address."
    ::= { hwL2mcMInstGroupCfgEntry 3 }

hwL2mcMInstGroupRowStatus OBJECT-TYPE
    SYNTAX       RowStatus
    MAX-ACCESS   read-create
    STATUS       current
    DESCRIPTION
        "The row status."
    ::= { hwL2mcMInstGroupCfgEntry 100 }


hwL2mcMInstUserCfgTable OBJECT-TYPE
    SYNTAX       SEQUENCE OF HWL2mcMInstUserCfgEntry
    MAX-ACCESS   not-accessible
    STATUS       current
    DESCRIPTION
        "User instance in the multicast instance."
    ::= { hwL2mcMInstCfgInfo 3 }
    
hwL2mcMInstUserCfgEntry OBJECT-TYPE
    SYNTAX       HWL2mcMInstUserCfgEntry
    MAX-ACCESS   not-accessible
    STATUS       current
    DESCRIPTION
        "."
    INDEX {  hwL2mcMInstUserMInstId, hwL2mcMInstUserVLANID, hwL2mcMInstUserEndVLANID, hwL2mcMInstUserVSIName
            }
    ::= { hwL2mcMInstUserCfgTable 1 } 

HWL2mcMInstUserCfgEntry ::= SEQUENCE { 
    hwL2mcMInstUserMInstId       Unsigned32,
    hwL2mcMInstUserVLANID        VlanIdOrAnyOrNone,
    hwL2mcMInstUserEndVLANID     VlanIdOrAnyOrNone,
    hwL2mcMInstUserVSIName       DisplayString,
    hwL2mcMInstUserRowStatus        RowStatus
    }
    
hwL2mcMInstUserMInstId OBJECT-TYPE
    SYNTAX       Unsigned32(1..32)
    MAX-ACCESS   not-accessible
    STATUS       current
    DESCRIPTION
        "L2 multicast instance ID"
    ::= { hwL2mcMInstUserCfgEntry 1 }
    
hwL2mcMInstUserVLANID OBJECT-TYPE
    SYNTAX       VlanIdOrAnyOrNone
    MAX-ACCESS   not-accessible
    STATUS       current
    DESCRIPTION
        "User VLAN ID."
    ::= { hwL2mcMInstUserCfgEntry 2 }

hwL2mcMInstUserEndVLANID OBJECT-TYPE
    SYNTAX       VlanIdOrAnyOrNone
    MAX-ACCESS   not-accessible
    STATUS       current
    DESCRIPTION
        "User End VLAN ID."
    ::= { hwL2mcMInstUserCfgEntry 3 }

hwL2mcMInstUserVSIName OBJECT-TYPE
    SYNTAX       DisplayString(SIZE (0..31))
    MAX-ACCESS   not-accessible
    STATUS       current
    DESCRIPTION
        "VSI name."
    ::= { hwL2mcMInstUserCfgEntry 4 }

hwL2mcMInstUserRowStatus OBJECT-TYPE
    SYNTAX       RowStatus
    MAX-ACCESS   read-create
    STATUS       current
    DESCRIPTION
        "The row status."
    ::= { hwL2mcMInstUserCfgEntry 100 }

--
--  The hwL2mcStaticGroupCfgInfo group.
--
hwL2mcStaticGroupCfgInfo     
        OBJECT IDENTIFIER ::= { hwIgspMibObject 29 }

hwL2mcStaticGroupCfgTable OBJECT-TYPE
    SYNTAX       SEQUENCE OF HWL2mcStaticGroupCfgEntry
    MAX-ACCESS   not-accessible
    STATUS       current
    DESCRIPTION
        "Table contains l2 multicast static group information
         for IGMP Snooping."
    ::= { hwL2mcStaticGroupCfgInfo 1 }
    
hwL2mcStaticGroupCfgEntry OBJECT-TYPE
    SYNTAX       HWL2mcStaticGroupCfgEntry
    MAX-ACCESS   not-accessible
    STATUS       current
    DESCRIPTION
        "An entry is created for each active VLAN or VSI in the device create a static group entry and delete when 
        a static group entry deleted."
    INDEX { hwStaticGroupCfgPortType, hwStaticGroupCfgPortIfIndex, hwStaticGroupCfgPortPeId, hwStaticGroupCfgPortPeIdEnd, hwStaticGroupCfgPortCeId, 
            hwStaticGroupCfgPortCeIdEnd, hwStaticGroupCfgPeerAddress, hwStaticGroupCfgVcOrSiteId, hwStaticGroupCfgVlanIndex, hwStaticGroupCfgVsiName,
            hwStaticGroupCfgGroupAddress, hwStaticGroupCfgSourceAddress }
    ::= { hwL2mcStaticGroupCfgTable 1 } 
     
HWL2mcStaticGroupCfgEntry ::= SEQUENCE { 
    hwStaticGroupCfgPortType       HWPortType,
    hwStaticGroupCfgPortIfIndex    InterfaceIndexOrZero,
    hwStaticGroupCfgPortPeId       VlanIdOrAny,
    hwStaticGroupCfgPortPeIdEnd    VlanIdOrAny,
    hwStaticGroupCfgPortCeId       VlanIdOrAny,
    hwStaticGroupCfgPortCeIdEnd    VlanIdOrAny,
    hwStaticGroupCfgPeerAddress    IpAddress,
    hwStaticGroupCfgVcOrSiteId     Unsigned32,
    hwStaticGroupCfgVlanIndex      VlanIdOrAny,
    hwStaticGroupCfgVsiName        DisplayString,
    hwStaticGroupCfgGroupAddress   IpAddress,
    hwStaticGroupCfgSourceAddress  IpAddress,     
    hwStaticGroupCfgRowStatus      RowStatus
    }

hwStaticGroupCfgPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcStaticGroupCfgEntry 1 }
    
hwStaticGroupCfgPortIfIndex OBJECT-TYPE
    SYNTAX       InterfaceIndexOrZero
    MAX-ACCESS   not-accessible
    STATUS       current
    DESCRIPTION
        "The interface index. The value 0 indicates that the interface index is invalid."
    ::= { hwL2mcStaticGroupCfgEntry 2 }
    
hwStaticGroupCfgPortPeId OBJECT-TYPE
    SYNTAX       VlanIdOrAny
    MAX-ACCESS   not-accessible
    STATUS       current
    DESCRIPTION
        "The begin of a PE VID batch.
                The value ranges from 1 to 4095.
                The value 4095 indicates that the PE VID is invalid.
                "
    ::= { hwL2mcStaticGroupCfgEntry 3 }  
    
hwStaticGroupCfgPortPeIdEnd OBJECT-TYPE
    SYNTAX       VlanIdOrAny
    MAX-ACCESS   not-accessible
    STATUS       current
    DESCRIPTION
        "The end of a PE VID batch.
                The value ranges from 1 to 4095.
                The value 4095 indicates that the PE VID is invalid.
                "
    ::= { hwL2mcStaticGroupCfgEntry 4 }
    
hwStaticGroupCfgPortCeId OBJECT-TYPE
    SYNTAX       VlanIdOrAny
    MAX-ACCESS   not-accessible
    STATUS       current
    DESCRIPTION
        "The begin of a CE VID batch.
                The value ranges from 1 to 4095.
                The value 0 indicates that the PE VID is invalid.
                "
    ::= { hwL2mcStaticGroupCfgEntry 5 }
        
hwStaticGroupCfgPortCeIdEnd OBJECT-TYPE
    SYNTAX       VlanIdOrAny
    MAX-ACCESS   not-accessible
    STATUS       current
    DESCRIPTION
        "The end of a CE VID batch.
                The value ranges from 1 to 4095.
                The value 0 indicates that the PE VID is invalid.
                "
    ::= { hwL2mcStaticGroupCfgEntry 6 }
    
hwStaticGroupCfgPeerAddress OBJECT-TYPE
    SYNTAX       IpAddress
    MAX-ACCESS   not-accessible
    STATUS       current
    DESCRIPTION
        "The peer IP address of a PW interface. The value 0.0.0.0 indicates that the IP address is invalid."
    ::= { hwL2mcStaticGroupCfgEntry 7 }
    
hwStaticGroupCfgVcOrSiteId OBJECT-TYPE
    SYNTAX       Unsigned32(1..4294967295) 
    MAX-ACCESS   not-accessible
    STATUS       current
    DESCRIPTION
        "The VC ID or SITE ID of a PW interface."
    ::= { hwL2mcStaticGroupCfgEntry 8 }
    
hwStaticGroupCfgVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcStaticGroupCfgEntry 9 }
    
hwStaticGroupCfgVsiName OBJECT-TYPE
    SYNTAX       DisplayString(SIZE (0..31))
    MAX-ACCESS   not-accessible
    STATUS       current
    DESCRIPTION
        "The name of a VSI. If a VLAN is specified, the value is 32."
    ::= { hwL2mcStaticGroupCfgEntry 10 }    
    
hwStaticGroupCfgGroupAddress OBJECT-TYPE
    SYNTAX       IpAddress
    MAX-ACCESS   not-accessible
    STATUS       current
    DESCRIPTION
        "The group address of a multicast group. In the case of MAC forwarding, the group address is the smallest of 32 IP addresses."
    ::= { hwL2mcStaticGroupCfgEntry 11 }  
        
hwStaticGroupCfgSourceAddress OBJECT-TYPE
    SYNTAX       IpAddress
    MAX-ACCESS   not-accessible
    STATUS       current
    DESCRIPTION
        "The source IP address of a multicast group."
    ::= { hwL2mcStaticGroupCfgEntry 12 }

hwStaticGroupCfgRowStatus OBJECT-TYPE
    SYNTAX       RowStatus
    MAX-ACCESS   read-create
    STATUS       current
    DESCRIPTION
        "The row status."
    ::= { hwL2mcStaticGroupCfgEntry 100 }    

--
--  The hwL2mcPortGroupPolicyBatchCfgInfo group.
--
hwL2mcPortGroupPolicyBatchCfgInfo     
        OBJECT IDENTIFIER ::= { hwIgspMibObject 30 }

hwL2mcPortGroupPolicyBatchCfgTable OBJECT-TYPE
    SYNTAX       SEQUENCE OF HWL2mcPortGroupPolicyBatchCfgEntry
    MAX-ACCESS   not-accessible
    STATUS       current
    DESCRIPTION
        "In this table, you can query or configure a group policy to filter entries on a port."
    ::= { hwL2mcPortGroupPolicyBatchCfgInfo 1 }
    
hwL2mcPortGroupPolicyBatchCfgEntry OBJECT-TYPE
    SYNTAX       HWL2mcPortGroupPolicyBatchCfgEntry
    MAX-ACCESS   not-accessible
    STATUS       current
    DESCRIPTION
        "An entry is created for each active VLAN or VSI in the device when a group policy added."
    INDEX {  hwPortGroupPolicyCfgPortType, hwPortGroupPolicyCfgPortIfIndex, hwPortGroupPolicyCfgPortPeId, hwPortGroupPolicyCfgPortPeIdEnd,
             hwPortGroupPolicyCfgPortCeId, hwPortGroupPolicyCfgPortCeIdEnd, hwPortGroupPolicyCfgPeerAddress, hwPortGroupPolicyCfgVcOrSiteId,
             hwPortGroupPolicyCfgVlanIndex, hwPortGroupPolicyCfgVsiName
            }
    ::= { hwL2mcPortGroupPolicyBatchCfgTable 1 } 
     
HWL2mcPortGroupPolicyBatchCfgEntry ::= SEQUENCE { 
    hwPortGroupPolicyCfgPortType       HWPortType,
    hwPortGroupPolicyCfgPortIfIndex    InterfaceIndexOrZero,
    hwPortGroupPolicyCfgPortPeId       VlanIdOrAny,
    hwPortGroupPolicyCfgPortPeIdEnd    VlanIdOrAny,
    hwPortGroupPolicyCfgPortCeId       VlanIdOrAny,
    hwPortGroupPolicyCfgPortCeIdEnd    VlanIdOrAny,
    hwPortGroupPolicyCfgPeerAddress    IpAddress,
    hwPortGroupPolicyCfgVcOrSiteId     Unsigned32, 
    hwPortGroupPolicyCfgVlanIndex      VlanIdOrAny,
    hwPortGroupPolicyCfgVsiName        DisplayString,
    hwPortGroupPolicyCfgAclNum         Integer32, 
    hwPortGroupPolicyCfgIgmpVersion    INTEGER, 
    hwPortGroupPolicyCfgRowStatus      RowStatus
    }
    
    
hwPortGroupPolicyCfgPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcPortGroupPolicyBatchCfgEntry 1 }
    
hwPortGroupPolicyCfgPortIfIndex OBJECT-TYPE
    SYNTAX       InterfaceIndexOrZero
    MAX-ACCESS   not-accessible
    STATUS       current
    DESCRIPTION
        "The interface index. The value 0 indicates that the interface index is invalid."
    ::= { hwL2mcPortGroupPolicyBatchCfgEntry 2 }
    
hwPortGroupPolicyCfgPortPeId OBJECT-TYPE
    SYNTAX       VlanIdOrAny
    MAX-ACCESS   not-accessible
    STATUS       current
    DESCRIPTION
        "The begin of a PE VID batch.
                The value ranges from 1 to 4095.
                The value 4095 indicates that the PE VID is invalid.
                "
    ::= { hwL2mcPortGroupPolicyBatchCfgEntry 3 }  
    
hwPortGroupPolicyCfgPortPeIdEnd OBJECT-TYPE
    SYNTAX       VlanIdOrAny
    MAX-ACCESS   not-accessible
    STATUS       current
    DESCRIPTION
        "The end of a PE VID batch.
                The value ranges from 1 to 4095.
                The value 4095 indicates that the PE VID is invalid.
                "
    ::= { hwL2mcPortGroupPolicyBatchCfgEntry 4 }
    
hwPortGroupPolicyCfgPortCeId OBJECT-TYPE
    SYNTAX       VlanIdOrAny
    MAX-ACCESS   not-accessible
    STATUS       current
    DESCRIPTION
        "The begin of a CE VID batch.
                The value ranges from 1 to 4095.
                The value 4095 indicates that the PE VID is invalid.
                "
    ::= { hwL2mcPortGroupPolicyBatchCfgEntry 5 }
    
hwPortGroupPolicyCfgPortCeIdEnd OBJECT-TYPE
    SYNTAX       VlanIdOrAny
    MAX-ACCESS   not-accessible
    STATUS       current
    DESCRIPTION
         "The end of a CE VID batch.
                The value ranges from 1 to 4095.
                The value 4095 indicates that the PE VID is invalid.
                "
    ::= { hwL2mcPortGroupPolicyBatchCfgEntry 6 }
    
hwPortGroupPolicyCfgPeerAddress OBJECT-TYPE
    SYNTAX       IpAddress
    MAX-ACCESS   not-accessible
    STATUS       current
    DESCRIPTION
        "The peer IP address of a PW interface. The value 0.0.0.0 indicates that the IP address is invalid."
    ::= { hwL2mcPortGroupPolicyBatchCfgEntry 7 }
    
hwPortGroupPolicyCfgVcOrSiteId OBJECT-TYPE
    SYNTAX       Unsigned32(1..4294967295) 
    MAX-ACCESS   not-accessible
    STATUS       current
    DESCRIPTION
        "The VC ID or SITE ID of a PW interface."
    ::= { hwL2mcPortGroupPolicyBatchCfgEntry 8 }
    
hwPortGroupPolicyCfgVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcPortGroupPolicyBatchCfgEntry 9 }
    
hwPortGroupPolicyCfgVsiName OBJECT-TYPE
    SYNTAX       DisplayString(SIZE (0..31))
    MAX-ACCESS   not-accessible
    STATUS       current
    DESCRIPTION
        "The name of a VSI. If a VLAN is specified, the value is 32."
    ::= { hwL2mcPortGroupPolicyBatchCfgEntry 10 }    
    
hwPortGroupPolicyCfgAclNum OBJECT-TYPE
    SYNTAX       Integer32(0|2000..3999)
    MAX-ACCESS   read-create
    STATUS       current
    DESCRIPTION
        "The number of a basic ACL.
                The ACL number ranges from 2000 to 3999.
                The default value is 0, indicating that the value is invalid.
                "
    ::= { hwL2mcPortGroupPolicyBatchCfgEntry 11 }
    
hwPortGroupPolicyCfgIgmpVersion OBJECT-TYPE
    SYNTAX       INTEGER
            {
            versionAll(0),
            version1(1),
            version2(2),
            version3(3)
            }
    MAX-ACCESS   read-create
    STATUS       current
    DESCRIPTION
        "The IGMP version.
                The value ranges from 0 to 3.
                The default is 0, indicating that no version is specified.
                "
    ::= { hwL2mcPortGroupPolicyBatchCfgEntry 12 }
    
hwPortGroupPolicyCfgRowStatus OBJECT-TYPE
    SYNTAX       RowStatus
    MAX-ACCESS   read-create
    STATUS       current
    DESCRIPTION
        "The row status."
    ::= { hwL2mcPortGroupPolicyBatchCfgEntry 100 }  
    
    
--
--  The hwL2mcCACPortLimitInfo group.
--
hwL2mcCACPortLimitInfo     
        OBJECT IDENTIFIER ::= { hwIgspMibObject 31 }

hwL2mcCACPortLimitTable OBJECT-TYPE
    SYNTAX       SEQUENCE OF HWL2mcCACPortLimitEntry
    MAX-ACCESS   not-accessible
    STATUS       current
    DESCRIPTION
        "This table describes the configurations of IGMP snooping CAC on an interface."
    ::= { hwL2mcCACPortLimitInfo 1 }
    
hwL2mcCACPortLimitEntry OBJECT-TYPE
    SYNTAX       HWL2mcCACPortLimitEntry
    MAX-ACCESS   not-accessible
    STATUS       current
    DESCRIPTION
        "An entry is created for each IGMP snooping CAC on an interface."
    INDEX { hwCACPortLimitVlanIndex, hwCACPortLimitVsiName, hwCACPortLimitPortType,
            hwCACPortLimitIfIndex, hwCACPortLimitPeId, hwCACPortLimitPeIdEnd, hwCACPortLimitCeId, hwCACPortLimitCeIdEnd, 
            hwCACPortLimitPeerAddress, hwCACPortLimitVcOrSiteId, hwCACPortLimitChnlName }
    ::= { hwL2mcCACPortLimitTable 1 } 
     
HWL2mcCACPortLimitEntry ::= SEQUENCE { 
    hwCACPortLimitVlanIndex      VlanIdOrAny,
    hwCACPortLimitVsiName        DisplayString,
    hwCACPortLimitPortType       HWPortType,
    hwCACPortLimitIfIndex        InterfaceIndexOrZero,
    hwCACPortLimitPeId           VlanIdOrAny,
    hwCACPortLimitPeIdEnd        VlanIdOrAny,
    hwCACPortLimitCeId           VlanIdOrAny,
    hwCACPortLimitCeIdEnd        VlanIdOrAny,
    hwCACPortLimitPeerAddress    IpAddress,
    hwCACPortLimitVcOrSiteId     Unsigned32, 
    hwCACPortLimitChnlName       DisplayString,
    hwCACPortLimitAcl            Integer32, 
    hwCACPortLimitMaxEntry       Integer32, 
    hwCACPortLimitEntryCnt       Counter32, 
    hwCACPortLimitMaxBandWidth   Integer32, 
    hwCACPortLimitBandWidth      Counter32, 
    hwCACPortLimitCfgRowStatus   RowStatus
    }
    
    
hwCACPortLimitVlanIndex OBJECT-TYPE
    SYNTAX       VlanIdOrAny
    MAX-ACCESS   not-accessible
    STATUS       current
    DESCRIPTION
        "The VLAN ID, which is the configuration index in a VLAN. If a VSI is specified, the value is 4095.
                The value ranges from 1 to 4095.
                "
    ::= { hwL2mcCACPortLimitEntry 1 }
    
hwCACPortLimitVsiName OBJECT-TYPE
    SYNTAX       DisplayString(SIZE (0..31))
    MAX-ACCESS   not-accessible
    STATUS       current
    DESCRIPTION
        "The name of a VSI. If a VLAN is specified, the value is 32."
    ::= { hwL2mcCACPortLimitEntry 2 }
    
hwCACPortLimitPortType OBJECT-TYPE
    SYNTAX       HWPortType
    MAX-ACCESS   not-accessible
    STATUS       current
    DESCRIPTION
        "The interface type:
                1: Invalid
                2: PW interface
                3: L2 interface
                4: Encapsulation sub-interface
                5: Termination sub-interface
                6: Interface Board
                7: Vlanif Port
                "
    ::= { hwL2mcCACPortLimitEntry 3 }
    
hwCACPortLimitIfIndex OBJECT-TYPE
    SYNTAX       InterfaceIndexOrZero
    MAX-ACCESS   not-accessible
    STATUS       current
    DESCRIPTION
        "The interface index. The value 0 indicates that the interface index is invalid."
    ::= { hwL2mcCACPortLimitEntry 4 }
    
hwCACPortLimitPeId OBJECT-TYPE
    SYNTAX       VlanIdOrAny
    MAX-ACCESS   not-accessible
    STATUS       current
    DESCRIPTION
        "The begin of a PE VID batch.
                The value ranges from 1 to 4095.
                The value 4095 indicates that the PE VID is invalid.
                "
    ::= { hwL2mcCACPortLimitEntry 5 }
hwCACPortLimitPeIdEnd OBJECT-TYPE
    SYNTAX       VlanIdOrAny
    MAX-ACCESS   not-accessible
    STATUS       current
    DESCRIPTION
        "The end of a PE VID batch.
                The value ranges from 1 to 4095.
                The value 4095 indicates that the PE VID is invalid.
                "
    ::= { hwL2mcCACPortLimitEntry 6 }
    
hwCACPortLimitCeId OBJECT-TYPE
    SYNTAX       VlanIdOrAny
    MAX-ACCESS   not-accessible
    STATUS       current
    DESCRIPTION
        "The begin of a CE VID batch.
                The value ranges from 1 to 4095.
                The value 4095 indicates that the PE VID is invalid.
                "
    ::= { hwL2mcCACPortLimitEntry 7 }
        
hwCACPortLimitCeIdEnd OBJECT-TYPE
    SYNTAX       VlanIdOrAny
    MAX-ACCESS   not-accessible
    STATUS       current
    DESCRIPTION
        "The end of a CE VID batch.
                The value ranges from 1 to 4095.
                The value 4095 indicates that the PE VID is invalid.
                "
    ::= { hwL2mcCACPortLimitEntry 8 }
    
hwCACPortLimitPeerAddress OBJECT-TYPE
    SYNTAX       IpAddress
    MAX-ACCESS   not-accessible
    STATUS       current
    DESCRIPTION
        "The peer IP address of a PW interface. The value 0.0.0.0 indicates that the IP address is invalid."
    ::= { hwL2mcCACPortLimitEntry 9 }
    
hwCACPortLimitVcOrSiteId OBJECT-TYPE
    SYNTAX       Unsigned32(1..4294967295) 
    MAX-ACCESS   not-accessible
    STATUS       current
    DESCRIPTION
        "The VC ID or SITE ID of a PW interface."
    ::= { hwL2mcCACPortLimitEntry 10 }
    
hwCACPortLimitChnlName OBJECT-TYPE
    SYNTAX       DisplayString(SIZE (0..31))
    MAX-ACCESS   not-accessible
    STATUS       current
    DESCRIPTION
        "The channel name."
    ::= { hwL2mcCACPortLimitEntry 11 }
    
hwCACPortLimitAcl OBJECT-TYPE
    SYNTAX       Integer32(0|2000..3999)
    MAX-ACCESS   read-create
    STATUS       current
    DESCRIPTION
        "The number of ACL for the multicast groups that do not need to be configured with CAC limit.
                The ACL number ranges from 2000 to 3999.
                The default value is 0, indicating that the number is invalid.
                "
    ::= { hwL2mcCACPortLimitEntry 12 }
    
hwCACPortLimitMaxEntry OBJECT-TYPE
    SYNTAX       Integer32(0..8000) 
    MAX-ACCESS   read-create
    STATUS       current
    DESCRIPTION
        "The maximum number of forwarding entries. The value 0 indicates that the number is invalid."
    ::= { hwL2mcCACPortLimitEntry 13 }
    
hwCACPortLimitEntryCnt OBJECT-TYPE
    SYNTAX       Counter32 
    MAX-ACCESS   read-only
    STATUS       current
    DESCRIPTION
        "The number of current forwarding entries."
    ::= { hwL2mcCACPortLimitEntry 14 }
    
hwCACPortLimitMaxBandWidth OBJECT-TYPE
    SYNTAX       Integer32(0..4194304)
    MAX-ACCESS   read-create
    STATUS       current
    DESCRIPTION
        "The maximum bandwidth. The value 0 indicates that the bandwidth is invalid."
    ::= { hwL2mcCACPortLimitEntry 15 }
    
hwCACPortLimitBandWidth OBJECT-TYPE
    SYNTAX       Counter32 
    MAX-ACCESS   read-only
    STATUS       current
    DESCRIPTION
        "The current bandwidth."
    ::= { hwL2mcCACPortLimitEntry 16 }
    
hwCACPortLimitCfgRowStatus OBJECT-TYPE
    SYNTAX       RowStatus
    MAX-ACCESS   read-create
    STATUS       current
    DESCRIPTION
        "The row status."
    ::= { hwL2mcCACPortLimitEntry 100 } 

--
--  The hwL2mcQinqGroupSourceLimitInfo group.
--
hwL2mcQinqGroupSourceLimitInfo     
        OBJECT IDENTIFIER ::= { hwIgspMibObject 32 }

hwL2mcQinqGroupLimitTable OBJECT-TYPE
    SYNTAX       SEQUENCE OF HWL2mcQinqGroupLimitEntry
    MAX-ACCESS   not-accessible
    STATUS       current
    DESCRIPTION
        "This table describes the configurations of IGMP snooping group limit on a QinQ interface."
    ::= { hwL2mcQinqGroupSourceLimitInfo 1 }
    
hwL2mcQinqGroupLimitEntry OBJECT-TYPE
    SYNTAX       HWL2mcQinqGroupLimitEntry
    MAX-ACCESS   not-accessible
    STATUS       current
    DESCRIPTION
        "An entry is created for each IGMP snooping group limit on a QinQ interface."
    INDEX { hwL2mcQinqGroupLimitPortType, hwL2mcQinqGroupLimitIfIndex, hwL2mcQinqGroupLimitPeVid,
            hwL2mcQinqGroupLimitPeVidEnd, hwL2mcQinqGroupLimitCeVid, hwL2mcQinqGroupLimitCeVidEnd }
    ::= { hwL2mcQinqGroupLimitTable 1 } 
     
HWL2mcQinqGroupLimitEntry ::= SEQUENCE { 
    hwL2mcQinqGroupLimitPortType       HWPortType,
    hwL2mcQinqGroupLimitIfIndex        InterfaceIndexOrZero,
    hwL2mcQinqGroupLimitPeVid          VlanIdOrAny,
    hwL2mcQinqGroupLimitPeVidEnd       VlanIdOrAny,
    hwL2mcQinqGroupLimitCeVid          VlanIdOrAny,
    hwL2mcQinqGroupLimitCeVidEnd       VlanIdOrAny,
    hwL2mcQinqGroupLimitNum            Unsigned32, 
    hwL2mcQinqGroupLimitRowStatus      RowStatus
    }

    
hwL2mcQinqGroupLimitPortType OBJECT-TYPE
    SYNTAX       HWPortType
    MAX-ACCESS   not-accessible
    STATUS       current
    DESCRIPTION
        "The interface type:
                1: Invalid
                5: Termination sub-interface
                "
    ::= { hwL2mcQinqGroupLimitEntry 1 }
    
hwL2mcQinqGroupLimitIfIndex OBJECT-TYPE
    SYNTAX       InterfaceIndexOrZero
    MAX-ACCESS   not-accessible
    STATUS       current
    DESCRIPTION
        "The interface index. The value 0 indicates that the interface index is invalid."
    ::= { hwL2mcQinqGroupLimitEntry 2 }
    
hwL2mcQinqGroupLimitPeVid OBJECT-TYPE
    SYNTAX       VlanIdOrAny
    MAX-ACCESS   not-accessible
    STATUS       current
    DESCRIPTION
        "The begin of a PE VID batch.
                The value ranges from 1 to 4095.
                The value 4095 indicates that the PE VID is invalid.
                "
    ::= { hwL2mcQinqGroupLimitEntry 3 }

hwL2mcQinqGroupLimitPeVidEnd OBJECT-TYPE
    SYNTAX       VlanIdOrAny
    MAX-ACCESS   not-accessible
    STATUS       current
    DESCRIPTION
        "The end of a PE VID batch.
                The value ranges from 1 to 4095.
                The value 4095 indicates that the PE VID is invalid.
                "
    ::= { hwL2mcQinqGroupLimitEntry 4 }
    
hwL2mcQinqGroupLimitCeVid OBJECT-TYPE
    SYNTAX       VlanIdOrAny
    MAX-ACCESS   not-accessible
    STATUS       current
    DESCRIPTION
        "The begin of a CE VID batch.
                The value ranges from 1 to 4095.
                The value 4095 indicates that the CE VID is invalid.
                "
    ::= { hwL2mcQinqGroupLimitEntry 5 }
        
hwL2mcQinqGroupLimitCeVidEnd OBJECT-TYPE
    SYNTAX       VlanIdOrAny
    MAX-ACCESS   not-accessible
    STATUS       current
    DESCRIPTION
        "The end of a CE VID batch.
                The value ranges from 1 to 4095.
                The value 4095 indicates that the CE VID is invalid.
                "
    ::= { hwL2mcQinqGroupLimitEntry 6 }
    
hwL2mcQinqGroupLimitNum OBJECT-TYPE
    SYNTAX       Unsigned32(1..16000) 
    MAX-ACCESS   read-create
    STATUS       current
    DESCRIPTION
        "The group limit number of a QinQ interface."
    ::= { hwL2mcQinqGroupLimitEntry 10 }
    
hwL2mcQinqGroupLimitRowStatus OBJECT-TYPE
    SYNTAX       RowStatus
    MAX-ACCESS   read-create
    STATUS       current
    DESCRIPTION
        "The row status."
    ::= { hwL2mcQinqGroupLimitEntry 100 } 
    
hwL2mcQinqSourceLimitTable OBJECT-TYPE
    SYNTAX       SEQUENCE OF HWL2mcQinqSourceLimitEntry
    MAX-ACCESS   not-accessible
    STATUS       current
    DESCRIPTION
        "This table describes the configurations of IGMP snooping source limit on a QinQ interface."
    ::= { hwL2mcQinqGroupSourceLimitInfo 2 }
    
hwL2mcQinqSourceLimitEntry OBJECT-TYPE
    SYNTAX       HWL2mcQinqSourceLimitEntry
    MAX-ACCESS   not-accessible
    STATUS       current
    DESCRIPTION
        "An entry is created for each IGMP snooping source limit on a QinQ interface."
    INDEX { hwL2mcQinqSourceLimitPortType, hwL2mcQinqSourceLimitIfIndex, hwL2mcQinqSourceLimitPeVid,
            hwL2mcQinqSourceLimitPeVidEnd, hwL2mcQinqSourceLimitCeVid, hwL2mcQinqSourceLimitCeVidEnd }
    ::= { hwL2mcQinqSourceLimitTable 1 } 
     
HWL2mcQinqSourceLimitEntry ::= SEQUENCE { 
    hwL2mcQinqSourceLimitPortType       HWPortType,
    hwL2mcQinqSourceLimitIfIndex        InterfaceIndexOrZero,
    hwL2mcQinqSourceLimitPeVid          VlanIdOrAny,
    hwL2mcQinqSourceLimitPeVidEnd       VlanIdOrAny,
    hwL2mcQinqSourceLimitCeVid          VlanIdOrAny,
    hwL2mcQinqSourceLimitCeVidEnd       VlanIdOrAny,
    hwL2mcQinqSourceLimitNum            Unsigned32, 
    hwL2mcQinqSourceLimitRowStatus      RowStatus
    }

    
hwL2mcQinqSourceLimitPortType OBJECT-TYPE
    SYNTAX       HWPortType
    MAX-ACCESS   not-accessible
    STATUS       current
    DESCRIPTION
        "The interface type:
                1: Invalid
                5: Termination sub-interface
                "
    ::= { hwL2mcQinqSourceLimitEntry 1 }
    
hwL2mcQinqSourceLimitIfIndex OBJECT-TYPE
    SYNTAX       InterfaceIndexOrZero
    MAX-ACCESS   not-accessible
    STATUS       current
    DESCRIPTION
        "The interface index. The value 0 indicates that the interface index is invalid."
    ::= { hwL2mcQinqSourceLimitEntry 2 }
    
hwL2mcQinqSourceLimitPeVid OBJECT-TYPE
    SYNTAX       VlanIdOrAny
    MAX-ACCESS   not-accessible
    STATUS       current
    DESCRIPTION
        "The begin of a PE VID batch.
                The value ranges from 1 to 4095.
                The value 4095 indicates that the PE VID is invalid.
                "
    ::= { hwL2mcQinqSourceLimitEntry 3 }

hwL2mcQinqSourceLimitPeVidEnd OBJECT-TYPE
    SYNTAX       VlanIdOrAny
    MAX-ACCESS   not-accessible
    STATUS       current
    DESCRIPTION
        "The end of a PE VID batch.
                The value ranges from 1 to 4095.
                The value 4095 indicates that the PE VID is invalid.
                "
    ::= { hwL2mcQinqSourceLimitEntry 4 }
    
hwL2mcQinqSourceLimitCeVid OBJECT-TYPE
    SYNTAX       VlanIdOrAny
    MAX-ACCESS   not-accessible
    STATUS       current
    DESCRIPTION
        "The begin of a CE VID batch.
                The value ranges from 1 to 4095.
                The value 4095 indicates that the CE VID is invalid.
                "
    ::= { hwL2mcQinqSourceLimitEntry 5 }
        
hwL2mcQinqSourceLimitCeVidEnd OBJECT-TYPE
    SYNTAX       VlanIdOrAny
    MAX-ACCESS   not-accessible
    STATUS       current
    DESCRIPTION
        "The end of a CE VID batch.
                The value ranges from 1 to 4095.
                The value 4095 indicates that the CE VID is invalid.
                "
    ::= { hwL2mcQinqSourceLimitEntry 6 }
    
hwL2mcQinqSourceLimitNum OBJECT-TYPE
    SYNTAX       Unsigned32(1..16000) 
    MAX-ACCESS   read-create
    STATUS       current
    DESCRIPTION
        "The source number of a QinQ interface."
    ::= { hwL2mcQinqSourceLimitEntry 10 }
    
hwL2mcQinqSourceLimitRowStatus OBJECT-TYPE
    SYNTAX       RowStatus
    MAX-ACCESS   read-create
    STATUS       current
    DESCRIPTION
        "The row status."
    ::= { hwL2mcQinqSourceLimitEntry 100 } 

--
-- Conformance Information
--
hwL2mcMibConformance OBJECT IDENTIFIER ::= { hwL2MultiCastMIB 100 }
hwL2mcMibCompliances OBJECT IDENTIFIER ::= { hwL2mcMibConformance 1 }
hwL2mcMibGroups      OBJECT IDENTIFIER ::= { hwL2mcMibConformance 2 }

hwIgspMibCompliance       MODULE-COMPLIANCE
        STATUS current
        DESCRIPTION
            "The compliance statement for device supporting
             IGMP Snooping."
        MODULE 
        MANDATORY-GROUPS{   
                hwIgspSystemInfoGroup,
                hwL2mcCfgInfoGroup,
                hwL2mcStatisticsInfoGroup,
                hwL2mcFwdInfoGroup,
                hwL2mcGroupInfoGroup,
                hwL2mcGroupCfgInfoGroup,
                hwL2mcSsmSourceInfoGroup,
                hwL2mcPortGroupPolicyCfgInfoGroup,
                hwL2mcChnlCfgInfoGroup,
                hwL2mcLimitInfoGroup,
                hwL2mcPortLimitInfoGroup,
                hwL2mcFastChnlCfgInfoGroup,
                hwL2mcRouterPortInfoGroup,
                hwL2mcRouterPortCfgInfoGroup,
                hwL2mcChnlGroupCfgInfoGroup,
                hwL2mcGroupPolicyCfgInfoGroup,
                hwL2mcChnlDenyCfgInfoGroup,
                hwL2mcQinQPortInfoGroup,
                hwL2mcETrackingInfoInfoGroup,
                hwL2mcSourceGroupInfoGroup,
                hwL2mcDTFwdInfoGroup,
                hwL2mcDTGroupInfoGroup,
                hwL2mcMulticastTrafficPolicyCfgInfoGroup,
                hwL2mcRouteLearnDisablePolicyCfgInfoGroup,
                hwL2mcTrackVRRPCfgInfoGroup
                }          
        ::= { hwL2mcMibCompliances 1 }
        
hwIgspSystemInfoGroup OBJECT-GROUP
       OBJECTS {
                hwIgmpSnoopingEnabled,
                hwSendQueryEnabled,
                hwSendQuerySourceIpAddr,
                hwL2mcCacTrapInterval,
                hwL2mcPerformanceStatisticsInterval
               }
        STATUS current
        DESCRIPTION
            "."
        ::= { hwL2mcMibGroups 1 }
        
hwL2mcCfgInfoGroup OBJECT-GROUP
       OBJECTS {
                hwL2mcEnabled,
                hwL2mcRouterAgingTime,
                hwL2mcMaxQueryRespTime,
                hwL2mcLastMemQueryInterval,
                hwL2mcQueryInterval,
                hwL2mcRobustCount,
                hwL2mcCheckRouterAlert,
                hwL2mcSendRouterAlert,
                hwL2mcIgmpVersion,
                hwL2mcFwdMode,
                hwL2mcPromptLeaveEnable,
                hwL2mcPromptLeaveAclNum,
                hwL2mcRouterPortLearningEnable,
                hwL2mcReportSuppressEnable,
                hwL2mcIgmpQuerierEnable,
                hwL2mcIgmpSsmMappingEnable,
                hwL2mcSsmAclNum,
                hwL2mcProxyRouterProtocolPass,
                hwL2mcAsmSsmFlag,
                hwL2mcSrcLifeTime,
                hwL2mcPerformanceStatistics,
                hwL2mcQuerierElection,
                hwETrackEnable,
                hwL2mcBackupQueryFwd,
                hwL2mcBackupReportFwd,
                hwL2mcQuerySuppress,
                hwL2mcRtLearnRingLinkage,
                hwL2mcRowStatus
               }
        STATUS current
        DESCRIPTION
            "."
        ::= { hwL2mcMibGroups 2 }

hwL2mcStatisticsInfoGroup OBJECT-GROUP
       OBJECTS {                                  
                hwL2mcRecvIgmpV1ReportNum,
                hwL2mcRecvIgmpV2ReportNum,
                hwL2mcRecvIgmpV3ReportNum,
                hwL2mcRecvIgmpLeaveNum,
                hwL2mcRecvIgmpV1QueryNum,
                hwL2mcRecvIgmpV2QueryNum,
                hwL2mcRecvIgmpV3QueryNum,
                hwL2mcRecvPimHelloNum,
                hwL2mcSendQueryNum,
                hwL2mcSendQuerySourceNum,
                hwL2mcProxyGenQueryNum,
                hwL2mcProxyGroupQueryNum,
                hwL2mcProxyGroupSourceQueryNum,
                hwL2mcIgmpPacketClearStats
               }                                  
        STATUS current                            
        DESCRIPTION                               
            "."                                   
        ::= { hwL2mcMibGroups 3 } 
        
hwL2mcFwdInfoGroup OBJECT-GROUP
       OBJECTS {       
               hwL2mcFwdAddressType,                           
                hwL2mcFwdHostFlag1,        
                hwL2mcFwdHostFlag2,        
                hwL2mcFwdHostFlag3,
                hwL2mcFwdHostFlag4
               }                                  
        STATUS current                            
        DESCRIPTION                               
            "."                                   
        ::= { hwL2mcMibGroups 4 }                   

hwL2mcGroupInfoGroup OBJECT-GROUP
       OBJECTS {                                  
                hwL2mcSourceUpTime,
                hwL2mcSourceExpires,
                hwL2mcGroupUpTime,
                hwL2mcGroupExpires,
                hwL2mcGroupFilterFlag,
                hwL2mcGroupHostFlag1,
                hwL2mcGroupHostFlag2,
                hwL2mcGroupRowStatus   
               }                                  
        STATUS current                            
        DESCRIPTION                               
            "."                                   
        ::= { hwL2mcMibGroups 5 } 


hwL2mcGroupCfgInfoGroup OBJECT-GROUP
       OBJECTS {                                  
                hwGroupCfgRowStatus
               }                                  
        STATUS current                            
        DESCRIPTION                               
            "."                                   
        ::= { hwL2mcMibGroups 6 } 

hwL2mcSsmSourceInfoGroup OBJECT-GROUP
       OBJECTS {                                  
                hwL2mcSsmSourceRowStatus
               }                                  
        STATUS current                            
        DESCRIPTION                               
            "."                                   
        ::= { hwL2mcMibGroups 7 } 
        
hwL2mcPortGroupPolicyCfgInfoGroup OBJECT-GROUP
       OBJECTS {                                  
                hwPortGroupPolicyAclNum,
                hwPortGroupPolicyIgmpVersion,
                hwPortGroupPolicyRowStatus
               }                                  
        STATUS current                            
        DESCRIPTION                               
            "."                                   
        ::= { hwL2mcMibGroups 8 }

hwL2mcChnlCfgInfoGroup OBJECT-GROUP
       OBJECTS {                                  
                hwChnlCfgChnlType,
                hwChnlCfgRowStatus
               }                                  
        STATUS current                            
        DESCRIPTION                               
            "."                                   
        ::= { hwL2mcMibGroups 9 }
        
hwL2mcLimitInfoGroup OBJECT-GROUP
       OBJECTS {                                  
                hwL2mcLimitMaxEntry,
                hwL2mcLimitEntryCnt,
                hwL2mcLimitMaxBandWidth,
                hwL2mcLimitBandWidth,
                hwL2mcLimitAcl,
                hwL2mcLimitCfgRowStatus
               }                                  
        STATUS current                            
        DESCRIPTION                               
            "."                                   
        ::= { hwL2mcMibGroups 10 }   

hwL2mcPortLimitInfoGroup OBJECT-GROUP
       OBJECTS {
                hwPortLimitAcl,                                  
                hwPortLimitMaxEntry,
                hwPortLimitEntryCnt,
                hwPortLimitMaxBandWidth,
                hwPortLimitBandWidth,
                hwPortLimitCfgRowStatus
               }                                  
        STATUS current                            
        DESCRIPTION                               
            "."                                   
        ::= { hwL2mcMibGroups 11 } 
             
 
hwL2mcFastChnlCfgInfoGroup OBJECT-GROUP
       OBJECTS {
                hwL2mcFastChnlCfgRowStatus
               }                                  
        STATUS current                            
        DESCRIPTION                               
            "."                                   
        ::= { hwL2mcMibGroups 12 } 
        
        
hwL2mcRouterPortInfoGroup OBJECT-GROUP
       OBJECTS {
                hwL2mcRouterPortGroupUpTime,
                hwL2mcRouterPortGroupExpires,
                hwL2mcRouterPortGroupHostFlag1
               }                                  
        STATUS current                            
        DESCRIPTION                               
            "."                                   
        ::= { hwL2mcMibGroups 13 }         

hwL2mcRouterPortCfgInfoGroup OBJECT-GROUP
       OBJECTS {
                hwL2mcRouterPortCfgRowStatus 
               }                                  
        STATUS current                            
        DESCRIPTION                               
            "."                                   
        ::= { hwL2mcMibGroups 14 }         

hwL2mcChnlGroupCfgInfoGroup OBJECT-GROUP
       OBJECTS {
                hwChnlGroupCfgPerBand,
                hwChnlGroupCfgRowStatus  
               }                                  
        STATUS current                            
        DESCRIPTION                               
            "."                                   
        ::= { hwL2mcMibGroups 15 }        

hwL2mcGroupPolicyCfgInfoGroup OBJECT-GROUP
       OBJECTS {
                hwGroupPolicyAclNum,
                hwGroupPolicyIgmpVersion,
                hwGroupPolicyRowStatus  
               }                                  
        STATUS current                            
        DESCRIPTION                               
            "."                                   
        ::= { hwL2mcMibGroups 16}  
        
hwL2mcChnlDenyCfgInfoGroup   OBJECT-GROUP
       OBJECTS {
                hwChnlDenyCfg ,
                hwChnlDenyCfgRowStatus 
               } 
        STATUS current
        DESCRIPTION 
            "."  
        ::= { hwL2mcMibGroups 17}              

hwL2mcQinQPortInfoGroup OBJECT-GROUP
       OBJECTS {
                hwQinQPortTime ,
                hwQinQPortFlag 
               }      
        STATUS current    
        DESCRIPTION        
            "."                  
        ::= { hwL2mcMibGroups 18}

hwL2mcETrackingInfoInfoGroup OBJECT-GROUP
       OBJECTS {
                hwETrackInfoFlag
               }      
        STATUS current    
        DESCRIPTION        
            "."                  
        ::= { hwL2mcMibGroups 19}         

hwL2mcSourceGroupInfoGroup OBJECT-GROUP
       OBJECTS {
                hwL2mcSourceGroupStat
               }      
        STATUS current    
        DESCRIPTION        
            "."                  
        ::= { hwL2mcMibGroups 22}       
        
hwL2mcDTFwdInfoGroup OBJECT-GROUP
       OBJECTS {       
               hwL2mcDTFwdAddressType,                           
                hwL2mcDTFwdHostFlag1,        
                hwL2mcDTFwdHostFlag2,        
                hwL2mcDTFwdHostFlag3,
                hwL2mcDTFwdHostFlag4
               }                                  
        STATUS current                            
        DESCRIPTION                               
            "."                                   
        ::= { hwL2mcMibGroups 23 }                   

hwL2mcDTGroupInfoGroup OBJECT-GROUP
       OBJECTS {                                  
                hwL2mcDTSourceUpTime,
                hwL2mcDTSourceExpires,
                hwL2mcDTGroupUpTime,
                hwL2mcDTGroupExpires,
                hwL2mcDTGroupHostFlag1,
                hwL2mcDTGroupHostFlag2,
                hwL2mcDTGroupRowStatus   
               }                                  
        STATUS current                            
        DESCRIPTION                               
            "."                                   
        ::= { hwL2mcMibGroups 24 }              

hwL2mcMulticastTrafficPolicyCfgInfoGroup OBJECT-GROUP
       OBJECTS {                                  
                hwMulticastTrafficPolicyRowStatus   
               }                                  
        STATUS current                            
        DESCRIPTION                               
            "."                                   
        ::= { hwL2mcMibGroups 25 } 

hwL2mcRouteLearnDisablePolicyCfgInfoGroup OBJECT-GROUP
       OBJECTS {                                  
                hwRouteLearnDisablePolicyRowStatus   
               }                                  
        STATUS current                            
        DESCRIPTION                               
            "."                                   
        ::= { hwL2mcMibGroups 26 } 

hwL2mcTrackVRRPCfgInfoGroup OBJECT-GROUP
       OBJECTS {                                  
                 hwTrackVRRPVridIfIndex,
                 hwTrackVRRPVridID,
                 hwTrackVRRPRowStatus
               }
        STATUS current                            
        DESCRIPTION                               
            "."                                   
        ::= { hwL2mcMibGroups 27 } 

END
