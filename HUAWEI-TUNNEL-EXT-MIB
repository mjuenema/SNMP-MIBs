-- =================================================================
-- Copyright (C) 2009 by  HUAWEI TECHNOLOGIES. All rights reserved
-- 
-- Description: The HUAWEI-TUNNEL-EXT-MIB provides information about Ipv4 Over Ipv6.
--              
-- Reference:
-- Version:     V2.0
-- History:
--              luxiaogang,2010.1.15,private 
-- =================================================================
	HUAWEI-TUNNEL-EXT-MIB DEFINITIONS ::= BEGIN
 
		IMPORTS
			hwDatacomm			
				FROM HUAWEI-MIB			
			ifIndex, InterfaceIndex			
				FROM IF-MIB			
			OBJECT-GROUP, MODULE-COMPLIANCE			
				FROM SNMPv2-CONF			
			Integer32, OBJECT-TYPE, MODULE-IDENTITY			
				FROM SNMPv2-SMI;
	
	
		-- 1.3.6.1.4.1.2011.5.25.204
		hwTunnelExtMib MODULE-IDENTITY 
			LAST-UPDATED "200906231610Z"		-- June 23, 2009 at 16:10 GMT
			ORGANIZATION 
				"Huawei"
			CONTACT-INFO 
				" R&D BeiJing, Huawei Technologies co.,Ltd.
				Huawei Bld., Xinxi Rd., 
				Shang-Di Information Industry Base,
				Hai-Dian District Beijing P.R. China
				Zip:100085 
				Http://www.huawei.com                                       
				E-mail:winstan@huawei.com"
			DESCRIPTION 
				"The MIB module for entities implementing binding 
				type and TSU of tunnel."
			::= { hwDatacomm 204 }

		
	
	
--
-- Node definitions
--
	
		-- 1.3.6.1.4.1.2011.5.25.204.1
		hwTunnelExtMibObjects OBJECT IDENTIFIER ::= { hwTunnelExtMib 1 }

		
--  
-- Binding table
-- 
		-- 1.3.6.1.4.1.2011.5.25.204.1.1
		hwBindingTable OBJECT-TYPE
			SYNTAX SEQUENCE OF HwBindingEntry
			MAX-ACCESS not-accessible
			STATUS current
			DESCRIPTION
				"The tunnel binding table contains tunnel type and TSU
				information on the entity's loopback interfaces."
			::= { hwTunnelExtMibObjects 1 }

		
		-- 1.3.6.1.4.1.2011.5.25.204.1.1.1
		hwBindingEntry OBJECT-TYPE
			SYNTAX HwBindingEntry
			MAX-ACCESS not-accessible
			STATUS current
			DESCRIPTION
				"An binding entry containing objects
				about tunnel type and TSU information 
				on the entity's loopback interfaces."
			INDEX { hwLoopBackIfIndex }
			::= { hwBindingTable 1 }

		
		HwBindingEntry ::=
			SEQUENCE { 
				hwLoopBackIfIndex
					InterfaceIndex,
				hwBindingTunnel
					INTEGER,
				hwTargetBoard
					Integer32
			 }

		-- 1.3.6.1.4.1.2011.5.25.204.1.1.1.1
		hwLoopBackIfIndex OBJECT-TYPE
			SYNTAX InterfaceIndex
			MAX-ACCESS read-only
			STATUS current
			DESCRIPTION
				"This object identifies index of LoopBack interface."
			::= { hwBindingEntry 1 }

		
--  Tunnel type is Ipv4 Over Ipv6
-- Tunnel type is GRE
-- No tunnel type
		-- 1.3.6.1.4.1.2011.5.25.204.1.1.1.2
		hwBindingTunnel OBJECT-TYPE
			SYNTAX INTEGER
				{
				ipv4ipv6(1),
				gre(2),
				null(3)
				}
			MAX-ACCESS read-write
			STATUS current
			DESCRIPTION
				"This object identifies binding type of loopback interface.
				The ipv4ipv6(1) state indicates that current tunnel is a 
				ipv4 over ipv6 tunnel.The gre(2) state indicates that 
				current tunnel is a gre tunnel.The null(3) state indicates 
				that the interface has not binded tunnel."
			::= { hwBindingEntry 2 }

		
		-- 1.3.6.1.4.1.2011.5.25.204.1.1.1.3
		hwTargetBoard OBJECT-TYPE
			SYNTAX Integer32 (0..255)
			MAX-ACCESS read-write
			STATUS current
			DESCRIPTION
				"This object identifies TSU of tunnel."
			::= { hwBindingEntry 3 }

		
		-- 1.3.6.1.4.1.2011.5.25.204.2
		hwTunnelExtMibConformance OBJECT IDENTIFIER ::= { hwTunnelExtMib 2 }

		
		-- 1.3.6.1.4.1.2011.5.25.204.2.1
		hwBindingCompliances OBJECT IDENTIFIER ::= { hwTunnelExtMibConformance 1 }

		
--  this module
		-- 1.3.6.1.4.1.2011.5.25.204.2.1.1
		hwBindingCompliance MODULE-COMPLIANCE
			STATUS current
			DESCRIPTION 
				"The compliance statement for systems supporting 
				the HUAWEI-TUNNEL-EXT-MIB."
			MODULE -- this module
				MANDATORY-GROUPS { hwBindingGroup }
			::= { hwBindingCompliances 1 }

		
		-- 1.3.6.1.4.1.2011.5.25.204.2.2
		hwBindingGroups OBJECT IDENTIFIER ::= { hwTunnelExtMibConformance 2 }

		
		-- 1.3.6.1.4.1.2011.5.25.204.2.2.1
		hwBindingGroup OBJECT-GROUP
			OBJECTS { hwLoopBackIfIndex, hwBindingTunnel, hwTargetBoard }
			STATUS current
			DESCRIPTION 
				"The binding table member."
			::= { hwBindingGroups 1 }

		
	
	END


-- HUAWEI-TUNNEL-EXT-MIB.mib
