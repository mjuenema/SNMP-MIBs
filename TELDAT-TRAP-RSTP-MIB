-- file automatically created


TELDAT-TRAP-RSTP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


rstpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the RSTP event subsystem."
    REVISION "201401200930Z"
    DESCRIPTION "Initial implementation"
        ::= { telEventTraps 196 }


rstpEventsGroup	OBJECT IDENTIFIER	::= { rstpTrapsMIB 1 }

rstpNotifications	OBJECT IDENTIFIER	::= { rstpTrapsMIB 2 }
rstpNotificationsPrefix	OBJECT IDENTIFIER	::= { rstpNotifications 0 }

rstpEventObjects1 OBJECT-IDENTITY
    STATUS current
    DESCRIPTION
        "Event RSTP.1
        Port receive state machine transition."
    ::= { rstpEventsGroup 1 }

rstp1_state_machine OBJECT-TYPE
    SYNTAX DisplayString
    MAX-ACCESS accessible-for-notify
    STATUS current
    DESCRIPTION
        "Parameter 'state_machine' in event RSTP.1"
    ::= { rstpEventObjects1 1 }

rstp1_state OBJECT-TYPE
    SYNTAX DisplayString
    MAX-ACCESS accessible-for-notify
    STATUS current
    DESCRIPTION
        "Parameter 'state' in event RSTP.1"
    ::= { rstpEventObjects1 2 }

rstp1_bridge_id OBJECT-TYPE
    SYNTAX Integer32
    MAX-ACCESS accessible-for-notify
    STATUS current
    DESCRIPTION
        "Parameter 'bridge_id' in event RSTP.1"
    ::= { rstpEventObjects1 3 }

rstp1_bridge_port OBJECT-TYPE
    SYNTAX Integer32
    MAX-ACCESS accessible-for-notify
    STATUS current
    DESCRIPTION
        "Parameter 'bridge_port' in event RSTP.1"
    ::= { rstpEventObjects1 4 }

rstp1_interface OBJECT-TYPE
    SYNTAX DisplayString
    MAX-ACCESS accessible-for-notify
    STATUS current
    DESCRIPTION
        "Parameter 'interface' in event RSTP.1"
    ::= { rstpEventObjects1 5 }

rstp1_circuit_name OBJECT-TYPE
    SYNTAX DisplayString
    MAX-ACCESS accessible-for-notify
    STATUS current
    DESCRIPTION
        "Parameter 'circuit_name' in event RSTP.1"
    ::= { rstpEventObjects1 6 }

rstpEventObjects2 OBJECT-IDENTITY
    STATUS current
    DESCRIPTION
        "Event RSTP.2
        Port protocol migration state machine transition."
    ::= { rstpEventsGroup 2 }

rstp2_state_machine OBJECT-TYPE
    SYNTAX DisplayString
    MAX-ACCESS accessible-for-notify
    STATUS current
    DESCRIPTION
        "Parameter 'state_machine' in event RSTP.2"
    ::= { rstpEventObjects2 1 }

rstp2_state OBJECT-TYPE
    SYNTAX DisplayString
    MAX-ACCESS accessible-for-notify
    STATUS current
    DESCRIPTION
        "Parameter 'state' in event RSTP.2"
    ::= { rstpEventObjects2 2 }

rstp2_bridge_id OBJECT-TYPE
    SYNTAX Integer32
    MAX-ACCESS accessible-for-notify
    STATUS current
    DESCRIPTION
        "Parameter 'bridge_id' in event RSTP.2"
    ::= { rstpEventObjects2 3 }

rstp2_bridge_port OBJECT-TYPE
    SYNTAX Integer32
    MAX-ACCESS accessible-for-notify
    STATUS current
    DESCRIPTION
        "Parameter 'bridge_port' in event RSTP.2"
    ::= { rstpEventObjects2 4 }

rstp2_interface OBJECT-TYPE
    SYNTAX DisplayString
    MAX-ACCESS accessible-for-notify
    STATUS current
    DESCRIPTION
        "Parameter 'interface' in event RSTP.2"
    ::= { rstpEventObjects2 5 }

rstp2_circuit_name OBJECT-TYPE
    SYNTAX DisplayString
    MAX-ACCESS accessible-for-notify
    STATUS current
    DESCRIPTION
        "Parameter 'circuit_name' in event RSTP.2"
    ::= { rstpEventObjects2 6 }

rstpEventObjects3 OBJECT-IDENTITY
    STATUS current
    DESCRIPTION
        "Event RSTP.3
        Bridge detection state machine transition."
    ::= { rstpEventsGroup 3 }

rstp3_state_machine OBJECT-TYPE
    SYNTAX DisplayString
    MAX-ACCESS accessible-for-notify
    STATUS current
    DESCRIPTION
        "Parameter 'state_machine' in event RSTP.3"
    ::= { rstpEventObjects3 1 }

rstp3_state OBJECT-TYPE
    SYNTAX DisplayString
    MAX-ACCESS accessible-for-notify
    STATUS current
    DESCRIPTION
        "Parameter 'state' in event RSTP.3"
    ::= { rstpEventObjects3 2 }

rstp3_bridge_id OBJECT-TYPE
    SYNTAX Integer32
    MAX-ACCESS accessible-for-notify
    STATUS current
    DESCRIPTION
        "Parameter 'bridge_id' in event RSTP.3"
    ::= { rstpEventObjects3 3 }

rstp3_bridge_port OBJECT-TYPE
    SYNTAX Integer32
    MAX-ACCESS accessible-for-notify
    STATUS current
    DESCRIPTION
        "Parameter 'bridge_port' in event RSTP.3"
    ::= { rstpEventObjects3 4 }

rstp3_interface OBJECT-TYPE
    SYNTAX DisplayString
    MAX-ACCESS accessible-for-notify
    STATUS current
    DESCRIPTION
        "Parameter 'interface' in event RSTP.3"
    ::= { rstpEventObjects3 5 }

rstp3_circuit_name OBJECT-TYPE
    SYNTAX DisplayString
    MAX-ACCESS accessible-for-notify
    STATUS current
    DESCRIPTION
        "Parameter 'circuit_name' in event RSTP.3"
    ::= { rstpEventObjects3 6 }

rstpEventObjects4 OBJECT-IDENTITY
    STATUS current
    DESCRIPTION
        "Event RSTP.4
        Port transmit state machine transition."
    ::= { rstpEventsGroup 4 }

rstp4_state_machine OBJECT-TYPE
    SYNTAX DisplayString
    MAX-ACCESS accessible-for-notify
    STATUS current
    DESCRIPTION
        "Parameter 'state_machine' in event RSTP.4"
    ::= { rstpEventObjects4 1 }

rstp4_state OBJECT-TYPE
    SYNTAX DisplayString
    MAX-ACCESS accessible-for-notify
    STATUS current
    DESCRIPTION
        "Parameter 'state' in event RSTP.4"
    ::= { rstpEventObjects4 2 }

rstp4_bridge_id OBJECT-TYPE
    SYNTAX Integer32
    MAX-ACCESS accessible-for-notify
    STATUS current
    DESCRIPTION
        "Parameter 'bridge_id' in event RSTP.4"
    ::= { rstpEventObjects4 3 }

rstp4_bridge_port OBJECT-TYPE
    SYNTAX Integer32
    MAX-ACCESS accessible-for-notify
    STATUS current
    DESCRIPTION
        "Parameter 'bridge_port' in event RSTP.4"
    ::= { rstpEventObjects4 4 }

rstp4_interface OBJECT-TYPE
    SYNTAX DisplayString
    MAX-ACCESS accessible-for-notify
    STATUS current
    DESCRIPTION
        "Parameter 'interface' in event RSTP.4"
    ::= { rstpEventObjects4 5 }

rstp4_circuit_name OBJECT-TYPE
    SYNTAX DisplayString
    MAX-ACCESS accessible-for-notify
    STATUS current
    DESCRIPTION
        "Parameter 'circuit_name' in event RSTP.4"
    ::= { rstpEventObjects4 6 }

rstpEventObjects5 OBJECT-IDENTITY
    STATUS current
    DESCRIPTION
        "Event RSTP.5
        Port information state machine transition."
    ::= { rstpEventsGroup 5 }

rstp5_state_machine OBJECT-TYPE
    SYNTAX DisplayString
    MAX-ACCESS accessible-for-notify
    STATUS current
    DESCRIPTION
        "Parameter 'state_machine' in event RSTP.5"
    ::= { rstpEventObjects5 1 }

rstp5_state OBJECT-TYPE
    SYNTAX DisplayString
    MAX-ACCESS accessible-for-notify
    STATUS current
    DESCRIPTION
        "Parameter 'state' in event RSTP.5"
    ::= { rstpEventObjects5 2 }

rstp5_bridge_id OBJECT-TYPE
    SYNTAX Integer32
    MAX-ACCESS accessible-for-notify
    STATUS current
    DESCRIPTION
        "Parameter 'bridge_id' in event RSTP.5"
    ::= { rstpEventObjects5 3 }

rstp5_bridge_port OBJECT-TYPE
    SYNTAX Integer32
    MAX-ACCESS accessible-for-notify
    STATUS current
    DESCRIPTION
        "Parameter 'bridge_port' in event RSTP.5"
    ::= { rstpEventObjects5 4 }

rstp5_interface OBJECT-TYPE
    SYNTAX DisplayString
    MAX-ACCESS accessible-for-notify
    STATUS current
    DESCRIPTION
        "Parameter 'interface' in event RSTP.5"
    ::= { rstpEventObjects5 5 }

rstp5_circuit_name OBJECT-TYPE
    SYNTAX DisplayString
    MAX-ACCESS accessible-for-notify
    STATUS current
    DESCRIPTION
        "Parameter 'circuit_name' in event RSTP.5"
    ::= { rstpEventObjects5 6 }

rstpEventObjects6 OBJECT-IDENTITY
    STATUS current
    DESCRIPTION
        "Event RSTP.6
        Port role selection state machine transition."
    ::= { rstpEventsGroup 6 }

rstp6_state_machine OBJECT-TYPE
    SYNTAX DisplayString
    MAX-ACCESS accessible-for-notify
    STATUS current
    DESCRIPTION
        "Parameter 'state_machine' in event RSTP.6"
    ::= { rstpEventObjects6 1 }

rstp6_state OBJECT-TYPE
    SYNTAX DisplayString
    MAX-ACCESS accessible-for-notify
    STATUS current
    DESCRIPTION
        "Parameter 'state' in event RSTP.6"
    ::= { rstpEventObjects6 2 }

rstp6_bridge_id OBJECT-TYPE
    SYNTAX Integer32
    MAX-ACCESS accessible-for-notify
    STATUS current
    DESCRIPTION
        "Parameter 'bridge_id' in event RSTP.6"
    ::= { rstpEventObjects6 3 }

rstpEventObjects7 OBJECT-IDENTITY
    STATUS current
    DESCRIPTION
        "Event RSTP.7
        Port role transitions state machine transition."
    ::= { rstpEventsGroup 7 }

rstp7_state_machine OBJECT-TYPE
    SYNTAX DisplayString
    MAX-ACCESS accessible-for-notify
    STATUS current
    DESCRIPTION
        "Parameter 'state_machine' in event RSTP.7"
    ::= { rstpEventObjects7 1 }

rstp7_state OBJECT-TYPE
    SYNTAX DisplayString
    MAX-ACCESS accessible-for-notify
    STATUS current
    DESCRIPTION
        "Parameter 'state' in event RSTP.7"
    ::= { rstpEventObjects7 2 }

rstp7_bridge_id OBJECT-TYPE
    SYNTAX Integer32
    MAX-ACCESS accessible-for-notify
    STATUS current
    DESCRIPTION
        "Parameter 'bridge_id' in event RSTP.7"
    ::= { rstpEventObjects7 3 }

rstp7_bridge_port OBJECT-TYPE
    SYNTAX Integer32
    MAX-ACCESS accessible-for-notify
    STATUS current
    DESCRIPTION
        "Parameter 'bridge_port' in event RSTP.7"
    ::= { rstpEventObjects7 4 }

rstp7_interface OBJECT-TYPE
    SYNTAX DisplayString
    MAX-ACCESS accessible-for-notify
    STATUS current
    DESCRIPTION
        "Parameter 'interface' in event RSTP.7"
    ::= { rstpEventObjects7 5 }

rstp7_circuit_name OBJECT-TYPE
    SYNTAX DisplayString
    MAX-ACCESS accessible-for-notify
    STATUS current
    DESCRIPTION
        "Parameter 'circuit_name' in event RSTP.7"
    ::= { rstpEventObjects7 6 }

rstpEventObjects8 OBJECT-IDENTITY
    STATUS current
    DESCRIPTION
        "Event RSTP.8
        Port state transition state machine transition."
    ::= { rstpEventsGroup 8 }

rstp8_state_machine OBJECT-TYPE
    SYNTAX DisplayString
    MAX-ACCESS accessible-for-notify
    STATUS current
    DESCRIPTION
        "Parameter 'state_machine' in event RSTP.8"
    ::= { rstpEventObjects8 1 }

rstp8_state OBJECT-TYPE
    SYNTAX DisplayString
    MAX-ACCESS accessible-for-notify
    STATUS current
    DESCRIPTION
        "Parameter 'state' in event RSTP.8"
    ::= { rstpEventObjects8 2 }

rstp8_bridge_id OBJECT-TYPE
    SYNTAX Integer32
    MAX-ACCESS accessible-for-notify
    STATUS current
    DESCRIPTION
        "Parameter 'bridge_id' in event RSTP.8"
    ::= { rstpEventObjects8 3 }

rstp8_bridge_port OBJECT-TYPE
    SYNTAX Integer32
    MAX-ACCESS accessible-for-notify
    STATUS current
    DESCRIPTION
        "Parameter 'bridge_port' in event RSTP.8"
    ::= { rstpEventObjects8 4 }

rstp8_interface OBJECT-TYPE
    SYNTAX DisplayString
    MAX-ACCESS accessible-for-notify
    STATUS current
    DESCRIPTION
        "Parameter 'interface' in event RSTP.8"
    ::= { rstpEventObjects8 5 }

rstp8_circuit_name OBJECT-TYPE
    SYNTAX DisplayString
    MAX-ACCESS accessible-for-notify
    STATUS current
    DESCRIPTION
        "Parameter 'circuit_name' in event RSTP.8"
    ::= { rstpEventObjects8 6 }

rstpEventObjects9 OBJECT-IDENTITY
    STATUS current
    DESCRIPTION
        "Event RSTP.9
        Topology change state machine transition."
    ::= { rstpEventsGroup 9 }

rstp9_state_machine OBJECT-TYPE
    SYNTAX DisplayString
    MAX-ACCESS accessible-for-notify
    STATUS current
    DESCRIPTION
        "Parameter 'state_machine' in event RSTP.9"
    ::= { rstpEventObjects9 1 }

rstp9_state OBJECT-TYPE
    SYNTAX DisplayString
    MAX-ACCESS accessible-for-notify
    STATUS current
    DESCRIPTION
        "Parameter 'state' in event RSTP.9"
    ::= { rstpEventObjects9 2 }

rstp9_bridge_id OBJECT-TYPE
    SYNTAX Integer32
    MAX-ACCESS accessible-for-notify
    STATUS current
    DESCRIPTION
        "Parameter 'bridge_id' in event RSTP.9"
    ::= { rstpEventObjects9 3 }

rstp9_bridge_port OBJECT-TYPE
    SYNTAX Integer32
    MAX-ACCESS accessible-for-notify
    STATUS current
    DESCRIPTION
        "Parameter 'bridge_port' in event RSTP.9"
    ::= { rstpEventObjects9 4 }

rstp9_interface OBJECT-TYPE
    SYNTAX DisplayString
    MAX-ACCESS accessible-for-notify
    STATUS current
    DESCRIPTION
        "Parameter 'interface' in event RSTP.9"
    ::= { rstpEventObjects9 5 }

rstp9_circuit_name OBJECT-TYPE
    SYNTAX DisplayString
    MAX-ACCESS accessible-for-notify
    STATUS current
    DESCRIPTION
        "Parameter 'circuit_name' in event RSTP.9"
    ::= { rstpEventObjects9 6 }

rstpEventObjects10 OBJECT-IDENTITY
    STATUS current
    DESCRIPTION
        "Event RSTP.10
        Generic informational event."
    ::= { rstpEventsGroup 10 }

rstp10_string OBJECT-TYPE
    SYNTAX DisplayString
    MAX-ACCESS accessible-for-notify
    STATUS current
    DESCRIPTION
        "Parameter 'string' in event RSTP.10"
    ::= { rstpEventObjects10 1 }


rstpNotification1 NOTIFICATION-TYPE
    OBJECTS { 
              rstp1_state_machine, 
              rstp1_state,
              rstp1_bridge_id,
              rstp1_bridge_port,
              rstp1_interface,
              rstp1_circuit_name 
            }
    STATUS current
    DESCRIPTION
        "Notification of Event RSTP.1

        Message: 'State Machine $1 entered state $2, bridge $3, port $4, ifc $5$6'

        Parameters list:
              $1: rstp1_state_machine
              $2: rstp1_state
              $3: rstp1_bridge_id
              $4: rstp1_bridge_port
              $5: rstp1_interface
              $6: rstp1_circuit_name

        Port receive state machine transition."
    ::= { rstpNotificationsPrefix 1 }

rstpNotification2 NOTIFICATION-TYPE
    OBJECTS { 
              rstp2_state_machine, 
              rstp2_state,
              rstp2_bridge_id,
              rstp2_bridge_port,
              rstp2_interface,
              rstp2_circuit_name 
            }
    STATUS current
    DESCRIPTION
        "Notification of Event RSTP.2

        Message: 'State Machine $1 entered state $2, bridge $3, port $4, ifc $5$6'

        Parameters list:
              $1: rstp2_state_machine
              $2: rstp2_state
              $3: rstp2_bridge_id
              $4: rstp2_bridge_port
              $5: rstp2_interface
              $6: rstp2_circuit_name

        Port protocol migration state machine transition."
    ::= { rstpNotificationsPrefix 2 }

rstpNotification3 NOTIFICATION-TYPE
    OBJECTS { 
              rstp3_state_machine, 
              rstp3_state,
              rstp3_bridge_id,
              rstp3_bridge_port,
              rstp3_interface,
              rstp3_circuit_name 
            }
    STATUS current
    DESCRIPTION
        "Notification of Event RSTP.3

        Message: 'State Machine $1 entered state $2, bridge $3, port $4, ifc $5$6'

        Parameters list:
              $1: rstp3_state_machine
              $2: rstp3_state
              $3: rstp3_bridge_id
              $4: rstp3_bridge_port
              $5: rstp3_interface
              $6: rstp3_circuit_name

        Bridge detection state machine transition."
    ::= { rstpNotificationsPrefix 3 }

rstpNotification4 NOTIFICATION-TYPE
    OBJECTS { 
              rstp4_state_machine, 
              rstp4_state,
              rstp4_bridge_id,
              rstp4_bridge_port,
              rstp4_interface,
              rstp4_circuit_name 
            }
    STATUS current
    DESCRIPTION
        "Notification of Event RSTP.4

        Message: 'State Machine $1 entered state $2, bridge $3, port $4, ifc $5$6'

        Parameters list:
              $1: rstp4_state_machine
              $2: rstp4_state
              $3: rstp4_bridge_id
              $4: rstp4_bridge_port
              $5: rstp4_interface
              $6: rstp4_circuit_name

        Port transmit state machine transition."
    ::= { rstpNotificationsPrefix 4 }

rstpNotification5 NOTIFICATION-TYPE
    OBJECTS { 
              rstp5_state_machine, 
              rstp5_state,
              rstp5_bridge_id,
              rstp5_bridge_port,
              rstp5_interface,
              rstp5_circuit_name 
            }
    STATUS current
    DESCRIPTION
        "Notification of Event RSTP.5

        Message: 'State Machine $1 entered state $2, bridge $3, port $4, ifc $5$6'

        Parameters list:
              $1: rstp5_state_machine
              $2: rstp5_state
              $3: rstp5_bridge_id
              $4: rstp5_bridge_port
              $5: rstp5_interface
              $6: rstp5_circuit_name

        Port information state machine transition."
    ::= { rstpNotificationsPrefix 5 }

rstpNotification6 NOTIFICATION-TYPE
    OBJECTS { 
              rstp6_state_machine, 
              rstp6_state,
              rstp6_bridge_id 
            }
    STATUS current
    DESCRIPTION
        "Notification of Event RSTP.6

        Message: 'State Machine $1 entered state $2, bridge $3'

        Parameters list:
              $1: rstp6_state_machine
              $2: rstp6_state
              $3: rstp6_bridge_id

        Port role selection state machine transition."
    ::= { rstpNotificationsPrefix 6 }

rstpNotification7 NOTIFICATION-TYPE
    OBJECTS { 
              rstp7_state_machine, 
              rstp7_state,
              rstp7_bridge_id,
              rstp7_bridge_port,
              rstp7_interface,
              rstp7_circuit_name 
            }
    STATUS current
    DESCRIPTION
        "Notification of Event RSTP.7

        Message: 'State Machine $1 entered state $2, bridge $3, port $4, ifc $5$6'

        Parameters list:
              $1: rstp7_state_machine
              $2: rstp7_state
              $3: rstp7_bridge_id
              $4: rstp7_bridge_port
              $5: rstp7_interface
              $6: rstp7_circuit_name

        Port role transitions state machine transition."
    ::= { rstpNotificationsPrefix 7 }

rstpNotification8 NOTIFICATION-TYPE
    OBJECTS { 
              rstp8_state_machine, 
              rstp8_state,
              rstp8_bridge_id,
              rstp8_bridge_port,
              rstp8_interface,
              rstp8_circuit_name 
            }
    STATUS current
    DESCRIPTION
        "Notification of Event RSTP.8

        Message: 'State Machine $1 entered state $2, bridge $3, port $4, ifc $5$6'

        Parameters list:
              $1: rstp8_state_machine
              $2: rstp8_state
              $3: rstp8_bridge_id
              $4: rstp8_bridge_port
              $5: rstp8_interface
              $6: rstp8_circuit_name

        Port state transition state machine transition."
    ::= { rstpNotificationsPrefix 8 }

rstpNotification9 NOTIFICATION-TYPE
    OBJECTS { 
              rstp9_state_machine, 
              rstp9_state,
              rstp9_bridge_id,
              rstp9_bridge_port,
              rstp9_interface,
              rstp9_circuit_name 
            }
    STATUS current
    DESCRIPTION
        "Notification of Event RSTP.9

        Message: 'State Machine $1 entered state $2, bridge $3, port $4, ifc $5$6'

        Parameters list:
              $1: rstp9_state_machine
              $2: rstp9_state
              $3: rstp9_bridge_id
              $4: rstp9_bridge_port
              $5: rstp9_interface
              $6: rstp9_circuit_name

        Topology change state machine transition."
    ::= { rstpNotificationsPrefix 9 }

rstpNotification10 NOTIFICATION-TYPE
    OBJECTS { 
              rstp10_string 
            }
    STATUS current
    DESCRIPTION
        "Notification of Event RSTP.10

        Message: '$1'

        Parameters list:
              $1: rstp10_string

        Generic informational event."
    ::= { rstpNotificationsPrefix 10 }


END
