BWM-MIB DEFINITIONS ::= BEGIN

-- Title:      RADWARE
--             This Private MIB supports the WSD/CSD/FP/LP
-- Version:    2.9
-- Date:       2/4/2001
-- By:         RMA (Radware MIB Authority)
-- E-mail:     US:            support@radware.com
--             International: support_int@radware.com
--
IMPORTS
       NetworkAddress,
       IpAddress,
       Counter,
       Gauge,
       enterprises
              FROM RFC1155-SMI
       Integer32
              FROM SNMPv2-SMI
       OBJECT-TYPE
              FROM RFC-1212
       DisplayString,
       ipAddrEntry
              FROM RFC1213-MIB
       TRAP-TYPE
              FROM RFC-1215
       rsBWM,
       rndErrorDesc,
       rndErrorSeverity
              FROM RADWARE-MIB
        MacAddress
              FROM SNMPv2-TC;

    TruthValue ::= INTEGER {
         true (1),
         false (2)
        }
    RowStatus ::= INTEGER {
        active(1),
        notInService(2),
        notReady(3),
        createAndGo(4),
        createAndWait(5),
        destroy(6)
        }
    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsBWMRulesTable OBJECT-TYPE
    SYNTAX SEQUENCE OF RsBWMRulesEntry
    ACCESS not-accessible
    STATUS  mandatory
    DESCRIPTION
      "Table containing the list of rules for classifer data base,
       these rules can be used to classify packets for bandwidth management,
       facs etc..."
    ::=  {rsBWM 1}

rsBWMRulesEntry OBJECT-TYPE
    SYNTAX RsBWMRulesEntry
    ACCESS not-accessible
    STATUS  mandatory
    DESCRIPTION
       "The row definition for this table."
    INDEX { rsBWMRulesName }
    ::=  { rsBWMRulesTable 1 }

RsBWMRulesEntry ::= SEQUENCE {
    rsBWMRulesIndex INTEGER,
    rsBWMRulesName DisplayString,
    rsBWMRulesDestination DisplayString,
    rsBWMRulesSource DisplayString,
    rsBWMRulesStatus  RowStatus,
    rsBWMRulesAction INTEGER,
    rsBWMRulesDirection INTEGER,
    rsBWMRulesPriority INTEGER,
    rsBWMRulesPhysicalPort INTEGER,
    rsBWMRulesType INTEGER,
    rsBWMRulesDescription DisplayString,
    rsBWMRulesGuaranteedBW Integer32,
    rsBWMRulesPolicyType INTEGER,
    rsBWMRulesPolicy DisplayString,
    rsBWMRulesOperationalStatus INTEGER,
    rsBWMRulesDSCPMarking INTEGER,
    rsBWMRulesReportBlockedPackets INTEGER,
    rsBWMRulesMaxBW Integer32,
    rsBWMRulesSpecific DisplayString,
    rsBWMRulesPhysicalPortGroup DisplayString,
    rsBWMRulesVLANTagGroup DisplayString,
    rsBWMRulesTrafficIdentification INTEGER,
    rsBWMRulesTrafficFlowMaxBW INTEGER,
    rsBWMRulesMaxConcurrentSessions INTEGER,
    rsBWMRulesTrafficIDCookieField DisplayString,
    rsBWMRulesPolicyGroup DisplayString
}

rsBWMRulesIndex OBJECT-TYPE
    SYNTAX INTEGER
    ACCESS  read-write
    STATUS  mandatory
    DESCRIPTION
       "This variable indicates the administrative index of a line it
       determines the order of the rules."
    ::=  { rsBWMRulesEntry 1 }

rsBWMRulesName OBJECT-TYPE
    SYNTAX DisplayString (SIZE(0..19))
    ACCESS  read-only
    STATUS  mandatory
    DESCRIPTION
      "The Name for the Rule must be unique."
    ::=  {rsBWMRulesEntry 2}

rsBWMRulesDestination OBJECT-TYPE
    SYNTAX DisplayString (SIZE(0..19))
    ACCESS  read-write
    STATUS  mandatory
    DESCRIPTION
      "The destination address / range of address for the packet, the name is
      defined in the Objects table or can be an IP address."
    ::=  {rsBWMRulesEntry 3}

rsBWMRulesSource OBJECT-TYPE
    SYNTAX DisplayString (SIZE(0..19))
    ACCESS  read-write
    STATUS  mandatory
    DESCRIPTION
      "The source address / range of address for the packet, the name is
      defined in the Objects table or can be an IP address."
    ::=  {rsBWMRulesEntry 4}

rsBWMRulesStatus OBJECT-TYPE
    SYNTAX RowStatus
    ACCESS  read-write
    STATUS  mandatory
    DESCRIPTION
       "This variable indicates the administrative status of this entry.
        Used to delete an entry of this table."
    ::=  { rsBWMRulesEntry 5 }

rsBWMRulesAction OBJECT-TYPE
    SYNTAX INTEGER {
          forward(1),
          block(2),
          blockAndReset(3),
          blockAndBiDirectionalReset(4),
          monitorHTTP(5),
          monitorHTTPS(6),
          monitorTCP(7) }
    ACCESS  read-write
    STATUS  mandatory
    DESCRIPTION
       "This variable indicates the action that the classifier / service
       must take on this entry."
    DEFVAL  { 2 }
    ::=  { rsBWMRulesEntry 6 }

rsBWMRulesDirection OBJECT-TYPE
    SYNTAX INTEGER {
              oneway(1),
              twoway(2) }
    ACCESS  read-write
    STATUS  mandatory
    DESCRIPTION
       "This variable indicates the direction of the incoming packet."
    DEFVAL { 1 }
    ::=  { rsBWMRulesEntry 7 }

rsBWMRulesPriority OBJECT-TYPE
    SYNTAX INTEGER
    ACCESS  read-write
    STATUS  mandatory
    DESCRIPTION
       "This variable indicates the priority for this entry."
    DEFVAL  { 3 }
    ::=  { rsBWMRulesEntry 8 }

rsBWMRulesPhysicalPort OBJECT-TYPE
    SYNTAX INTEGER
    ACCESS  read-write
    STATUS  mandatory
    DESCRIPTION
       "This variable indicates the port from which the packet arrived."
    DEFVAL  { 0 }
    ::=  { rsBWMRulesEntry 9 }

rsBWMRulesType OBJECT-TYPE
    SYNTAX INTEGER {
              facsBandwidth(1),
              counter(2),
              ids(3),
              chain(4) }
    ACCESS  read-write
    STATUS  mandatory
    DESCRIPTION
       "This variable indicates the type of rules (services) ."
    DEFVAL  { 1 }
    ::=  { rsBWMRulesEntry 10 }

rsBWMRulesDescription OBJECT-TYPE
    SYNTAX DisplayString (SIZE(0..19))
    ACCESS  read-write
    STATUS  mandatory
    DESCRIPTION
      "Description."
    ::=  { rsBWMRulesEntry 11 }

rsBWMRulesGuaranteedBW OBJECT-TYPE
    SYNTAX Integer32
    ACCESS  read-write
    STATUS  mandatory
    DESCRIPTION
       "Bandwidth allocated for a certain rule."
--  DEFVAL  { 0 }
    ::=  { rsBWMRulesEntry 12 }

rsBWMRulesPolicyType OBJECT-TYPE
    SYNTAX INTEGER {
              none(1),
              filter(2),
              group(3),
              policy(4)}
    ACCESS  read-write
    STATUS  mandatory
    DESCRIPTION
       "The type of policy - i.e. if this is a filter, group or policy."
    DEFVAL  { 1 }
    ::=  { rsBWMRulesEntry 13 }

rsBWMRulesPolicy OBJECT-TYPE
    SYNTAX DisplayString (SIZE(0..29))
    ACCESS  read-write
    STATUS  mandatory
    DESCRIPTION
       "The name for the filter policy for the rule."
    ::=  { rsBWMRulesEntry 14 }

rsBWMRulesOperationalStatus OBJECT-TYPE
    SYNTAX INTEGER {
        active (1),
        inactive (2)
    }
    ACCESS  read-write
    STATUS  mandatory
    DESCRIPTION
       "This variable indicates if the rule is active or inactive.
        The active rule table contains only active rules."
    ::= { rsBWMRulesEntry 15 }

rsBWMRulesDSCPMarking OBJECT-TYPE
    SYNTAX INTEGER (-1 | 0..63)
    ACCESS  read-write
    STATUS  mandatory
    DESCRIPTION
       "This variable indicates the DSCP value to mark the ToS field in the IP header
        in the matching packets. If equals -1, the marking is not performed."
    ::= { rsBWMRulesEntry 16 }

rsBWMRulesReportBlockedPackets OBJECT-TYPE
    SYNTAX INTEGER {
        disable (0),
        enable (1)
    }
    ACCESS  read-write
    STATUS  mandatory
    DESCRIPTION
       "This variable indicates if blocked packets are be reported."
    ::= { rsBWMRulesEntry 17 }

rsBWMRulesMaxBW OBJECT-TYPE
    SYNTAX Integer32
    ACCESS  read-write
    STATUS  mandatory
    DESCRIPTION
       "Maximum bandwidth allocated for a certain rule."
--  DEFVAL  { 0 }
    ::=  { rsBWMRulesEntry 18 }

rsBWMRulesSpecific OBJECT-TYPE
    SYNTAX DisplayString (SIZE(0..19))
    ACCESS  read-write
    STATUS  mandatory
    DESCRIPTION
       "This variable indicates if there is additional data to the 
       policy."
    ::= { rsBWMRulesEntry 19 }

rsBWMRulesPhysicalPortGroup OBJECT-TYPE
    SYNTAX DisplayString
    ACCESS  read-write
    STATUS  mandatory
    DESCRIPTION
       "The name of the physical port group for this rule."
    ::=  { rsBWMRulesEntry 20 }

rsBWMRulesVLANTagGroup OBJECT-TYPE
    SYNTAX DisplayString
    ACCESS  read-write
    STATUS  mandatory
    DESCRIPTION
        "The name of the VLAN tag group for this rule."
    ::= { rsBWMRulesEntry 21 }

rsBWMRulesTrafficIdentification OBJECT-TYPE
    SYNTAX INTEGER {
        none (0),
        client (1),
        session (2),
        connection (3),
        fullL4Session (4),
        sessionCookie (5)
    }
    ACCESS  read-write
    STATUS  mandatory
    DESCRIPTION
        "This variable indicates how a traffic flow is defined for this policy."
    ::= { rsBWMRulesEntry 22 }

rsBWMRulesTrafficFlowMaxBW OBJECT-TYPE
    SYNTAX INTEGER
    ACCESS  read-write
    STATUS  mandatory
    DESCRIPTION
        "Maximum bandwidth allocated for a certain traffic flow (session) that match this rule."
    ::= { rsBWMRulesEntry 23 }

rsBWMRulesMaxConcurrentSessions OBJECT-TYPE
    SYNTAX INTEGER
    ACCESS  read-write
    STATUS  mandatory
    DESCRIPTION
        "Maximum number of sessions that can be open simultaneously per traffic flow."
    ::= { rsBWMRulesEntry 24 }

rsBWMRulesTrafficIDCookieField OBJECT-TYPE
    SYNTAX DisplayString
    ACCESS  read-write
    STATUS  mandatory
    DESCRIPTION
        "The name of cookie field for Traafic Flow ID by cookie."
    ::= { rsBWMRulesEntry 25 }

rsBWMRulesPolicyGroup OBJECT-TYPE
    SYNTAX DisplayString (SIZE(0..19))
    ACCESS  read-write
    STATUS  mandatory
    DESCRIPTION
        "Group the policies for bandwidth sharing."
    ::= { rsBWMRulesEntry 26 }

rsBWMRulesIPObjectTable OBJECT-TYPE
    SYNTAX SEQUENCE OF RsBWMRulesIPObjectEntry
    ACCESS not-accessible
    STATUS  mandatory
    DESCRIPTION
      "Table containing the grouping for ranges."
    ::=  {rsBWM 2}

rsBWMRulesIPObjectEntry OBJECT-TYPE
    SYNTAX RsBWMRulesIPObjectEntry
    ACCESS not-accessible
    STATUS  mandatory
    DESCRIPTION
       "The row definition for this table."
    INDEX {rsBWMRulesIPObjectName,rsBWMRulesIPObjectSubIndex}
    ::=  { rsBWMRulesIPObjectTable 1 }

RsBWMRulesIPObjectEntry ::= SEQUENCE {
    rsBWMRulesIPObjectName DisplayString,
    rsBWMRulesIPObjectSubIndex INTEGER,
    rsBWMRulesIPObjectAddress IpAddress,
    rsBWMRulesIPObjectMask IpAddress,
    rsBWMRulesIPObjectFromIP IpAddress,
    rsBWMRulesIPObjectToIP IpAddress,
    rsBWMRulesIPObjectMode INTEGER,
    rsBWMRulesIPObjectStatus RowStatus
}

rsBWMRulesIPObjectName OBJECT-TYPE
    SYNTAX DisplayString (SIZE(0..19))
    ACCESS  read-only
    STATUS  mandatory
    DESCRIPTION
      "The Name for the IP Object Rule, must be unique."
    ::=  { rsBWMRulesIPObjectEntry 1 }

rsBWMRulesIPObjectSubIndex OBJECT-TYPE
    SYNTAX INTEGER
    ACCESS  read-only
    STATUS  mandatory
    DESCRIPTION
       "SubIndex."
    DEFVAL  { 0 }
    ::=  { rsBWMRulesIPObjectEntry 2 }

rsBWMRulesIPObjectAddress OBJECT-TYPE
    SYNTAX IpAddress
    ACCESS  read-write
    STATUS  mandatory
    DESCRIPTION
      "IP address"
    DEFVAL  { 0 }
    ::=  { rsBWMRulesIPObjectEntry 3 }

rsBWMRulesIPObjectMask OBJECT-TYPE
    SYNTAX IpAddress
    ACCESS  read-write
    STATUS  mandatory
    DESCRIPTION
      "IP address mask."
    DEFVAL  { 0 }
    ::=  { rsBWMRulesIPObjectEntry 4 }

rsBWMRulesIPObjectFromIP OBJECT-TYPE
    SYNTAX IpAddress
    ACCESS  read-write
    STATUS  mandatory
    DESCRIPTION
      "The from IP Address of the range."
    DEFVAL  { 0 }
    ::=  { rsBWMRulesIPObjectEntry 5 }

rsBWMRulesIPObjectToIP OBJECT-TYPE
    SYNTAX IpAddress
    ACCESS  read-write
    STATUS  mandatory
    DESCRIPTION
      "The to IP Address of the range."
    DEFVAL  { 0 }
    ::=  { rsBWMRulesIPObjectEntry 6 }

rsBWMRulesIPObjectMode OBJECT-TYPE
    SYNTAX INTEGER {
              ipMask(1),
              ipRange(2),
			  dynamic(3)
    }
    ACCESS  read-write
    STATUS  mandatory
    DESCRIPTION
       "This variable indicates the mode of the entry. This is either
       a range or an IP address and mask."
--    DEFVAL  { 1 }
    ::=  { rsBWMRulesIPObjectEntry 7 }

rsBWMRulesIPObjectStatus OBJECT-TYPE
    SYNTAX RowStatus 
    ACCESS  read-write
    STATUS  mandatory
    DESCRIPTION
       "This variable indicates the administrative status of this entry.
        Used to delete an entry of this table."
    ::=  { rsBWMRulesIPObjectEntry 8 }

rsBWMCBQMode  OBJECT-TYPE
    SYNTAX  INTEGER {
            cyclic(1),
            cbq(2)
    }
    ACCESS  read-write
    STATUS  mandatory
    DESCRIPTION
        "CBQ Mode."
    DEFVAL  { 1 }
    ::=  {rsBWM 3}

rsBWMActualQueueSize  OBJECT-TYPE
    SYNTAX  INTEGER
    ACCESS  read-only
    STATUS  mandatory
    DESCRIPTION
        "The current size of the queue."
    DEFVAL  { 0 }
    ::=  {rsBWM 4}

rsBWMAverageQueueSize  OBJECT-TYPE
    SYNTAX  INTEGER
    ACCESS  read-only
    STATUS  mandatory
    DESCRIPTION
        "The current average queue size."
    DEFVAL  { 0 }
    ::=  {rsBWM 5}

rsBWMQueueRedDropped  OBJECT-TYPE
    SYNTAX  INTEGER
    ACCESS  read-only
    STATUS  mandatory
    DESCRIPTION
        "The current red dropped packets."
    DEFVAL  { 0 }
    ::=  {rsBWM 6}

rsBWMPriorityTable OBJECT-TYPE
    SYNTAX SEQUENCE OF RsBWMPriorityEntry
    ACCESS not-accessible
    STATUS mandatory
    DESCRIPTION "The table for reading the packets sent via each priority"
    ::= {rsBWM 7}

rsBWMPriorityEntry OBJECT-TYPE
    SYNTAX RsBWMPriorityEntry
    ACCESS not-accessible
    STATUS mandatory
    DESCRIPTION "The row definition for the priority table"
    INDEX {rsBWMPriority}
    ::= {rsBWMPriorityTable 1}

RsBWMPriorityEntry ::= SEQUENCE {
    rsBWMPriority INTEGER,
    rsBWMPacketsSent INTEGER
}

rsBWMPriority OBJECT-TYPE
    SYNTAX INTEGER
    ACCESS read-only
    STATUS mandatory
    DESCRIPTION "The priority"
    ::= {rsBWMPriorityEntry 1}

rsBWMPacketsSent OBJECT-TYPE
    SYNTAX INTEGER
    ACCESS read-only
    STATUS mandatory
    DESCRIPTION "The number of packets sent via this priority"
    ::= {rsBWMPriorityEntry 2}

rsBWMRedMode OBJECT-TYPE
    SYNTAX INTEGER {
        none (1),
        global (2),
        weighted (3)
    }
    ACCESS  read-write
    STATUS  mandatory
    DESCRIPTION "The RED algorithm mode"
--  DEFVAL  { none }
    ::= {rsBWM 8}

rsBWMCurrentRulesTable OBJECT-TYPE
    SYNTAX SEQUENCE OF RsBWMCurrentRulesEntry
    ACCESS not-accessible
    STATUS  mandatory
    DESCRIPTION
      "Table containing the list of rules for classifer data base,
       these rules can be used to classify packets for bandwidth management,
       facs etc..."
    ::=  {rsBWM 9}

rsBWMCurrentRulesEntry OBJECT-TYPE
    SYNTAX RsBWMCurrentRulesEntry
    ACCESS not-accessible
    STATUS  mandatory
    DESCRIPTION
       "The row definition for this table."
    INDEX { rsBWMCurrentRulesName }
    ::=  { rsBWMCurrentRulesTable 1 }

RsBWMCurrentRulesEntry ::= SEQUENCE {
    rsBWMCurrentRulesIndex INTEGER,
    rsBWMCurrentRulesName DisplayString,
    rsBWMCurrentRulesDestination DisplayString,
    rsBWMCurrentRulesSource DisplayString,
    rsBWMCurrentRulesAction INTEGER,
    rsBWMCurrentRulesDirection INTEGER,
    rsBWMCurrentRulesPriority INTEGER,
    rsBWMCurrentRulesPhysicalPort INTEGER,
    rsBWMCurrentRulesType INTEGER,
    rsBWMCurrentRulesDescription DisplayString,
    rsBWMCurrentRulesGuaranteedBW Counter,
    rsBWMCurrentRulesMaxBW Counter,
    rsBWMCurrentRulesPolicyType INTEGER,
    rsBWMCurrentRulesPolicy DisplayString,
    rsBWMCurrentRulesDSCPMarking INTEGER,
    rsBWMCurrentRulesReportBlockedPackets INTEGER,
    rsBWMCurrentRulesSpecific DisplayString,
    rsBWMCurrentRulesPhysicalPortGroup DisplayString,
    rsBWMCurrentRulesVLANTagGroup DisplayString,
    rsBWMCurrentRulesTrafficIdentification INTEGER,
    rsBWMCurrentRulesTrafficFlowMaxBW INTEGER,
    rsBWMCurrentRulesMaxConcurrentSessions INTEGER,
    rsBWMCurrentRulesTrafficIDCookieField DisplayString,
    rsBWMCurrentRulesPolicyGroup DisplayString
}

rsBWMCurrentRulesIndex OBJECT-TYPE
    SYNTAX INTEGER
    ACCESS  read-only
    STATUS  mandatory
    DESCRIPTION
       "This variable indicates the administrative index of a line it
       determine the order of the rules."
    ::=  { rsBWMCurrentRulesEntry 1 }

rsBWMCurrentRulesName OBJECT-TYPE
    SYNTAX DisplayString (SIZE(0..19))
    ACCESS  read-only
    STATUS  mandatory
    DESCRIPTION
      "The Name for the Rule must be unique."
    ::=  {rsBWMCurrentRulesEntry 2}

rsBWMCurrentRulesDestination OBJECT-TYPE
    SYNTAX DisplayString (SIZE(0..19))
    ACCESS  read-only
    STATUS  mandatory
    DESCRIPTION
      "The destination address / range of address for the packet, the name is
      defined in the Objects table or can be an IP address."
    ::=  {rsBWMCurrentRulesEntry 3}

rsBWMCurrentRulesSource OBJECT-TYPE
    SYNTAX DisplayString (SIZE(0..19))
    ACCESS  read-only
    STATUS  mandatory
    DESCRIPTION
      "The source address / range of address for the packet, the name is
      defined in the Objects table or can be an IP address."
    ::=  {rsBWMCurrentRulesEntry 4}

rsBWMCurrentRulesAction OBJECT-TYPE
    SYNTAX INTEGER {
              forward(1),
              block(2),
              blockAndReset(3),
              blockAndBiDirectionalReset(4),
              monitorHTTP(5),
              monitorHTTPS(6),
              monitorTCP(7) }
    ACCESS  read-only
    STATUS  mandatory
    DESCRIPTION
       "This variable indicates the action that the classifier / service must
       take on this entry."
    ::=  { rsBWMCurrentRulesEntry 5 }

rsBWMCurrentRulesDirection OBJECT-TYPE
    SYNTAX INTEGER {
              oneway(1),
              twoway(2) }
    ACCESS read-only
    STATUS mandatory
    DESCRIPTION
       "This variable indicates the direction of the incoming packet."
    ::=  { rsBWMCurrentRulesEntry 6 }

rsBWMCurrentRulesPriority OBJECT-TYPE
    SYNTAX INTEGER
    ACCESS  read-only
    STATUS  mandatory
    DESCRIPTION
       "This variable indicates the priority for this entry."
    ::=  { rsBWMCurrentRulesEntry 7 }

rsBWMCurrentRulesPhysicalPort OBJECT-TYPE
    SYNTAX INTEGER
    ACCESS  read-only
    STATUS  mandatory
    DESCRIPTION
       "This variable indicates the port from which the packet arrived."
    ::=  { rsBWMCurrentRulesEntry 8 }

rsBWMCurrentRulesType OBJECT-TYPE
    SYNTAX INTEGER {
              facsBandwidth(1),
              counter(2),
              ids(3),
              chain(4) }
    ACCESS  read-only
    STATUS  mandatory
    DESCRIPTION
       "This variable indicates the type of rules (services) ."
    ::=  { rsBWMCurrentRulesEntry 9 }

rsBWMCurrentRulesDescription OBJECT-TYPE
    SYNTAX DisplayString (SIZE(0..19))
    ACCESS  read-only
    STATUS  mandatory
    DESCRIPTION
      "Description."
    ::=  { rsBWMCurrentRulesEntry 10 }

rsBWMCurrentRulesGuaranteedBW OBJECT-TYPE
    SYNTAX Counter
    ACCESS  read-only
    STATUS  mandatory
    DESCRIPTION
       "Bandwidth allocated for a certain rule."
    ::=  { rsBWMCurrentRulesEntry 11 }

rsBWMCurrentRulesMaxBW OBJECT-TYPE
    SYNTAX Counter
    ACCESS  read-only
    STATUS  mandatory
    DESCRIPTION
       "Maximum bandwidth allocated for a certain rule."
    ::=  { rsBWMCurrentRulesEntry 12 }

rsBWMCurrentRulesPolicyType OBJECT-TYPE
    SYNTAX INTEGER {
              none(1),
              filter(2),
              group(3),
              policy(4)}
    ACCESS  read-only
    STATUS  mandatory
    DESCRIPTION
       "The type of policy - i.e. if this is a filter, group or policy."
    DEFVAL  { 1 }
    ::=  { rsBWMCurrentRulesEntry 13 }

rsBWMCurrentRulesPolicy OBJECT-TYPE
    SYNTAX DisplayString (SIZE(0..29))
    ACCESS  read-only
    STATUS  mandatory
    DESCRIPTION
       "The name for the filter policy for the rule."
    ::=  { rsBWMCurrentRulesEntry 14 }

rsBWMCurrentRulesDSCPMarking OBJECT-TYPE
    SYNTAX INTEGER (-1 | 0..63)
    ACCESS  read-only
    STATUS  mandatory
    DESCRIPTION
       "This variable indicates the DSCP value to mark the ToS field in the IP header
        in the matching packets. If equals -1, the marking is not performed."
    ::= { rsBWMCurrentRulesEntry 15 }

rsBWMCurrentRulesReportBlockedPackets OBJECT-TYPE
    SYNTAX INTEGER {
        disable (0),
        enable (1)
    }
    ACCESS  read-only
    STATUS  mandatory
    DESCRIPTION
       "This variable indicates if blocked packets are be reported."
    ::= { rsBWMCurrentRulesEntry 16 }

rsBWMCurrentRulesSpecific OBJECT-TYPE
    SYNTAX DisplayString (SIZE(0..19))
    ACCESS  read-only
    STATUS  mandatory
    DESCRIPTION
       "This variable indicates if there is additional data to the 
       policy."
    ::= { rsBWMCurrentRulesEntry 17 }

rsBWMCurrentRulesPhysicalPortGroup OBJECT-TYPE
    SYNTAX DisplayString
    ACCESS  read-only
    STATUS  mandatory
    DESCRIPTION
       "The name of the physical port group for this rule."
    ::=  { rsBWMCurrentRulesEntry 18 }

rsBWMCurrentRulesVLANTagGroup OBJECT-TYPE
    SYNTAX DisplayString
    ACCESS  read-only
    STATUS  mandatory
    DESCRIPTION
        "The name of the VLAN tag group for this rule."
    ::= { rsBWMCurrentRulesEntry 19 }

rsBWMCurrentRulesTrafficIdentification OBJECT-TYPE
    SYNTAX INTEGER {
        none (0),
        client (1),
        session (2),
        connection (3),
        fullL4Session (4),
        sessionCookie (5)
    }
    ACCESS  read-only
    STATUS  mandatory
    DESCRIPTION
        "This variable indicates how a traffic flow is defined for this policy."
    ::= { rsBWMCurrentRulesEntry 20 }

rsBWMCurrentRulesTrafficFlowMaxBW OBJECT-TYPE
    SYNTAX INTEGER
    ACCESS  read-only
    STATUS  mandatory
    DESCRIPTION
        "Maximum bandwidth allocated for a certain traffic flow (session) that match this rule."
    ::= { rsBWMCurrentRulesEntry 21 }

rsBWMCurrentRulesMaxConcurrentSessions OBJECT-TYPE
    SYNTAX INTEGER
    ACCESS  read-only
    STATUS  mandatory
    DESCRIPTION
        "Maximum number of sessions that can be open simultaneously per traffic flow."
    ::= { rsBWMCurrentRulesEntry 22 }

rsBWMCurrentRulesTrafficIDCookieField OBJECT-TYPE
    SYNTAX DisplayString
    ACCESS  read-only
    STATUS  mandatory
    DESCRIPTION
        "The name of cookie field for Traafic Flow ID by cookie."
    ::= { rsBWMCurrentRulesEntry 23 }

rsBWMCurrentRulesPolicyGroup OBJECT-TYPE
    SYNTAX DisplayString (SIZE(0..19))
    ACCESS  read-only
    STATUS  mandatory
    DESCRIPTION
        "Group the policies for bandwidth sharing."
    ::= { rsBWMCurrentRulesEntry 24 }

rsBWMCurrentRulesIPObjectTable OBJECT-TYPE
    SYNTAX SEQUENCE OF RsBWMCurrentRulesIPObjectEntry
    ACCESS not-accessible
    STATUS  mandatory
    DESCRIPTION
      "Table containing the grouping for ranges."
    ::=  {rsBWM 10}

rsBWMCurrentRulesIPObjectEntry OBJECT-TYPE
    SYNTAX RsBWMCurrentRulesIPObjectEntry
    ACCESS not-accessible
    STATUS  mandatory
    DESCRIPTION
       "The row definition for this table."
    INDEX {rsBWMCurrentRulesIPObjectName,rsBWMCurrentRulesIPObjectSubIndex}
    ::=  { rsBWMCurrentRulesIPObjectTable 1 }

RsBWMCurrentRulesIPObjectEntry ::= SEQUENCE {
    rsBWMCurrentRulesIPObjectName DisplayString,
    rsBWMCurrentRulesIPObjectSubIndex INTEGER,
    rsBWMCurrentRulesIPObjectAddress IpAddress,
    rsBWMCurrentRulesIPObjectMask IpAddress,
    rsBWMCurrentRulesIPObjectFromIP IpAddress,
    rsBWMCurrentRulesIPObjectToIP IpAddress,
    rsBWMCurrentRulesIPObjectMode INTEGER
}

rsBWMCurrentRulesIPObjectName OBJECT-TYPE
    SYNTAX DisplayString (SIZE(0..19))
    ACCESS  read-only
    STATUS  mandatory
    DESCRIPTION
      "The Name for the IP Object Rule, must be unique."
    ::=  { rsBWMCurrentRulesIPObjectEntry 1 }

rsBWMCurrentRulesIPObjectSubIndex OBJECT-TYPE
    SYNTAX INTEGER
    ACCESS  read-only
    STATUS  mandatory
    DESCRIPTION
       "SubIndex."
    ::=  { rsBWMCurrentRulesIPObjectEntry 2 }

rsBWMCurrentRulesIPObjectAddress OBJECT-TYPE
    SYNTAX IpAddress
    ACCESS  read-only
    STATUS  mandatory
    DESCRIPTION
      "IP address"
    ::=  { rsBWMCurrentRulesIPObjectEntry 3 }

rsBWMCurrentRulesIPObjectMask OBJECT-TYPE
    SYNTAX IpAddress
    ACCESS  read-only
    STATUS  mandatory
    DESCRIPTION
      "IP address mask."
    ::=  { rsBWMCurrentRulesIPObjectEntry 4 }

rsBWMCurrentRulesIPObjectFromIP OBJECT-TYPE
    SYNTAX IpAddress
    ACCESS  read-only
    STATUS  mandatory
    DESCRIPTION
      "The from IP Address of the range."
    ::=  { rsBWMCurrentRulesIPObjectEntry 5 }

rsBWMCurrentRulesIPObjectToIP OBJECT-TYPE
    SYNTAX IpAddress
    ACCESS  read-only
    STATUS  mandatory
    DESCRIPTION
      "The to IP Address of the range."
    ::=  { rsBWMCurrentRulesIPObjectEntry 6 }

rsBWMCurrentRulesIPObjectMode OBJECT-TYPE
    SYNTAX INTEGER {
              ipMask(1),
              ipRange(2),
			  dynamic(3)
    }
    ACCESS  read-only
    STATUS  mandatory
    DESCRIPTION
       "This variable indicates the mode of the entry. This is either
       a range or an IP address and mask."
    ::=  { rsBWMCurrentRulesIPObjectEntry 7 }

rsBWMClassificationMode OBJECT-TYPE
    SYNTAX INTEGER {
        policies(1),
        disabled(2),
        diffserv(3),
        tos(4)
    }
    ACCESS  read-write
    STATUS  mandatory
    DESCRIPTION "The rule classifiction mode"
--  DEFVAL  { disable }
    ::= { rsBWM 11 }

rsBWMMaximumBandwidth OBJECT-TYPE
    SYNTAX Counter
    ACCESS  read-only
    STATUS  mandatory
    DESCRIPTION "The maximum output bandwidth of the device. This is in Bytes"
    ::= { rsBWM 12 }

rsBWMBandwidthBorrowingMode OBJECT-TYPE
    SYNTAX INTEGER {
        enable(1),
        disable(2)
    }
    ACCESS  read-write
    STATUS  mandatory
    DESCRIPTION "Whether or not rules are able to borrow bandwidth from
    other rules"
--  DEFVAL  { disable }
    ::= { rsBWM 13 }

rsBWMActions OBJECT-TYPE
    SYNTAX INTEGER {
        updateRules(1),
        defaultDSCPs(2)
    }
    ACCESS  read-write
    STATUS  mandatory
    DESCRIPTION "Allows the application to perform specific actions"
    ::= { rsBWM 14 }

rsBWMFilterEntryTable OBJECT-TYPE
    SYNTAX SEQUENCE OF RsBWMFilterEntry
    ACCESS not-accessible
    STATUS  mandatory
    DESCRIPTION
      "Table containing the filters."
    ::= { rsBWM 15 }

rsBWMFilterEntry OBJECT-TYPE
    SYNTAX RsBWMFilterEntry
    ACCESS not-accessible
    STATUS mandatory
    DESCRIPTION
       "The row definition for this table."
    INDEX { rsBWMFilterName }
    ::=  { rsBWMFilterEntryTable 1 }

RsBWMFilterEntry ::= SEQUENCE {
    rsBWMFilterName DisplayString,
    rsBWMFilterDescription DisplayString,
    rsBWMFilterProtocol INTEGER,
    rsBWMFilterDestinationPort INTEGER,
    rsBWMFilterSourceFromPort INTEGER,
    rsBWMFilterSourceToPort INTEGER,
    rsBWMFilterOMPCOffset INTEGER,
    rsBWMFilterOMPCMask OCTET STRING,
    rsBWMFilterOMPCPattern OCTET STRING,
    rsBWMFilterOMPCCondition INTEGER,
    rsBWMFilterOMPCLength INTEGER,
    rsBWMFilterContentOffset INTEGER,
    rsBWMFilterContent DisplayString,
    rsBWMFilterContentType INTEGER,
    rsBWMFilterType INTEGER,
    rsBWMFilterStatus RowStatus,
    rsBWMFilterContentEnd INTEGER,
    rsBWMFilterContentData DisplayString,
    rsBWMFilterContentCoding INTEGER,
    rsBWMFilterContentDataCoding INTEGER,
    rsBWMFilterOMPCOffsetBase INTEGER,
    rsBWMFilterDestinationMaxPort INTEGER
}

rsBWMFilterName OBJECT-TYPE
    SYNTAX DisplayString (SIZE(0..29))
    ACCESS read-only
    STATUS mandatory
    DESCRIPTION
      "The name of the filter object."
    ::=  { rsBWMFilterEntry 1 }

rsBWMFilterDescription OBJECT-TYPE
    SYNTAX DisplayString (SIZE(0..29))
    ACCESS read-write
    STATUS mandatory
    DESCRIPTION
       "The description of the filter."
    ::=  { rsBWMFilterEntry 2 }

rsBWMFilterProtocol OBJECT-TYPE
    SYNTAX INTEGER {
        ip (1),
        tcp (2),
        udp (3),
        icmp (4),
        nonIp (5)
    }
    ACCESS read-write
    STATUS mandatory
    DESCRIPTION
      "The protocol for the filter."
--  DEFVAL  ( 1 )
    ::=  { rsBWMFilterEntry 3 }

rsBWMFilterDestinationPort OBJECT-TYPE
    SYNTAX INTEGER
    ACCESS read-write
    STATUS mandatory
    DESCRIPTION
      "The initial destination port."
    ::=  { rsBWMFilterEntry 4 }

rsBWMFilterSourceFromPort OBJECT-TYPE
    SYNTAX INTEGER
    ACCESS read-write
    STATUS mandatory
    DESCRIPTION
      "The starting source port."
    ::=  { rsBWMFilterEntry 5 }

rsBWMFilterSourceToPort OBJECT-TYPE
    SYNTAX INTEGER
    ACCESS read-write
    STATUS mandatory
    DESCRIPTION
       "The last valid source port."
    ::=  { rsBWMFilterEntry 6 }

rsBWMFilterOMPCOffset OBJECT-TYPE
    SYNTAX INTEGER
    ACCESS read-write
    STATUS mandatory
    DESCRIPTION
      "The offset of the OMPC data."
    ::=  { rsBWMFilterEntry 7 }

rsBWMFilterOMPCMask OBJECT-TYPE
    SYNTAX OCTET STRING (SIZE(4))
    ACCESS read-write
    STATUS mandatory
    DESCRIPTION
      "The mask for the OMPC object."
    ::=  { rsBWMFilterEntry 8 }

rsBWMFilterOMPCPattern OBJECT-TYPE
    SYNTAX OCTET STRING (SIZE(4))
    ACCESS read-write
    STATUS mandatory
    DESCRIPTION
      "The pattern for the OMPC data."
    ::=  { rsBWMFilterEntry 9 }

rsBWMFilterOMPCCondition OBJECT-TYPE
    SYNTAX INTEGER {
        notApplicable (1),
        equal (2),
        notEqual (3),
        greaterThan (4),
        lessThan (5)
    }
    ACCESS read-write
    STATUS mandatory
    DESCRIPTION
      "The condition for the OMPC data check."
    ::=  { rsBWMFilterEntry 10 }

rsBWMFilterOMPCLength OBJECT-TYPE
    SYNTAX INTEGER {
        oneByte (1),
        twoBytes (2),
        threeBytes (3),
        fourBytes (4),
        notApplicable (5)
    }
    ACCESS read-write
    STATUS mandatory
    DESCRIPTION
      "The length of the OMPC."
    ::=  { rsBWMFilterEntry 11 }

rsBWMFilterContentOffset OBJECT-TYPE
    SYNTAX INTEGER
    ACCESS read-write
    STATUS mandatory
    DESCRIPTION
      "The offset for the content."
    ::=  { rsBWMFilterEntry 12 }

rsBWMFilterContent OBJECT-TYPE
    SYNTAX DisplayString (SIZE(0..255))
    ACCESS read-write
    STATUS mandatory
    DESCRIPTION
      "The content to be checked."
    ::=  { rsBWMFilterEntry 13 }

rsBWMFilterContentType OBJECT-TYPE
    SYNTAX INTEGER {
        notApplicable (1),
        url (2),
        text(3),
        hostname(4),
        headertype(5),
        expression(6),
        maildomain(7),
        mailto(8),
        mailfrom(9),
        mailsubject(10),
        filetype(11),
        cookiedata(12),
        idsurl(13),
        pop3user(14),
		urilength(15)
    }
    ACCESS read-write
    STATUS mandatory
    DESCRIPTION
      "The type of content. In the case of URL only the url is checked. (No
      offset is used). In the case of text then the entire packet is checked.
      (will make use of the offset)."
    ::=  { rsBWMFilterEntry 14 }

rsBWMFilterType OBJECT-TYPE
    SYNTAX INTEGER {
        regular (1),
        static (2),
        ids (3),
        idsStatic (4)
    }
    ACCESS read-write
    STATUS mandatory
    DESCRIPTION
      "The type of object. This can be regular (user defined), static (defined
      by the application), ids (defined by the user for ids) or idsStatic 
      (defined by the application for the ids)."
    ::=  { rsBWMFilterEntry 15 }

rsBWMFilterStatus OBJECT-TYPE
    SYNTAX RowStatus 
    ACCESS read-write
    STATUS mandatory
    DESCRIPTION
      "The status of the object."
    ::=  { rsBWMFilterEntry 16 }

rsBWMFilterContentEnd OBJECT-TYPE
    SYNTAX INTEGER 
    ACCESS read-write
    STATUS mandatory
    DESCRIPTION
      "End of search data."
    ::=  { rsBWMFilterEntry 17 }

rsBWMFilterContentData OBJECT-TYPE
    SYNTAX DisplayString (SIZE(0..255))
    ACCESS read-write
    STATUS mandatory
    DESCRIPTION
      "Additional content data, used for header type entries."
    ::=  { rsBWMFilterEntry 18 }

rsBWMFilterContentCoding OBJECT-TYPE
    SYNTAX INTEGER {
        notApplicable (1),	
        caseInsensitive (2),
        caseSensitive (3),
        hex (4),
        international(5)
    }
    ACCESS read-write
    STATUS mandatory
    DESCRIPTION
      "The type of content coding that is used."
    ::=  { rsBWMFilterEntry 19 }

rsBWMFilterContentDataCoding OBJECT-TYPE
    SYNTAX INTEGER {
		notApplicable (1),	
        caseInsensitive (2),
        caseSensitive (3),
        hex (4),
        international(5)
    }
    ACCESS read-write
    STATUS mandatory
    DESCRIPTION
      "The type of content data coding that is used."
    ::=  { rsBWMFilterEntry 20 }

rsBWMFilterOMPCOffsetBase OBJECT-TYPE
    SYNTAX INTEGER {
        none (0),
        ipHeader (1),
        ipData (2),
        tcpData (3),
        asn1 (4),
        ethernet (5)
    }
    ACCESS read-write
    STATUS mandatory
    DESCRIPTION
      "The base of filter OMPC offset."
    ::=  { rsBWMFilterEntry 21 }

rsBWMFilterDestinationMaxPort OBJECT-TYPE
    SYNTAX INTEGER
    ACCESS read-write
    STATUS mandatory
    DESCRIPTION
      "The Maximal destination port of the range."
    ::=  { rsBWMFilterEntry 22 }

rsBWMCurrentFilterEntryTable OBJECT-TYPE
    SYNTAX SEQUENCE OF RsBWMCurrentFilterEntry
    ACCESS not-accessible
    STATUS  mandatory
    DESCRIPTION
      "Table containing the filters."
    ::= { rsBWM 16 }

rsBWMCurrentFilterEntry OBJECT-TYPE
    SYNTAX RsBWMCurrentFilterEntry
    ACCESS not-accessible
    STATUS mandatory
    DESCRIPTION
       "The row definition for this table."
    INDEX { rsBWMCurrentFilterName }
    ::=  { rsBWMCurrentFilterEntryTable 1 }

RsBWMCurrentFilterEntry ::= SEQUENCE {
    rsBWMCurrentFilterName DisplayString,
    rsBWMCurrentFilterDescription DisplayString,
    rsBWMCurrentFilterProtocol INTEGER,
    rsBWMCurrentFilterDestinationPort INTEGER,
    rsBWMCurrentFilterSourceFromPort INTEGER,
    rsBWMCurrentFilterSourceToPort INTEGER,
    rsBWMCurrentFilterOMPCOffset INTEGER,
    rsBWMCurrentFilterOMPCMask OCTET STRING,
    rsBWMCurrentFilterOMPCPattern OCTET STRING,
    rsBWMCurrentFilterOMPCCondition INTEGER,
    rsBWMCurrentFilterOMPCLength INTEGER,
    rsBWMCurrentFilterContentOffset INTEGER,
    rsBWMCurrentFilterContent DisplayString,
    rsBWMCurrentFilterContentType INTEGER,
    rsBWMCurrentFilterType INTEGER,
    rsBWMCurrentFilterContentEnd INTEGER,
    rsBWMCurrentFilterContentData DisplayString,
	rsBWMCurrentFilterContentCoding INTEGER,
	rsBWMCurrentFilterContentDataCoding INTEGER,
	rsBWMCurrentFilterOMPCOffsetBase INTEGER,
    rsBWMCurrentFilterDestinationMaxPort INTEGER
}

rsBWMCurrentFilterName OBJECT-TYPE
    SYNTAX DisplayString (SIZE(0..29))
    ACCESS read-only
    STATUS mandatory
    DESCRIPTION
      "The name of the filter object."
    ::=  { rsBWMCurrentFilterEntry 1 }

rsBWMCurrentFilterDescription OBJECT-TYPE
    SYNTAX DisplayString (SIZE(0..29))
    ACCESS read-only
    STATUS mandatory
    DESCRIPTION
       "The description of the filter."
    ::=  { rsBWMCurrentFilterEntry 2 }

rsBWMCurrentFilterProtocol OBJECT-TYPE
    SYNTAX INTEGER {
        ip (1),
        tcp (2),
        udp (3),
        icmp (4),
        nonIp (5)
    }
    ACCESS read-only
    STATUS mandatory
    DESCRIPTION
      "The protocol for the filter."
--  DEFVAL  ( 1 )
    ::=  { rsBWMCurrentFilterEntry 3 }

rsBWMCurrentFilterDestinationPort OBJECT-TYPE
    SYNTAX INTEGER
    ACCESS read-only
    STATUS mandatory
    DESCRIPTION
      "The initial destination port."
    ::=  { rsBWMCurrentFilterEntry 4 }

rsBWMCurrentFilterSourceFromPort OBJECT-TYPE
    SYNTAX INTEGER
    ACCESS read-only
    STATUS mandatory
    DESCRIPTION
      "The starting source port."
    ::=  { rsBWMCurrentFilterEntry 5 }

rsBWMCurrentFilterSourceToPort OBJECT-TYPE
    SYNTAX INTEGER
    ACCESS read-only
    STATUS mandatory
    DESCRIPTION
       "The last valid source port."
    ::=  { rsBWMCurrentFilterEntry 6 }

rsBWMCurrentFilterOMPCOffset OBJECT-TYPE
    SYNTAX INTEGER
    ACCESS read-only
    STATUS mandatory
    DESCRIPTION
      "The offset of the OMPC data."
    ::=  { rsBWMCurrentFilterEntry 7 }

rsBWMCurrentFilterOMPCMask OBJECT-TYPE
    SYNTAX OCTET STRING (SIZE(4))
    ACCESS read-only
    STATUS mandatory
    DESCRIPTION
      "The mask for the OMPC object."
    ::=  { rsBWMCurrentFilterEntry 8 }

rsBWMCurrentFilterOMPCPattern OBJECT-TYPE
    SYNTAX OCTET STRING (SIZE(4))
    ACCESS read-only
    STATUS mandatory
    DESCRIPTION
      "The pattern for the OMPC data."
    ::=  { rsBWMCurrentFilterEntry 9 }

rsBWMCurrentFilterOMPCCondition OBJECT-TYPE
    SYNTAX INTEGER {
        notApplicable (1),
        equal (2),
        notEqual (3),
        greaterThan (4),
        lessThan (5)
    }
    ACCESS read-only
    STATUS mandatory
    DESCRIPTION
      "The condition for the OMPC data check."
    ::=  { rsBWMCurrentFilterEntry 10 }

rsBWMCurrentFilterOMPCLength OBJECT-TYPE
    SYNTAX INTEGER {
        oneByte (1),
        twoBytes (2),
        threeBytes (3),
        fourBytes (4),
        notApplicable (5)
    }
    ACCESS read-only
    STATUS mandatory
    DESCRIPTION
      "The length of the OMPC."
    ::=  { rsBWMCurrentFilterEntry 11 }

rsBWMCurrentFilterContentOffset OBJECT-TYPE
    SYNTAX INTEGER
    ACCESS read-only
    STATUS mandatory
    DESCRIPTION
      "The offset for the content."
    ::=  { rsBWMCurrentFilterEntry 12 }

rsBWMCurrentFilterContent OBJECT-TYPE
    SYNTAX DisplayString (SIZE(0..255))
    ACCESS read-only
    STATUS mandatory
    DESCRIPTION
      "The content to be checked."
    ::=  { rsBWMCurrentFilterEntry 13 }


rsBWMCurrentFilterContentType OBJECT-TYPE
    SYNTAX INTEGER {
        notApplicable (1),
        url (2),
        text (3),
        hostname(4),
        headertype(5),
        expression(6),
        maildomain(7),
        mailto(8),
        mailfrom(9),
        mailsubject(10),
        filetype(11),
        cookiedata(12),
        idsurl(13),
        pop3user(14),
		urilength(15)
    }
    ACCESS read-only
    STATUS mandatory
    DESCRIPTION
      "The type of content that is used."
    ::=  { rsBWMCurrentFilterEntry 14 }

rsBWMCurrentFilterType OBJECT-TYPE
    SYNTAX INTEGER {
        regular (1),
        static (2),
        ids (3),
        idsStatic (4)
    }
    ACCESS read-only
    STATUS mandatory
    DESCRIPTION
      "The type of object. This can be regular (user defined), static (defined
      by the application), ids (defined by the user for ids) or idsStatic 
      (defined by the application for the ids)."
    ::=  { rsBWMCurrentFilterEntry 15 }

rsBWMCurrentFilterContentEnd OBJECT-TYPE
    SYNTAX INTEGER
    ACCESS read-only
    STATUS mandatory
    DESCRIPTION
      "End of search data."
    ::=  { rsBWMCurrentFilterEntry 16 }

rsBWMCurrentFilterContentData OBJECT-TYPE
    SYNTAX DisplayString (SIZE(0..255))
    ACCESS read-only
    STATUS mandatory
    DESCRIPTION
      "Additional content data, used for header type entries."
    ::=  { rsBWMCurrentFilterEntry 17 }

rsBWMCurrentFilterContentCoding OBJECT-TYPE
    SYNTAX INTEGER {
		notApplicable (1),	
        caseInsensitive (2),
        caseSensitive (3),
        hex (4),
        international(5)
    }
    ACCESS read-only
    STATUS mandatory
    DESCRIPTION
      "The type of content coding that is used."
    ::=  { rsBWMCurrentFilterEntry 18 }

rsBWMCurrentFilterContentDataCoding OBJECT-TYPE
    SYNTAX INTEGER {
		notApplicable (1),	
        caseInsensitive (2),
        caseSensitive (3),
        hex (4),
        international(5)
    }
    ACCESS read-only
    STATUS mandatory
    DESCRIPTION
      "The type of content data coding that is used."
    ::=  { rsBWMCurrentFilterEntry 19 }

rsBWMCurrentFilterOMPCOffsetBase OBJECT-TYPE
    SYNTAX INTEGER {
        none (0),
        ipHeader (1),
        ipData (2),
        tcpData (3),
        asn1 (4),
        ethernet (5)
    }
    ACCESS read-only
    STATUS mandatory
    DESCRIPTION
      "The base of filter OMPC offset."
    ::=  { rsBWMCurrentFilterEntry 20 }

rsBWMCurrentFilterDestinationMaxPort OBJECT-TYPE
    SYNTAX INTEGER
    ACCESS read-only
    STATUS mandatory
    DESCRIPTION
      "The Maximal destination port of the range."
    ::=  { rsBWMCurrentFilterEntry 21 }

rsBWMFilterGroupTable OBJECT-TYPE
    SYNTAX SEQUENCE OF RsBWMFilterGroup
    ACCESS not-accessible
    STATUS  mandatory
    DESCRIPTION
      "Table containing groups of filters."
    ::= { rsBWM 17 }

rsBWMFilterGroup OBJECT-TYPE
    SYNTAX RsBWMFilterGroup
    ACCESS not-accessible
    STATUS mandatory
    DESCRIPTION
       "The row definition for this table."
    INDEX { rsBWMFilterGroupName, rsBWMFilterEntryName }
    ::=  { rsBWMFilterGroupTable 1 }

RsBWMFilterGroup ::= SEQUENCE {
    rsBWMFilterGroupName DisplayString,
    rsBWMFilterEntryName DisplayString,
    rsBWMFilterGroupType INTEGER,
    rsBWMFilterGroupStatus RowStatus
}

rsBWMFilterGroupName OBJECT-TYPE
    SYNTAX DisplayString(SIZE(0..29))
    ACCESS read-only
    STATUS mandatory
    DESCRIPTION
      "The name of the group entry."
    ::=  { rsBWMFilterGroup 1 }

rsBWMFilterEntryName OBJECT-TYPE
    SYNTAX DisplayString(SIZE(0..29))
    ACCESS read-only
    STATUS mandatory
    DESCRIPTION
      "The name of the filter entry in the group."
    ::=  { rsBWMFilterGroup 2 }

rsBWMFilterGroupType OBJECT-TYPE
    SYNTAX INTEGER {
        regular (1),
        static (2),
        ids (3),
        idsStatic (4)
    }
    ACCESS read-write
    STATUS mandatory
    DESCRIPTION
      "The type of object. This can be regular (user defined), static (defined
      by the application), ids (defined by the user for ids) or idsStatic 
      (defined by the application for the ids)."
    ::=  { rsBWMFilterGroup 3 }

rsBWMFilterGroupStatus OBJECT-TYPE
    SYNTAX RowStatus 
    ACCESS read-write
    STATUS mandatory
    DESCRIPTION
      "The status of the object."
    ::=  { rsBWMFilterGroup 4 }

rsBWMCurrentFilterGroupTable OBJECT-TYPE
    SYNTAX SEQUENCE OF RsBWMCurrentFilterGroup
    ACCESS not-accessible
    STATUS  mandatory
    DESCRIPTION
      "Table containing groups of filters."
    ::= { rsBWM 18 }

rsBWMCurrentFilterGroup OBJECT-TYPE
    SYNTAX RsBWMCurrentFilterGroup
    ACCESS not-accessible
    STATUS mandatory
    DESCRIPTION
       "The row definition for this table."
    INDEX { rsBWMCurrentFilterGroupName, rsBWMCurrentFilterEntryName }
    ::=  { rsBWMCurrentFilterGroupTable 1 }

RsBWMCurrentFilterGroup ::= SEQUENCE {
    rsBWMCurrentFilterGroupName DisplayString,
    rsBWMCurrentFilterEntryName DisplayString,
    rsBWMCurrentFilterGroupType INTEGER
}

rsBWMCurrentFilterGroupName OBJECT-TYPE
    SYNTAX DisplayString(SIZE(0..29))
    ACCESS read-only
    STATUS mandatory
    DESCRIPTION
      "The name of the group entry."
    ::=  { rsBWMCurrentFilterGroup 1 }

rsBWMCurrentFilterEntryName OBJECT-TYPE
    SYNTAX DisplayString(SIZE(0..29))
    ACCESS read-only
    STATUS mandatory
    DESCRIPTION
      "The name of the filter entry in the group."
    ::=  { rsBWMCurrentFilterGroup 2 }

rsBWMCurrentFilterGroupType OBJECT-TYPE
    SYNTAX INTEGER {
        regular (1),
        static (2),
        ids (3),
        idsStatic (4)
    }
    ACCESS read-only
    STATUS mandatory
    DESCRIPTION
      "The type of object. This can be regular (user defined), static (defined
      by the application), ids (defined by the user for ids) or idsStatic 
      (defined by the application for the ids)."
    ::=  { rsBWMCurrentFilterGroup 3 }

rsBWMFilterPolicyTable OBJECT-TYPE
    SYNTAX SEQUENCE OF RsBWMFilterPolicyEntry
    ACCESS not-accessible
    STATUS  mandatory
    DESCRIPTION
      "Table containing the set of filters and group filters - used by
      rule."
    ::= { rsBWM 19 }

rsBWMFilterPolicyEntry OBJECT-TYPE
    SYNTAX RsBWMFilterPolicyEntry
    ACCESS not-accessible
    STATUS mandatory
    DESCRIPTION
       "The row definition for this table."
    INDEX { rsBWMFilterPolicyName, rsBWMFilterPolicyEntryName }
    ::=  { rsBWMFilterPolicyTable 1 }

RsBWMFilterPolicyEntry ::= SEQUENCE {
    rsBWMFilterPolicyName DisplayString,
    rsBWMFilterPolicyEntryName DisplayString,
    rsBWMFilterPolicyType INTEGER,
    rsBWMFilterPolicyStatus RowStatus,
    rsBWMFilterPolicyEntryType INTEGER
}

rsBWMFilterPolicyName OBJECT-TYPE
    SYNTAX DisplayString(SIZE(0..29))
    ACCESS read-only
    STATUS mandatory
    DESCRIPTION
      "The name of the filter policy."
    ::=  { rsBWMFilterPolicyEntry 1 }

rsBWMFilterPolicyEntryName OBJECT-TYPE
    SYNTAX DisplayString(SIZE(0..29))
    ACCESS read-only
    STATUS mandatory
    DESCRIPTION
      "The name of the filter entry. This can either be a group or a 
      filter. The device will resolve the type - i.e. filter or group."
    ::=  { rsBWMFilterPolicyEntry 2 }

rsBWMFilterPolicyType OBJECT-TYPE
    SYNTAX INTEGER {
        regular (1),
        static (2),
        ids (3),
        idsStatic (4)
    }
    ACCESS read-write
    STATUS mandatory
    DESCRIPTION
      "Denotes the type of the filter policy."
    ::=  { rsBWMFilterPolicyEntry 3 }

rsBWMFilterPolicyStatus OBJECT-TYPE
    SYNTAX RowStatus 
    ACCESS read-write
    STATUS mandatory
    DESCRIPTION
      "The status of the object."
    ::=  { rsBWMFilterPolicyEntry 4 }

rsBWMFilterPolicyEntryType OBJECT-TYPE
    SYNTAX INTEGER {
        basic (1),
        advanced (2)
    }
    ACCESS read-write
    STATUS mandatory
    DEFVAL { 1 }
    DESCRIPTION
      "Denotes the type of this filter in the policy."
    ::=  { rsBWMFilterPolicyEntry 5 }

rsBWMCurrentFilterPolicyTable OBJECT-TYPE
    SYNTAX SEQUENCE OF RsBWMCurrentFilterPolicyEntry
    ACCESS not-accessible
    STATUS  mandatory
    DESCRIPTION
      "Table containing the current set of filters and group filters - used by
      rule."
    ::= { rsBWM 20 }

rsBWMCurrentFilterPolicyEntry OBJECT-TYPE
    SYNTAX RsBWMCurrentFilterPolicyEntry
    ACCESS not-accessible
    STATUS mandatory
    DESCRIPTION
       "The row definition for this table."
    INDEX { rsBWMCurrentFilterPolicyName, rsBWMCurrentFilterPolicyEntryName }
    ::=  { rsBWMCurrentFilterPolicyTable 1 }

RsBWMCurrentFilterPolicyEntry ::= SEQUENCE {
    rsBWMCurrentFilterPolicyName DisplayString,
    rsBWMCurrentFilterPolicyEntryName DisplayString,
    rsBWMCurrentFilterPolicyType INTEGER,
	rsBWMCurrentFilterPolicyEntryType INTEGER
}

rsBWMCurrentFilterPolicyName OBJECT-TYPE
    SYNTAX DisplayString(SIZE(0..29))
    ACCESS read-only
    STATUS mandatory
    DESCRIPTION
      "The name of the filter policy."
    ::=  { rsBWMCurrentFilterPolicyEntry 1 }

rsBWMCurrentFilterPolicyEntryName OBJECT-TYPE
    SYNTAX DisplayString(SIZE(0..29))
    ACCESS read-only
    STATUS mandatory
    DESCRIPTION
      "The name of the filter entry. This can either be a group or a 
      filter. The device will resolve the type - i.e. filter or group."
    ::=  { rsBWMCurrentFilterPolicyEntry 2 }

rsBWMCurrentFilterPolicyType OBJECT-TYPE
    SYNTAX INTEGER {
        regular (1),
        static (2),
        ids (3),
        idsStatic (4)
    }
    ACCESS read-only
    STATUS mandatory
    DESCRIPTION
      "Denotes the type of the filter policy."
    ::=  { rsBWMCurrentFilterPolicyEntry 3 }

rsBWMCurrentFilterPolicyEntryType OBJECT-TYPE
    SYNTAX INTEGER {
        basic (1),
        advanced (2)
    }
    ACCESS read-only
    STATUS mandatory
    DESCRIPTION
      "Denotes the type of this filter in the policy."
    ::=  { rsBWMCurrentFilterPolicyEntry 4 }

rsBWMApplicationClassification OBJECT-TYPE
    SYNTAX INTEGER {
        enable (1),
        disable (2)
    }
    ACCESS  read-write
    STATUS  mandatory
    DESCRIPTION "Defines the nature of the application classification.
    Enable entails that the client entry is classified and the rule is
    appended to the client table. Disable implies that the data will be
    classified in the forwarding table. That is, each packet for the 
    client entry will be classified."
--  DEFVAL  { disable }
    ::= { rsBWM 21 } 

rsBWMPortBandwidthEntryTable OBJECT-TYPE
    SYNTAX SEQUENCE OF RsBWMPortBandwidthEntry
    ACCESS not-accessible
    STATUS  mandatory
    DESCRIPTION
      "Table containing the bandwidth for each port."
    ::= { rsBWM 22 }

rsBWMPortBandwidthEntry OBJECT-TYPE
    SYNTAX RsBWMPortBandwidthEntry
    ACCESS not-accessible
    STATUS mandatory
    DESCRIPTION
       "The row definition for this table."
    INDEX { rsBWMPortIndex }
    ::=  { rsBWMPortBandwidthEntryTable 1 }

RsBWMPortBandwidthEntry ::= SEQUENCE {
    rsBWMPortIndex INTEGER,
    rsBWMPortBandwidth Integer32,
    rsBwmPortUsedBandwidth Integer32
}

rsBWMPortIndex OBJECT-TYPE
    SYNTAX INTEGER
    ACCESS read-only
    STATUS mandatory
    DESCRIPTION
      "The index of the bandwidths."
    ::=  { rsBWMPortBandwidthEntry 1 }

rsBWMPortBandwidth OBJECT-TYPE
    SYNTAX Integer32
    ACCESS read-write
    STATUS mandatory
    DESCRIPTION
      "The bandwidth of the specific port."
    ::=  { rsBWMPortBandwidthEntry 2 }

rsBwmPortUsedBandwidth OBJECT-TYPE
    SYNTAX Integer32
    ACCESS read-only
    STATUS mandatory
    DESCRIPTION
      "The bandwidth of the specific port."
    ::=  { rsBWMPortBandwidthEntry 3 }

rsBWMTuning OBJECT IDENTIFIER ::= { rsBWM 23 }

rsBWMPolicyTuning OBJECT IDENTIFIER ::= { rsBWMTuning 1 }

rsBWMPolicyEntries OBJECT-TYPE
    SYNTAX INTEGER
    ACCESS  read-only
    STATUS  mandatory
    DESCRIPTION
      "Maximum number of policy entries."
    ::= { rsBWMPolicyTuning 1 }

rsBWMPolicyEntriesAfterReset OBJECT-TYPE
    SYNTAX INTEGER
    ACCESS  read-write
    STATUS  mandatory
    DESCRIPTION
      "Future maximum maximum number of policy entries."
    ::=  { rsBWMPolicyTuning 2 }

rsBWMNetworkTuning OBJECT IDENTIFIER ::= { rsBWMTuning 2 }

rsBWMNetworkEntries OBJECT-TYPE
    SYNTAX INTEGER
    ACCESS  read-only
    STATUS  mandatory
    DESCRIPTION
      "Maximum number of network entries."
    ::= { rsBWMNetworkTuning 1 }

rsBWMNetworkEntriesAfterReset OBJECT-TYPE
    SYNTAX INTEGER
    ACCESS  read-write
    STATUS  mandatory
    DESCRIPTION
      "Future maximum maximum number of network entries."
    ::=  { rsBWMNetworkTuning 2 }

rsBWMFilterTuning OBJECT IDENTIFIER ::= { rsBWMTuning 3 }

rsBWMFilterEntries OBJECT-TYPE
    SYNTAX INTEGER
    ACCESS  read-only
    STATUS  mandatory
    DESCRIPTION
      "Maximum number of filter entries."
    ::= { rsBWMFilterTuning 1 }

rsBWMFilterEntriesAfterReset OBJECT-TYPE
    SYNTAX INTEGER
    ACCESS  read-write
    STATUS  mandatory
    DESCRIPTION
      "Future maximum maximum number of filter entries."
    ::=  { rsBWMFilterTuning 2 }

rsBWMAdvancedTuning OBJECT IDENTIFIER ::= { rsBWMTuning 4 }

rsBWMAdvancedEntries OBJECT-TYPE
    SYNTAX INTEGER
    ACCESS  read-only
    STATUS  mandatory
    DESCRIPTION
      "Maximum number of advanced entries."
    ::= { rsBWMAdvancedTuning 1 }

rsBWMAdvancedEntriesAfterReset OBJECT-TYPE
    SYNTAX INTEGER
    ACCESS  read-write
    STATUS  mandatory
    DESCRIPTION
      "Future maximum maximum number of advanced entries."
    ::=  { rsBWMAdvancedTuning 2 }

rsBWMGroupTuning OBJECT IDENTIFIER ::= { rsBWMTuning 5 }

rsBWMGroupEntries OBJECT-TYPE
    SYNTAX INTEGER
    ACCESS  read-only
    STATUS  mandatory
    DESCRIPTION
      "Maximum number of group entries."
    ::= { rsBWMGroupTuning 1 }

rsBWMGroupEntriesAfterReset OBJECT-TYPE
    SYNTAX INTEGER
    ACCESS  read-write
    STATUS  mandatory
    DESCRIPTION
      "Future maximum maximum number of group entries."
    ::=  { rsBWMGroupTuning 2 }

rsBWMDestinationTuning OBJECT IDENTIFIER ::= { rsBWMTuning 6 }
rsBWMDestinationEntries OBJECT-TYPE
    SYNTAX INTEGER
    ACCESS  read-only
    STATUS  mandatory
    DESCRIPTION
      "Maximum number of destination entries."
    ::= { rsBWMDestinationTuning 1 }

rsBWMDestinationEntriesAfterReset OBJECT-TYPE
    SYNTAX INTEGER
    ACCESS  read-write
    STATUS  mandatory
    DESCRIPTION
      "Future maximum maximum number of destination entries."
    ::=  { rsBWMDestinationTuning 2 }

rsBWMSessionTuning OBJECT IDENTIFIER ::= { rsBWMTuning 7 }

rsBWMSessionEntries OBJECT-TYPE
    SYNTAX INTEGER
    ACCESS  read-only
    STATUS  mandatory
    DESCRIPTION
      "Maximum number of session table."
    ::= { rsBWMSessionTuning 1 }

rsBWMSessionEntriesAfterReset OBJECT-TYPE
    SYNTAX INTEGER
    ACCESS  read-write
    STATUS  mandatory
    DESCRIPTION
      "Future maximum maximum number of session table entries."
    ::=  { rsBWMSessionTuning 2 }

rsBWMChainTuning OBJECT IDENTIFIER ::= { rsBWMTuning 8 }

rsBWMMaxChainPolicies OBJECT-TYPE
    SYNTAX INTEGER
    ACCESS  read-only
    STATUS  mandatory
    DESCRIPTION
      "Maximum number of chain (farm cluster) policies."
    ::= { rsBWMChainTuning 1 }

rsBWMMaxChainPoliciesAfterReset OBJECT-TYPE
    SYNTAX INTEGER
    ACCESS  read-write
    STATUS  mandatory
    DESCRIPTION
      "Future maximum number of chain (farm cluster) policies."
    ::=  { rsBWMChainTuning 2 }

rsBWMDSCPEntryTable OBJECT-TYPE
    SYNTAX SEQUENCE OF RsBWMDSCPEntry
    ACCESS not-accessible
    STATUS  mandatory
    DESCRIPTION
      "Table containing priority and bandwidth for each DSCP."
    ::= { rsBWM 24 }

rsBWMDSCPEntry OBJECT-TYPE
    SYNTAX RsBWMDSCPEntry
    ACCESS not-accessible
    STATUS mandatory
    DESCRIPTION
       "The row definition for this table."
    INDEX { rsBWMDSCP }
    ::=  { rsBWMDSCPEntryTable 1 }

RsBWMDSCPEntry ::= SEQUENCE {
    rsBWMDSCP INTEGER,
    rsBWMDSCPPriority INTEGER,
    rsBWMDSCPGuaranteedBW Integer32,
    rsBWMDSCPMaxBW Integer32
}

rsBWMDSCP OBJECT-TYPE
    SYNTAX INTEGER (0..63)
    ACCESS read-only
    STATUS mandatory
    DESCRIPTION
      "The DSCP - the value of DiffServ field in the IP header."
    ::=  { rsBWMDSCPEntry 1 }

rsBWMDSCPPriority OBJECT-TYPE
    SYNTAX INTEGER (65535 | 0..7)
    ACCESS read-write
    STATUS mandatory
    DESCRIPTION
      "The priority of the packets with the specified DSCP."
    DEFVAL { 0 }
    ::=  { rsBWMDSCPEntry 2 }

rsBWMDSCPGuaranteedBW OBJECT-TYPE
    SYNTAX Integer32
    ACCESS read-write
    STATUS mandatory
    DESCRIPTION
      "The bandwidth allocated for the specified DSCP."
    ::=  { rsBWMDSCPEntry 3 }

rsBWMDSCPMaxBW OBJECT-TYPE
    SYNTAX Integer32
    ACCESS read-write
    STATUS mandatory
    DESCRIPTION
      "The maximum bandwidth for the specified DSCP."
    ::=  { rsBWMDSCPEntry 4 }

rsBWMCurrentDSCPEntryTable OBJECT-TYPE
    SYNTAX SEQUENCE OF RsBWMCurrentDSCPEntry
    ACCESS not-accessible
    STATUS  mandatory
    DESCRIPTION
      "Table containing priority and bandwidth for each DSCP."
    ::= { rsBWM 25 }

rsBWMCurrentDSCPEntry OBJECT-TYPE
    SYNTAX RsBWMCurrentDSCPEntry
    ACCESS not-accessible
    STATUS mandatory
    DESCRIPTION
       "The row definition for this table."
    INDEX { rsBWMCurrentDSCP }
    ::=  { rsBWMCurrentDSCPEntryTable 1 }

RsBWMCurrentDSCPEntry ::= SEQUENCE {
    rsBWMCurrentDSCP INTEGER,
    rsBWMCurrentDSCPPriority INTEGER,
    rsBWMCurrentDSCPGuaranteedBW Counter,
    rsBWMCurrentDSCPMaxBW Counter
}

rsBWMCurrentDSCP OBJECT-TYPE
    SYNTAX INTEGER (0..63)
    ACCESS read-only
    STATUS mandatory
    DESCRIPTION
      "The DSCP - the value of DiffServ field in the IP header."
    ::=  { rsBWMCurrentDSCPEntry 1 }

rsBWMCurrentDSCPPriority OBJECT-TYPE
    SYNTAX INTEGER (65535 | 0..7)
    ACCESS read-write
    STATUS mandatory
    DESCRIPTION
      "The priority of the packets with the specified DSCP."
    ::=  { rsBWMCurrentDSCPEntry 2 }

rsBWMCurrentDSCPGuaranteedBW OBJECT-TYPE
    SYNTAX Counter
    ACCESS read-write
    STATUS mandatory
    DESCRIPTION
      "The bandwidth allocated for the specified DSCP."
    ::=  { rsBWMCurrentDSCPEntry 3 }

rsBWMCurrentDSCPMaxBW OBJECT-TYPE
    SYNTAX Counter
    ACCESS read-write
    STATUS mandatory
    DESCRIPTION
      "The maximum bandwidth for the specified DSCP."
    ::=  { rsBWMCurrentDSCPEntry 4 }

rsBWMVersion OBJECT-TYPE
    SYNTAX DisplayString
    ACCESS  read-only
    STATUS  mandatory
    DESCRIPTION
        "The current QoS software version."
    ::= { rsBWM 26 }

rsBWMBwmPortOperationTable OBJECT-TYPE
    SYNTAX SEQUENCE OF RsBWMBwmPortOperationEntry
    ACCESS not-accessible
    STATUS  mandatory
    DESCRIPTION
      "Table containing the operation for each port."
    ::= { rsBWM 27 }

rsBWMBwmPortOperationEntry OBJECT-TYPE
    SYNTAX RsBWMBwmPortOperationEntry
    ACCESS not-accessible
    STATUS mandatory
    DESCRIPTION
       "The row definition for this table."
    INDEX { rsBWMBwmInboundPort, rsBWMBwmOutboundPort }
    ::=  { rsBWMBwmPortOperationTable 1 }

RsBWMBwmPortOperationEntry ::= SEQUENCE {
     rsBWMBwmInboundPort INTEGER,
     rsBWMBwmOutboundPort INTEGER,
     rsBWMBwmDirection INTEGER,
     rsBWMBwmOperationStatus RowStatus
}

rsBWMBwmInboundPort OBJECT-TYPE
    SYNTAX INTEGER
    ACCESS read-only
    STATUS mandatory
    DESCRIPTION
      "The index of the inbound port."
    ::=  { rsBWMBwmPortOperationEntry 1 }

rsBWMBwmOutboundPort OBJECT-TYPE
    SYNTAX INTEGER
    ACCESS read-only
    STATUS mandatory
    DESCRIPTION
      "The index of the outbound port."
    ::=  { rsBWMBwmPortOperationEntry 2 }

rsBWMBwmDirection OBJECT-TYPE
    SYNTAX INTEGER {
              oneway(1),
              twoway(2) }
    ACCESS  read-write
    STATUS  mandatory
    DESCRIPTION
       "This variable indicates the direction of the incoming packet."
    DEFVAL { 1 }
    ::=  { rsBWMBwmPortOperationEntry 3 }

rsBWMBwmOperationStatus OBJECT-TYPE
    SYNTAX RowStatus
    ACCESS read-write
    STATUS mandatory
    DESCRIPTION
      "The status of the current entry. "
    ::=  { rsBWMBwmPortOperationEntry 4 }

rsBWMBwmVLANOperationTable OBJECT-TYPE
    SYNTAX SEQUENCE OF RsBWMBwmVLANOperationEntry
    ACCESS not-accessible
    STATUS  mandatory
    DESCRIPTION
      "Table containing the operation for each VLAN."
    ::= { rsBWM 28 }

rsBWMBwmVLANOperationEntry OBJECT-TYPE
    SYNTAX RsBWMBwmVLANOperationEntry
    ACCESS not-accessible
    STATUS mandatory
    DESCRIPTION
       "The row definition for this table."
    INDEX { rsBWMBwmVLAN}
    ::=  { rsBWMBwmVLANOperationTable 1 }

RsBWMBwmVLANOperationEntry ::= SEQUENCE {
     rsBWMBwmVLAN INTEGER,
     rsBWMBwmVLANOperationStatus RowStatus
}

rsBWMBwmVLAN OBJECT-TYPE
    SYNTAX INTEGER
    ACCESS read-only
    STATUS mandatory
    DESCRIPTION
      "The VLAN."
    ::=  { rsBWMBwmVLANOperationEntry 1 }

rsBWMBwmVLANOperationStatus OBJECT-TYPE
    SYNTAX RowStatus
    ACCESS read-write
    STATUS mandatory
    DESCRIPTION
      "The status of the current entry. "
    ::=  { rsBWMBwmVLANOperationEntry 2 }

rsBWMSessionAgingTime OBJECT-TYPE
    SYNTAX INTEGER
    ACCESS  read-write
    STATUS  mandatory
    DESCRIPTION
        "The aging time for the session table."
    ::= {rsBWM 29}

rsBWMStatisticsTable OBJECT-TYPE
    SYNTAX SEQUENCE OF RsBWMStatisticsEntry
    ACCESS not-accessible
    STATUS  mandatory
    DESCRIPTION
      "Table containing statistics data for rules"
    ::=  {rsBWM 30}

rsBWMStatisticsEntry OBJECT-TYPE
    SYNTAX RsBWMStatisticsEntry
    ACCESS not-accessible
    STATUS  mandatory
    DESCRIPTION
       "The row definition for this table."
    INDEX { rsBWMStatisticsPolicyName }
    ::=  { rsBWMStatisticsTable 1 }

RsBWMStatisticsEntry ::= SEQUENCE {
    rsBWMStatisticsPolicyName DisplayString,
    rsBWMStatisticsBandwidthUsedLastSec Counter,
    rsBWMStatisticsPacketNumberLastSec Counter,
    rsBWMStatisticsFullQueueFailuresBWLastSec Counter,
    rsBWMStatisticsAgedPacketsFailuresBWLastSec Counter,
    rsBWMStatisticsGuaranteedReachedLastSec TruthValue,
    rsBWMStatisticsMaximumReachedLastSec TruthValue,    
    rsBWMStatisticsBandwidthUsedLastPeriod Counter,
    rsBWMStatisticsPeakBandwidthLastPeriod Counter,
    rsBWMStatisticsPacketNumberLastPeriod Counter,
    rsBWMStatisticsFullQueueFailuresBWLastPeriod Counter,
    rsBWMStatisticsAgedPacketsFailuresBWLastPeriod Counter,
    rsBWMStatisticsGuaranteedReachedCounterLastPeriod INTEGER,
    rsBWMStatisticsMaximumReachedCounterLastPeriod INTEGER,
    rsBWMStatisticsMatchedBandwidthLastSec Counter,
    rsBWMStatisticsMatchedBandwidthLastPeriod Counter
}

rsBWMStatisticsPolicyName OBJECT-TYPE
    SYNTAX DisplayString (SIZE(0..19))
    ACCESS  read-only
    STATUS  mandatory
    DESCRIPTION
      "The name of the rule."
    ::=  {rsBWMStatisticsEntry 1}

rsBWMStatisticsBandwidthUsedLastSec OBJECT-TYPE
    SYNTAX Counter
    ACCESS  read-only
    STATUS  mandatory
    DESCRIPTION
       "The bandwidth used by the rule in the last second."
    ::=  {rsBWMStatisticsEntry 2}

rsBWMStatisticsPacketNumberLastSec OBJECT-TYPE
    SYNTAX Counter
    ACCESS  read-only
    STATUS  mandatory
    DESCRIPTION
       "The number of packets that match the rule in the last second."
    ::=  {rsBWMStatisticsEntry 3}

rsBWMStatisticsFullQueueFailuresBWLastSec OBJECT-TYPE
    SYNTAX Counter
    ACCESS  read-only
    STATUS  mandatory
    DESCRIPTION
       "The amount of bandwidth that the device failed to allocate in the last second."
    ::=  {rsBWMStatisticsEntry 4}

rsBWMStatisticsAgedPacketsFailuresBWLastSec OBJECT-TYPE
    SYNTAX Counter
    ACCESS  read-only
    STATUS  mandatory
    DESCRIPTION
	   "The amount of bandwidth that the device failed to allocate in the last second, 
	    since the packets were discarded because of aging."
    ::=  {rsBWMStatisticsEntry 5}

rsBWMStatisticsGuaranteedReachedLastSec OBJECT-TYPE
    SYNTAX TruthValue
    ACCESS  read-only
    STATUS  mandatory
    DESCRIPTION
	   "Whether the guaranteed bandwidth threshold was reached in the last second."
    ::=  {rsBWMStatisticsEntry 6}

rsBWMStatisticsMaximumReachedLastSec OBJECT-TYPE
    SYNTAX TruthValue
    ACCESS  read-only
    STATUS  mandatory
    DESCRIPTION
	   "The number of times the maximum bandwidth threshold was reached in the last second."
    ::=  {rsBWMStatisticsEntry 7}

rsBWMStatisticsBandwidthUsedLastPeriod OBJECT-TYPE
    SYNTAX Counter
    ACCESS  read-only
    STATUS  mandatory
    DESCRIPTION
       "The bandwidth used by the rule in the last sampling period 
            defined in rsBWMStatisticsReportingPeriod."
    ::=  {rsBWMStatisticsEntry 8}

rsBWMStatisticsPeakBandwidthLastPeriod OBJECT-TYPE
    SYNTAX Counter
    ACCESS  read-only
    STATUS  mandatory
    DESCRIPTION
       "The highest bandwidth in the last sampling period defined in 
            rsBWMStatisticsReportingPeriod."
    ::=  {rsBWMStatisticsEntry 9}

rsBWMStatisticsPacketNumberLastPeriod OBJECT-TYPE
    SYNTAX Counter
    ACCESS  read-only
    STATUS  mandatory
    DESCRIPTION
       "The number of packets that match the rule in the last sampling period
            defined in rsBWMStatisticsReportingPeriod."
    ::=  {rsBWMStatisticsEntry 10}

rsBWMStatisticsFullQueueFailuresBWLastPeriod OBJECT-TYPE
    SYNTAX Counter
    ACCESS  read-only
    STATUS  mandatory
    DESCRIPTION
       "The amount of bandwidth that the device failed to allocate in the last sampling 
                period defined in rsBWMStatisticsReportingPeriod, because the queue was full."
    ::=  {rsBWMStatisticsEntry 11}

rsBWMStatisticsAgedPacketsFailuresBWLastPeriod OBJECT-TYPE
    SYNTAX Counter
    ACCESS  read-only
    STATUS  mandatory
    DESCRIPTION
	   "The amount of bandwidth that the device failed to allocate in the last sampling 
                period defined in rsBWMStatisticsReportingPeriod, since the packets were discarded
		because of aging."
    ::=  {rsBWMStatisticsEntry 12}

rsBWMStatisticsGuaranteedReachedCounterLastPeriod OBJECT-TYPE
    SYNTAX INTEGER
    ACCESS  read-only
    STATUS  mandatory
    DESCRIPTION
	   "The number of times the guaranteed bandwidth threshold was reached in the last
            sampling period defined in rsBWMStatisticsReportingPeriod."
    ::=  {rsBWMStatisticsEntry 13}

rsBWMStatisticsMaximumReachedCounterLastPeriod OBJECT-TYPE
    SYNTAX INTEGER
    ACCESS  read-only
    STATUS  mandatory
    DESCRIPTION
	   "The number of times the maximum bandwidth threshold was reached in the last
            sampling period defined in rsBWMStatisticsReportingPeriod."
    ::=  {rsBWMStatisticsEntry 14}

rsBWMStatisticsMatchedBandwidthLastSec OBJECT-TYPE
    SYNTAX Counter
    ACCESS  read-only
    STATUS  mandatory
    DESCRIPTION
           "The matched bandwidth in the last second."
    ::=  {rsBWMStatisticsEntry 15}

rsBWMStatisticsMatchedBandwidthLastPeriod OBJECT-TYPE
    SYNTAX Counter
    ACCESS  read-only
    STATUS  mandatory
    DESCRIPTION
           "The matched bandwidth in the last sampling period."
    ::=  {rsBWMStatisticsEntry 16}

rsBWMStatisticsMonitorPolicy OBJECT-TYPE
    SYNTAX INTEGER {
        enabled(1),
        disabled(2) }
    ACCESS  read-write
    STATUS  mandatory
    DESCRIPTION
        "This variable indicates whether the device will gather policies' statistics."
    DEFVAL  { disabled }
    ::=  {rsBWMStatisticsTable 2}

rsBWMStatisticsTableUseSRP OBJECT-TYPE
    SYNTAX TruthValue
    ACCESS  read-write
    STATUS  mandatory
    DESCRIPTION
        "This variable indicates whether the device will send the data to ConfigWare using SRP."
    DEFVAL  { false }
    ::=  {rsBWMStatisticsTable 3}

rsBWMStatisticsReportingPeriod OBJECT-TYPE
    SYNTAX INTEGER
    ACCESS  read-write
    STATUS  mandatory
    DESCRIPTION
        "This variable indicates reporting frequency (in seconds) using SRP for BWM."
    DEFVAL  { 60 } 
    ::=  {rsBWMStatisticsTable 4}

rsBWMSamplingRatio OBJECT-TYPE
    SYNTAX INTEGER
    ACCESS  read-write
    STATUS  mandatory
    DESCRIPTION "Sampling ratio: one of how many packets is sampled."
	DEFVAL  {100}
    ::= {rsBWM 31}

rsBWMSamplerOverloadMode OBJECT-TYPE
    SYNTAX INTEGER {
        forward(1),
        discard(2)
    }
    ACCESS  read-write
    STATUS  mandatory
    DESCRIPTION "Overload mechanism mode: forward/discard excess traffic."
	DEFVAL  {forward}
    ::= {rsBWM 32}

rsBWMChainRulesTable OBJECT-TYPE
    SYNTAX SEQUENCE OF RsBWMChainRulesEntry
    ACCESS not-accessible
    STATUS  mandatory
    DESCRIPTION
      "Table containing the list of chain rules for classifer data base,
       these rules can be used to classify packets for chaining."
    ::=  {rsBWM 33}

rsBWMChainRulesEntry OBJECT-TYPE
    SYNTAX RsBWMChainRulesEntry
    ACCESS not-accessible
    STATUS  mandatory
    DESCRIPTION
       "The row definition for this table."
    INDEX { rsBWMChainRulesName }
    ::=  { rsBWMChainRulesTable 1 }

RsBWMChainRulesEntry ::= SEQUENCE {
    rsBWMChainRulesIndex INTEGER,
    rsBWMChainRulesName DisplayString,
    rsBWMChainRulesDestination DisplayString,
    rsBWMChainRulesSource DisplayString,
    rsBWMChainRulesStatus  RowStatus,
    rsBWMChainRulesDirection INTEGER,
    rsBWMChainRulesDescription DisplayString,
    rsBWMChainRulesPolicyType INTEGER,
    rsBWMChainRulesPolicy DisplayString,
    rsBWMChainRulesOperationalStatus INTEGER,
    rsBWMChainRulesSpecific DisplayString,
    rsBWMChainRulesPhysicalPortGroup DisplayString,
    rsBWMChainRulesVLANTagGroup DisplayString,
    rsBWMChainRulesDSCPMarking INTEGER
}

rsBWMChainRulesIndex OBJECT-TYPE
    SYNTAX INTEGER
    ACCESS  read-write
    STATUS  mandatory
    DESCRIPTION
       "This variable indicates the administrative index of a line it
       determines the order of the rules."
    ::=  { rsBWMChainRulesEntry 1 }

rsBWMChainRulesName OBJECT-TYPE
    SYNTAX DisplayString (SIZE(0..19))
    ACCESS  read-only
    STATUS  mandatory
    DESCRIPTION
      "The Name for the Rule must be unique."
    ::=  {rsBWMChainRulesEntry 2}

rsBWMChainRulesDestination OBJECT-TYPE
    SYNTAX DisplayString (SIZE(0..19))
    ACCESS  read-write
    STATUS  mandatory
    DESCRIPTION
      "The destination address / range of address for the packet, the name is
      defined in the Objects table or can be an IP address."
    ::=  {rsBWMChainRulesEntry 3}

rsBWMChainRulesSource OBJECT-TYPE
    SYNTAX DisplayString (SIZE(0..19))
    ACCESS  read-write
    STATUS  mandatory
    DESCRIPTION
      "The source address / range of address for the packet, the name is
      defined in the Objects table or can be an IP address."
    ::=  {rsBWMChainRulesEntry 4}

rsBWMChainRulesStatus OBJECT-TYPE
    SYNTAX RowStatus
    ACCESS  read-write
    STATUS  mandatory
    DESCRIPTION
       "This variable indicates the administrative status of this entry.
        Used to delete an entry of this table."
    ::=  { rsBWMChainRulesEntry 5 }

rsBWMChainRulesDirection OBJECT-TYPE
    SYNTAX INTEGER {
              oneway(1),
              twoway(2) }
    ACCESS  read-write
    STATUS  mandatory
    DESCRIPTION
       "This variable indicates the direction of the incoming packet."
    DEFVAL { 1 }
    ::=  { rsBWMChainRulesEntry 6 }

rsBWMChainRulesDescription OBJECT-TYPE
    SYNTAX DisplayString (SIZE(0..19))
    ACCESS  read-write
    STATUS  mandatory
    DESCRIPTION
      "Description."
    ::=  { rsBWMChainRulesEntry 7 }

rsBWMChainRulesPolicyType OBJECT-TYPE
    SYNTAX INTEGER {
              none(1),
              filter(2),
              group(3),
              policy(4)}
    ACCESS  read-write
    STATUS  mandatory
    DESCRIPTION
       "The type of policy - i.e. if this is a filter, group or policy."
    DEFVAL  { 1 }
    ::=  { rsBWMChainRulesEntry 8 }

rsBWMChainRulesPolicy OBJECT-TYPE
    SYNTAX DisplayString (SIZE(0..29))
    ACCESS  read-write
    STATUS  mandatory
    DESCRIPTION
       "The name for the filter policy for the rule."
    ::=  { rsBWMChainRulesEntry 9 }

rsBWMChainRulesOperationalStatus OBJECT-TYPE
    SYNTAX INTEGER {
        active (1),
        inactive (2)
    }
    ACCESS  read-write
    STATUS  mandatory
    DESCRIPTION
       "This variable indicates if the rule is active or inactive.
        The active rule table contains only active rules."
    ::= { rsBWMChainRulesEntry 10 }

rsBWMChainRulesSpecific OBJECT-TYPE
    SYNTAX DisplayString (SIZE(0..19))
    ACCESS  read-write
    STATUS  mandatory
    DESCRIPTION
       "This variable indicates if there is additional data to the 
       policy."
    ::= { rsBWMChainRulesEntry 11 }

rsBWMChainRulesPhysicalPortGroup OBJECT-TYPE
    SYNTAX DisplayString
    ACCESS  read-write
    STATUS  mandatory
    DESCRIPTION
       "The name of the physical port group for this rule."
    ::=  { rsBWMChainRulesEntry 12 }

rsBWMChainRulesVLANTagGroup OBJECT-TYPE
    SYNTAX DisplayString
    ACCESS  read-write
    STATUS  mandatory
    DESCRIPTION
        "The name of the VLAN tag group for this rule."
    ::= { rsBWMChainRulesEntry 13 }

rsBWMChainRulesDSCPMarking OBJECT-TYPE
    SYNTAX INTEGER (-1 | 0..63)
    ACCESS  read-write
    STATUS  mandatory
    DESCRIPTION
       "This variable indicates the DSCP value to mark the ToS field in the IP header
        in the matching packets. If equals -1, the marking is not performed."
    ::= { rsBWMChainRulesEntry 14 }

rsBWMCurrentChainRulesTable OBJECT-TYPE
    SYNTAX SEQUENCE OF RsBWMCurrentChainRulesEntry
    ACCESS not-accessible
    STATUS  mandatory
    DESCRIPTION
      "Table containing the list of chain rules for classifer data base,
       these rules can be used to classify packets for chaining."
    ::=  {rsBWM 34}

rsBWMCurrentChainRulesEntry OBJECT-TYPE
    SYNTAX RsBWMCurrentChainRulesEntry
    ACCESS not-accessible
    STATUS  mandatory
    DESCRIPTION
       "The row definition for this table."
    INDEX { rsBWMCurrentChainRulesName }
    ::=  { rsBWMCurrentChainRulesTable 1 }

RsBWMCurrentChainRulesEntry ::= SEQUENCE {
    rsBWMCurrentChainRulesIndex INTEGER,
    rsBWMCurrentChainRulesName DisplayString,
    rsBWMCurrentChainRulesDestination DisplayString,
    rsBWMCurrentChainRulesSource DisplayString,
    rsBWMCurrentChainRulesDirection INTEGER,
    rsBWMCurrentChainRulesDescription DisplayString,
    rsBWMCurrentChainRulesPolicyType INTEGER,
    rsBWMCurrentChainRulesPolicy DisplayString,
    rsBWMCurrentChainRulesSpecific DisplayString,
    rsBWMCurrentChainBandwidthLastSec Counter,
    rsBWMCurrentChainPacketsLastSec Counter,
    rsBWMCurrentChainRulesPhysicalPortGroup DisplayString,
    rsBWMCurrentChainRulesVLANTagGroup DisplayString,
    rsBWMCurrentChainRulesDSCPMarking INTEGER
}

rsBWMCurrentChainRulesIndex OBJECT-TYPE
    SYNTAX INTEGER
    ACCESS  read-only
    STATUS  mandatory
    DESCRIPTION
       "This variable indicates the administrative index of a line it
       determine the order of the rules."
    ::=  { rsBWMCurrentChainRulesEntry 1 }

rsBWMCurrentChainRulesName OBJECT-TYPE
    SYNTAX DisplayString (SIZE(0..19))
    ACCESS  read-only
    STATUS  mandatory
    DESCRIPTION
      "The Name for the Rule must be unique."
    ::=  {rsBWMCurrentChainRulesEntry 2}

rsBWMCurrentChainRulesDestination OBJECT-TYPE
    SYNTAX DisplayString (SIZE(0..19))
    ACCESS  read-only
    STATUS  mandatory
    DESCRIPTION
      "The destination address / range of address for the packet, the name is
      defined in the Objects table or can be an IP address."
    ::=  {rsBWMCurrentChainRulesEntry 3}

rsBWMCurrentChainRulesSource OBJECT-TYPE
    SYNTAX DisplayString (SIZE(0..19))
    ACCESS  read-only
    STATUS  mandatory
    DESCRIPTION
      "The source address / range of address for the packet, the name is
      defined in the Objects table or can be an IP address."
    ::=  {rsBWMCurrentChainRulesEntry 4}

rsBWMCurrentChainRulesDirection OBJECT-TYPE
    SYNTAX INTEGER {
              oneway(1),
              twoway(2) }
    ACCESS read-only
    STATUS mandatory
    DESCRIPTION
       "This variable indicates the direction of the incoming packet."
    ::=  { rsBWMCurrentChainRulesEntry 5 }

rsBWMCurrentChainRulesDescription OBJECT-TYPE
    SYNTAX DisplayString (SIZE(0..19))
    ACCESS  read-only
    STATUS  mandatory
    DESCRIPTION
      "Description."
    ::=  { rsBWMCurrentChainRulesEntry 6 }

rsBWMCurrentChainRulesPolicyType OBJECT-TYPE
    SYNTAX INTEGER {
              none(1),
              filter(2),
              group(3),
              policy(4)}
    ACCESS  read-only
    STATUS  mandatory
    DESCRIPTION
       "The type of policy - i.e. if this is a filter, group or policy."
    DEFVAL  { 1 }
    ::=  { rsBWMCurrentChainRulesEntry 7 }

rsBWMCurrentChainRulesPolicy OBJECT-TYPE
    SYNTAX DisplayString (SIZE(0..29))
    ACCESS  read-only
    STATUS  mandatory
    DESCRIPTION
       "The name for the filter policy for the rule."
    ::=  { rsBWMCurrentChainRulesEntry 8 }

rsBWMCurrentChainRulesSpecific OBJECT-TYPE
    SYNTAX DisplayString (SIZE(0..19))
    ACCESS  read-only
    STATUS  mandatory
    DESCRIPTION
       "This variable indicates if there is additional data to the 
       policy."
    ::= { rsBWMCurrentChainRulesEntry 9 }

rsBWMCurrentChainBandwidthLastSec OBJECT-TYPE
    SYNTAX Counter
    ACCESS  read-only
    STATUS  mandatory
    DESCRIPTION
       "The bandwidth used by the policy in the last second."
    ::=  {rsBWMCurrentChainRulesEntry 10}

rsBWMCurrentChainPacketsLastSec OBJECT-TYPE
    SYNTAX Counter
    ACCESS  read-only
    STATUS  mandatory
    DESCRIPTION
       "The packets that matched the policy in the last second."
    ::=  {rsBWMCurrentChainRulesEntry 11}

rsBWMCurrentChainRulesPhysicalPortGroup OBJECT-TYPE
    SYNTAX DisplayString
    ACCESS  read-only
    STATUS  mandatory
    DESCRIPTION
       "This name of the physical port group for this rule."
    ::=  { rsBWMCurrentChainRulesEntry 12 }

rsBWMCurrentChainRulesVLANTagGroup OBJECT-TYPE
    SYNTAX DisplayString
    ACCESS  read-only
    STATUS  mandatory
    DESCRIPTION
        "The name of the VLAN tag group for this rule."
    ::=  { rsBWMCurrentChainRulesEntry 13 }

rsBWMCurrentChainRulesDSCPMarking OBJECT-TYPE
    SYNTAX INTEGER (-1 | 0..63)
    ACCESS  read-write
    STATUS  mandatory
    DESCRIPTION
       "This variable indicates the DSCP value to mark the ToS field in the IP header
        in the matching packets. If equals -1, the marking is not performed."
    ::= { rsBWMCurrentChainRulesEntry 14 }

rsBWMPPCInboundPortOnlyTable OBJECT-TYPE
    SYNTAX SEQUENCE OF RsBWMPPCInboundPortOnlyEntry
    ACCESS not-accessible
    STATUS  mandatory
    DESCRIPTION
      "Table containing the operation for each inbound port (and not for port pairs)."
    ::= { rsBWM 35 }

rsBWMPPCInboundPortOnlyEntry OBJECT-TYPE
    SYNTAX RsBWMPPCInboundPortOnlyEntry
    ACCESS not-accessible
    STATUS mandatory
    DESCRIPTION
       "The row definition for this table."
    INDEX { rsBWMPPCInboundPort }
    ::=  { rsBWMPPCInboundPortOnlyTable 1 }

RsBWMPPCInboundPortOnlyEntry ::= SEQUENCE {
     rsBWMPPCInboundPort INTEGER,
     rsBWMPPCOperationStatus RowStatus
}

rsBWMPPCInboundPort OBJECT-TYPE
    SYNTAX INTEGER
    ACCESS read-only
    STATUS mandatory
    DESCRIPTION
      "The index of the inbound port."
    ::=  { rsBWMPPCInboundPortOnlyEntry 1 }

rsBWMPPCOperationStatus OBJECT-TYPE
    SYNTAX RowStatus
    ACCESS read-write
    STATUS mandatory
    DESCRIPTION
      "The status of the current entry. "
    ::=  { rsBWMPPCInboundPortOnlyEntry 2 }

rsBWMPhysicalPortGroupTable OBJECT-TYPE
    SYNTAX SEQUENCE OF RsBWMPhysicalPortGroupEntry
    ACCESS not-accessible
    STATUS  mandatory
    DESCRIPTION
      "Table containing the entries of physical port groups."
    ::= { rsBWM 36 }

rsBWMPhysicalPortGroupEntry OBJECT-TYPE
    SYNTAX RsBWMPhysicalPortGroupEntry
    ACCESS not-accessible
    STATUS mandatory
    DESCRIPTION
       "The row definition for this table."
    INDEX { rsBWMPhysicalPortGroupName,  rsBWMPhysicalPortGroupPort }
    ::=  { rsBWMPhysicalPortGroupTable 1 }

RsBWMPhysicalPortGroupEntry ::= SEQUENCE {
     rsBWMPhysicalPortGroupName DisplayString,
     rsBWMPhysicalPortGroupPort INTEGER,
     rsBWMPhysicalPortGroupOperationStatus RowStatus
}

rsBWMPhysicalPortGroupName OBJECT-TYPE
    SYNTAX DisplayString
    ACCESS read-only
    STATUS mandatory
    DESCRIPTION
      "The name of the entry."
    ::=  { rsBWMPhysicalPortGroupEntry 1 }

rsBWMPhysicalPortGroupPort OBJECT-TYPE
    SYNTAX INTEGER
    ACCESS read-only
    STATUS mandatory
    DESCRIPTION
      "The inbound port."
    ::=  { rsBWMPhysicalPortGroupEntry 2 }

rsBWMPhysicalPortGroupOperationStatus OBJECT-TYPE
    SYNTAX RowStatus
    ACCESS read-write
    STATUS mandatory
    DESCRIPTION
      "The status of the current entry. "
    ::=  { rsBWMPhysicalPortGroupEntry 3 }

rsBWMCurrentPhysicalPortGroupTable OBJECT-TYPE
    SYNTAX SEQUENCE OF RsBWMCurrentPhysicalPortGroupEntry
    ACCESS not-accessible
    STATUS  mandatory
    DESCRIPTION
      "Table containing the entries of current physical port groups."
    ::= { rsBWM 37 }

rsBWMCurrentPhysicalPortGroupEntry OBJECT-TYPE
    SYNTAX RsBWMCurrentPhysicalPortGroupEntry
    ACCESS not-accessible
    STATUS mandatory
    DESCRIPTION
       "The row definition for this table."
    INDEX { rsBWMCurrentPhysicalPortGroupName,  rsBWMCurrentPhysicalPortGroupPort }
    ::=  { rsBWMCurrentPhysicalPortGroupTable 1 }

RsBWMCurrentPhysicalPortGroupEntry ::= SEQUENCE {
     rsBWMCurrentPhysicalPortGroupName DisplayString,
     rsBWMCurrentPhysicalPortGroupPort INTEGER
}

rsBWMCurrentPhysicalPortGroupName OBJECT-TYPE
    SYNTAX DisplayString
    ACCESS read-only
    STATUS mandatory
    DESCRIPTION
      "The name of the entry."
    ::=  { rsBWMCurrentPhysicalPortGroupEntry 1 }

rsBWMCurrentPhysicalPortGroupPort OBJECT-TYPE
    SYNTAX INTEGER
    ACCESS read-only
    STATUS mandatory
    DESCRIPTION
      "The inbound port."
    ::=  { rsBWMCurrentPhysicalPortGroupEntry 2 }

rsBWMContentTuning OBJECT IDENTIFIER ::= { rsBWMTuning 9 }
rsBWMContentEntries OBJECT-TYPE
    SYNTAX INTEGER
    ACCESS  read-only
    STATUS  mandatory
    DESCRIPTION
      "Maximum number of content entries."
    ::= { rsBWMContentTuning 1 }

rsBWMContentEntriesAfterReset OBJECT-TYPE
    SYNTAX INTEGER
    ACCESS  read-write
    STATUS  mandatory
    DESCRIPTION
      "Future maximum maximum number of content entries."
    ::=  { rsBWMContentTuning 2 }

rsBWMNetworkIPTuning OBJECT IDENTIFIER ::= { rsBWMTuning 10 }

rsBWMNetworkIPHashEntries OBJECT-TYPE
    SYNTAX INTEGER
    ACCESS  read-only
    STATUS  mandatory
    DESCRIPTION
      "Maximum number of entries in discrete IPs hash per network."
    ::= { rsBWMNetworkIPTuning 1 }

rsBWMNetworkIPHashEntriesAfterReset OBJECT-TYPE
    SYNTAX INTEGER
    ACCESS  read-write
    STATUS  mandatory
    DESCRIPTION
      "Future maximum maximum number of entries in discrete IPs hash per network."
    ::=  { rsBWMNetworkIPTuning 2 }

rsBWMNetworkRangeTuning OBJECT IDENTIFIER ::= { rsBWMTuning 11 }

rsBWMNetworkRangeEntries OBJECT-TYPE
    SYNTAX INTEGER
    ACCESS  read-only
    STATUS  mandatory
    DESCRIPTION
      "Maximum number of ranges per network."
    ::= { rsBWMNetworkRangeTuning 1 }

rsBWMNetworkRangeEntriesAfterReset OBJECT-TYPE
    SYNTAX INTEGER
    ACCESS  read-write
    STATUS  mandatory
    DESCRIPTION
      "Future maximum maximum number of ranges per network."
    ::=  { rsBWMNetworkRangeTuning 2 }

rsBWMFarmRulesTable OBJECT-TYPE
    SYNTAX SEQUENCE OF RsBWMFarmRulesEntry
    ACCESS not-accessible
    STATUS  mandatory
    DESCRIPTION
      "Table containing the list of farm rules for classifer data base,
       these rules can be used to classify packets for farm."
    ::=  {rsBWM 38}

rsBWMFarmRulesEntry OBJECT-TYPE
    SYNTAX RsBWMFarmRulesEntry
    ACCESS not-accessible
    STATUS  mandatory
    DESCRIPTION
       "The row definition for this table."
    INDEX { rsBWMFarmRulesName }
    ::=  { rsBWMFarmRulesTable 1 }

RsBWMFarmRulesEntry ::= SEQUENCE {
    rsBWMFarmRulesIndex INTEGER,
    rsBWMFarmRulesName DisplayString,
    rsBWMFarmRulesDestination DisplayString,
    rsBWMFarmRulesSource DisplayString,
    rsBWMFarmRulesStatus  RowStatus,
    rsBWMFarmRulesDirection INTEGER,
    rsBWMFarmRulesDescription DisplayString,
    rsBWMFarmRulesPolicyType INTEGER,
    rsBWMFarmRulesPolicy DisplayString,
    rsBWMFarmRulesOperationalStatus INTEGER,
    rsBWMFarmRulesSpecific DisplayString,
    rsBWMFarmRulesPhysicalPortGroup DisplayString,
    rsBWMFarmRulesVLANTagGroup DisplayString,
    rsBWMFarmRulesDSCPMarking INTEGER
}

rsBWMFarmRulesIndex OBJECT-TYPE
    SYNTAX INTEGER
    ACCESS  read-write
    STATUS  mandatory
    DESCRIPTION
       "This variable indicates the administrative index of a line it
       determines the order of the rules."
    ::=  { rsBWMFarmRulesEntry 1 }

rsBWMFarmRulesName OBJECT-TYPE
    SYNTAX DisplayString (SIZE(0..19))
    ACCESS  read-only
    STATUS  mandatory
    DESCRIPTION
      "The Name for the Rule must be unique."
    ::=  {rsBWMFarmRulesEntry 2}

rsBWMFarmRulesDestination OBJECT-TYPE
    SYNTAX DisplayString (SIZE(0..19))
    ACCESS  read-write
    STATUS  mandatory
    DESCRIPTION
      "The destination address / range of address for the packet, the name is
      defined in the Objects table or can be an IP address."
    ::=  {rsBWMFarmRulesEntry 3}

rsBWMFarmRulesSource OBJECT-TYPE
    SYNTAX DisplayString (SIZE(0..19))
    ACCESS  read-write
    STATUS  mandatory
    DESCRIPTION
      "The source address / range of address for the packet, the name is
      defined in the Objects table or can be an IP address."
    ::=  {rsBWMFarmRulesEntry 4}

rsBWMFarmRulesStatus OBJECT-TYPE
    SYNTAX RowStatus
    ACCESS  read-write
    STATUS  mandatory
    DESCRIPTION
       "This variable indicates the administrative status of this entry.
        Used to delete an entry of this table."
    ::=  { rsBWMFarmRulesEntry 5 }

rsBWMFarmRulesDirection OBJECT-TYPE
    SYNTAX INTEGER {
              oneway(1),
              twoway(2) }
    ACCESS  read-write
    STATUS  mandatory
    DESCRIPTION
       "This variable indicates the direction of the incoming packet."
    DEFVAL { 1 }
    ::=  { rsBWMFarmRulesEntry 6 }

rsBWMFarmRulesDescription OBJECT-TYPE
    SYNTAX DisplayString (SIZE(0..19))
    ACCESS  read-write
    STATUS  mandatory
    DESCRIPTION
      "Description."
    ::=  { rsBWMFarmRulesEntry 7 }

rsBWMFarmRulesPolicyType OBJECT-TYPE
    SYNTAX INTEGER {
              none(1),
              filter(2),
              group(3),
              policy(4)}
    ACCESS  read-write
    STATUS  mandatory
    DESCRIPTION
       "The type of policy - i.e. if this is a filter, group or policy."
    DEFVAL  { 1 }
    ::=  { rsBWMFarmRulesEntry 8 }

rsBWMFarmRulesPolicy OBJECT-TYPE
    SYNTAX DisplayString (SIZE(0..29))
    ACCESS  read-write
    STATUS  mandatory
    DESCRIPTION
       "The name for the filter policy for the rule."
    ::=  { rsBWMFarmRulesEntry 9 }

rsBWMFarmRulesOperationalStatus OBJECT-TYPE
    SYNTAX INTEGER {
        active (1),
        inactive (2)
    }
    ACCESS  read-write
    STATUS  mandatory
    DESCRIPTION
       "This variable indicates if the rule is active or inactive.
        The active rule table contains only active rules."
    ::= { rsBWMFarmRulesEntry 10 }

rsBWMFarmRulesSpecific OBJECT-TYPE
    SYNTAX DisplayString (SIZE(0..19))
    ACCESS  read-write
    STATUS  mandatory
    DESCRIPTION
       "This variable indicates if there is additional data to the 
       policy."
    ::= { rsBWMFarmRulesEntry 11 }

rsBWMFarmRulesPhysicalPortGroup OBJECT-TYPE
    SYNTAX DisplayString
    ACCESS  read-write
    STATUS  mandatory
    DESCRIPTION
       "This name of the physical port group for this rule."
    ::=  { rsBWMFarmRulesEntry 12 }

rsBWMFarmRulesVLANTagGroup OBJECT-TYPE
    SYNTAX DisplayString
    ACCESS  read-write
    STATUS  mandatory
    DESCRIPTION
        "The name of the VLAN tag group for this rule."
    ::= { rsBWMFarmRulesEntry 13 }

rsBWMFarmRulesDSCPMarking OBJECT-TYPE
    SYNTAX INTEGER (-1 | 0..63)
    ACCESS  read-write
    STATUS  mandatory
    DESCRIPTION
       "This variable indicates the DSCP value to mark the ToS field in the IP header
        in the matching packets. If equals -1, the marking is not performed."
    ::= { rsBWMFarmRulesEntry 14 }

rsBWMCurrentFarmRulesTable OBJECT-TYPE
    SYNTAX SEQUENCE OF RsBWMCurrentFarmRulesEntry
    ACCESS not-accessible
    STATUS  mandatory
    DESCRIPTION
      "Table containing the list of chain rules for classifer data base,
       these rules can be used to classify packets for chaining."
    ::=  {rsBWM 39}

rsBWMCurrentFarmRulesEntry OBJECT-TYPE
    SYNTAX RsBWMCurrentFarmRulesEntry
    ACCESS not-accessible
    STATUS  mandatory
    DESCRIPTION
       "The row definition for this table."
    INDEX { rsBWMCurrentFarmRulesName }
    ::=  { rsBWMCurrentFarmRulesTable 1 }

RsBWMCurrentFarmRulesEntry ::= SEQUENCE {
    rsBWMCurrentFarmRulesIndex INTEGER,
    rsBWMCurrentFarmRulesName DisplayString,
    rsBWMCurrentFarmRulesDestination DisplayString,
    rsBWMCurrentFarmRulesSource DisplayString,
    rsBWMCurrentFarmRulesDirection INTEGER,
    rsBWMCurrentFarmRulesDescription DisplayString,
    rsBWMCurrentFarmRulesPolicyType INTEGER,
    rsBWMCurrentFarmRulesPolicy DisplayString,
    rsBWMCurrentFarmRulesSpecific DisplayString,
    rsBWMCurrentFarmBandwidthLastSec Counter,
    rsBWMCurrentFarmPacketsLastSec Counter,
    rsBWMCurrentFarmRulesPhysicalPortGroup DisplayString,
    rsBWMCurrentFarmRulesVLANTagGroup DisplayString,
    rsBWMCurrentFarmRulesDSCPMarking INTEGER
}

rsBWMCurrentFarmRulesIndex OBJECT-TYPE
    SYNTAX INTEGER
    ACCESS  read-only
    STATUS  mandatory
    DESCRIPTION
       "This variable indicates the administrative index of a line it
       determine the order of the rules."
    ::=  { rsBWMCurrentFarmRulesEntry 1 }

rsBWMCurrentFarmRulesName OBJECT-TYPE
    SYNTAX DisplayString (SIZE(0..19))
    ACCESS  read-only
    STATUS  mandatory
    DESCRIPTION
      "The Name for the Rule must be unique."
    ::=  {rsBWMCurrentFarmRulesEntry 2}

rsBWMCurrentFarmRulesDestination OBJECT-TYPE
    SYNTAX DisplayString (SIZE(0..19))
    ACCESS  read-only
    STATUS  mandatory
    DESCRIPTION
      "The destination address / range of address for the packet, the name is
      defined in the Objects table or can be an IP address."
    ::=  {rsBWMCurrentFarmRulesEntry 3}

rsBWMCurrentFarmRulesSource OBJECT-TYPE
    SYNTAX DisplayString (SIZE(0..19))
    ACCESS  read-only
    STATUS  mandatory
    DESCRIPTION
      "The source address / range of address for the packet, the name is
      defined in the Objects table or can be an IP address."
    ::=  {rsBWMCurrentFarmRulesEntry 4}

rsBWMCurrentFarmRulesDirection OBJECT-TYPE
    SYNTAX INTEGER {
              oneway(1),
              twoway(2) }
    ACCESS read-only
    STATUS mandatory
    DESCRIPTION
       "This variable indicates the direction of the incoming packet."
    ::=  { rsBWMCurrentFarmRulesEntry 5 }

rsBWMCurrentFarmRulesDescription OBJECT-TYPE
    SYNTAX DisplayString (SIZE(0..19))
    ACCESS  read-only
    STATUS  mandatory
    DESCRIPTION
      "Description."
    ::=  { rsBWMCurrentFarmRulesEntry 6 }

rsBWMCurrentFarmRulesPolicyType OBJECT-TYPE
    SYNTAX INTEGER {
              none(1),
              filter(2),
              group(3),
              policy(4)}
    ACCESS  read-only
    STATUS  mandatory
    DESCRIPTION
       "The type of policy - i.e. if this is a filter, group or policy."
    DEFVAL  { 1 }
    ::=  { rsBWMCurrentFarmRulesEntry 7 }

rsBWMCurrentFarmRulesPolicy OBJECT-TYPE
    SYNTAX DisplayString (SIZE(0..29))
    ACCESS  read-only
    STATUS  mandatory
    DESCRIPTION
       "The name for the filter policy for the rule."
    ::=  { rsBWMCurrentFarmRulesEntry 8 }

rsBWMCurrentFarmRulesSpecific OBJECT-TYPE
    SYNTAX DisplayString (SIZE(0..19))
    ACCESS  read-only
    STATUS  mandatory
    DESCRIPTION
       "This variable indicates if there is additional data to the 
       policy."
    ::= { rsBWMCurrentFarmRulesEntry 9 }

rsBWMCurrentFarmBandwidthLastSec OBJECT-TYPE
    SYNTAX Counter
    ACCESS  read-only
    STATUS  mandatory
    DESCRIPTION
       "The bandwidth used by the policy in the last second."
    ::=  {rsBWMCurrentFarmRulesEntry 10}

rsBWMCurrentFarmPacketsLastSec OBJECT-TYPE
    SYNTAX Counter
    ACCESS  read-only
    STATUS  mandatory
    DESCRIPTION
       "The packets that matched the policy in the last second."
    ::=  {rsBWMCurrentFarmRulesEntry 11}

rsBWMCurrentFarmRulesPhysicalPortGroup OBJECT-TYPE
    SYNTAX DisplayString
    ACCESS  read-only
    STATUS  mandatory
    DESCRIPTION
       "This name of the physical port group for this rule."
    ::=  { rsBWMCurrentFarmRulesEntry 12 }

rsBWMCurrentFarmRulesVLANTagGroup OBJECT-TYPE
    SYNTAX DisplayString
    ACCESS  read-only
    STATUS  mandatory
    DESCRIPTION
        "The name of the VLAN tag group for this rule."
    ::=  { rsBWMCurrentFarmRulesEntry 13 }

rsBWMCurrentFarmRulesDSCPMarking OBJECT-TYPE
    SYNTAX INTEGER (-1 | 0..63)
    ACCESS  read-write
    STATUS  mandatory
    DESCRIPTION
       "This variable indicates the DSCP value to mark the ToS field in the IP header
        in the matching packets. If equals -1, the marking is not performed."
    ::= { rsBWMCurrentFarmRulesEntry 14 }

rsBWMDynamicNetworkTuning OBJECT IDENTIFIER ::= { rsBWMTuning 12 }

rsBWMDynamicNetworkEntries OBJECT-TYPE
    SYNTAX INTEGER
    ACCESS  read-only
    STATUS  mandatory
    DESCRIPTION
      "Maximum number of dynamic network entries."
    ::= { rsBWMDynamicNetworkTuning 1 }

rsBWMDynamicNetworkEntriesAfterReset OBJECT-TYPE
    SYNTAX INTEGER
    ACCESS  read-write
    STATUS  mandatory
    DESCRIPTION
      "Future maximum maximum number of dynamic network entries."
    ::=  { rsBWMDynamicNetworkTuning 2 }

rsBWMDynamicNetworkIPTuning OBJECT IDENTIFIER ::= { rsBWMTuning 13 }

rsBWMDynamicNetworkIPHashEntries OBJECT-TYPE
    SYNTAX INTEGER
    ACCESS  read-only
    STATUS  mandatory
    DESCRIPTION
      "Maximum number of entries in discrete IPs hash per dynamic network."
    ::= { rsBWMDynamicNetworkIPTuning 1 }

rsBWMDynamicNetworkIPHashEntriesAfterReset OBJECT-TYPE
    SYNTAX INTEGER
    ACCESS  read-write
    STATUS  mandatory
    DESCRIPTION
      "Future maximum maximum number of entries in discrete IPs hash per dynamic network."
    ::=  { rsBWMDynamicNetworkIPTuning 2 }

rsBWMDynamicNetworkRangeTuning OBJECT IDENTIFIER ::= { rsBWMTuning 14 }

rsBWMDynamicNetworkRangeEntries OBJECT-TYPE
    SYNTAX INTEGER
    ACCESS  read-only
    STATUS  mandatory
    DESCRIPTION
      "Maximum number of ranges per dynamic network."
    ::= { rsBWMDynamicNetworkRangeTuning 1 }

rsBWMDynamicNetworkRangeEntriesAfterReset OBJECT-TYPE
    SYNTAX INTEGER
    ACCESS  read-write
    STATUS  mandatory
    DESCRIPTION
      "Future maximum maximum number of ranges per dynamic network."
    ::=  { rsBWMDynamicNetworkRangeTuning 2 }

rsBWMOMPCHashTableOffset OBJECT-TYPE
    SYNTAX INTEGER
    ACCESS  read-write
    STATUS  mandatory
    DESCRIPTION "The offset of the OMPC hash table."
    ::= {rsBWM 40}

rsBWMOMPCHashTableMask OBJECT-TYPE
    SYNTAX OCTET STRING
    ACCESS  read-write
    STATUS  mandatory
    DESCRIPTION "The mask of the OMPC hash table."
    ::= {rsBWM 41}

rsBWMNoSaveMode OBJECT-TYPE
    SYNTAX INTEGER {
        enable(1),
        disable(2)
    }
    ACCESS  read-write
    STATUS  mandatory
    DESCRIPTION "Indicates if BWM data structures are stored in CDB (disable) or in cdbbuf(enable)."
	DEFVAL  {disable}
    ::= {rsBWM 42}


rsBWMStringSearchMode OBJECT-TYPE
    SYNTAX INTEGER {
        regular(1),
        parallel(2)
    }
    ACCESS  read-write
    STATUS  mandatory
    DESCRIPTION "Indicates if parallel or regular string search is used in the content module."
    ::= {rsBWM 46}

rsBWMMacGroupTuning OBJECT IDENTIFIER ::= { rsBWMTuning 15 }

rsBWMMacGroupEntries OBJECT-TYPE
    SYNTAX INTEGER
    ACCESS  read-only
    STATUS  mandatory
    DESCRIPTION
      "Maximum number of MAC address groups."
    ::= { rsBWMMacGroupTuning 1 }

rsBWMMacGroupEntriesAfterReset OBJECT-TYPE
    SYNTAX INTEGER
    ACCESS  read-write
    STATUS  mandatory
    DESCRIPTION
      "Future maximum number of MAC address groups."
    ::=  { rsBWMMacGroupTuning 2 }

rsBWMParallelStringSearchMemoryTuning OBJECT IDENTIFIER ::= { rsBWMTuning 18 }

rsBWMParallelStringSearchMemory OBJECT-TYPE
    SYNTAX INTEGER
    ACCESS  read-only
    STATUS  mandatory
    DESCRIPTION
      "Maximum memory size for Parallel String Search."
    ::= { rsBWMParallelStringSearchMemoryTuning 1 }

rsBWMParallelStringSearchMemoryAfterReset OBJECT-TYPE
    SYNTAX INTEGER
    ACCESS  read-write
    STATUS  mandatory
    DESCRIPTION
      "Future maximum memory size for Parallel String Search."
    ::=  { rsBWMParallelStringSearchMemoryTuning 2 }

rsBWMTrafficFlowBWTuning OBJECT IDENTIFIER ::= { rsBWMTuning 19 }

rsBWMTrafficFlowBWEntries OBJECT-TYPE
    SYNTAX INTEGER
    ACCESS  read-only
    STATUS  mandatory
    DESCRIPTION
      "Maximum number of entries in the table that keeps track of  sessions for BW per Traffic Flow Support."
    ::= { rsBWMTrafficFlowBWTuning 1 }

rsBWMTrafficFlowBWEntriesAfterReset OBJECT-TYPE
    SYNTAX INTEGER
    ACCESS  read-write
    STATUS  mandatory
    DESCRIPTION
      "Future maximum number of entries in the table that keeps track of  sessions for BW per Traffic Flow Support.."
    ::=  { rsBWMTrafficFlowBWTuning 2 }

rsBWMVLANTagGroupTable OBJECT-TYPE
    SYNTAX SEQUENCE OF RsBWMVLANTagGroupEntry
    ACCESS not-accessible
    STATUS  mandatory
    DESCRIPTION
        "Table for VLAN tag groups."
    ::=  {rsBWM 47}

rsBWMVLANTagGroupEntry OBJECT-TYPE
    SYNTAX RsBWMVLANTagGroupEntry
    ACCESS not-accessible
    STATUS  mandatory
    DESCRIPTION
	    "The row definition for this table."
    INDEX { rsBWMVLANTagGroupName, rsBWMVLANTagGroupVLANTag, rsBWMVLANTagGroupVLANTagFrom }
    ::=  { rsBWMVLANTagGroupTable  1}

RsBWMVLANTagGroupEntry ::= SEQUENCE {
    rsBWMVLANTagGroupName DisplayString,
    rsBWMVLANTagGroupVLANTag INTEGER,
    rsBWMVLANTagGroupVLANTagFrom INTEGER,
    rsBWMVLANTagGroupVLANTagTo INTEGER,
    rsBWMVLANTagGroupMode INTEGER,
    rsBWMVLANTagGroupStatus RowStatus
}

rsBWMVLANTagGroupName OBJECT-TYPE
    SYNTAX DisplayString (SIZE(0..19))
    ACCESS  read-only
    STATUS  mandatory
    DESCRIPTION
	    "The name of the VLAN tag group."
    ::=  { rsBWMVLANTagGroupEntry  1}

rsBWMVLANTagGroupVLANTag OBJECT-TYPE
    SYNTAX INTEGER
    ACCESS  read-only
    STATUS  mandatory
    DESCRIPTION
	    "The value of VLAN tag in discrete mode."
    ::=  { rsBWMVLANTagGroupEntry  2}

rsBWMVLANTagGroupVLANTagFrom OBJECT-TYPE
    SYNTAX INTEGER
    ACCESS  read-only
    STATUS  mandatory
    DESCRIPTION
	    "The 'from' part of the VLAN tag range."
    ::=  { rsBWMVLANTagGroupEntry  3}

rsBWMVLANTagGroupVLANTagTo OBJECT-TYPE
    SYNTAX INTEGER
    ACCESS  read-write
    STATUS  mandatory
    DESCRIPTION
	    "The 'to' part of the VLAN tag range."
    ::=  { rsBWMVLANTagGroupEntry  4}

rsBWMVLANTagGroupMode OBJECT-TYPE
    SYNTAX INTEGER {
	    discrete(1),
	    range(2)
    }                
    ACCESS  read-write
    STATUS  mandatory
    DESCRIPTION
	    "The mode of the VLAN tag group: discrete or range."
    ::=  { rsBWMVLANTagGroupEntry  5}

rsBWMVLANTagGroupStatus OBJECT-TYPE
    SYNTAX RowStatus 
    ACCESS  read-write
    STATUS  mandatory
    DESCRIPTION
        "The row status of the entry."
    ::=  { rsBWMVLANTagGroupEntry  6}

rsBWMCurrentVLANTagGroupTable OBJECT-TYPE
    SYNTAX SEQUENCE OF RsBWMCurrentVLANTagGroupEntry
    ACCESS not-accessible
    STATUS  mandatory
    DESCRIPTION
	    "Current table for VLAN tag groups."
    ::=  {rsBWM 48}

rsBWMCurrentVLANTagGroupEntry OBJECT-TYPE
    SYNTAX RsBWMCurrentVLANTagGroupEntry
    ACCESS not-accessible
    STATUS  mandatory
    DESCRIPTION
	    "The row definition for this table."
    INDEX { rsBWMCurrentVLANTagGroupName, rsBWMCurrentVLANTagGroupVLANTag, rsBWMCurrentVLANTagGroupVLANTagFrom }
    ::=  { rsBWMCurrentVLANTagGroupTable  1}

RsBWMCurrentVLANTagGroupEntry ::= SEQUENCE {
    rsBWMCurrentVLANTagGroupName DisplayString,
    rsBWMCurrentVLANTagGroupVLANTag INTEGER,
    rsBWMCurrentVLANTagGroupVLANTagFrom INTEGER,
    rsBWMCurrentVLANTagGroupVLANTagTo INTEGER,
    rsBWMCurrentVLANTagGroupMode INTEGER
}

rsBWMCurrentVLANTagGroupName OBJECT-TYPE
    SYNTAX DisplayString (SIZE(0..19))
    ACCESS  read-only
    STATUS  mandatory
    DESCRIPTION
	    "The name of the VLAN tag group."
    ::=  { rsBWMCurrentVLANTagGroupEntry  1}

rsBWMCurrentVLANTagGroupVLANTag OBJECT-TYPE
    SYNTAX INTEGER
    ACCESS  read-only
    STATUS  mandatory
    DESCRIPTION
	    "The value of VLAN tag in discrete mode."
    ::=  { rsBWMCurrentVLANTagGroupEntry  2}

rsBWMCurrentVLANTagGroupVLANTagFrom OBJECT-TYPE
    SYNTAX INTEGER
    ACCESS  read-only
    STATUS  mandatory
    DESCRIPTION
	    "The 'from' part of the VLAN tag range."
    ::=  { rsBWMCurrentVLANTagGroupEntry  3}

rsBWMCurrentVLANTagGroupVLANTagTo OBJECT-TYPE
    SYNTAX INTEGER
    ACCESS  read-only
    STATUS  mandatory
    DESCRIPTION
	    "The 'to' part of the VLAN tag range."
    ::=  { rsBWMCurrentVLANTagGroupEntry  4}

rsBWMCurrentVLANTagGroupMode OBJECT-TYPE
    SYNTAX INTEGER {
	discrete(1),
	range(2)
    }                
    ACCESS  read-only
    STATUS  mandatory
    DESCRIPTION
	    "The mode of the VLAN tag group: discrete or range."
    ::=  { rsBWMCurrentVLANTagGroupEntry  5}

rsBWMMacGroupTable OBJECT-TYPE
    SYNTAX SEQUENCE OF RsBWMMacGroupEntry
    ACCESS not-accessible
    STATUS  mandatory
    DESCRIPTION
      "Table containing the groups of MAC addresses."
    ::=  {rsBWM 49}

rsBWMMacGroupEntry OBJECT-TYPE
    SYNTAX RsBWMMacGroupEntry
    ACCESS not-accessible
    STATUS  mandatory
    DESCRIPTION
       "The row definition for this table."
    INDEX {rsBWMMacGroupEntryName,rsBWMMacGroupEntryAddress}
    ::=  { rsBWMMacGroupTable 1 }

RsBWMMacGroupEntry ::= SEQUENCE {
    rsBWMMacGroupEntryName DisplayString,
    rsBWMMacGroupEntryAddress MacAddress,
    rsBWMMacGroupEntryStatus RowStatus
}

rsBWMMacGroupEntryName OBJECT-TYPE
    SYNTAX DisplayString (SIZE(0..19))
    ACCESS  read-only
    STATUS  mandatory
    DESCRIPTION
      "The Name for the MACs group."
    ::=  { rsBWMMacGroupEntry 1 }

rsBWMMacGroupEntryAddress OBJECT-TYPE
    SYNTAX MacAddress
    ACCESS  read-only
    STATUS  mandatory
    DESCRIPTION
      "the MAC address in the group."
    ::=  { rsBWMMacGroupEntry 2 }

rsBWMMacGroupEntryStatus OBJECT-TYPE
    SYNTAX RowStatus
    ACCESS  read-write
    STATUS  mandatory
    DESCRIPTION
       "This variable indicates the administrative status of this entry.
        Used to delete an entry of this table."
    ::=  { rsBWMMacGroupEntry 3 }


rsBWMMacGroupCurrentTable OBJECT-TYPE
    SYNTAX SEQUENCE OF RsBWMMacGroupCurrentEntry
    ACCESS not-accessible
    STATUS  mandatory
    DESCRIPTION
      "Table containing the current groups of MAC addresses."
    ::=  {rsBWM 50}

rsBWMMacGroupCurrentEntry OBJECT-TYPE
    SYNTAX RsBWMMacGroupCurrentEntry
    ACCESS not-accessible
    STATUS  mandatory
    DESCRIPTION
       "The row definition for this table."
    INDEX {rsBWMMacGroupCurrentEntryName,rsBWMMacGroupCurrentEntryAddress}
    ::=  { rsBWMMacGroupCurrentTable 1 }

RsBWMMacGroupCurrentEntry ::= SEQUENCE {
    rsBWMMacGroupCurrentEntryName DisplayString,
    rsBWMMacGroupCurrentEntryAddress MacAddress
}

rsBWMMacGroupCurrentEntryName OBJECT-TYPE
    SYNTAX DisplayString (SIZE(0..19))
    ACCESS  read-only
    STATUS  mandatory
    DESCRIPTION
      "The Name for the MACs group."
    ::=  { rsBWMMacGroupCurrentEntry 1 }

rsBWMMacGroupCurrentEntryAddress OBJECT-TYPE
    SYNTAX MacAddress
    ACCESS  read-only
    STATUS  mandatory
    DESCRIPTION
      "the MAC address in the group."
    ::=  { rsBWMMacGroupCurrentEntry 2 }

rsBWMQueueSize OBJECT-TYPE
    SYNTAX INTEGER
    ACCESS  read-write
    STATUS  mandatory
    DESCRIPTION
        "Enables the user to configure the queue size"
    DEFVAL  { 512 }
    ::=  {rsBWM 51}

rsBWMTrafficFlowBWAgingTime OBJECT-TYPE
    SYNTAX INTEGER
    ACCESS  read-write
    STATUS  mandatory
    DESCRIPTION
        "The aging time for the traffic flow BW table. After this number of seconds without activity, the session is deleted."
    ::= {rsBWM 52}

rsBWMServiceTable OBJECT-TYPE
    SYNTAX SEQUENCE OF RsBWMServiceEntry
    ACCESS not-accessible
    STATUS  mandatory
    DESCRIPTION
      "Table containing the available services."
    ::=  {rsBWM 53}

rsBWMServiceEntry OBJECT-TYPE
    SYNTAX RsBWMServiceEntry
    ACCESS not-accessible
    STATUS  mandatory
    DESCRIPTION
       "The row definition for this table."
    INDEX {rsBWMServiceTableType, rsBWMServiceType, rsBWMServiceName} 
    ::=  {rsBWMServiceTable 1}

RsBWMServiceEntry ::= SEQUENCE {
    rsBWMServiceTableType INTEGER,
    rsBWMServiceType INTEGER,
    rsBWMServiceName DisplayString
}

rsBWMServiceTableType OBJECT-TYPE
    SYNTAX INTEGER {
        filterActive (1),
        filterModify (2),
        advancedActive (3),
        advancedModify (4),
        groupActive (5),
        groupModify (6)
    }
    ACCESS  read-only
    STATUS  mandatory
    DESCRIPTION
      "The specific table to access."
    ::=  {rsBWMServiceEntry 1}

rsBWMServiceType OBJECT-TYPE
    SYNTAX INTEGER {
        regular (1),
        static (2),
        ids (3),
        idsStatic (4)
    }
    ACCESS read-only
    STATUS  mandatory
    DESCRIPTION
       "The type of entry."
    ::=  {rsBWMServiceEntry 2}

rsBWMServiceName OBJECT-TYPE
    SYNTAX DisplayString (SIZE(0..29))
    ACCESS read-only
    STATUS mandatory
    DESCRIPTION
      "The filter or advanced or group name (of type rsBWMServiceType)."
    ::=  {rsBWMServiceEntry 3}

rsBWMPolicyGroupTable OBJECT-TYPE
    SYNTAX SEQUENCE OF RsBWMPolicyGroupEntry
    ACCESS not-accessible
    STATUS  mandatory
    DESCRIPTION
      "Table containing the available Policy groups."
    ::=  {rsBWM 54}

rsBWMPolicyGroupEntry OBJECT-TYPE
    SYNTAX RsBWMPolicyGroupEntry
    ACCESS not-accessible
    STATUS  mandatory
    DESCRIPTION
       "The row definition for this table."
    INDEX {rsBWMPolicyGroupEntryName}
    ::=  { rsBWMPolicyGroupTable 1 }

RsBWMPolicyGroupEntry ::= SEQUENCE {
    rsBWMPolicyGroupEntryName DisplayString,
    rsBWMPolicyGroupEntryStatus RowStatus
}

rsBWMPolicyGroupEntryName OBJECT-TYPE
    SYNTAX DisplayString (SIZE(0..19))
    ACCESS  read-only
    STATUS  mandatory
    DESCRIPTION
      "The Name for the Policy group."
    ::=  { rsBWMPolicyGroupEntry 1 }

rsBWMPolicyGroupEntryStatus OBJECT-TYPE
    SYNTAX RowStatus
    ACCESS  read-write
    STATUS  mandatory
    DESCRIPTION
       "This variable indicates the administrative status of this entry.
        Used to delete an entry of this table."
    ::=  { rsBWMPolicyGroupEntry 2 }

rsBWMPolicyGroupCurrentTable OBJECT-TYPE
    SYNTAX SEQUENCE OF RsBWMPolicyGroupCurrentEntry
    ACCESS not-accessible
    STATUS  mandatory
    DESCRIPTION
      "Table containing the current groups of classes."
    ::=  {rsBWM 55}

rsBWMPolicyGroupCurrentEntry OBJECT-TYPE
    SYNTAX RsBWMPolicyGroupCurrentEntry
    ACCESS not-accessible
    STATUS  mandatory
    DESCRIPTION
       "The row definition for this table."
    INDEX {rsBWMPolicyGroupCurrentEntryName}
    ::=  { rsBWMPolicyGroupCurrentTable 1 }

RsBWMPolicyGroupCurrentEntry ::= SEQUENCE {
    rsBWMPolicyGroupCurrentEntryName DisplayString
}

rsBWMPolicyGroupCurrentEntryName OBJECT-TYPE
    SYNTAX DisplayString (SIZE(0..19))
    ACCESS  read-only
    STATUS  mandatory
    DESCRIPTION
      "The Name for the Classs group."
    ::=  { rsBWMPolicyGroupCurrentEntry 1 }

rsBWMTCPSessionClassification OBJECT-TYPE
    SYNTAX INTEGER {
        enable (1),
        disable (2)
    }
    ACCESS  read-write
    STATUS  mandatory
    DESCRIPTION "Indicates the mode of classification for a TCP session."
--  DEFVAL  { disable }
    ::= { rsBWM 62 }

-- Application-specific traps for BWM
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------

rsBWMPacketBlocked TRAP-TYPE
        ENTERPRISE rsBWM
        VARIABLES  { rndErrorDesc, rndErrorSeverity }
        DESCRIPTION
             "This trap is sent to inform the user about blocked packets."
		::=  1

rsBWMTrafficFlowBWTablesFull   TRAP-TYPE
       ENTERPRISE  rsBWM
        VARIABLES  { rndErrorDesc, rndErrorSeverity }
        DESCRIPTION
             "This trap is sent to inform the user about one of the tables for BW per traffic flow support being full."
       ::=  2


END
