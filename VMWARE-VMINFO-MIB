-- **********************************************************
-- Copyright 2007 VMware, Inc.  All rights reserved. 
-- 
--  This MIB Module provides status of virtual machines
--
-- **********************************************************
-- Version 1.0

VMWARE-VMINFO-MIB DEFINITIONS ::= BEGIN

IMPORTS
   OBJECT-TYPE
      FROM RFC-1212
   DisplayString 
      FROM RFC1213-MIB 
   vmwVirtMachines 
      FROM VMWARE-ROOT-MIB;

vmTable       OBJECT-TYPE
   SYNTAX     SEQUENCE OF  VmEntry
   ACCESS     not-accessible
   STATUS     mandatory 
   DESCRIPTION
      "A table containing information on virtual machines that have been 
       configured on the system."
   ::= { vmwVirtMachines 1 } 


vmEntry     OBJECT-TYPE
   SYNTAX   VmEntry  
   ACCESS   not-accessible
   STATUS   mandatory
   DESCRIPTION 
      "The record for a single virtual machine."
   INDEX    { vmIdx } 
   ::= { vmTable 1 }


VmEntry    ::= SEQUENCE 
{
   vmIdx          INTEGER,
   vmDisplayName  DisplayString,
   vmConfigFile   DisplayString,
   vmGuestOS      DisplayString,
   vmMemSize      INTEGER,
   vmState        DisplayString,
   vmVMID         INTEGER,
   vmGuestState   DisplayString
}

vmIdx          OBJECT-TYPE
   SYNTAX      INTEGER (0..255)
   ACCESS      read-only 
   STATUS      mandatory
   DESCRIPTION 
      "This is a dummy number for an index.  " 
   ::= { vmEntry 1 }

vmDisplayName  OBJECT-TYPE
   SYNTAX      DisplayString 
   ACCESS      read-only
   STATUS      mandatory
   DESCRIPTION 
      "Name by which this vm is displayed."
   ::= { vmEntry 2 }


vmConfigFile   OBJECT-TYPE
   SYNTAX      DisplayString
   ACCESS      read-only
   STATUS      mandatory
   DESCRIPTION
      "Path to the configuration file for this vm."
   ::= { vmEntry 3 }

vmGuestOS      OBJECT-TYPE
   SYNTAX      DisplayString
   ACCESS      read-only
   STATUS      mandatory
   DESCRIPTION
      "Operating system running on this vm."
   ::= { vmEntry 4 }

vmMemSize      OBJECT-TYPE
   SYNTAX      INTEGER 
   ACCESS      read-only
   STATUS      mandatory
   DESCRIPTION
      "Memory configured for this vm. (MB) "
   ::= { vmEntry 5 }

vmState        OBJECT-TYPE 
   SYNTAX      DisplayString
   ACCESS      read-only
   STATUS      mandatory
   DESCRIPTION
      "Virtual machine ON or OFF."
   ::= { vmEntry 6 }

vmVMID         OBJECT-TYPE 
   SYNTAX      INTEGER 
   ACCESS      read-only
   STATUS      mandatory
   DESCRIPTION
      "If a VM is active, an ID is assigned to it (like a pid). Some VMs may 
      have been configured but not running. Information about these VMs without
      VM IDs is also displayed, so we can't use VM ID as the table's index."
   ::= { vmEntry 7 }

vmGuestState   OBJECT-TYPE 
   SYNTAX      DisplayString
   ACCESS      read-only
   STATUS      mandatory
   DESCRIPTION
      "Guest operating system ON or OFF."
   ::= { vmEntry 8 }

-- end of configuration information

-- Per-vm HBA Information

hbaTable       OBJECT-TYPE 
   SYNTAX      SEQUENCE OF HbaEntry
   ACCESS      not-accessible 
   STATUS      mandatory
   DESCRIPTION
      "Table of disk adapters seen by this vm."
   ::= { vmwVirtMachines 2 }

hbaEntry     OBJECT-TYPE
   SYNTAX      HbaEntry 
   ACCESS      not-accessible 
   STATUS      mandatory
   DESCRIPTION
      "Record for a single host bus adapter."
   INDEX       { hbaVmIdx, hbaIdx }
   ::= { hbaTable 1 }

HbaEntry  ::= SEQUENCE
{
   hbaVmIdx    INTEGER,       
   hbaIdx      INTEGER,
   hbaNum      DisplayString,
   hbaVirtDev  DisplayString
}

hbaVmIdx     OBJECT-TYPE
   SYNTAX      INTEGER (0..255)
   ACCESS      read-only
   STATUS      mandatory
   DESCRIPTION
      "This number corresponds to the vm's index in the VM info table."
   ::= { hbaEntry 1 }

hbaIdx       OBJECT-TYPE
   SYNTAX      INTEGER (0..3) 
   ACCESS      read-only
   STATUS      mandatory
   DESCRIPTION
      "VM's virtual SCSI adapter number; second part of the table index."
   ::= { hbaEntry 2 }

hbaNum        OBJECT-TYPE
   SYNTAX      DisplayString
   ACCESS      read-only
   STATUS      mandatory
   DESCRIPTION 
      "Device number ( format: 'scsi*' ). "
   ::= { hbaEntry 3 }

hbaVirtDev    OBJECT-TYPE
   SYNTAX      DisplayString
   ACCESS      read-only
   STATUS      mandatory
   DESCRIPTION 
      " Virtual device type for this adapter."
   ::= { hbaEntry 4 }

-- end of hba section

-- Per-vm HBA Targets table

hbaTgtTable    OBJECT-TYPE 
   SYNTAX      SEQUENCE OF HbaTgtEntry
   ACCESS      not-accessible 
   STATUS      mandatory
   DESCRIPTION
      "Table of scsi targets seen by this vm."
   ::= { vmwVirtMachines 3 }

hbaTgtEntry    OBJECT-TYPE
   SYNTAX      HbaTgtEntry 
   ACCESS      not-accessible 
   STATUS      mandatory
   DESCRIPTION
      "Record for a single target."
   INDEX       { hbaTgtVmIdx, hbaTgtIdx }
   ::= { hbaTgtTable 1 }

HbaTgtEntry  ::= SEQUENCE
{
   hbaTgtVmIdx   INTEGER,       
   hbaTgtIdx     INTEGER,
   hbaTgtNum     DisplayString
}

hbaTgtVmIdx    OBJECT-TYPE
   SYNTAX      INTEGER (0..255)
   ACCESS      read-only
   STATUS      mandatory
   DESCRIPTION
      "This number corresponds to the vm's index in the VM info table."
   ::= { hbaTgtEntry 1 }

hbaTgtIdx       OBJECT-TYPE
   SYNTAX      INTEGER (0..15)
   ACCESS      read-only
   STATUS      mandatory
   DESCRIPTION
      "Virtual SCSI target number; second part of target entry index."
   ::= { hbaTgtEntry 2 }

hbaTgtNum        OBJECT-TYPE
   SYNTAX      DisplayString
   ACCESS      read-only
   STATUS      mandatory
   DESCRIPTION 
      "Target description ( format: 'scsi<hba>:<tgt>' ). "
   ::= { hbaTgtEntry 3 }

-- end of hba-target section

-- Per-VM NIC Table
netTable       OBJECT-TYPE 
   SYNTAX      SEQUENCE OF NetEntry
   ACCESS      not-accessible 
   STATUS      mandatory
   DESCRIPTION
      "Table of network adapters seen by this vm."
   ::= { vmwVirtMachines 4 }

netEntry     OBJECT-TYPE
   SYNTAX      NetEntry 
   ACCESS      not-accessible 
   STATUS      mandatory
   DESCRIPTION
      "Record for a single NIC."
   INDEX       { netVmIdx, netIdx }
   ::= { netTable 1 }

NetEntry  ::= SEQUENCE
{
   netVmIdx INTEGER,
   netIdx   INTEGER,
   netNum   DisplayString,
   netName  DisplayString,
   netConnType DisplayString
}

netVmIdx     OBJECT-TYPE
   SYNTAX      INTEGER (0..255)
   ACCESS      read-only
   STATUS      mandatory
   DESCRIPTION
      "This number corresponds to the vm's index in the VM info table."
   ::= { netEntry 1 }

netIdx         OBJECT-TYPE
   SYNTAX      INTEGER (0..3)
   ACCESS      read-only
   STATUS      mandatory
   DESCRIPTION
      "Index for this table." 
   ::= { netEntry 2 }

netNum         OBJECT-TYPE
   SYNTAX      DisplayString
   ACCESS      read-only
   STATUS      mandatory
   DESCRIPTION 
      "Device number. (format: 'ethernet*')"
   ::= { netEntry 3 }

netName        OBJECT-TYPE
   SYNTAX      DisplayString
   ACCESS      read-only
   STATUS      mandatory
   DESCRIPTION 
      "Device name. (format: 'vmnic*')"
   ::= { netEntry 4 }

netConnType    OBJECT-TYPE
   SYNTAX      DisplayString
   ACCESS      read-only
   STATUS      mandatory
   DESCRIPTION 
      "Connection Type (user or monitor device)."
   ::= { netEntry 5 }

-- end of net section

-- Per-VM Floppy devices 

floppyTable    OBJECT-TYPE 
   SYNTAX      SEQUENCE OF FdEntry
   ACCESS      not-accessible 
   STATUS      mandatory
   DESCRIPTION
      "Table of floppy drives seen by this vm."
   ::= { vmwVirtMachines 5 }

floppyEntry    OBJECT-TYPE
   SYNTAX      FdEntry
   ACCESS      not-accessible 
   STATUS      mandatory
   DESCRIPTION
      "Record for a single floppy drive."
   INDEX       { fdVmIdx, fdIdx }
   ::= { floppyTable 1 }

FdEntry    ::= SEQUENCE
{
   fdVmIdx     INTEGER,
   fdIdx       INTEGER,
   fdName      DisplayString,
   fdConnected DisplayString
}

fdVmIdx      OBJECT-TYPE
   SYNTAX      INTEGER (0..255)
   ACCESS      read-only
   STATUS      mandatory
   DESCRIPTION
      "This number corresponds to the vm's index in the VM info table."
   ::= { floppyEntry 1 }

fdIdx          OBJECT-TYPE
   SYNTAX      INTEGER (0..3)
   ACCESS      read-only
   STATUS      mandatory
   DESCRIPTION
      "Index into floppy table. Order of the floppy device on this vm."
   ::= { floppyEntry 2 }

fdName         OBJECT-TYPE
   SYNTAX      DisplayString 
   ACCESS      read-only
   STATUS      mandatory
   DESCRIPTION
      "Device number/name (/dev/fd0, etc. NULL if not present)."
   ::= { floppyEntry 3 }

fdConnected    OBJECT-TYPE
   SYNTAX      DisplayString 
   ACCESS      read-only
   STATUS      mandatory
   DESCRIPTION
      "Is the floppy drive connected? (mounted)"
   ::= { floppyEntry 4 }

-- end of fd section

-- Per-VM CDROM devices

cdromTable    OBJECT-TYPE 
   SYNTAX      SEQUENCE OF CdromEntry
   ACCESS      not-accessible 
   STATUS      mandatory
   DESCRIPTION
      "Table of CDROM drives seen by this vm."
   ::= { vmwVirtMachines 6 }

cdromEntry     OBJECT-TYPE
   SYNTAX      CdromEntry
   ACCESS      not-accessible 
   STATUS      mandatory
   DESCRIPTION
      "Record for a single CDROM drive."
   INDEX       { cdVmIdx, cdromIdx }
   ::= { cdromTable 1 }

CdromEntry    ::= SEQUENCE
{
   cdVmIdx        INTEGER,
   cdromIdx       INTEGER,
   cdromName      DisplayString,
   cdromConnected DisplayString
}

cdVmIdx       OBJECT-TYPE
   SYNTAX      INTEGER (0..255)
   ACCESS      read-only
   STATUS      mandatory
   DESCRIPTION
      "This number corresponds to the vm's index in the VM info table."
   ::= { cdromEntry 1 }

cdromIdx          OBJECT-TYPE
   SYNTAX      INTEGER (0..3)
   ACCESS      read-only
   STATUS      mandatory
   DESCRIPTION
      "Index into CDROM table. Order of the CDROM device on this vm."
   ::= { cdromEntry 2 }

cdromName         OBJECT-TYPE
   SYNTAX      DisplayString 
   ACCESS      read-only
   STATUS      mandatory
   DESCRIPTION
      "Device number/name (/dev/CDROM, etc. NULL if not present)."
   ::= { cdromEntry 3 }

cdromConnected    OBJECT-TYPE
   SYNTAX      DisplayString 
   ACCESS      read-only
   STATUS      mandatory
   DESCRIPTION
      "Is the CDROM drive connected? (mounted)"
   ::= { cdromEntry 4 }

-- end of CDROM section

END
