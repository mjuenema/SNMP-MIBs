-- file automatically created


TELDAT-TRAP-SRT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


srtTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SRT event subsystem."
    REVISION "201401200930Z"
    DESCRIPTION "Initial implementation"
        ::= { telEventTraps 72 }


srtEventsGroup	OBJECT IDENTIFIER	::= { srtTrapsMIB 1 }

srtNotifications	OBJECT IDENTIFIER	::= { srtTrapsMIB 2 }
srtNotificationsPrefix	OBJECT IDENTIFIER	::= { srtNotifications 0 }

srtEventObjects1 OBJECT-IDENTITY
    STATUS current
    DESCRIPTION
        "Event SRT.1
        No buffer available to copy a frame in order to send a bridged frame on
        multiple interfaces. Bridged packets are sent on multiple interfaces
        either for multicast destination addresses, or in the case of
        certain static entries. No copy of this frame will be sent on
        the specified port and interface."
    ::= { srtEventsGroup 1 }

srt1_source_mac OBJECT-TYPE
    SYNTAX DisplayString
    MAX-ACCESS accessible-for-notify
    STATUS current
    DESCRIPTION
        "Parameter 'source_mac' in event SRT.1"
    ::= { srtEventObjects1 1 }

srt1_dest_mac OBJECT-TYPE
    SYNTAX DisplayString
    MAX-ACCESS accessible-for-notify
    STATUS current
    DESCRIPTION
        "Parameter 'dest_mac' in event SRT.1"
    ::= { srtEventObjects1 2 }

srt1_port OBJECT-TYPE
    SYNTAX Integer32
    MAX-ACCESS accessible-for-notify
    STATUS current
    DESCRIPTION
        "Parameter 'port' in event SRT.1"
    ::= { srtEventObjects1 3 }

srt1_interface OBJECT-TYPE
    SYNTAX DisplayString
    MAX-ACCESS accessible-for-notify
    STATUS current
    DESCRIPTION
        "Parameter 'interface' in event SRT.1"
    ::= { srtEventObjects1 4 }

srt1_circuit_name OBJECT-TYPE
    SYNTAX DisplayString
    MAX-ACCESS accessible-for-notify
    STATUS current
    DESCRIPTION
        "Parameter 'circuit_name' in event SRT.1"
    ::= { srtEventObjects1 5 }

srtEventObjects2 OBJECT-IDENTITY
    STATUS current
    DESCRIPTION
        "Event SRT.2
        The Spanning Tree Protocol requested setting this network into
        Learning state, but the command to the device failed. The error_code is
        a device-specific error code that may indicate what the error is."
    ::= { srtEventsGroup 2 }

srt2_error_code OBJECT-TYPE
    SYNTAX Integer32
    MAX-ACCESS accessible-for-notify
    STATUS current
    DESCRIPTION
        "Parameter 'error_code' in event SRT.2"
    ::= { srtEventObjects2 1 }

srt2_interface OBJECT-TYPE
    SYNTAX DisplayString
    MAX-ACCESS accessible-for-notify
    STATUS current
    DESCRIPTION
        "Parameter 'interface' in event SRT.2"
    ::= { srtEventObjects2 2 }

srt2_circuit_name OBJECT-TYPE
    SYNTAX DisplayString
    MAX-ACCESS accessible-for-notify
    STATUS current
    DESCRIPTION
        "Parameter 'circuit_name' in event SRT.2"
    ::= { srtEventObjects2 3 }

srtEventObjects3 OBJECT-IDENTITY
    STATUS current
    DESCRIPTION
        "Event SRT.3
        An attempt to add a set of static entries to the internal database of
        a bridging interface having internal filtering failed.
        The error_code is a device-specific error code that may indicate
        what the error is."
    ::= { srtEventsGroup 3 }

srt3_error_code OBJECT-TYPE
    SYNTAX Integer32
    MAX-ACCESS accessible-for-notify
    STATUS current
    DESCRIPTION
        "Parameter 'error_code' in event SRT.3"
    ::= { srtEventObjects3 1 }

srt3_interface OBJECT-TYPE
    SYNTAX DisplayString
    MAX-ACCESS accessible-for-notify
    STATUS current
    DESCRIPTION
        "Parameter 'interface' in event SRT.3"
    ::= { srtEventObjects3 2 }

srt3_circuit_name OBJECT-TYPE
    SYNTAX DisplayString
    MAX-ACCESS accessible-for-notify
    STATUS current
    DESCRIPTION
        "Parameter 'circuit_name' in event SRT.3"
    ::= { srtEventObjects3 3 }

srtEventObjects4 OBJECT-IDENTITY
    STATUS current
    DESCRIPTION
        "Event SRT.4
        No buffer was available to send a command to the device.
        The possible command names are
        'D_CNFGSRB' (configure source-routing bridging),
        'SRT_ON' (promiscuous on),
        'SRT_INFORM' (learn capabilities of device),
        'SRT_SET_AGE' (set age for filtering database in device),
        'SRT_DECR_AGE' (do ageing pass on filtering database in device),
        'SRT_ADD_ENTRY' (add static entry),
        'SRT_DEL_ENTRY' (delete entry, from console),
        'SRT_SEARCH_ENTRY' (search for particular entry, from console) and
        'SRT_LIST_ENTRY' (list contents of learning database in card).
        For commands 'D_CNFGSRB' and 'SRT_ON' the result will be that
        the interface may remain in the wrong state. A failure on 'SRT_INFORM'
        could cause serious problems. For other commands the results will be
        less serious."
    ::= { srtEventsGroup 4 }

srt4_command_name OBJECT-TYPE
    SYNTAX DisplayString
    MAX-ACCESS accessible-for-notify
    STATUS current
    DESCRIPTION
        "Parameter 'command_name' in event SRT.4"
    ::= { srtEventObjects4 1 }

srt4_interface OBJECT-TYPE
    SYNTAX DisplayString
    MAX-ACCESS accessible-for-notify
    STATUS current
    DESCRIPTION
        "Parameter 'interface' in event SRT.4"
    ::= { srtEventObjects4 2 }

srtEventObjects5 OBJECT-IDENTITY
    STATUS current
    DESCRIPTION
        "Event SRT.5
        The sending of a packet being forwarded failed. The reason is
        the internal error code for the failure."
    ::= { srtEventsGroup 5 }

srt5_source_mac OBJECT-TYPE
    SYNTAX DisplayString
    MAX-ACCESS accessible-for-notify
    STATUS current
    DESCRIPTION
        "Parameter 'source_mac' in event SRT.5"
    ::= { srtEventObjects5 1 }

srt5_dest_mac OBJECT-TYPE
    SYNTAX DisplayString
    MAX-ACCESS accessible-for-notify
    STATUS current
    DESCRIPTION
        "Parameter 'dest_mac' in event SRT.5"
    ::= { srtEventObjects5 2 }

srt5_reason_code OBJECT-TYPE
    SYNTAX Integer32
    MAX-ACCESS accessible-for-notify
    STATUS current
    DESCRIPTION
        "Parameter 'reason_code' in event SRT.5"
    ::= { srtEventObjects5 3 }

srt5_port OBJECT-TYPE
    SYNTAX Integer32
    MAX-ACCESS accessible-for-notify
    STATUS current
    DESCRIPTION
        "Parameter 'port' in event SRT.5"
    ::= { srtEventObjects5 4 }

srt5_interface_name OBJECT-TYPE
    SYNTAX DisplayString
    MAX-ACCESS accessible-for-notify
    STATUS current
    DESCRIPTION
        "Parameter 'interface_name' in event SRT.5"
    ::= { srtEventObjects5 5 }

srt5_circuit_name OBJECT-TYPE
    SYNTAX DisplayString
    MAX-ACCESS accessible-for-notify
    STATUS current
    DESCRIPTION
        "Parameter 'circuit_name' in event SRT.5"
    ::= { srtEventObjects5 6 }

srtEventObjects6 OBJECT-IDENTITY
    STATUS current
    DESCRIPTION
        "Event SRT.6
        The input queue for frames to be forwarded is too long, and this frame
        has been dropped to attempt to alleviate the congestion."
    ::= { srtEventsGroup 6 }

srt6_source_mac OBJECT-TYPE
    SYNTAX DisplayString
    MAX-ACCESS accessible-for-notify
    STATUS current
    DESCRIPTION
        "Parameter 'source_mac' in event SRT.6"
    ::= { srtEventObjects6 1 }

srt6_dest_mac OBJECT-TYPE
    SYNTAX DisplayString
    MAX-ACCESS accessible-for-notify
    STATUS current
    DESCRIPTION
        "Parameter 'dest_mac' in event SRT.6"
    ::= { srtEventObjects6 2 }

srt6_interface OBJECT-TYPE
    SYNTAX DisplayString
    MAX-ACCESS accessible-for-notify
    STATUS current
    DESCRIPTION
        "Parameter 'interface' in event SRT.6"
    ::= { srtEventObjects6 3 }

srt6_circuit_name OBJECT-TYPE
    SYNTAX DisplayString
    MAX-ACCESS accessible-for-notify
    STATUS current
    DESCRIPTION
        "Parameter 'circuit_name' in event SRT.6"
    ::= { srtEventObjects6 4 }

srtEventObjects7 OBJECT-IDENTITY
    STATUS current
    DESCRIPTION
        "Event SRT.7
        The input queue for Spanning Tree Protocol Bridge Protocl Data Units
        is too long, and this frame has been dropped to attempt to alleviate
        the congestion."
    ::= { srtEventsGroup 7 }

srt7_source_mac OBJECT-TYPE
    SYNTAX DisplayString
    MAX-ACCESS accessible-for-notify
    STATUS current
    DESCRIPTION
        "Parameter 'source_mac' in event SRT.7"
    ::= { srtEventObjects7 1 }

srt7_interface OBJECT-TYPE
    SYNTAX DisplayString
    MAX-ACCESS accessible-for-notify
    STATUS current
    DESCRIPTION
        "Parameter 'interface' in event SRT.7"
    ::= { srtEventObjects7 2 }

srt7_circuit_name OBJECT-TYPE
    SYNTAX DisplayString
    MAX-ACCESS accessible-for-notify
    STATUS current
    DESCRIPTION
        "Parameter 'circuit_name' in event SRT.7"
    ::= { srtEventObjects7 3 }

srtEventObjects8 OBJECT-IDENTITY
    STATUS current
    DESCRIPTION
        "Event SRT.8
        The specified frame is too large to send on this outgoing port and
        interface. The reformatted_length is the size of the frame including
        MAC headers after any mapping of data link headers."
    ::= { srtEventsGroup 8 }

srt8_source_mac OBJECT-TYPE
    SYNTAX DisplayString
    MAX-ACCESS accessible-for-notify
    STATUS current
    DESCRIPTION
        "Parameter 'source_mac' in event SRT.8"
    ::= { srtEventObjects8 1 }

srt8_dest_mac OBJECT-TYPE
    SYNTAX DisplayString
    MAX-ACCESS accessible-for-notify
    STATUS current
    DESCRIPTION
        "Parameter 'dest_mac' in event SRT.8"
    ::= { srtEventObjects8 2 }

srt8_reformatted_length OBJECT-TYPE
    SYNTAX Integer32
    MAX-ACCESS accessible-for-notify
    STATUS current
    DESCRIPTION
        "Parameter 'reformatted_length' in event SRT.8"
    ::= { srtEventObjects8 3 }

srt8_output_maximum OBJECT-TYPE
    SYNTAX Integer32
    MAX-ACCESS accessible-for-notify
    STATUS current
    DESCRIPTION
        "Parameter 'output_maximum' in event SRT.8"
    ::= { srtEventObjects8 4 }

srt8_port OBJECT-TYPE
    SYNTAX Integer32
    MAX-ACCESS accessible-for-notify
    STATUS current
    DESCRIPTION
        "Parameter 'port' in event SRT.8"
    ::= { srtEventObjects8 5 }

srt8_interface OBJECT-TYPE
    SYNTAX DisplayString
    MAX-ACCESS accessible-for-notify
    STATUS current
    DESCRIPTION
        "Parameter 'interface' in event SRT.8"
    ::= { srtEventObjects8 6 }

srt8_circuit_name OBJECT-TYPE
    SYNTAX DisplayString
    MAX-ACCESS accessible-for-notify
    STATUS current
    DESCRIPTION
        "Parameter 'circuit_name' in event SRT.8"
    ::= { srtEventObjects8 7 }

srtEventObjects9 OBJECT-IDENTITY
    STATUS current
    DESCRIPTION
        "Event SRT.9
        A frame has been received for bridging on an interface that is down.
        It will be ignored."
    ::= { srtEventsGroup 9 }

srt9_source_mac OBJECT-TYPE
    SYNTAX DisplayString
    MAX-ACCESS accessible-for-notify
    STATUS current
    DESCRIPTION
        "Parameter 'source_mac' in event SRT.9"
    ::= { srtEventObjects9 1 }

srt9_dest_mac OBJECT-TYPE
    SYNTAX DisplayString
    MAX-ACCESS accessible-for-notify
    STATUS current
    DESCRIPTION
        "Parameter 'dest_mac' in event SRT.9"
    ::= { srtEventObjects9 2 }

srt9_interface OBJECT-TYPE
    SYNTAX DisplayString
    MAX-ACCESS accessible-for-notify
    STATUS current
    DESCRIPTION
        "Parameter 'interface' in event SRT.9"
    ::= { srtEventObjects9 3 }

srtEventObjects10 OBJECT-IDENTITY
    STATUS current
    DESCRIPTION
        "Event SRT.10
        A MAC frame has been received by the hardware, but is being dropped
        because the source MAC address is being administratively filtered
        by the bridge. The frame will be dropped."
    ::= { srtEventsGroup 10 }

srt10_source_mac OBJECT-TYPE
    SYNTAX DisplayString
    MAX-ACCESS accessible-for-notify
    STATUS current
    DESCRIPTION
        "Parameter 'source_mac' in event SRT.10"
    ::= { srtEventObjects10 1 }

srt10_dest_mac OBJECT-TYPE
    SYNTAX DisplayString
    MAX-ACCESS accessible-for-notify
    STATUS current
    DESCRIPTION
        "Parameter 'dest_mac' in event SRT.10"
    ::= { srtEventObjects10 2 }

srt10_port OBJECT-TYPE
    SYNTAX Integer32
    MAX-ACCESS accessible-for-notify
    STATUS current
    DESCRIPTION
        "Parameter 'port' in event SRT.10"
    ::= { srtEventObjects10 3 }

srt10_interface OBJECT-TYPE
    SYNTAX DisplayString
    MAX-ACCESS accessible-for-notify
    STATUS current
    DESCRIPTION
        "Parameter 'interface' in event SRT.10"
    ::= { srtEventObjects10 4 }

srt10_circuit_name OBJECT-TYPE
    SYNTAX DisplayString
    MAX-ACCESS accessible-for-notify
    STATUS current
    DESCRIPTION
        "Parameter 'circuit_name' in event SRT.10"
    ::= { srtEventObjects10 5 }

srtEventObjects11 OBJECT-IDENTITY
    STATUS current
    DESCRIPTION
        "Event SRT.11
        A MAC frame was received on a port that is still only in 'learning'
        state. Frames are only bridged when the input port is in 'forwarding'
        state. While the port is still in 'learning' state, they are only
        processed to learn the source addresses for the filtering database.
        The frame will not be bridged."
    ::= { srtEventsGroup 11 }

srt11_source_mac OBJECT-TYPE
    SYNTAX DisplayString
    MAX-ACCESS accessible-for-notify
    STATUS current
    DESCRIPTION
        "Parameter 'source_mac' in event SRT.11"
    ::= { srtEventObjects11 1 }

srt11_dest_mac OBJECT-TYPE
    SYNTAX DisplayString
    MAX-ACCESS accessible-for-notify
    STATUS current
    DESCRIPTION
        "Parameter 'dest_mac' in event SRT.11"
    ::= { srtEventObjects11 2 }

srt11_port OBJECT-TYPE
    SYNTAX Integer32
    MAX-ACCESS accessible-for-notify
    STATUS current
    DESCRIPTION
        "Parameter 'port' in event SRT.11"
    ::= { srtEventObjects11 3 }

srt11_interface OBJECT-TYPE
    SYNTAX DisplayString
    MAX-ACCESS accessible-for-notify
    STATUS current
    DESCRIPTION
        "Parameter 'interface' in event SRT.11"
    ::= { srtEventObjects11 4 }

srt11_circuit_name OBJECT-TYPE
    SYNTAX DisplayString
    MAX-ACCESS accessible-for-notify
    STATUS current
    DESCRIPTION
        "Parameter 'circuit_name' in event SRT.11"
    ::= { srtEventObjects11 5 }

srtEventObjects12 OBJECT-IDENTITY
    STATUS current
    DESCRIPTION
        "Event SRT.12
        A MAC frame was being bridged, but the destination port was not
        in 'forwarding' state. It will not be sent on that port."
    ::= { srtEventsGroup 12 }

srt12_source_mac OBJECT-TYPE
    SYNTAX DisplayString
    MAX-ACCESS accessible-for-notify
    STATUS current
    DESCRIPTION
        "Parameter 'source_mac' in event SRT.12"
    ::= { srtEventObjects12 1 }

srt12_dest_mac OBJECT-TYPE
    SYNTAX DisplayString
    MAX-ACCESS accessible-for-notify
    STATUS current
    DESCRIPTION
        "Parameter 'dest_mac' in event SRT.12"
    ::= { srtEventObjects12 2 }

srt12_port OBJECT-TYPE
    SYNTAX Integer32
    MAX-ACCESS accessible-for-notify
    STATUS current
    DESCRIPTION
        "Parameter 'port' in event SRT.12"
    ::= { srtEventObjects12 3 }

srt12_interface OBJECT-TYPE
    SYNTAX DisplayString
    MAX-ACCESS accessible-for-notify
    STATUS current
    DESCRIPTION
        "Parameter 'interface' in event SRT.12"
    ::= { srtEventObjects12 4 }

srt12_circuit_name OBJECT-TYPE
    SYNTAX DisplayString
    MAX-ACCESS accessible-for-notify
    STATUS current
    DESCRIPTION
        "Parameter 'circuit_name' in event SRT.12"
    ::= { srtEventObjects12 5 }

srtEventObjects13 OBJECT-IDENTITY
    STATUS current
    DESCRIPTION
        "Event SRT.13
        A MAC frame has been received whose destination address is known to be
        on the same side of the bridge as the packet came from. It is dropped
        by the filtering logic since it does not need to be bridged."
    ::= { srtEventsGroup 13 }

srt13_source_mac OBJECT-TYPE
    SYNTAX DisplayString
    MAX-ACCESS accessible-for-notify
    STATUS current
    DESCRIPTION
        "Parameter 'source_mac' in event SRT.13"
    ::= { srtEventObjects13 1 }

srt13_dest_mac OBJECT-TYPE
    SYNTAX DisplayString
    MAX-ACCESS accessible-for-notify
    STATUS current
    DESCRIPTION
        "Parameter 'dest_mac' in event SRT.13"
    ::= { srtEventObjects13 2 }

srt13_port OBJECT-TYPE
    SYNTAX Integer32
    MAX-ACCESS accessible-for-notify
    STATUS current
    DESCRIPTION
        "Parameter 'port' in event SRT.13"
    ::= { srtEventObjects13 3 }

srt13_interface OBJECT-TYPE
    SYNTAX DisplayString
    MAX-ACCESS accessible-for-notify
    STATUS current
    DESCRIPTION
        "Parameter 'interface' in event SRT.13"
    ::= { srtEventObjects13 4 }

srt13_circuit_name OBJECT-TYPE
    SYNTAX DisplayString
    MAX-ACCESS accessible-for-notify
    STATUS current
    DESCRIPTION
        "Parameter 'circuit_name' in event SRT.13"
    ::= { srtEventObjects13 5 }

srtEventObjects14 OBJECT-IDENTITY
    STATUS current
    DESCRIPTION
        "Event SRT.14
        A frame being bridged was destined for a port which is not running
        transparent bridging, or not in 'forwarding' state for transparent
        bridging."
    ::= { srtEventsGroup 14 }

srt14_source_mac OBJECT-TYPE
    SYNTAX DisplayString
    MAX-ACCESS accessible-for-notify
    STATUS current
    DESCRIPTION
        "Parameter 'source_mac' in event SRT.14"
    ::= { srtEventObjects14 1 }

srt14_dest_mac OBJECT-TYPE
    SYNTAX DisplayString
    MAX-ACCESS accessible-for-notify
    STATUS current
    DESCRIPTION
        "Parameter 'dest_mac' in event SRT.14"
    ::= { srtEventObjects14 2 }

srt14_port OBJECT-TYPE
    SYNTAX Integer32
    MAX-ACCESS accessible-for-notify
    STATUS current
    DESCRIPTION
        "Parameter 'port' in event SRT.14"
    ::= { srtEventObjects14 3 }

srt14_interface OBJECT-TYPE
    SYNTAX DisplayString
    MAX-ACCESS accessible-for-notify
    STATUS current
    DESCRIPTION
        "Parameter 'interface' in event SRT.14"
    ::= { srtEventObjects14 4 }

srt14_circuit_name OBJECT-TYPE
    SYNTAX DisplayString
    MAX-ACCESS accessible-for-notify
    STATUS current
    DESCRIPTION
        "Parameter 'circuit_name' in event SRT.14"
    ::= { srtEventObjects14 5 }

srtEventObjects15 OBJECT-IDENTITY
    STATUS current
    DESCRIPTION
        "Event SRT.15
        A frame is being bridged between these two interfaces. The destination
        address was known, so it was sent only to the correct destination
        network."
    ::= { srtEventsGroup 15 }

srt15_source_mac OBJECT-TYPE
    SYNTAX DisplayString
    MAX-ACCESS accessible-for-notify
    STATUS current
    DESCRIPTION
        "Parameter 'source_mac' in event SRT.15"
    ::= { srtEventObjects15 1 }

srt15_dest_mac OBJECT-TYPE
    SYNTAX DisplayString
    MAX-ACCESS accessible-for-notify
    STATUS current
    DESCRIPTION
        "Parameter 'dest_mac' in event SRT.15"
    ::= { srtEventObjects15 2 }

srt15_port OBJECT-TYPE
    SYNTAX Integer32
    MAX-ACCESS accessible-for-notify
    STATUS current
    DESCRIPTION
        "Parameter 'port' in event SRT.15"
    ::= { srtEventObjects15 3 }

srt15_interface OBJECT-TYPE
    SYNTAX DisplayString
    MAX-ACCESS accessible-for-notify
    STATUS current
    DESCRIPTION
        "Parameter 'interface' in event SRT.15"
    ::= { srtEventObjects15 4 }

srt15_circuit_name OBJECT-TYPE
    SYNTAX DisplayString
    MAX-ACCESS accessible-for-notify
    STATUS current
    DESCRIPTION
        "Parameter 'circuit_name' in event SRT.15"
    ::= { srtEventObjects15 5 }

srt15_out_port OBJECT-TYPE
    SYNTAX Integer32
    MAX-ACCESS accessible-for-notify
    STATUS current
    DESCRIPTION
        "Parameter 'out_port' in event SRT.15"
    ::= { srtEventObjects15 6 }

srt15_out_interface OBJECT-TYPE
    SYNTAX DisplayString
    MAX-ACCESS accessible-for-notify
    STATUS current
    DESCRIPTION
        "Parameter 'out_interface' in event SRT.15"
    ::= { srtEventObjects15 7 }

srt15_out_circuit_name OBJECT-TYPE
    SYNTAX DisplayString
    MAX-ACCESS accessible-for-notify
    STATUS current
    DESCRIPTION
        "Parameter 'out_circuit_name' in event SRT.15"
    ::= { srtEventObjects15 8 }

srtEventObjects16 OBJECT-IDENTITY
    STATUS current
    DESCRIPTION
        "Event SRT.16
        A frame is being transparently bridged to all active transparent
        bridging ports. This happens when the frame destination is a multicast,
        when the frame destination is not in the learning database, or when
        required by static entries in the learning database.
        There will be one message for each port the frame is sent on."
    ::= { srtEventsGroup 16 }

srt16_source_mac OBJECT-TYPE
    SYNTAX DisplayString
    MAX-ACCESS accessible-for-notify
    STATUS current
    DESCRIPTION
        "Parameter 'source_mac' in event SRT.16"
    ::= { srtEventObjects16 1 }

srt16_dest_mac OBJECT-TYPE
    SYNTAX DisplayString
    MAX-ACCESS accessible-for-notify
    STATUS current
    DESCRIPTION
        "Parameter 'dest_mac' in event SRT.16"
    ::= { srtEventObjects16 2 }

srt16_port OBJECT-TYPE
    SYNTAX Integer32
    MAX-ACCESS accessible-for-notify
    STATUS current
    DESCRIPTION
        "Parameter 'port' in event SRT.16"
    ::= { srtEventObjects16 3 }

srt16_interface OBJECT-TYPE
    SYNTAX DisplayString
    MAX-ACCESS accessible-for-notify
    STATUS current
    DESCRIPTION
        "Parameter 'interface' in event SRT.16"
    ::= { srtEventObjects16 4 }

srt16_circuit_name OBJECT-TYPE
    SYNTAX DisplayString
    MAX-ACCESS accessible-for-notify
    STATUS current
    DESCRIPTION
        "Parameter 'circuit_name' in event SRT.16"
    ::= { srtEventObjects16 5 }

srt16_out_port OBJECT-TYPE
    SYNTAX Integer32
    MAX-ACCESS accessible-for-notify
    STATUS current
    DESCRIPTION
        "Parameter 'out_port' in event SRT.16"
    ::= { srtEventObjects16 6 }

srt16_out_interface OBJECT-TYPE
    SYNTAX DisplayString
    MAX-ACCESS accessible-for-notify
    STATUS current
    DESCRIPTION
        "Parameter 'out_interface' in event SRT.16"
    ::= { srtEventObjects16 7 }

srt16_out_circuit_name OBJECT-TYPE
    SYNTAX DisplayString
    MAX-ACCESS accessible-for-notify
    STATUS current
    DESCRIPTION
        "Parameter 'out_circuit_name' in event SRT.16"
    ::= { srtEventObjects16 8 }

srtEventObjects17 OBJECT-IDENTITY
    STATUS current
    DESCRIPTION
        "Event SRT.17
        The SRT forwarder is starting the process of enabling bridging
        on the specified interface. This starts when the interface comes up
        from a self-test."
    ::= { srtEventsGroup 17 }

srt17_port OBJECT-TYPE
    SYNTAX Integer32
    MAX-ACCESS accessible-for-notify
    STATUS current
    DESCRIPTION
        "Parameter 'port' in event SRT.17"
    ::= { srtEventObjects17 1 }

srt17_interface OBJECT-TYPE
    SYNTAX DisplayString
    MAX-ACCESS accessible-for-notify
    STATUS current
    DESCRIPTION
        "Parameter 'interface' in event SRT.17"
    ::= { srtEventObjects17 2 }

srt17_circuit_name OBJECT-TYPE
    SYNTAX DisplayString
    MAX-ACCESS accessible-for-notify
    STATUS current
    DESCRIPTION
        "Parameter 'circuit_name' in event SRT.17"
    ::= { srtEventObjects17 3 }

srtEventObjects18 OBJECT-IDENTITY
    STATUS current
    DESCRIPTION
        "Event SRT.18
        The SRT forwarder has completed the process of enabling bridging
        on the specified interface. It will now enter 'blocking' state."
    ::= { srtEventsGroup 18 }

srt18_port OBJECT-TYPE
    SYNTAX Integer32
    MAX-ACCESS accessible-for-notify
    STATUS current
    DESCRIPTION
        "Parameter 'port' in event SRT.18"
    ::= { srtEventObjects18 1 }

srt18_interface OBJECT-TYPE
    SYNTAX DisplayString
    MAX-ACCESS accessible-for-notify
    STATUS current
    DESCRIPTION
        "Parameter 'interface' in event SRT.18"
    ::= { srtEventObjects18 2 }

srt18_circuit_name OBJECT-TYPE
    SYNTAX DisplayString
    MAX-ACCESS accessible-for-notify
    STATUS current
    DESCRIPTION
        "Parameter 'circuit_name' in event SRT.18"
    ::= { srtEventObjects18 3 }

srtEventObjects19 OBJECT-IDENTITY
    STATUS current
    DESCRIPTION
        "Event SRT.19
        The SRT forwarder had been enabled on a type of interface it does not
        support."
    ::= { srtEventsGroup 19 }

srt19_interface_name OBJECT-TYPE
    SYNTAX DisplayString
    MAX-ACCESS accessible-for-notify
    STATUS current
    DESCRIPTION
        "Parameter 'interface_name' in event SRT.19"
    ::= { srtEventObjects19 1 }

srtEventObjects20 OBJECT-IDENTITY
    STATUS current
    DESCRIPTION
        "Event SRT.20
        The user has configured the bridge to autoconfigure the bridge address
        based on the MAC address of the lowest number port. However, the lowest
        numbered port is of a type that does not have a MAC address, such as
        a serial line."
    ::= { srtEventsGroup 20 }

srt20_port OBJECT-TYPE
    SYNTAX Integer32
    MAX-ACCESS accessible-for-notify
    STATUS current
    DESCRIPTION
        "Parameter 'port' in event SRT.20"
    ::= { srtEventObjects20 1 }

srt20_interface OBJECT-TYPE
    SYNTAX DisplayString
    MAX-ACCESS accessible-for-notify
    STATUS current
    DESCRIPTION
        "Parameter 'interface' in event SRT.20"
    ::= { srtEventObjects20 2 }

srt20_circuit_name OBJECT-TYPE
    SYNTAX DisplayString
    MAX-ACCESS accessible-for-notify
    STATUS current
    DESCRIPTION
        "Parameter 'circuit_name' in event SRT.20"
    ::= { srtEventObjects20 3 }

srtEventObjects21 OBJECT-IDENTITY
    STATUS current
    DESCRIPTION
        "Event SRT.21
        Bridge frame received, but there is no bridging available in this load.
        The frame will be ignored."
    ::= { srtEventsGroup 21 }

srt21_source_mac OBJECT-TYPE
    SYNTAX DisplayString
    MAX-ACCESS accessible-for-notify
    STATUS current
    DESCRIPTION
        "Parameter 'source_mac' in event SRT.21"
    ::= { srtEventObjects21 1 }

srt21_dest_mac OBJECT-TYPE
    SYNTAX DisplayString
    MAX-ACCESS accessible-for-notify
    STATUS current
    DESCRIPTION
        "Parameter 'dest_mac' in event SRT.21"
    ::= { srtEventObjects21 2 }

srt21_interface OBJECT-TYPE
    SYNTAX DisplayString
    MAX-ACCESS accessible-for-notify
    STATUS current
    DESCRIPTION
        "Parameter 'interface' in event SRT.21"
    ::= { srtEventObjects21 3 }

srtEventObjects23 OBJECT-IDENTITY
    STATUS current
    DESCRIPTION
        "Event SRT.23
        The port has been configured to use an interface that has not been
        configured with the Config> ADD DEVICE command.
        This port of the bridge will be disabled."
    ::= { srtEventsGroup 23 }

srt23_port OBJECT-TYPE
    SYNTAX Integer32
    MAX-ACCESS accessible-for-notify
    STATUS current
    DESCRIPTION
        "Parameter 'port' in event SRT.23"
    ::= { srtEventObjects23 1 }

srt23_interface_number OBJECT-TYPE
    SYNTAX Integer32
    MAX-ACCESS accessible-for-notify
    STATUS current
    DESCRIPTION
        "Parameter 'interface_number' in event SRT.23"
    ::= { srtEventObjects23 2 }

srtEventObjects24 OBJECT-IDENTITY
    STATUS current
    DESCRIPTION
        "Event SRT.24
        Less than two (valid) ports have been configured on the bridge.
        There must be at least two ports."
    ::= { srtEventsGroup 24 }

srt24_existent_port_count OBJECT-TYPE
    SYNTAX Integer32
    MAX-ACCESS accessible-for-notify
    STATUS current
    DESCRIPTION
        "Parameter 'existent_port_count' in event SRT.24"
    ::= { srtEventObjects24 1 }

srtEventObjects25 OBJECT-IDENTITY
    STATUS current
    DESCRIPTION
        "Event SRT.25
        There is not enough free memory to allocate even a minimal size
        filtering database. The bridge will be disabled.
        The bridge starts by trying to allocate requested_size bytes, and then
        tries with progressively smaller sizes down to minimum_size.
        The minimum size is enough only for the registered and static entries."
    ::= { srtEventsGroup 25 }

srt25_requested_size OBJECT-TYPE
    SYNTAX Integer32
    MAX-ACCESS accessible-for-notify
    STATUS current
    DESCRIPTION
        "Parameter 'requested_size' in event SRT.25"
    ::= { srtEventObjects25 1 }

srt25_minimum_size OBJECT-TYPE
    SYNTAX Integer32
    MAX-ACCESS accessible-for-notify
    STATUS current
    DESCRIPTION
        "Parameter 'minimum_size' in event SRT.25"
    ::= { srtEventObjects25 2 }

srtEventObjects26 OBJECT-IDENTITY
    STATUS current
    DESCRIPTION
        "Event SRT.26
        Frames to and from the same address are not bridged by this bridge."
    ::= { srtEventsGroup 26 }

srt26_source_mac OBJECT-TYPE
    SYNTAX DisplayString
    MAX-ACCESS accessible-for-notify
    STATUS current
    DESCRIPTION
        "Parameter 'source_mac' in event SRT.26"
    ::= { srtEventObjects26 1 }

srt26_dest_mac OBJECT-TYPE
    SYNTAX DisplayString
    MAX-ACCESS accessible-for-notify
    STATUS current
    DESCRIPTION
        "Parameter 'dest_mac' in event SRT.26"
    ::= { srtEventObjects26 2 }

srt26_port OBJECT-TYPE
    SYNTAX Integer32
    MAX-ACCESS accessible-for-notify
    STATUS current
    DESCRIPTION
        "Parameter 'port' in event SRT.26"
    ::= { srtEventObjects26 3 }

srt26_interface OBJECT-TYPE
    SYNTAX DisplayString
    MAX-ACCESS accessible-for-notify
    STATUS current
    DESCRIPTION
        "Parameter 'interface' in event SRT.26"
    ::= { srtEventObjects26 4 }

srt26_circuit_name OBJECT-TYPE
    SYNTAX DisplayString
    MAX-ACCESS accessible-for-notify
    STATUS current
    DESCRIPTION
        "Parameter 'circuit_name' in event SRT.26"
    ::= { srtEventObjects26 5 }

srtEventObjects27 OBJECT-IDENTITY
    STATUS current
    DESCRIPTION
        "Event SRT.27
        The Spanning Tree Protocol has requested this state change for this port
        in the SRT bridge. The old_state and new_state are one of:
        FORWARDING (Spanning Tree Protocol Forwarding state),
        LEARNING (Spanning Tree Protocol Learning state),
        LISTENING (Spanning Tree Protocol Listening state),
        BLOCKED (Spanning Tree Protocol Blocking state),
        CONFIGURING (configuration of port device pending),
        POSTCONFIGURING (configuration of port device done),
        PRECONFIGURING (port enabled, configuration of port device to start) and
        DISABLED (port disabled)."
    ::= { srtEventsGroup 27 }

srt27_old_state OBJECT-TYPE
    SYNTAX DisplayString
    MAX-ACCESS accessible-for-notify
    STATUS current
    DESCRIPTION
        "Parameter 'old_state' in event SRT.27"
    ::= { srtEventObjects27 1 }

srt27_new_state OBJECT-TYPE
    SYNTAX DisplayString
    MAX-ACCESS accessible-for-notify
    STATUS current
    DESCRIPTION
        "Parameter 'new_state' in event SRT.27"
    ::= { srtEventObjects27 2 }

srt27_port OBJECT-TYPE
    SYNTAX Integer32
    MAX-ACCESS accessible-for-notify
    STATUS current
    DESCRIPTION
        "Parameter 'port' in event SRT.27"
    ::= { srtEventObjects27 3 }

srt27_interface OBJECT-TYPE
    SYNTAX DisplayString
    MAX-ACCESS accessible-for-notify
    STATUS current
    DESCRIPTION
        "Parameter 'interface' in event SRT.27"
    ::= { srtEventObjects27 4 }

srt27_circuit_name OBJECT-TYPE
    SYNTAX DisplayString
    MAX-ACCESS accessible-for-notify
    STATUS current
    DESCRIPTION
        "Parameter 'circuit_name' in event SRT.27"
    ::= { srtEventObjects27 5 }

srtEventObjects28 OBJECT-IDENTITY
    STATUS current
    DESCRIPTION
        "Event SRT.28
        There is no room for the permanent entry in the filtering database.
        The bridge will be disabled."
    ::= { srtEventsGroup 28 }

srt28_mac_address OBJECT-TYPE
    SYNTAX DisplayString
    MAX-ACCESS accessible-for-notify
    STATUS current
    DESCRIPTION
        "Parameter 'mac_address' in event SRT.28"
    ::= { srtEventObjects28 1 }

srtEventObjects29 OBJECT-IDENTITY
    STATUS current
    DESCRIPTION
        "Event SRT.29
        There is no room for the permanent entry in an auxiliary database.
        The bridge will be disabled."
    ::= { srtEventsGroup 29 }

srt29_mac_address OBJECT-TYPE
    SYNTAX DisplayString
    MAX-ACCESS accessible-for-notify
    STATUS current
    DESCRIPTION
        "Parameter 'mac_address' in event SRT.29"
    ::= { srtEventObjects29 1 }

srtEventObjects30 OBJECT-IDENTITY
    STATUS current
    DESCRIPTION
        "Event SRT.30
        A command to a network device failed.
        The possible command names are
        'SRT_ON' (promiscuous on),
        'SRT_OFF' (promiscuous off),
        'SRT_INFORM' (learn capabilities of device),
        'SRT_ADD_ENTRY' (add static entry in device),
        'SRT_SET_AGE' (set age for filtering database in device) and
        'SRT_DECR_AGE' (do ageing pass on filtering database in device).
        For commands 'SRT_ON' and 'SRT_OFF' the result will be that
        the interface may remain in the worong state. A failure on 'SRT_INFORM'
        could cause serious problems. For other commands the results will be
        less serious."
    ::= { srtEventsGroup 30 }

srt30_command OBJECT-TYPE
    SYNTAX DisplayString
    MAX-ACCESS accessible-for-notify
    STATUS current
    DESCRIPTION
        "Parameter 'command' in event SRT.30"
    ::= { srtEventObjects30 1 }

srt30_interface OBJECT-TYPE
    SYNTAX DisplayString
    MAX-ACCESS accessible-for-notify
    STATUS current
    DESCRIPTION
        "Parameter 'interface' in event SRT.30"
    ::= { srtEventObjects30 2 }

srtEventObjects31 OBJECT-IDENTITY
    STATUS current
    DESCRIPTION
        "Event SRT.31
        No buffer available to copy a frame in order to send an
        All Routes Explorer (ARE) or Spanning Tree Explorer (STE) routing_type
        frame on multiple interfaces. ARE frames are sent on all interfaces
        which are part of the SRT spanning tree, STE frames are sent
        on all interfaces running source-routing.
        No copy of this frame will be sent on the specified port and interface."
    ::= { srtEventsGroup 31 }

srt31_routing_type OBJECT-TYPE
    SYNTAX DisplayString
    MAX-ACCESS accessible-for-notify
    STATUS current
    DESCRIPTION
        "Parameter 'routing_type' in event SRT.31"
    ::= { srtEventObjects31 1 }

srt31_source_mac OBJECT-TYPE
    SYNTAX DisplayString
    MAX-ACCESS accessible-for-notify
    STATUS current
    DESCRIPTION
        "Parameter 'source_mac' in event SRT.31"
    ::= { srtEventObjects31 2 }

srt31_dest_mac OBJECT-TYPE
    SYNTAX DisplayString
    MAX-ACCESS accessible-for-notify
    STATUS current
    DESCRIPTION
        "Parameter 'dest_mac' in event SRT.31"
    ::= { srtEventObjects31 3 }

srt31_port OBJECT-TYPE
    SYNTAX Integer32
    MAX-ACCESS accessible-for-notify
    STATUS current
    DESCRIPTION
        "Parameter 'port' in event SRT.31"
    ::= { srtEventObjects31 4 }

srt31_interface OBJECT-TYPE
    SYNTAX DisplayString
    MAX-ACCESS accessible-for-notify
    STATUS current
    DESCRIPTION
        "Parameter 'interface' in event SRT.31"
    ::= { srtEventObjects31 5 }

srt31_circuit_name OBJECT-TYPE
    SYNTAX DisplayString
    MAX-ACCESS accessible-for-notify
    STATUS current
    DESCRIPTION
        "Parameter 'circuit_name' in event SRT.31"
    ::= { srtEventObjects31 6 }

srtEventObjects32 OBJECT-IDENTITY
    STATUS current
    DESCRIPTION
        "Event SRT.32
        The sending of a source routed frame being forwarded failed.
        The reason_code is the internal error code for the failure."
    ::= { srtEventsGroup 32 }

srt32_source_mac OBJECT-TYPE
    SYNTAX DisplayString
    MAX-ACCESS accessible-for-notify
    STATUS current
    DESCRIPTION
        "Parameter 'source_mac' in event SRT.32"
    ::= { srtEventObjects32 1 }

srt32_dest_mac OBJECT-TYPE
    SYNTAX DisplayString
    MAX-ACCESS accessible-for-notify
    STATUS current
    DESCRIPTION
        "Parameter 'dest_mac' in event SRT.32"
    ::= { srtEventObjects32 2 }

srt32_reason_code OBJECT-TYPE
    SYNTAX Integer32
    MAX-ACCESS accessible-for-notify
    STATUS current
    DESCRIPTION
        "Parameter 'reason_code' in event SRT.32"
    ::= { srtEventObjects32 3 }

srt32_port OBJECT-TYPE
    SYNTAX Integer32
    MAX-ACCESS accessible-for-notify
    STATUS current
    DESCRIPTION
        "Parameter 'port' in event SRT.32"
    ::= { srtEventObjects32 4 }

srt32_interface_name OBJECT-TYPE
    SYNTAX DisplayString
    MAX-ACCESS accessible-for-notify
    STATUS current
    DESCRIPTION
        "Parameter 'interface_name' in event SRT.32"
    ::= { srtEventObjects32 5 }

srt32_circuit_name OBJECT-TYPE
    SYNTAX DisplayString
    MAX-ACCESS accessible-for-notify
    STATUS current
    DESCRIPTION
        "Parameter 'circuit_name' in event SRT.32"
    ::= { srtEventObjects32 6 }

srtEventObjects33 OBJECT-IDENTITY
    STATUS current
    DESCRIPTION
        "Event SRT.33
        A source-routed frame having a All Routes Descriptor (ARE)
        or Spanning Tree Explorer (STE) routing_type in the RIF has a duplicate
        Routing Descriptor in the RIF. The frame will be dropped. This is
        a normal occurrence for ARE frames when there are any duplicate paths
        in the source routing domain. For STE frames, this indicates that
        there is an interface that is part of the source-routing spanning tree
        that should not be."
    ::= { srtEventsGroup 33 }

srt33_routing_type OBJECT-TYPE
    SYNTAX DisplayString
    MAX-ACCESS accessible-for-notify
    STATUS current
    DESCRIPTION
        "Parameter 'routing_type' in event SRT.33"
    ::= { srtEventObjects33 1 }

srt33_source_mac OBJECT-TYPE
    SYNTAX DisplayString
    MAX-ACCESS accessible-for-notify
    STATUS current
    DESCRIPTION
        "Parameter 'source_mac' in event SRT.33"
    ::= { srtEventObjects33 2 }

srt33_dest_mac OBJECT-TYPE
    SYNTAX DisplayString
    MAX-ACCESS accessible-for-notify
    STATUS current
    DESCRIPTION
        "Parameter 'dest_mac' in event SRT.33"
    ::= { srtEventObjects33 3 }

srt33_port OBJECT-TYPE
    SYNTAX Integer32
    MAX-ACCESS accessible-for-notify
    STATUS current
    DESCRIPTION
        "Parameter 'port' in event SRT.33"
    ::= { srtEventObjects33 4 }

srt33_interface OBJECT-TYPE
    SYNTAX DisplayString
    MAX-ACCESS accessible-for-notify
    STATUS current
    DESCRIPTION
        "Parameter 'interface' in event SRT.33"
    ::= { srtEventObjects33 5 }

srt33_circuit_name OBJECT-TYPE
    SYNTAX DisplayString
    MAX-ACCESS accessible-for-notify
    STATUS current
    DESCRIPTION
        "Parameter 'circuit_name' in event SRT.33"
    ::= { srtEventObjects33 6 }

srtEventObjects34 OBJECT-IDENTITY
    STATUS current
    DESCRIPTION
        "Event SRT.34
        A source-routed frame of Specifically-routed frame (SRF) type has
        a duplicate LOUT (outgoing LAN ID). This is illegal, and the frame
        will be dropped."
    ::= { srtEventsGroup 34 }

srt34_RIF OBJECT-TYPE
    SYNTAX DisplayString
    MAX-ACCESS accessible-for-notify
    STATUS current
    DESCRIPTION
        "Parameter 'RIF' in event SRT.34"
    ::= { srtEventObjects34 1 }

srt34_source_mac OBJECT-TYPE
    SYNTAX DisplayString
    MAX-ACCESS accessible-for-notify
    STATUS current
    DESCRIPTION
        "Parameter 'source_mac' in event SRT.34"
    ::= { srtEventObjects34 2 }

srt34_dest_mac OBJECT-TYPE
    SYNTAX DisplayString
    MAX-ACCESS accessible-for-notify
    STATUS current
    DESCRIPTION
        "Parameter 'dest_mac' in event SRT.34"
    ::= { srtEventObjects34 3 }

srt34_port OBJECT-TYPE
    SYNTAX Integer32
    MAX-ACCESS accessible-for-notify
    STATUS current
    DESCRIPTION
        "Parameter 'port' in event SRT.34"
    ::= { srtEventObjects34 4 }

srt34_interface OBJECT-TYPE
    SYNTAX DisplayString
    MAX-ACCESS accessible-for-notify
    STATUS current
    DESCRIPTION
        "Parameter 'interface' in event SRT.34"
    ::= { srtEventObjects34 5 }

srt34_circuit_name OBJECT-TYPE
    SYNTAX DisplayString
    MAX-ACCESS accessible-for-notify
    STATUS current
    DESCRIPTION
        "Parameter 'circuit_name' in event SRT.34"
    ::= { srtEventObjects34 6 }

srtEventObjects35 OBJECT-IDENTITY
    STATUS current
    DESCRIPTION
        "Event SRT.35
        An All Routes Explorer (ARE) source-routed frame has more Route
        Descriptors than this bridge is configured to allow for ARE frames.
        The frame will be dropped."
    ::= { srtEventsGroup 35 }

srt35_RIF OBJECT-TYPE
    SYNTAX DisplayString
    MAX-ACCESS accessible-for-notify
    STATUS current
    DESCRIPTION
        "Parameter 'RIF' in event SRT.35"
    ::= { srtEventObjects35 1 }

srt35_source_mac OBJECT-TYPE
    SYNTAX DisplayString
    MAX-ACCESS accessible-for-notify
    STATUS current
    DESCRIPTION
        "Parameter 'source_mac' in event SRT.35"
    ::= { srtEventObjects35 2 }

srt35_dest_mac OBJECT-TYPE
    SYNTAX DisplayString
    MAX-ACCESS accessible-for-notify
    STATUS current
    DESCRIPTION
        "Parameter 'dest_mac' in event SRT.35"
    ::= { srtEventObjects35 3 }

srt35_port OBJECT-TYPE
    SYNTAX Integer32
    MAX-ACCESS accessible-for-notify
    STATUS current
    DESCRIPTION
        "Parameter 'port' in event SRT.35"
    ::= { srtEventObjects35 4 }

srt35_interface OBJECT-TYPE
    SYNTAX DisplayString
    MAX-ACCESS accessible-for-notify
    STATUS current
    DESCRIPTION
        "Parameter 'interface' in event SRT.35"
    ::= { srtEventObjects35 5 }

srt35_circuit_name OBJECT-TYPE
    SYNTAX DisplayString
    MAX-ACCESS accessible-for-notify
    STATUS current
    DESCRIPTION
        "Parameter 'circuit_name' in event SRT.35"
    ::= { srtEventObjects35 6 }

srtEventObjects36 OBJECT-IDENTITY
    STATUS current
    DESCRIPTION
        "Event SRT.36
        A Spanning Tree Explorer (STE) source-routed frame has more Route
        Descriptors than this bridge is configured to allow for STE frames.
        The frame will be dropped."
    ::= { srtEventsGroup 36 }

srt36_RIF OBJECT-TYPE
    SYNTAX DisplayString
    MAX-ACCESS accessible-for-notify
    STATUS current
    DESCRIPTION
        "Parameter 'RIF' in event SRT.36"
    ::= { srtEventObjects36 1 }

srt36_source_mac OBJECT-TYPE
    SYNTAX DisplayString
    MAX-ACCESS accessible-for-notify
    STATUS current
    DESCRIPTION
        "Parameter 'source_mac' in event SRT.36"
    ::= { srtEventObjects36 2 }

srt36_dest_mac OBJECT-TYPE
    SYNTAX DisplayString
    MAX-ACCESS accessible-for-notify
    STATUS current
    DESCRIPTION
        "Parameter 'dest_mac' in event SRT.36"
    ::= { srtEventObjects36 3 }

srt36_port OBJECT-TYPE
    SYNTAX Integer32
    MAX-ACCESS accessible-for-notify
    STATUS current
    DESCRIPTION
        "Parameter 'port' in event SRT.36"
    ::= { srtEventObjects36 4 }

srt36_interface OBJECT-TYPE
    SYNTAX DisplayString
    MAX-ACCESS accessible-for-notify
    STATUS current
    DESCRIPTION
        "Parameter 'interface' in event SRT.36"
    ::= { srtEventObjects36 5 }

srt36_circuit_name OBJECT-TYPE
    SYNTAX DisplayString
    MAX-ACCESS accessible-for-notify
    STATUS current
    DESCRIPTION
        "Parameter 'circuit_name' in event SRT.36"
    ::= { srtEventObjects36 6 }

srtEventObjects37 OBJECT-IDENTITY
    STATUS current
    DESCRIPTION
        "Event SRT.37
        A source-routed frame of Specifically-routed frame (SRF) type has
        an outgoing LOUT (LAN ID Out) that does not match that of any active
        source-routing interface in the router. It will be dropped."
    ::= { srtEventsGroup 37 }

srt37_RIF OBJECT-TYPE
    SYNTAX DisplayString
    MAX-ACCESS accessible-for-notify
    STATUS current
    DESCRIPTION
        "Parameter 'RIF' in event SRT.37"
    ::= { srtEventObjects37 1 }

srt37_source_mac OBJECT-TYPE
    SYNTAX DisplayString
    MAX-ACCESS accessible-for-notify
    STATUS current
    DESCRIPTION
        "Parameter 'source_mac' in event SRT.37"
    ::= { srtEventObjects37 2 }

srt37_dest_mac OBJECT-TYPE
    SYNTAX DisplayString
    MAX-ACCESS accessible-for-notify
    STATUS current
    DESCRIPTION
        "Parameter 'dest_mac' in event SRT.37"
    ::= { srtEventObjects37 3 }

srt37_port OBJECT-TYPE
    SYNTAX Integer32
    MAX-ACCESS accessible-for-notify
    STATUS current
    DESCRIPTION
        "Parameter 'port' in event SRT.37"
    ::= { srtEventObjects37 4 }

srt37_interface OBJECT-TYPE
    SYNTAX DisplayString
    MAX-ACCESS accessible-for-notify
    STATUS current
    DESCRIPTION
        "Parameter 'interface' in event SRT.37"
    ::= { srtEventObjects37 5 }

srtEventObjects38 OBJECT-IDENTITY
    STATUS current
    DESCRIPTION
        "Event SRT.38
        An All Routes Explorer frame has been received on the specified port."
    ::= { srtEventsGroup 38 }

srt38_RIF OBJECT-TYPE
    SYNTAX DisplayString
    MAX-ACCESS accessible-for-notify
    STATUS current
    DESCRIPTION
        "Parameter 'RIF' in event SRT.38"
    ::= { srtEventObjects38 1 }

srt38_source_mac OBJECT-TYPE
    SYNTAX DisplayString
    MAX-ACCESS accessible-for-notify
    STATUS current
    DESCRIPTION
        "Parameter 'source_mac' in event SRT.38"
    ::= { srtEventObjects38 2 }

srt38_dest_mac OBJECT-TYPE
    SYNTAX DisplayString
    MAX-ACCESS accessible-for-notify
    STATUS current
    DESCRIPTION
        "Parameter 'dest_mac' in event SRT.38"
    ::= { srtEventObjects38 3 }

srt38_port OBJECT-TYPE
    SYNTAX Integer32
    MAX-ACCESS accessible-for-notify
    STATUS current
    DESCRIPTION
        "Parameter 'port' in event SRT.38"
    ::= { srtEventObjects38 4 }

srt38_interface OBJECT-TYPE
    SYNTAX DisplayString
    MAX-ACCESS accessible-for-notify
    STATUS current
    DESCRIPTION
        "Parameter 'interface' in event SRT.38"
    ::= { srtEventObjects38 5 }

srt38_circuit_name OBJECT-TYPE
    SYNTAX DisplayString
    MAX-ACCESS accessible-for-notify
    STATUS current
    DESCRIPTION
        "Parameter 'circuit_name' in event SRT.38"
    ::= { srtEventObjects38 6 }

srtEventObjects39 OBJECT-IDENTITY
    STATUS current
    DESCRIPTION
        "Event SRT.39
        An All Routes Explorer frame has been sent on the specified port."
    ::= { srtEventsGroup 39 }

srt39_RIF OBJECT-TYPE
    SYNTAX DisplayString
    MAX-ACCESS accessible-for-notify
    STATUS current
    DESCRIPTION
        "Parameter 'RIF' in event SRT.39"
    ::= { srtEventObjects39 1 }

srt39_source_mac OBJECT-TYPE
    SYNTAX DisplayString
    MAX-ACCESS accessible-for-notify
    STATUS current
    DESCRIPTION
        "Parameter 'source_mac' in event SRT.39"
    ::= { srtEventObjects39 2 }

srt39_dest_mac OBJECT-TYPE
    SYNTAX DisplayString
    MAX-ACCESS accessible-for-notify
    STATUS current
    DESCRIPTION
        "Parameter 'dest_mac' in event SRT.39"
    ::= { srtEventObjects39 3 }

srt39_port OBJECT-TYPE
    SYNTAX Integer32
    MAX-ACCESS accessible-for-notify
    STATUS current
    DESCRIPTION
        "Parameter 'port' in event SRT.39"
    ::= { srtEventObjects39 4 }

srt39_interface OBJECT-TYPE
    SYNTAX DisplayString
    MAX-ACCESS accessible-for-notify
    STATUS current
    DESCRIPTION
        "Parameter 'interface' in event SRT.39"
    ::= { srtEventObjects39 5 }

srt39_circuit_name OBJECT-TYPE
    SYNTAX DisplayString
    MAX-ACCESS accessible-for-notify
    STATUS current
    DESCRIPTION
        "Parameter 'circuit_name' in event SRT.39"
    ::= { srtEventObjects39 6 }

srtEventObjects40 OBJECT-IDENTITY
    STATUS current
    DESCRIPTION
        "Event SRT.40
        A Spanning Tree Explorer frame has been received on the specified port."
    ::= { srtEventsGroup 40 }

srt40_RIF OBJECT-TYPE
    SYNTAX DisplayString
    MAX-ACCESS accessible-for-notify
    STATUS current
    DESCRIPTION
        "Parameter 'RIF' in event SRT.40"
    ::= { srtEventObjects40 1 }

srt40_source_mac OBJECT-TYPE
    SYNTAX DisplayString
    MAX-ACCESS accessible-for-notify
    STATUS current
    DESCRIPTION
        "Parameter 'source_mac' in event SRT.40"
    ::= { srtEventObjects40 2 }

srt40_dest_mac OBJECT-TYPE
    SYNTAX DisplayString
    MAX-ACCESS accessible-for-notify
    STATUS current
    DESCRIPTION
        "Parameter 'dest_mac' in event SRT.40"
    ::= { srtEventObjects40 3 }

srt40_port OBJECT-TYPE
    SYNTAX Integer32
    MAX-ACCESS accessible-for-notify
    STATUS current
    DESCRIPTION
        "Parameter 'port' in event SRT.40"
    ::= { srtEventObjects40 4 }

srt40_interface OBJECT-TYPE
    SYNTAX DisplayString
    MAX-ACCESS accessible-for-notify
    STATUS current
    DESCRIPTION
        "Parameter 'interface' in event SRT.40"
    ::= { srtEventObjects40 5 }

srt40_circuit_name OBJECT-TYPE
    SYNTAX DisplayString
    MAX-ACCESS accessible-for-notify
    STATUS current
    DESCRIPTION
        "Parameter 'circuit_name' in event SRT.40"
    ::= { srtEventObjects40 6 }

srtEventObjects41 OBJECT-IDENTITY
    STATUS current
    DESCRIPTION
        "Event SRT.41
        A Spanning Tree Explorer frame has been sent on the specified port."
    ::= { srtEventsGroup 41 }

srt41_RIF OBJECT-TYPE
    SYNTAX DisplayString
    MAX-ACCESS accessible-for-notify
    STATUS current
    DESCRIPTION
        "Parameter 'RIF' in event SRT.41"
    ::= { srtEventObjects41 1 }

srt41_source_mac OBJECT-TYPE
    SYNTAX DisplayString
    MAX-ACCESS accessible-for-notify
    STATUS current
    DESCRIPTION
        "Parameter 'source_mac' in event SRT.41"
    ::= { srtEventObjects41 2 }

srt41_dest_mac OBJECT-TYPE
    SYNTAX DisplayString
    MAX-ACCESS accessible-for-notify
    STATUS current
    DESCRIPTION
        "Parameter 'dest_mac' in event SRT.41"
    ::= { srtEventObjects41 3 }

srt41_port OBJECT-TYPE
    SYNTAX Integer32
    MAX-ACCESS accessible-for-notify
    STATUS current
    DESCRIPTION
        "Parameter 'port' in event SRT.41"
    ::= { srtEventObjects41 4 }

srt41_interface OBJECT-TYPE
    SYNTAX DisplayString
    MAX-ACCESS accessible-for-notify
    STATUS current
    DESCRIPTION
        "Parameter 'interface' in event SRT.41"
    ::= { srtEventObjects41 5 }

srt41_circuit_name OBJECT-TYPE
    SYNTAX DisplayString
    MAX-ACCESS accessible-for-notify
    STATUS current
    DESCRIPTION
        "Parameter 'circuit_name' in event SRT.41"
    ::= { srtEventObjects41 6 }

srtEventObjects42 OBJECT-IDENTITY
    STATUS current
    DESCRIPTION
        "Event SRT.42
        A source-routing explorer (ARE or STE in routing_type) has had
        the Largest Frame (LF) field lowered in its RIF. This happens
        whenever a frame is received from a segment with a smaller maximum
        frame size than the one presently encoded in the LF bits. This is
        a normal part of the spanning tree protocol to determine the maximum
        frame size on all routes."
    ::= { srtEventsGroup 42 }

srt42_routing_type OBJECT-TYPE
    SYNTAX DisplayString
    MAX-ACCESS accessible-for-notify
    STATUS current
    DESCRIPTION
        "Parameter 'routing_type' in event SRT.42"
    ::= { srtEventObjects42 1 }

srt42_old_LF OBJECT-TYPE
    SYNTAX Integer32
    MAX-ACCESS accessible-for-notify
    STATUS current
    DESCRIPTION
        "Parameter 'old_LF' in event SRT.42"
    ::= { srtEventObjects42 2 }

srt42_new_LF OBJECT-TYPE
    SYNTAX Integer32
    MAX-ACCESS accessible-for-notify
    STATUS current
    DESCRIPTION
        "Parameter 'new_LF' in event SRT.42"
    ::= { srtEventObjects42 3 }

srt42_source_mac OBJECT-TYPE
    SYNTAX DisplayString
    MAX-ACCESS accessible-for-notify
    STATUS current
    DESCRIPTION
        "Parameter 'source_mac' in event SRT.42"
    ::= { srtEventObjects42 4 }

srt42_dest_mac OBJECT-TYPE
    SYNTAX DisplayString
    MAX-ACCESS accessible-for-notify
    STATUS current
    DESCRIPTION
        "Parameter 'dest_mac' in event SRT.42"
    ::= { srtEventObjects42 5 }

srt42_port OBJECT-TYPE
    SYNTAX Integer32
    MAX-ACCESS accessible-for-notify
    STATUS current
    DESCRIPTION
        "Parameter 'port' in event SRT.42"
    ::= { srtEventObjects42 6 }

srt42_interface OBJECT-TYPE
    SYNTAX DisplayString
    MAX-ACCESS accessible-for-notify
    STATUS current
    DESCRIPTION
        "Parameter 'interface' in event SRT.42"
    ::= { srtEventObjects42 7 }

srt42_circuit_name OBJECT-TYPE
    SYNTAX DisplayString
    MAX-ACCESS accessible-for-notify
    STATUS current
    DESCRIPTION
        "Parameter 'circuit_name' in event SRT.42"
    ::= { srtEventObjects42 8 }

srtEventObjects43 OBJECT-IDENTITY
    STATUS current
    DESCRIPTION
        "Event SRT.43
        A source-routing explorer (ARE or STE in routing_type) has had
        the Largest Frame (LF) field lowered in its RIF. This happens
        whenever a frame is sent to a segment with a smaller maximum frame size
        than the one presently encoded in the LF bits. This is a normal part of
        the spanning tree protocol to determine the maximum frame size
        on all routes."
    ::= { srtEventsGroup 43 }

srt43_routing_type OBJECT-TYPE
    SYNTAX DisplayString
    MAX-ACCESS accessible-for-notify
    STATUS current
    DESCRIPTION
        "Parameter 'routing_type' in event SRT.43"
    ::= { srtEventObjects43 1 }

srt43_old_LF OBJECT-TYPE
    SYNTAX Integer32
    MAX-ACCESS accessible-for-notify
    STATUS current
    DESCRIPTION
        "Parameter 'old_LF' in event SRT.43"
    ::= { srtEventObjects43 2 }

srt43_new_LF OBJECT-TYPE
    SYNTAX Integer32
    MAX-ACCESS accessible-for-notify
    STATUS current
    DESCRIPTION
        "Parameter 'new_LF' in event SRT.43"
    ::= { srtEventObjects43 3 }

srt43_source_mac OBJECT-TYPE
    SYNTAX DisplayString
    MAX-ACCESS accessible-for-notify
    STATUS current
    DESCRIPTION
        "Parameter 'source_mac' in event SRT.43"
    ::= { srtEventObjects43 4 }

srt43_dest_mac OBJECT-TYPE
    SYNTAX DisplayString
    MAX-ACCESS accessible-for-notify
    STATUS current
    DESCRIPTION
        "Parameter 'dest_mac' in event SRT.43"
    ::= { srtEventObjects43 5 }

srt43_port OBJECT-TYPE
    SYNTAX Integer32
    MAX-ACCESS accessible-for-notify
    STATUS current
    DESCRIPTION
        "Parameter 'port' in event SRT.43"
    ::= { srtEventObjects43 6 }

srt43_interface OBJECT-TYPE
    SYNTAX DisplayString
    MAX-ACCESS accessible-for-notify
    STATUS current
    DESCRIPTION
        "Parameter 'interface' in event SRT.43"
    ::= { srtEventObjects43 7 }

srt43_circuit_name OBJECT-TYPE
    SYNTAX DisplayString
    MAX-ACCESS accessible-for-notify
    STATUS current
    DESCRIPTION
        "Parameter 'circuit_name' in event SRT.43"
    ::= { srtEventObjects43 8 }

srtEventObjects44 OBJECT-IDENTITY
    STATUS current
    DESCRIPTION
        "Event SRT.44
        A Specifically-routed frame has been received on the specified port."
    ::= { srtEventsGroup 44 }

srt44_RIF OBJECT-TYPE
    SYNTAX DisplayString
    MAX-ACCESS accessible-for-notify
    STATUS current
    DESCRIPTION
        "Parameter 'RIF' in event SRT.44"
    ::= { srtEventObjects44 1 }

srt44_source_mac OBJECT-TYPE
    SYNTAX DisplayString
    MAX-ACCESS accessible-for-notify
    STATUS current
    DESCRIPTION
        "Parameter 'source_mac' in event SRT.44"
    ::= { srtEventObjects44 2 }

srt44_dest_mac OBJECT-TYPE
    SYNTAX DisplayString
    MAX-ACCESS accessible-for-notify
    STATUS current
    DESCRIPTION
        "Parameter 'dest_mac' in event SRT.44"
    ::= { srtEventObjects44 3 }

srt44_port OBJECT-TYPE
    SYNTAX Integer32
    MAX-ACCESS accessible-for-notify
    STATUS current
    DESCRIPTION
        "Parameter 'port' in event SRT.44"
    ::= { srtEventObjects44 4 }

srt44_interface OBJECT-TYPE
    SYNTAX DisplayString
    MAX-ACCESS accessible-for-notify
    STATUS current
    DESCRIPTION
        "Parameter 'interface' in event SRT.44"
    ::= { srtEventObjects44 5 }

srt44_circuit_name OBJECT-TYPE
    SYNTAX DisplayString
    MAX-ACCESS accessible-for-notify
    STATUS current
    DESCRIPTION
        "Parameter 'circuit_name' in event SRT.44"
    ::= { srtEventObjects44 6 }

srtEventObjects45 OBJECT-IDENTITY
    STATUS current
    DESCRIPTION
        "Event SRT.45
        A Specifically-routed frame is being sent on the specified port."
    ::= { srtEventsGroup 45 }

srt45_RIF OBJECT-TYPE
    SYNTAX DisplayString
    MAX-ACCESS accessible-for-notify
    STATUS current
    DESCRIPTION
        "Parameter 'RIF' in event SRT.45"
    ::= { srtEventObjects45 1 }

srt45_source_mac OBJECT-TYPE
    SYNTAX DisplayString
    MAX-ACCESS accessible-for-notify
    STATUS current
    DESCRIPTION
        "Parameter 'source_mac' in event SRT.45"
    ::= { srtEventObjects45 2 }

srt45_dest_mac OBJECT-TYPE
    SYNTAX DisplayString
    MAX-ACCESS accessible-for-notify
    STATUS current
    DESCRIPTION
        "Parameter 'dest_mac' in event SRT.45"
    ::= { srtEventObjects45 3 }

srt45_port OBJECT-TYPE
    SYNTAX Integer32
    MAX-ACCESS accessible-for-notify
    STATUS current
    DESCRIPTION
        "Parameter 'port' in event SRT.45"
    ::= { srtEventObjects45 4 }

srt45_interface OBJECT-TYPE
    SYNTAX DisplayString
    MAX-ACCESS accessible-for-notify
    STATUS current
    DESCRIPTION
        "Parameter 'interface' in event SRT.45"
    ::= { srtEventObjects45 5 }

srt45_circuit_name OBJECT-TYPE
    SYNTAX DisplayString
    MAX-ACCESS accessible-for-notify
    STATUS current
    DESCRIPTION
        "Parameter 'circuit_name' in event SRT.45"
    ::= { srtEventObjects45 6 }

srtEventObjects46 OBJECT-IDENTITY
    STATUS current
    DESCRIPTION
        "Event SRT.46
        A source-routed frame has been received on the specified port, but
        that port is not configured for bridging.
        The routing_type is one of SRF (Specifically-routed frame),
        STE (Spanning Tree Expolorer) or ARE (All Routes Explorer).
        This really should not happen on more than a transient basis, because
        ports that are not enabled for bridging should not be queueing packets
        to the source-routing forwarder."
    ::= { srtEventsGroup 46 }

srt46_routing_type OBJECT-TYPE
    SYNTAX DisplayString
    MAX-ACCESS accessible-for-notify
    STATUS current
    DESCRIPTION
        "Parameter 'routing_type' in event SRT.46"
    ::= { srtEventObjects46 1 }

srt46_source_mac OBJECT-TYPE
    SYNTAX DisplayString
    MAX-ACCESS accessible-for-notify
    STATUS current
    DESCRIPTION
        "Parameter 'source_mac' in event SRT.46"
    ::= { srtEventObjects46 2 }

srt46_dest_mac OBJECT-TYPE
    SYNTAX DisplayString
    MAX-ACCESS accessible-for-notify
    STATUS current
    DESCRIPTION
        "Parameter 'dest_mac' in event SRT.46"
    ::= { srtEventObjects46 3 }

srt46_port OBJECT-TYPE
    SYNTAX Integer32
    MAX-ACCESS accessible-for-notify
    STATUS current
    DESCRIPTION
        "Parameter 'port' in event SRT.46"
    ::= { srtEventObjects46 4 }

srt46_interface OBJECT-TYPE
    SYNTAX DisplayString
    MAX-ACCESS accessible-for-notify
    STATUS current
    DESCRIPTION
        "Parameter 'interface' in event SRT.46"
    ::= { srtEventObjects46 5 }

srt46_circuit_name OBJECT-TYPE
    SYNTAX DisplayString
    MAX-ACCESS accessible-for-notify
    STATUS current
    DESCRIPTION
        "Parameter 'circuit_name' in event SRT.46"
    ::= { srtEventObjects46 6 }

srtEventObjects47 OBJECT-IDENTITY
    STATUS current
    DESCRIPTION
        "Event SRT.47
        A source-routed frame has been received on the specified port, but
        that port is not configured for source-routing bridging.
        The routing_type is one of SRF (Specifically-routed frame),
        STE (Spanning Tree Expolorer) or ARE (All Routes Explorer).
        This really should not happen on more than a transient basis, because
        ports that are not enabled for bridging should not be queueing packets
        to the source-routing forwarder."
    ::= { srtEventsGroup 47 }

srt47_routing_type OBJECT-TYPE
    SYNTAX DisplayString
    MAX-ACCESS accessible-for-notify
    STATUS current
    DESCRIPTION
        "Parameter 'routing_type' in event SRT.47"
    ::= { srtEventObjects47 1 }

srt47_source_mac OBJECT-TYPE
    SYNTAX DisplayString
    MAX-ACCESS accessible-for-notify
    STATUS current
    DESCRIPTION
        "Parameter 'source_mac' in event SRT.47"
    ::= { srtEventObjects47 2 }

srt47_dest_mac OBJECT-TYPE
    SYNTAX DisplayString
    MAX-ACCESS accessible-for-notify
    STATUS current
    DESCRIPTION
        "Parameter 'dest_mac' in event SRT.47"
    ::= { srtEventObjects47 3 }

srt47_port OBJECT-TYPE
    SYNTAX Integer32
    MAX-ACCESS accessible-for-notify
    STATUS current
    DESCRIPTION
        "Parameter 'port' in event SRT.47"
    ::= { srtEventObjects47 4 }

srt47_interface OBJECT-TYPE
    SYNTAX DisplayString
    MAX-ACCESS accessible-for-notify
    STATUS current
    DESCRIPTION
        "Parameter 'interface' in event SRT.47"
    ::= { srtEventObjects47 5 }

srt47_circuit_name OBJECT-TYPE
    SYNTAX DisplayString
    MAX-ACCESS accessible-for-notify
    STATUS current
    DESCRIPTION
        "Parameter 'circuit_name' in event SRT.47"
    ::= { srtEventObjects47 6 }

srtEventObjects48 OBJECT-IDENTITY
    STATUS current
    DESCRIPTION
        "Event SRT.48
        A Spanning Tree Explorer (STE) frame was dropped, and not forwarded,
        because the incoming port is not part of the spanning tree, or has been
        configured not to forward STE frames."
    ::= { srtEventsGroup 48 }

srt48_RIF OBJECT-TYPE
    SYNTAX DisplayString
    MAX-ACCESS accessible-for-notify
    STATUS current
    DESCRIPTION
        "Parameter 'RIF' in event SRT.48"
    ::= { srtEventObjects48 1 }

srt48_source_mac OBJECT-TYPE
    SYNTAX DisplayString
    MAX-ACCESS accessible-for-notify
    STATUS current
    DESCRIPTION
        "Parameter 'source_mac' in event SRT.48"
    ::= { srtEventObjects48 2 }

srt48_dest_mac OBJECT-TYPE
    SYNTAX DisplayString
    MAX-ACCESS accessible-for-notify
    STATUS current
    DESCRIPTION
        "Parameter 'dest_mac' in event SRT.48"
    ::= { srtEventObjects48 3 }

srt48_port OBJECT-TYPE
    SYNTAX Integer32
    MAX-ACCESS accessible-for-notify
    STATUS current
    DESCRIPTION
        "Parameter 'port' in event SRT.48"
    ::= { srtEventObjects48 4 }

srt48_interface OBJECT-TYPE
    SYNTAX DisplayString
    MAX-ACCESS accessible-for-notify
    STATUS current
    DESCRIPTION
        "Parameter 'interface' in event SRT.48"
    ::= { srtEventObjects48 5 }

srt48_circuit_name OBJECT-TYPE
    SYNTAX DisplayString
    MAX-ACCESS accessible-for-notify
    STATUS current
    DESCRIPTION
        "Parameter 'circuit_name' in event SRT.48"
    ::= { srtEventObjects48 6 }

srtEventObjects49 OBJECT-IDENTITY
    STATUS current
    DESCRIPTION
        "Event SRT.49
        A Spanning Tree Explorer (STE) frame was not sent on the specified port
        because it is not part of the spanning tree, or has been configured
        not to forward STE frames."
    ::= { srtEventsGroup 49 }

srt49_RIF OBJECT-TYPE
    SYNTAX DisplayString
    MAX-ACCESS accessible-for-notify
    STATUS current
    DESCRIPTION
        "Parameter 'RIF' in event SRT.49"
    ::= { srtEventObjects49 1 }

srt49_source_mac OBJECT-TYPE
    SYNTAX DisplayString
    MAX-ACCESS accessible-for-notify
    STATUS current
    DESCRIPTION
        "Parameter 'source_mac' in event SRT.49"
    ::= { srtEventObjects49 2 }

srt49_dest_mac OBJECT-TYPE
    SYNTAX DisplayString
    MAX-ACCESS accessible-for-notify
    STATUS current
    DESCRIPTION
        "Parameter 'dest_mac' in event SRT.49"
    ::= { srtEventObjects49 3 }

srt49_port OBJECT-TYPE
    SYNTAX Integer32
    MAX-ACCESS accessible-for-notify
    STATUS current
    DESCRIPTION
        "Parameter 'port' in event SRT.49"
    ::= { srtEventObjects49 4 }

srt49_interface OBJECT-TYPE
    SYNTAX DisplayString
    MAX-ACCESS accessible-for-notify
    STATUS current
    DESCRIPTION
        "Parameter 'interface' in event SRT.49"
    ::= { srtEventObjects49 5 }

srt49_circuit_name OBJECT-TYPE
    SYNTAX DisplayString
    MAX-ACCESS accessible-for-notify
    STATUS current
    DESCRIPTION
        "Parameter 'circuit_name' in event SRT.49"
    ::= { srtEventObjects49 6 }

srtEventObjects50 OBJECT-IDENTITY
    STATUS current
    DESCRIPTION
        "Event SRT.50
        The bridge tried to enable source-routing bridging on this interface,
        but the interface refused the configuration command.
        Source-routing will be left disabled on this interface."
    ::= { srtEventsGroup 50 }

srt50_error_string OBJECT-TYPE
    SYNTAX DisplayString
    MAX-ACCESS accessible-for-notify
    STATUS current
    DESCRIPTION
        "Parameter 'error_string' in event SRT.50"
    ::= { srtEventObjects50 1 }

srt50_interface OBJECT-TYPE
    SYNTAX DisplayString
    MAX-ACCESS accessible-for-notify
    STATUS current
    DESCRIPTION
        "Parameter 'interface' in event SRT.50"
    ::= { srtEventObjects50 2 }

srtEventObjects51 OBJECT-IDENTITY
    STATUS current
    DESCRIPTION
        "Event SRT.51
        The specified Specifically-routed (source-routed) frame is too large
        to send on this outgoing port and interface. The reformatted_length is
        the size of the frame including MAC headers after any mapping of
        data link headers."
    ::= { srtEventsGroup 51 }

srt51_source_mac OBJECT-TYPE
    SYNTAX DisplayString
    MAX-ACCESS accessible-for-notify
    STATUS current
    DESCRIPTION
        "Parameter 'source_mac' in event SRT.51"
    ::= { srtEventObjects51 1 }

srt51_dest_mac OBJECT-TYPE
    SYNTAX DisplayString
    MAX-ACCESS accessible-for-notify
    STATUS current
    DESCRIPTION
        "Parameter 'dest_mac' in event SRT.51"
    ::= { srtEventObjects51 2 }

srt51_reformatted_length OBJECT-TYPE
    SYNTAX Integer32
    MAX-ACCESS accessible-for-notify
    STATUS current
    DESCRIPTION
        "Parameter 'reformatted_length' in event SRT.51"
    ::= { srtEventObjects51 3 }

srt51_output_maximum OBJECT-TYPE
    SYNTAX Integer32
    MAX-ACCESS accessible-for-notify
    STATUS current
    DESCRIPTION
        "Parameter 'output_maximum' in event SRT.51"
    ::= { srtEventObjects51 4 }

srt51_port OBJECT-TYPE
    SYNTAX Integer32
    MAX-ACCESS accessible-for-notify
    STATUS current
    DESCRIPTION
        "Parameter 'port' in event SRT.51"
    ::= { srtEventObjects51 5 }

srt51_interface OBJECT-TYPE
    SYNTAX DisplayString
    MAX-ACCESS accessible-for-notify
    STATUS current
    DESCRIPTION
        "Parameter 'interface' in event SRT.51"
    ::= { srtEventObjects51 6 }

srt51_circuit_name OBJECT-TYPE
    SYNTAX DisplayString
    MAX-ACCESS accessible-for-notify
    STATUS current
    DESCRIPTION
        "Parameter 'circuit_name' in event SRT.51"
    ::= { srtEventObjects51 7 }

srtEventObjects52 OBJECT-IDENTITY
    STATUS current
    DESCRIPTION
        "Event SRT.52
        The source-routed explorer (ARE or STE routing_type) frame is too large
        to send on this outgoing port and interface. The reformatted_length is
        the size of the frame including MAC headers after any mapping of
        data link headers."
    ::= { srtEventsGroup 52 }

srt52_routing_type OBJECT-TYPE
    SYNTAX DisplayString
    MAX-ACCESS accessible-for-notify
    STATUS current
    DESCRIPTION
        "Parameter 'routing_type' in event SRT.52"
    ::= { srtEventObjects52 1 }

srt52_source_mac OBJECT-TYPE
    SYNTAX DisplayString
    MAX-ACCESS accessible-for-notify
    STATUS current
    DESCRIPTION
        "Parameter 'source_mac' in event SRT.52"
    ::= { srtEventObjects52 2 }

srt52_dest_mac OBJECT-TYPE
    SYNTAX DisplayString
    MAX-ACCESS accessible-for-notify
    STATUS current
    DESCRIPTION
        "Parameter 'dest_mac' in event SRT.52"
    ::= { srtEventObjects52 3 }

srt52_reformatted_length OBJECT-TYPE
    SYNTAX Integer32
    MAX-ACCESS accessible-for-notify
    STATUS current
    DESCRIPTION
        "Parameter 'reformatted_length' in event SRT.52"
    ::= { srtEventObjects52 4 }

srt52_output_maximum OBJECT-TYPE
    SYNTAX Integer32
    MAX-ACCESS accessible-for-notify
    STATUS current
    DESCRIPTION
        "Parameter 'output_maximum' in event SRT.52"
    ::= { srtEventObjects52 5 }

srt52_port OBJECT-TYPE
    SYNTAX Integer32
    MAX-ACCESS accessible-for-notify
    STATUS current
    DESCRIPTION
        "Parameter 'port' in event SRT.52"
    ::= { srtEventObjects52 6 }

srt52_interface OBJECT-TYPE
    SYNTAX DisplayString
    MAX-ACCESS accessible-for-notify
    STATUS current
    DESCRIPTION
        "Parameter 'interface' in event SRT.52"
    ::= { srtEventObjects52 7 }

srt52_circuit_name OBJECT-TYPE
    SYNTAX DisplayString
    MAX-ACCESS accessible-for-notify
    STATUS current
    DESCRIPTION
        "Parameter 'circuit_name' in event SRT.52"
    ::= { srtEventObjects52 8 }

srtEventObjects53 OBJECT-IDENTITY
    STATUS current
    DESCRIPTION
        "Event SRT.53
        A source-routing frame was received with an invalid RIF length encoded
        in the Length bits of the RIF.
        The routing_type is one of SRF (Specifically-routed frame),
        STE (Spanning Tree Expolorer) or ARE (All Routes Explorer)."
    ::= { srtEventsGroup 53 }

srt53_routing_type OBJECT-TYPE
    SYNTAX DisplayString
    MAX-ACCESS accessible-for-notify
    STATUS current
    DESCRIPTION
        "Parameter 'routing_type' in event SRT.53"
    ::= { srtEventObjects53 1 }

srt53_RIF_length OBJECT-TYPE
    SYNTAX Integer32
    MAX-ACCESS accessible-for-notify
    STATUS current
    DESCRIPTION
        "Parameter 'RIF_length' in event SRT.53"
    ::= { srtEventObjects53 2 }

srt53_source_mac OBJECT-TYPE
    SYNTAX DisplayString
    MAX-ACCESS accessible-for-notify
    STATUS current
    DESCRIPTION
        "Parameter 'source_mac' in event SRT.53"
    ::= { srtEventObjects53 3 }

srt53_dest_mac OBJECT-TYPE
    SYNTAX DisplayString
    MAX-ACCESS accessible-for-notify
    STATUS current
    DESCRIPTION
        "Parameter 'dest_mac' in event SRT.53"
    ::= { srtEventObjects53 4 }

srt53_port OBJECT-TYPE
    SYNTAX Integer32
    MAX-ACCESS accessible-for-notify
    STATUS current
    DESCRIPTION
        "Parameter 'port' in event SRT.53"
    ::= { srtEventObjects53 5 }

srt53_interface OBJECT-TYPE
    SYNTAX DisplayString
    MAX-ACCESS accessible-for-notify
    STATUS current
    DESCRIPTION
        "Parameter 'interface' in event SRT.53"
    ::= { srtEventObjects53 6 }

srt53_circuit_name OBJECT-TYPE
    SYNTAX DisplayString
    MAX-ACCESS accessible-for-notify
    STATUS current
    DESCRIPTION
        "Parameter 'circuit_name' in event SRT.53"
    ::= { srtEventObjects53 7 }

srtEventObjects54 OBJECT-IDENTITY
    STATUS current
    DESCRIPTION
        "Event SRT.54
        There is not enough free memory to allocate the hash table for
        the filtering database. The bridge will be disabled."
    ::= { srtEventsGroup 54 }

srt54_requested_size OBJECT-TYPE
    SYNTAX Integer32
    MAX-ACCESS accessible-for-notify
    STATUS current
    DESCRIPTION
        "Parameter 'requested_size' in event SRT.54"
    ::= { srtEventObjects54 1 }

srtEventObjects55 OBJECT-IDENTITY
    STATUS current
    DESCRIPTION
        "Event SRT.55
        There is not enough free memory to allocate the hash table for
        the conversion database. The bridge will be disabled."
    ::= { srtEventsGroup 55 }

srt55_requested_size OBJECT-TYPE
    SYNTAX Integer32
    MAX-ACCESS accessible-for-notify
    STATUS current
    DESCRIPTION
        "Parameter 'requested_size' in event SRT.55"
    ::= { srtEventObjects55 1 }

srtEventObjects56 OBJECT-IDENTITY
    STATUS current
    DESCRIPTION
        "Event SRT.56
        The input queue for source-routed frames to be forwarded is too long,
        and this frame has been dropped to attempt to alleviate the congestion."
    ::= { srtEventsGroup 56 }

srt56_source_mac OBJECT-TYPE
    SYNTAX DisplayString
    MAX-ACCESS accessible-for-notify
    STATUS current
    DESCRIPTION
        "Parameter 'source_mac' in event SRT.56"
    ::= { srtEventObjects56 1 }

srt56_dest_mac OBJECT-TYPE
    SYNTAX DisplayString
    MAX-ACCESS accessible-for-notify
    STATUS current
    DESCRIPTION
        "Parameter 'dest_mac' in event SRT.56"
    ::= { srtEventObjects56 2 }

srt56_interface OBJECT-TYPE
    SYNTAX DisplayString
    MAX-ACCESS accessible-for-notify
    STATUS current
    DESCRIPTION
        "Parameter 'interface' in event SRT.56"
    ::= { srtEventObjects56 3 }

srt56_circuit_name OBJECT-TYPE
    SYNTAX DisplayString
    MAX-ACCESS accessible-for-notify
    STATUS current
    DESCRIPTION
        "Parameter 'circuit_name' in event SRT.56"
    ::= { srtEventObjects56 4 }

srtEventObjects57 OBJECT-IDENTITY
    STATUS current
    DESCRIPTION
        "Event SRT.57
        A frame is being bridged between these two interfaces.
        The destination address was known, so it was sent only to
        the correct destination network."
    ::= { srtEventsGroup 57 }

srt57_source_mac OBJECT-TYPE
    SYNTAX DisplayString
    MAX-ACCESS accessible-for-notify
    STATUS current
    DESCRIPTION
        "Parameter 'source_mac' in event SRT.57"
    ::= { srtEventObjects57 1 }

srt57_dest_mac OBJECT-TYPE
    SYNTAX DisplayString
    MAX-ACCESS accessible-for-notify
    STATUS current
    DESCRIPTION
        "Parameter 'dest_mac' in event SRT.57"
    ::= { srtEventObjects57 2 }

srt57_port OBJECT-TYPE
    SYNTAX Integer32
    MAX-ACCESS accessible-for-notify
    STATUS current
    DESCRIPTION
        "Parameter 'port' in event SRT.57"
    ::= { srtEventObjects57 3 }

srt57_interface OBJECT-TYPE
    SYNTAX DisplayString
    MAX-ACCESS accessible-for-notify
    STATUS current
    DESCRIPTION
        "Parameter 'interface' in event SRT.57"
    ::= { srtEventObjects57 4 }

srt57_circuit_name OBJECT-TYPE
    SYNTAX DisplayString
    MAX-ACCESS accessible-for-notify
    STATUS current
    DESCRIPTION
        "Parameter 'circuit_name' in event SRT.57"
    ::= { srtEventObjects57 5 }

srt57_out_port OBJECT-TYPE
    SYNTAX Integer32
    MAX-ACCESS accessible-for-notify
    STATUS current
    DESCRIPTION
        "Parameter 'out_port' in event SRT.57"
    ::= { srtEventObjects57 6 }

srt57_out_interface OBJECT-TYPE
    SYNTAX DisplayString
    MAX-ACCESS accessible-for-notify
    STATUS current
    DESCRIPTION
        "Parameter 'out_interface' in event SRT.57"
    ::= { srtEventObjects57 7 }

srt57_out_circuit_name OBJECT-TYPE
    SYNTAX DisplayString
    MAX-ACCESS accessible-for-notify
    STATUS current
    DESCRIPTION
        "Parameter 'out_circuit_name' in event SRT.57"
    ::= { srtEventObjects57 8 }

srtEventObjects58 OBJECT-IDENTITY
    STATUS current
    DESCRIPTION
        "Event SRT.58
        The specified transparent bridge frame is too large to send as
        a source-routed frame on this outgoing port and interface.
        The reformatted_length is the size of the frame including MAC headers
        and RIF after any mapping of data link headers."
    ::= { srtEventsGroup 58 }

srt58_source_mac OBJECT-TYPE
    SYNTAX DisplayString
    MAX-ACCESS accessible-for-notify
    STATUS current
    DESCRIPTION
        "Parameter 'source_mac' in event SRT.58"
    ::= { srtEventObjects58 1 }

srt58_dest_mac OBJECT-TYPE
    SYNTAX DisplayString
    MAX-ACCESS accessible-for-notify
    STATUS current
    DESCRIPTION
        "Parameter 'dest_mac' in event SRT.58"
    ::= { srtEventObjects58 2 }

srt58_reformatted_length OBJECT-TYPE
    SYNTAX Integer32
    MAX-ACCESS accessible-for-notify
    STATUS current
    DESCRIPTION
        "Parameter 'reformatted_length' in event SRT.58"
    ::= { srtEventObjects58 3 }

srt58_output_maximum OBJECT-TYPE
    SYNTAX Integer32
    MAX-ACCESS accessible-for-notify
    STATUS current
    DESCRIPTION
        "Parameter 'output_maximum' in event SRT.58"
    ::= { srtEventObjects58 4 }

srt58_port OBJECT-TYPE
    SYNTAX Integer32
    MAX-ACCESS accessible-for-notify
    STATUS current
    DESCRIPTION
        "Parameter 'port' in event SRT.58"
    ::= { srtEventObjects58 5 }

srt58_interface OBJECT-TYPE
    SYNTAX DisplayString
    MAX-ACCESS accessible-for-notify
    STATUS current
    DESCRIPTION
        "Parameter 'interface' in event SRT.58"
    ::= { srtEventObjects58 6 }

srt58_circuit_name OBJECT-TYPE
    SYNTAX DisplayString
    MAX-ACCESS accessible-for-notify
    STATUS current
    DESCRIPTION
        "Parameter 'circuit_name' in event SRT.58"
    ::= { srtEventObjects58 7 }

srtEventObjects59 OBJECT-IDENTITY
    STATUS current
    DESCRIPTION
        "Event SRT.59
        A frame is being conversion bridged between these two interfaces.
        The destination address and RIF were known, so it was sent only to
        the correct destination network."
    ::= { srtEventsGroup 59 }

srt59_source_mac OBJECT-TYPE
    SYNTAX DisplayString
    MAX-ACCESS accessible-for-notify
    STATUS current
    DESCRIPTION
        "Parameter 'source_mac' in event SRT.59"
    ::= { srtEventObjects59 1 }

srt59_dest_mac OBJECT-TYPE
    SYNTAX DisplayString
    MAX-ACCESS accessible-for-notify
    STATUS current
    DESCRIPTION
        "Parameter 'dest_mac' in event SRT.59"
    ::= { srtEventObjects59 2 }

srt59_RIF OBJECT-TYPE
    SYNTAX DisplayString
    MAX-ACCESS accessible-for-notify
    STATUS current
    DESCRIPTION
        "Parameter 'RIF' in event SRT.59"
    ::= { srtEventObjects59 3 }

srt59_port OBJECT-TYPE
    SYNTAX Integer32
    MAX-ACCESS accessible-for-notify
    STATUS current
    DESCRIPTION
        "Parameter 'port' in event SRT.59"
    ::= { srtEventObjects59 4 }

srt59_interface OBJECT-TYPE
    SYNTAX DisplayString
    MAX-ACCESS accessible-for-notify
    STATUS current
    DESCRIPTION
        "Parameter 'interface' in event SRT.59"
    ::= { srtEventObjects59 5 }

srt59_circuit_name OBJECT-TYPE
    SYNTAX DisplayString
    MAX-ACCESS accessible-for-notify
    STATUS current
    DESCRIPTION
        "Parameter 'circuit_name' in event SRT.59"
    ::= { srtEventObjects59 6 }

srt59_out_port OBJECT-TYPE
    SYNTAX Integer32
    MAX-ACCESS accessible-for-notify
    STATUS current
    DESCRIPTION
        "Parameter 'out_port' in event SRT.59"
    ::= { srtEventObjects59 7 }

srt59_out_interface OBJECT-TYPE
    SYNTAX DisplayString
    MAX-ACCESS accessible-for-notify
    STATUS current
    DESCRIPTION
        "Parameter 'out_interface' in event SRT.59"
    ::= { srtEventObjects59 8 }

srt59_out_circuit_name OBJECT-TYPE
    SYNTAX DisplayString
    MAX-ACCESS accessible-for-notify
    STATUS current
    DESCRIPTION
        "Parameter 'out_circuit_name' in event SRT.59"
    ::= { srtEventObjects59 9 }

srtEventObjects60 OBJECT-IDENTITY
    STATUS current
    DESCRIPTION
        "Event SRT.60
        A frame is being conversion bridged to all active source-routing ports.
        This happens when the frame destination is a multicast or when
        the frame destination is not in the source-routing learning database.
        There will be one message for each port the frame is sent on."
    ::= { srtEventsGroup 60 }

srt60_source_mac OBJECT-TYPE
    SYNTAX DisplayString
    MAX-ACCESS accessible-for-notify
    STATUS current
    DESCRIPTION
        "Parameter 'source_mac' in event SRT.60"
    ::= { srtEventObjects60 1 }

srt60_dest_mac OBJECT-TYPE
    SYNTAX DisplayString
    MAX-ACCESS accessible-for-notify
    STATUS current
    DESCRIPTION
        "Parameter 'dest_mac' in event SRT.60"
    ::= { srtEventObjects60 2 }

srt60_RIF OBJECT-TYPE
    SYNTAX Integer32
    MAX-ACCESS accessible-for-notify
    STATUS current
    DESCRIPTION
        "Parameter 'RIF' in event SRT.60"
    ::= { srtEventObjects60 3 }

srt60_port OBJECT-TYPE
    SYNTAX Integer32
    MAX-ACCESS accessible-for-notify
    STATUS current
    DESCRIPTION
        "Parameter 'port' in event SRT.60"
    ::= { srtEventObjects60 4 }

srt60_interface OBJECT-TYPE
    SYNTAX DisplayString
    MAX-ACCESS accessible-for-notify
    STATUS current
    DESCRIPTION
        "Parameter 'interface' in event SRT.60"
    ::= { srtEventObjects60 5 }

srt60_circuit_name OBJECT-TYPE
    SYNTAX DisplayString
    MAX-ACCESS accessible-for-notify
    STATUS current
    DESCRIPTION
        "Parameter 'circuit_name' in event SRT.60"
    ::= { srtEventObjects60 6 }

srt60_out_port OBJECT-TYPE
    SYNTAX Integer32
    MAX-ACCESS accessible-for-notify
    STATUS current
    DESCRIPTION
        "Parameter 'out_port' in event SRT.60"
    ::= { srtEventObjects60 7 }

srt60_out_interface OBJECT-TYPE
    SYNTAX DisplayString
    MAX-ACCESS accessible-for-notify
    STATUS current
    DESCRIPTION
        "Parameter 'out_interface' in event SRT.60"
    ::= { srtEventObjects60 8 }

srt60_out_circuit_name OBJECT-TYPE
    SYNTAX DisplayString
    MAX-ACCESS accessible-for-notify
    STATUS current
    DESCRIPTION
        "Parameter 'out_circuit_name' in event SRT.60"
    ::= { srtEventObjects60 9 }

srtEventObjects61 OBJECT-IDENTITY
    STATUS current
    DESCRIPTION
        "Event SRT.61
        A Specifically Routed frame has been received whose RIF would send it
        on the specified port, but that port is not configured for bridging."
    ::= { srtEventsGroup 61 }

srt61_source_mac OBJECT-TYPE
    SYNTAX DisplayString
    MAX-ACCESS accessible-for-notify
    STATUS current
    DESCRIPTION
        "Parameter 'source_mac' in event SRT.61"
    ::= { srtEventObjects61 1 }

srt61_dest_mac OBJECT-TYPE
    SYNTAX DisplayString
    MAX-ACCESS accessible-for-notify
    STATUS current
    DESCRIPTION
        "Parameter 'dest_mac' in event SRT.61"
    ::= { srtEventObjects61 2 }

srt61_RIF OBJECT-TYPE
    SYNTAX DisplayString
    MAX-ACCESS accessible-for-notify
    STATUS current
    DESCRIPTION
        "Parameter 'RIF' in event SRT.61"
    ::= { srtEventObjects61 3 }

srt61_port OBJECT-TYPE
    SYNTAX Integer32
    MAX-ACCESS accessible-for-notify
    STATUS current
    DESCRIPTION
        "Parameter 'port' in event SRT.61"
    ::= { srtEventObjects61 4 }

srt61_interface OBJECT-TYPE
    SYNTAX DisplayString
    MAX-ACCESS accessible-for-notify
    STATUS current
    DESCRIPTION
        "Parameter 'interface' in event SRT.61"
    ::= { srtEventObjects61 5 }

srt61_circuit_name OBJECT-TYPE
    SYNTAX DisplayString
    MAX-ACCESS accessible-for-notify
    STATUS current
    DESCRIPTION
        "Parameter 'circuit_name' in event SRT.61"
    ::= { srtEventObjects61 6 }

srtEventObjects62 OBJECT-IDENTITY
    STATUS current
    DESCRIPTION
        "Event SRT.62
        The specified source-routed frame is larger than that is allowed
        by LF-BIT configuration for the transparent bridge domain. After mapping
        to the MAC headers of the outgoing port, the packet may get dropped
        if it exceeds the MSDU limit of the port."
    ::= { srtEventsGroup 62 }

srt62_source_mac OBJECT-TYPE
    SYNTAX DisplayString
    MAX-ACCESS accessible-for-notify
    STATUS current
    DESCRIPTION
        "Parameter 'source_mac' in event SRT.62"
    ::= { srtEventObjects62 1 }

srt62_dest_mac OBJECT-TYPE
    SYNTAX DisplayString
    MAX-ACCESS accessible-for-notify
    STATUS current
    DESCRIPTION
        "Parameter 'dest_mac' in event SRT.62"
    ::= { srtEventObjects62 2 }

srt62_reformatted_length OBJECT-TYPE
    SYNTAX Integer32
    MAX-ACCESS accessible-for-notify
    STATUS current
    DESCRIPTION
        "Parameter 'reformatted_length' in event SRT.62"
    ::= { srtEventObjects62 3 }

srt62_output_maximum OBJECT-TYPE
    SYNTAX Integer32
    MAX-ACCESS accessible-for-notify
    STATUS current
    DESCRIPTION
        "Parameter 'output_maximum' in event SRT.62"
    ::= { srtEventObjects62 4 }

srt62_port OBJECT-TYPE
    SYNTAX Integer32
    MAX-ACCESS accessible-for-notify
    STATUS current
    DESCRIPTION
        "Parameter 'port' in event SRT.62"
    ::= { srtEventObjects62 5 }

srt62_interface OBJECT-TYPE
    SYNTAX DisplayString
    MAX-ACCESS accessible-for-notify
    STATUS current
    DESCRIPTION
        "Parameter 'interface' in event SRT.62"
    ::= { srtEventObjects62 6 }

srt62_circuit_name OBJECT-TYPE
    SYNTAX DisplayString
    MAX-ACCESS accessible-for-notify
    STATUS current
    DESCRIPTION
        "Parameter 'circuit_name' in event SRT.62"
    ::= { srtEventObjects62 7 }

srtEventObjects63 OBJECT-IDENTITY
    STATUS current
    DESCRIPTION
        "Event SRT.63
        No buffer available to copy a frame in order to send Routes Explorer
        (ARE) or Spanning Tree Explorer (STE) routing_type frame out as
        a transparent bridged frame in the transparent bridging domain.
        No copy of this frame will be sent into the transparent bridge domain."
    ::= { srtEventsGroup 63 }

srt63_routing_type OBJECT-TYPE
    SYNTAX DisplayString
    MAX-ACCESS accessible-for-notify
    STATUS current
    DESCRIPTION
        "Parameter 'routing_type' in event SRT.63"
    ::= { srtEventObjects63 1 }

srt63_source_mac OBJECT-TYPE
    SYNTAX DisplayString
    MAX-ACCESS accessible-for-notify
    STATUS current
    DESCRIPTION
        "Parameter 'source_mac' in event SRT.63"
    ::= { srtEventObjects63 2 }

srt63_dest_mac OBJECT-TYPE
    SYNTAX DisplayString
    MAX-ACCESS accessible-for-notify
    STATUS current
    DESCRIPTION
        "Parameter 'dest_mac' in event SRT.63"
    ::= { srtEventObjects63 3 }

srt63_port OBJECT-TYPE
    SYNTAX Integer32
    MAX-ACCESS accessible-for-notify
    STATUS current
    DESCRIPTION
        "Parameter 'port' in event SRT.63"
    ::= { srtEventObjects63 4 }

srt63_interface OBJECT-TYPE
    SYNTAX DisplayString
    MAX-ACCESS accessible-for-notify
    STATUS current
    DESCRIPTION
        "Parameter 'interface' in event SRT.63"
    ::= { srtEventObjects63 5 }

srt63_circuit_name OBJECT-TYPE
    SYNTAX DisplayString
    MAX-ACCESS accessible-for-notify
    STATUS current
    DESCRIPTION
        "Parameter 'circuit_name' in event SRT.63"
    ::= { srtEventObjects63 6 }

srtEventObjects64 OBJECT-IDENTITY
    STATUS current
    DESCRIPTION
        "Event SRT.64
        There is not enough free memory to allocate even a minimal size
        conversion database. The bridge will be disabled."
    ::= { srtEventsGroup 64 }

srt64_requested_size OBJECT-TYPE
    SYNTAX Integer32
    MAX-ACCESS accessible-for-notify
    STATUS current
    DESCRIPTION
        "Parameter 'requested_size' in event SRT.64"
    ::= { srtEventObjects64 1 }

srtEventObjects65 OBJECT-IDENTITY
    STATUS current
    DESCRIPTION
        "Event SRT.65
        An attempt to add a particular static entry to the internal database of
        a bridging interface having internal filtering failed."
    ::= { srtEventsGroup 65 }

srt65_MAC_address OBJECT-TYPE
    SYNTAX DisplayString
    MAX-ACCESS accessible-for-notify
    STATUS current
    DESCRIPTION
        "Parameter 'MAC_address' in event SRT.65"
    ::= { srtEventObjects65 1 }

srt65_interface OBJECT-TYPE
    SYNTAX DisplayString
    MAX-ACCESS accessible-for-notify
    STATUS current
    DESCRIPTION
        "Parameter 'interface' in event SRT.65"
    ::= { srtEventObjects65 2 }

srtEventObjects66 OBJECT-IDENTITY
    STATUS current
    DESCRIPTION
        "Event SRT.66
        The bridge has been configured to enable transparent bridging on
        an IEEE 802.5 Token-Ring interface that does not have the hardware
        to support transparent bridging. Transparent bridging will not be
        enabled on this interface."
    ::= { srtEventsGroup 66 }

srt66_interface OBJECT-TYPE
    SYNTAX DisplayString
    MAX-ACCESS accessible-for-notify
    STATUS current
    DESCRIPTION
        "Parameter 'interface' in event SRT.66"
    ::= { srtEventObjects66 1 }

srt66_circuit_name OBJECT-TYPE
    SYNTAX DisplayString
    MAX-ACCESS accessible-for-notify
    STATUS current
    DESCRIPTION
        "Parameter 'circuit_name' in event SRT.66"
    ::= { srtEventObjects66 2 }

srtEventObjects67 OBJECT-IDENTITY
    STATUS current
    DESCRIPTION
        "Event SRT.67
        A Specifically Routed frame has been sent on a port, but that port is
        not configured for bridging. This should never happen, since prior
        checks should prevent calling this code if the port is not configured
        for bridging."
    ::= { srtEventsGroup 67 }

srt67_source_mac OBJECT-TYPE
    SYNTAX DisplayString
    MAX-ACCESS accessible-for-notify
    STATUS current
    DESCRIPTION
        "Parameter 'source_mac' in event SRT.67"
    ::= { srtEventObjects67 1 }

srt67_dest_mac OBJECT-TYPE
    SYNTAX DisplayString
    MAX-ACCESS accessible-for-notify
    STATUS current
    DESCRIPTION
        "Parameter 'dest_mac' in event SRT.67"
    ::= { srtEventObjects67 2 }

srt67_RIF OBJECT-TYPE
    SYNTAX DisplayString
    MAX-ACCESS accessible-for-notify
    STATUS current
    DESCRIPTION
        "Parameter 'RIF' in event SRT.67"
    ::= { srtEventObjects67 3 }

srt67_port OBJECT-TYPE
    SYNTAX Integer32
    MAX-ACCESS accessible-for-notify
    STATUS current
    DESCRIPTION
        "Parameter 'port' in event SRT.67"
    ::= { srtEventObjects67 4 }

srt67_interface OBJECT-TYPE
    SYNTAX DisplayString
    MAX-ACCESS accessible-for-notify
    STATUS current
    DESCRIPTION
        "Parameter 'interface' in event SRT.67"
    ::= { srtEventObjects67 5 }

srt67_circuit_name OBJECT-TYPE
    SYNTAX DisplayString
    MAX-ACCESS accessible-for-notify
    STATUS current
    DESCRIPTION
        "Parameter 'circuit_name' in event SRT.67"
    ::= { srtEventObjects67 6 }

srtEventObjects68 OBJECT-IDENTITY
    STATUS current
    DESCRIPTION
        "Event SRT.68
        There is no space in the Ethernet type registration table for
        the specified ethernet_type. This happens when there are too many
        hash collisions, and there are not enough overflow buckets."
    ::= { srtEventsGroup 68 }

srt68_ethernet_type OBJECT-TYPE
    SYNTAX Integer32
    MAX-ACCESS accessible-for-notify
    STATUS current
    DESCRIPTION
        "Parameter 'ethernet_type' in event SRT.68"
    ::= { srtEventObjects68 1 }

srtEventObjects69 OBJECT-IDENTITY
    STATUS current
    DESCRIPTION
        "Event SRT.69
        There is no space in the SNAP PID registration table for
        the specified protocol. This happens when there are too many
        hash collisions, and there are not enough overflow buckets."
    ::= { srtEventsGroup 69 }

srt69_protocol OBJECT-TYPE
    SYNTAX Integer32
    MAX-ACCESS accessible-for-notify
    STATUS current
    DESCRIPTION
        "Parameter 'protocol' in event SRT.69"
    ::= { srtEventObjects69 1 }

srtEventObjects70 OBJECT-IDENTITY
    STATUS current
    DESCRIPTION
        "Event SRT.70
        A MAC frame has been received by the hardware, but is being dropped
        because the destination MAC address is being administratively filtered
        by the bridge. The frame will be dropped."
    ::= { srtEventsGroup 70 }

srt70_source_mac OBJECT-TYPE
    SYNTAX DisplayString
    MAX-ACCESS accessible-for-notify
    STATUS current
    DESCRIPTION
        "Parameter 'source_mac' in event SRT.70"
    ::= { srtEventObjects70 1 }

srt70_dest_mac OBJECT-TYPE
    SYNTAX DisplayString
    MAX-ACCESS accessible-for-notify
    STATUS current
    DESCRIPTION
        "Parameter 'dest_mac' in event SRT.70"
    ::= { srtEventObjects70 2 }

srt70_port OBJECT-TYPE
    SYNTAX Integer32
    MAX-ACCESS accessible-for-notify
    STATUS current
    DESCRIPTION
        "Parameter 'port' in event SRT.70"
    ::= { srtEventObjects70 3 }

srt70_interface OBJECT-TYPE
    SYNTAX DisplayString
    MAX-ACCESS accessible-for-notify
    STATUS current
    DESCRIPTION
        "Parameter 'interface' in event SRT.70"
    ::= { srtEventObjects70 4 }

srt70_circuit_name OBJECT-TYPE
    SYNTAX DisplayString
    MAX-ACCESS accessible-for-notify
    STATUS current
    DESCRIPTION
        "Parameter 'circuit_name' in event SRT.70"
    ::= { srtEventObjects70 5 }

srtEventObjects71 OBJECT-IDENTITY
    STATUS current
    DESCRIPTION
        "Event SRT.71
        Source Routing is configured on the port which is attached to an
        underlying network which inherently does not support source routing
        type of functionalities. Such networks are Ethernet and FDDI.
        Bridge disables source routing on the port."
    ::= { srtEventsGroup 71 }

srt71_port OBJECT-TYPE
    SYNTAX Integer32
    MAX-ACCESS accessible-for-notify
    STATUS current
    DESCRIPTION
        "Parameter 'port' in event SRT.71"
    ::= { srtEventObjects71 1 }

srt71_interface OBJECT-TYPE
    SYNTAX DisplayString
    MAX-ACCESS accessible-for-notify
    STATUS current
    DESCRIPTION
        "Parameter 'interface' in event SRT.71"
    ::= { srtEventObjects71 2 }

srt71_circuit_name OBJECT-TYPE
    SYNTAX DisplayString
    MAX-ACCESS accessible-for-notify
    STATUS current
    DESCRIPTION
        "Parameter 'circuit_name' in event SRT.71"
    ::= { srtEventObjects71 3 }

srtEventObjects74 OBJECT-IDENTITY
    STATUS current
    DESCRIPTION
        "Event SRT.74
        Source-routing bridging has been enabled, but that feature was not
        purchased as part of this software load. The source-routing bridging
        feature will not be enabled."
    ::= { srtEventsGroup 74 }

srt74_interface OBJECT-TYPE
    SYNTAX DisplayString
    MAX-ACCESS accessible-for-notify
    STATUS current
    DESCRIPTION
        "Parameter 'interface' in event SRT.74"
    ::= { srtEventObjects74 1 }

srt74_circuit_name OBJECT-TYPE
    SYNTAX DisplayString
    MAX-ACCESS accessible-for-notify
    STATUS current
    DESCRIPTION
        "Parameter 'circuit_name' in event SRT.74"
    ::= { srtEventObjects74 2 }

srtEventObjects75 OBJECT-IDENTITY
    STATUS current
    DESCRIPTION
        "Event SRT.75
        Spanning tree (transparent) bridging has been enabled, but that feature
        was not purchased as part of this software load.
        The spanning tree (transparent) bridging feature will not be enabled."
    ::= { srtEventsGroup 75 }

srt75_interface OBJECT-TYPE
    SYNTAX DisplayString
    MAX-ACCESS accessible-for-notify
    STATUS current
    DESCRIPTION
        "Parameter 'interface' in event SRT.75"
    ::= { srtEventObjects75 1 }

srt75_circuit_name OBJECT-TYPE
    SYNTAX DisplayString
    MAX-ACCESS accessible-for-notify
    STATUS current
    DESCRIPTION
        "Parameter 'circuit_name' in event SRT.75"
    ::= { srtEventObjects75 2 }

srtEventObjects77 OBJECT-IDENTITY
    STATUS current
    DESCRIPTION
        "Event SRT.77
        The user deleted a filter list, which was part of an already
        configured filter. The filter will not be enabled."
    ::= { srtEventsGroup 77 }

srt77_input_output OBJECT-TYPE
    SYNTAX DisplayString
    MAX-ACCESS accessible-for-notify
    STATUS current
    DESCRIPTION
        "Parameter 'input_output' in event SRT.77"
    ::= { srtEventObjects77 1 }

srt77_port_number OBJECT-TYPE
    SYNTAX Integer32
    MAX-ACCESS accessible-for-notify
    STATUS current
    DESCRIPTION
        "Parameter 'port_number' in event SRT.77"
    ::= { srtEventObjects77 2 }

srtEventObjects78 OBJECT-IDENTITY
    STATUS current
    DESCRIPTION
        "Event SRT.78
        The user configured a NETBIOS filter for a particular port, but that
        port number is not configured."
    ::= { srtEventsGroup 78 }

srt78_input_output OBJECT-TYPE
    SYNTAX DisplayString
    MAX-ACCESS accessible-for-notify
    STATUS current
    DESCRIPTION
        "Parameter 'input_output' in event SRT.78"
    ::= { srtEventObjects78 1 }

srt78_port_number OBJECT-TYPE
    SYNTAX Integer32
    MAX-ACCESS accessible-for-notify
    STATUS current
    DESCRIPTION
        "Parameter 'port_number' in event SRT.78"
    ::= { srtEventObjects78 2 }

srtEventObjects79 OBJECT-IDENTITY
    STATUS current
    DESCRIPTION
        "Event SRT.79
        A NETBIOS packet has matched the criteria specified in a NETBIOS Filter
        configuration record. The packet is dropped."
    ::= { srtEventsGroup 79 }

srt79_source_mac OBJECT-TYPE
    SYNTAX DisplayString
    MAX-ACCESS accessible-for-notify
    STATUS current
    DESCRIPTION
        "Parameter 'source_mac' in event SRT.79"
    ::= { srtEventObjects79 1 }

srt79_dest_mac OBJECT-TYPE
    SYNTAX DisplayString
    MAX-ACCESS accessible-for-notify
    STATUS current
    DESCRIPTION
        "Parameter 'dest_mac' in event SRT.79"
    ::= { srtEventObjects79 2 }

srt79_port OBJECT-TYPE
    SYNTAX Integer32
    MAX-ACCESS accessible-for-notify
    STATUS current
    DESCRIPTION
        "Parameter 'port' in event SRT.79"
    ::= { srtEventObjects79 3 }

srt79_interface OBJECT-TYPE
    SYNTAX DisplayString
    MAX-ACCESS accessible-for-notify
    STATUS current
    DESCRIPTION
        "Parameter 'interface' in event SRT.79"
    ::= { srtEventObjects79 4 }

srt79_circuit_name OBJECT-TYPE
    SYNTAX DisplayString
    MAX-ACCESS accessible-for-notify
    STATUS current
    DESCRIPTION
        "Parameter 'circuit_name' in event SRT.79"
    ::= { srtEventObjects79 5 }

srtEventObjects81 OBJECT-IDENTITY
    STATUS current
    DESCRIPTION
        "Event SRT.81
        A NETBIOS STE converted to SRF by NETBIOS Name Caching."
    ::= { srtEventsGroup 81 }

srt81_RIF OBJECT-TYPE
    SYNTAX DisplayString
    MAX-ACCESS accessible-for-notify
    STATUS current
    DESCRIPTION
        "Parameter 'RIF' in event SRT.81"
    ::= { srtEventObjects81 1 }

srt81_source_mac OBJECT-TYPE
    SYNTAX DisplayString
    MAX-ACCESS accessible-for-notify
    STATUS current
    DESCRIPTION
        "Parameter 'source_mac' in event SRT.81"
    ::= { srtEventObjects81 2 }

srt81_dest_mac OBJECT-TYPE
    SYNTAX DisplayString
    MAX-ACCESS accessible-for-notify
    STATUS current
    DESCRIPTION
        "Parameter 'dest_mac' in event SRT.81"
    ::= { srtEventObjects81 3 }

srt81_port OBJECT-TYPE
    SYNTAX Integer32
    MAX-ACCESS accessible-for-notify
    STATUS current
    DESCRIPTION
        "Parameter 'port' in event SRT.81"
    ::= { srtEventObjects81 4 }

srtEventObjects83 OBJECT-IDENTITY
    STATUS current
    DESCRIPTION
        "Event SRT.83
        A NETBIOS find-name STE has been filtered."
    ::= { srtEventsGroup 83 }

srt83_RIF OBJECT-TYPE
    SYNTAX DisplayString
    MAX-ACCESS accessible-for-notify
    STATUS current
    DESCRIPTION
        "Parameter 'RIF' in event SRT.83"
    ::= { srtEventObjects83 1 }

srt83_source_mac OBJECT-TYPE
    SYNTAX DisplayString
    MAX-ACCESS accessible-for-notify
    STATUS current
    DESCRIPTION
        "Parameter 'source_mac' in event SRT.83"
    ::= { srtEventObjects83 2 }

srt83_dest_mac OBJECT-TYPE
    SYNTAX DisplayString
    MAX-ACCESS accessible-for-notify
    STATUS current
    DESCRIPTION
        "Parameter 'dest_mac' in event SRT.83"
    ::= { srtEventObjects83 3 }

srt83_port OBJECT-TYPE
    SYNTAX Integer32
    MAX-ACCESS accessible-for-notify
    STATUS current
    DESCRIPTION
        "Parameter 'port' in event SRT.83"
    ::= { srtEventObjects83 4 }

srtEventObjects84 OBJECT-IDENTITY
    STATUS current
    DESCRIPTION
        "Event SRT.84
        A spanning tree BPDU frame was received on a port that has been
        disabled for spanning tree participation by the 'disable tree port#'
        command."
    ::= { srtEventsGroup 84 }

srt84_port OBJECT-TYPE
    SYNTAX Integer32
    MAX-ACCESS accessible-for-notify
    STATUS current
    DESCRIPTION
        "Parameter 'port' in event SRT.84"
    ::= { srtEventObjects84 1 }

srt84_interface OBJECT-TYPE
    SYNTAX DisplayString
    MAX-ACCESS accessible-for-notify
    STATUS current
    DESCRIPTION
        "Parameter 'interface' in event SRT.84"
    ::= { srtEventObjects84 2 }

srtEventObjects85 OBJECT-IDENTITY
    STATUS current
    DESCRIPTION
        "Event SRT.85
        The port has been configured to use a Frame Relay interface. However,
        subsequent to bridge configuration, device configuration changed such
        that the device is no longer configured to be a Frame Relay device.
        This could have happened if the user changed the data link support
        on the device, or re-ordered the device records."
    ::= { srtEventsGroup 85 }

srt85_port OBJECT-TYPE
    SYNTAX Integer32
    MAX-ACCESS accessible-for-notify
    STATUS current
    DESCRIPTION
        "Parameter 'port' in event SRT.85"
    ::= { srtEventObjects85 1 }

srt85_interface_number OBJECT-TYPE
    SYNTAX Integer32
    MAX-ACCESS accessible-for-notify
    STATUS current
    DESCRIPTION
        "Parameter 'interface_number' in event SRT.85"
    ::= { srtEventObjects85 2 }

srtEventObjects86 OBJECT-IDENTITY
    STATUS current
    DESCRIPTION
        "Event SRT.86
        During bridge initialization, ports are associated with Frame Relay
        registers with the Frame Relay interface. During registration, both let
        each other know about their existence and exchange some
        useful information to keep about each other."
    ::= { srtEventsGroup 86 }

srt86_port OBJECT-TYPE
    SYNTAX Integer32
    MAX-ACCESS accessible-for-notify
    STATUS current
    DESCRIPTION
        "Parameter 'port' in event SRT.86"
    ::= { srtEventObjects86 1 }

srt86_circuit_name OBJECT-TYPE
    SYNTAX DisplayString
    MAX-ACCESS accessible-for-notify
    STATUS current
    DESCRIPTION
        "Parameter 'circuit_name' in event SRT.86"
    ::= { srtEventObjects86 2 }

srt86_interface OBJECT-TYPE
    SYNTAX DisplayString
    MAX-ACCESS accessible-for-notify
    STATUS current
    DESCRIPTION
        "Parameter 'interface' in event SRT.86"
    ::= { srtEventObjects86 3 }

srt86_reason OBJECT-TYPE
    SYNTAX DisplayString
    MAX-ACCESS accessible-for-notify
    STATUS current
    DESCRIPTION
        "Parameter 'reason' in event SRT.86"
    ::= { srtEventObjects86 4 }

srtEventObjects87 OBJECT-IDENTITY
    STATUS current
    DESCRIPTION
        "Event SRT.87
        An All Routes Explorer (ARE) source-routed frame has more
        Route Descriptors than this bridge is configured to allow for
        ARE frames.
        The frame will be dropped."
    ::= { srtEventsGroup 87 }

srt87_source_mac OBJECT-TYPE
    SYNTAX DisplayString
    MAX-ACCESS accessible-for-notify
    STATUS current
    DESCRIPTION
        "Parameter 'source_mac' in event SRT.87"
    ::= { srtEventObjects87 1 }

srt87_dest_mac OBJECT-TYPE
    SYNTAX DisplayString
    MAX-ACCESS accessible-for-notify
    STATUS current
    DESCRIPTION
        "Parameter 'dest_mac' in event SRT.87"
    ::= { srtEventObjects87 2 }

srt87_port OBJECT-TYPE
    SYNTAX Integer32
    MAX-ACCESS accessible-for-notify
    STATUS current
    DESCRIPTION
        "Parameter 'port' in event SRT.87"
    ::= { srtEventObjects87 3 }

srt87_interface OBJECT-TYPE
    SYNTAX DisplayString
    MAX-ACCESS accessible-for-notify
    STATUS current
    DESCRIPTION
        "Parameter 'interface' in event SRT.87"
    ::= { srtEventObjects87 4 }

srt87_circuit_name OBJECT-TYPE
    SYNTAX DisplayString
    MAX-ACCESS accessible-for-notify
    STATUS current
    DESCRIPTION
        "Parameter 'circuit_name' in event SRT.87"
    ::= { srtEventObjects87 5 }

srtEventObjects89 OBJECT-IDENTITY
    STATUS current
    DESCRIPTION
        "Event SRT.89
        A frame is being bridged between these two interfaces. The destination
        address was broadcast or unregistered."
    ::= { srtEventsGroup 89 }

srt89_source_mac OBJECT-TYPE
    SYNTAX DisplayString
    MAX-ACCESS accessible-for-notify
    STATUS current
    DESCRIPTION
        "Parameter 'source_mac' in event SRT.89"
    ::= { srtEventObjects89 1 }

srt89_dest_mac OBJECT-TYPE
    SYNTAX DisplayString
    MAX-ACCESS accessible-for-notify
    STATUS current
    DESCRIPTION
        "Parameter 'dest_mac' in event SRT.89"
    ::= { srtEventObjects89 2 }

srt89_port OBJECT-TYPE
    SYNTAX Integer32
    MAX-ACCESS accessible-for-notify
    STATUS current
    DESCRIPTION
        "Parameter 'port' in event SRT.89"
    ::= { srtEventObjects89 3 }

srt89_interface OBJECT-TYPE
    SYNTAX DisplayString
    MAX-ACCESS accessible-for-notify
    STATUS current
    DESCRIPTION
        "Parameter 'interface' in event SRT.89"
    ::= { srtEventObjects89 4 }

srt89_circuit_name OBJECT-TYPE
    SYNTAX DisplayString
    MAX-ACCESS accessible-for-notify
    STATUS current
    DESCRIPTION
        "Parameter 'circuit_name' in event SRT.89"
    ::= { srtEventObjects89 5 }

srt89_out_port OBJECT-TYPE
    SYNTAX Integer32
    MAX-ACCESS accessible-for-notify
    STATUS current
    DESCRIPTION
        "Parameter 'out_port' in event SRT.89"
    ::= { srtEventObjects89 6 }

srt89_out_interface OBJECT-TYPE
    SYNTAX DisplayString
    MAX-ACCESS accessible-for-notify
    STATUS current
    DESCRIPTION
        "Parameter 'out_interface' in event SRT.89"
    ::= { srtEventObjects89 7 }

srt89_out_circuit_name OBJECT-TYPE
    SYNTAX DisplayString
    MAX-ACCESS accessible-for-notify
    STATUS current
    DESCRIPTION
        "Parameter 'out_circuit_name' in event SRT.89"
    ::= { srtEventObjects89 8 }

srtEventObjects90 OBJECT-IDENTITY
    STATUS current
    DESCRIPTION
        "Event SRT.90
        A VLAN tagged frame on a ethernet subinterface was received but bridging 
        is disabled for vlans.
        The frame will not be bridged."
    ::= { srtEventsGroup 90 }

srt90_source_mac OBJECT-TYPE
    SYNTAX DisplayString
    MAX-ACCESS accessible-for-notify
    STATUS current
    DESCRIPTION
        "Parameter 'source_mac' in event SRT.90"
    ::= { srtEventObjects90 1 }

srt90_dest_mac OBJECT-TYPE
    SYNTAX DisplayString
    MAX-ACCESS accessible-for-notify
    STATUS current
    DESCRIPTION
        "Parameter 'dest_mac' in event SRT.90"
    ::= { srtEventObjects90 2 }

srt90_vid OBJECT-TYPE
    SYNTAX Integer32
    MAX-ACCESS accessible-for-notify
    STATUS current
    DESCRIPTION
        "Parameter 'vid' in event SRT.90"
    ::= { srtEventObjects90 3 }


srtNotification1 NOTIFICATION-TYPE
    OBJECTS { 
              srt1_source_mac, 
              srt1_dest_mac,
              srt1_port,
              srt1_interface,
              srt1_circuit_name 
            }
    STATUS current
    DESCRIPTION
        "Notification of Event SRT.1

        Message: 'No buffer available to duplicate frame from $1 to $2 on port $3, interface $4$5'

        Parameters list:
              $1: srt1_source_mac
              $2: srt1_dest_mac
              $3: srt1_port
              $4: srt1_interface
              $5: srt1_circuit_name

        No buffer available to copy a frame in order to send a bridged frame on
        multiple interfaces. Bridged packets are sent on multiple interfaces
        either for multicast destination addresses, or in the case of
        certain static entries. No copy of this frame will be sent on
        the specified port and interface."
    ::= { srtNotificationsPrefix 1 }

srtNotification2 NOTIFICATION-TYPE
    OBJECTS { 
              srt2_error_code, 
              srt2_interface,
              srt2_circuit_name 
            }
    STATUS current
    DESCRIPTION
        "Notification of Event SRT.2

        Message: 'Error code $1 trying to set promiscuous mode on interface $2$3'

        Parameters list:
              $1: srt2_error_code
              $2: srt2_interface
              $3: srt2_circuit_name

        The Spanning Tree Protocol requested setting this network into
        Learning state, but the command to the device failed. The error_code is
        a device-specific error code that may indicate what the error is."
    ::= { srtNotificationsPrefix 2 }

srtNotification3 NOTIFICATION-TYPE
    OBJECTS { 
              srt3_error_code, 
              srt3_interface,
              srt3_circuit_name 
            }
    STATUS current
    DESCRIPTION
        "Notification of Event SRT.3

        Message: 'Error code $1 trying to add static entries on interface $2$3'

        Parameters list:
              $1: srt3_error_code
              $2: srt3_interface
              $3: srt3_circuit_name

        An attempt to add a set of static entries to the internal database of
        a bridging interface having internal filtering failed.
        The error_code is a device-specific error code that may indicate
        what the error is."
    ::= { srtNotificationsPrefix 3 }

srtNotification4 NOTIFICATION-TYPE
    OBJECTS { 
              srt4_command_name, 
              srt4_interface 
            }
    STATUS current
    DESCRIPTION
        "Notification of Event SRT.4

        Message: 'No buffer available for $1 command to interface $2'

        Parameters list:
              $1: srt4_command_name
              $2: srt4_interface

        No buffer was available to send a command to the device.
        The possible command names are
        'D_CNFGSRB' (configure source-routing bridging),
        'SRT_ON' (promiscuous on),
        'SRT_INFORM' (learn capabilities of device),
        'SRT_SET_AGE' (set age for filtering database in device),
        'SRT_DECR_AGE' (do ageing pass on filtering database in device),
        'SRT_ADD_ENTRY' (add static entry),
        'SRT_DEL_ENTRY' (delete entry, from console),
        'SRT_SEARCH_ENTRY' (search for particular entry, from console) and
        'SRT_LIST_ENTRY' (list contents of learning database in card).
        For commands 'D_CNFGSRB' and 'SRT_ON' the result will be that
        the interface may remain in the wrong state. A failure on 'SRT_INFORM'
        could cause serious problems. For other commands the results will be
        less serious."
    ::= { srtNotificationsPrefix 4 }

srtNotification5 NOTIFICATION-TYPE
    OBJECTS { 
              srt5_source_mac, 
              srt5_dest_mac,
              srt5_reason_code,
              srt5_port,
              srt5_interface_name,
              srt5_circuit_name 
            }
    STATUS current
    DESCRIPTION
        "Notification of Event SRT.5

        Message: 'Sending frame from $1 to $2 failed, reason $3, on port $4 interface $5$6'

        Parameters list:
              $1: srt5_source_mac
              $2: srt5_dest_mac
              $3: srt5_reason_code
              $4: srt5_port
              $5: srt5_interface_name
              $6: srt5_circuit_name

        The sending of a packet being forwarded failed. The reason is
        the internal error code for the failure."
    ::= { srtNotificationsPrefix 5 }

srtNotification6 NOTIFICATION-TYPE
    OBJECTS { 
              srt6_source_mac, 
              srt6_dest_mac,
              srt6_interface,
              srt6_circuit_name 
            }
    STATUS current
    DESCRIPTION
        "Notification of Event SRT.6

        Message: 'Input queue overflow on frame from $1 to $2, packet dropped interface $3$4'

        Parameters list:
              $1: srt6_source_mac
              $2: srt6_dest_mac
              $3: srt6_interface
              $4: srt6_circuit_name

        The input queue for frames to be forwarded is too long, and this frame
        has been dropped to attempt to alleviate the congestion."
    ::= { srtNotificationsPrefix 6 }

srtNotification7 NOTIFICATION-TYPE
    OBJECTS { 
              srt7_source_mac, 
              srt7_interface,
              srt7_circuit_name 
            }
    STATUS current
    DESCRIPTION
        "Notification of Event SRT.7

        Message: 'Bridge Protocol Data Unit input queue overflow on frame from $1, dropped from interface $2$3'

        Parameters list:
              $1: srt7_source_mac
              $2: srt7_interface
              $3: srt7_circuit_name

        The input queue for Spanning Tree Protocol Bridge Protocl Data Units
        is too long, and this frame has been dropped to attempt to alleviate
        the congestion."
    ::= { srtNotificationsPrefix 7 }

srtNotification8 NOTIFICATION-TYPE
    OBJECTS { 
              srt8_source_mac, 
              srt8_dest_mac,
              srt8_reformatted_length,
              srt8_output_maximum,
              srt8_port,
              srt8_interface,
              srt8_circuit_name 
            }
    STATUS current
    DESCRIPTION
        "Notification of Event SRT.8

        Message: 'Frame from $1 to $2 is too big (reformatted length $3 bytes > output maximum size $4 bytes) for port $5 interface $6$7, dropped'

        Parameters list:
              $1: srt8_source_mac
              $2: srt8_dest_mac
              $3: srt8_reformatted_length
              $4: srt8_output_maximum
              $5: srt8_port
              $6: srt8_interface
              $7: srt8_circuit_name

        The specified frame is too large to send on this outgoing port and
        interface. The reformatted_length is the size of the frame including
        MAC headers after any mapping of data link headers."
    ::= { srtNotificationsPrefix 8 }

srtNotification9 NOTIFICATION-TYPE
    OBJECTS { 
              srt9_source_mac, 
              srt9_dest_mac,
              srt9_interface 
            }
    STATUS current
    DESCRIPTION
        "Notification of Event SRT.9

        Message: 'Frame from $1 to $2 dropped, input interface $3 is down'

        Parameters list:
              $1: srt9_source_mac
              $2: srt9_dest_mac
              $3: srt9_interface

        A frame has been received for bridging on an interface that is down.
        It will be ignored."
    ::= { srtNotificationsPrefix 9 }

srtNotification10 NOTIFICATION-TYPE
    OBJECTS { 
              srt10_source_mac, 
              srt10_dest_mac,
              srt10_port,
              srt10_interface,
              srt10_circuit_name 
            }
    STATUS current
    DESCRIPTION
        "Notification of Event SRT.10

        Message: 'Frame from $1 to $2 dropped, source address filtered, port $3 interface $4$5'

        Parameters list:
              $1: srt10_source_mac
              $2: srt10_dest_mac
              $3: srt10_port
              $4: srt10_interface
              $5: srt10_circuit_name

        A MAC frame has been received by the hardware, but is being dropped
        because the source MAC address is being administratively filtered
        by the bridge. The frame will be dropped."
    ::= { srtNotificationsPrefix 10 }

srtNotification11 NOTIFICATION-TYPE
    OBJECTS { 
              srt11_source_mac, 
              srt11_dest_mac,
              srt11_port,
              srt11_interface,
              srt11_circuit_name 
            }
    STATUS current
    DESCRIPTION
        "Notification of Event SRT.11

        Message: 'Frame from $1 to $2 dropped, input port $3 interface $4$5 not in forwarding state'

        Parameters list:
              $1: srt11_source_mac
              $2: srt11_dest_mac
              $3: srt11_port
              $4: srt11_interface
              $5: srt11_circuit_name

        A MAC frame was received on a port that is still only in 'learning'
        state. Frames are only bridged when the input port is in 'forwarding'
        state. While the port is still in 'learning' state, they are only
        processed to learn the source addresses for the filtering database.
        The frame will not be bridged."
    ::= { srtNotificationsPrefix 11 }

srtNotification12 NOTIFICATION-TYPE
    OBJECTS { 
              srt12_source_mac, 
              srt12_dest_mac,
              srt12_port,
              srt12_interface,
              srt12_circuit_name 
            }
    STATUS current
    DESCRIPTION
        "Notification of Event SRT.12

        Message: 'Frame from $1 to $2 dropped, output port $3 interface $4$5 not in forwarding state'

        Parameters list:
              $1: srt12_source_mac
              $2: srt12_dest_mac
              $3: srt12_port
              $4: srt12_interface
              $5: srt12_circuit_name

        A MAC frame was being bridged, but the destination port was not
        in 'forwarding' state. It will not be sent on that port."
    ::= { srtNotificationsPrefix 12 }

srtNotification13 NOTIFICATION-TYPE
    OBJECTS { 
              srt13_source_mac, 
              srt13_dest_mac,
              srt13_port,
              srt13_interface,
              srt13_circuit_name 
            }
    STATUS current
    DESCRIPTION
        "Notification of Event SRT.13

        Message: 'Frame from $1 to $2 dropped, destination on same LAN, port $3 interface $4$5'

        Parameters list:
              $1: srt13_source_mac
              $2: srt13_dest_mac
              $3: srt13_port
              $4: srt13_interface
              $5: srt13_circuit_name

        A MAC frame has been received whose destination address is known to be
        on the same side of the bridge as the packet came from. It is dropped
        by the filtering logic since it does not need to be bridged."
    ::= { srtNotificationsPrefix 13 }

srtNotification14 NOTIFICATION-TYPE
    OBJECTS { 
              srt14_source_mac, 
              srt14_dest_mac,
              srt14_port,
              srt14_interface,
              srt14_circuit_name 
            }
    STATUS current
    DESCRIPTION
        "Notification of Event SRT.14

        Message: 'Frame from $1 to $2 dropped, destination port $3 not enabled, interface $4$5'

        Parameters list:
              $1: srt14_source_mac
              $2: srt14_dest_mac
              $3: srt14_port
              $4: srt14_interface
              $5: srt14_circuit_name

        A frame being bridged was destined for a port which is not running
        transparent bridging, or not in 'forwarding' state for transparent
        bridging."
    ::= { srtNotificationsPrefix 14 }

srtNotification15 NOTIFICATION-TYPE
    OBJECTS { 
              srt15_source_mac, 
              srt15_dest_mac,
              srt15_port,
              srt15_interface,
              srt15_circuit_name,
              srt15_out_port,
              srt15_out_interface,
              srt15_out_circuit_name 
            }
    STATUS current
    DESCRIPTION
        "Notification of Event SRT.15

        Message: 'Frame from $1 to $2 bridged from port number $3 interface $4$5 to port number $6 interface $7$8'

        Parameters list:
              $1: srt15_source_mac
              $2: srt15_dest_mac
              $3: srt15_port
              $4: srt15_interface
              $5: srt15_circuit_name
              $6: srt15_out_port
              $7: srt15_out_interface
              $8: srt15_out_circuit_name

        A frame is being bridged between these two interfaces. The destination
        address was known, so it was sent only to the correct destination
        network."
    ::= { srtNotificationsPrefix 15 }

srtNotification16 NOTIFICATION-TYPE
    OBJECTS { 
              srt16_source_mac, 
              srt16_dest_mac,
              srt16_port,
              srt16_interface,
              srt16_circuit_name,
              srt16_out_port,
              srt16_out_interface,
              srt16_out_circuit_name 
            }
    STATUS current
    DESCRIPTION
        "Notification of Event SRT.16

        Message: 'Frame from $1 to $2 bridged to all ports from port number $3 interface $4$5 to port number $6 interface $7$8'

        Parameters list:
              $1: srt16_source_mac
              $2: srt16_dest_mac
              $3: srt16_port
              $4: srt16_interface
              $5: srt16_circuit_name
              $6: srt16_out_port
              $7: srt16_out_interface
              $8: srt16_out_circuit_name

        A frame is being transparently bridged to all active transparent
        bridging ports. This happens when the frame destination is a multicast,
        when the frame destination is not in the learning database, or when
        required by static entries in the learning database.
        There will be one message for each port the frame is sent on."
    ::= { srtNotificationsPrefix 16 }

srtNotification17 NOTIFICATION-TYPE
    OBJECTS { 
              srt17_port, 
              srt17_interface,
              srt17_circuit_name 
            }
    STATUS current
    DESCRIPTION
        "Notification of Event SRT.17

        Message: 'Enabling SRT on port $1 interface $2$3'

        Parameters list:
              $1: srt17_port
              $2: srt17_interface
              $3: srt17_circuit_name

        The SRT forwarder is starting the process of enabling bridging
        on the specified interface. This starts when the interface comes up
        from a self-test."
    ::= { srtNotificationsPrefix 17 }

srtNotification18 NOTIFICATION-TYPE
    OBJECTS { 
              srt18_port, 
              srt18_interface,
              srt18_circuit_name 
            }
    STATUS current
    DESCRIPTION
        "Notification of Event SRT.18

        Message: 'SRT startup complete on port $1 interface $2$3'

        Parameters list:
              $1: srt18_port
              $2: srt18_interface
              $3: srt18_circuit_name

        The SRT forwarder has completed the process of enabling bridging
        on the specified interface. It will now enter 'blocking' state."
    ::= { srtNotificationsPrefix 18 }

srtNotification19 NOTIFICATION-TYPE
    OBJECTS { 
              srt19_interface_name 
            }
    STATUS current
    DESCRIPTION
        "Notification of Event SRT.19

        Message: 'Unsupported interface $1'

        Parameters list:
              $1: srt19_interface_name

        The SRT forwarder had been enabled on a type of interface it does not
        support."
    ::= { srtNotificationsPrefix 19 }

srtNotification20 NOTIFICATION-TYPE
    OBJECTS { 
              srt20_port, 
              srt20_interface,
              srt20_circuit_name 
            }
    STATUS current
    DESCRIPTION
        "Notification of Event SRT.20

        Message: 'Cannot autoconfigure the bridge address, the lowest numbered port $1 interface $2$3 has no MAC address'

        Parameters list:
              $1: srt20_port
              $2: srt20_interface
              $3: srt20_circuit_name

        The user has configured the bridge to autoconfigure the bridge address
        based on the MAC address of the lowest number port. However, the lowest
        numbered port is of a type that does not have a MAC address, such as
        a serial line."
    ::= { srtNotificationsPrefix 20 }

srtNotification21 NOTIFICATION-TYPE
    OBJECTS { 
              srt21_source_mac, 
              srt21_dest_mac,
              srt21_interface 
            }
    STATUS current
    DESCRIPTION
        "Notification of Event SRT.21

        Message: 'Bridge frame from $1 to $2, no forwarder, interface $3'

        Parameters list:
              $1: srt21_source_mac
              $2: srt21_dest_mac
              $3: srt21_interface

        Bridge frame received, but there is no bridging available in this load.
        The frame will be ignored."
    ::= { srtNotificationsPrefix 21 }

srtNotification22 NOTIFICATION-TYPE
    STATUS current
    DESCRIPTION
        "Notification of Event SRT.22

        Message: 'Bridge configured with no ports on it, disabling the bridge'

        The bridge has been enabled, but there are no ports configured
        on that bridge. The bridge will be left disabled.
        It takes at least two ports to be a bridge."
    ::= { srtNotificationsPrefix 22 }

srtNotification23 NOTIFICATION-TYPE
    OBJECTS { 
              srt23_port, 
              srt23_interface_number 
            }
    STATUS current
    DESCRIPTION
        "Notification of Event SRT.23

        Message: 'Port $1 configured on nonexistent interface number $2'

        Parameters list:
              $1: srt23_port
              $2: srt23_interface_number

        The port has been configured to use an interface that has not been
        configured with the Config> ADD DEVICE command.
        This port of the bridge will be disabled."
    ::= { srtNotificationsPrefix 23 }

srtNotification24 NOTIFICATION-TYPE
    OBJECTS { 
              srt24_existent_port_count 
            }
    STATUS current
    DESCRIPTION
        "Notification of Event SRT.24

        Message: '$1 existent ports is less than 2, disabling bridge'

        Parameters list:
              $1: srt24_existent_port_count

        Less than two (valid) ports have been configured on the bridge.
        There must be at least two ports."
    ::= { srtNotificationsPrefix 24 }

srtNotification25 NOTIFICATION-TYPE
    OBJECTS { 
              srt25_requested_size, 
              srt25_minimum_size 
            }
    STATUS current
    DESCRIPTION
        "Notification of Event SRT.25

        Message: 'No memory for filtering database (desired size $1 bytes, absolute minimum size $2 bytes), disabling bridge'

        Parameters list:
              $1: srt25_requested_size
              $2: srt25_minimum_size

        There is not enough free memory to allocate even a minimal size
        filtering database. The bridge will be disabled.
        The bridge starts by trying to allocate requested_size bytes, and then
        tries with progressively smaller sizes down to minimum_size.
        The minimum size is enough only for the registered and static entries."
    ::= { srtNotificationsPrefix 25 }

srtNotification26 NOTIFICATION-TYPE
    OBJECTS { 
              srt26_source_mac, 
              srt26_dest_mac,
              srt26_port,
              srt26_interface,
              srt26_circuit_name 
            }
    STATUS current
    DESCRIPTION
        "Notification of Event SRT.26

        Message: 'Frame from $1 to $2, source same as destination, dropping, from port $3 interface $4$5'

        Parameters list:
              $1: srt26_source_mac
              $2: srt26_dest_mac
              $3: srt26_port
              $4: srt26_interface
              $5: srt26_circuit_name

        Frames to and from the same address are not bridged by this bridge."
    ::= { srtNotificationsPrefix 26 }

srtNotification27 NOTIFICATION-TYPE
    OBJECTS { 
              srt27_old_state, 
              srt27_new_state,
              srt27_port,
              srt27_interface,
              srt27_circuit_name 
            }
    STATUS current
    DESCRIPTION
        "Notification of Event SRT.27

        Message: 'Changing port state from $1 to $2 for port $3, interface $4$5'

        Parameters list:
              $1: srt27_old_state
              $2: srt27_new_state
              $3: srt27_port
              $4: srt27_interface
              $5: srt27_circuit_name

        The Spanning Tree Protocol has requested this state change for this port
        in the SRT bridge. The old_state and new_state are one of:
        FORWARDING (Spanning Tree Protocol Forwarding state),
        LEARNING (Spanning Tree Protocol Learning state),
        LISTENING (Spanning Tree Protocol Listening state),
        BLOCKED (Spanning Tree Protocol Blocking state),
        CONFIGURING (configuration of port device pending),
        POSTCONFIGURING (configuration of port device done),
        PRECONFIGURING (port enabled, configuration of port device to start) and
        DISABLED (port disabled)."
    ::= { srtNotificationsPrefix 27 }

srtNotification28 NOTIFICATION-TYPE
    OBJECTS { 
              srt28_mac_address 
            }
    STATUS current
    DESCRIPTION
        "Notification of Event SRT.28

        Message: 'No room for permanent address $1 in filtering database, disabling bridge'

        Parameters list:
              $1: srt28_mac_address

        There is no room for the permanent entry in the filtering database.
        The bridge will be disabled."
    ::= { srtNotificationsPrefix 28 }

srtNotification29 NOTIFICATION-TYPE
    OBJECTS { 
              srt29_mac_address 
            }
    STATUS current
    DESCRIPTION
        "Notification of Event SRT.29

        Message: 'No memory for permanent address $1, disabling bridge'

        Parameters list:
              $1: srt29_mac_address

        There is no room for the permanent entry in an auxiliary database.
        The bridge will be disabled."
    ::= { srtNotificationsPrefix 29 }

srtNotification30 NOTIFICATION-TYPE
    OBJECTS { 
              srt30_command, 
              srt30_interface 
            }
    STATUS current
    DESCRIPTION
        "Notification of Event SRT.30

        Message: '$1 command failed to interface $2'

        Parameters list:
              $1: srt30_command
              $2: srt30_interface

        A command to a network device failed.
        The possible command names are
        'SRT_ON' (promiscuous on),
        'SRT_OFF' (promiscuous off),
        'SRT_INFORM' (learn capabilities of device),
        'SRT_ADD_ENTRY' (add static entry in device),
        'SRT_SET_AGE' (set age for filtering database in device) and
        'SRT_DECR_AGE' (do ageing pass on filtering database in device).
        For commands 'SRT_ON' and 'SRT_OFF' the result will be that
        the interface may remain in the worong state. A failure on 'SRT_INFORM'
        could cause serious problems. For other commands the results will be
        less serious."
    ::= { srtNotificationsPrefix 30 }

srtNotification31 NOTIFICATION-TYPE
    OBJECTS { 
              srt31_routing_type, 
              srt31_source_mac,
              srt31_dest_mac,
              srt31_port,
              srt31_interface,
              srt31_circuit_name 
            }
    STATUS current
    DESCRIPTION
        "Notification of Event SRT.31

        Message: 'No buffer available to duplicate $1 frame from $2 to $3 on port $4, interface $5$6'

        Parameters list:
              $1: srt31_routing_type
              $2: srt31_source_mac
              $3: srt31_dest_mac
              $4: srt31_port
              $5: srt31_interface
              $6: srt31_circuit_name

        No buffer available to copy a frame in order to send an
        All Routes Explorer (ARE) or Spanning Tree Explorer (STE) routing_type
        frame on multiple interfaces. ARE frames are sent on all interfaces
        which are part of the SRT spanning tree, STE frames are sent
        on all interfaces running source-routing.
        No copy of this frame will be sent on the specified port and interface."
    ::= { srtNotificationsPrefix 31 }

srtNotification32 NOTIFICATION-TYPE
    OBJECTS { 
              srt32_source_mac, 
              srt32_dest_mac,
              srt32_reason_code,
              srt32_port,
              srt32_interface_name,
              srt32_circuit_name 
            }
    STATUS current
    DESCRIPTION
        "Notification of Event SRT.32

        Message: 'Sending source routed frame from $1 to $2 failed, reason $3, on port $4 interface $5$6'

        Parameters list:
              $1: srt32_source_mac
              $2: srt32_dest_mac
              $3: srt32_reason_code
              $4: srt32_port
              $5: srt32_interface_name
              $6: srt32_circuit_name

        The sending of a source routed frame being forwarded failed.
        The reason_code is the internal error code for the failure."
    ::= { srtNotificationsPrefix 32 }

srtNotification33 NOTIFICATION-TYPE
    OBJECTS { 
              srt33_routing_type, 
              srt33_source_mac,
              srt33_dest_mac,
              srt33_port,
              srt33_interface,
              srt33_circuit_name 
            }
    STATUS current
    DESCRIPTION
        "Notification of Event SRT.33

        Message: '$1 with duplicate Route Descriptor from $2 to $3 from port $4, interface $5$6'

        Parameters list:
              $1: srt33_routing_type
              $2: srt33_source_mac
              $3: srt33_dest_mac
              $4: srt33_port
              $5: srt33_interface
              $6: srt33_circuit_name

        A source-routed frame having a All Routes Descriptor (ARE)
        or Spanning Tree Explorer (STE) routing_type in the RIF has a duplicate
        Routing Descriptor in the RIF. The frame will be dropped. This is
        a normal occurrence for ARE frames when there are any duplicate paths
        in the source routing domain. For STE frames, this indicates that
        there is an interface that is part of the source-routing spanning tree
        that should not be."
    ::= { srtNotificationsPrefix 33 }

srtNotification34 NOTIFICATION-TYPE
    OBJECTS { 
              srt34_RIF, 
              srt34_source_mac,
              srt34_dest_mac,
              srt34_port,
              srt34_interface,
              srt34_circuit_name 
            }
    STATUS current
    DESCRIPTION
        "Notification of Event SRT.34

        Message: 'SRF with duplicate LOUT (RIF $1) from $2 to $3 from port $4, interface $5$6'

        Parameters list:
              $1: srt34_RIF
              $2: srt34_source_mac
              $3: srt34_dest_mac
              $4: srt34_port
              $5: srt34_interface
              $6: srt34_circuit_name

        A source-routed frame of Specifically-routed frame (SRF) type has
        a duplicate LOUT (outgoing LAN ID). This is illegal, and the frame
        will be dropped."
    ::= { srtNotificationsPrefix 34 }

srtNotification35 NOTIFICATION-TYPE
    OBJECTS { 
              srt35_RIF, 
              srt35_source_mac,
              srt35_dest_mac,
              srt35_port,
              srt35_interface,
              srt35_circuit_name 
            }
    STATUS current
    DESCRIPTION
        "Notification of Event SRT.35

        Message: 'All Routes Explorer exceeds maximum Route Descriptors (RIF $1) from $2 to $3 from port $4, interface $5$6, dropped'

        Parameters list:
              $1: srt35_RIF
              $2: srt35_source_mac
              $3: srt35_dest_mac
              $4: srt35_port
              $5: srt35_interface
              $6: srt35_circuit_name

        An All Routes Explorer (ARE) source-routed frame has more Route
        Descriptors than this bridge is configured to allow for ARE frames.
        The frame will be dropped."
    ::= { srtNotificationsPrefix 35 }

srtNotification36 NOTIFICATION-TYPE
    OBJECTS { 
              srt36_RIF, 
              srt36_source_mac,
              srt36_dest_mac,
              srt36_port,
              srt36_interface,
              srt36_circuit_name 
            }
    STATUS current
    DESCRIPTION
        "Notification of Event SRT.36

        Message: 'Spanning Tree Explorer exceeds maximum Route Descriptors (RIF $1) from $2 to $3 from port $4, interface $5$6'

        Parameters list:
              $1: srt36_RIF
              $2: srt36_source_mac
              $3: srt36_dest_mac
              $4: srt36_port
              $5: srt36_interface
              $6: srt36_circuit_name

        A Spanning Tree Explorer (STE) source-routed frame has more Route
        Descriptors than this bridge is configured to allow for STE frames.
        The frame will be dropped."
    ::= { srtNotificationsPrefix 36 }

srtNotification37 NOTIFICATION-TYPE
    OBJECTS { 
              srt37_RIF, 
              srt37_source_mac,
              srt37_dest_mac,
              srt37_port,
              srt37_interface 
            }
    STATUS current
    DESCRIPTION
        "Notification of Event SRT.37

        Message: 'SRF with unknown LOUT (RIF $1) from $2 to $3 from port $4, interface $5'

        Parameters list:
              $1: srt37_RIF
              $2: srt37_source_mac
              $3: srt37_dest_mac
              $4: srt37_port
              $5: srt37_interface

        A source-routed frame of Specifically-routed frame (SRF) type has
        an outgoing LOUT (LAN ID Out) that does not match that of any active
        source-routing interface in the router. It will be dropped."
    ::= { srtNotificationsPrefix 37 }

srtNotification38 NOTIFICATION-TYPE
    OBJECTS { 
              srt38_RIF, 
              srt38_source_mac,
              srt38_dest_mac,
              srt38_port,
              srt38_interface,
              srt38_circuit_name 
            }
    STATUS current
    DESCRIPTION
        "Notification of Event SRT.38

        Message: 'All Routes Explorer received (RIF $1) from $2 to $3 from port $4, interface $5$6'

        Parameters list:
              $1: srt38_RIF
              $2: srt38_source_mac
              $3: srt38_dest_mac
              $4: srt38_port
              $5: srt38_interface
              $6: srt38_circuit_name

        An All Routes Explorer frame has been received on the specified port."
    ::= { srtNotificationsPrefix 38 }

srtNotification39 NOTIFICATION-TYPE
    OBJECTS { 
              srt39_RIF, 
              srt39_source_mac,
              srt39_dest_mac,
              srt39_port,
              srt39_interface,
              srt39_circuit_name 
            }
    STATUS current
    DESCRIPTION
        "Notification of Event SRT.39

        Message: 'All Routes Explorer sent (RIF $1) from $2 to $3 to port $4, interface $5$6'

        Parameters list:
              $1: srt39_RIF
              $2: srt39_source_mac
              $3: srt39_dest_mac
              $4: srt39_port
              $5: srt39_interface
              $6: srt39_circuit_name

        An All Routes Explorer frame has been sent on the specified port."
    ::= { srtNotificationsPrefix 39 }

srtNotification40 NOTIFICATION-TYPE
    OBJECTS { 
              srt40_RIF, 
              srt40_source_mac,
              srt40_dest_mac,
              srt40_port,
              srt40_interface,
              srt40_circuit_name 
            }
    STATUS current
    DESCRIPTION
        "Notification of Event SRT.40

        Message: 'Spanning Tree Explorer received (RIF $1) from $2 to $3 from port $4, interface $5$6'

        Parameters list:
              $1: srt40_RIF
              $2: srt40_source_mac
              $3: srt40_dest_mac
              $4: srt40_port
              $5: srt40_interface
              $6: srt40_circuit_name

        A Spanning Tree Explorer frame has been received on the specified port."
    ::= { srtNotificationsPrefix 40 }

srtNotification41 NOTIFICATION-TYPE
    OBJECTS { 
              srt41_RIF, 
              srt41_source_mac,
              srt41_dest_mac,
              srt41_port,
              srt41_interface,
              srt41_circuit_name 
            }
    STATUS current
    DESCRIPTION
        "Notification of Event SRT.41

        Message: 'Spanning Tree Explorer sent (RIF $1) from $2 to $3 to port $4, interface $5$6'

        Parameters list:
              $1: srt41_RIF
              $2: srt41_source_mac
              $3: srt41_dest_mac
              $4: srt41_port
              $5: srt41_interface
              $6: srt41_circuit_name

        A Spanning Tree Explorer frame has been sent on the specified port."
    ::= { srtNotificationsPrefix 41 }

srtNotification42 NOTIFICATION-TYPE
    OBJECTS { 
              srt42_routing_type, 
              srt42_old_LF,
              srt42_new_LF,
              srt42_source_mac,
              srt42_dest_mac,
              srt42_port,
              srt42_interface,
              srt42_circuit_name 
            }
    STATUS current
    DESCRIPTION
        "Notification of Event SRT.42

        Message: '$1 Largest Frame size lowered (from $2 bytes to $3 bytes) from $4 to $5 from port $6, interface $7$8'

        Parameters list:
              $1: srt42_routing_type
              $2: srt42_old_LF
              $3: srt42_new_LF
              $4: srt42_source_mac
              $5: srt42_dest_mac
              $6: srt42_port
              $7: srt42_interface
              $8: srt42_circuit_name

        A source-routing explorer (ARE or STE in routing_type) has had
        the Largest Frame (LF) field lowered in its RIF. This happens
        whenever a frame is received from a segment with a smaller maximum
        frame size than the one presently encoded in the LF bits. This is
        a normal part of the spanning tree protocol to determine the maximum
        frame size on all routes."
    ::= { srtNotificationsPrefix 42 }

srtNotification43 NOTIFICATION-TYPE
    OBJECTS { 
              srt43_routing_type, 
              srt43_old_LF,
              srt43_new_LF,
              srt43_source_mac,
              srt43_dest_mac,
              srt43_port,
              srt43_interface,
              srt43_circuit_name 
            }
    STATUS current
    DESCRIPTION
        "Notification of Event SRT.43

        Message: '$1 Largest Frame size lowered (from $2 bytes to $3 bytes) from $4 to $5 to port $6, interface $7$8'

        Parameters list:
              $1: srt43_routing_type
              $2: srt43_old_LF
              $3: srt43_new_LF
              $4: srt43_source_mac
              $5: srt43_dest_mac
              $6: srt43_port
              $7: srt43_interface
              $8: srt43_circuit_name

        A source-routing explorer (ARE or STE in routing_type) has had
        the Largest Frame (LF) field lowered in its RIF. This happens
        whenever a frame is sent to a segment with a smaller maximum frame size
        than the one presently encoded in the LF bits. This is a normal part of
        the spanning tree protocol to determine the maximum frame size
        on all routes."
    ::= { srtNotificationsPrefix 43 }

srtNotification44 NOTIFICATION-TYPE
    OBJECTS { 
              srt44_RIF, 
              srt44_source_mac,
              srt44_dest_mac,
              srt44_port,
              srt44_interface,
              srt44_circuit_name 
            }
    STATUS current
    DESCRIPTION
        "Notification of Event SRT.44

        Message: 'Specifically-routed frame received (RIF $1) from $2 to $3 from port $4, interface $5$6'

        Parameters list:
              $1: srt44_RIF
              $2: srt44_source_mac
              $3: srt44_dest_mac
              $4: srt44_port
              $5: srt44_interface
              $6: srt44_circuit_name

        A Specifically-routed frame has been received on the specified port."
    ::= { srtNotificationsPrefix 44 }

srtNotification45 NOTIFICATION-TYPE
    OBJECTS { 
              srt45_RIF, 
              srt45_source_mac,
              srt45_dest_mac,
              srt45_port,
              srt45_interface,
              srt45_circuit_name 
            }
    STATUS current
    DESCRIPTION
        "Notification of Event SRT.45

        Message: 'Sending Specifically-routed frame (RIF $1) from $2 to $3 to port $4, interface $5$6'

        Parameters list:
              $1: srt45_RIF
              $2: srt45_source_mac
              $3: srt45_dest_mac
              $4: srt45_port
              $5: srt45_interface
              $6: srt45_circuit_name

        A Specifically-routed frame is being sent on the specified port."
    ::= { srtNotificationsPrefix 45 }

srtNotification46 NOTIFICATION-TYPE
    OBJECTS { 
              srt46_routing_type, 
              srt46_source_mac,
              srt46_dest_mac,
              srt46_port,
              srt46_interface,
              srt46_circuit_name 
            }
    STATUS current
    DESCRIPTION
        "Notification of Event SRT.46

        Message: '$1 frame received from $2 to $3 on disabled port $4, interface $5$6, discarded'

        Parameters list:
              $1: srt46_routing_type
              $2: srt46_source_mac
              $3: srt46_dest_mac
              $4: srt46_port
              $5: srt46_interface
              $6: srt46_circuit_name

        A source-routed frame has been received on the specified port, but
        that port is not configured for bridging.
        The routing_type is one of SRF (Specifically-routed frame),
        STE (Spanning Tree Expolorer) or ARE (All Routes Explorer).
        This really should not happen on more than a transient basis, because
        ports that are not enabled for bridging should not be queueing packets
        to the source-routing forwarder."
    ::= { srtNotificationsPrefix 46 }

srtNotification47 NOTIFICATION-TYPE
    OBJECTS { 
              srt47_routing_type, 
              srt47_source_mac,
              srt47_dest_mac,
              srt47_port,
              srt47_interface,
              srt47_circuit_name 
            }
    STATUS current
    DESCRIPTION
        "Notification of Event SRT.47

        Message: '$1 frame received from $2 to $3 on non-source-routing port $4, interface $5$6, discarded'

        Parameters list:
              $1: srt47_routing_type
              $2: srt47_source_mac
              $3: srt47_dest_mac
              $4: srt47_port
              $5: srt47_interface
              $6: srt47_circuit_name

        A source-routed frame has been received on the specified port, but
        that port is not configured for source-routing bridging.
        The routing_type is one of SRF (Specifically-routed frame),
        STE (Spanning Tree Expolorer) or ARE (All Routes Explorer).
        This really should not happen on more than a transient basis, because
        ports that are not enabled for bridging should not be queueing packets
        to the source-routing forwarder."
    ::= { srtNotificationsPrefix 47 }

srtNotification48 NOTIFICATION-TYPE
    OBJECTS { 
              srt48_RIF, 
              srt48_source_mac,
              srt48_dest_mac,
              srt48_port,
              srt48_interface,
              srt48_circuit_name 
            }
    STATUS current
    DESCRIPTION
        "Notification of Event SRT.48

        Message: 'Spanning Tree Explorer dropped (RIF $1) from $2 to $3 from blocked port $4, interface $5$6'

        Parameters list:
              $1: srt48_RIF
              $2: srt48_source_mac
              $3: srt48_dest_mac
              $4: srt48_port
              $5: srt48_interface
              $6: srt48_circuit_name

        A Spanning Tree Explorer (STE) frame was dropped, and not forwarded,
        because the incoming port is not part of the spanning tree, or has been
        configured not to forward STE frames."
    ::= { srtNotificationsPrefix 48 }

srtNotification49 NOTIFICATION-TYPE
    OBJECTS { 
              srt49_RIF, 
              srt49_source_mac,
              srt49_dest_mac,
              srt49_port,
              srt49_interface,
              srt49_circuit_name 
            }
    STATUS current
    DESCRIPTION
        "Notification of Event SRT.49

        Message: 'Spanning Tree Explorer not sent (RIF $1) from $2 to $3 to blocked port $4, interface $5$6'

        Parameters list:
              $1: srt49_RIF
              $2: srt49_source_mac
              $3: srt49_dest_mac
              $4: srt49_port
              $5: srt49_interface
              $6: srt49_circuit_name

        A Spanning Tree Explorer (STE) frame was not sent on the specified port
        because it is not part of the spanning tree, or has been configured
        not to forward STE frames."
    ::= { srtNotificationsPrefix 49 }

srtNotification50 NOTIFICATION-TYPE
    OBJECTS { 
              srt50_error_string, 
              srt50_interface 
            }
    STATUS current
    DESCRIPTION
        "Notification of Event SRT.50

        Message: 'Got $1 error trying to enable source-routing on interface $2'

        Parameters list:
              $1: srt50_error_string
              $2: srt50_interface

        The bridge tried to enable source-routing bridging on this interface,
        but the interface refused the configuration command.
        Source-routing will be left disabled on this interface."
    ::= { srtNotificationsPrefix 50 }

srtNotification51 NOTIFICATION-TYPE
    OBJECTS { 
              srt51_source_mac, 
              srt51_dest_mac,
              srt51_reformatted_length,
              srt51_output_maximum,
              srt51_port,
              srt51_interface,
              srt51_circuit_name 
            }
    STATUS current
    DESCRIPTION
        "Notification of Event SRT.51

        Message: 'Specifically-routed frame from $1 to $2 is too big (reformatted length $3 > output maximum size $4) for port $5 interface $6$7, dropped'

        Parameters list:
              $1: srt51_source_mac
              $2: srt51_dest_mac
              $3: srt51_reformatted_length
              $4: srt51_output_maximum
              $5: srt51_port
              $6: srt51_interface
              $7: srt51_circuit_name

        The specified Specifically-routed (source-routed) frame is too large
        to send on this outgoing port and interface. The reformatted_length is
        the size of the frame including MAC headers after any mapping of
        data link headers."
    ::= { srtNotificationsPrefix 51 }

srtNotification52 NOTIFICATION-TYPE
    OBJECTS { 
              srt52_routing_type, 
              srt52_source_mac,
              srt52_dest_mac,
              srt52_reformatted_length,
              srt52_output_maximum,
              srt52_port,
              srt52_interface,
              srt52_circuit_name 
            }
    STATUS current
    DESCRIPTION
        "Notification of Event SRT.52

        Message: '$1 frame from $2 to $3 is too big (reformatted length $4 > output maximum size $5) for port $6 interface $7$8, dropped'

        Parameters list:
              $1: srt52_routing_type
              $2: srt52_source_mac
              $3: srt52_dest_mac
              $4: srt52_reformatted_length
              $5: srt52_output_maximum
              $6: srt52_port
              $7: srt52_interface
              $8: srt52_circuit_name

        The source-routed explorer (ARE or STE routing_type) frame is too large
        to send on this outgoing port and interface. The reformatted_length is
        the size of the frame including MAC headers after any mapping of
        data link headers."
    ::= { srtNotificationsPrefix 52 }

srtNotification53 NOTIFICATION-TYPE
    OBJECTS { 
              srt53_routing_type, 
              srt53_RIF_length,
              srt53_source_mac,
              srt53_dest_mac,
              srt53_port,
              srt53_interface,
              srt53_circuit_name 
            }
    STATUS current
    DESCRIPTION
        "Notification of Event SRT.53

        Message: '$1 with invalid RIF lenth $2 from $3 to $4 from port $5, interface $6$7, discarded'

        Parameters list:
              $1: srt53_routing_type
              $2: srt53_RIF_length
              $3: srt53_source_mac
              $4: srt53_dest_mac
              $5: srt53_port
              $6: srt53_interface
              $7: srt53_circuit_name

        A source-routing frame was received with an invalid RIF length encoded
        in the Length bits of the RIF.
        The routing_type is one of SRF (Specifically-routed frame),
        STE (Spanning Tree Expolorer) or ARE (All Routes Explorer)."
    ::= { srtNotificationsPrefix 53 }

srtNotification54 NOTIFICATION-TYPE
    OBJECTS { 
              srt54_requested_size 
            }
    STATUS current
    DESCRIPTION
        "Notification of Event SRT.54

        Message: 'No memory for hash table (desired size $1 bytes), disabling bridge'

        Parameters list:
              $1: srt54_requested_size

        There is not enough free memory to allocate the hash table for
        the filtering database. The bridge will be disabled."
    ::= { srtNotificationsPrefix 54 }

srtNotification55 NOTIFICATION-TYPE
    OBJECTS { 
              srt55_requested_size 
            }
    STATUS current
    DESCRIPTION
        "Notification of Event SRT.55

        Message: 'No memory for conversion hash table (desired size $1 bytes), disabling bridge'

        Parameters list:
              $1: srt55_requested_size

        There is not enough free memory to allocate the hash table for
        the conversion database. The bridge will be disabled."
    ::= { srtNotificationsPrefix 55 }

srtNotification56 NOTIFICATION-TYPE
    OBJECTS { 
              srt56_source_mac, 
              srt56_dest_mac,
              srt56_interface,
              srt56_circuit_name 
            }
    STATUS current
    DESCRIPTION
        "Notification of Event SRT.56

        Message: 'Input source-routing queue overflow on frame from $1 to $2, packet dropped from interface $3$4'

        Parameters list:
              $1: srt56_source_mac
              $2: srt56_dest_mac
              $3: srt56_interface
              $4: srt56_circuit_name

        The input queue for source-routed frames to be forwarded is too long,
        and this frame has been dropped to attempt to alleviate the congestion."
    ::= { srtNotificationsPrefix 56 }

srtNotification57 NOTIFICATION-TYPE
    OBJECTS { 
              srt57_source_mac, 
              srt57_dest_mac,
              srt57_port,
              srt57_interface,
              srt57_circuit_name,
              srt57_out_port,
              srt57_out_interface,
              srt57_out_circuit_name 
            }
    STATUS current
    DESCRIPTION
        "Notification of Event SRT.57

        Message: 'Frame from $1 to $2 bridged from port number $3 interface $4$5 to port number $6 interface $7$8'

        Parameters list:
              $1: srt57_source_mac
              $2: srt57_dest_mac
              $3: srt57_port
              $4: srt57_interface
              $5: srt57_circuit_name
              $6: srt57_out_port
              $7: srt57_out_interface
              $8: srt57_out_circuit_name

        A frame is being bridged between these two interfaces.
        The destination address was known, so it was sent only to
        the correct destination network."
    ::= { srtNotificationsPrefix 57 }

srtNotification58 NOTIFICATION-TYPE
    OBJECTS { 
              srt58_source_mac, 
              srt58_dest_mac,
              srt58_reformatted_length,
              srt58_output_maximum,
              srt58_port,
              srt58_interface,
              srt58_circuit_name 
            }
    STATUS current
    DESCRIPTION
        "Notification of Event SRT.58

        Message: 'Transparent frame converted to source-routed frame from $1 to $2 is too big (reformatted length $3 bytes > output maximum size $4 bytes) for port $5 interface $6$7, dropped'

        Parameters list:
              $1: srt58_source_mac
              $2: srt58_dest_mac
              $3: srt58_reformatted_length
              $4: srt58_output_maximum
              $5: srt58_port
              $6: srt58_interface
              $7: srt58_circuit_name

        The specified transparent bridge frame is too large to send as
        a source-routed frame on this outgoing port and interface.
        The reformatted_length is the size of the frame including MAC headers
        and RIF after any mapping of data link headers."
    ::= { srtNotificationsPrefix 58 }

srtNotification59 NOTIFICATION-TYPE
    OBJECTS { 
              srt59_source_mac, 
              srt59_dest_mac,
              srt59_RIF,
              srt59_port,
              srt59_interface,
              srt59_circuit_name,
              srt59_out_port,
              srt59_out_interface,
              srt59_out_circuit_name 
            }
    STATUS current
    DESCRIPTION
        "Notification of Event SRT.59

        Message: 'Transparent frame converted to source-routed frame from $1 to $2 (RIF $3) bridged from port number $4 interface $5$6 to port number $7 interface $8$9'

        Parameters list:
              $1: srt59_source_mac
              $2: srt59_dest_mac
              $3: srt59_RIF
              $4: srt59_port
              $5: srt59_interface
              $6: srt59_circuit_name
              $7: srt59_out_port
              $8: srt59_out_interface
              $9: srt59_out_circuit_name

        A frame is being conversion bridged between these two interfaces.
        The destination address and RIF were known, so it was sent only to
        the correct destination network."
    ::= { srtNotificationsPrefix 59 }

srtNotification60 NOTIFICATION-TYPE
    OBJECTS { 
              srt60_source_mac, 
              srt60_dest_mac,
              srt60_RIF,
              srt60_RIF,
              srt60_port,
              srt60_interface,
              srt60_circuit_name,
              srt60_out_port,
              srt60_out_interface,
              srt60_out_circuit_name 
            }
    STATUS current
    DESCRIPTION
        "Notification of Event SRT.60

        Message: 'Transparent frame converted to source-routed frame from $1 to $2 (RIF $3$4) bridged to all ports from port number $5 interface $6$7 to port number $8 interface $9$10'

        Parameters list:
              $1: srt60_source_mac
              $2: srt60_dest_mac
              $3: srt60_RIF
              $4: srt60_RIF
              $5: srt60_port
              $6: srt60_interface
              $7: srt60_circuit_name
              $8: srt60_out_port
              $9: srt60_out_interface
              $10: srt60_out_circuit_name

        A frame is being conversion bridged to all active source-routing ports.
        This happens when the frame destination is a multicast or when
        the frame destination is not in the source-routing learning database.
        There will be one message for each port the frame is sent on."
    ::= { srtNotificationsPrefix 60 }

srtNotification61 NOTIFICATION-TYPE
    OBJECTS { 
              srt61_source_mac, 
              srt61_dest_mac,
              srt61_RIF,
              srt61_port,
              srt61_interface,
              srt61_circuit_name 
            }
    STATUS current
    DESCRIPTION
        "Notification of Event SRT.61

        Message: 'Specifically routed frame received from $1 to $2 (RIF $3) to disabled port $4, interface $5$6, discarded'

        Parameters list:
              $1: srt61_source_mac
              $2: srt61_dest_mac
              $3: srt61_RIF
              $4: srt61_port
              $5: srt61_interface
              $6: srt61_circuit_name

        A Specifically Routed frame has been received whose RIF would send it
        on the specified port, but that port is not configured for bridging."
    ::= { srtNotificationsPrefix 61 }

srtNotification62 NOTIFICATION-TYPE
    OBJECTS { 
              srt62_source_mac, 
              srt62_dest_mac,
              srt62_reformatted_length,
              srt62_output_maximum,
              srt62_port,
              srt62_interface,
              srt62_circuit_name 
            }
    STATUS current
    DESCRIPTION
        "Notification of Event SRT.62

        Message: 'Source-routed frame converted to transparent frame from $1 to $2 is too big (reformatted length $3 bytes > output maximum size $4 bytes) from port $5 interface $6$7, may get dropped'

        Parameters list:
              $1: srt62_source_mac
              $2: srt62_dest_mac
              $3: srt62_reformatted_length
              $4: srt62_output_maximum
              $5: srt62_port
              $6: srt62_interface
              $7: srt62_circuit_name

        The specified source-routed frame is larger than that is allowed
        by LF-BIT configuration for the transparent bridge domain. After mapping
        to the MAC headers of the outgoing port, the packet may get dropped
        if it exceeds the MSDU limit of the port."
    ::= { srtNotificationsPrefix 62 }

srtNotification63 NOTIFICATION-TYPE
    OBJECTS { 
              srt63_routing_type, 
              srt63_source_mac,
              srt63_dest_mac,
              srt63_port,
              srt63_interface,
              srt63_circuit_name 
            }
    STATUS current
    DESCRIPTION
        "Notification of Event SRT.63

        Message: 'No buffer available to duplicate $1 frame from $2 to $3 for source-routing to transparent bridging conversion from port $4 interface $5$6'

        Parameters list:
              $1: srt63_routing_type
              $2: srt63_source_mac
              $3: srt63_dest_mac
              $4: srt63_port
              $5: srt63_interface
              $6: srt63_circuit_name

        No buffer available to copy a frame in order to send Routes Explorer
        (ARE) or Spanning Tree Explorer (STE) routing_type frame out as
        a transparent bridged frame in the transparent bridging domain.
        No copy of this frame will be sent into the transparent bridge domain."
    ::= { srtNotificationsPrefix 63 }

srtNotification64 NOTIFICATION-TYPE
    OBJECTS { 
              srt64_requested_size 
            }
    STATUS current
    DESCRIPTION
        "Notification of Event SRT.64

        Message: 'No memory for conversion database (desired size $1 bytes), disabling bridge'

        Parameters list:
              $1: srt64_requested_size

        There is not enough free memory to allocate even a minimal size
        conversion database. The bridge will be disabled."
    ::= { srtNotificationsPrefix 64 }

srtNotification65 NOTIFICATION-TYPE
    OBJECTS { 
              srt65_MAC_address, 
              srt65_interface 
            }
    STATUS current
    DESCRIPTION
        "Notification of Event SRT.65

        Message: 'Cannot add static entry for address $1 on interface $2'

        Parameters list:
              $1: srt65_MAC_address
              $2: srt65_interface

        An attempt to add a particular static entry to the internal database of
        a bridging interface having internal filtering failed."
    ::= { srtNotificationsPrefix 65 }

srtNotification66 NOTIFICATION-TYPE
    OBJECTS { 
              srt66_interface, 
              srt66_circuit_name 
            }
    STATUS current
    DESCRIPTION
        "Notification of Event SRT.66

        Message: 'Cannot enable transparent bridging on interface $1$2'

        Parameters list:
              $1: srt66_interface
              $2: srt66_circuit_name

        The bridge has been configured to enable transparent bridging on
        an IEEE 802.5 Token-Ring interface that does not have the hardware
        to support transparent bridging. Transparent bridging will not be
        enabled on this interface."
    ::= { srtNotificationsPrefix 66 }

srtNotification67 NOTIFICATION-TYPE
    OBJECTS { 
              srt67_source_mac, 
              srt67_dest_mac,
              srt67_RIF,
              srt67_port,
              srt67_interface,
              srt67_circuit_name 
            }
    STATUS current
    DESCRIPTION
        "Notification of Event SRT.67

        Message: 'Specifically routed frame frame from $1 to $2 (RIF $3) forwarded to disabled port $4, interface $5$6, discarded'

        Parameters list:
              $1: srt67_source_mac
              $2: srt67_dest_mac
              $3: srt67_RIF
              $4: srt67_port
              $5: srt67_interface
              $6: srt67_circuit_name

        A Specifically Routed frame has been sent on a port, but that port is
        not configured for bridging. This should never happen, since prior
        checks should prevent calling this code if the port is not configured
        for bridging."
    ::= { srtNotificationsPrefix 67 }

srtNotification68 NOTIFICATION-TYPE
    OBJECTS { 
              srt68_ethernet_type 
            }
    STATUS current
    DESCRIPTION
        "Notification of Event SRT.68

        Message: 'Ethernet type table full for Ethernet type $1'

        Parameters list:
              $1: srt68_ethernet_type

        There is no space in the Ethernet type registration table for
        the specified ethernet_type. This happens when there are too many
        hash collisions, and there are not enough overflow buckets."
    ::= { srtNotificationsPrefix 68 }

srtNotification69 NOTIFICATION-TYPE
    OBJECTS { 
              srt69_protocol, 
              srt69_protocol,
              srt69_protocol,
              srt69_protocol,
              srt69_protocol 
            }
    STATUS current
    DESCRIPTION
        "Notification of Event SRT.69

        Message: 'Subnetwork Access Protocol table full for Protocol Identifier type $1-$2-$3-$4-$5'

        Parameters list:
              $1: srt69_protocol
              $2: srt69_protocol
              $3: srt69_protocol
              $4: srt69_protocol
              $5: srt69_protocol

        There is no space in the SNAP PID registration table for
        the specified protocol. This happens when there are too many
        hash collisions, and there are not enough overflow buckets."
    ::= { srtNotificationsPrefix 69 }

srtNotification70 NOTIFICATION-TYPE
    OBJECTS { 
              srt70_source_mac, 
              srt70_dest_mac,
              srt70_port,
              srt70_interface,
              srt70_circuit_name 
            }
    STATUS current
    DESCRIPTION
        "Notification of Event SRT.70

        Message: 'Frame from $1 to $2 dropped, destination address filtered, port $3 interface $4$5'

        Parameters list:
              $1: srt70_source_mac
              $2: srt70_dest_mac
              $3: srt70_port
              $4: srt70_interface
              $5: srt70_circuit_name

        A MAC frame has been received by the hardware, but is being dropped
        because the destination MAC address is being administratively filtered
        by the bridge. The frame will be dropped."
    ::= { srtNotificationsPrefix 70 }

srtNotification71 NOTIFICATION-TYPE
    OBJECTS { 
              srt71_port, 
              srt71_interface,
              srt71_circuit_name 
            }
    STATUS current
    DESCRIPTION
        "Notification of Event SRT.71

        Message: 'Source Routing not supported on port $1, interface $2$3'

        Parameters list:
              $1: srt71_port
              $2: srt71_interface
              $3: srt71_circuit_name

        Source Routing is configured on the port which is attached to an
        underlying network which inherently does not support source routing
        type of functionalities. Such networks are Ethernet and FDDI.
        Bridge disables source routing on the port."
    ::= { srtNotificationsPrefix 71 }

srtNotification72 NOTIFICATION-TYPE
    STATUS current
    DESCRIPTION
        "Notification of Event SRT.72

        Message: 'Conversion bridging (Adaptive or SR-TB) enabled, but not licensed, disabling'

        Conversion bridging has been enabled, but that feature was not purchased
        as part of this software load. The conversion bridging feature will not
        be enabled."
    ::= { srtNotificationsPrefix 72 }

srtNotification73 NOTIFICATION-TYPE
    STATUS current
    DESCRIPTION
        "Notification of Event SRT.73

        Message: 'Source-routing bridging enabled, but not licensed, disabling'

        Source-routing bridging has been enabled, but that feature was not
        purchased as part of this software load. The source-routing bridging
        feature will not be enabled."
    ::= { srtNotificationsPrefix 73 }

srtNotification74 NOTIFICATION-TYPE
    OBJECTS { 
              srt74_interface, 
              srt74_circuit_name 
            }
    STATUS current
    DESCRIPTION
        "Notification of Event SRT.74

        Message: 'Source-routing bridging enabled on interface $1$2, but not licensed, disabling'

        Parameters list:
              $1: srt74_interface
              $2: srt74_circuit_name

        Source-routing bridging has been enabled, but that feature was not
        purchased as part of this software load. The source-routing bridging
        feature will not be enabled."
    ::= { srtNotificationsPrefix 74 }

srtNotification75 NOTIFICATION-TYPE
    OBJECTS { 
              srt75_interface, 
              srt75_circuit_name 
            }
    STATUS current
    DESCRIPTION
        "Notification of Event SRT.75

        Message: 'Spanning tree (transparent) bridging enabled on interface $1$2, but not licensed, disabling'

        Parameters list:
              $1: srt75_interface
              $2: srt75_circuit_name

        Spanning tree (transparent) bridging has been enabled, but that feature
        was not purchased as part of this software load.
        The spanning tree (transparent) bridging feature will not be enabled."
    ::= { srtNotificationsPrefix 75 }

srtNotification76 NOTIFICATION-TYPE
    STATUS current
    DESCRIPTION
        "Notification of Event SRT.76

        Message: 'No memory to allocate a NETBIOS Filter'

        At least one configured NETBIOS Filter will not be enabled, because
        there is not enough memory."
    ::= { srtNotificationsPrefix 76 }

srtNotification77 NOTIFICATION-TYPE
    OBJECTS { 
              srt77_input_output, 
              srt77_port_number 
            }
    STATUS current
    DESCRIPTION
        "Notification of Event SRT.77

        Message: '$1 NETBIOS filter list, for port $2, deleted by user. Filter will not be enabled'

        Parameters list:
              $1: srt77_input_output
              $2: srt77_port_number

        The user deleted a filter list, which was part of an already
        configured filter. The filter will not be enabled."
    ::= { srtNotificationsPrefix 77 }

srtNotification78 NOTIFICATION-TYPE
    OBJECTS { 
              srt78_input_output, 
              srt78_port_number 
            }
    STATUS current
    DESCRIPTION
        "Notification of Event SRT.78

        Message: '$1 NETBIOS filter for port $2 is configured, but that port number is not configured'

        Parameters list:
              $1: srt78_input_output
              $2: srt78_port_number

        The user configured a NETBIOS filter for a particular port, but that
        port number is not configured."
    ::= { srtNotificationsPrefix 78 }

srtNotification79 NOTIFICATION-TYPE
    OBJECTS { 
              srt79_source_mac, 
              srt79_dest_mac,
              srt79_port,
              srt79_interface,
              srt79_circuit_name 
            }
    STATUS current
    DESCRIPTION
        "Notification of Event SRT.79

        Message: 'NETBIOS Output Packet Filtered - $1->$2, port $3, interface $4$5'

        Parameters list:
              $1: srt79_source_mac
              $2: srt79_dest_mac
              $3: srt79_port
              $4: srt79_interface
              $5: srt79_circuit_name

        A NETBIOS packet has matched the criteria specified in a NETBIOS Filter
        configuration record. The packet is dropped."
    ::= { srtNotificationsPrefix 79 }

srtNotification80 NOTIFICATION-TYPE
    STATUS current
    DESCRIPTION
        "Notification of Event SRT.80

        Message: 'No memory to allocate information for NETBIOS Filter console display'

        The part of the router that handles NETBIOS console display cannot
        allocate enough memory to do the complete display. Some part of the
        NETBIOS console display will not be shown from the T 5 process."
    ::= { srtNotificationsPrefix 80 }

srtNotification81 NOTIFICATION-TYPE
    OBJECTS { 
              srt81_RIF, 
              srt81_source_mac,
              srt81_dest_mac,
              srt81_port 
            }
    STATUS current
    DESCRIPTION
        "Notification of Event SRT.81

        Message: 'NETBIOS STE converted to SRF (RIF $1) $2->$3 from port $4'

        Parameters list:
              $1: srt81_RIF
              $2: srt81_source_mac
              $3: srt81_dest_mac
              $4: srt81_port

        A NETBIOS STE converted to SRF by NETBIOS Name Caching."
    ::= { srtNotificationsPrefix 81 }

srtNotification82 NOTIFICATION-TYPE
    STATUS current
    DESCRIPTION
        "Notification of Event SRT.82

        Message: 'NETBIOS STE not converted, RIF too long'

        NETBIOS STE not converted, RIF too long."
    ::= { srtNotificationsPrefix 82 }

srtNotification83 NOTIFICATION-TYPE
    OBJECTS { 
              srt83_RIF, 
              srt83_source_mac,
              srt83_dest_mac,
              srt83_port 
            }
    STATUS current
    DESCRIPTION
        "Notification of Event SRT.83

        Message: 'NETBIOS find-name STE filtered (RIF $1) $2->$3 from port $4'

        Parameters list:
              $1: srt83_RIF
              $2: srt83_source_mac
              $3: srt83_dest_mac
              $4: srt83_port

        A NETBIOS find-name STE has been filtered."
    ::= { srtNotificationsPrefix 83 }

srtNotification84 NOTIFICATION-TYPE
    OBJECTS { 
              srt84_port, 
              srt84_interface 
            }
    STATUS current
    DESCRIPTION
        "Notification of Event SRT.84

        Message: 'BPDU dropped because STP disabled on port $1, interface $2'

        Parameters list:
              $1: srt84_port
              $2: srt84_interface

        A spanning tree BPDU frame was received on a port that has been
        disabled for spanning tree participation by the 'disable tree port#'
        command."
    ::= { srtNotificationsPrefix 84 }

srtNotification85 NOTIFICATION-TYPE
    OBJECTS { 
              srt85_port, 
              srt85_interface_number 
            }
    STATUS current
    DESCRIPTION
        "Notification of Event SRT.85

        Message: 'Frame relay Port $1 configured on non-Frame relay interface $2'

        Parameters list:
              $1: srt85_port
              $2: srt85_interface_number

        The port has been configured to use a Frame Relay interface. However,
        subsequent to bridge configuration, device configuration changed such
        that the device is no longer configured to be a Frame Relay device.
        This could have happened if the user changed the data link support
        on the device, or re-ordered the device records."
    ::= { srtNotificationsPrefix 85 }

srtNotification86 NOTIFICATION-TYPE
    OBJECTS { 
              srt86_port, 
              srt86_circuit_name,
              srt86_interface,
              srt86_reason 
            }
    STATUS current
    DESCRIPTION
        "Notification of Event SRT.86

        Message: 'Bridge port $1 with circuit=$2 registration with interface $3 failed, reason=$4'

        Parameters list:
              $1: srt86_port
              $2: srt86_circuit_name
              $3: srt86_interface
              $4: srt86_reason

        During bridge initialization, ports are associated with Frame Relay
        registers with the Frame Relay interface. During registration, both let
        each other know about their existence and exchange some
        useful information to keep about each other."
    ::= { srtNotificationsPrefix 86 }

srtNotification87 NOTIFICATION-TYPE
    OBJECTS { 
              srt87_source_mac, 
              srt87_dest_mac,
              srt87_port,
              srt87_interface,
              srt87_circuit_name 
            }
    STATUS current
    DESCRIPTION
        "Notification of Event SRT.87

        Message: 'All Routes Explorer exceeds maximum Route Descriptors from $1 to $2 from port $3, interface $4$5'

        Parameters list:
              $1: srt87_source_mac
              $2: srt87_dest_mac
              $3: srt87_port
              $4: srt87_interface
              $5: srt87_circuit_name

        An All Routes Explorer (ARE) source-routed frame has more
        Route Descriptors than this bridge is configured to allow for
        ARE frames.
        The frame will be dropped."
    ::= { srtNotificationsPrefix 87 }

srtNotification88 NOTIFICATION-TYPE
    STATUS current
    DESCRIPTION
        "Notification of Event SRT.88

        Message: 'Cannot autoconfigure the bridge address, there is no available MAC address'

        The user has configured the bridge to autoconfigure the bridge address.
        However, there is no port with a configured MAC address and it is no
        possible to get one from BIOS."
    ::= { srtNotificationsPrefix 88 }

srtNotification89 NOTIFICATION-TYPE
    OBJECTS { 
              srt89_source_mac, 
              srt89_dest_mac,
              srt89_port,
              srt89_interface,
              srt89_circuit_name,
              srt89_out_port,
              srt89_out_interface,
              srt89_out_circuit_name 
            }
    STATUS current
    DESCRIPTION
        "Notification of Event SRT.89

        Message: 'Frame from $1 to $2 bridged from port number $3 interface $4$5 to port number $6 interface $7$8'

        Parameters list:
              $1: srt89_source_mac
              $2: srt89_dest_mac
              $3: srt89_port
              $4: srt89_interface
              $5: srt89_circuit_name
              $6: srt89_out_port
              $7: srt89_out_interface
              $8: srt89_out_circuit_name

        A frame is being bridged between these two interfaces. The destination
        address was broadcast or unregistered."
    ::= { srtNotificationsPrefix 89 }

srtNotification90 NOTIFICATION-TYPE
    OBJECTS { 
              srt90_source_mac, 
              srt90_dest_mac,
              srt90_vid 
            }
    STATUS current
    DESCRIPTION
        "Notification of Event SRT.90

        Message: 'Frame from $1 to $2 for vlan $3 not bridged because vlan bridging is disabled'

        Parameters list:
              $1: srt90_source_mac
              $2: srt90_dest_mac
              $3: srt90_vid

        A VLAN tagged frame on a ethernet subinterface was received but bridging 
        is disabled for vlans.
        The frame will not be bridged."
    ::= { srtNotificationsPrefix 90 }


END
