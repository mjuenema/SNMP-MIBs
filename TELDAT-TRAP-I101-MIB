-- file automatically created


TELDAT-TRAP-I101-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


i101TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the I101 event subsystem."
    REVISION "201401200930Z"
    DESCRIPTION "Initial implementation"
        ::= { telEventTraps 229 }


i101EventsGroup	OBJECT IDENTIFIER	::= { i101TrapsMIB 1 }

i101Notifications	OBJECT IDENTIFIER	::= { i101TrapsMIB 2 }
i101NotificationsPrefix	OBJECT IDENTIFIER	::= { i101Notifications 0 }

i101EventObjects1 OBJECT-IDENTITY
    STATUS current
    DESCRIPTION
        "Event I101.1
        Data has been received from Serial Terminal."
    ::= { i101EventsGroup 1 }

i1011_bytes_number OBJECT-TYPE
    SYNTAX Integer32
    MAX-ACCESS accessible-for-notify
    STATUS current
    DESCRIPTION
        "Parameter 'bytes_number' in event I101.1"
    ::= { i101EventObjects1 1 }

i1011_interface OBJECT-TYPE
    SYNTAX DisplayString
    MAX-ACCESS accessible-for-notify
    STATUS current
    DESCRIPTION
        "Parameter 'interface' in event I101.1"
    ::= { i101EventObjects1 2 }

i101EventObjects2 OBJECT-IDENTITY
    STATUS current
    DESCRIPTION
        "Event I101.2
        One OK Message has been received from Serial Terminal."
    ::= { i101EventsGroup 2 }

i1012_coment OBJECT-TYPE
    SYNTAX DisplayString
    MAX-ACCESS accessible-for-notify
    STATUS current
    DESCRIPTION
        "Parameter 'coment' in event I101.2"
    ::= { i101EventObjects2 1 }

i1012_serrial_address OBJECT-TYPE
    SYNTAX Integer32
    MAX-ACCESS accessible-for-notify
    STATUS current
    DESCRIPTION
        "Parameter 'serrial_address' in event I101.2"
    ::= { i101EventObjects2 2 }

i1012_bytes_number OBJECT-TYPE
    SYNTAX Integer32
    MAX-ACCESS accessible-for-notify
    STATUS current
    DESCRIPTION
        "Parameter 'bytes_number' in event I101.2"
    ::= { i101EventObjects2 3 }

i1012_interface OBJECT-TYPE
    SYNTAX DisplayString
    MAX-ACCESS accessible-for-notify
    STATUS current
    DESCRIPTION
        "Parameter 'interface' in event I101.2"
    ::= { i101EventObjects2 4 }

i101EventObjects3 OBJECT-IDENTITY
    STATUS current
    DESCRIPTION
        "Event I101.3
        One Bad Message has been received from Serial Terminal."
    ::= { i101EventsGroup 3 }

i1013_cause OBJECT-TYPE
    SYNTAX DisplayString
    MAX-ACCESS accessible-for-notify
    STATUS current
    DESCRIPTION
        "Parameter 'cause' in event I101.3"
    ::= { i101EventObjects3 1 }

i1013_interface OBJECT-TYPE
    SYNTAX DisplayString
    MAX-ACCESS accessible-for-notify
    STATUS current
    DESCRIPTION
        "Parameter 'interface' in event I101.3"
    ::= { i101EventObjects3 2 }

i101EventObjects4 OBJECT-IDENTITY
    STATUS current
    DESCRIPTION
        "Event I101.4
        A message with LRC/CRC error has been received from Serial Terminal."
    ::= { i101EventsGroup 4 }

i1014_interface OBJECT-TYPE
    SYNTAX DisplayString
    MAX-ACCESS accessible-for-notify
    STATUS current
    DESCRIPTION
        "Parameter 'interface' in event I101.4"
    ::= { i101EventObjects4 1 }

i101EventObjects5 OBJECT-IDENTITY
    STATUS current
    DESCRIPTION
        "Event I101.5
        A Message has been transmitted to Serial Terminal."
    ::= { i101EventsGroup 5 }

i1015_bytes OBJECT-TYPE
    SYNTAX Integer32
    MAX-ACCESS accessible-for-notify
    STATUS current
    DESCRIPTION
        "Parameter 'bytes' in event I101.5"
    ::= { i101EventObjects5 1 }

i1015_interface OBJECT-TYPE
    SYNTAX DisplayString
    MAX-ACCESS accessible-for-notify
    STATUS current
    DESCRIPTION
        "Parameter 'interface' in event I101.5"
    ::= { i101EventObjects5 2 }

i101EventObjects6 OBJECT-IDENTITY
    STATUS current
    DESCRIPTION
        "Event I101.6
        A change ON/OFF has been detected in Serial Control Signal Input."
    ::= { i101EventsGroup 6 }

i1016_message_type OBJECT-TYPE
    SYNTAX DisplayString
    MAX-ACCESS accessible-for-notify
    STATUS current
    DESCRIPTION
        "Parameter 'message_type' in event I101.6"
    ::= { i101EventObjects6 1 }

i1016_interface OBJECT-TYPE
    SYNTAX DisplayString
    MAX-ACCESS accessible-for-notify
    STATUS current
    DESCRIPTION
        "Parameter 'interface' in event I101.6"
    ::= { i101EventObjects6 2 }

i101EventObjects7 OBJECT-IDENTITY
    STATUS current
    DESCRIPTION
        "Event I101.7
        A change ON/OFF has been make in Serial Control Signal Output."
    ::= { i101EventsGroup 7 }

i1017_message_type OBJECT-TYPE
    SYNTAX DisplayString
    MAX-ACCESS accessible-for-notify
    STATUS current
    DESCRIPTION
        "Parameter 'message_type' in event I101.7"
    ::= { i101EventObjects7 1 }

i1017_interface OBJECT-TYPE
    SYNTAX DisplayString
    MAX-ACCESS accessible-for-notify
    STATUS current
    DESCRIPTION
        "Parameter 'interface' in event I101.7"
    ::= { i101EventObjects7 2 }

i101EventObjects8 OBJECT-IDENTITY
    STATUS current
    DESCRIPTION
        "Event I101.8
        Data error from Serial Terminal has been received."
    ::= { i101EventsGroup 8 }

i1018_message_type OBJECT-TYPE
    SYNTAX DisplayString
    MAX-ACCESS accessible-for-notify
    STATUS current
    DESCRIPTION
        "Parameter 'message_type' in event I101.8"
    ::= { i101EventObjects8 1 }

i1018_interface OBJECT-TYPE
    SYNTAX DisplayString
    MAX-ACCESS accessible-for-notify
    STATUS current
    DESCRIPTION
        "Parameter 'interface' in event I101.8"
    ::= { i101EventObjects8 2 }

i101EventObjects9 OBJECT-IDENTITY
    STATUS current
    DESCRIPTION
        "Event I101.9
        Detailed Data send to serial interface."
    ::= { i101EventsGroup 9 }

i1019_interface OBJECT-TYPE
    SYNTAX DisplayString
    MAX-ACCESS accessible-for-notify
    STATUS current
    DESCRIPTION
        "Parameter 'interface' in event I101.9"
    ::= { i101EventObjects9 1 }

i1019_serial_address OBJECT-TYPE
    SYNTAX Integer32
    MAX-ACCESS accessible-for-notify
    STATUS current
    DESCRIPTION
        "Parameter 'serial_address' in event I101.9"
    ::= { i101EventObjects9 2 }

i1019_lenght OBJECT-TYPE
    SYNTAX Integer32
    MAX-ACCESS accessible-for-notify
    STATUS current
    DESCRIPTION
        "Parameter 'lenght' in event I101.9"
    ::= { i101EventObjects9 3 }

i1019_hex_data OBJECT-TYPE
    SYNTAX DisplayString
    MAX-ACCESS accessible-for-notify
    STATUS current
    DESCRIPTION
        "Parameter 'hex_data' in event I101.9"
    ::= { i101EventObjects9 4 }

i101EventObjects10 OBJECT-IDENTITY
    STATUS current
    DESCRIPTION
        "Event I101.10
        Detailed Data received from serial interface."
    ::= { i101EventsGroup 10 }

i10110_interface OBJECT-TYPE
    SYNTAX DisplayString
    MAX-ACCESS accessible-for-notify
    STATUS current
    DESCRIPTION
        "Parameter 'interface' in event I101.10"
    ::= { i101EventObjects10 1 }

i10110_serial_address OBJECT-TYPE
    SYNTAX Integer32
    MAX-ACCESS accessible-for-notify
    STATUS current
    DESCRIPTION
        "Parameter 'serial_address' in event I101.10"
    ::= { i101EventObjects10 2 }

i10110_lenght OBJECT-TYPE
    SYNTAX Integer32
    MAX-ACCESS accessible-for-notify
    STATUS current
    DESCRIPTION
        "Parameter 'lenght' in event I101.10"
    ::= { i101EventObjects10 3 }

i10110_hex_data OBJECT-TYPE
    SYNTAX DisplayString
    MAX-ACCESS accessible-for-notify
    STATUS current
    DESCRIPTION
        "Parameter 'hex_data' in event I101.10"
    ::= { i101EventObjects10 4 }

i101EventObjects11 OBJECT-IDENTITY
    STATUS current
    DESCRIPTION
        "Event I101.11
        A status change has occurred on RTU."
    ::= { i101EventsGroup 11 }

i10111_rtu OBJECT-TYPE
    SYNTAX DisplayString
    MAX-ACCESS accessible-for-notify
    STATUS current
    DESCRIPTION
        "Parameter 'rtu' in event I101.11"
    ::= { i101EventObjects11 1 }

i10111_statsu OBJECT-TYPE
    SYNTAX DisplayString
    MAX-ACCESS accessible-for-notify
    STATUS current
    DESCRIPTION
        "Parameter 'statsu' in event I101.11"
    ::= { i101EventObjects11 2 }

i101EventObjects12 OBJECT-IDENTITY
    STATUS current
    DESCRIPTION
        "Event I101.12
        Tx data discarted due interface is in down state."
    ::= { i101EventsGroup 12 }

i10112_interface OBJECT-TYPE
    SYNTAX DisplayString
    MAX-ACCESS accessible-for-notify
    STATUS current
    DESCRIPTION
        "Parameter 'interface' in event I101.12"
    ::= { i101EventObjects12 1 }


i101Notification1 NOTIFICATION-TYPE
    OBJECTS { 
              i1011_bytes_number, 
              i1011_interface 
            }
    STATUS current
    DESCRIPTION
        "Notification of Event I101.1

        Message: 'Rx Data from Serial Terminal $1 bytes, interface $2'

        Parameters list:
              $1: i1011_bytes_number
              $2: i1011_interface

        Data has been received from Serial Terminal."
    ::= { i101NotificationsPrefix 1 }

i101Notification2 NOTIFICATION-TYPE
    OBJECTS { 
              i1012_coment, 
              i1012_serrial_address,
              i1012_bytes_number,
              i1012_interface 
            }
    STATUS current
    DESCRIPTION
        "Notification of Event I101.2

        Message: 'Rx Message $1 from Serial Terminal address $2, $3 bytes, interface $4'

        Parameters list:
              $1: i1012_coment
              $2: i1012_serrial_address
              $3: i1012_bytes_number
              $4: i1012_interface

        One OK Message has been received from Serial Terminal."
    ::= { i101NotificationsPrefix 2 }

i101Notification3 NOTIFICATION-TYPE
    OBJECTS { 
              i1013_cause, 
              i1013_interface 
            }
    STATUS current
    DESCRIPTION
        "Notification of Event I101.3

        Message: 'Rx Bad Message from Serial Terminal ($1), interface $2'

        Parameters list:
              $1: i1013_cause
              $2: i1013_interface

        One Bad Message has been received from Serial Terminal."
    ::= { i101NotificationsPrefix 3 }

i101Notification4 NOTIFICATION-TYPE
    OBJECTS { 
              i1014_interface 
            }
    STATUS current
    DESCRIPTION
        "Notification of Event I101.4

        Message: 'A block with LRC/CRC error has been received from Serial Terminal, interface $1'

        Parameters list:
              $1: i1014_interface

        A message with LRC/CRC error has been received from Serial Terminal."
    ::= { i101NotificationsPrefix 4 }

i101Notification5 NOTIFICATION-TYPE
    OBJECTS { 
              i1015_bytes, 
              i1015_interface 
            }
    STATUS current
    DESCRIPTION
        "Notification of Event I101.5

        Message: 'Tx Message to Serial Terminal, $1 bytes interface $2'

        Parameters list:
              $1: i1015_bytes
              $2: i1015_interface

        A Message has been transmitted to Serial Terminal."
    ::= { i101NotificationsPrefix 5 }

i101Notification6 NOTIFICATION-TYPE
    OBJECTS { 
              i1016_message_type, 
              i1016_interface 
            }
    STATUS current
    DESCRIPTION
        "Notification of Event I101.6

        Message: 'Serial Control Signal Imput CD change to $1, interface $2'

        Parameters list:
              $1: i1016_message_type
              $2: i1016_interface

        A change ON/OFF has been detected in Serial Control Signal Input."
    ::= { i101NotificationsPrefix 6 }

i101Notification7 NOTIFICATION-TYPE
    OBJECTS { 
              i1017_message_type, 
              i1017_interface 
            }
    STATUS current
    DESCRIPTION
        "Notification of Event I101.7

        Message: 'Serial Control signal Output DTR change to $1, interface $2'

        Parameters list:
              $1: i1017_message_type
              $2: i1017_interface

        A change ON/OFF has been make in Serial Control Signal Output."
    ::= { i101NotificationsPrefix 7 }

i101Notification8 NOTIFICATION-TYPE
    OBJECTS { 
              i1018_message_type, 
              i1018_interface 
            }
    STATUS current
    DESCRIPTION
        "Notification of Event I101.8

        Message: 'Data ERROR from Serial Terminal has been received type: $1. Interface $2'

        Parameters list:
              $1: i1018_message_type
              $2: i1018_interface

        Data error from Serial Terminal has been received."
    ::= { i101NotificationsPrefix 8 }

i101Notification9 NOTIFICATION-TYPE
    OBJECTS { 
              i1019_interface, 
              i1019_serial_address,
              i1019_lenght,
              i1019_hex_data 
            }
    STATUS current
    DESCRIPTION
        "Notification of Event I101.9

        Message: 'Data transmitted to serial interface $1 (addr:$2,$3 bytes):$4'

        Parameters list:
              $1: i1019_interface
              $2: i1019_serial_address
              $3: i1019_lenght
              $4: i1019_hex_data

        Detailed Data send to serial interface."
    ::= { i101NotificationsPrefix 9 }

i101Notification10 NOTIFICATION-TYPE
    OBJECTS { 
              i10110_interface, 
              i10110_serial_address,
              i10110_lenght,
              i10110_hex_data 
            }
    STATUS current
    DESCRIPTION
        "Notification of Event I101.10

        Message: 'Data received from serial interface $1 (addr:$2,$3 bytes):$4'

        Parameters list:
              $1: i10110_interface
              $2: i10110_serial_address
              $3: i10110_lenght
              $4: i10110_hex_data

        Detailed Data received from serial interface."
    ::= { i101NotificationsPrefix 10 }

i101Notification11 NOTIFICATION-TYPE
    OBJECTS { 
              i10111_rtu, 
              i10111_statsu 
            }
    STATUS current
    DESCRIPTION
        "Notification of Event I101.11

        Message: 'RTU $1 link status change to $2'

        Parameters list:
              $1: i10111_rtu
              $2: i10111_statsu

        A status change has occurred on RTU."
    ::= { i101NotificationsPrefix 11 }

i101Notification12 NOTIFICATION-TYPE
    OBJECTS { 
              i10112_interface 
            }
    STATUS current
    DESCRIPTION
        "Notification of Event I101.12

        Message: 'Data transmitted is discarted since interface $1 is down'

        Parameters list:
              $1: i10112_interface

        Tx data discarted due interface is in down state."
    ::= { i101NotificationsPrefix 12 }


END
