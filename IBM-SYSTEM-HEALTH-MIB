IBM-SYSTEM-HEALTH-MIB DEFINITIONS ::= BEGIN

IMPORTS
   OBJECT-TYPE
      FROM RFC-1212

   TRAP-TYPE
      FROM RFC-1215

   ibmSystemHealth,
   Boolean, Uint8, Sint8, Uint16, Sint16, Uint32,
   Sint32, Uint64, Sint64, Real32, Real64, String, Datetime
      FROM IBM-SYSTEM-MIB;



--
-- Primitive types
--
Boolean  ::= INTEGER (0..1)
Uint8    ::= INTEGER (0..255)
Sint8    ::= INTEGER (-128..127)
Uint16   ::= INTEGER (0..65535)
Sint16   ::= INTEGER (-32767..32766)
Uint32   ::= INTEGER (0..4294967295)
Sint32   ::= INTEGER (-2147483647..2147483646)
Uint64   ::= OCTET STRING
Sint64   ::= OCTET STRING
Real32   ::= INTEGER (-1..1)
Real64   ::= INTEGER (-1..1)
String   ::= OCTET STRING
Datetime ::= OCTET STRING

ibmSystemComponentHealthTable OBJECT-TYPE
   SYNTAX         SEQUENCE OF IbmSystemComponentHealthEntry
   ACCESS         not-accessible
   STATUS         mandatory
   DESCRIPTION    ""
   REFERENCE      "IBMPSG_ComponentHealth"
::= { ibmSystemHealth 3 }

ibmSystemComponentHealthEntry OBJECT-TYPE
   SYNTAX         IbmSystemComponentHealthEntry
   ACCESS         not-accessible
   STATUS         mandatory
   DESCRIPTION    ""
   INDEX          { ibmSystemComponentHealthKeyIndex }
::= { ibmSystemComponentHealthTable 1 }

IbmSystemComponentHealthEntry ::= SEQUENCE
{
   ibmSystemComponentHealthKeyIndex String,
   ibmSystemComponentHealthCurrentState Uint16,
   ibmSystemComponentHealthLastState Uint16,
   ibmSystemComponentHealthDateTime Datetime,
   ibmSystemComponentHealthLastUpdate Datetime,
   ibmSystemComponentHealthDescription String,
   ibmSystemComponentHealthEventCategory String,
   ibmSystemComponentHealthResolution String,
   ibmSystemComponentHealthEventID String,
   ibmSystemComponentHealthAlertingManagedElement String,
   ibmSystemComponentHealthStatus String
}

ibmSystemComponentHealthKeyIndex OBJECT-TYPE
   SYNTAX         String
   ACCESS         read-only
   STATUS         mandatory
   DESCRIPTION    ""
   REFERENCE      "IBMPSG_ComponentHealth.KeyIndex"
::= { ibmSystemComponentHealthEntry 1 }

ibmSystemComponentHealthCurrentState OBJECT-TYPE
   SYNTAX         Uint16
   ACCESS         read-only
   STATUS         mandatory
   DESCRIPTION    ""
   REFERENCE      "IBMPSG_ComponentHealth.CurrentState"
::= { ibmSystemComponentHealthEntry 2 }

ibmSystemComponentHealthLastState OBJECT-TYPE
   SYNTAX         Uint16
   ACCESS         read-only
   STATUS         mandatory
   DESCRIPTION    ""
   REFERENCE      "IBMPSG_ComponentHealth.LastState"
::= { ibmSystemComponentHealthEntry 3 }

ibmSystemComponentHealthDateTime OBJECT-TYPE
   SYNTAX         Datetime
   ACCESS         read-write
   STATUS         mandatory
   DESCRIPTION    ""
   REFERENCE      "IBMPSG_ComponentHealth.DateTime"
::= { ibmSystemComponentHealthEntry 4 }

ibmSystemComponentHealthLastUpdate OBJECT-TYPE
   SYNTAX         Datetime
   ACCESS         read-write
   STATUS         mandatory
   DESCRIPTION    ""
   REFERENCE      "IBMPSG_ComponentHealth.LastUpdate"
::= { ibmSystemComponentHealthEntry 5 }

ibmSystemComponentHealthDescription OBJECT-TYPE
   SYNTAX         String
   ACCESS         read-write
   STATUS         mandatory
   DESCRIPTION    ""
   REFERENCE      "IBMPSG_ComponentHealth.Description"
::= { ibmSystemComponentHealthEntry 6 }

ibmSystemComponentHealthEventCategory OBJECT-TYPE
   SYNTAX         String
   ACCESS         read-write
   STATUS         mandatory
   DESCRIPTION    ""
   REFERENCE      "IBMPSG_ComponentHealth.EventCategory"
::= { ibmSystemComponentHealthEntry 7 }

ibmSystemComponentHealthResolution OBJECT-TYPE
   SYNTAX         String
   ACCESS         read-write
   STATUS         mandatory
   DESCRIPTION    ""
   REFERENCE      "IBMPSG_ComponentHealth.Resolution"
::= { ibmSystemComponentHealthEntry 8 }

ibmSystemComponentHealthEventID OBJECT-TYPE
   SYNTAX         String
   ACCESS         read-write
   STATUS         mandatory
   DESCRIPTION    ""
   REFERENCE      "IBMPSG_ComponentHealth.EventID"
::= { ibmSystemComponentHealthEntry 9 }

ibmSystemComponentHealthAlertingManagedElement OBJECT-TYPE
   SYNTAX         String
   ACCESS         read-write
   STATUS         mandatory
   DESCRIPTION    ""
   REFERENCE      "IBMPSG_ComponentHealth.AlertingManagedElement"
::= { ibmSystemComponentHealthEntry 10 }

ibmSystemComponentHealthStatus OBJECT-TYPE
   SYNTAX         String
   ACCESS         read-write
   STATUS         mandatory
   DESCRIPTION    ""
   REFERENCE      "IBMPSG_ComponentHealth.Status"
::= { ibmSystemComponentHealthEntry 11 }

END
