-- file automatically created


TELDAT-TRAP-WLAN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


wlanTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the WLAN event subsystem."
    REVISION "201401200930Z"
    DESCRIPTION "Initial implementation"
        ::= { telEventTraps 188 }


wlanEventsGroup	OBJECT IDENTIFIER	::= { wlanTrapsMIB 1 }

wlanNotifications	OBJECT IDENTIFIER	::= { wlanTrapsMIB 2 }
wlanNotificationsPrefix	OBJECT IDENTIFIER	::= { wlanNotifications 0 }

wlanEventObjects1 OBJECT-IDENTITY
    STATUS current
    DESCRIPTION
        "Event WLAN.1
        Generic informational event."
    ::= { wlanEventsGroup 1 }

wlan1_string OBJECT-TYPE
    SYNTAX DisplayString
    MAX-ACCESS accessible-for-notify
    STATUS current
    DESCRIPTION
        "Parameter 'string' in event WLAN.1"
    ::= { wlanEventObjects1 1 }

wlanEventObjects2 OBJECT-IDENTITY
    STATUS current
    DESCRIPTION
        "Event WLAN.2
        MLME Transmit Event."
    ::= { wlanEventsGroup 2 }

wlan2_subtype OBJECT-TYPE
    SYNTAX DisplayString
    MAX-ACCESS accessible-for-notify
    STATUS current
    DESCRIPTION
        "Parameter 'subtype' in event WLAN.2"
    ::= { wlanEventObjects2 1 }

wlan2_result OBJECT-TYPE
    SYNTAX DisplayString
    MAX-ACCESS accessible-for-notify
    STATUS current
    DESCRIPTION
        "Parameter 'result' in event WLAN.2"
    ::= { wlanEventObjects2 2 }

wlan2_mac_address OBJECT-TYPE
    SYNTAX DisplayString
    MAX-ACCESS accessible-for-notify
    STATUS current
    DESCRIPTION
        "Parameter 'mac_address' in event WLAN.2"
    ::= { wlanEventObjects2 3 }

wlan2_ifc OBJECT-TYPE
    SYNTAX DisplayString
    MAX-ACCESS accessible-for-notify
    STATUS current
    DESCRIPTION
        "Parameter 'ifc' in event WLAN.2"
    ::= { wlanEventObjects2 4 }

wlanEventObjects3 OBJECT-IDENTITY
    STATUS current
    DESCRIPTION
        "Event WLAN.3
        MLME Receive Event."
    ::= { wlanEventsGroup 3 }

wlan3_subtype OBJECT-TYPE
    SYNTAX DisplayString
    MAX-ACCESS accessible-for-notify
    STATUS current
    DESCRIPTION
        "Parameter 'subtype' in event WLAN.3"
    ::= { wlanEventObjects3 1 }

wlan3_mac_address OBJECT-TYPE
    SYNTAX DisplayString
    MAX-ACCESS accessible-for-notify
    STATUS current
    DESCRIPTION
        "Parameter 'mac_address' in event WLAN.3"
    ::= { wlanEventObjects3 2 }

wlan3_ifc OBJECT-TYPE
    SYNTAX DisplayString
    MAX-ACCESS accessible-for-notify
    STATUS current
    DESCRIPTION
        "Parameter 'ifc' in event WLAN.3"
    ::= { wlanEventObjects3 3 }

wlanEventObjects4 OBJECT-IDENTITY
    STATUS current
    DESCRIPTION
        "Event WLAN.4
        Beacon frame received."
    ::= { wlanEventsGroup 4 }

wlan4_mac_address OBJECT-TYPE
    SYNTAX DisplayString
    MAX-ACCESS accessible-for-notify
    STATUS current
    DESCRIPTION
        "Parameter 'mac_address' in event WLAN.4"
    ::= { wlanEventObjects4 1 }

wlan4_channel OBJECT-TYPE
    SYNTAX Integer32
    MAX-ACCESS accessible-for-notify
    STATUS current
    DESCRIPTION
        "Parameter 'channel' in event WLAN.4"
    ::= { wlanEventObjects4 2 }

wlan4_transState OBJECT-TYPE
    SYNTAX Integer32
    MAX-ACCESS accessible-for-notify
    STATUS current
    DESCRIPTION
        "Parameter 'transState' in event WLAN.4"
    ::= { wlanEventObjects4 3 }

wlan4_rssi OBJECT-TYPE
    SYNTAX Integer32
    MAX-ACCESS accessible-for-notify
    STATUS current
    DESCRIPTION
        "Parameter 'rssi' in event WLAN.4"
    ::= { wlanEventObjects4 4 }

wlanEventObjects5 OBJECT-IDENTITY
    STATUS current
    DESCRIPTION
        "Event WLAN.5
        Station PTK state machine."
    ::= { wlanEventsGroup 5 }

wlan5_state_machine OBJECT-TYPE
    SYNTAX DisplayString
    MAX-ACCESS accessible-for-notify
    STATUS current
    DESCRIPTION
        "Parameter 'state_machine' in event WLAN.5"
    ::= { wlanEventObjects5 1 }

wlan5_state OBJECT-TYPE
    SYNTAX DisplayString
    MAX-ACCESS accessible-for-notify
    STATUS current
    DESCRIPTION
        "Parameter 'state' in event WLAN.5"
    ::= { wlanEventObjects5 2 }

wlan5_interface OBJECT-TYPE
    SYNTAX DisplayString
    MAX-ACCESS accessible-for-notify
    STATUS current
    DESCRIPTION
        "Parameter 'interface' in event WLAN.5"
    ::= { wlanEventObjects5 3 }

wlan5_aid OBJECT-TYPE
    SYNTAX Integer32
    MAX-ACCESS accessible-for-notify
    STATUS current
    DESCRIPTION
        "Parameter 'aid' in event WLAN.5"
    ::= { wlanEventObjects5 4 }

wlanEventObjects6 OBJECT-IDENTITY
    STATUS current
    DESCRIPTION
        "Event WLAN.6
        Station GTK state machine."
    ::= { wlanEventsGroup 6 }

wlan6_state_machine OBJECT-TYPE
    SYNTAX DisplayString
    MAX-ACCESS accessible-for-notify
    STATUS current
    DESCRIPTION
        "Parameter 'state_machine' in event WLAN.6"
    ::= { wlanEventObjects6 1 }

wlan6_state OBJECT-TYPE
    SYNTAX DisplayString
    MAX-ACCESS accessible-for-notify
    STATUS current
    DESCRIPTION
        "Parameter 'state' in event WLAN.6"
    ::= { wlanEventObjects6 2 }

wlan6_interface OBJECT-TYPE
    SYNTAX DisplayString
    MAX-ACCESS accessible-for-notify
    STATUS current
    DESCRIPTION
        "Parameter 'interface' in event WLAN.6"
    ::= { wlanEventObjects6 3 }

wlan6_aid OBJECT-TYPE
    SYNTAX Integer32
    MAX-ACCESS accessible-for-notify
    STATUS current
    DESCRIPTION
        "Parameter 'aid' in event WLAN.6"
    ::= { wlanEventObjects6 4 }

wlanEventObjects7 OBJECT-IDENTITY
    STATUS current
    DESCRIPTION
        "Event WLAN.7
        Global GTK state machine."
    ::= { wlanEventsGroup 7 }

wlan7_state_machine OBJECT-TYPE
    SYNTAX DisplayString
    MAX-ACCESS accessible-for-notify
    STATUS current
    DESCRIPTION
        "Parameter 'state_machine' in event WLAN.7"
    ::= { wlanEventObjects7 1 }

wlan7_state OBJECT-TYPE
    SYNTAX DisplayString
    MAX-ACCESS accessible-for-notify
    STATUS current
    DESCRIPTION
        "Parameter 'state' in event WLAN.7"
    ::= { wlanEventObjects7 2 }

wlan7_interface OBJECT-TYPE
    SYNTAX DisplayString
    MAX-ACCESS accessible-for-notify
    STATUS current
    DESCRIPTION
        "Parameter 'interface' in event WLAN.7"
    ::= { wlanEventObjects7 3 }

wlanEventObjects8 OBJECT-IDENTITY
    STATUS current
    DESCRIPTION
        "Event WLAN.8
        Generic WLAN application informational event."
    ::= { wlanEventsGroup 8 }

wlan8_string OBJECT-TYPE
    SYNTAX DisplayString
    MAX-ACCESS accessible-for-notify
    STATUS current
    DESCRIPTION
        "Parameter 'string' in event WLAN.8"
    ::= { wlanEventObjects8 1 }

wlanEventObjects9 OBJECT-IDENTITY
    STATUS current
    DESCRIPTION
        "Event WLAN.9
        Supplicant key management state machine."
    ::= { wlanEventsGroup 9 }

wlan9_state_machine OBJECT-TYPE
    SYNTAX DisplayString
    MAX-ACCESS accessible-for-notify
    STATUS current
    DESCRIPTION
        "Parameter 'state_machine' in event WLAN.9"
    ::= { wlanEventObjects9 1 }

wlan9_state OBJECT-TYPE
    SYNTAX DisplayString
    MAX-ACCESS accessible-for-notify
    STATUS current
    DESCRIPTION
        "Parameter 'state' in event WLAN.9"
    ::= { wlanEventObjects9 2 }

wlan9_interface OBJECT-TYPE
    SYNTAX DisplayString
    MAX-ACCESS accessible-for-notify
    STATUS current
    DESCRIPTION
        "Parameter 'interface' in event WLAN.9"
    ::= { wlanEventObjects9 3 }

wlanEventObjects10 OBJECT-IDENTITY
    STATUS current
    DESCRIPTION
        "Event WLAN.10
        A WLAN multicast packet was received and it was discarded because
        it did not match registered multicast addresses on interface."
    ::= { wlanEventsGroup 10 }

wlan10_source_WLAN_address OBJECT-TYPE
    SYNTAX DisplayString
    MAX-ACCESS accessible-for-notify
    STATUS current
    DESCRIPTION
        "Parameter 'source_WLAN_address' in event WLAN.10"
    ::= { wlanEventObjects10 1 }

wlan10_destination_WLAN_address OBJECT-TYPE
    SYNTAX DisplayString
    MAX-ACCESS accessible-for-notify
    STATUS current
    DESCRIPTION
        "Parameter 'destination_WLAN_address' in event WLAN.10"
    ::= { wlanEventObjects10 2 }

wlan10_interface OBJECT-TYPE
    SYNTAX DisplayString
    MAX-ACCESS accessible-for-notify
    STATUS current
    DESCRIPTION
        "Parameter 'interface' in event WLAN.10"
    ::= { wlanEventObjects10 3 }

wlanEventObjects11 OBJECT-IDENTITY
    STATUS current
    DESCRIPTION
        "Event WLAN.11
        A WLAN unicast packet was received and it was discarded because
        it did not match local unicast addresses."
    ::= { wlanEventsGroup 11 }

wlan11_source_WLAN_address OBJECT-TYPE
    SYNTAX DisplayString
    MAX-ACCESS accessible-for-notify
    STATUS current
    DESCRIPTION
        "Parameter 'source_WLAN_address' in event WLAN.11"
    ::= { wlanEventObjects11 1 }

wlan11_destination_WLAN_address OBJECT-TYPE
    SYNTAX DisplayString
    MAX-ACCESS accessible-for-notify
    STATUS current
    DESCRIPTION
        "Parameter 'destination_WLAN_address' in event WLAN.11"
    ::= { wlanEventObjects11 2 }

wlan11_interface OBJECT-TYPE
    SYNTAX DisplayString
    MAX-ACCESS accessible-for-notify
    STATUS current
    DESCRIPTION
        "Parameter 'interface' in event WLAN.11"
    ::= { wlanEventObjects11 3 }

wlanEventObjects12 OBJECT-IDENTITY
    STATUS current
    DESCRIPTION
        "Event WLAN.12
        Generic driver informational event"
    ::= { wlanEventsGroup 12 }

wlan12_string OBJECT-TYPE
    SYNTAX DisplayString
    MAX-ACCESS accessible-for-notify
    STATUS current
    DESCRIPTION
        "Parameter 'string' in event WLAN.12"
    ::= { wlanEventObjects12 1 }


wlanNotification1 NOTIFICATION-TYPE
    OBJECTS { 
              wlan1_string 
            }
    STATUS current
    DESCRIPTION
        "Notification of Event WLAN.1

        Message: '$1'

        Parameters list:
              $1: wlan1_string

        Generic informational event."
    ::= { wlanNotificationsPrefix 1 }

wlanNotification2 NOTIFICATION-TYPE
    OBJECTS { 
              wlan2_subtype, 
              wlan2_result,
              wlan2_mac_address,
              wlan2_ifc 
            }
    STATUS current
    DESCRIPTION
        "Notification of Event WLAN.2

        Message: 'mlmeMgtTxCompletion $1 result: $2, destination address $3 in $4'

        Parameters list:
              $1: wlan2_subtype
              $2: wlan2_result
              $3: wlan2_mac_address
              $4: wlan2_ifc

        MLME Transmit Event."
    ::= { wlanNotificationsPrefix 2 }

wlanNotification3 NOTIFICATION-TYPE
    OBJECTS { 
              wlan3_subtype, 
              wlan3_mac_address,
              wlan3_ifc 
            }
    STATUS current
    DESCRIPTION
        "Notification of Event WLAN.3

        Message: 'mlmeMgtRxCompletion $1, destination address $2 in $3'

        Parameters list:
              $1: wlan3_subtype
              $2: wlan3_mac_address
              $3: wlan3_ifc

        MLME Receive Event."
    ::= { wlanNotificationsPrefix 3 }

wlanNotification4 NOTIFICATION-TYPE
    OBJECTS { 
              wlan4_mac_address, 
              wlan4_channel,
              wlan4_transState,
              wlan4_rssi 
            }
    STATUS current
    DESCRIPTION
        "Notification of Event WLAN.4

        Message: 'mlmeBeaconReceive: Beacon from $1 on channel $2, transState: $3, RSSI: $4'

        Parameters list:
              $1: wlan4_mac_address
              $2: wlan4_channel
              $3: wlan4_transState
              $4: wlan4_rssi

        Beacon frame received."
    ::= { wlanNotificationsPrefix 4 }

wlanNotification5 NOTIFICATION-TYPE
    OBJECTS { 
              wlan5_state_machine, 
              wlan5_state,
              wlan5_interface,
              wlan5_aid 
            }
    STATUS current
    DESCRIPTION
        "Notification of Event WLAN.5

        Message: 'State Machine $1 entered state $2, ifc $3 aid $4'

        Parameters list:
              $1: wlan5_state_machine
              $2: wlan5_state
              $3: wlan5_interface
              $4: wlan5_aid

        Station PTK state machine."
    ::= { wlanNotificationsPrefix 5 }

wlanNotification6 NOTIFICATION-TYPE
    OBJECTS { 
              wlan6_state_machine, 
              wlan6_state,
              wlan6_interface,
              wlan6_aid 
            }
    STATUS current
    DESCRIPTION
        "Notification of Event WLAN.6

        Message: 'State Machine $1 entered state $2, ifc $3 aid $4'

        Parameters list:
              $1: wlan6_state_machine
              $2: wlan6_state
              $3: wlan6_interface
              $4: wlan6_aid

        Station GTK state machine."
    ::= { wlanNotificationsPrefix 6 }

wlanNotification7 NOTIFICATION-TYPE
    OBJECTS { 
              wlan7_state_machine, 
              wlan7_state,
              wlan7_interface 
            }
    STATUS current
    DESCRIPTION
        "Notification of Event WLAN.7

        Message: 'State Machine $1 entered state $2, ifc $3'

        Parameters list:
              $1: wlan7_state_machine
              $2: wlan7_state
              $3: wlan7_interface

        Global GTK state machine."
    ::= { wlanNotificationsPrefix 7 }

wlanNotification8 NOTIFICATION-TYPE
    OBJECTS { 
              wlan8_string 
            }
    STATUS current
    DESCRIPTION
        "Notification of Event WLAN.8

        Message: '$1'

        Parameters list:
              $1: wlan8_string

        Generic WLAN application informational event."
    ::= { wlanNotificationsPrefix 8 }

wlanNotification9 NOTIFICATION-TYPE
    OBJECTS { 
              wlan9_state_machine, 
              wlan9_state,
              wlan9_interface 
            }
    STATUS current
    DESCRIPTION
        "Notification of Event WLAN.9

        Message: 'State Machine $1 entered state $2, ifc $3'

        Parameters list:
              $1: wlan9_state_machine
              $2: wlan9_state
              $3: wlan9_interface

        Supplicant key management state machine."
    ::= { wlanNotificationsPrefix 9 }

wlanNotification10 NOTIFICATION-TYPE
    OBJECTS { 
              wlan10_source_WLAN_address, 
              wlan10_destination_WLAN_address,
              wlan10_interface 
            }
    STATUS current
    DESCRIPTION
        "Notification of Event WLAN.10

        Message: 'WLAN multicast packet received from $1 to $2 is filtered interface $3'

        Parameters list:
              $1: wlan10_source_WLAN_address
              $2: wlan10_destination_WLAN_address
              $3: wlan10_interface

        A WLAN multicast packet was received and it was discarded because
        it did not match registered multicast addresses on interface."
    ::= { wlanNotificationsPrefix 10 }

wlanNotification11 NOTIFICATION-TYPE
    OBJECTS { 
              wlan11_source_WLAN_address, 
              wlan11_destination_WLAN_address,
              wlan11_interface 
            }
    STATUS current
    DESCRIPTION
        "Notification of Event WLAN.11

        Message: 'WLAN unicast packet received from $1 to $2 is filtered interface $3'

        Parameters list:
              $1: wlan11_source_WLAN_address
              $2: wlan11_destination_WLAN_address
              $3: wlan11_interface

        A WLAN unicast packet was received and it was discarded because
        it did not match local unicast addresses."
    ::= { wlanNotificationsPrefix 11 }

wlanNotification12 NOTIFICATION-TYPE
    OBJECTS { 
              wlan12_string 
            }
    STATUS current
    DESCRIPTION
        "Notification of Event WLAN.12

        Message: '$1'

        Parameters list:
              $1: wlan12_string

        Generic driver informational event"
    ::= { wlanNotificationsPrefix 12 }


END
