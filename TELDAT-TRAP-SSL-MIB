-- file automatically created


TELDAT-TRAP-SSL-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


sslTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SSL event subsystem."
    REVISION "201401200930Z"
    DESCRIPTION "Initial implementation"
        ::= { telEventTraps 209 }


sslEventsGroup	OBJECT IDENTIFIER	::= { sslTrapsMIB 1 }

sslNotifications	OBJECT IDENTIFIER	::= { sslTrapsMIB 2 }
sslNotificationsPrefix	OBJECT IDENTIFIER	::= { sslNotifications 0 }

sslEventObjects1 OBJECT-IDENTITY
    STATUS current
    DESCRIPTION
        "Event SSL.1
        An SSL error has happened"
    ::= { sslEventsGroup 1 }

ssl1_string OBJECT-TYPE
    SYNTAX DisplayString
    MAX-ACCESS accessible-for-notify
    STATUS current
    DESCRIPTION
        "Parameter 'string' in event SSL.1"
    ::= { sslEventObjects1 1 }

ssl1_add_string OBJECT-TYPE
    SYNTAX DisplayString
    MAX-ACCESS accessible-for-notify
    STATUS current
    DESCRIPTION
        "Parameter 'add_string' in event SSL.1"
    ::= { sslEventObjects1 2 }


sslNotification1 NOTIFICATION-TYPE
    OBJECTS { 
              ssl1_string, 
              ssl1_add_string 
            }
    STATUS current
    DESCRIPTION
        "Notification of Event SSL.1

        Message: 'Error $1 data $2'

        Parameters list:
              $1: ssl1_string
              $2: ssl1_add_string

        An SSL error has happened"
    ::= { sslNotificationsPrefix 1 }


END
