AirWave-SMI-MIB DEFINITIONS ::= BEGIN

IMPORTS
	MODULE-IDENTITY, 
	OBJECT-IDENTITY,
	enterprises
		FROM SNMPv2-SMI;

airwave	MODULE-IDENTITY
	LAST-UPDATED "200401070000Z"
	ORGANIZATION "AirWave Wireless"
	CONTACT-INFO
		"        Paul Gray
		
		 Postal: Aruba Networks, Inc.
		         1344 Crossman Ave
		         Sunnyvale, CA 94402
		         
		    Tel: +1 408 227 4500
		    
		  Email: paul@arubanetworks.com
		    Web: http://www.arubanetworks.com/"
	DESCRIPTION
		"The MIB module for AirWave products."
	REVISION "200401070000Z"
	DESCRIPTION
		"Updated contact info and revised MIB items."
	REVISION "200201030000Z"
	DESCRIPTION
		"The initial version of this MIB module."
 
	::= { enterprises 12028 }

airwaveProducts OBJECT-IDENTITY
	STATUS current
	DESCRIPTION
		"AirWave products. See AirWave-Products-MIB."
	::= { airwave 1 }

airwaveModules OBJECT-IDENTITY 
	STATUS current
	DESCRIPTION
		"AirWave MIB modules."
	::= { airwave 2 }

airwaveDev OBJECT-IDENTITY 
	STATUS current
	DESCRIPTION
		"AirWave internal MIB for products under development."
	::= { airwave 3 }

awamp OBJECT-IDENTITY
	STATUS current
	DESCRIPTION
		"AirWave Management Platform MIB for NMS integration.
		 See AWAMP-MIB."
	::= { airwave 4 }

airwaveSimulator OBJECT IDENTIFIER ::= { airwave 5 }

END
