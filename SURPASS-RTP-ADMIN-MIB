-- ==================================================================
--  Copyright © 1999 - 2008 Siemens Enterpise Communications
--
--  All Rights Reserved.
--
--  Reproduction of this document is authorized on condition that
--  this copyright notice is included.
--
--  This MIB document embodies proprietary intellectual property. 
--  of Siemens Network Convergence LLC, which retains all title and
--  ownership in this MIB, including any revisions.
--
--  This module will be extended, as required.
--
--  Siemens Network Convergence LLC reserves the right to make 
--  changes in specification and other information contained in this 
--  document without prior notice. The reader should consult 
--  Siemens Network Convergence LLC to determine whether any such
--  changes have been made.
-- ==================================================================

-- **************************************************************************
-- Revision History
-- 08/01/02    K. Teelucksingh      Initial code
-- 05/08/03    Polly Yu             Updated copyright text 
-- 06/12/08    C. Chatzidimitriou   Updated MIB to be fully compatible with SNMPv2
--
-- **************************************************************************

SURPASS-RTP-ADMIN-MIB DEFINITIONS ::= BEGIN

IMPORTS
    surpassRtp                           
        FROM SURPASS-RTP-MIB
    MODULE-IDENTITY, OBJECT-IDENTITY                      
        FROM SNMPv2-SMI; 
	
-- **************************************************************************

    surpassRtpAdmin MODULE-IDENTITY
        LAST-UPDATED "200806111500Z"
        ORGANIZATION "Siemens Network Convergence LLC"
        CONTACT-INFO " "
        DESCRIPTION
                     "The MIB module describes the top level of the 
                     Surpass RTP Managed Objects."     
        REVISION     "200806111500Z"
        DESCRIPTION
                     "Updated the MIB to be fully compatible with SNMPv2"
        ::= { surpassRtp 2 }

    hiq8000Admin OBJECT-IDENTITY
        STATUS current
        DESCRIPTION
            "The hiQ 8000 Managed Object."
        ::= { surpassRtpAdmin 1 }

END
