-- **********************************************************
-- Copyright 2007 VMware, Inc.  All rights reserved. 
-- 
--  This MIB Module provides root oid assignments for 
--  VMware Management
--
-- **********************************************************

-- Version 1.0

VMWARE-ROOT-MIB DEFINITIONS ::= BEGIN

IMPORTS
   enterprises
      FROM RFC1155-SMI;

-- This file defines the VMware SNMP MIB root and its primary subtrees.
-- Currently, each subtree has its own MIB file.

vmware             OBJECT IDENTIFIER ::= { enterprises 6876 }
vmwSystem          OBJECT IDENTIFIER ::= { vmware 1 }
vmwVirtMachines    OBJECT IDENTIFIER ::= { vmware 2 }
vmwResources       OBJECT IDENTIFIER ::= { vmware 3 }
vmwProductSpecific OBJECT IDENTIFIER ::= { vmware 4 }
vmwTraps           OBJECT IDENTIFIER ::= { vmware 50 }
vmwOID             OBJECT IDENTIFIER ::= { vmware 60 }
vmwExperimental    OBJECT IDENTIFIER ::= { vmware 700 }
   
END
