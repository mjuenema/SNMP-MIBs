-- ==================================================================
--  Copyright © 1999 - 2008 Siemens Enterprise Communications
--
--  All Rights Reserved.
--
--  Reproduction of this document is authorized on condition that
--  this copyright notice is included.
--
--  This MIB document embodies proprietary intellectual property. 
--  of Siemens Network Convergence LLC, which retains all title and
--  ownership in this MIB, including any revisions.
--
--  This module will be extended, as required.
--
--  Siemens Network Convergence LLC reserves the right to make 
--  changes in specification and other information contained in this 
--  document without prior notice. The reader should consult 
--  Siemens Network Convergence LLC to determine whether any such
--  changes have been made.
--
--  Copyright © 1999 - 2008 Siemens Enterprise Communications
-- ==================================================================

-- ==================================================================
-- Revision History
--  01/28/05      Dana Brooks           initial definition for hiq traps
--  02/17/05      Dana Brooks           added new traps based on
--                                      existing alarms
--  03/16/05      Dana Brooks           Modified description for TCA
--                                      clear trap
--  04/19/05      Dana Brooks           Removed 2 USC traps
--                                      Added registration failure and
--                                      success traps for CSTA
--                                      Removed 3 PRM traps
--                                      Combined MGCP traps into one
--                                      MGCP section
--                                      General formatting changes to
--                                      make trap definitions consistent
--                                      Removed exited and shutting down
--                                      traps
--                                      Removed CSTA CAP link failure
--                                      Added new SNM node status change
--                                      trap
--                                      Renamed hiqOmapStartingTrap to
--                                      hiqOmap
--                                      Removed some ISUP traps
--  05/03/05      Dana Brooks           Added 2 new SNM traps
--                                      Removed usage collection client
--                                      terminated and authentication
--                                      client terminated traps
--                                      Removed severity and alarm type
--                                      comments for all traps
--  05/18/05      Dana Brooks           Removed hiQAucUscServerTerminationTrap
--  06/07/05      Dana Brooks           Removed hiQNmProcessRestartFailedTrap
--  07/01/05      Dana Brooks           Added hiQSnmSubsysFailedTrap and
--                                      removed soap server process started
--                                      and ended traps. Removed
--                                      hiQRtmSharedMemoryTrap,
--                                      hiQRtmDynamicMemoryTrap,
--                                      hiQRtmCallProcessingTrap traps.
--                                      Removed hiQPrmInitTrap and
--                                      hiQPrmMonitorFailedTrap.
--  09/27/05      Dana Brooks           Changed names of some traps,
--                                      removed repair text and modified
--                                      descriptions of some traps.
--  10/14/05      Dana Brooks           Added new traps for FRN0384.
--                                      Traps were added in the following
--                                      areas: Global, SMDI, USC,
--                                      Overload Manager and Subscriber
--                                      Management (SOAP).
--  04/07/06      Dana Brooks           Added four new traps to the Global
--                                      traps section (217) for queue
--                                      threshold exceeded. Three alarm
--                                      traps and one clear trap.
--  04/21/06      Dana Brooks           Add new trap definition for
--                                      Survival Authority feature. This
--                                      trap is not an alarm - it is
--                                      used for communications with the
--                                      NMC.
--  05/25/06      Dana Brooks           Mark unused traps as obsolete.
--  06/02/06      Dana Brooks           Add new alarm for operating in
--                                      survival mode.
--  06/20/06      Dana Brooks           Mark Oracle-related traps as
--                                      obsolete (merge).
--  06/29/06      Dana Brooks           Add new SS7 traps. These traps
--                                      are based on events generated by
--                                      RTP SS7 processing.
--  12/13/06      Dana Brooks           Added new alarms (and clears)
--                                      for the Solid database system.
--  01/26/07      Dana Brooks           Add two new RTP ticket alarms.
--  01/30/07      Dana Brooks           Added new alarms (and clears)
--                                      for Sigtran RTP SS7 processing.
--                                      Changed status of SunCluster
--                                      alarms to obsolete.
--  03/23/07      Jess Henson           Add new RTP ticket alarm (111-7).
--  04/09/07      Jesse Henson          Add new Solid DB alarm (141-1103).
--  04/11/07      Jesse Henson          Dynamic licensing alarms/clears (FRN1940)
--  04/12/07      Jesse Henson          Add trunking session alarms/clears (FRN2099)
--  05/04/07      Jesse Henson          Add new OMM alarm set for BGCF (FRN2438)
--  05/04/07      Dana Brooks           Mark remaining three current H323
--                                      traps as obsolete.
--  04/10/08      C. Chatzidimitriou    FRN3208. Cleanup of MIBS 
-- ==================================================================

US-HIQ-TRAP-MIB    DEFINITIONS ::= BEGIN

IMPORTS
   MODULE-IDENTITY, OBJECT-IDENTITY, OBJECT-TYPE, NOTIFICATION-TYPE, IpAddress
        FROM SNMPv2-SMI
   surpassRtp
	FROM SURPASS-RTP-MIB
   hiq8000Admin
        FROM SURPASS-RTP-ADMIN-MIB
   rtpEvtSequenceNumberIndex,
   rtpEvtCurrId, rtpEvtSet, rtpEvtNum,
   rtpEvtSeverity, rtpEvtEventTime,
   rtpEvtReportingObject, rtpEvtFaultyObject,
   rtpEvtEndkey, rtpEvtFormatText,
   rtpEvtParameters,  rtpEvtAlarmType, rtpEvtShortText,
   rtpEvtFilterLastTransId 
    	FROM FSC-RTP-MIB-EVENT-MGMT;
          
-- =================================================================
--      rtpEvtSeverity:  level 1-7, 1 is critical, 
--                                  2 major
--                                  3 minor
--                                  4 warning
--                                  5 informational
--                                  6 cleared
--                                  7 unknown
--      rtpEvtAlarmType: types 0-99, 0 is undeterminate,
--                                   1 is communication alarm
--                                   2 is service alarm
--                                   3 is processing alarm
--                                   4 is equipement alarm
--                                   5 is environment alarm
--                                   6 is db alarm
--                                   7 is mib alarm
--                                   8 is the first user defineable alarm
--
-- ==================================================================

hiqTraps   MODULE-IDENTITY
           LAST-UPDATED "200806111500Z"
           ORGANIZATION "Siemens Enterprise Communications"
           CONTACT-INFO " " 
           DESCRIPTION
           "This MIB describes the Siemens Network Convergence LLC RTP trap
           information.  The definition of the event is taken from
           RtpAdmEventMgmt.mib. For the description
           of these objects:  rtpEvtSequenceNumberIndex,
                              rtpEvtCurrId,
                              rtpEvtSet,
                              rtpEvtNum,
                              rtpEvtSeverity,
                              rtpEvtEventTime,
                              rtpEvtReportingObject,
                              rtpEvtFaultyObject,
                              rtpEvtEndkey,
                              rtpEvtFormatText,
                              rtpEvtParameters,
                              rtpEvtAlarmType,
                              rtpEvtShortText,
                              rtpEvtFilterLastTransId" 
                              
           REVISION "200806111500Z"    
           DESCRIPTION
           "Updated the MIB to be fully compatible with SNMPv2"

        ::= { hiq8000Admin 47 }

hiQSs7FaultMgt OBJECT-IDENTITY
                STATUS obsolete
                DESCRIPTION
                "Events from Rtp event set 69."
                ::= { hiqTraps 69 }
		
hiQEvtFaultMgt OBJECT-IDENTITY
                STATUS current
                DESCRIPTION
                "Events from Rtp event set RTP_NLS_EVT (100)."
                ::= { hiqTraps 100 }		

hiQAudFaultMgt OBJECT-IDENTITY
                STATUS current
                DESCRIPTION
                "Events from Rtp event set RTP_NLS_AUD (102)."
                ::= { hiqTraps 102 }

hiQNmFaultMgt OBJECT-IDENTITY
                STATUS current
                DESCRIPTION
                "Events from Rtp event set RTP_NLS_NM (107)."
                ::= { hiqTraps 107 }

hiQTicFaultMgt OBJECT-IDENTITY
                STATUS current
                DESCRIPTION
                "Events from Rtp event set 111."
                ::= { hiqTraps 111 }

hiQSnmFaultMgt OBJECT-IDENTITY
                STATUS current
                DESCRIPTION
                "Events from Rtp event set RTP_NLS_SNM (119)."
                ::= { hiqTraps 119 }

hiQLogOracleFaultMgt OBJECT-IDENTITY
                STATUS obsolete
                DESCRIPTION
                "Events from Rtp event set RTP_NLS_ORA (140)."
                ::= { hiqTraps 140 }

hiQLogSolidFaultMgt OBJECT-IDENTITY
                STATUS current
                DESCRIPTION
                "Events from Rtp event set RTP_NLS_SOLID (141)."
                ::= { hiqTraps 141 }

hiQMgcpFaultMgmt OBJECT-IDENTITY
        	STATUS obsolete
        	DESCRIPTION
            	"The MGCP Fault Management MOs."
        	::= { hiqTraps 178 }

hiQAucAuthFaultMgmt OBJECT-IDENTITY
        	STATUS obsolete
        	DESCRIPTION
            	"The AUC, Authentication (AUTH) Fault Management MOs."
        	::= { hiqTraps 181 }

hiQAucUscFaultMgmt OBJECT-IDENTITY
        	STATUS current
        	DESCRIPTION
            	"The AUC, User Collection(USC) Fault Management MOs."
        	::= { hiqTraps 182 }

hiQH323FaultMgmt OBJECT-IDENTITY
        	STATUS obsolete
        	DESCRIPTION
            	"The H323 Fault Management MOs."
        	::= { hiqTraps 180 }

hiQUceFaultMgmt OBJECT-IDENTITY
        	STATUS obsolete
        	DESCRIPTION
            	"The UCE Fault Management MOs."
        	::= { hiqTraps 176 }

hiQOvlFaultMgmt OBJECT-IDENTITY
        	STATUS current
        	DESCRIPTION
            	"The Overload Fault Management MOs."
        	::= { hiqTraps 190 }

hiQPrmFaultMgmt OBJECT-IDENTITY
        	STATUS current
        	DESCRIPTION
            	"The PRM Fault Management MOs."
        	::= { hiqTraps 189 }

hiQRtmFaultMgmt OBJECT-IDENTITY
        	STATUS current
        	DESCRIPTION
            	"The ISDN Fault Management MOs."
        	::= { hiqTraps 199 }

hiQIsupFaultMgmt OBJECT-IDENTITY
        	STATUS obsolete
        	DESCRIPTION
            	"The ISUP Fault Management MOs."
        	::= { hiqTraps 177 }

hiQLnpFaultMgmt OBJECT-IDENTITY
        	STATUS current
        	DESCRIPTION
            	"The LNP Fault Management MOs."
        	::= { hiqTraps 193 }

hiQTcapFaultMgmt OBJECT-IDENTITY
        	STATUS obsolete
        	DESCRIPTION
            	"The TCAP Fault Management MOs."
        	::= { hiqTraps 192 }

hiQCdmFaultMgmt OBJECT-IDENTITY
        	STATUS obsolete
		DESCRIPTION
            	"The CDM Fault Management MOs."
        	::= { hiqTraps 188 }

hiQXdmFaultMgmt OBJECT-IDENTITY
        	STATUS obsolete
        	DESCRIPTION
            	"The XDM Fault Management MOs."
        	::= { hiqTraps 183 }

hiQOmapFaultMgmt OBJECT-IDENTITY
        	STATUS obsolete
        	DESCRIPTION
            	"The OMAP Fault Management MOs."
        	::= { hiqTraps 187 }

hiQDbFaultMgmt OBJECT-IDENTITY
        	STATUS obsolete
        	DESCRIPTION
            	"The DB Fault Management MOs."
        	::= { hiqTraps 191 }

hiQOmapDispFaultMgmt OBJECT-IDENTITY
                STATUS obsolete
                DESCRIPTION
                "The Omap Fault Management MOs."
                ::= { hiqTraps 194 }

hiQSipFaultMgmt OBJECT-IDENTITY
                STATUS obsolete
                DESCRIPTION
                "The SIP Fault Management MOs."
                ::= { hiqTraps 198 }

hiQSoapServerFaultMgmt OBJECT-IDENTITY
                STATUS current
                DESCRIPTION
                "The SOAP Server Fault Management Messages."
                ::= { hiqTraps 207 }

hiQCstaFaultMgmt OBJECT-IDENTITY
                STATUS current
                DESCRIPTION
                "The CSTA Fault Management Messages."
                ::= { hiqTraps 210 }

hiQSmdiFaultMgmt OBJECT-IDENTITY
                STATUS obsolete
                DESCRIPTION
                "The SMDI Fault Management Messages."
                ::= { hiqTraps 208 }

hiQHardwareFaultMgt OBJECT-IDENTITY
                STATUS current
                DESCRIPTION
                "Events from hardware event set HARDWARE_EVT_SET_ID (219)."
                ::= { hiqTraps 219 }

hiQSecurityFaultMgt OBJECT-IDENTITY
                STATUS current
                DESCRIPTION
                "Events from security event set SECURITY_EVT_SET_ID (218)."
                ::= { hiqTraps 218 }

hiQLicensingFaultMgt OBJECT-IDENTITY
                STATUS current
                DESCRIPTION
                "Events from software licensing event set LICENSING_EVT_SET_ID (220)."
                ::= { hiqTraps 220 }

hiQGlobalFaultMgt OBJECT-IDENTITY
                STATUS current
                DESCRIPTION
                "Events from global event set GLOBAL_EVT_SET_ID (217)."
                ::= { hiqTraps 217 }

hiQAccountMgmtFaultMgt OBJECT-IDENTITY
                STATUS current
                DESCRIPTION
                "Events from account management event set ACCOUNT_EVT_SET_ID (221)."
                ::= { hiqTraps 221 }

hiQOmmMgmtFaultMgt OBJECT-IDENTITY
                STATUS current
                DESCRIPTION
                "Events from operational maintenance measurement event set OMM_EVT_SET_ID (230)."
                ::= { hiqTraps 230 }


hiQTcaFaultMgt OBJECT-IDENTITY
                STATUS current
                DESCRIPTION
                "Events from TCA event set TCA_EVT_SET_ID (216)."
                ::= { hiqTraps 216 }

-- *******************************
-- SS7 Traps
-- *******************************

hiQSS7SCTPAssociationCreated NOTIFICATION-TYPE
            OBJECTS { rtpEvtSequenceNumberIndex,
                      rtpEvtCurrId,
                      rtpEvtSet,                    -- 69
                      rtpEvtNum,                    -- 60
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The specified SCTP association has been created."
            ::= { hiQSs7FaultMgt 60 }

hiQSS7SCTPAssociationDeleted NOTIFICATION-TYPE
            OBJECTS { rtpEvtSequenceNumberIndex,
                      rtpEvtCurrId,
                      rtpEvtSet,                    -- 69
                      rtpEvtNum,                    -- 61
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete 
            DESCRIPTION "The specified SCTP association has been deleted."
            ::= { hiQSs7FaultMgt 61 }

hiQSS7IPSignalingLinkActivated NOTIFICATION-TYPE
            OBJECTS { rtpEvtSequenceNumberIndex,
                      rtpEvtCurrId,
                      rtpEvtSet,                    -- 69
                      rtpEvtNum,                    -- 62
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The specified IP signaling link has been activated."
            ::= { hiQSs7FaultMgt 62 }

hiQSS7IPSignalingLinkDeactivated NOTIFICATION-TYPE
            OBJECTS { rtpEvtSequenceNumberIndex,
                      rtpEvtCurrId,
                      rtpEvtSet,                    -- 69
                      rtpEvtNum,                    -- 63
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The specified IP signaling link has been deactivated."
            ::= { hiQSs7FaultMgt 63 }

hiQSS7M3UARoutingKeyActivated NOTIFICATION-TYPE
            OBJECTS { rtpEvtSequenceNumberIndex,
                      rtpEvtCurrId,
                      rtpEvtSet,                    -- 69
                      rtpEvtNum,                    -- 64
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The specified M3UA routing key has been activated."
            ::= { hiQSs7FaultMgt 64 }

hiQSS7M3UARoutingKeyDeactivated NOTIFICATION-TYPE
            OBJECTS { rtpEvtSequenceNumberIndex,
                      rtpEvtCurrId,
                      rtpEvtSet,                    -- 69
                      rtpEvtNum,                    -- 65
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The specified M3UA routing key has been deactivated."
            ::= { hiQSs7FaultMgt 65 }

hiQSS7SCTPNetStatusChange NOTIFICATION-TYPE
            OBJECTS { rtpEvtSequenceNumberIndex,
                      rtpEvtCurrId,
                      rtpEvtSet,                    -- 69
                      rtpEvtNum,                    -- 66
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The network status of the specified SCTP association
                         has changed."
            ::= { hiQSs7FaultMgt 66 }

-- *******************************
-- RTP Evt Traps
-- *******************************

hiQProcessExitedTrap NOTIFICATION-TYPE
            OBJECTS { rtpEvtSequenceNumberIndex,
                      rtpEvtCurrId,
                      rtpEvtSet,                    -- 100
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Process with given pid exits with given RTP error." 
            ::= { hiQEvtFaultMgt 2 }



-- *******************************
-- RTP Audit Traps
-- *******************************

hiQAuditStartingTrap NOTIFICATION-TYPE
            OBJECTS { rtpEvtSequenceNumberIndex,
                      rtpEvtCurrId,
                      rtpEvtSet,                    -- 102
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Audit Manager process is starting." 
            ::= { hiQAudFaultMgt 1 }

hiQAudNamedDetectorStartingTrap NOTIFICATION-TYPE
            OBJECTS { rtpEvtSequenceNumberIndex,
                      rtpEvtCurrId,
                      rtpEvtSet,                    -- 102
                      rtpEvtNum,                    -- 80
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The named detector is starting or restarting." 
            ::= { hiQAudFaultMgt 80 }

hiQAudDetectorWithinLimitTrap NOTIFICATION-TYPE
            OBJECTS { rtpEvtSequenceNumberIndex,
                      rtpEvtCurrId,
                      rtpEvtSet,                    -- 102
                      rtpEvtNum,                    -- 89
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The named detector previously took longer than its configured maximum
                        run interval. It is now running within this limit again."
            ::= { hiQAudFaultMgt 89 }

hiQAudAvailDiskSpBelowCritThld NOTIFICATION-TYPE
            OBJECTS { rtpEvtSequenceNumberIndex,
                      rtpEvtCurrId,
                      rtpEvtSet,                    -- 102
                      rtpEvtNum,                    -- 201
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The available space in the file system is below the configured critical
                         threshold."
            ::= { hiQAudFaultMgt 201 }

hiQAudAvailDiskSpBelowMajorThld NOTIFICATION-TYPE
            OBJECTS { rtpEvtSequenceNumberIndex,
                      rtpEvtCurrId,
                      rtpEvtSet,                    -- 102
                      rtpEvtNum,                    -- 202
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The available space in the file system is below the configured major
                         threshold."
            ::= { hiQAudFaultMgt 202 }

hiQAudAvailDiskSpBelowMinorThld NOTIFICATION-TYPE
            OBJECTS { rtpEvtSequenceNumberIndex,
                      rtpEvtCurrId,
                      rtpEvtSet,                    -- 102
                      rtpEvtNum,                    -- 203
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The available space in the file system is below the configured minor
                        threshold level."
            ::= { hiQAudFaultMgt 203 }

hiQAudFreeSpaceOkTrap NOTIFICATION-TYPE
            OBJECTS { rtpEvtSequenceNumberIndex,
                      rtpEvtCurrId,
                      rtpEvtSet,                    -- 102
                      rtpEvtNum,                    -- 210
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "There had been a problem determining the free space on the
                        given file system. The problem no longer exists."
            ::= { hiQAudFaultMgt 210 }

hiQAudFileSystemBelowMin1Trap NOTIFICATION-TYPE
            OBJECTS { rtpEvtSequenceNumberIndex,
                      rtpEvtCurrId,
                      rtpEvtSet,                    -- 102
                      rtpEvtNum,                    -- 211
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Available File system  space has changed but it is still below
                        one of the configured thresholds."
            ::= { hiQAudFaultMgt 211 }

hiQAudFileSystemBelowMin2Trap NOTIFICATION-TYPE
            OBJECTS { rtpEvtSequenceNumberIndex,
                      rtpEvtCurrId,
                      rtpEvtSet,                    -- 102
                      rtpEvtNum,                    -- 212
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Available File system  space has echanged but it is still below
                        one of the configured thresholds."
            ::= { hiQAudFaultMgt 212 }

hiQAudFileSystemBelowMin3Trap NOTIFICATION-TYPE
            OBJECTS { rtpEvtSequenceNumberIndex,
                      rtpEvtCurrId,
                      rtpEvtSet,                    -- 102
                      rtpEvtNum,                    -- 213
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Available File system  space has changed but it is still below
                        one of the configured thresholds."
            ::= { hiQAudFaultMgt 213 }

hiQAudFileSystemBelowMin4Trap NOTIFICATION-TYPE
            OBJECTS { rtpEvtSequenceNumberIndex,
                      rtpEvtCurrId,
                      rtpEvtSet,                    -- 102
                      rtpEvtNum,                    -- 214
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Available File system  space has changed but it is still below
                        one of the configured thresholds."
            ::= { hiQAudFaultMgt 214 }

hiQAudFileSystemAboveMinTrap NOTIFICATION-TYPE
            OBJECTS { rtpEvtSequenceNumberIndex,
                      rtpEvtCurrId,
                      rtpEvtSet,                    -- 102
                      rtpEvtNum,                    -- 215
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Available File system space has increased above the configured minimum
                        threshold level."
            ::= { hiQAudFaultMgt 215 }

hiQAudFileGrpAboveCritThld NOTIFICATION-TYPE
            OBJECTS { rtpEvtSequenceNumberIndex,
                      rtpEvtCurrId,
                      rtpEvtSet,                    -- 102
                      rtpEvtNum,                    -- 301
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The size of the given file group is monitored by the audit process
                        and has exceeded the configured critical threshold."
            ::= { hiQAudFaultMgt 301 }

hiQAudFileGrpAboveMajorThld NOTIFICATION-TYPE
            OBJECTS { rtpEvtSequenceNumberIndex,
                      rtpEvtCurrId,
                      rtpEvtSet,                    -- 102
                      rtpEvtNum,                    -- 302
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The size of the given file group is monitored by the audit process
                        and has exceeded the configured major threshold."
            ::= { hiQAudFaultMgt 302 }

hiQAudFileGrpAboveMinorThld NOTIFICATION-TYPE
            OBJECTS { rtpEvtSequenceNumberIndex,
                      rtpEvtCurrId,
                      rtpEvtSet,                    -- 102
                      rtpEvtNum,                    -- 303
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The size of the given file group is monitored by the audit process
                        and has exceeded the configured minor threshold."
            ::= { hiQAudFaultMgt 303 }

hiQAudFileGroupSizeChanged1Trap NOTIFICATION-TYPE
            OBJECTS { rtpEvtSequenceNumberIndex,
                      rtpEvtCurrId,
                      rtpEvtSet,                    -- 102
                      rtpEvtNum,                    -- 311
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The size of the given file group has changed but
                        is still too high."
            ::= { hiQAudFaultMgt 311 }

hiQAudFileGroupSizeChanged2Trap NOTIFICATION-TYPE
            OBJECTS { rtpEvtSequenceNumberIndex,
                      rtpEvtCurrId,
                      rtpEvtSet,                    -- 102
                      rtpEvtNum,                    -- 312
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The size of the given file group has changed but
                        is still too high."
            ::= { hiQAudFaultMgt 312 }

hiQAudFileGroupSizeChanged3Trap NOTIFICATION-TYPE
            OBJECTS { rtpEvtSequenceNumberIndex,
                      rtpEvtCurrId,
                      rtpEvtSet,                    -- 102
                      rtpEvtNum,                    -- 313
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The size of the given file group has changed but
                        is still too high."
            ::= { hiQAudFaultMgt 313 }

hiQAudFileGroupSizeChanged4Trap NOTIFICATION-TYPE
            OBJECTS { rtpEvtSequenceNumberIndex,
                      rtpEvtCurrId,
                      rtpEvtSet,                    -- 102
                      rtpEvtNum,                    -- 314
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The size of the given file group has changed but
                        is still too high."
            ::= { hiQAudFaultMgt 314 }

hiQAudFileGrpBelowThreshTrap NOTIFICATION-TYPE
            OBJECTS { rtpEvtSequenceNumberIndex,
                      rtpEvtCurrId,
                      rtpEvtSet,                    -- 102
                      rtpEvtNum,                    -- 315
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The size of the given file group has previously been reported as
                        too high. The size of this file group has now decreased below
                        all configured thresholds."
            ::= { hiQAudFaultMgt 315 }

hiQAudProcHeapAboveCritThld NOTIFICATION-TYPE
            OBJECTS { rtpEvtSequenceNumberIndex,
                      rtpEvtCurrId,
                      rtpEvtSet,                    -- 102
                      rtpEvtNum,                    -- 401
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The heap of the named process is above the configured critical
                        threshold."
            ::= { hiQAudFaultMgt 401 }

hiQAudProcHeapAboveMajorThld NOTIFICATION-TYPE
            OBJECTS { rtpEvtSequenceNumberIndex,
                      rtpEvtCurrId,
                      rtpEvtSet,                    -- 102
                      rtpEvtNum,                    -- 402
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The heap of the named process is above the configured major
                        threshold."
            ::= { hiQAudFaultMgt 402 }

hiQAudProcHeapAboveMinorThld NOTIFICATION-TYPE
            OBJECTS { rtpEvtSequenceNumberIndex,
                      rtpEvtCurrId,
                      rtpEvtSet,                    -- 102
                      rtpEvtNum,                    -- 403
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The heap of the named process is above the configured minor
                        threshold."
            ::= { hiQAudFaultMgt 403 }

hiQAudProcHeapSizeChanged1Trap NOTIFICATION-TYPE
            OBJECTS { rtpEvtSequenceNumberIndex,
                      rtpEvtCurrId,
                      rtpEvtSet,                    -- 102
                      rtpEvtNum,                    -- 411
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The heap size of the named process has changed, but it is
                        still above one of the configured thresholds."
            ::= { hiQAudFaultMgt 411 }

hiQAudProcHeapSizeChanged2Trap NOTIFICATION-TYPE
            OBJECTS { rtpEvtSequenceNumberIndex,
                      rtpEvtCurrId,
                      rtpEvtSet,                    -- 102
                      rtpEvtNum,                    -- 412
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The heap size of the named process has changed, but it is
                        still above one of the configured thresholds."
            ::= { hiQAudFaultMgt 412 }

hiQAudProcHeapSizeChanged3Trap NOTIFICATION-TYPE
            OBJECTS { rtpEvtSequenceNumberIndex,
                      rtpEvtCurrId,
                      rtpEvtSet,                    -- 102
                      rtpEvtNum,                    -- 413
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The heap size of the named process has changed, but it is
                        still above one of the configured thresholds."
            ::= { hiQAudFaultMgt 413 }

hiQAudProcHeapSizeChanged4Trap NOTIFICATION-TYPE
            OBJECTS { rtpEvtSequenceNumberIndex,
                      rtpEvtCurrId,
                      rtpEvtSet,                    -- 102
                      rtpEvtNum,                    -- 414
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The heap size of the named process has changed, but it is
                        still above one of the configured thresholds."
            ::= { hiQAudFaultMgt 414 }

hiQAudProcHeapSizeOkTrap NOTIFICATION-TYPE
            OBJECTS { rtpEvtSequenceNumberIndex,
                      rtpEvtCurrId,
                      rtpEvtSet,                    -- 102
                      rtpEvtNum,                    -- 415
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The heap size of the process is now below all of the configured thresholds."
            ::= { hiQAudFaultMgt 415 }

hiQAudProcStackAboveCritThld NOTIFICATION-TYPE
            OBJECTS { rtpEvtSequenceNumberIndex,
                      rtpEvtCurrId,
                      rtpEvtSet,                    -- 102
                      rtpEvtNum,                    -- 421
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The program stack size  of the named process is above the
                        configured critical threshold."
            ::= { hiQAudFaultMgt 421 }

hiQAudProcStackAboveMajorThld NOTIFICATION-TYPE
            OBJECTS { rtpEvtSequenceNumberIndex,
                      rtpEvtCurrId,
                      rtpEvtSet,                    -- 102
                      rtpEvtNum,                    -- 422
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The program stack size  of the named process is above the
                        configured major threshold."
            ::= { hiQAudFaultMgt 422 }

hiQAudProcStackAboveMinorThld NOTIFICATION-TYPE
            OBJECTS { rtpEvtSequenceNumberIndex,
                      rtpEvtCurrId,
                      rtpEvtSet,                    -- 102
                      rtpEvtNum,                    -- 423
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The program stack size  of the named process is above the
                        configured minor threshold."
            ::= { hiQAudFaultMgt 423 }

hiQAudProcStackSizeChanged1Trap NOTIFICATION-TYPE
            OBJECTS { rtpEvtSequenceNumberIndex,
                      rtpEvtCurrId,
                      rtpEvtSet,                    -- 102
                      rtpEvtNum,                    -- 431
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The stack size of the named process has changed but is still
                        above one of the configured thresholds."
            ::= { hiQAudFaultMgt 431 }

hiQAudProcStackSizeChanged2Trap NOTIFICATION-TYPE
            OBJECTS { rtpEvtSequenceNumberIndex,
                      rtpEvtCurrId,
                      rtpEvtSet,                    -- 102
                      rtpEvtNum,                    -- 432
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The stack size of the named process has changed but is still
                        above one of the configured thresholds."
            ::= { hiQAudFaultMgt 432 }

hiQAudProcStackSizeChanged3Trap NOTIFICATION-TYPE
            OBJECTS { rtpEvtSequenceNumberIndex,
                      rtpEvtCurrId,
                      rtpEvtSet,                    -- 102
                      rtpEvtNum,                    -- 433
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The stack size of the named process has changed but is still
                        above one of the configured thresholds."
            ::= { hiQAudFaultMgt 433 }

hiQAudProcStackSizeChanged4Trap NOTIFICATION-TYPE
            OBJECTS { rtpEvtSequenceNumberIndex,
                      rtpEvtCurrId,
                      rtpEvtSet,                    -- 102
                      rtpEvtNum,                    -- 434
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The stack size of the named process has changed but is still
                        above one of the configured threshold."
            ::= { hiQAudFaultMgt 434 }

hiQAudProcStackSizeOkTrap NOTIFICATION-TYPE
            OBJECTS { rtpEvtSequenceNumberIndex,
                      rtpEvtCurrId,
                      rtpEvtSet,                    -- 102
                      rtpEvtNum,                    -- 435
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The stack size of the process is now below all of the 
                        configured thresholds."
            ::= { hiQAudFaultMgt 435 }

hiQAudProcessInfoAvailTrap NOTIFICATION-TYPE
            OBJECTS { rtpEvtSequenceNumberIndex,
                      rtpEvtCurrId,
                      rtpEvtSet,                    -- 102
                      rtpEvtNum,                    -- 448
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The process information for the given process can
                        now be retrieved again." 
            ::= { hiQAudFaultMgt 448 }

hiQAudOSProcNotRunningTrap NOTIFICATION-TYPE
            OBJECTS { rtpEvtSequenceNumberIndex,
                      rtpEvtCurrId,
                      rtpEvtSet,                    -- 102
                      rtpEvtNum,                    -- 481
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The named OS process is currently not running. The RTP_NORUN_SEVERITY
                        of this process has been configured as major."
            ::= { hiQAudFaultMgt 481 }

hiQAudOSProcInstanceNotRunningTrap NOTIFICATION-TYPE
            OBJECTS { rtpEvtSequenceNumberIndex,
                      rtpEvtCurrId,
                      rtpEvtSet,                    -- 102
                      rtpEvtNum,                    -- 482
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The named OS process is currently not running. The RTP_NORUN_SEVERITY
                        of this process has been configured as major."
            ::= { hiQAudFaultMgt 482 }

hiQAudProcNotRunningCriticalTrap NOTIFICATION-TYPE
            OBJECTS { rtpEvtSequenceNumberIndex,
                      rtpEvtCurrId,
                      rtpEvtSet,                    -- 102
                      rtpEvtNum,                    -- 491
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The named process is currently not running. The RTP_NORUN_SEVERITY of
                        this process has been configured as critical."
            ::= { hiQAudFaultMgt 491 }

hiQAudProcessNotRunningMajorTrap NOTIFICATION-TYPE
            OBJECTS { rtpEvtSequenceNumberIndex,
                      rtpEvtCurrId,
                      rtpEvtSet,                    -- 102
                      rtpEvtNum,                    -- 492
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The named process is currently not running. The RTP_NORUN_SEVERITY of
                        this process has been configured as major."
            ::= { hiQAudFaultMgt 492 }

hiQAudProcessNotRunningMinorTrap NOTIFICATION-TYPE
            OBJECTS { rtpEvtSequenceNumberIndex,
                      rtpEvtCurrId,
                      rtpEvtSet,                    -- 102
                      rtpEvtNum,                    -- 493
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The named process is currently not running. The RTP_NORUN_SEVERITY of
                        this process has been configured as minor."
            ::= { hiQAudFaultMgt 493 }

hiQAudProcessRunningTrap NOTIFICATION-TYPE
            OBJECTS { rtpEvtSequenceNumberIndex,
                      rtpEvtCurrId,
                      rtpEvtSet,                    -- 102
                      rtpEvtNum,                    -- 496
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The named process is now running."
            ::= { hiQAudFaultMgt 496 }

hiQAudOmniRegisterError1Trap NOTIFICATION-TYPE
            OBJECTS { rtpEvtSequenceNumberIndex,
                      rtpEvtCurrId,
                      rtpEvtSet,                    -- 102
                      rtpEvtNum,                    -- 503
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The RTP Audit has to register at the OMNI platform for checking
                        OMNI processes. An error occurred when the audit tried to
                        register."
            ::= { hiQAudFaultMgt 503 }

hiQAudSubsystemRunningTrap NOTIFICATION-TYPE
            OBJECTS { rtpEvtSequenceNumberIndex,
                      rtpEvtCurrId,
                      rtpEvtSet,                    -- 102
                      rtpEvtNum,                    -- 508
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The given subsystem is now running."
            ::= { hiQAudFaultMgt 508 }

hiQAudOmniRegisterError2Trap NOTIFICATION-TYPE
            OBJECTS { rtpEvtSequenceNumberIndex,
                      rtpEvtCurrId,
                      rtpEvtSet,                    -- 102
                      rtpEvtNum,                    -- 509
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The RTP Audit has to register at the OMNI platform for checking
                        OMNI processes. An error occurred when the audit tried to
                        register."
            ::= { hiQAudFaultMgt 509 }

hiQAudOmniRegisterOkTrap NOTIFICATION-TYPE
            OBJECTS { rtpEvtSequenceNumberIndex,
                      rtpEvtCurrId,
                      rtpEvtSet,                    -- 102
                      rtpEvtNum,                    -- 522
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Audit can now register at OMNI and thus check
                        OMNI processes." 
            ::= { hiQAudFaultMgt 522 }

hiQAudCpuUtilAboveCritThld NOTIFICATION-TYPE
            OBJECTS { rtpEvtSequenceNumberIndex,
                      rtpEvtCurrId,
                      rtpEvtSet,                    -- 102
                      rtpEvtNum,                    -- 620
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The current CPU utilization is above the configured critical threshold.
                        CPU utilization checks are done periodically by audit and if
                        this is a temporary situation which no longer exists during the
                        next check cycle, a clearing event will then be issue."
            ::= { hiQAudFaultMgt 620 }

hiQAudCpuUtilAboveMajorThld NOTIFICATION-TYPE
            OBJECTS { rtpEvtSequenceNumberIndex,
                      rtpEvtCurrId,
                      rtpEvtSet,                    -- 102
                      rtpEvtNum,                    -- 621
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The current CPU utilization is above the configured major threshold.
                        CPU utilization checks are done periodically by audit and if
                        this is a temporary situation which no longer exists during the
                        next check cycle, a clearing event will then be issue."
            ::= { hiQAudFaultMgt 621 }

hiQAudCpuUtilAboveMinorThld NOTIFICATION-TYPE
            OBJECTS { rtpEvtSequenceNumberIndex,
                      rtpEvtCurrId,
                      rtpEvtSet,                    -- 102
                      rtpEvtNum,                    -- 622
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The current CPU utilization is above the configured minor threshold.
                        CPU utilization checks are done periodically by audit and if
                        this is a temporary situation which no longer exists during the
                        next check cycle, a clearing event will then be issue."
            ::= { hiQAudFaultMgt 622 }

hiQAudCpuUtilTrap NOTIFICATION-TYPE
            OBJECTS { rtpEvtSequenceNumberIndex,
                      rtpEvtCurrId,
                      rtpEvtSet,                    -- 102
                      rtpEvtNum,                    -- 628
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Information about the current CPU utilization."
            ::= { hiQAudFaultMgt 628 }

hiQAudCpuUtilBelowThreshTrap NOTIFICATION-TYPE
            OBJECTS { rtpEvtSequenceNumberIndex,
                      rtpEvtCurrId,
                      rtpEvtSet,                    -- 102
                      rtpEvtNum,                    -- 629
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The current CPU utilization is now below all configured thresholds."
            ::= { hiQAudFaultMgt 629 }

hiQAudCpuUtilChangedTrap NOTIFICATION-TYPE
            OBJECTS { rtpEvtSequenceNumberIndex,
                      rtpEvtCurrId,
                      rtpEvtSet,                    -- 102
                      rtpEvtNum,                    -- 630
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The current CPU utilization has changed but is still  above
                        one of the configured threshold."
            ::= { hiQAudFaultMgt 630 }

hiQAudSwapSpaceAboveCritThld NOTIFICATION-TYPE
            OBJECTS { rtpEvtSequenceNumberIndex,
                      rtpEvtCurrId,
                      rtpEvtSet,                    -- 102
                      rtpEvtNum,                    -- 640
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The swap space utilization is above the configured critical threshold.
                        Swap space checks are done periodically by the RTP audit and
                        if this is a temporary situation which no longer exists during
                        the next check cycle, a clearing event will be issued."
            ::= { hiQAudFaultMgt 640 }

hiQAudSwapSpaceAboveMajorThld NOTIFICATION-TYPE
            OBJECTS { rtpEvtSequenceNumberIndex,
                      rtpEvtCurrId,
                      rtpEvtSet,                    -- 102
                      rtpEvtNum,                    -- 641
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The swap space utilization is above the configured major threshold.
                        Swap space checks are done periodically by the RTP audit and
                        if this is a temporary situation which no longer exists during
                        the next check cycle, a clearing event will be issued."
            ::= { hiQAudFaultMgt 641 }

hiQAudSwapSpaceAboveMinorThld NOTIFICATION-TYPE
            OBJECTS { rtpEvtSequenceNumberIndex,
                      rtpEvtCurrId,
                      rtpEvtSet,                    -- 102
                      rtpEvtNum,                    -- 642
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The swap space utilization is above the configured minor threshold.
                        Swap space checks are done periodically by the RTP audit and
                        if this is a temporary situation which no longer exists during
                        the next check cycle, a clearing event will be issued."
            ::= { hiQAudFaultMgt 642 }

hiQAudSwapUtilTrap NOTIFICATION-TYPE
            OBJECTS { rtpEvtSequenceNumberIndex,
                      rtpEvtCurrId,
                      rtpEvtSet,                    -- 102
                      rtpEvtNum,                    -- 648
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Information about the current swap space utilization."
                        
            ::= { hiQAudFaultMgt 648 }

hiQAudSwapUtilBelowThreshTrap NOTIFICATION-TYPE
            OBJECTS { rtpEvtSequenceNumberIndex,
                      rtpEvtCurrId,
                      rtpEvtSet,                    -- 102
                      rtpEvtNum,                    -- 649
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Current swap space utilization is now below all configured thresholds."
            ::= { hiQAudFaultMgt 649 }

hiQAudSwapUtilChangedTrap NOTIFICATION-TYPE
            OBJECTS { rtpEvtSequenceNumberIndex,
                      rtpEvtCurrId,
                      rtpEvtSet,                    -- 102
                      rtpEvtNum,                    -- 650
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The swap space utilization has changed, but it is still above
                        one of the configured thresholds."
            ::= { hiQAudFaultMgt 650 }

hiQAudMemUtilAboveCritThld NOTIFICATION-TYPE
            OBJECTS { rtpEvtSequenceNumberIndex,
                      rtpEvtCurrId,
                      rtpEvtSet,                    -- 102
                      rtpEvtNum,                    -- 660
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The current memory utilization is above the configured critical
                        threshold.  Memory utilization checks are done periodically by
                        the RTP audit and if this is a temporary situation which no
                        longer exists during the next check cycle, a clearing event will
                        be issued."
            ::= { hiQAudFaultMgt 660 }

hiQAudMemUtilAboveMajorThld NOTIFICATION-TYPE
            OBJECTS { rtpEvtSequenceNumberIndex,
                      rtpEvtCurrId,
                      rtpEvtSet,                    -- 102
                      rtpEvtNum,                    -- 661
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The current memory utilization is above the configured major
                        threshold.  Memory utilization checks are done periodically by
                        the RTP audit and if this is a temporary situation which no
                        longer exists during the next check cycle, a clearing event will
                        be issued."
            ::= { hiQAudFaultMgt 661 }

hiQAudMemUtilAboveMinorThld NOTIFICATION-TYPE
            OBJECTS { rtpEvtSequenceNumberIndex,
                      rtpEvtCurrId,
                      rtpEvtSet,                    -- 102
                      rtpEvtNum,                    -- 662
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The current memory utilization is above the configured minor
                        threshold.  Memory utilization checks are done periodically by
                        the RTP audit and if this is a temporary situation which no
                        longer exists during the next check cycle, a clearing event will
                        be issued."
            ::= { hiQAudFaultMgt 662 }

hiQAudMemUtilTrap NOTIFICATION-TYPE
            OBJECTS { rtpEvtSequenceNumberIndex,
                      rtpEvtCurrId,
                      rtpEvtSet,                    -- 102
                      rtpEvtNum,                    -- 668
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Information about the current memory utilization." 
            ::= { hiQAudFaultMgt 668 }

hiQAudMemUtilBelowThreshTrap NOTIFICATION-TYPE
            OBJECTS { rtpEvtSequenceNumberIndex,
                      rtpEvtCurrId,
                      rtpEvtSet,                    -- 102
                      rtpEvtNum,                    -- 669
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The current memory utilization is now below all configured thresholds."
            ::= { hiQAudFaultMgt 669 }

hiQAudMemUtilChangedTrap NOTIFICATION-TYPE
            OBJECTS { rtpEvtSequenceNumberIndex,
                      rtpEvtCurrId,
                      rtpEvtSet,                    -- 102
                      rtpEvtNum,                    -- 670
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The current memory utilization has changed but is still above
                        one of the configured thresholds."
            ::= { hiQAudFaultMgt 670 }

hiQAudShMemUtilTooAboveCritThld NOTIFICATION-TYPE
            OBJECTS { rtpEvtSequenceNumberIndex,
                      rtpEvtCurrId,
                      rtpEvtSet,                    -- 102
                      rtpEvtNum,                    -- 680
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of currently used shared memory ids is above the
                        configured critical threshold. Shared memory ids checks are
                        done periodically by audit and if this is a temporary situation which
                        no longer exists during the next check cycle, a clearing event
                        will be issued."
            ::= { hiQAudFaultMgt 680 }

hiQAudShMemUtilTooAboveMajorThld NOTIFICATION-TYPE
            OBJECTS { rtpEvtSequenceNumberIndex,
                      rtpEvtCurrId,
                      rtpEvtSet,                    -- 102
                      rtpEvtNum,                    -- 681
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of currently used shared memory ids is above the
                        configured major threshold. Shared memory ids checks are done
                        periodically by audit and if this is a temporary situation which
                        no longer exists during the next check cycle, a clearing event
                        will be issued."
            ::= { hiQAudFaultMgt 681 }

hiQAudShMemUtilTooAboveMinorThld NOTIFICATION-TYPE
            OBJECTS { rtpEvtSequenceNumberIndex,
                      rtpEvtCurrId,
                      rtpEvtSet,                    -- 102
                      rtpEvtNum,                    -- 682
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of currently used shared memory ids is above the
                        configured minor threshold. Shared memory ids checks are done
                        periodically by audit and if this is a temporary situation which
                        no longer exists during the next check cycle, a clearing event
                        will be issued."
            ::= { hiQAudFaultMgt 682 }

hiQAudShMemUtilTrap NOTIFICATION-TYPE
            OBJECTS { rtpEvtSequenceNumberIndex,
                      rtpEvtCurrId,
                      rtpEvtSet,                    -- 102
                      rtpEvtNum,                    -- 688
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Information about the current shared memory id
                        utilization." 
            ::= { hiQAudFaultMgt 688 }

hiQAudShMemUtilBelowThreshTrap NOTIFICATION-TYPE
            OBJECTS { rtpEvtSequenceNumberIndex,
                      rtpEvtCurrId,
                      rtpEvtSet,                    -- 102
                      rtpEvtNum,                    -- 689
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of currently used shared memory ids is now below
                        all configured thresholds."
            ::= { hiQAudFaultMgt 689 }

hiQAudShMemUtilChangedTrap NOTIFICATION-TYPE
            OBJECTS { rtpEvtSequenceNumberIndex,
                      rtpEvtCurrId,
                      rtpEvtSet,                    -- 102
                      rtpEvtNum,                    -- 690
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of currently used shared memory ids has changed, but
                        is still above one of the configured thresholds."
            ::= { hiQAudFaultMgt 690 }

hiQAudSemUtilAboveCritThld NOTIFICATION-TYPE
            OBJECTS { rtpEvtSequenceNumberIndex,
                      rtpEvtCurrId,
                      rtpEvtSet,                    -- 102
                      rtpEvtNum,                    -- 700
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of currently used semaphores is above the configured critical
                        threshold. Semaphore utilization checks are done periodically by
                        audit and if this is a temporary situation which no longer exists
                        during the next check cycle, a clearing event will be issued."
            ::= { hiQAudFaultMgt 700 }

hiQAudSemUtilAboveMajorThld NOTIFICATION-TYPE
            OBJECTS { rtpEvtSequenceNumberIndex,
                      rtpEvtCurrId,
                      rtpEvtSet,                    -- 102
                      rtpEvtNum,                    -- 701
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of currently used semaphores is above the configured major
                        threshold. Semaphore utilization checks are done periodically by
                        audit and if this is a temporary situation which no longer exists
                        during the next check cycle, a clearing event will be issued."
            ::= { hiQAudFaultMgt 701 }

hiQAudSemUtilAboveMinorThld NOTIFICATION-TYPE
            OBJECTS { rtpEvtSequenceNumberIndex,
                      rtpEvtCurrId,
                      rtpEvtSet,                    -- 102
                      rtpEvtNum,                    -- 702
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of currently used semaphores is above the configured minor
                        threshold. Semaphore utilization checks are done periodically by
                        audit and if this is a temporary situation which no longer exists
                        during the next check cycle, a clearing event will be issued."
            ::= { hiQAudFaultMgt 702 }

hiQAudSemUtilTrap NOTIFICATION-TYPE
            OBJECTS { rtpEvtSequenceNumberIndex,
                      rtpEvtCurrId,
                      rtpEvtSet,                    -- 102
                      rtpEvtNum,                    -- 708
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Information about the current semaphore utilization."
                        
            ::= { hiQAudFaultMgt 708 }

hiQAudSemUtilBelowThreshTrap NOTIFICATION-TYPE
            OBJECTS { rtpEvtSequenceNumberIndex,
                      rtpEvtCurrId,
                      rtpEvtSet,                    -- 102
                      rtpEvtNum,                    -- 709
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of currently used semaphores is now below all configured
                        thresholds."
            ::= { hiQAudFaultMgt 709 }

hiQAudSemUtilChangedTrap NOTIFICATION-TYPE
            OBJECTS { rtpEvtSequenceNumberIndex,
                      rtpEvtCurrId,
                      rtpEvtSet,                    -- 102
                      rtpEvtNum,                    -- 710
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of currently used semaphores has changed, but is
                        still above one of the configured thresholds."
            ::= { hiQAudFaultMgt 710 }

-- *******************************
-- RTP Node Manager Traps
-- *******************************

hiQNmProcessInitCompleteTrap NOTIFICATION-TYPE
            OBJECTS { rtpEvtSequenceNumberIndex,
                      rtpEvtCurrId,
                      rtpEvtSet,                    -- 107
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Process called RtpNmReady() to
                        indicate, that it finished its initialization phase
                        successfully." 
            ::= { hiQNmFaultMgt 1 }

hiQNmProcessExitedTrap NOTIFICATION-TYPE
            OBJECTS { rtpEvtSequenceNumberIndex,
                      rtpEvtCurrId,
                      rtpEvtSet,                    -- 107
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Could not lower given process priority." 
            ::= { hiQNmFaultMgt 3 }

hiQNmDbUnreachable1Trap NOTIFICATION-TYPE
            OBJECTS { rtpEvtSequenceNumberIndex,
                      rtpEvtCurrId,
                      rtpEvtSet,                    -- 107
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The database could not be reached from the RTP node manager process."
            ::= { hiQNmFaultMgt 5 }

hiQNmDbMaxProcGrpExceededTrap NOTIFICATION-TYPE
            OBJECTS { rtpEvtSequenceNumberIndex,
                      rtpEvtCurrId,
                      rtpEvtSet,                    -- 107
                      rtpEvtNum,                    -- 8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The database contains more <processes/groups> than can be
                        handled by the RTP node manager process. The node manager ignores
                        these entries."
            ::= { hiQNmFaultMgt 8 }

hiQNmDbUnreachable2Trap NOTIFICATION-TYPE
            OBJECTS { rtpEvtSequenceNumberIndex,
                      rtpEvtCurrId,
                      rtpEvtSet,                    -- 107
                      rtpEvtNum,                    -- 9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The database could not be reached from the RTP node manager process."
            ::= { hiQNmFaultMgt 9 }

hiQNmDbTableNotOpenedTrap NOTIFICATION-TYPE
            OBJECTS { rtpEvtSequenceNumberIndex,
                      rtpEvtCurrId,
                      rtpEvtSet,                    -- 107
                      rtpEvtNum,                    -- 10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The database table could not be opened by the RTP node manager
                        process."
            ::= { hiQNmFaultMgt 10 }

hiQNmDbTableNotClosedTrap NOTIFICATION-TYPE
            OBJECTS { rtpEvtSequenceNumberIndex,
                      rtpEvtCurrId,
                      rtpEvtSet,                    -- 107
                      rtpEvtNum,                    -- 11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The database table could not be closed the RTP node manager process."
            ::= { hiQNmFaultMgt 11 }

hiQNmProcessReadyTimeoutTrap NOTIFICATION-TYPE
            OBJECTS { rtpEvtSequenceNumberIndex,
                      rtpEvtCurrId,
                      rtpEvtSet,                    -- 107
                      rtpEvtNum,                    -- 12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Process did not call RtpNmReady() within
                        the specified time."
            ::= { hiQNmFaultMgt 12 }

hiQNmProcessHealthChkTimeoutTrap NOTIFICATION-TYPE
            OBJECTS { rtpEvtSequenceNumberIndex,
                      rtpEvtCurrId,
                      rtpEvtSet,                    -- 107
                      rtpEvtNum,                    -- 13
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Process did not answer the healthcheck
                        in time."
            ::= { hiQNmFaultMgt 13 }

hiQNmNodeShutdownTrap NOTIFICATION-TYPE
            OBJECTS { rtpEvtSequenceNumberIndex,
                      rtpEvtCurrId,
                      rtpEvtSet,                    -- 107
                      rtpEvtNum,                    -- 19
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Node will be stopped on behalf of the
                        specified process." 
            ::= { hiQNmFaultMgt 19 }

hiQNmQueueCorruptedTrap NOTIFICATION-TYPE
            OBJECTS { rtpEvtSequenceNumberIndex,
                      rtpEvtCurrId,
                      rtpEvtSet,                    -- 107
                      rtpEvtNum,                    -- 22
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The queue of process %s is not in a consistent state. The
                        process will be restarted which will clear the queue."
            ::= { hiQNmFaultMgt 22 }

hiQNmNodeMgrStartingTrap NOTIFICATION-TYPE
            OBJECTS { rtpEvtSequenceNumberIndex,
                      rtpEvtCurrId,
                      rtpEvtSet,                    -- 107
                      rtpEvtNum,                    -- 31
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "RTP local node manager starting."
            ::= { hiQNmFaultMgt 31 }

hiQNmProcessRestartShortTimeTrap NOTIFICATION-TYPE
            OBJECTS { rtpEvtSequenceNumberIndex,
                      rtpEvtCurrId,
                      rtpEvtSet,                    -- 107
                      rtpEvtNum,                    -- 36
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Process <LogicalName> restarts too soon. The node manager will
                        now wait <number> seconds, before it tries again to bring the
                        process up."
            ::= { hiQNmFaultMgt 36 }

hiQNmQueueAllocErrorTrap NOTIFICATION-TYPE
            OBJECTS { rtpEvtSequenceNumberIndex,
                      rtpEvtCurrId,
                      rtpEvtSet,                    -- 107
                      rtpEvtNum,                    -- 39
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The process queue could not be allocated, due
                        to problems with shared memory."
            ::= { hiQNmFaultMgt 39 }

hiQNmResizeGlobalProcTblTrap NOTIFICATION-TYPE
            OBJECTS { rtpEvtSequenceNumberIndex,
                      rtpEvtCurrId,
                      rtpEvtSet,                    -- 107
                      rtpEvtNum,                    -- 42
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of processes on another node has
                        changed due to a node restart. As a consequence the
                        process table for that node must be resized."
            ::= { hiQNmFaultMgt 42 }

hiQNmAliasTableLenExceededTrap NOTIFICATION-TYPE
            OBJECTS { rtpEvtSequenceNumberIndex,
                      rtpEvtCurrId,
                      rtpEvtSet,                    -- 107
                      rtpEvtNum,                    -- 43
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The RTP parameter Rtp/Nm/MaxAliases must be
                        greater or equal to the number of aliases configured
                        by tcn files or by the GUI/CLI."
            ::= { hiQNmFaultMgt 43 }

hiQNmAliasMembersExceededTrap NOTIFICATION-TYPE
            OBJECTS { rtpEvtSequenceNumberIndex,
                      rtpEvtCurrId,
                      rtpEvtSet,                    -- 107
                      rtpEvtNum,                    -- 44
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The RTP parameter Rtp/Nm/ProcsPerAlias specified the
                        maximal number of members for all aliases. This
                        parameter must suffice for all alias members configured
                        by tcn files or CLI/GUI."
            ::= { hiQNmFaultMgt 44 }

hiQNmProcessExecvErrorTrap NOTIFICATION-TYPE
            OBJECTS { rtpEvtSequenceNumberIndex,
                      rtpEvtCurrId,
                      rtpEvtSet,                    -- 107
                      rtpEvtNum,                    -- 46
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The binary could not be started since RTPexecv returned the
                        errno. If restart is set for the RTP process,  it will be
                        restarted by RTP."
            ::= { hiQNmFaultMgt 46 }
	    
hiQNmProcessExitedwithCodeTrap NOTIFICATION-TYPE
            OBJECTS { rtpEvtSequenceNumberIndex,
                      rtpEvtCurrId,
                      rtpEvtSet,                    -- 107
                      rtpEvtNum,                    -- 47
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Rtp process which name and pid are given exits with
	                 given code and to a given state."
            ::= { hiQNmFaultMgt 47 }	    
	    
hiQNmProcessTerminatedBySignalTrap NOTIFICATION-TYPE
            OBJECTS { rtpEvtSequenceNumberIndex,
                      rtpEvtCurrId,
                      rtpEvtSet,                    -- 107
                      rtpEvtNum,                    -- 48
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Rtp process which name and pid are given was killed
	                 by given signal while in a given status ."
            ::= { hiQNmFaultMgt 48 }	    

hiQNmProcessCoreCreatedTrap NOTIFICATION-TYPE
            OBJECTS { rtpEvtSequenceNumberIndex,
                      rtpEvtCurrId,
                      rtpEvtSet,                    -- 107
                      rtpEvtNum,                    -- 49
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The core is found in the directory $HOME/$PLID/core if
                        the core was written by RtpWriteCore()."
            ::= { hiQNmFaultMgt 49 }

hiQNmDiagnosticErrorTrap NOTIFICATION-TYPE
            OBJECTS { rtpEvtSequenceNumberIndex,
                      rtpEvtCurrId,
                      rtpEvtSet,                    -- 107
                      rtpEvtNum,                    -- 53
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The occurrence of this event is not necessarily a problem, but
                        it might help with diagnosing related problems."
            ::= { hiQNmFaultMgt 53 }

hiQNmNodeDownMsgErrorTrap NOTIFICATION-TYPE
            OBJECTS { rtpEvtSequenceNumberIndex,
                      rtpEvtCurrId,
                      rtpEvtSet,                    -- 107
                      rtpEvtNum,                    -- 102
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "When trying to send the NODEDOWN message to the specified node
                        an error occurred. The NODEDOWN message is very important for
                        an orderly termination of the shutdown."
            ::= { hiQNmFaultMgt 102 }

hiQNmNodeMgrSignalRestartTrap NOTIFICATION-TYPE
            OBJECTS { rtpEvtSequenceNumberIndex,
                      rtpEvtCurrId,
                      rtpEvtSet,                    -- 107
                      rtpEvtNum,                    -- 104
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "A signal of type SIGTERM, SIGINT or SIGQUIT was sent to the
                        node manager."
            ::= { hiQNmFaultMgt 104 }

-- *******************************
-- RTP Ticket Manager Traps
-- *******************************

hiQTicDiskFullTicketPoolFailed NOTIFICATION-TYPE
            OBJECTS { rtpEvtSequenceNumberIndex,
                      rtpEvtCurrId,
                      rtpEvtSet,                    -- 111
                      rtpEvtNum,                    -- 7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Configured ticket pool disk partition is full."
            ::= { hiQTicFaultMgt 7 }

hiQTicCopyToTicketPoolFailed NOTIFICATION-TYPE
            OBJECTS { rtpEvtSequenceNumberIndex,
                      rtpEvtCurrId,
                      rtpEvtSet,                    -- 111
                      rtpEvtNum,                    -- 23
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager tried to start an already
                        running subsystem." 
            ::= { hiQTicFaultMgt 23 }

hiQTicPoolDiskDevNotAccessible NOTIFICATION-TYPE
            OBJECTS { rtpEvtSequenceNumberIndex,
                      rtpEvtCurrId,
                      rtpEvtSet,                    -- 111
                      rtpEvtNum,                    -- 47
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Configured ticket pool disk device is not
                         accessible." 
            ::= { hiQTicFaultMgt 47 }

-- *******************************
-- RTP Super Node Manager Traps
-- *******************************

hiQSnmSubsysAlreadyRunningTrap NOTIFICATION-TYPE
            OBJECTS { rtpEvtSequenceNumberIndex,
                      rtpEvtCurrId,
                      rtpEvtSet,                    -- 119
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager tried to start an already
                        running subsystem." 
            ::= { hiQSnmFaultMgt 1 }

hiQSnmSubsystemStartErrorTrap NOTIFICATION-TYPE
            OBJECTS { rtpEvtSequenceNumberIndex,
                      rtpEvtCurrId,
                      rtpEvtSet,                    -- 119
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager can't start the mentioned subsystem.
                        The associated start script returns an error."
            ::= { hiQSnmFaultMgt 2 }

hiQSnmSubsystemStartSuccessTrap NOTIFICATION-TYPE
            OBJECTS { rtpEvtSequenceNumberIndex,
                      rtpEvtCurrId,
                      rtpEvtSet,                    -- 119
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager started the mentioned subsystem
                        successfully." 
            ::= { hiQSnmFaultMgt 3 }

hiQSnmSubsystemStopSuccessTrap NOTIFICATION-TYPE
            OBJECTS { rtpEvtSequenceNumberIndex,
                      rtpEvtCurrId,
                      rtpEvtSet,                    -- 119
                      rtpEvtNum,                    -- 6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager stopped the mentioned subsystem
                        successfully." 
            ::= { hiQSnmFaultMgt 6 }

hiQSnmSubsysAdmInterventionTrap NOTIFICATION-TYPE
            OBJECTS { rtpEvtSequenceNumberIndex,
                      rtpEvtCurrId,
                      rtpEvtSet,                    -- 119
                      rtpEvtNum,                    -- 7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The health detector script of the mentioned subsystem
                        requires an administrator intervention."
            ::= { hiQSnmFaultMgt 7 }

hiQSnmRtpRestartForSubsystemTrap NOTIFICATION-TYPE
            OBJECTS { rtpEvtSequenceNumberIndex,
                      rtpEvtCurrId,
                      rtpEvtSet,                    -- 119
                      rtpEvtNum,                    -- 10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The health detector script of the mentioned subsystem
                        requires to restart the whole RTP. Refer to
                        the logfile of the health detector script in
                        $HOME/$PLID/log for the reason."
            ::= { hiQSnmFaultMgt 10 }

hiQSnmRebootForSubsystemTrap NOTIFICATION-TYPE
            OBJECTS { rtpEvtSequenceNumberIndex,
                      rtpEvtCurrId,
                      rtpEvtSet,                    -- 119
                      rtpEvtNum,                    -- 11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The health detector script requires to reboot the
                        system. Refer to the logfile of the health detector
                        script in $HOME/$PLID/log for more informations."
            ::= { hiQSnmFaultMgt 11 }

hiQSnmSystemSwitchOffTrap NOTIFICATION-TYPE
            OBJECTS { rtpEvtSequenceNumberIndex,
                      rtpEvtCurrId,
                      rtpEvtSet,                    -- 119
                      rtpEvtNum,                    -- 13
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The health detector script requires to switch off
                        the system. Refer to the logfile of the health detector
                        script in $HOME/$PLID/log for more informations."
            ::= { hiQSnmFaultMgt 13 }

hiQSnmSpecialActScrSuccessTrap NOTIFICATION-TYPE
            OBJECTS { rtpEvtSequenceNumberIndex,
                      rtpEvtCurrId,
                      rtpEvtSet,                    -- 119
                      rtpEvtNum,                    -- 18
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The special action script of the mentioned subsystem
                        returns successfully." 
            ::= { hiQSnmFaultMgt 18 }

hiQSnmClusterChangeTrap NOTIFICATION-TYPE
            OBJECTS { rtpEvtSequenceNumberIndex,
                      rtpEvtCurrId,
                      rtpEvtSet,                    -- 119
                      rtpEvtNum,                    -- 20
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager detects a cluster change
                        via the interface to the cluster software." 
            ::= { hiQSnmFaultMgt 20 }

hiQSnmStartupSuccessTrap NOTIFICATION-TYPE
            OBJECTS { rtpEvtSequenceNumberIndex,
                      rtpEvtCurrId,
                      rtpEvtSet,                    -- 119
                      rtpEvtNum,                    -- 22
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager process started successfully."
            ::= { hiQSnmFaultMgt 22 }

hiQSnmStartupFailedTrap NOTIFICATION-TYPE
            OBJECTS { rtpEvtSequenceNumberIndex,
                      rtpEvtCurrId,
                      rtpEvtSet,                    -- 119
                      rtpEvtNum,                    -- 39
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager fails to start a single
                        subsystem during the start of the whole RTP. For
                        this reason, the start of the RTP cannot be
                        continued, and all subsystems having been started
                        so far, are stopped."
            ::= { hiQSnmFaultMgt 39 }

hiQSnmSubsysRestartSuccessTrap NOTIFICATION-TYPE
            OBJECTS { rtpEvtSequenceNumberIndex,
                      rtpEvtCurrId,
                      rtpEvtSet,                    -- 119
                      rtpEvtNum,                    -- 45
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager has tried to restart the
                        subsystem without success in the past, but now
                        the subsystem is detected as running again." 
            ::= { hiQSnmFaultMgt 45 }

hiQSnmSubsysRestartSuccDepTrap NOTIFICATION-TYPE
            OBJECTS { rtpEvtSequenceNumberIndex,
                      rtpEvtCurrId,
                      rtpEvtSet,                    -- 119
                      rtpEvtNum,                    -- 46
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager has tried to restart the
                        subsystem without success in the past, but now
                        the subsystem is detected as running again. The
                        super node manager will restart depending subsystems
                        as well." 
            ::= { hiQSnmFaultMgt 46 }

hiQSnmSubsysFailedTrap NOTIFICATION-TYPE
            OBJECTS { rtpEvtSequenceNumberIndex,
                      rtpEvtCurrId,
                      rtpEvtSet,                    -- 119
                      rtpEvtNum,                    -- 49
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager ran the detector for the given
                         subsystem, and it failed."
            ::= { hiQSnmFaultMgt 49 }

hiQSnmClusterChangeInfoSentTrap NOTIFICATION-TYPE
            OBJECTS { rtpEvtSequenceNumberIndex,
                      rtpEvtCurrId,
                      rtpEvtSet,                    -- 119
                      rtpEvtNum,                    -- 51
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager managed to inform the
                        local RTP node manager about a change in the
                        cluster configuration." 
            ::= { hiQSnmFaultMgt 51 }

hiQSnmRtpPlatformPlidReportTrap NOTIFICATION-TYPE
            OBJECTS { rtpEvtSequenceNumberIndex,
                      rtpEvtCurrId,
                      rtpEvtSet,                    -- 119
                      rtpEvtNum,                    -- 60
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager reports the ID with which
                        the RTP platform is started." 
            ::= { hiQSnmFaultMgt 60 }

hiQSnmRtpNodeUpTrap NOTIFICATION-TYPE
            OBJECTS { rtpEvtSequenceNumberIndex,
                      rtpEvtCurrId,
                      rtpEvtSet,                    -- 119
                      rtpEvtNum,                    -- 100
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager reports that the node is up."
            ::= { hiQSnmFaultMgt 100 }

hiQSnmRtpNodeUpWasDownTrap NOTIFICATION-TYPE
            OBJECTS { rtpEvtSequenceNumberIndex,
                      rtpEvtCurrId,
                      rtpEvtSet,                    -- 119
                      rtpEvtNum,                    -- 101
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager reports that the node that was
                         down is now up."
            ::= { hiQSnmFaultMgt 101 }

hiQSnmRtpNodeDownTrap NOTIFICATION-TYPE
            OBJECTS { rtpEvtSequenceNumberIndex,
                      rtpEvtCurrId,
                      rtpEvtSet,                    -- 119
                      rtpEvtNum,                    -- 102
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager reports that the node is down."
            ::= { hiQSnmFaultMgt 102 }

hiQSnmRtpNodeDownWasUpTrap NOTIFICATION-TYPE
            OBJECTS { rtpEvtSequenceNumberIndex,
                      rtpEvtCurrId,
                      rtpEvtSet,                    -- 119
                      rtpEvtNum,                    -- 103
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager reports that the node that was
                         up is now down."
            ::= { hiQSnmFaultMgt 103 }

hiQSnmNodeInfoMismatchTrap NOTIFICATION-TYPE
            OBJECTS { rtpEvtSequenceNumberIndex,
                      rtpEvtCurrId,
                      rtpEvtSet,                    -- 119
                      rtpEvtNum,                    -- 109
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager detects a mismatch between
                        the own node information (name and ID)  listed in
                        the RtpClustertab and the node information supplied
                        by the cluster software."
            ::= { hiQSnmFaultMgt 109 }

hiQSnmRmsWorkingAgainTrap NOTIFICATION-TYPE
            OBJECTS { rtpEvtSequenceNumberIndex,
                      rtpEvtCurrId,
                      rtpEvtSet,                    -- 119
                      rtpEvtNum,                    -- 135
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager finds that the RMS is working again after
                        a failure had been detected in the past. The Reliant Monitor System
                        is responsible for monitoring the cluster interconnect and
                        the current cluster configuration, i.e. which nodes currently belong
                        to the cluster and which do not."
            ::= { hiQSnmFaultMgt 135 }

hiQSnmSpsClusterSwInstalledTrap NOTIFICATION-TYPE
            OBJECTS { rtpEvtSequenceNumberIndex,
                      rtpEvtCurrId,
                      rtpEvtSet,                    -- 119
                      rtpEvtNum,                    -- 137
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager found that the SPS (Siemens Parallel Server)
                        cluster software is installed. It will retrieve its cluster configuration
                        information from SPS."
            ::= { hiQSnmFaultMgt 137 }

hiQSnmRmsClusterSwInstalledTrap NOTIFICATION-TYPE
            OBJECTS { rtpEvtSequenceNumberIndex,
                      rtpEvtCurrId,
                      rtpEvtSet,                    -- 119
                      rtpEvtNum,                    -- 139
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager found that the RMS cluster software is
                        installed. It will retrieve its cluster configuration information from
                        RMS. The Reliant Monitor System is responsible for monitoring the
                        cluster interconnect and the current cluster configuration, i.e.
                        which nodes currently belong to the cluster and which do not."
            ::= { hiQSnmFaultMgt 139 }

hiQSnmCfNodeStatusTrap NOTIFICATION-TYPE
            OBJECTS { rtpEvtSequenceNumberIndex,
                      rtpEvtCurrId,
                      rtpEvtSet,                    -- 119
                      rtpEvtNum,                    -- 145
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The status of the given CF (Cluster Foundation) node is reported
                        when the super node manager starts up or when a state change on
                        the node happened."
            ::= { hiQSnmFaultMgt 145 }

hiQPrimeClusterInstalledSnmTrap NOTIFICATION-TYPE
            OBJECTS { rtpEvtSequenceNumberIndex,
                      rtpEvtCurrId,
                      rtpEvtSet,                    -- 119
                      rtpEvtNum,                    -- 147
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The super node manager found that the PRIMECLUSTER/CF cluster
                        software is installed. It will retrieve its cluster configuration information
                        from CF (Cluster Foundation)."
            ::= { hiQSnmFaultMgt 147 }

hiQSnmSunCluster30InstalledTrap NOTIFICATION-TYPE
            OBJECTS { rtpEvtSequenceNumberIndex,
                      rtpEvtCurrId,
                      rtpEvtSet,                    -- 119
                      rtpEvtNum,                    -- 163
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The super node manager found that the SunCluster 3.0
                        cluster software is installed. It will retrieve its
                        cluster configuration information from SunCluster 3.0."
                        
            ::= { hiQSnmFaultMgt 163 }

hiQSnmSunCluster22InstalledTrap NOTIFICATION-TYPE
            OBJECTS { rtpEvtSequenceNumberIndex,
                      rtpEvtCurrId,
                      rtpEvtSet,                    -- 119
                      rtpEvtNum,                    -- 173
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The super node manager found that the Sun Cluster
                        2.2 cluster software is installed. It will retrieve
                        its cluster configuration information from Sun
                        Cluster 2.2." 
            ::= { hiQSnmFaultMgt 173 }


-- *******************************
-- RTP Oracle Traps
-- *******************************

hiQLogOracleDeadlockDetectedTrap NOTIFICATION-TYPE
            OBJECTS { rtpEvtSequenceNumberIndex,
                      rtpEvtCurrId,
                      rtpEvtSet,                    -- 140
                      rtpEvtNum,                    -- 104
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "All available public servers are servicing requests that require
                        resources locked by a client which is unable to get a public server
                        to release the resources. The number of servers is limited by
                        the system parameter MTS_MAX_SERVER."
            ::= { hiQLogOracleFaultMgt 104 }

hiQLogOracleDbStartShutErrorTrap NOTIFICATION-TYPE
            OBJECTS { rtpEvtSequenceNumberIndex,
                      rtpEvtCurrId,
                      rtpEvtSet,                    -- 140
                      rtpEvtNum,                    -- 106
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "An attempt was made to start or shut down an
                        instance while connected to a shared server via
                        a dispatcher."
            ::= { hiQLogOracleFaultMgt 106 }

hiQLogOracleRecovSessionCnclTrap NOTIFICATION-TYPE
            OBJECTS { rtpEvtSequenceNumberIndex,
                      rtpEvtCurrId,
                      rtpEvtSet,                    -- 140
                      rtpEvtNum,                    -- 283
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "An error during recovery was determined to
                        be fatal enough to end the current recovery session."
            ::= { hiQLogOracleFaultMgt 283 }

hiQLogOracleBackProcessFatalTrap NOTIFICATION-TYPE
            OBJECTS { rtpEvtSequenceNumberIndex,
                      rtpEvtCurrId,
                      rtpEvtSet,                    -- 140
                      rtpEvtNum,                    -- 447
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "One of the background processes died unexpectedly. The background
                        trace file in BACKGROUND_DUMP_DEST may have more information."
            ::= { hiQLogOracleFaultMgt 447 }

hiQLogOracleServerSessFatalTrap NOTIFICATION-TYPE
            OBJECTS { rtpEvtSequenceNumberIndex,
                      rtpEvtCurrId,
                      rtpEvtSet,                    -- 140
                      rtpEvtNum,                    -- 603
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "An Oracle Server session is in an unrecoverable state."
            ::= { hiQLogOracleFaultMgt 603 }

hiQLogOracleFatalConnErrorTrap NOTIFICATION-TYPE
            OBJECTS { rtpEvtSequenceNumberIndex,
                      rtpEvtCurrId,
                      rtpEvtSet,                    -- 140
                      rtpEvtNum,                    -- 1073
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "An illegal internal operation was attempted."
            ::= { hiQLogOracleFaultMgt 1073 }

hiQLogOracleFatalLogMinerTrap NOTIFICATION-TYPE
            OBJECTS { rtpEvtSequenceNumberIndex,
                      rtpEvtCurrId,
                      rtpEvtSet,                    -- 140
                      rtpEvtNum,                    -- 1280
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "One of the following: - One or more input parameters in the
                        DBMS_LOGMNR.START_LOGMNR() procedure may be invalid.   
                        - The start or the end SCN may not be available in the log
                        files selected.     - The dictionary file specified may be
                        from a different database."
            ::= { hiQLogOracleFaultMgt 1280 }

hiQLogOracleSevereErrorTrap NOTIFICATION-TYPE
            OBJECTS { rtpEvtSequenceNumberIndex,
                      rtpEvtCurrId,
                      rtpEvtSet,                    -- 140
                      rtpEvtNum,                    -- 2068
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "A severe error (disconnect, fatal Oracle error) was received from
                        the indicated database link."
            ::= { hiQLogOracleFaultMgt 2068 }

hiQLogOracleTwoTaskCommErrorTrap NOTIFICATION-TYPE
            OBJECTS { rtpEvtSequenceNumberIndex,
                      rtpEvtCurrId,
                      rtpEvtSet,                    -- 140
                      rtpEvtNum,                    -- 3106
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The communication path between Oracle and the
                        user task has stopped. This is an internal error
                        message not usually issued."
            ::= { hiQLogOracleFaultMgt 3106 }

hiQLogOracleDisconnectFailTrap NOTIFICATION-TYPE
            OBJECTS { rtpEvtSequenceNumberIndex,
                      rtpEvtCurrId,
                      rtpEvtSet,                    -- 140
                      rtpEvtNum,                    -- 6300
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "A fatal error occurred during the disconnect from
                        the server. This was probably caused by inaccessible message
                        queues."
            ::= { hiQLogOracleFaultMgt 6300 }

hiQLogOracleIpaResetConnErrTrap NOTIFICATION-TYPE
            OBJECTS { rtpEvtSequenceNumberIndex,
                      rtpEvtCurrId,
                      rtpEvtSet,                    -- 140
                      rtpEvtNum,                    -- 6307
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "A fatal error occurred during the resetting of
                        the connection."
            ::= { hiQLogOracleFaultMgt 6307 }

hiQLogOracleIpaEvtSetupFailTrap NOTIFICATION-TYPE
            OBJECTS { rtpEvtSequenceNumberIndex,
                      rtpEvtCurrId,
                      rtpEvtSet,                    -- 140
                      rtpEvtNum,                    -- 6314
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "Fatal interprocess communication error."
            ::= { hiQLogOracleFaultMgt 6314 }

hiQLogOracleIpaSharedMemErrTrap NOTIFICATION-TYPE
            OBJECTS { rtpEvtSequenceNumberIndex,
                      rtpEvtCurrId,
                      rtpEvtSet,                    -- 140
                      rtpEvtNum,                    -- 6322
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "An internal error has occurred in the shared memory
                        handling."
            ::= { hiQLogOracleFaultMgt 6322 }

hiQLogOracleIpaCauseEventErrTrap NOTIFICATION-TYPE
            OBJECTS { rtpEvtSequenceNumberIndex,
                      rtpEvtCurrId,
                      rtpEvtSet,                    -- 140
                      rtpEvtNum,                    -- 6323
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "Fatal interprocess communication error."
            ::= { hiQLogOracleFaultMgt 6323 }

hiQLogOracleRemFileServerErrTrap NOTIFICATION-TYPE
            OBJECTS { rtpEvtSequenceNumberIndex,
                      rtpEvtCurrId,
                      rtpEvtSet,                    -- 140
                      rtpEvtNum,                    -- 16041
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The Remote File Server (RFS) process at the
                        standby destination archive log site has encountered
                        a disabling error and is no longer available. Further
                        archiving to the standby site may not be possible."
            ::= { hiQLogOracleFaultMgt 16041 }

hiQLogOracleProgramTermByErrTrap NOTIFICATION-TYPE
            OBJECTS { rtpEvtSequenceNumberIndex,
                      rtpEvtCurrId,
                      rtpEvtSet,                    -- 140
                      rtpEvtNum,                    -- 21503
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "A program is in an unrecoverable error state."
            ::= { hiQLogOracleFaultMgt 21503 }

hiQLogOracleRemPortConnErrTrap NOTIFICATION-TYPE
            OBJECTS { rtpEvtSequenceNumberIndex,
                      rtpEvtCurrId,
                      rtpEvtSet,                    -- 140
                      rtpEvtNum,                    -- 27541
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "Either the remote address is not valid,  or the process is
                        in a state which does not allow connection."
            ::= { hiQLogOracleFaultMgt 27541 }

hiQLogOracleLostRpcConnRemTrap NOTIFICATION-TYPE
            OBJECTS { rtpEvtSequenceNumberIndex,
                      rtpEvtCurrId,
                      rtpEvtSet,                    -- 140
                      rtpEvtNum,                    -- 28511
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "A fatal error occurred in one of the following places: the
                        connection between the Oracle server and the agent, the heterogeneous
                        services remote agent itself, the connection to the non-Oracle
                        system. This error occurred after loss of  communicatio."
            ::= { hiQLogOracleFaultMgt 28511 }

hiQLogOracleLostRpcConnExtTrap NOTIFICATION-TYPE
            OBJECTS { rtpEvtSequenceNumberIndex,
                      rtpEvtCurrId,
                      rtpEvtSet,                    -- 140
                      rtpEvtNum,                    -- 28576
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "A fatal error occurred in either an RPC network
                        connection, the external procedure agent, or
                        the invoked 3GL after communication had been established
                        successfully."
            ::= { hiQLogOracleFaultMgt 28576 }

-- *******************************
-- RTP Solid Traps
-- *******************************

hiQSolidTooManyClientsTrap NOTIFICATION-TYPE
            OBJECTS { rtpEvtSequenceNumberIndex,
                      rtpEvtCurrId,
                      rtpEvtSet,                    -- 141
                      rtpEvtNum,                    -- 12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The specified user failed to connect due to
                         too many connected clients."
            ::= { hiQLogSolidFaultMgt 12 }

hiQSolidNewConnsAllowedTrap NOTIFICATION-TYPE
            OBJECTS { rtpEvtSequenceNumberIndex,
                      rtpEvtCurrId,
                      rtpEvtSet,                    -- 141
                      rtpEvtNum,                    -- 13
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "New database connections are allowed."
            ::= { hiQLogSolidFaultMgt 13 }

hiQSolidNoNewConnsAllowedTrap NOTIFICATION-TYPE
            OBJECTS { rtpEvtSequenceNumberIndex,
                      rtpEvtCurrId,
                      rtpEvtSet,                    -- 141
                      rtpEvtNum,                    -- 20
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database server is in a fatal state
                         - no new connections are allowed."
            ::= { hiQLogSolidFaultMgt 20 }

hiQSolidFlowEngineStartedTrap NOTIFICATION-TYPE
            OBJECTS { rtpEvtSequenceNumberIndex,
                      rtpEvtCurrId,
                      rtpEvtSet,                    -- 141
                      rtpEvtNum,                    -- 119
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database server was started."
            ::= { hiQLogSolidFaultMgt 119 }

hiQSolidServerStartFailedTrap NOTIFICATION-TYPE
            OBJECTS { rtpEvtSequenceNumberIndex,
                      rtpEvtCurrId,
                      rtpEvtSet,                    -- 141
                      rtpEvtNum,                    -- 120
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database failed to start."
            ::= { hiQLogSolidFaultMgt 120 }

hiQSolidFlowEngineIntErrorTrap  NOTIFICATION-TYPE
            OBJECTS { rtpEvtSequenceNumberIndex,
                      rtpEvtCurrId,
                      rtpEvtSet,                    -- 141
                      rtpEvtNum,                    -- 130
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid FlowEngine process has encountered
                         an internal error and is unable to continue normally."
            ::= { hiQLogSolidFaultMgt 130 }

hiQSolidFatalErrSrvShutdownTrap NOTIFICATION-TYPE
            OBJECTS { rtpEvtSequenceNumberIndex,
                      rtpEvtCurrId,
                      rtpEvtSet,                    -- 141
                      rtpEvtNum,                    -- 149
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "An emergency shutdown of the Solid database
                         server has occurred due to a fatal error."
            ::= { hiQLogSolidFaultMgt 149 }

hiQSolidFatalErrSrvNotStartTrap NOTIFICATION-TYPE
            OBJECTS { rtpEvtSequenceNumberIndex,
                      rtpEvtCurrId,
                      rtpEvtSet,                    -- 141
                      rtpEvtNum,                    -- 150
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database server was not started due
                         to a fatal error."
            ::= { hiQLogSolidFaultMgt 150 }

hiQSolidDatabaseStartedTrap NOTIFICATION-TYPE
            OBJECTS { rtpEvtSequenceNumberIndex,
                      rtpEvtCurrId,
                      rtpEvtSet,                    -- 141
                      rtpEvtNum,                    -- 151
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database was started."
            ::= { hiQLogSolidFaultMgt 151 }

hiQSolidDbConvertedTrap NOTIFICATION-TYPE
            OBJECTS { rtpEvtSequenceNumberIndex,
                      rtpEvtCurrId,
                      rtpEvtSet,                    -- 141
                      rtpEvtNum,                    -- 201
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database was successfully converted."
            ::= { hiQLogSolidFaultMgt 201 }

hiQSolidOldDbVersionTrap NOTIFICATION-TYPE
            OBJECTS { rtpEvtSequenceNumberIndex,
                      rtpEvtCurrId,
                      rtpEvtSet,                    -- 141
                      rtpEvtNum,                    -- 204
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database is from an older version of
                         Solid."
            ::= { hiQLogSolidFaultMgt 204 }

hiQSolidNewDbNotCreatedTrap NOTIFICATION-TYPE
            OBJECTS { rtpEvtSequenceNumberIndex,
                      rtpEvtCurrId,
                      rtpEvtSet,                    -- 141
                      rtpEvtNum,                    -- 205
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The new Solid database was not created."
            ::= { hiQLogSolidFaultMgt 205 }

hiQSolidDbDoesNotExistsTrap NOTIFICATION-TYPE
            OBJECTS { rtpEvtSequenceNumberIndex,
                      rtpEvtCurrId,
                      rtpEvtSet,                    -- 141
                      rtpEvtNum,                    -- 206
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database does not exist."
            ::= { hiQLogSolidFaultMgt 206 }

hiQSolidDbOpenFailureTrap NOTIFICATION-TYPE
            OBJECTS { rtpEvtSequenceNumberIndex,
                      rtpEvtCurrId,
                      rtpEvtSet,                    -- 141
                      rtpEvtNum,                    -- 207
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database failed to open."
            ::= { hiQLogSolidFaultMgt 207 }

hiQSolidDbIndexTestSuccessTrap NOTIFICATION-TYPE
            OBJECTS { rtpEvtSequenceNumberIndex,
                      rtpEvtCurrId,
                      rtpEvtSet,                    -- 141
                      rtpEvtNum,                    -- 224
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database index has been tested and
                         is OK."
            ::= { hiQLogSolidFaultMgt 224 }

hiQSolidDbIndexErrorTrap NOTIFICATION-TYPE
            OBJECTS { rtpEvtSequenceNumberIndex,
                      rtpEvtCurrId,
                      rtpEvtSet,                    -- 141
                      rtpEvtNum,                    -- 225
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The index for the specified Solid database is
                         not OK."
            ::= { hiQLogSolidFaultMgt 225 }

hiQSolidDbTstOpenFailureTrap NOTIFICATION-TYPE
            OBJECTS { rtpEvtSequenceNumberIndex,
                      rtpEvtCurrId,
                      rtpEvtSet,                    -- 141
                      rtpEvtNum,                    -- 226
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database failed to open for testing
                         with a fatal error."
            ::= { hiQLogSolidFaultMgt 226 }

hiQSolidDbTstConnectFailureTrap NOTIFICATION-TYPE
            OBJECTS { rtpEvtSequenceNumberIndex,
                      rtpEvtCurrId,
                      rtpEvtSet,                    -- 141
                      rtpEvtNum,                    -- 227
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database failed to connect for
                         testing with a fatal error."
            ::= { hiQLogSolidFaultMgt 227 }

hiQSolidCreateNewDbFailedTrap NOTIFICATION-TYPE
            OBJECTS { rtpEvtSequenceNumberIndex,
                      rtpEvtCurrId,
                      rtpEvtSet,                    -- 141
                      rtpEvtNum,                    -- 240
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "A failure occurred when creating a new Solid database."
            ::= { hiQLogSolidFaultMgt 240 }

hiQSolidTableConvertedTrap NOTIFICATION-TYPE
            OBJECTS { rtpEvtSequenceNumberIndex,
                      rtpEvtCurrId,
                      rtpEvtSet,                    -- 141
                      rtpEvtNum,                    -- 247
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The specified Solid database table was converted."
            ::= { hiQLogSolidFaultMgt 247 }

hiQSolidDbOpeningProblemTrap NOTIFICATION-TYPE
            OBJECTS { rtpEvtSequenceNumberIndex,
                      rtpEvtCurrId,
                      rtpEvtSet,                    -- 141
                      rtpEvtNum,                    -- 249
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "A problem was encountered when opening a Solid
                         database."
            ::= { hiQLogSolidFaultMgt 249 }

hiQSolidDbBrokenCopyTrap NOTIFICATION-TYPE
            OBJECTS { rtpEvtSequenceNumberIndex,
                      rtpEvtCurrId,
                      rtpEvtSet,                    -- 141
                      rtpEvtNum,                    -- 254
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database is a broken hot standby or
                         netcopy database."
            ::= { hiQLogSolidFaultMgt 254 }

hiQSolidBackupSuccessTrap NOTIFICATION-TYPE
            OBJECTS { rtpEvtSequenceNumberIndex,
                      rtpEvtCurrId,
                      rtpEvtSet,                    -- 141
                      rtpEvtNum,                    -- 300
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid backup completed successfully."
            ::= { hiQLogSolidFaultMgt 300 }

hiQSolidBackupFailedTrap NOTIFICATION-TYPE
            OBJECTS { rtpEvtSequenceNumberIndex,
                      rtpEvtCurrId,
                      rtpEvtSet,                    -- 141
                      rtpEvtNum,                    -- 304
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid backup failed."
            ::= { hiQLogSolidFaultMgt 304 }

hiQSolidStartedHSBPrimaryTrap NOTIFICATION-TYPE
            OBJECTS { rtpEvtSequenceNumberIndex,
                      rtpEvtCurrId,
                      rtpEvtSet,                    -- 141
                      rtpEvtNum,                    -- 500
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Started as a hot standby primary."
            ::= { hiQLogSolidFaultMgt 500 }

hiQSolidStartedHSBSecondaryTrap NOTIFICATION-TYPE
            OBJECTS { rtpEvtSequenceNumberIndex,
                      rtpEvtCurrId,
                      rtpEvtSet,                    -- 141
                      rtpEvtNum,                    -- 501
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Started as a hot standby secondary."
            ::= { hiQLogSolidFaultMgt 501 }

hiQSolidHSBSwitchPrimErrTrap NOTIFICATION-TYPE
            OBJECTS { rtpEvtSequenceNumberIndex,
                      rtpEvtCurrId,
                      rtpEvtSet,                    -- 141
                      rtpEvtNum,                    -- 512
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Failed to switch hot standby role to primary
                         with the specified error."
            ::= { hiQLogSolidFaultMgt 512 }

hiQSolidHSBSwitchSecErrTrap NOTIFICATION-TYPE
            OBJECTS { rtpEvtSequenceNumberIndex,
                      rtpEvtCurrId,
                      rtpEvtSet,                    -- 141
                      rtpEvtNum,                    -- 513
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Failed to switch hot standby role to secondary
                         with the specified error."
            ::= { hiQLogSolidFaultMgt 513 }

hiQSolidBothHSBDbPrimaryTrap NOTIFICATION-TYPE
            OBJECTS { rtpEvtSequenceNumberIndex,
                      rtpEvtCurrId,
                      rtpEvtSet,                    -- 141
                      rtpEvtNum,                    -- 515
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Both Solid hot standby databases are marked as
                         primary."
            ::= { hiQLogSolidFaultMgt 515 }

hiQSolidDatabaseStarted2Trap NOTIFICATION-TYPE
            OBJECTS { rtpEvtSequenceNumberIndex,
                      rtpEvtCurrId,
                      rtpEvtSet,                    -- 141
                      rtpEvtNum,                    -- 572
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The Solid database was started."
            ::= { hiQLogSolidFaultMgt 572 }

hiQSolidDbServerCorruptTrap NOTIFICATION-TYPE
            OBJECTS { rtpEvtSequenceNumberIndex,
                      rtpEvtCurrId,
                      rtpEvtSet,                    -- 141
                      rtpEvtNum,                    -- 1101
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The single database server is corrupted."
            ::= { hiQLogSolidFaultMgt 1101 }

hiQSolidLocalDbServerCorruptTrap NOTIFICATION-TYPE
            OBJECTS { rtpEvtSequenceNumberIndex,
                      rtpEvtCurrId,
                      rtpEvtSet,                    -- 141
                      rtpEvtNum,                    -- 1103
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The local database server is corrupted."
            ::= { hiQLogSolidFaultMgt 1103 }

-- *******************************
-- MGCP Fault Management Traps
-- *******************************

hiQMgcpNoResponseTrap NOTIFICATION-TYPE
            OBJECTS { rtpEvtSequenceNumberIndex,
                      rtpEvtCurrId,
                      rtpEvtSet,                    -- 178
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "MGCP: This trap indicates the processing error due to 
                        no response from Media Gateway."
            ::= { hiQMgcpFaultMgmt 2 }

hiQMgcpMtaTimeOutMsgTrap NOTIFICATION-TYPE
            OBJECTS { rtpEvtSequenceNumberIndex,
                      rtpEvtCurrId,
                      rtpEvtSet,                    -- 178
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "MGCP: This trap indicates that the NCS Media Gateway 
                         endpoint does not respond to the following message 
                         from hiQ 8000, namely, the timer has expired:

                         msg                               msgType
                         **********************************************       
                         CreateConnection                  CRCX

                         ModifyConnection                  MDCX

                         DeleteConnection                  DLCX

                         NotificationRequest               RQNT

                         AuditEndpoint                     AUEP
                         **********************************************       


                         rtpEvtShortText will be as follows:

                         msgType TransactionID EndPointID@Hostname Protocol

                         where:

                         msgType                             as in the above table 

                         TransactionID                       0..999,999,999
                
                         EndPointID(Id for Line/DS0)  aaln/1, aaln/2, aaln/3, aaln/4  

                         Hostname                            FQDN 

                         Protocol                            MGCP 1.0 NCS 1.0
 

                         For example: 
                         CRCX 18 aaln/1@motomta101.ipfonix.com  MGCP 1.0 NCS 1.0

                         This trap is informational. There is no corresponding trap
                         for its abatement(clear).

                         To avoid flooding the element manager system, this trap will be
                         suppressed if the same msgType is received from the same 
                         hostname twice in a pre-determined suppresion interval 
                         of 15 seconds."
            ::= { hiQMgcpFaultMgmt 3 }

hiQMgcpInvalidRxMsgTrap NOTIFICATION-TYPE
            OBJECTS { rtpEvtSequenceNumberIndex,
                      rtpEvtCurrId,
                      rtpEvtSet,                    -- 178
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "MGCP: This trap indicates the processing error due to
                         receiving invalid messages."
            ::= { hiQMgcpFaultMgmt 4 }

hiQMgcpMtaErrorCodeReasonMsgTrap NOTIFICATION-TYPE
            OBJECTS { rtpEvtSequenceNumberIndex,
                      rtpEvtCurrId,
                      rtpEvtSet,                    -- 178
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "MGCP: This trap indicates NCS Media Gateway endpoint has 
                         reported an ErrorCode or a Reason Code:

                         error
                         code      commentary
                         ++++++++++++++++++++++++++++++++++++++++++++++++++++++++
                         400       The transaction could not be executed, due to 
                                   a transient error
                         502       The transaction could not be executed because the 
                                   endpoint does not have sufficient resources
                         504       Unknown or unsupported command (this code is in 
                                   RFC3435, but not in PacketCable NCS I07)
                         507       Unsupported functionality (this code is in RFC3435,
                                   but not in PacketCable NCS I07)
                         508       Unknown or unsupported quarantine handling
                         510       The transaction could not be executed because a 
                                   protocol error was detected
                         516       The transaction refers to an unknown call-id
                         518       Unsupported or unkown package
                         520       The transaction could not be executed because 
                                   the endpoint is restarting
                         526       Insufficient bandwidth
                         528       Incompatible protocol version
                         529       Internal hardware failure
                         534       Codec negotiation failure^M
            
                         reason
                         code      commentary 
                         ++++++++++++++++++++++++++++++++++++++++++++++++++++++++++
                         900       Endpoint malfunctioning
                         901       Endpoint taken out of service
                         902       Loss of lower layer connectivity (e.g., downstream 
                                   sync)
                         903       QoS resource reservation was lost

                         An example of rtpEvtShortText will be as follows:
                         
                         errorCode or reasonCode Commentary TransactionID 
                         EndPointID@Hostname Protocol

                         where:

                         error code or reason code           as in the above 
                       
                         Commentary                          as in the above

                         TransactionID                       0..999,999,999
                                 
                         EndPointID(Id for the Line or DS0)  aaln/1, aaln/2, aaln/3, aaln/4 
                 
                         Hostname                            fully qualified domain name

                         Protocol                            MGCP 1.0 NCS 1.0
 
                         An example of rtpEvtShortText will be as follows:

                         520 Endpoint malfunctioning 18 aaln/1@motomta101.ipfonix.com  MGCP 1.                              0 NCS 1.0

                         This trap is informational. There is no corresponding trap for its 
                                               its abatement(clear).
                          To avoid flooding the element manager system, this trap will be 
                         suppressed if the same msgType is received from the same hostname  
                         twice in a pre-determined suppresion interval of 15 seconds."
            ::= { hiQMgcpFaultMgmt 5 }

hiQCcmStatMgmtStartedUp NOTIFICATION-TYPE
            OBJECTS { rtpEvtSequenceNumberIndex,
                      rtpEvtCurrId,
                      rtpEvtSet,                   -- 178
                      rtpEvtNum,                   -- 8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The Ccm Statistics Manager started properly."
            ::= { hiQMgcpFaultMgmt 8 }

hiQCcmStatMgmtStartupFailed NOTIFICATION-TYPE
            OBJECTS { rtpEvtSequenceNumberIndex,
                      rtpEvtCurrId,
                      rtpEvtSet,                   -- 178
                      rtpEvtNum,                   -- 9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The Ccm Statistics Manager failed to start properly."
            ::= { hiQMgcpFaultMgmt 9 }


hiQMgcp500ResponseMsgs NOTIFICATION-TYPE
            OBJECTS { rtpEvtSequenceNumberIndex,
                      rtpEvtCurrId,
                      rtpEvtSet,                   -- 178
                      rtpEvtNum,                   -- 10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "Msg sent to invalid address <MTA ListenAddress> or
                         ckt::<MTA FQDN>. This trap is requested when CCM
                         receives 500 response from MTA, even after message
                         sent to the DNS Query resulted new IP Address for
                         the MTA."
            ::= { hiQMgcpFaultMgmt 10 }

hiQMgcpInvalidMTARecognized NOTIFICATION-TYPE
            OBJECTS { rtpEvtSequenceNumberIndex,
                      rtpEvtCurrId,
                      rtpEvtSet,                   -- 178
                      rtpEvtNum,                   -- 11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The MTA is not recognized."
            ::= { hiQMgcpFaultMgmt 11 }

-- *******************************
-- AUC, AUTH Fault Management Traps
-- *******************************

hiQAucClientInitTrap NOTIFICATION-TYPE
            OBJECTS { rtpEvtSequenceNumberIndex,
                      rtpEvtCurrId,
                      rtpEvtSet,                    -- 181
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: Authentication client is initialized."
            ::= { hiQAucAuthFaultMgmt 2 }

hiQAucClientImproperInitTrap NOTIFICATION-TYPE
            OBJECTS { rtpEvtSequenceNumberIndex,
                      rtpEvtCurrId,
                      rtpEvtSet,                    -- 181
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: Authentication client is improperly initialized."
            ::= { hiQAucAuthFaultMgmt 3 }

hiQAucAuthRtpMsgTxTrap NOTIFICATION-TYPE
            OBJECTS { rtpEvtSequenceNumberIndex,
                      rtpEvtCurrId,
                      rtpEvtSet,                    -- 181
                      rtpEvtNum,                    -- 10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: RTP message is not properly sent from
                         Authentication server."
            ::= { hiQAucAuthFaultMgmt 10 }

hiQAucAuthServerLinkDownTrap NOTIFICATION-TYPE
            OBJECTS { rtpEvtSequenceNumberIndex,
                      rtpEvtCurrId,
                      rtpEvtSet,                    -- 181
                      rtpEvtNum,                    -- 15
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: Link to A3 database from Authentication server is
                         down."
            ::= { hiQAucAuthFaultMgmt 15 }

hiQAucAuthServerLinkUpTrap NOTIFICATION-TYPE
            OBJECTS { rtpEvtSequenceNumberIndex,
                      rtpEvtCurrId,
                      rtpEvtSet,                    -- 181
                      rtpEvtNum,                    -- 14
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: Link to A3 database from Authentication server is
                         up. This will clear A3 link down trap."
            ::= { hiQAucAuthFaultMgmt 14 }

-- *******************************
-- AUC, USC Fault Management Traps
-- *******************************

hiQAucUscClientInitTrap NOTIFICATION-TYPE
            OBJECTS { rtpEvtSequenceNumberIndex,
                      rtpEvtCurrId,
                      rtpEvtSet,                    -- 182
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: Usage Collection client is initialized."
            ::= { hiQAucUscFaultMgmt 1 }

hiQAucUscClientImproperInitTrap NOTIFICATION-TYPE
            OBJECTS { rtpEvtSequenceNumberIndex,
                      rtpEvtCurrId,
                      rtpEvtSet,                    -- 182
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: Usage Collection client is improperly
                         initialized."
            ::= { hiQAucUscFaultMgmt 2 }

hiQAucUscServerInitTrap NOTIFICATION-TYPE
            OBJECTS { rtpEvtSequenceNumberIndex,
                      rtpEvtCurrId,
                      rtpEvtSet,                    -- 182
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: Usage Collection server is initialized."
            ::= { hiQAucUscFaultMgmt 3 }

hiQAucUscServerImproperInitTrap NOTIFICATION-TYPE
            OBJECTS { rtpEvtSequenceNumberIndex,
                      rtpEvtCurrId,
                      rtpEvtSet,                    -- 182
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: Usage Collection server is improperly
                         initialized."
            ::= { hiQAucUscFaultMgmt 4 }

hiQAucUscServerFtpUpTrap NOTIFICATION-TYPE
            OBJECTS { rtpEvtSequenceNumberIndex,
                      rtpEvtCurrId,
                      rtpEvtSet,                    -- 182
                      rtpEvtNum,                    -- 9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "AUC: Link to Primary FTP site from Usage Collection
                         server is up. It clears the Link Down trap for FTP
                         site."
            ::= { hiQAucUscFaultMgmt 9 }

hiQAucUscServerFtpDownTrap NOTIFICATION-TYPE
            OBJECTS { rtpEvtSequenceNumberIndex,
                      rtpEvtCurrId,
                      rtpEvtSet,                    -- 182
                      rtpEvtNum,                    -- 10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION
                    "AUC: Link to Primary FTP site from Usage Collection server is down." 
            ::= { hiQAucUscFaultMgmt 10 }

hiQAucUscServerDeleteCdrTrap NOTIFICATION-TYPE
            OBJECTS { rtpEvtSequenceNumberIndex,
                      rtpEvtCurrId,
                      rtpEvtSet,                    -- 182
                      rtpEvtNum,                    -- 12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: Usage Collection Server is unable to delete CDR
                         file from RTP."
            ::= { hiQAucUscFaultMgmt 12 }

hiQAucUscServerRxCdrTrap NOTIFICATION-TYPE
            OBJECTS { rtpEvtSequenceNumberIndex,
                      rtpEvtCurrId,
                      rtpEvtSet,                    -- 182
                      rtpEvtNum,                    -- 14
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: Usage Collection server has failed to receive
                         CDR file from RTP." 
            ::= { hiQAucUscFaultMgmt 14 }

hiQAucUscServerTxCdrTrap NOTIFICATION-TYPE
            OBJECTS { rtpEvtSequenceNumberIndex,
                      rtpEvtCurrId,
                      rtpEvtSet,                    -- 182
                      rtpEvtNum,                    -- 15
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION
                    "AUC: Usage Collection server has failed to send CDR file to FTP site." 
            ::= { hiQAucUscFaultMgmt 15 }

hiQAucUscServerBackupUpTrap NOTIFICATION-TYPE
            OBJECTS { rtpEvtSequenceNumberIndex,
                      rtpEvtCurrId,
                      rtpEvtSet,                    -- 182
                      rtpEvtNum,                    -- 16
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "AUC: Link to Backup FTP site from Usage Collection
                         server is up."
            ::= { hiQAucUscFaultMgmt 16 }

hiQAucUscServerBackupDownTrap NOTIFICATION-TYPE
            OBJECTS { rtpEvtSequenceNumberIndex,
                      rtpEvtCurrId,
                      rtpEvtSet,                    -- 182
                      rtpEvtNum,                    -- 17
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "AUC: Link to Backup FTP site from Usage Collection
                         server is down."
            ::= { hiQAucUscFaultMgmt 17 }

hiQAucUscServerFaultyBillingTrap NOTIFICATION-TYPE
            OBJECTS { rtpEvtSequenceNumberIndex,
                      rtpEvtCurrId,
                      rtpEvtSet,                    -- 182
                      rtpEvtNum,                    -- 19
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "AUC: Usage Collection Server trap: Faulty Billing File
                         is being sent to Billing Server as binary and marked as
                         an error."
            ::= { hiQAucUscFaultMgmt 19 }

hiQAucUscPriStorNotPossibleTrap NOTIFICATION-TYPE
            OBJECTS { rtpEvtSequenceNumberIndex,
                      rtpEvtCurrId,
                      rtpEvtSet,                    -- 182
                      rtpEvtNum,                    -- 35
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "Primary storage of CDR billing data is no
                         longer possible on this node. This may be
                         caused by lack of disk space or the cdr
                         disk partition is not writable."
            ::= { hiQAucUscFaultMgmt 35 }

hiQAucUscPriStorOKTrap NOTIFICATION-TYPE
            OBJECTS { rtpEvtSequenceNumberIndex,
                      rtpEvtCurrId,
                      rtpEvtSet,                    -- 182
                      rtpEvtNum,                    -- 36
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "Primary storage of CDR billing data is
                         possible on this node."
            ::= { hiQAucUscFaultMgmt 36 }

hiQAucUscSecStorNotPossibleTrap NOTIFICATION-TYPE
            OBJECTS { rtpEvtSequenceNumberIndex,
                      rtpEvtCurrId,
                      rtpEvtSet,                    -- 182
                      rtpEvtNum,                    -- 37
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "Secondary storage of CDR billing data is no
                         longer possible on this node. This may be
                         caused by lack of disk space or the cdr
                         disk partition is not writable."
            ::= { hiQAucUscFaultMgmt 37 }

hiQAucUscFileSeqNumberErrorTrap NOTIFICATION-TYPE
            OBJECTS { rtpEvtSequenceNumberIndex,
                      rtpEvtCurrId,
                      rtpEvtSet,                    -- 182
                      rtpEvtNum,                    -- 38
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "The CDR file sequence number may be incorrect.
                         This is caused by a database read or write
                         error."
            ::= { hiQAucUscFaultMgmt 38 }

hiQAucUscLocalSecStorageOk NOTIFICATION-TYPE
            OBJECTS { rtpEvtSequenceNumberIndex,
                      rtpEvtCurrId,
                      rtpEvtSet,                    -- 182
                      rtpEvtNum,                    -- 39
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "Secondary storage of CDR billing data is OK on
                         this node."
            ::= { hiQAucUscFaultMgmt 39 }

hiQAucUscStbPriFTPLinkUp NOTIFICATION-TYPE
            OBJECTS { rtpEvtSequenceNumberIndex,
                      rtpEvtCurrId,
                      rtpEvtSet,                    -- 182
                      rtpEvtNum,                    -- 40
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "Usage collection: Standby primary ftp link is
                         up."
            ::= { hiQAucUscFaultMgmt 40 }

hiQAucUscStbPriFTPLinkDown NOTIFICATION-TYPE
            OBJECTS { rtpEvtSequenceNumberIndex,
                      rtpEvtCurrId,
                      rtpEvtSet,                    -- 182
                      rtpEvtNum,                    -- 41
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "Usage collection: Standby primary ftp link is
                         down."
            ::= { hiQAucUscFaultMgmt 41 }

hiQAucUscStbBackupFTPLinkUp NOTIFICATION-TYPE
            OBJECTS { rtpEvtSequenceNumberIndex,
                      rtpEvtCurrId,
                      rtpEvtSet,                    -- 182
                      rtpEvtNum,                    -- 42
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "Usage collection: Standby backup ftp link is
                         up."
            ::= { hiQAucUscFaultMgmt 42 }

hiQAucUscStbBackupFTPLinkDown NOTIFICATION-TYPE
            OBJECTS { rtpEvtSequenceNumberIndex,
                      rtpEvtCurrId,
                      rtpEvtSet,                    -- 182
                      rtpEvtNum,                    -- 43
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "Usage collection: Standby backup ftp link is
                         down."
            ::= { hiQAucUscFaultMgmt 43 }

-- *******************************
-- H323 Fault Management Traps
-- *******************************

hiQH323InitFailedTrap NOTIFICATION-TYPE
            OBJECTS { rtpEvtSequenceNumberIndex,
                      rtpEvtCurrId,
                      rtpEvtSet,                    -- 180
                      rtpEvtNum,                    -- 11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "H323 SM Initialization has failed."
            ::= { hiQH323FaultMgmt 11 }

hiQH323InitializedTrap NOTIFICATION-TYPE
            OBJECTS { rtpEvtSequenceNumberIndex,
                      rtpEvtCurrId,
                      rtpEvtSet,                    -- 180
                      rtpEvtNum,                    -- 12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "H323 SM Initialization has succeeded."
            ::= { hiQH323FaultMgmt 12 }

hiQH323ResourceFailedTrap NOTIFICATION-TYPE
            OBJECTS { rtpEvtSequenceNumberIndex,
                      rtpEvtCurrId,
                      rtpEvtSet,                    -- 180
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "H323 SM, static/dynamic resource allocation or
                         deallocation failed."
            ::= { hiQH323FaultMgmt 3 }

hiQH323TxCongestionStartTrap NOTIFICATION-TYPE
            OBJECTS { rtpEvtSequenceNumberIndex,
                      rtpEvtCurrId,
                      rtpEvtSet,                    -- 180
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "H323 SM has congestion started for the Tx queue. New
                         calls will be dropped."
            ::= { hiQH323FaultMgmt 4 }

hiQH323TxCongestionDropTrap NOTIFICATION-TYPE
            OBJECTS { rtpEvtSequenceNumberIndex,
                      rtpEvtCurrId,
                      rtpEvtSet,                    -- 180
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "H323 SM has congestion dropped for the Tx queue. Active
                         calls are dropping."
            ::= { hiQH323FaultMgmt 5 }

hiQH323TxCongestionStopTrap NOTIFICATION-TYPE
            OBJECTS { rtpEvtSequenceNumberIndex,
                      rtpEvtCurrId,
                      rtpEvtSet,                    -- 180
                      rtpEvtNum,                    -- 6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "H323 SM has congestion stopped for the Tx queue. All calls are accepted. 
                         This will clear any congestion trap for Tx queue."

            ::= { hiQH323FaultMgmt 6 }

-- *******************************
-- UCE Fault Management Traps
-- *******************************

hiQUceReadyTrap NOTIFICATION-TYPE
            OBJECTS { rtpEvtSequenceNumberIndex,
                      rtpEvtCurrId,
                      rtpEvtSet,                    -- 176
                      rtpEvtNum,                    -- 8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION ""
            ::= { hiQUceFaultMgmt 8 }

-- *******************************
-- Overload Fault Management Traps
-- *******************************
hiQOvlCongLevelToCL3Trap NOTIFICATION-TYPE
            OBJECTS { rtpEvtSequenceNumberIndex,
                      rtpEvtCurrId,
                      rtpEvtSet,                    -- 190
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "OVL: This Trap is sent to report various Over Load Manager
                         Major (Critical) Congestion Level conditions for several 
                         signaling managers including 'ISUP', 'OMAP', 'H323', 
                         'MGCP', and 'SIP+'. This informs that congestion level 
                         changed from CL* to CL3 for a certain SM. This will clear 
                         up previos CL2 level trap. CL3 means highest level of 
                         congestion and CL0 means no congestion."
            ::= { hiQOvlFaultMgmt 2 }

hiQOvlCongLevelToCL2Trap NOTIFICATION-TYPE
            OBJECTS { rtpEvtSequenceNumberIndex,
                      rtpEvtCurrId,
                      rtpEvtSet,                    -- 190
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "OVL: This Trap is sent to report various Over Load Manager 
                         Major (Critical) Congestion Level conditions for several 
                         signaling managers including 'ISUP', 'OMAP', 'H323',
                         'MGCP', and 'SIP+'. This informs that congestion level 
                         changed from CL* to CL2 for a certain SM. This will clear
                         previous CL1 or CL3 traps from which it changed from.  
                         CL3 means highest level of congestion and CL0 means no congestion."
            ::= { hiQOvlFaultMgmt 3 }

hiQOvlCongLevelToCL1Trap NOTIFICATION-TYPE
            OBJECTS { rtpEvtSequenceNumberIndex,
                      rtpEvtCurrId,
                      rtpEvtSet,                    -- 190
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION  "OVL: This Trap is sent to report various Over Load Manager
                         Major (Critical) Congestion Level conditions for several 
                         signaling managers including 'ISUP', 'OMAP', 'H323', 
                         'MGCP', and 'SIP+'. This informs that congestion level 
                         changed from CL* to CL1 for a certain SM. This will clear
                         previous CL2 traps from which it changed from.
                         CL3 means highest level of congestion and CL0 means no congestion."
            ::= { hiQOvlFaultMgmt 4 }

hiQOvlCongLevelToCL0Trap NOTIFICATION-TYPE
            OBJECTS { rtpEvtSequenceNumberIndex,
                      rtpEvtCurrId,
                      rtpEvtSet,                    -- 190
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "OVL: This Trap is sent to report to clear various
                         Over Load Manager Major (Critical) Congestion Level
                         conditions for several signaling managers including
                         'ISUP', 'OMAP', 'H323', 'MGCP', and 'SIP+'. This
                         informs that congestion level changed to 0 level
                         congestion. This will clear any previous CL* traps.
                         CL3 means highest level of congestion and CL0 means
                         no congestion."
            ::= { hiQOvlFaultMgmt 5 }

hiQOvlNewCallsExceedingTrap NOTIFICATION-TYPE
            OBJECTS { rtpEvtSequenceNumberIndex,
                      rtpEvtCurrId,
                      rtpEvtSet,                    -- 190
                      rtpEvtNum,                    -- 6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "OVL: New-call attempts exceeding limit of number
                         in time interval of millisecs."
            ::= { hiQOvlFaultMgmt 6 }

hiQOvlNewCallsBelowLimitTrap NOTIFICATION-TYPE
            OBJECTS { rtpEvtSequenceNumberIndex,
                      rtpEvtCurrId,
                      rtpEvtSet,                    -- 190
                      rtpEvtNum,                    -- 7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "OVL: New-call attempts below limit of number in
                         time interval of millisecs. This trap clears
                         New-call attempts exceeding limit trap."
            ::= { hiQOvlFaultMgmt 7 }

hiQOvlNewCallsBlockTrap NOTIFICATION-TYPE
            OBJECTS { rtpEvtSequenceNumberIndex,
                      rtpEvtCurrId,
                      rtpEvtSet,                    -- 190
                      rtpEvtNum,                    -- 8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "OVL: Call processing status set to block new calls for a SM."
            ::= { hiQOvlFaultMgmt 8 }

hiQOvlNewCallsAcceptTrap NOTIFICATION-TYPE
            OBJECTS { rtpEvtSequenceNumberIndex,
                      rtpEvtCurrId,
                      rtpEvtSet,                    -- 190
                      rtpEvtNum,                    -- 9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS obsolete
            DESCRIPTION "OVL: Call processing status set to accept new calls for a SM. 
                         This trap clears the set to block new calls trap."
            ::= { hiQOvlFaultMgmt 9 }

hiQOvlCongLevelChangeTrap NOTIFICATION-TYPE
            OBJECTS { rtpEvtSequenceNumberIndex,
                      rtpEvtCurrId,
                      rtpEvtSet,                    -- 190
                      rtpEvtNum,                    -- 10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,              
                      rtpEvtFilterLastTransId
            }
            STATUS current
            DESCRIPTION "OVL: This Trap is sent to clear various
                         Over Load Manager Major Congestion Level
                         conditions before reporting a new level."
            ::= { hiQOvlFaultMgmt 10 }


-- ******************************************
-- ISUP Fault Management Traps
-- ******************************************

hiQIsupRsetNotAvailable NOTIFICATION-TYPE
            OBJECTS { rtpEvtSequenceNumberIndex,
                      rtpEvtCurrId,
                      rtpEvtSet,                    -- 177
                      rtpEvtNum,                    -- 7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The RouteSet is not available. The faulty object will
                         contain the DPC for which the alarm is being generated."
            ::= { hiQIsupFaultMgmt 7 }

hiQIsupRsetAvailable NOTIFICATION-TYPE
            OBJECTS { rtpEvtSequenceNumberIndex,
                      rtpEvtCurrId,
                      rtpEvtSet,                    -- 177
                      rtpEvtNum,                    -- 8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The RouteSet is  available. The faulty object will contain
                         the DPC for which the alarm is being cleared."
            ::= { hiQIsupFaultMgmt 8 }

-- ******************************************
-- LNP Fault Management Traps
-- ******************************************
hiQLnpSuccessfulRegistrationTrap NOTIFICATION-TYPE
           OBJECTS { rtpEvtSequenceNumberIndex,
                     rtpEvtCurrId,
                     rtpEvtSet,                     -- 193
                     rtpEvtNum,                     -- 1
                     rtpEvtSeverity,
                     rtpEvtEventTime,
                     rtpEvtReportingObject,
                     rtpEvtFaultyObject,
                     rtpEvtEndkey,
                     rtpEvtFormatText,
                     rtpEvtParameters,
                     rtpEvtAlarmType,
                     rtpEvtShortText,
                     rtpEvtFilterLastTransId
           }
           STATUS current
           DESCRIPTION "LNP successfully registered for use within call
                        processing. It clears the failed registration trap."
           ::= { hiQLnpFaultMgmt 1 }

hiQLnpFailedRegistrationTrap NOTIFICATION-TYPE
           OBJECTS { rtpEvtSequenceNumberIndex,
                     rtpEvtCurrId,
                     rtpEvtSet,                    -- 193
                     rtpEvtNum,                    -- 2
                     rtpEvtSeverity,
                     rtpEvtEventTime,
                     rtpEvtReportingObject,
                     rtpEvtFaultyObject,
                     rtpEvtEndkey,
                     rtpEvtFormatText,
                     rtpEvtParameters,
                     rtpEvtAlarmType,
                     rtpEvtShortText,
                     rtpEvtFilterLastTransId
            }
            STATUS current
            DESCRIPTION "LNP registration failed for use within the call
                         processing."
            ::= { hiQLnpFaultMgmt 2 }

-- ******************************************
-- TCAP Fault Management Traps
-- ******************************************

hiQTcapInstanceReadyTrap NOTIFICATION-TYPE
            OBJECTS { rtpEvtSequenceNumberIndex,
                      rtpEvtCurrId,
                      rtpEvtSet,                    -- 192
                      rtpEvtNum,                    -- 8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "TCAP Instance is ready for Call Processing. It will
                         clear the TCAP Exited trap."
            ::= { hiQTcapFaultMgmt 8 }

        -- ******************************************
        -- CDM Fault Management Traps
        -- ******************************************
hiQCdmInitializedTrap NOTIFICATION-TYPE
            OBJECTS { rtpEvtSequenceNumberIndex,
                      rtpEvtCurrId,
                      rtpEvtSet,                    -- 188
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM is initialized and ready to process ISDN
                         configuration commands."
            ::= { hiQCdmFaultMgmt 1 }

hiQCdmNotInitializedTrap NOTIFICATION-TYPE
            OBJECTS { rtpEvtSequenceNumberIndex,
                      rtpEvtCurrId,
                      rtpEvtSet,                    -- 188
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM process did not start correctly and is unable to process ISDN
                         configuration commands."
            ::= { hiQCdmFaultMgmt 2 }

hiQCdmTerminatedTrap NOTIFICATION-TYPE
            OBJECTS { rtpEvtSequenceNumberIndex,
                      rtpEvtCurrId,
                      rtpEvtSet,                    -- 188
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM process is being shut down and will not process
                         further ISDN configuration commands."
            ::= { hiQCdmFaultMgmt 3 }

hiQCdmNotTerminatedTrap NOTIFICATION-TYPE
            OBJECTS { rtpEvtSequenceNumberIndex,
                      rtpEvtCurrId,
                      rtpEvtSet,                    -- 188
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM process is not properly shut down."
            ::= { hiQCdmFaultMgmt 4 }

hiQCdmSendToMgTrap NOTIFICATION-TYPE
            OBJECTS { rtpEvtSequenceNumberIndex,
                      rtpEvtCurrId,
                      rtpEvtSet,                    -- 188
                      rtpEvtNum,                    -- 19
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM can not send provisioning data to a Media Gateway
                         shelf."
            ::= { hiQCdmFaultMgmt 19 }

hiQCdmReceiveFromMgTrap NOTIFICATION-TYPE
            OBJECTS { rtpEvtSequenceNumberIndex,
                      rtpEvtCurrId,
                      rtpEvtSet,                    -- 188
                      rtpEvtNum,                    -- 20
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM failed to receive data from a Media Gateway shelf."
            ::= { hiQCdmFaultMgmt 20 }

hiQCdmMgShelfRebootedTrap NOTIFICATION-TYPE
            OBJECTS { rtpEvtSequenceNumberIndex,
                      rtpEvtCurrId,
                      rtpEvtSet,                    -- 188
                      rtpEvtNum,                    -- 23
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM, Media Gateway shelf has been rebooted
                         successfully."
            ::= { hiQCdmFaultMgmt 23 }

hiQCdmMgShelfNotRebootedTrap NOTIFICATION-TYPE
            OBJECTS { rtpEvtSequenceNumberIndex,
                      rtpEvtCurrId,
                      rtpEvtSet,                    -- 188
                      rtpEvtNum,                    -- 24
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM, Media Gateway shelf has not benn rebooted
                         successfully."
            ::= { hiQCdmFaultMgmt 24 }

hiQCdmMgProvisioningTimedOutTrap NOTIFICATION-TYPE
            OBJECTS { rtpEvtSequenceNumberIndex,
                      rtpEvtCurrId,
                      rtpEvtSet,                    -- 188
                      rtpEvtNum,                    -- 25
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM, Media Gateway shelf did not respond to
                         provisioning with an acknowledgement within certain
                         time."
            ::= { hiQCdmFaultMgmt 25 }

hiQCdmMgProvisioningFailedTrap NOTIFICATION-TYPE
            OBJECTS { rtpEvtSequenceNumberIndex,
                      rtpEvtCurrId,
                      rtpEvtSet,                    -- 188
                      rtpEvtNum,                    -- 26
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM, Media Gateway shelf did not respond to
                         provisioning with a failure acknowledgement."
            ::= { hiQCdmFaultMgmt 26 }

hiQCdmMgConnectionSuccessTrap NOTIFICATION-TYPE
            OBJECTS { rtpEvtSequenceNumberIndex,
                      rtpEvtCurrId,
                      rtpEvtSet,                    -- 188
                      rtpEvtNum,                    -- 27
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM, a connection was successfully established between
                          CDM and a Media Gateway shelf."
            ::= { hiQCdmFaultMgmt 27 }

hiQCdmMgConnectionFailTrap NOTIFICATION-TYPE
            OBJECTS { rtpEvtSequenceNumberIndex,
                      rtpEvtCurrId,
                      rtpEvtSet,                    -- 188
                      rtpEvtNum,                    -- 28
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "CDM,a connection was not successfully established
                         between CDM and a Media Gateway shelf."
            ::= { hiQCdmFaultMgmt 28 }

-- ******************************************
-- XDM Manager Fault Management Traps
-- ******************************************

hiQXdmInitializedTrap NOTIFICATION-TYPE
            OBJECTS { rtpEvtSequenceNumberIndex,
                      rtpEvtCurrId,
                      rtpEvtSet,                    -- 183
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "XDM process is initialized and ready to process
                         translation/routing commands."
            ::= { hiQXdmFaultMgmt 1 }

hiQXdmNotTerminatedTrap NOTIFICATION-TYPE
            OBJECTS { rtpEvtSequenceNumberIndex,
                      rtpEvtCurrId,
                      rtpEvtSet,                    -- 183
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "XDM process is not properly shutdown."
            ::= { hiQXdmFaultMgmt 4 }

hiQXdmXlaInitializedTrap NOTIFICATION-TYPE
            OBJECTS { rtpEvtSequenceNumberIndex,
                      rtpEvtCurrId,
                      rtpEvtSet,                    -- 183
                      rtpEvtNum,                    -- 14
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "XDM initialized the XLA shared memory from the
                         database."
            ::= { hiQXdmFaultMgmt 14 }

hiQXdmXlaNotInitializedTrap NOTIFICATION-TYPE
            OBJECTS { rtpEvtSequenceNumberIndex,
                      rtpEvtCurrId,
                      rtpEvtSet,                    -- 183
                      rtpEvtNum,                    -- 15
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "XDM failed to initialize the XLA shared memory from the
                         database."
            ::= { hiQXdmFaultMgmt 15 }

        -- ******************************************
        -- OMAP Signalling Manager Fault Management Traps
        -- ******************************************

hiQOmapInitFailureTrap NOTIFICATION-TYPE
            OBJECTS { rtpEvtSequenceNumberIndex,
                      rtpEvtCurrId,
                      rtpEvtSet,                    -- 187
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "OMAP initialization failure."
            ::= { hiQOmapFaultMgmt 1 }

hiQOmapMissingPriTrap NOTIFICATION-TYPE
            OBJECTS { rtpEvtSequenceNumberIndex,
                      rtpEvtCurrId,
                      rtpEvtSet,                    -- 187
                      rtpEvtNum,                    -- 20
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "OMAP:Call processing failed.  There is missing PRI info
                         in UCE setup message, aborting the call."
            ::= { hiQOmapFaultMgmt 20 }

hiQOmapBchBusyTrap NOTIFICATION-TYPE
            OBJECTS { rtpEvtSequenceNumberIndex,
                      rtpEvtCurrId,
                      rtpEvtSet,                    -- 187
                      rtpEvtNum,                    -- 21
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "OMAP:Call processing failed.  Setting B-ch busy failed."
            ::= { hiQOmapFaultMgmt 21 }

hiQOmapMissingChannelTrap NOTIFICATION-TYPE
            OBJECTS { rtpEvtSequenceNumberIndex,
                      rtpEvtCurrId,
                      rtpEvtSet,                    -- 187
                      rtpEvtNum,                    -- 26
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "OMAP:Call processing failed. Missing channel info in
                         OMAP setup, aborting the call."
            ::= { hiQOmapFaultMgmt 26 }

hiQOmapSaveCallTrap NOTIFICATION-TYPE 
            OBJECTS { rtpEvtSequenceNumberIndex,
                      rtpEvtCurrId,
                      rtpEvtSet,                    -- 187
                      rtpEvtNum,                    -- 27
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "OMAP:Call processing failed, unable to save call Id in
                         RTM."
            ::= { hiQOmapFaultMgmt 27 }

-- ******************************************
-- DB Manager Fault Management Traps
-- ******************************************

hiQDBInitCompleteTrap NOTIFICATION-TYPE
            OBJECTS { rtpEvtSequenceNumberIndex,
                      rtpEvtCurrId,
                      rtpEvtSet,                    -- 191
                      rtpEvtNum,                    -- 10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "Process DBManager has completed initialization."
            ::= { hiQDbFaultMgmt 10 }

hiQDBOperationalTrap NOTIFICATION-TYPE
            OBJECTS { rtpEvtSequenceNumberIndex,
                      rtpEvtCurrId,
                      rtpEvtSet,                    -- 191
                      rtpEvtNum,                    -- 33
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "Process DBManager operational error has occurred."
            ::= { hiQDbFaultMgmt 33 }

-- ******************************************
-- OMAP Dispatcher Fault Management Traps
-- ******************************************

hiQOmapDispInitFailedTrap NOTIFICATION-TYPE
            OBJECTS { rtpEvtSequenceNumberIndex,
                      rtpEvtCurrId,
                      rtpEvtSet,                    -- 194
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "OMAP Dispatcher initialization has failed. and probable cause
                        is RTP related functionality. This will abort the Dispatcher."
            ::= { hiQOmapDispFaultMgmt 5 }

hiQOmapDispConnToMgDownTrap NOTIFICATION-TYPE
            OBJECTS { rtpEvtSequenceNumberIndex,
                      rtpEvtCurrId,
                      rtpEvtSet,                    -- 194
                      rtpEvtNum,                    -- 6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "OMAP Dispatcher process failed to connect to Media Gateway."
            ::= { hiQOmapDispFaultMgmt 6 }

hiQOmapDispStartedTrap NOTIFICATION-TYPE
            OBJECTS { rtpEvtSequenceNumberIndex,
                      rtpEvtCurrId,
                      rtpEvtSet,                    -- 194
                      rtpEvtNum,                    -- 21
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "OMAP Dispatcher process started successfully."
            ::= { hiQOmapDispFaultMgmt 21 }

hiQOmapDispConnToMgUpTrap NOTIFICATION-TYPE
            OBJECTS { rtpEvtSequenceNumberIndex,
                      rtpEvtCurrId,
                      rtpEvtSet,                    -- 194
                      rtpEvtNum,                    -- 22
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "OMAP Dispatcher process succeeded to connect to Media Gateway."
            ::= { hiQOmapDispFaultMgmt 22 }

hiQOmapDispConnFailOverFailTrap NOTIFICATION-TYPE
            OBJECTS { rtpEvtSequenceNumberIndex,
                      rtpEvtCurrId,
                      rtpEvtSet,                    -- 194
                      rtpEvtNum,                    -- 23
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "OMAP Dispatcher process failed to connect to another dispatcher when
                        dispatcher connection to MG is down."
            ::= { hiQOmapDispFaultMgmt 23 }

hiQOmapDispConnFailOverSuccTrap NOTIFICATION-TYPE
            OBJECTS { rtpEvtSequenceNumberIndex,
                      rtpEvtCurrId,
                      rtpEvtSet,                    -- 194
                      rtpEvtNum,                    -- 24
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "OMAP Dispatcher process successfully connected to another dispatcher
                        when dispatcher connection to MG is down."
            ::= { hiQOmapDispFaultMgmt 24 }

-- ******************************************
-- RTM Fault Management Traps
-- ******************************************

hiQRtmStartedTrap NOTIFICATION-TYPE
            OBJECTS { rtpEvtSequenceNumberIndex,
                      rtpEvtCurrId,
                      rtpEvtSet,                    -- 199
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "RTM process started properly."
            ::= { hiQRtmFaultMgmt 1 }

hiQRtmInitFailedTrap NOTIFICATION-TYPE
            OBJECTS { rtpEvtSequenceNumberIndex,
                      rtpEvtCurrId,
                      rtpEvtSet,                    -- 199
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "RTM Initialization failed. A probable cause could be RTP related
                        resource."
            ::= { hiQRtmFaultMgmt 2 }


-- ******************************************
-- SIP Fault Management Traps
-- ******************************************

hiQSipStartUpTrap NOTIFICATION-TYPE
            OBJECTS { rtpEvtSequenceNumberIndex,
                      rtpEvtCurrId,
                      rtpEvtSet,                    -- 198
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "SIP SM process is up and running."
            ::= { hiQSipFaultMgmt 1 }


-- ******************************************
-- Subscriber Management (SOAP) Traps
-- ******************************************

hiQSubMgmtRemoveResourceError NOTIFICATION-TYPE
            OBJECTS { rtpEvtSequenceNumberIndex,
                      rtpEvtCurrId,
                      rtpEvtSet,                    -- 207
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
             }
             STATUS current
             DESCRIPTION "The job to remove subscriber management
                          resources failed."
             ::= { hiQSoapServerFaultMgmt 5 }

hiQSubMgmtRemoveResourceSuccess NOTIFICATION-TYPE
            OBJECTS { rtpEvtSequenceNumberIndex,
                      rtpEvtCurrId,
                      rtpEvtSet,                    -- 207
                      rtpEvtNum,                    -- 6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
             }
             STATUS current
             DESCRIPTION "The job to remove subscriber management
                          resources completed successfully."
             ::= { hiQSoapServerFaultMgmt 6 }


-- ******************************************
-- CSTA Fault Management Traps
-- ******************************************

hiQCstaStartedUp NOTIFICATION-TYPE
            OBJECTS { rtpEvtSequenceNumberIndex,
                      rtpEvtCurrId,
                      rtpEvtSet,                    -- 210
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The CSTA signaling manager process started properly."
            ::= { hiQCstaFaultMgmt 1 }

hiQCstaCAPLinkUp NOTIFICATION-TYPE
            OBJECTS { rtpEvtSequenceNumberIndex,
                      rtpEvtCurrId,
                      rtpEvtSet,                    -- 210
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The link to the CAP (Common Application Platform) is up."
            ::= { hiQCstaFaultMgmt 4 }

hiQCstaTTUDRegistrationFailure NOTIFICATION-TYPE
            OBJECTS { rtpEvtSequenceNumberIndex,
                      rtpEvtCurrId,
                      rtpEvtSet,                    -- 210
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The CSTA SM process was unable to register with the TTUD process."
            ::= { hiQCstaFaultMgmt 5 }

hiQCstaTTUDRegistrationSuccess NOTIFICATION-TYPE
            OBJECTS { rtpEvtSequenceNumberIndex,
                      rtpEvtCurrId,
                      rtpEvtSet,                    -- 210
                      rtpEvtNum,                    -- 6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The CSTA SM process registered successfully with the TTUD process."
            ::= { hiQCstaFaultMgmt 6 }

-- ******************************************
-- SMDI Fault Management Traps
-- ******************************************

hiQSmdiStartingUp NOTIFICATION-TYPE
            OBJECTS { rtpEvtSequenceNumberIndex,
                      rtpEvtCurrId,
                      rtpEvtSet,                    -- 208
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The SMDI process is being initialized."
            ::= { hiQSmdiFaultMgmt 1 }

hiQSmdiDbError NOTIFICATION-TYPE
            OBJECTS { rtpEvtSequenceNumberIndex,
                      rtpEvtCurrId,
                      rtpEvtSet,                    -- 208
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "SMDI process could not be initialized due to a database error."
            ::= { hiQSmdiFaultMgmt 3 }

hiQSmdiDbErrorCleared NOTIFICATION-TYPE
            OBJECTS { rtpEvtSequenceNumberIndex,
                      rtpEvtCurrId,
                      rtpEvtSet,                    -- 208
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The SMDI error caused by database initialization was resolved by
                        manual intervention."
            ::= { hiQSmdiFaultMgmt 4 }

hiQSmdiLinkError NOTIFICATION-TYPE
            OBJECTS { rtpEvtSequenceNumberIndex,
                      rtpEvtCurrId,
                      rtpEvtSet,                    -- 208
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "SMDI process could not establish a link within the provisioned amount
                        of time and tries. Manual intervention is required for immediate
                        reconnection."
            ::= { hiQSmdiFaultMgmt 5 }

hiQSmdiLinkUp NOTIFICATION-TYPE
            OBJECTS { rtpEvtSequenceNumberIndex,
                      rtpEvtCurrId,
                      rtpEvtSet,                    -- 208
                      rtpEvtNum,                    -- 6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "SMDI process has resolved the previously reported link error."
            ::= { hiQSmdiFaultMgmt 6 }

hiQSmdiREcvIPAddrPortError NOTIFICATION-TYPE
            OBJECTS { rtpEvtSequenceNumberIndex,
                      rtpEvtCurrId,
                      rtpEvtSet,                    -- 208
                      rtpEvtNum,                    -- 7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "An error occurred during initialization of the SMDI receive IP
                        address and port."
            ::= { hiQSmdiFaultMgmt 7 }

hiQSmdiRecvIPAddrPortOk NOTIFICATION-TYPE
            OBJECTS { rtpEvtSequenceNumberIndex,
                      rtpEvtCurrId,
                      rtpEvtSet,                    -- 208
                      rtpEvtNum,                    -- 8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "Trap indicates that SMDI (Simplified Message
                         Desk Interface) can listen on the IP address
                         and port."
            ::= { hiQSmdiFaultMgmt 8 }


--
-- HardwareTraps
--

hiQVerySevereHardwareFailureTrap NOTIFICATION-TYPE
            OBJECTS { rtpEvtSequenceNumberIndex,
                      rtpEvtCurrId,
                      rtpEvtSet,                    -- 219
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "A very severe HW failure has been detected."
            ::= { hiQHardwareFaultMgt 1 }

hiQSevereHardwareTrap NOTIFICATION-TYPE
            OBJECTS { rtpEvtSequenceNumberIndex,
                      rtpEvtCurrId,
                      rtpEvtSet,                    -- 219
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "A severe HW failure has been detected."
            ::= { hiQHardwareFaultMgt 2 }

hiQHardwareFailureTrap NOTIFICATION-TYPE
            OBJECTS { rtpEvtSequenceNumberIndex,
                      rtpEvtCurrId,
                      rtpEvtSet,                    -- 219
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "A HW failure has been detected."
            ::= { hiQHardwareFaultMgt 3 }

hiQHardwareInServiceTrap NOTIFICATION-TYPE
            OBJECTS { rtpEvtSequenceNumberIndex,
                      rtpEvtCurrId,
                      rtpEvtSet,                    -- 219
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This event is used to clear a hardware-related alarm."
            ::= { hiQHardwareFaultMgt 4 }

hiQSystemSurvivalModeTrap NOTIFICATION-TYPE
            OBJECTS { rtpEvtSequenceNumberIndex,
                      rtpEvtCurrId,
                      rtpEvtSet,                    -- 219
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The system is operating in survival mode."
            ::= { hiQHardwareFaultMgt 5 }

--
-- Security Traps
--
hiQSecurityFirewallTrigTrap NOTIFICATION-TYPE
            OBJECTS { rtpEvtSequenceNumberIndex,
                      rtpEvtCurrId,
                      rtpEvtSet,                    -- 218
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The firewall has started to discard IP packets. The number of
                        IP packets/second/user from at least a single user has exceeded
                        the configured threshold."
            ::= { hiQSecurityFaultMgt 1 }

hiQSecurityFirewallTrigClearTrap NOTIFICATION-TYPE
            OBJECTS { rtpEvtSequenceNumberIndex,
                      rtpEvtCurrId,
                      rtpEvtSet,                    -- 218
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The condition causing the triggering of the firewall has been
                        cleared. No more IP packets are being  discarded."
            ::= { hiQSecurityFaultMgt 2 }

--
-- Licensing Traps
--
hiQLicensesExceededTrap NOTIFICATION-TYPE
            OBJECTS { rtpEvtSequenceNumberIndex,
                      rtpEvtCurrId,
                      rtpEvtSet,                    -- 220
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of assigned licenses has exceeded the number of activated licenses
                         for the type identified by faultyObject."
            ::= { hiQLicensingFaultMgt 1 }

hiQLicenseCountOkTrap NOTIFICATION-TYPE
            OBJECTS { rtpEvtSequenceNumberIndex,
                      rtpEvtCurrId,
                      rtpEvtSet,                    -- 220
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of assigned licenses is now within the limit allowed by the
                         number of licenses activated for the type identified by faultyObject."
            ::= { hiQLicensingFaultMgt 2 }

hiQLicenseCountMismatchTrap NOTIFICATION-TYPE
            OBJECTS { rtpEvtSequenceNumberIndex,
                      rtpEvtCurrId,
                      rtpEvtSet,                    -- 220
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The license count is different between the two nodes of the hiQ cluster
                         for the type identified by faultyObject."
            ::= { hiQLicensingFaultMgt 3 }

hiQLicenseCountSyncTrap NOTIFICATION-TYPE
            OBJECTS { rtpEvtSequenceNumberIndex,
                      rtpEvtCurrId,
                      rtpEvtSet,                    -- 220
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The license count is now the same between the two nodes of the hiQ cluster
                         for the type identified by faultyObject."
            ::= { hiQLicensingFaultMgt 4 }

hiQLicenseSessionsTrap NOTIFICATION-TYPE
            OBJECTS { rtpEvtSequenceNumberIndex,
                      rtpEvtCurrId,
                      rtpEvtSet,                    -- 220
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of license sessions exceeds the warning threshold
                         for the type identified by faultyObject."
            ::= { hiQLicensingFaultMgt 5 }

hiQLicenseSessionCountOkTrap NOTIFICATION-TYPE
            OBJECTS { rtpEvtSequenceNumberIndex,
                      rtpEvtCurrId,
                      rtpEvtSet,                    -- 220
                      rtpEvtNum,                    -- 6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of license sessions is now below the warning threshold
                         for the type identified by faultyObject."
            ::= { hiQLicensingFaultMgt 6 }
	    
hiQLicenseRestoreTrap NOTIFICATION-TYPE
            OBJECTS { rtpEvtSequenceNumberIndex,
                      rtpEvtCurrId,
                      rtpEvtSet,                    -- 220
                      rtpEvtNum,                    -- 7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Restoring the system to a release older from the last more than or equal
	    to 72 hours causes licensing enforcement resulting in licensing violations."
            ::= { hiQLicensingFaultMgt 7 }

hiQLicenseRestoreOkTrap NOTIFICATION-TYPE
            OBJECTS { rtpEvtSequenceNumberIndex,
                      rtpEvtCurrId,
                      rtpEvtSet,                    -- 220
                      rtpEvtNum,                    -- 8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Licensing in now properly working in the system, after it has been restored."
            ::= { hiQLicensingFaultMgt 8 }

--
-- Global traps
--
hiQGlobalCriticalLossOfCommsTrap NOTIFICATION-TYPE
            OBJECTS { rtpEvtSequenceNumberIndex,
                      rtpEvtCurrId,
                      rtpEvtSet,                    -- 217
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This event is used to report a critical loss of communication."
            ::= { hiQGlobalFaultMgt 1 }

hiQGlobalMajorLossOfCommsTrap NOTIFICATION-TYPE
            OBJECTS { rtpEvtSequenceNumberIndex,
                      rtpEvtCurrId,
                      rtpEvtSet,                    -- 217
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This event is used to report a major loss of communication."
            ::= { hiQGlobalFaultMgt 2 }

hiQGlobalMinorLossOfCommsTrap NOTIFICATION-TYPE
            OBJECTS { rtpEvtSequenceNumberIndex,
                      rtpEvtCurrId,
                      rtpEvtSet,                    -- 217
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This event is used to report a minor loss of communication."
            ::= { hiQGlobalFaultMgt 3 }

hiQGlobalCommsEstablishedTrap NOTIFICATION-TYPE
            OBJECTS { rtpEvtSequenceNumberIndex,
                      rtpEvtCurrId,
                      rtpEvtSet,                    -- 217
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This event is used to report that communication has been (re-)e
                        established."
            ::= { hiQGlobalFaultMgt 4 }

hiQGlobalProcessInitActiveTrap NOTIFICATION-TYPE
            OBJECTS { rtpEvtSequenceNumberIndex,
                      rtpEvtCurrId,
                      rtpEvtSet,                    -- 217
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The process has started successfully."
            ::= { hiQGlobalFaultMgt 5 }

hiQGlobalProcSevereInitFailTrap NOTIFICATION-TYPE
            OBJECTS { rtpEvtSequenceNumberIndex,
                      rtpEvtCurrId,
                      rtpEvtSet,                    -- 217
                      rtpEvtNum,                    -- 6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The process encountered an error during initialization and
                        cannot continue."
            ::= { hiQGlobalFaultMgt 6 }

hiQGlobalProcPartialInitFailTrap NOTIFICATION-TYPE
            OBJECTS { rtpEvtSequenceNumberIndex,
                      rtpEvtCurrId,
                      rtpEvtSet,                    -- 217
                      rtpEvtNum,                    -- 7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This trap is used to report that the specified process
                        encountered a partial initialization failure." 
            ::= { hiQGlobalFaultMgt 7 }

hiQGlobalProcAbnormalTermTrap NOTIFICATION-TYPE
            OBJECTS { rtpEvtSequenceNumberIndex,
                      rtpEvtCurrId,
                      rtpEvtSet,                    -- 217
                      rtpEvtNum,                    -- 8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This trap is used to report that the specified process
                         terminated abnormally." 
            ::= { hiQGlobalFaultMgt 8 }

hiQGlobalProcessAliasGrpAvail NOTIFICATION-TYPE
            OBJECTS { rtpEvtSequenceNumberIndex,
                      rtpEvtCurrId,
                      rtpEvtSet,                    -- 217
                      rtpEvtNum,                    -- 9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The process Alias group, which is a collection of redundant processes,
                        is available."
            ::= { hiQGlobalFaultMgt 9 }

hiQGlobalProcessAliasGrpUnavail NOTIFICATION-TYPE
            OBJECTS { rtpEvtSequenceNumberIndex,
                      rtpEvtCurrId,
                      rtpEvtSet,                    -- 217
                      rtpEvtNum,                    -- 10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The process Alias group, which is a collection of redundant processes,
                        is not available. This means that none of the functions provided
                        by these processes is available."
            ::= { hiQGlobalFaultMgt 10 }

hiQGlobalResourceExceedLimitTrap NOTIFICATION-TYPE
            OBJECTS { rtpEvtSequenceNumberIndex,
                      rtpEvtCurrId,
                      rtpEvtSet,                    -- 217
                      rtpEvtNum,                    -- 11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The specified resource has exceeded a defined limit."
            ::= { hiQGlobalFaultMgt 11 }

hiQGlobalResourceWithinLimitTrap NOTIFICATION-TYPE
            OBJECTS { rtpEvtSequenceNumberIndex,
                      rtpEvtCurrId,
                      rtpEvtSet,                    -- 217
                      rtpEvtNum,                    -- 12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The specified resource is within the defined limit."
            ::= { hiQGlobalFaultMgt 12 }


hiQVeryImportantFuncUnavailTrap NOTIFICATION-TYPE
            OBJECTS { rtpEvtSequenceNumberIndex,
                      rtpEvtCurrId,
                      rtpEvtSet,                    -- 217
                      rtpEvtNum,                    -- 13
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This trap is used to report that the specified function
                         is unavailable." 
            ::= { hiQGlobalFaultMgt 13 }

hiQImportantFuncUnavailTrap NOTIFICATION-TYPE
            OBJECTS { rtpEvtSequenceNumberIndex,
                      rtpEvtCurrId,
                      rtpEvtSet,                    -- 217
                      rtpEvtNum,                    -- 14
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This trap is used to report that the specified function
                         is unavailable." 
            ::= { hiQGlobalFaultMgt 14 }

hiQGlobalFuncUnavailTrap NOTIFICATION-TYPE
            OBJECTS { rtpEvtSequenceNumberIndex,
                      rtpEvtCurrId,
                      rtpEvtSet,                    -- 217
                      rtpEvtNum,                    -- 15
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This trap is used to report that the specified function
                         is unavailable." 
            ::= { hiQGlobalFaultMgt 15 }

hiQGlobalFuncAvailTrap NOTIFICATION-TYPE
            OBJECTS { rtpEvtSequenceNumberIndex,
                      rtpEvtCurrId,
                      rtpEvtSet,                    -- 217
                      rtpEvtNum,                    -- 16
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This trap is used to report that the specified function
                         is available." 
            ::= { hiQGlobalFaultMgt 16 }

hiQGlobalMsgQueueAboveHighThld NOTIFICATION-TYPE
            OBJECTS { rtpEvtSequenceNumberIndex,
                      rtpEvtCurrId,
                      rtpEvtSet,                    -- 217
                      rtpEvtNum,                    -- 17
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This trap is used to report that the number of
                         elements in the specified queue has exceeded a
                         defined threshold limit." 
            ::= { hiQGlobalFaultMgt 17 }

hiQGlobalMsgQueueAboveMedThld NOTIFICATION-TYPE
            OBJECTS { rtpEvtSequenceNumberIndex,
                      rtpEvtCurrId,
                      rtpEvtSet,                    -- 217
                      rtpEvtNum,                    -- 18
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This trap is used to report that the number of
                         elements in the specified queue has exceeded a
                         defined threshold limit." 
            ::= { hiQGlobalFaultMgt 18 }

hiQGlobalMsgQueueAboveLowThld NOTIFICATION-TYPE
            OBJECTS { rtpEvtSequenceNumberIndex,
                      rtpEvtCurrId,
                      rtpEvtSet,                    -- 217
                      rtpEvtNum,                    -- 19
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This trap is used to report that the number of
                         elements in the specified queue has exceeded a
                         defined threshold limit." 
            ::= { hiQGlobalFaultMgt 19 }

hiQGlobalMsgQueueBelowThld NOTIFICATION-TYPE
            OBJECTS { rtpEvtSequenceNumberIndex,
                      rtpEvtCurrId,
                      rtpEvtSet,                    -- 217
                      rtpEvtNum,                    -- 20
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This trap is used to report that the number of
                         elements in the specified queue is below the
                         defined threshold limit." 
            ::= { hiQGlobalFaultMgt 20 }

hiQGlobalVerySevereDegradedCommsTrap NOTIFICATION-TYPE
            OBJECTS { rtpEvtSequenceNumberIndex,
                      rtpEvtCurrId,
                      rtpEvtSet,                    -- 217
                      rtpEvtNum,                    -- 21
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This event is used to report that the specified communication link
                         is either congested or operating in a degraded state."
            ::= { hiQGlobalFaultMgt 21 }

hiQGlobalSevereDegradedCommsTrap NOTIFICATION-TYPE
            OBJECTS { rtpEvtSequenceNumberIndex,
                      rtpEvtCurrId,
                      rtpEvtSet,                    -- 217
                      rtpEvtNum,                    -- 22
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This event is used to report that the specified communication link
                         is either congested or operating in a degraded state."
            ::= { hiQGlobalFaultMgt 22 }

hiQGlobalDegradedCommsTrap NOTIFICATION-TYPE
            OBJECTS { rtpEvtSequenceNumberIndex,
                      rtpEvtCurrId,
                      rtpEvtSet,                    -- 217
                      rtpEvtNum,                    -- 23
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This event is used to report that the specified communication link
                         is either congested or operating in a degraded state."
            ::= { hiQGlobalFaultMgt 23 }

hiQGlobalCommsOperationalTrap NOTIFICATION-TYPE
            OBJECTS { rtpEvtSequenceNumberIndex,
                      rtpEvtCurrId,
                      rtpEvtSet,                    -- 217
                      rtpEvtNum,                    -- 24
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "This event is used to report that the specified
                         communication link is operational."
            ::= { hiQGlobalFaultMgt 24 }

--
-- Account Management Traps
--
hiQAccountInactiveTrap NOTIFICATION-TYPE
            OBJECTS { rtpEvtSequenceNumberIndex,
                      rtpEvtCurrId,
                      rtpEvtSet,                    -- 221
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The specified login account has not been used recently and may be disabled in the
                         future."
            ::= { hiQAccountMgmtFaultMgt 1 }

hiQAccountDisabledTrap NOTIFICATION-TYPE
            OBJECTS { rtpEvtSequenceNumberIndex,
                      rtpEvtCurrId,
                      rtpEvtSet,                    -- 221
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The specified login account has not been used recently and may be deleted in the
                         future."
            ::= { hiQAccountMgmtFaultMgt 2 }

hiQAccountDeletedTrap NOTIFICATION-TYPE
            OBJECTS { rtpEvtSequenceNumberIndex,
                      rtpEvtCurrId,
                      rtpEvtSet,                    -- 221
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "Alarms were previously reported, indicating that the specified
                         account has been inactive and subsequently disabled. The account
                         was still not used and has now been deleted."
            ::= { hiQAccountMgmtFaultMgt 3 }

--
-- OMM Traps
--
hiQOmmBGCFCounterAboveHighThld NOTIFICATION-TYPE
            OBJECTS { rtpEvtSequenceNumberIndex,
                      rtpEvtCurrId,
                      rtpEvtSet,                    -- 230
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The event count has exceeded the alarm threshold
                         for the type identified by faultyObject."
            ::= { hiQOmmMgmtFaultMgt 1 }

hiQOmmBGCFCounterAboveLowThld NOTIFICATION-TYPE
            OBJECTS { rtpEvtSequenceNumberIndex,
                      rtpEvtCurrId,
                      rtpEvtSet,                    -- 230
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The event count has exceeded the alarm threshold
                         for the type identified by faultyObject."
            ::= { hiQOmmMgmtFaultMgt 2 }

hiQOmmBGCFCounterBelowThld NOTIFICATION-TYPE
            OBJECTS { rtpEvtSequenceNumberIndex,
                      rtpEvtCurrId,
                      rtpEvtSet,                    -- 230
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The event count is below the threshold allowed for 
                         the type identified by faultyObject."
            ::= { hiQOmmMgmtFaultMgt 3 }

--
-- Clear All TCA Alarms
--
hiQTcaClearedTrap NOTIFICATION-TYPE
            OBJECTS { rtpEvtSequenceNumberIndex,
                      rtpEvtCurrId,
                      rtpEvtSet,                    -- 216
                      rtpEvtNum,                    -- 100
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of logged entries for the specified log category has
                        not crossed the threshold that caused a previous alarm for
                        a certain period of time."
            ::= { hiQTcaFaultMgt 100 }

--
-- TCA Traps for Communication
--
hiQTcaL3CommunicationTrap NOTIFICATION-TYPE
            OBJECTS { rtpEvtSequenceNumberIndex,
                      rtpEvtCurrId,
                      rtpEvtSet,                    -- 216
                      rtpEvtNum,                    -- 1
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the highest level L3
                        threshold of logs per time interval. The alarm can be cleared manually
                        or, it will clear automatically after the configured time
                        interval."
            ::= { hiQTcaFaultMgt 1 }

hiQTcaL2CommunicationTrap NOTIFICATION-TYPE
            OBJECTS { rtpEvtSequenceNumberIndex,
                      rtpEvtCurrId,
                      rtpEvtSet,                    -- 216
                      rtpEvtNum,                    -- 2
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the medium level L2
                        threshold of logs per time interval. The alarm can be cleared manually
                        or, it will clear automatically after the configured time
                        interval."
            ::= { hiQTcaFaultMgt 2 }

hiQTcaL1CommunicationTrap NOTIFICATION-TYPE
            OBJECTS { rtpEvtSequenceNumberIndex,
                      rtpEvtCurrId,
                      rtpEvtSet,                    -- 216
                      rtpEvtNum,                    -- 3
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the lowest level L1
                        threshold of logs per time interval. The alarm can be cleared manually
                        or, it will clear automatically after the configured time
                        interval."
            ::= { hiQTcaFaultMgt 3 }

--
-- TCA Traps for Service
--
hiQTcaL3ServiceTrap NOTIFICATION-TYPE
            OBJECTS { rtpEvtSequenceNumberIndex,
                      rtpEvtCurrId,
                      rtpEvtSet,                    -- 216
                      rtpEvtNum,                    -- 4
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the highest level L3
                        threshold of logs per time interval. The alarm can be cleared manually
                        or, it will clear automatically after the configured time
                        interval."
            ::= { hiQTcaFaultMgt 4 }

hiQTcaL2ServiceTrap NOTIFICATION-TYPE
            OBJECTS { rtpEvtSequenceNumberIndex,
                      rtpEvtCurrId,
                      rtpEvtSet,                    -- 216
                      rtpEvtNum,                    -- 5
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the medium level L2
                        threshold of logs per time interval. The alarm can be cleared manually
                        or, it will clear automatically after the configured time
                        interval."
            ::= { hiQTcaFaultMgt 5 }

hiQTcaL1ServiceTrap NOTIFICATION-TYPE
            OBJECTS { rtpEvtSequenceNumberIndex,
                      rtpEvtCurrId,
                      rtpEvtSet,                    -- 216
                      rtpEvtNum,                    -- 6
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the lowest level L1
                        threshold of logs per time interval. The alarm can be cleared manually
                        or, it will clear automatically after the configured time
                        interval."
            ::= { hiQTcaFaultMgt 6 }

--
-- TCA Traps for Processing
--
hiQTcaL3ProcessingTrap NOTIFICATION-TYPE
            OBJECTS { rtpEvtSequenceNumberIndex,
                      rtpEvtCurrId,
                      rtpEvtSet,                    -- 216
                      rtpEvtNum,                    -- 7
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the highest level L3
                        threshold of logs per time interval. The alarm can be cleared manually
                        or, it will clear automatically after the configured time
                        interval."
            ::= { hiQTcaFaultMgt 7 }

hiQTcaL2ProcessingTrap NOTIFICATION-TYPE
            OBJECTS { rtpEvtSequenceNumberIndex,
                      rtpEvtCurrId,
                      rtpEvtSet,                    -- 216
                      rtpEvtNum,                    -- 8
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the medium level L2
                        threshold of logs per time interval. The alarm can be cleared manually
                        or, it will clear automatically after the configured time
                        interval."
            ::= { hiQTcaFaultMgt 8 }

hiQTcaL1ProcessingTrap NOTIFICATION-TYPE
            OBJECTS { rtpEvtSequenceNumberIndex,
                      rtpEvtCurrId,
                      rtpEvtSet,                    -- 216
                      rtpEvtNum,                    -- 9
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the lowest level L1
                        threshold of logs per time interval. The alarm can be cleared manually
                        or, it will clear automatically after the configured time
                        interval."
            ::= { hiQTcaFaultMgt 9 }

--
-- TCA Traps for Equipment
--
hiQTcaL3EquipmentTrap NOTIFICATION-TYPE
            OBJECTS { rtpEvtSequenceNumberIndex,
                      rtpEvtCurrId,
                      rtpEvtSet,                    -- 216
                      rtpEvtNum,                    -- 10
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the highest level L3
                        threshold of logs per time interval. The alarm can be cleared manually
                        or, it will clear automatically after the configured time
                        interval."
            ::= { hiQTcaFaultMgt 10 }

hiQTcaL2EquipmentTrap NOTIFICATION-TYPE
            OBJECTS { rtpEvtSequenceNumberIndex,
                      rtpEvtCurrId,
                      rtpEvtSet,                    -- 216
                      rtpEvtNum,                    -- 11
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the medium level L2
                        threshold of logs per time interval. The alarm can be cleared manually
                        or, it will clear automatically after the configured time
                        interval."
            ::= { hiQTcaFaultMgt 11 }

hiQTcaL1EquipmentTrap NOTIFICATION-TYPE
            OBJECTS { rtpEvtSequenceNumberIndex,
                      rtpEvtCurrId,
                      rtpEvtSet,                    -- 216
                      rtpEvtNum,                    -- 12
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the lowest level L1
                        threshold of logs per time interval. The alarm can be cleared manually
                        or, it will clear automatically after the configured time
                        interval."
            ::= { hiQTcaFaultMgt 12 }

--
-- TCA Traps for Environment
--
hiQTcaL3EnvironmentTrap NOTIFICATION-TYPE
            OBJECTS { rtpEvtSequenceNumberIndex,
                      rtpEvtCurrId,
                      rtpEvtSet,                    -- 216
                      rtpEvtNum,                    -- 13
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the highest level L3
                        threshold of logs per time interval. The alarm can be cleared manually
                        or, it will clear automatically after the configured time
                        interval."
            ::= { hiQTcaFaultMgt 13 }

hiQTcaL2EnvironmentTrap NOTIFICATION-TYPE
            OBJECTS { rtpEvtSequenceNumberIndex,
                      rtpEvtCurrId,
                      rtpEvtSet,                    -- 216
                      rtpEvtNum,                    -- 14
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the medium level L2
                        threshold of logs per time interval. The alarm can be cleared manually
                        or, it will clear automatically after the configured time
                        interval."
            ::= { hiQTcaFaultMgt 14 }

hiQTcaL1EnvironmentTrap NOTIFICATION-TYPE
            OBJECTS { rtpEvtSequenceNumberIndex,
                      rtpEvtCurrId,
                      rtpEvtSet,                    -- 216
                      rtpEvtNum,                    -- 15
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the lowest level L1
                        threshold of logs per time interval. The alarm can be cleared manually
                        or, it will clear automatically after the configured time
                        interval."
            ::= { hiQTcaFaultMgt 15 }

--
-- TCA Traps for Database
--
hiQTcaL3DatabaseTrap NOTIFICATION-TYPE
            OBJECTS { rtpEvtSequenceNumberIndex,
                      rtpEvtCurrId,
                      rtpEvtSet,                    -- 216
                      rtpEvtNum,                    -- 16
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the highest level L3
                        threshold of logs per time interval. The alarm can be cleared manually
                        or, it will clear automatically after the configured time
                        interval."
            ::= { hiQTcaFaultMgt 16 }

hiQTcaL2DatabaseTrap NOTIFICATION-TYPE
            OBJECTS { rtpEvtSequenceNumberIndex,
                      rtpEvtCurrId,
                      rtpEvtSet,                    -- 216
                      rtpEvtNum,                    -- 17
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the medium level L2
                        threshold of logs per time interval. The alarm can be cleared manually
                        or, it will clear automatically after the configured time
                        interval."
            ::= { hiQTcaFaultMgt 17 }

hiQTcaL1DatabaseTrap NOTIFICATION-TYPE
            OBJECTS { rtpEvtSequenceNumberIndex,
                      rtpEvtCurrId,
                      rtpEvtSet,                    -- 216
                      rtpEvtNum,                    -- 18
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the lowest level L1
                        threshold of logs per time interval. The alarm can be cleared manually
                        or, it will clear automatically after the configured time
                        interval."
            ::= { hiQTcaFaultMgt 18 }

--
-- TCA Traps for Mib
--
hiQTcaL3MibTrap NOTIFICATION-TYPE
            OBJECTS { rtpEvtSequenceNumberIndex,
                      rtpEvtCurrId,
                      rtpEvtSet,                    -- 216
                      rtpEvtNum,                    -- 19
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the highest level L3
                        threshold of logs per time interval. The alarm can be cleared manually
                        or, it will clear automatically after the configured time
                        interval."
            ::= { hiQTcaFaultMgt 19 }

hiQTcaL2MibTrap NOTIFICATION-TYPE
            OBJECTS { rtpEvtSequenceNumberIndex,
                      rtpEvtCurrId,
                      rtpEvtSet,                    -- 216
                      rtpEvtNum,                    -- 20
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the medium level L2
                        threshold of logs per time interval. The alarm can be cleared manually
                        or, it will clear automatically after the configured time
                        interval."
            ::= { hiQTcaFaultMgt 20 }

hiQTcaL1MibTrap NOTIFICATION-TYPE
            OBJECTS { rtpEvtSequenceNumberIndex,
                      rtpEvtCurrId,
                      rtpEvtSet,                    -- 216
                      rtpEvtNum,                    -- 21
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the lowest level L1
                        threshold of logs per time interval. The alarm can be cleared manually
                        or, it will clear automatically after the configured time
                        interval."
            ::= { hiQTcaFaultMgt 21 }

--
-- TCA Traps for Security
--
hiQTcaL3SecurityTrap NOTIFICATION-TYPE
            OBJECTS { rtpEvtSequenceNumberIndex,
                      rtpEvtCurrId,
                      rtpEvtSet,                    -- 216
                      rtpEvtNum,                    -- 25
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the highest level L3
                        threshold of logs per time interval. The alarm can be cleared manually
                        or, it will clear automatically after the configured time
                        interval."
            ::= { hiQTcaFaultMgt 25 }

hiQTcaL2SecurityTrap NOTIFICATION-TYPE
            OBJECTS { rtpEvtSequenceNumberIndex,
                      rtpEvtCurrId,
                      rtpEvtSet,                    -- 216
                      rtpEvtNum,                    -- 26
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the medium level L2
                        threshold of logs per time interval. The alarm can be cleared manually
                        or, it will clear automatically after the configured time
                        interval."
            ::= { hiQTcaFaultMgt 26 }

hiQTcaL1SecurityTrap NOTIFICATION-TYPE
            OBJECTS { rtpEvtSequenceNumberIndex,
                      rtpEvtCurrId,
                      rtpEvtSet,                    -- 216
                      rtpEvtNum,                    -- 27
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the lowest level L1
                        threshold of logs per time interval. The alarm can be cleared manually
                        or, it will clear automatically after the configured time
                        interval."
            ::= { hiQTcaFaultMgt 27 }

--
-- TCA Traps for SS7
--
hiQTcaL3SS7Trap NOTIFICATION-TYPE
            OBJECTS { rtpEvtSequenceNumberIndex,
                      rtpEvtCurrId,
                      rtpEvtSet,                    -- 216
                      rtpEvtNum,                    -- 28
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The number of log requests for the specified log category in
                        the last sampling interval has crossed the highest level L3
                        threshold of logs per time interval. The alarm can be cleared manually
                        or, it will clear automatically after the configured time
                        interval."
            ::= { hiQTcaFaultMgt 28 }

hiQTcaL2SS7Trap NOTIFICATION-TYPE
            OBJECTS { rtpEvtSequenceNumberIndex,
                      rtpEvtCurrId,
                      rtpEvtSet,                    -- 216
                      rtpEvtNum,                    -- 29
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The number of log requests for the specified log category in
                        the last sampling interval has crossed the medium level L2
                        threshold of logs per time interval. The alarm can be cleared manually
                        or, it will clear automatically after the configured time
                        interval."
            ::= { hiQTcaFaultMgt 29 }

hiQTcaL1SS7Trap NOTIFICATION-TYPE
            OBJECTS { rtpEvtSequenceNumberIndex,
                      rtpEvtCurrId,
                      rtpEvtSet,                    -- 216
                      rtpEvtNum,                    -- 30
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS obsolete
            DESCRIPTION "The number of log requests for the specified log category in
                        the last sampling interval has crossed the lowest level L1
                        threshold of logs per time interval. The alarm can be cleared manually
                        or, it will clear automatically after the configured time
                        interval."
            ::= { hiQTcaFaultMgt 30 }

--
-- TCA Traps for Indication
--
hiQTcaL3IndicationTrap NOTIFICATION-TYPE
            OBJECTS { rtpEvtSequenceNumberIndex,
                      rtpEvtCurrId,
                      rtpEvtSet,                    -- 216
                      rtpEvtNum,                    -- 31
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the highest level L3
                        threshold of logs per time interval. The alarm can be cleared manually
                        or, it will clear automatically after the configured time
                        interval."
            ::= { hiQTcaFaultMgt 31 }

hiQTcaL2IndicationTrap NOTIFICATION-TYPE
            OBJECTS { rtpEvtSequenceNumberIndex,
                      rtpEvtCurrId,
                      rtpEvtSet,                    -- 216
                      rtpEvtNum,                    -- 32
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the medium level L2
                        threshold of logs per time interval. The alarm can be cleared manually
                        or, it will clear automatically after the configured time
                        interval."
            ::= { hiQTcaFaultMgt 32 }

hiQTcaL1IndicationTrap NOTIFICATION-TYPE
            OBJECTS { rtpEvtSequenceNumberIndex,
                      rtpEvtCurrId,
                      rtpEvtSet,                    -- 216
                      rtpEvtNum,                    -- 33
                      rtpEvtSeverity,
                      rtpEvtEventTime,
                      rtpEvtReportingObject,
                      rtpEvtFaultyObject,
                      rtpEvtEndkey,
                      rtpEvtFormatText,
                      rtpEvtParameters,
                      rtpEvtAlarmType,
                      rtpEvtShortText,
                      rtpEvtFilterLastTransId
            }
            STATUS current
            DESCRIPTION "The number of log requests for the specified log category in
                        the last sampling interval has crossed the lowest level L1
                        threshold of logs per time interval. The alarm can be cleared manually
                        or, it will clear automatically after the configured time
                        interval."
            ::= { hiQTcaFaultMgt 33 }


------------------------------------------------------------------------
--
-- Survival Authority Definitions
--
------------------------------------------------------------------------

--
-- New variables for Survival Authority trap
--
hiQSurvivalAuthorityObjects OBJECT IDENTIFIER ::= { hiqTraps 222 }
 
-- Trap type
hiQSurvivalTrapType OBJECT-TYPE
    SYNTAX INTEGER { takeover(1), requestcommtest(2) }
    MAX-ACCESS read-only
    STATUS current
    DESCRIPTION "An enumerated value indicating the trap type."
    ::= { hiQSurvivalAuthorityObjects 1 }
 
-- Node name
hiQSurvivalNodeName OBJECT-TYPE
    SYNTAX OCTET STRING (SIZE (0..63))
    MAX-ACCESS read-only
    STATUS current
    DESCRIPTION "Name of node reporting to survival authority."
    ::= { hiQSurvivalAuthorityObjects 2 }
 
-- Cluster name
hiQSurvivalClusterName OBJECT-TYPE
    SYNTAX OCTET STRING (SIZE (0..63))
    MAX-ACCESS read-only
    STATUS current
    DESCRIPTION "Name of cluster reporting to survival authority."
    ::= { hiQSurvivalAuthorityObjects 3 }
 
-- IP Address
hiQSurvivalNodeIPAddress OBJECT-TYPE
    SYNTAX IpAddress
    MAX-ACCESS read-only
    STATUS current
    DESCRIPTION "IP address of node reporting to survival authority."
    ::= { hiQSurvivalAuthorityObjects 4 }
 
--
-- Definition for "Partner node left cluster" trap sent
-- to the Survival Authority when a node loses communication
-- with its partner node.
--
hiQSurvivalAuthorityTraps OBJECT-IDENTITY
                STATUS current
                DESCRIPTION
                "Events for Survival Authority processing"
                ::= { hiqTraps 223 }
 
hiQPartnerNodeLeftClusterTrap NOTIFICATION-TYPE
            OBJECTS {
                hiQSurvivalTrapType,
                hiQSurvivalNodeName,
                hiQSurvivalClusterName,
                hiQSurvivalNodeIPAddress
            }
            STATUS current
            DESCRIPTION  "Sent to the 'Survival Authority' to request
                          a communication test or when a node cannot
                          communicate with its partner, the 'Survival
                          Authority' is requested to respond with an
                          SNMP set command."
            ::= { hiQSurvivalAuthorityTraps 1 }
END
