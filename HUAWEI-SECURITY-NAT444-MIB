--  =================================================================
-- Copyright (C) 2009 by  HUAWEI TECHNOLOGIES. All rights reserved
-- 
-- Description:
-- Reference:
-- Version: V1.0
-- History:
-- shaoyu,2009-03-12,<contents>
-- =================================================================

    HUAWEI-SECURITY-NAT444-MIB DEFINITIONS ::= BEGIN
 
        IMPORTS
	    enterprises			
		FROM RFC1155-SMI
            OBJECT-GROUP            
                FROM SNMPv2-CONF            
            Integer32, Counter64, OBJECT-TYPE, MODULE-IDENTITY            
                FROM SNMPv2-SMI            
            TruthValue            
                FROM SNMPv2-TC;
    
    

--
-- Node definitions
--                       
 	-- 1.3.6.1.4.1.2011
	huawei OBJECT IDENTIFIER ::= { enterprises 2011 }
        
        -- 1.3.6.1.4.1.2011.6
        huaweiUtility OBJECT IDENTIFIER ::= { huawei 6 }
        
        -- 1.3.6.1.4.1.2011.6.122
        hwSecurity OBJECT IDENTIFIER ::= { huaweiUtility 122 }          
        
        -- 1.3.6.1.4.1.2011.6.122.58
        hwSecNat444MibObjects OBJECT IDENTIFIER ::= { hwSecurity 58 }
   
       	-- 1.3.6.1.4.1.2011.6.122.58.1                          
    	hwSecNat444TrapsObjests OBJECT IDENTIFIER ::= { hwSecNat444MibObjects 1 } 
        	
        -- 1.3.6.1.4.1.2011.6.122.58.1.1	//session number      
    	hwSecNat444SessionNumber OBJECT-TYPE
        	SYNTAX Gauge32 (0..3000000)        	
        	MAX-ACCESS accessible-for-notify
        	STATUS current
        	DESCRIPTION
            		"Number of sessions or ports at the NAT444 IP-CAR node."
        	::= { hwSecNat444TrapsObjests 1 } 	
       
       -- 1.3.6.1.4.1.2011.6.122.58.1.2 	//threshold number     
    	hwSecNat444ThresholdNum OBJECT-TYPE
        	SYNTAX Gauge32 (0..3000000)        	
        	MAX-ACCESS accessible-for-notify
        	STATUS current
        	DESCRIPTION
            		"Alarm threshold at the NAT444 IP-CAR node."
        	::= { hwSecNat444TrapsObjests 2 }
        	        	     
    	
        -- 1.3.6.1.4.1.2011.6.122.58.1.3	//slot 		
       	hwSecNat444TrapSlot OBJECT-TYPE
        	SYNTAX Integer32 (1..16)
        	MAX-ACCESS accessible-for-notify
        	STATUS current
        	DESCRIPTION
            		"Slot number."
        	::= { hwSecNat444TrapsObjests 3 }     
        
        -- 1.3.6.1.4.1.2011.6.122.58.1.4	//cpu        
    	hwSecNat444TrapCPU OBJECT-TYPE
        	SYNTAX Integer32 (0..3) 
        	MAX-ACCESS accessible-for-notify
       	 	STATUS current
        	DESCRIPTION
            		"CPU number."
        	::= { hwSecNat444TrapsObjests 4 }                 
        
        -- 1.3.6.1.4.1.2011.6.122.58.1.5       //ip address
    	hwSecNat444TrapIpAddr OBJECT-TYPE
        	--SYNTAX Gauge32 (0..2000000)
        	SYNTAX IpAddress
        	MAX-ACCESS accessible-for-notify
        	STATUS current
        	DESCRIPTION
            		"Session IP address at the NAT444 IP-CAR node."
        	::= { hwSecNat444TrapsObjests 5 }   
   	
        -- 1.3.6.1.4.1.2011.6.122.58.2                          
    	hwSecNat444Traps OBJECT IDENTIFIER ::= { hwSecNat444MibObjects 2 }   	 
                		                                
		-- 1.3.6.1.4.1.2011.6.122.58.2.1  
   		hwSecNat444TcpSessionOverThreshold NOTIFICATION-TYPE
		OBJECTS { 
			  hwSecNat444TrapSlot,
			  hwSecNat444TrapCPU, 
			  hwSecNat444TrapIpAddr,
			  hwSecNat444ThresholdNum,
			  hwSecNat444SessionNumber
		        }
		STATUS     current
		DESCRIPTION
		    "The number of TCP sessions at the NAT444 node exceeds the threshold."
		::= { hwSecNat444Traps 1 } 

		-- 1.3.6.1.4.1.2011.6.122.58.2.2		
		hwSecNat444UdpSessionOverThreshold NOTIFICATION-TYPE
		OBJECTS { 
			  hwSecNat444TrapSlot,
			  hwSecNat444TrapCPU, 
			  hwSecNat444TrapIpAddr,
			  hwSecNat444ThresholdNum,
			  hwSecNat444SessionNumber
			    }
		STATUS     current
		DESCRIPTION
		    "The number of UDP sessions at the NAT444 node exceeds the threshold."
		::= { hwSecNat444Traps 2 }
	
		-- 1.3.6.1.4.1.2011.6.122.58.2.3		
		hwSecNat444TotalSessionOverThreshold NOTIFICATION-TYPE
		OBJECTS { 
			  hwSecNat444TrapSlot,
			  hwSecNat444TrapCPU, 
			  hwSecNat444TrapIpAddr,
			  hwSecNat444ThresholdNum,
			  hwSecNat444SessionNumber  
		        }
		STATUS     current
		DESCRIPTION
		    "The number of total sessions at the NAT444 node exceeds the threshold."
		::= { hwSecNat444Traps 3 }

		-- 1.3.6.1.4.1.2011.6.122.58.2.4			
		hwSecNat444TcpSessionLessThreshold NOTIFICATION-TYPE
		OBJECTS { 
			  hwSecNat444TrapSlot,
			  hwSecNat444TrapCPU, 
			  hwSecNat444TrapIpAddr,
			  hwSecNat444ThresholdNum,
			  hwSecNat444SessionNumber 
		        }
		STATUS     current
		DESCRIPTION
		    "The number of TCP sessions at the NAT444 node is below the threshold."
		::= { hwSecNat444Traps 4 } 

		-- 1.3.6.1.4.1.2011.6.122.58.2.5		
		hwSecNat444UdpSessionLessThreshold NOTIFICATION-TYPE
		OBJECTS { 
			  hwSecNat444TrapSlot,
			  hwSecNat444TrapCPU, 
			  hwSecNat444TrapIpAddr,
			  hwSecNat444ThresholdNum,
			  hwSecNat444SessionNumber
			   }
		STATUS     current
		DESCRIPTION
		    "The number of UDP sessions at the NAT444 node is below the threshold."
		::= { hwSecNat444Traps 5 }
	
		-- 1.3.6.1.4.1.2011.6.122.58.2.6	
		hwSecNat444TotalSessionLessThreshold NOTIFICATION-TYPE
		OBJECTS { 
			  hwSecNat444TrapSlot,
			  hwSecNat444TrapCPU, 
			  hwSecNat444TrapIpAddr,
			  hwSecNat444ThresholdNum,
			  hwSecNat444SessionNumber 
			   }
		STATUS     current
		DESCRIPTION
		    "The number of total sessions at the NAT444 node is below the threshold."
		::= { hwSecNat444Traps 6 }    
		
 -- ===============================================
-- Conformance Information             
-- ===============================================

		hwNAT444MibConformance OBJECT IDENTIFIER ::= { hwSecNat444MibObjects 3 }
		
		hwNAT444MibCompliances OBJECT IDENTIFIER ::= { hwNAT444MibConformance 1 }
		
		hwNAT444MibGroups OBJECT IDENTIFIER ::= { hwNAT444MibConformance 2 }
  
-- ===============================================
-- Compliance Statements             
-- ===============================================
        hwNAT444MibCompliance MODULE-COMPLIANCE
			 STATUS current
			 DESCRIPTION 
				" "
			 MODULE -- this module
			 MANDATORY-GROUPS 
				{  
				hwNAT444TrapObjectsGroup,
				hwNAT444TrapsGroup
				}
			::= { hwNAT444MibCompliances 1 }   

		hwNAT444TrapObjectsGroup OBJECT-GROUP
			OBJECTS { 
			  hwSecNat444TrapSlot,
			  hwSecNat444TrapCPU, 
			  hwSecNat444TrapIpAddr,
			  hwSecNat444ThresholdNum,
			  hwSecNat444SessionNumber		
				}
			STATUS current
			DESCRIPTION 
				"This table specifies the objects used for traps."
			::= { hwNAT444MibGroups 1 }
			
	    hwNAT444TrapsGroup NOTIFICATION-GROUP
			NOTIFICATIONS {                               
                    hwSecNat444TcpSessionOverThreshold,
                    hwSecNat444UdpSessionOverThreshold,
                    hwSecNat444TotalSessionOverThreshold,
                    hwSecNat444TcpSessionLessThreshold,
                    hwSecNat444UdpSessionLessThreshold,
                    hwSecNat444TotalSessionLessThreshold
               		}
			STATUS current
			DESCRIPTION 
				"NAT444 traps."
			::= { hwNAT444MibGroups 2 }
  
    END

--
-- HUAWEI-SECSTAT-MIB.mib
--
