--MibName=caiW2kOs
--	------------------------------------------------------------------------
--
--	This material contains, and is a part of a computer software program
--	which is, proprietary and confidential information owned by:
--	               COMPUTER ASSOCIATES INTERNATIONAL, INC.
--	The program, including this material, may not be duplicated, disclosed
--	or reproduced in whole or in part for any purpose without the express
--	written authorisation of COMPUTER ASSOCIATES.  All authorised
--	reproductions must be marked with this legend.
--
--	        Copyright 2000 - 2006 Computer Associates International, Inc.
--	                 The Software that Manages eBusiness
--
--	------------------------------------------------------------------------
--
--      Windows 2000 System Agent MIB
--      v1.0.0
--


CA-W2KOS-MIB DEFINITIONS ::= BEGIN


IMPORTS
	enterprises,
	IpAddress,
	Counter,
	Gauge         FROM RFC1155-SMI

	PhysAddress,
	DisplayString FROM RFC1213-MIB

	OBJECT-TYPE   FROM RFC-1212

	TRAP-TYPE     FROM RFC-1215;

-- FROM RFC1514-MIB
KBytes ::= INTEGER (0..2147483647)


--	------------------------------------------------------------------------
--      Oids of caiW2kOs agent start with 1.3.6.1.4.1.791.2.10.2.43
--	------------------------------------------------------------------------
cai       OBJECT IDENTIFIER ::= { enterprises 791 }
caiSysMgr OBJECT IDENTIFIER ::= { cai 2 }
tng       OBJECT IDENTIFIER ::= { caiSysMgr 10 }
agents    OBJECT IDENTIFIER ::= { tng 2 }
caiW2kOs  OBJECT IDENTIFIER ::= { agents 43 }


--	------------------------------------------------------------------------
--      The four big groups
--	------------------------------------------------------------------------
w2kConfigGroup    OBJECT IDENTIFIER ::= { caiW2kOs 1 }
w2kStatusGroup    OBJECT IDENTIFIER ::= { caiW2kOs 2 }
w2kAvailableGroup OBJECT IDENTIFIER ::= { caiW2kOs 3 }
w2kHistoryGroup   OBJECT IDENTIFIER ::= { caiW2kOs 4 }


--	------------------------------------------------------------------------
--      Configuration Groups
--	------------------------------------------------------------------------
w2kConfigGeneralGroup OBJECT IDENTIFIER ::= { w2kConfigGroup 1 }
w2kConfigSysGroup     OBJECT IDENTIFIER ::= { w2kConfigGroup 2 }
w2kConfigCpuGroup     OBJECT IDENTIFIER ::= { w2kConfigGroup 3 }
w2kConfigMemGroup     OBJECT IDENTIFIER ::= { w2kConfigGroup 4 }
w2kConfigLVolGroup    OBJECT IDENTIFIER ::= { w2kConfigGroup 5 }
w2kConfigMntGroup     OBJECT IDENTIFIER ::= { w2kConfigGroup 6 }
w2kConfigDfsGroup     OBJECT IDENTIFIER ::= { w2kConfigGroup 7 }
w2kConfigQuotGroup    OBJECT IDENTIFIER ::= { w2kConfigGroup 8 }
w2kConfigDirGroup     OBJECT IDENTIFIER ::= { w2kConfigGroup 9 }
w2kConfigFileGroup    OBJECT IDENTIFIER ::= { w2kConfigGroup 10 }
w2kConfigProcGroup    OBJECT IDENTIFIER ::= { w2kConfigGroup 11 }
w2kConfigSrvcGroup    OBJECT IDENTIFIER ::= { w2kConfigGroup 12 }
w2kConfigJobGroup     OBJECT IDENTIFIER ::= { w2kConfigGroup 13 }
w2kConfigSessGroup    OBJECT IDENTIFIER ::= { w2kConfigGroup 14 }
w2kConfigPrnGroup     OBJECT IDENTIFIER ::= { w2kConfigGroup 15 }
w2kConfigNetGroup     OBJECT IDENTIFIER ::= { w2kConfigGroup 16 }
w2kConfigRegGroup     OBJECT IDENTIFIER ::= { w2kConfigGroup 17 }


--	------------------------------------------------------------------------
--      Status Groups
--	------------------------------------------------------------------------
w2kStatusGeneralGroup OBJECT IDENTIFIER ::= { w2kStatusGroup 1 }
w2kStatusCpuGroup     OBJECT IDENTIFIER ::= { w2kStatusGroup 2 }
w2kStatusMemGroup     OBJECT IDENTIFIER ::= { w2kStatusGroup 3 }
w2kStatusLVolGroup    OBJECT IDENTIFIER ::= { w2kStatusGroup 4 }
w2kStatusMntGroup     OBJECT IDENTIFIER ::= { w2kStatusGroup 5 }
w2kStatusDfsGroup     OBJECT IDENTIFIER ::= { w2kStatusGroup 6 }
w2kStatusQuotGroup    OBJECT IDENTIFIER ::= { w2kStatusGroup 7 }
w2kStatusDirGroup     OBJECT IDENTIFIER ::= { w2kStatusGroup 8 }
w2kStatusFileGroup    OBJECT IDENTIFIER ::= { w2kStatusGroup 9 }
w2kStatusProcGroup    OBJECT IDENTIFIER ::= { w2kStatusGroup 10 }
w2kStatusSrvcGroup    OBJECT IDENTIFIER ::= { w2kStatusGroup 11 }
w2kStatusJobGroup     OBJECT IDENTIFIER ::= { w2kStatusGroup 12 }
w2kStatusSessGroup    OBJECT IDENTIFIER ::= { w2kStatusGroup 13 }
w2kStatusPrnGroup     OBJECT IDENTIFIER ::= { w2kStatusGroup 14 }
w2kStatusNetGroup     OBJECT IDENTIFIER ::= { w2kStatusGroup 15 }
w2kStatusRegGroup     OBJECT IDENTIFIER ::= { w2kStatusGroup 16 }


--	------------------------------------------------------------------------
--      Availability Groups
--	------------------------------------------------------------------------
w2kAvailLVolGroup OBJECT IDENTIFIER ::= { w2kAvailableGroup 1 }
w2kAvailMntGroup  OBJECT IDENTIFIER ::= { w2kAvailableGroup 2 }
w2kAvailDfsGroup  OBJECT IDENTIFIER ::= { w2kAvailableGroup 3 }
w2kAvailQuotGroup OBJECT IDENTIFIER ::= { w2kAvailableGroup 4 }
w2kAvailProcGroup OBJECT IDENTIFIER ::= { w2kAvailableGroup 5 }
w2kAvailSrvcGroup OBJECT IDENTIFIER ::= { w2kAvailableGroup 6 }
w2kAvailJobGroup  OBJECT IDENTIFIER ::= { w2kAvailableGroup 7 }
w2kAvailSessGroup OBJECT IDENTIFIER ::= { w2kAvailableGroup 8 }
w2kAvailPrnGroup  OBJECT IDENTIFIER ::= { w2kAvailableGroup 9 }




--	------------------------------------------------------------------------
--      General Config Group
--	------------------------------------------------------------------------


w2kConfigGeneralAgentVersion OBJECT-TYPE
	SYNTAX DisplayString
	ACCESS read-only
	STATUS mandatory
	DESCRIPTION
		"&<caiW2kOs.100>The currently installed version of the agent."
	::= { w2kConfigGeneralGroup 1 }


w2kConfigGeneralColdStartTime OBJECT-TYPE
	SYNTAX DisplayString
	ACCESS read-only
	STATUS mandatory
	DESCRIPTION
		"&<caiW2kOs.101>The date and time that the agent was last started."
	::= { w2kConfigGeneralGroup 2 }


w2kConfigGeneralWarmStartTime OBJECT-TYPE
	SYNTAX DisplayString
	ACCESS read-only
	STATUS mandatory
	DESCRIPTION
		"&<caiW2kOs.102>The date and time that the agent's configuration was last changed."
	::= { w2kConfigGeneralGroup 3 }


w2kConfigGeneralCpuPollTime OBJECT-TYPE
	SYNTAX DisplayString
	ACCESS read-only
	STATUS mandatory
	DESCRIPTION
		"&<caiW2kOs.103>The date and time that the agent last polled the processor information."
	::= { w2kConfigGeneralGroup 4 }


w2kConfigGeneralMemPollTime OBJECT-TYPE
	SYNTAX DisplayString
	ACCESS read-only
	STATUS mandatory
	DESCRIPTION
		"&<caiW2kOs.104>The date and time that the agent last polled the memory information."
	::= { w2kConfigGeneralGroup 5 }


w2kConfigGeneralLVolPollTime OBJECT-TYPE
	SYNTAX DisplayString
	ACCESS read-only
	STATUS mandatory
	DESCRIPTION
		"&<caiW2kOs.105>The date and time that the agent last polled the logical volume information."
	::= { w2kConfigGeneralGroup 6 }


w2kConfigGeneralMntPollTime OBJECT-TYPE
	SYNTAX DisplayString
	ACCESS read-only
	STATUS mandatory
	DESCRIPTION
		"&<caiW2kOs.106>The date and time that the agent last polled the mounts information."
	::= { w2kConfigGeneralGroup 7 }


w2kConfigGeneralDfsPollTime OBJECT-TYPE
	SYNTAX DisplayString
	ACCESS read-only
	STATUS mandatory
	DESCRIPTION
		"&<caiW2kOs.107>The date and time that the agent last polled the distributed file system link information."
	::= { w2kConfigGeneralGroup 8 }


w2kConfigGeneralQuotPollTime OBJECT-TYPE
	SYNTAX DisplayString
	ACCESS read-only
	STATUS mandatory
	DESCRIPTION
		"&<caiW2kOs.108>The date and time that the agent last polled the quota information."
	::= { w2kConfigGeneralGroup 9 }


w2kConfigGeneralDirPollTime OBJECT-TYPE
	SYNTAX DisplayString
	ACCESS read-only
	STATUS mandatory
	DESCRIPTION
		"&<caiW2kOs.109>The date and time that the agent last polled the directory information."
	::= { w2kConfigGeneralGroup 10 }


w2kConfigGeneralFilePollTime OBJECT-TYPE
	SYNTAX DisplayString
	ACCESS read-only
	STATUS mandatory
	DESCRIPTION
		"&<caiW2kOs.110>The date and time that the agent last polled the file information."
	::= { w2kConfigGeneralGroup 11 }


w2kConfigGeneralProcPollTime OBJECT-TYPE
	SYNTAX DisplayString
	ACCESS read-only
	STATUS mandatory
	DESCRIPTION
		"&<caiW2kOs.111>The date and time that the agent last polled the process information."
	::= { w2kConfigGeneralGroup 12 }


w2kConfigGeneralSrvcPollTime OBJECT-TYPE
	SYNTAX DisplayString
	ACCESS read-only
	STATUS mandatory
	DESCRIPTION
		"&<caiW2kOs.112>The date and time that the agent last polled the service information."
	::= { w2kConfigGeneralGroup 13 }


w2kConfigGeneralJobPollTime OBJECT-TYPE
	SYNTAX DisplayString
	ACCESS read-only
	STATUS mandatory
	DESCRIPTION
		"&<caiW2kOs.113>The date and time that the agent last polled the job information."
	::= { w2kConfigGeneralGroup 14 }


w2kConfigGeneralSessPollTime OBJECT-TYPE
	SYNTAX DisplayString
	ACCESS read-only
	STATUS mandatory
	DESCRIPTION
		"&<caiW2kOs.114>The date and time that the agent last polled the session information."
	::= { w2kConfigGeneralGroup 15 }


w2kConfigGeneralPrnPollTime OBJECT-TYPE
	SYNTAX DisplayString
	ACCESS read-only
	STATUS mandatory
	DESCRIPTION
		"&<caiW2kOs.115>The date and time that the agent last polled the printer information."
	::= { w2kConfigGeneralGroup 16 }


w2kConfigGeneralNetPollTime OBJECT-TYPE
	SYNTAX DisplayString
	ACCESS read-only
	STATUS mandatory
	DESCRIPTION
		"&<caiW2kOs.116>The date and time that the agent last polled the network interface information."
	::= { w2kConfigGeneralGroup 17 }


w2kConfigGeneralRegPollTime OBJECT-TYPE
	SYNTAX DisplayString
	ACCESS read-only
	STATUS mandatory
	DESCRIPTION
		"&<caiW2kOs.117>The date and time that the agent last polled the registry entry information."
	::= { w2kConfigGeneralGroup 18 }




--	------------------------------------------------------------------------
--      System Config Group
--	------------------------------------------------------------------------


w2kConfigSysNodeName OBJECT-TYPE
	SYNTAX DisplayString
	ACCESS read-only
	STATUS mandatory
	DESCRIPTION
		"&<caiW2kOs.118>The node name of the system."
	::= { w2kConfigSysGroup 1 }


w2kConfigSysVersion OBJECT-TYPE
	SYNTAX DisplayString
	ACCESS read-only
	STATUS mandatory
	DESCRIPTION
		"&<caiW2kOs.119>The OS version (build, service pack, etc.) of the system."
	::= { w2kConfigSysGroup 2 }


w2kConfigSysBios OBJECT-TYPE
	SYNTAX DisplayString
	ACCESS read-only
	STATUS mandatory
	DESCRIPTION
		"&<caiW2kOs.120>The BIOS version (date, revision, etc.) of the system."
	::= { w2kConfigSysGroup 3 }


w2kConfigSysColdStartTime OBJECT-TYPE
	SYNTAX DisplayString
	ACCESS read-only
	STATUS mandatory
	DESCRIPTION
		"&<caiW2kOs.121>The date and time that the system was last started."
	::= { w2kConfigSysGroup 4 }




--	------------------------------------------------------------------------
--      Processor Config Group
--	------------------------------------------------------------------------


w2kConfigCpuPollInterval OBJECT-TYPE
	SYNTAX INTEGER
	ACCESS read-write
	STATUS mandatory
	DESCRIPTION
		"&<caiW2kOs.122>The time (in seconds) between the polling of the processor information. Valid values are greater than or equal to 30."
	DEFVAL { 120 }
	::= { w2kConfigCpuGroup 1 }


w2kConfigCpuPollMethod OBJECT-TYPE
	SYNTAX INTEGER {
		disabled(1),
		poll-interval-only(2),
		poll-interval-and-query(3),
		query-only(4)
	}
	ACCESS read-write
	STATUS mandatory
	DESCRIPTION
		"&<caiW2kOs.123>If set to 'disabled', the agent no more retrieves the processor information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigCpuGroup 2 }


w2kConfigCpuLoadLag OBJECT-TYPE
	SYNTAX INTEGER
	ACCESS read-write
	STATUS mandatory
	DESCRIPTION
		"&<caiW2kOs.124>The number of consecutive poll intervals that the threshold has to be (b)reached before the status changes. Valid values are greater than 0."
	DEFVAL { 3 }
	::= { w2kConfigCpuGroup 3 }


w2kConfigCpuLoadWarn OBJECT-TYPE
	SYNTAX INTEGER
	ACCESS read-write
	STATUS mandatory
	DESCRIPTION
		"&<caiW2kOs.125>Warning threshold for the utilization of the processor (as percentage value of 100). Valid values are 1 to 99 and smaller than the critical threshold."
	DEFVAL { 70 }
	::= { w2kConfigCpuGroup 4 }


w2kConfigCpuLoadCrit OBJECT-TYPE
	SYNTAX INTEGER
	ACCESS read-write
	STATUS mandatory
	DESCRIPTION
		"&<caiW2kOs.126>Critical threshold for the utilization of the processor (as percentage value of 100). Valid values are 2 to 100 and greater than the warning threshold."
	DEFVAL { 90 }
	::= { w2kConfigCpuGroup 5 }


w2kConfigCpuLoadMonitor OBJECT-TYPE
	SYNTAX INTEGER {
		do-not-monitor(1),
		warning-only(2),
		critical-only(3),
		both(4)
	}
	ACCESS read-write
	STATUS mandatory
	DESCRIPTION
		"&<caiW2kOs.127>Flag indicating whether the utilization of the processor should be monitored and if so, which threshold should be compared with."
	DEFVAL { 4 }
	::= { w2kConfigCpuGroup 6 }


w2kConfigCpuLossAction OBJECT-TYPE
	SYNTAX INTEGER {
		remove(1),
		up(2),
		down-warning(3),
		down-critical(4)
	}
	ACCESS read-write
	STATUS mandatory
	DESCRIPTION
		"&<caiW2kOs.128>Flag defining the severity if the loss of the processor is detected or whether to remove this watcher in that case."
	DEFVAL { 1 }
	::= { w2kConfigCpuGroup 7 }




--	------------------------------------------------------------------------
--      Memory Config Group
--	------------------------------------------------------------------------


w2kConfigMemPollInterval OBJECT-TYPE
	SYNTAX INTEGER
	ACCESS read-write
	STATUS mandatory
	DESCRIPTION
		"&<caiW2kOs.129>The time (in seconds) between the polling of the memory information. Valid values are greater than or equal to 30."
	DEFVAL { 120 }
	::= { w2kConfigMemGroup 1 }


w2kConfigMemPollMethod OBJECT-TYPE
	SYNTAX INTEGER {
		disabled(1),
		poll-interval-only(2),
		poll-interval-and-query(3),
		query-only(4)
	}
	ACCESS read-write
	STATUS mandatory
	DESCRIPTION
		"&<caiW2kOs.130>If set to 'disabled', the agent no more retrieves the memory information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigMemGroup 2 }




--	------------------------------------------------------------------------
--      Logical Volumes Config Group
--	------------------------------------------------------------------------


w2kConfigLVolPollInterval OBJECT-TYPE
	SYNTAX INTEGER
	ACCESS read-write
	STATUS mandatory
	DESCRIPTION
		"&<caiW2kOs.131>The time (in seconds) between the polling of the logical volume information. Valid values are greater than or equal to 30."
	DEFVAL { 120 }
	::= { w2kConfigLVolGroup 1 }


w2kConfigLVolPollMethod OBJECT-TYPE
	SYNTAX INTEGER {
		disabled(1),
		poll-interval-only(2),
		poll-interval-and-query(3),
		query-only(4)
	}
	ACCESS read-write
	STATUS mandatory
	DESCRIPTION
		"&<caiW2kOs.132>If set to 'disabled', the agent no more retrieves the logical volume information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigLVolGroup 2 }


w2kConfigLVolAutoPollInterval OBJECT-TYPE
	SYNTAX INTEGER
	ACCESS read-write
	STATUS mandatory
	DESCRIPTION
		"&<caiW2kOs.133>The time (in minutes), when a new auto discovery process is started. Valid values are greater than or equal to 30 or set to -1. If set to -1, auto discovery of logical volumes will no more be made."
	DEFVAL { 60 }
	::= { w2kConfigLVolGroup 3 }


w2kConfigLVolFragPollInterval OBJECT-TYPE
	SYNTAX INTEGER
	ACCESS read-write
	STATUS mandatory
	DESCRIPTION
		"&<caiW2kOs.134>The time (in hours), when the fragmentation determination of the watched logical volumes is started again (triggered by the next polling or a get request). The agent will not determine the fragmentation every standard poll interval, because it is a long lasting task. Valid values are greater than or equal to 1 or set to -1. After a set on this attribute, the fragmentation determination will be started new by the next polling or by a get request. If set to -1, the fragmentation is no more polled."
	DEFVAL { 8 }
	::= { w2kConfigLVolGroup 4 }


w2kConfigLVolName OBJECT-TYPE
	SYNTAX DisplayString
	ACCESS read-write
	STATUS mandatory
	DESCRIPTION
		"&<caiW2kOs.135>Name of the watcher to be added/removed, monitoring a logical volume with this name. If adding an auto discovery watcher, this name can be a wildcarded logical volume name filtering the logical volumes to be auto discovered (any backslash in the wildcarded name must be doubled). For each auto discovered logical volume a watcher will be created. Important: This name is case insensitive."
	::= { w2kConfigLVolGroup 5 }


w2kConfigLVolDescription OBJECT-TYPE
	SYNTAX DisplayString
	ACCESS read-write
	STATUS mandatory
	DESCRIPTION
		"&<caiW2kOs.136>Any description for this watcher."
	::= { w2kConfigLVolGroup 6 }


w2kConfigLVolAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigLVolGroup 7 }


w2kConfigLVolSizeWarn OBJECT-TYPE
	SYNTAX DisplayString
	ACCESS read-write
	STATUS mandatory
	DESCRIPTION
		"&<caiW2kOs.138>Warning threshold in megabytes, either for the free (by appending a 'F') or for the used logical volume size. The used size can also be defined as a percentage value of the total logical volume size (by appending a '%'). Valid values are greater than 0 and smaller (in case of 'free' greater) than the critical threshold."
	DEFVAL { "70%" }
	::= { w2kConfigLVolGroup 8 }


w2kConfigLVolSizeCrit OBJECT-TYPE
	SYNTAX DisplayString
	ACCESS read-write
	STATUS mandatory
	DESCRIPTION
		"&<caiW2kOs.139>Critical threshold in megabytes, either for the free (by appending a 'F') or for the used logical volume size. The used size can also be defined as a percentage value of the total logical volume size (by appending a '%'). Valid values are greater than 1 and greater (in case of 'free' smaller) than the warning threshold."
	DEFVAL { "90%" }
	::= { w2kConfigLVolGroup 9 }


w2kConfigLVolSizeMonitor OBJECT-TYPE
	SYNTAX INTEGER {
		do-not-monitor(1),
		warning-only(2),
		critical-only(3),
		both(4)
	}
	ACCESS read-write
	STATUS mandatory
	DESCRIPTION
		"&<caiW2kOs.140>Flag indicating whether the used logical volume size should be monitored and if so, which threshold should be compared with."
	DEFVAL { 4 }
	::= { w2kConfigLVolGroup 10 }


w2kConfigLVolSizeDWarn OBJECT-TYPE
	SYNTAX DisplayString
	ACCESS read-write
	STATUS mandatory
	DESCRIPTION
		"&<caiW2kOs.141>Warning threshold, either for the growth (by appending a '+') or for the shrinkage (by appending a '-') or for the absolute delta in used logical volume size monitored in one poll interval. Growth, shrinkage and absolute delta can be given in megabytes or as a percentage value of the total logical volume size (by appending a '%'). Valid values are greater than 0 and smaller than the critical threshold."
	DEFVAL { "1%" }
	::= { w2kConfigLVolGroup 11 }


w2kConfigLVolSizeDCrit OBJECT-TYPE
	SYNTAX DisplayString
	ACCESS read-write
	STATUS mandatory
	DESCRIPTION
		"&<caiW2kOs.142>Critical threshold, either for the growth (by appending a '+') or for the shrinkage (by appending a '-') or for the absolute delta in used logical volume size monitored in one poll interval. Growth, shrinkage and absolute delta can be given in megabytes or as a percentage value of the total logical volume size (by appending a '%'). Valid values are greater than 1 and greater than the warning threshold."
	DEFVAL { "2%" }
	::= { w2kConfigLVolGroup 12 }


w2kConfigLVolSizeDMonitor OBJECT-TYPE
	SYNTAX INTEGER {
		do-not-monitor(1),
		warning-only(2),
		critical-only(3),
		both(4)
	}
	ACCESS read-write
	STATUS mandatory
	DESCRIPTION
		"&<caiW2kOs.143>Flag indicating whether the delta in used logical volume size should be monitored and if so, which threshold should be compared with."
	DEFVAL { 4 }
	::= { w2kConfigLVolGroup 13 }


w2kConfigLVolTPutWarn OBJECT-TYPE
	SYNTAX INTEGER
	ACCESS read-write
	STATUS mandatory
	DESCRIPTION
		"&<caiW2kOs.144>Warning threshold for the throughput rate (kilobytes per second). Valid values are greater than 0 and smaller than the critical threshold."
	DEFVAL { 400 }
	::= { w2kConfigLVolGroup 14 }


w2kConfigLVolTPutCrit OBJECT-TYPE
	SYNTAX INTEGER
	ACCESS read-write
	STATUS mandatory
	DESCRIPTION
		"&<caiW2kOs.145>Critical threshold for the throughput rate (kilobytes per second). Valid values are greater than 1 and greater than the warning threshold."
	DEFVAL { 800 }
	::= { w2kConfigLVolGroup 15 }


w2kConfigLVolTPutMonitor OBJECT-TYPE
	SYNTAX INTEGER {
		do-not-monitor(1),
		warning-only(2),
		critical-only(3),
		both(4)
	}
	ACCESS read-write
	STATUS mandatory
	DESCRIPTION
		"&<caiW2kOs.146>Flag indicating whether the throughput rate should be monitored and if so, which threshold should be compared with."
	DEFVAL { 4 }
	::= { w2kConfigLVolGroup 16 }


w2kConfigLVolFragWarn OBJECT-TYPE
	SYNTAX INTEGER
	ACCESS read-write
	STATUS mandatory
	DESCRIPTION
		"&<caiW2kOs.147>Warning threshold for the file fragmentation (as percentage value of 100). Valid values are 1 to 99 and smaller than the critical threshold."
	DEFVAL { 30 }
	::= { w2kConfigLVolGroup 17 }


w2kConfigLVolFragCrit OBJECT-TYPE
	SYNTAX INTEGER
	ACCESS read-write
	STATUS mandatory
	DESCRIPTION
		"&<caiW2kOs.148>Critical threshold for the file fragmentation (as percentage value of 100). Valid values are 2 to 100 and greater than the warning threshold."
	DEFVAL { 50 }
	::= { w2kConfigLVolGroup 18 }


w2kConfigLVolFragMonitor OBJECT-TYPE
	SYNTAX INTEGER {
		do-not-monitor(1),
		warning-only(2),
		critical-only(3),
		both(4)
	}
	ACCESS read-write
	STATUS mandatory
	DESCRIPTION
		"&<caiW2kOs.149>Flag indicating whether the file fragmentation should be monitored and if so, which threshold should be compared with."
	DEFVAL { 4 }
	::= { w2kConfigLVolGroup 19 }


w2kConfigLVolLossAction OBJECT-TYPE
	SYNTAX INTEGER {
		remove(1),
		up(2),
		down-warning(3),
		down-critical(4)
	}
	ACCESS read-write
	STATUS mandatory
	DESCRIPTION
		"&<caiW2kOs.150>Flag defining the severity if the loss of the logical volume is detected or whether to remove this watcher in that case."
	DEFVAL { 4 }
	::= { w2kConfigLVolGroup 20 }


w2kConfigLVolAutoTableWatcherName OBJECT-TYPE
	SYNTAX DisplayString
	ACCESS read-write
	STATUS mandatory
	DESCRIPTION
		"&<caiW2kOs.151>Name of the watcher to be added in the auto discovery table."
	::= { w2kConfigLVolGroup 21 }


w2kConfigLVolButton OBJECT-TYPE
	SYNTAX INTEGER {
		none(1),
		add(2),
		remove(3),
		add-auto(4),
		remove-auto(5)
	}
	ACCESS read-write
	STATUS mandatory
	DESCRIPTION
		"&<caiW2kOs.152>This attribute is used to add or remove a watcher with the current value of the watcher name attribute in this group, or to add or remove an auto discovery watcher with the current value of the auto table watcher name attribute in this group."
	::= { w2kConfigLVolGroup 22 }


w2kConfigLVolAutoTable OBJECT-TYPE
	SYNTAX SEQUENCE OF W2kConfigLVolAutoRow
	ACCESS not-accessible
	STATUS mandatory
	DESCRIPTION
		"&<caiW2kOs.153>A table containing all auto discovery watchers for logical volumes."
	::= { w2kConfigLVolGroup 23 }


w2kConfigLVolAutoEntry OBJECT-TYPE
	SYNTAX W2kConfigLVolAutoRow
	ACCESS not-accessible
	STATUS mandatory
	DESCRIPTION
		"&<caiW2kOs.154>The table entry."
	INDEX { w2kConfigLVolAutoWatcherName }
	::= { w2kConfigLVolAutoTable 1 }


W2kConfigLVolAutoRow ::=
	SEQUENCE {
		w2kConfigLVolAutoWatcherName DisplayString,
		w2kConfigLVolAutoName DisplayString,
		w2kConfigLVolAutoDescription DisplayString,
		w2kConfigLVolAutoAggLag INTEGER,
		w2kConfigLVolAutoSizeWarn DisplayString,
		w2kConfigLVolAutoSizeCrit DisplayString,
		w2kConfigLVolAutoSizeMonitor INTEGER,
		w2kConfigLVolAutoSizeDWarn DisplayString,
		w2kConfigLVolAutoSizeDCrit DisplayString,
		w2kConfigLVolAutoSizeDMonitor INTEGER,
		w2kConfigLVolAutoTPutWarn INTEGER,
		w2kConfigLVolAutoTPutCrit INTEGER,
		w2kConfigLVolAutoTPutMonitor INTEGER,
		w2kConfigLVolAutoFragWarn INTEGER,
		w2kConfigLVolAutoFragCrit INTEGER,
		w2kConfigLVolAutoFragMonitor INTEGER,
		w2kConfigLVolAutoLossAction INTEGER,
		w2kConfigLVolAutoButton INTEGER
	}


w2kConfigLVolAutoWatcherName OBJECT-TYPE
	SYNTAX DisplayString
	ACCESS read-only
	STATUS mandatory
	DESCRIPTION
		"&<caiW2kOs.155>Name of the auto discovery watcher."
	::= { w2kConfigLVolAutoEntry 1 }


w2kConfigLVolAutoName OBJECT-TYPE
	SYNTAX DisplayString
	ACCESS read-write
	STATUS mandatory
	DESCRIPTION
		"&<caiW2kOs.156>Wildcarded logical volume name filtering the logical volumes to be auto discovered (any backslash in the wildcarded name must be doubled). For each auto discovered logical volume a watcher will be created. Important: This name is case insensitive."
	::= { w2kConfigLVolAutoEntry 2 }


w2kConfigLVolAutoDescription OBJECT-TYPE
	SYNTAX DisplayString
	ACCESS read-write
	STATUS mandatory
	DESCRIPTION
		"&<caiW2kOs.157>This attribute has the same purpose as the corresponding attribute in the config group (please see there). The difference is that it specifies the default if the logical volume is automatically discovered (in contrast to manually adding a watcher for the logical volume)."
	::= { w2kConfigLVolAutoEntry 3 }


w2kConfigLVolAutoAggLag OBJECT-TYPE
	SYNTAX INTEGER
	ACCESS read-write
	STATUS mandatory
	DESCRIPTION
		"&<caiW2kOs.157>This attribute has the same purpose as the corresponding attribute in the config group (please see there). The difference is that it specifies the default if the logical volume is automatically discovered (in contrast to manually adding a watcher for the logical volume)."
	::= { w2kConfigLVolAutoEntry 4 }


w2kConfigLVolAutoSizeWarn OBJECT-TYPE
	SYNTAX DisplayString
	ACCESS read-write
	STATUS mandatory
	DESCRIPTION
		"&<caiW2kOs.157>This attribute has the same purpose as the corresponding attribute in the config group (please see there). The difference is that it specifies the default if the logical volume is automatically discovered (in contrast to manually adding a watcher for the logical volume)."
	::= { w2kConfigLVolAutoEntry 5 }


w2kConfigLVolAutoSizeCrit OBJECT-TYPE
	SYNTAX DisplayString
	ACCESS read-write
	STATUS mandatory
	DESCRIPTION
		"&<caiW2kOs.157>This attribute has the same purpose as the corresponding attribute in the config group (please see there). The difference is that it specifies the default if the logical volume is automatically discovered (in contrast to manually adding a watcher for the logical volume)."
	::= { w2kConfigLVolAutoEntry 6 }


w2kConfigLVolAutoSizeMonitor OBJECT-TYPE
	SYNTAX INTEGER {
		do-not-monitor(1),
		warning-only(2),
		critical-only(3),
		both(4)
	}
	ACCESS read-write
	STATUS mandatory
	DESCRIPTION
		"&<caiW2kOs.157>This attribute has the same purpose as the corresponding attribute in the config group (please see there). The difference is that it specifies the default if the logical volume is automatically discovered (in contrast to manually adding a watcher for the logical volume)."
	DEFVAL { 0 }
	::= { w2kConfigLVolAutoEntry 7 }


w2kConfigLVolAutoSizeDWarn OBJECT-TYPE
	SYNTAX DisplayString
	ACCESS read-write
	STATUS mandatory
	DESCRIPTION
		"&<caiW2kOs.157>This attribute has the same purpose as the corresponding attribute in the config group (please see there). The difference is that it specifies the default if the logical volume is automatically discovered (in contrast to manually adding a watcher for the logical volume)."
	::= { w2kConfigLVolAutoEntry 8 }


w2kConfigLVolAutoSizeDCrit OBJECT-TYPE
	SYNTAX DisplayString
	ACCESS read-write
	STATUS mandatory
	DESCRIPTION
		"&<caiW2kOs.157>This attribute has the same purpose as the corresponding attribute in the config group (please see there). The difference is that it specifies the default if the logical volume is automatically discovered (in contrast to manually adding a watcher for the logical volume)."
	::= { w2kConfigLVolAutoEntry 9 }


w2kConfigLVolAutoSizeDMonitor OBJECT-TYPE
	SYNTAX INTEGER {
		do-not-monitor(1),
		warning-only(2),
		critical-only(3),
		both(4)
	}
	ACCESS read-write
	STATUS mandatory
	DESCRIPTION
		"&<caiW2kOs.157>This attribute has the same purpose as the corresponding attribute in the config group (please see there). The difference is that it specifies the default if the logical volume is automatically discovered (in contrast to manually adding a watcher for the logical volume)."
	DEFVAL { 0 }
	::= { w2kConfigLVolAutoEntry 10 }


w2kConfigLVolAutoTPutWarn OBJECT-TYPE
	SYNTAX INTEGER
	ACCESS read-write
	STATUS mandatory
	DESCRIPTION
		"&<caiW2kOs.157>This attribute has the same purpose as the corresponding attribute in the config group (please see there). The difference is that it specifies the default if the logical volume is automatically discovered (in contrast to manually adding a watcher for the logical volume)."
	::= { w2kConfigLVolAutoEntry 11 }


w2kConfigLVolAutoTPutCrit OBJECT-TYPE
	SYNTAX INTEGER
	ACCESS read-write
	STATUS mandatory
	DESCRIPTION
		"&<caiW2kOs.157>This attribute has the same purpose as the corresponding attribute in the config group (please see there). The difference is that it specifies the default if the logical volume is automatically discovered (in contrast to manually adding a watcher for the logical volume)."
	::= { w2kConfigLVolAutoEntry 12 }


w2kConfigLVolAutoTPutMonitor OBJECT-TYPE
	SYNTAX INTEGER {
		do-not-monitor(1),
		warning-only(2),
		critical-only(3),
		both(4)
	}
	ACCESS read-write
	STATUS mandatory
	DESCRIPTION
		"&<caiW2kOs.157>This attribute has the same purpose as the corresponding attribute in the config group (please see there). The difference is that it specifies the default if the logical volume is automatically discovered (in contrast to manually adding a watcher for the logical volume)."
	DEFVAL { 0 }
	::= { w2kConfigLVolAutoEntry 13 }


w2kConfigLVolAutoFragWarn OBJECT-TYPE
	SYNTAX INTEGER
	ACCESS read-write
	STATUS mandatory
	DESCRIPTION
		"&<caiW2kOs.157>This attribute has the same purpose as the corresponding attribute in the config group (please see there). The difference is that it specifies the default if the logical volume is automatically discovered (in contrast to manually adding a watcher for the logical volume)."
	::= { w2kConfigLVolAutoEntry 14 }


w2kConfigLVolAutoFragCrit OBJECT-TYPE
	SYNTAX INTEGER
	ACCESS read-write
	STATUS mandatory
	DESCRIPTION
		"&<caiW2kOs.157>This attribute has the same purpose as the corresponding attribute in the config group (please see there). The difference is that it specifies the default if the logical volume is automatically discovered (in contrast to manually adding a watcher for the logical volume)."
	::= { w2kConfigLVolAutoEntry 15 }


w2kConfigLVolAutoFragMonitor OBJECT-TYPE
	SYNTAX INTEGER {
		do-not-monitor(1),
		warning-only(2),
		critical-only(3),
		both(4)
	}
	ACCESS read-write
	STATUS mandatory
	DESCRIPTION
		"&<caiW2kOs.157>This attribute has the same purpose as the corresponding attribute in the config group (please see there). The difference is that it specifies the default if the logical volume is automatically discovered (in contrast to manually adding a watcher for the logical volume)."
	DEFVAL { 0 }
	::= { w2kConfigLVolAutoEntry 16 }


w2kConfigLVolAutoLossAction OBJECT-TYPE
	SYNTAX INTEGER {
		remove(1),
		up(2),
		down-warning(3),
		down-critical(4)
	}
	ACCESS read-write
	STATUS mandatory
	DESCRIPTION
		"&<caiW2kOs.157>This attribute has the same purpose as the corresponding attribute in the config group (please see there). The difference is that it specifies the default if the logical volume is automatically discovered (in contrast to manually adding a watcher for the logical volume)."
	DEFVAL { 0 }
	::= { w2kConfigLVolAutoEntry 17 }


w2kConfigLVolAutoButton OBJECT-TYPE
	SYNTAX INTEGER {
		none(1),
		remove(2)
	}
	ACCESS read-write
	STATUS mandatory
	DESCRIPTION
		"&<caiW2kOs.172>This attribute is used to remove this auto discovery watcher."
	::= { w2kConfigLVolAutoEntry 18 }




--	------------------------------------------------------------------------
--      Mounts Config Group
--	------------------------------------------------------------------------


w2kConfigMntPollInterval OBJECT-TYPE
	SYNTAX INTEGER
	ACCESS read-write
	STATUS mandatory
	DESCRIPTION
		"&<caiW2kOs.173>The time (in seconds) between the polling of the mount information. Valid values are greater than or equal to 30."
	DEFVAL { 120 }
	::= { w2kConfigMntGroup 1 }


w2kConfigMntPollMethod OBJECT-TYPE
	SYNTAX INTEGER {
		disabled(1),
		poll-interval-only(2),
		poll-interval-and-query(3),
		query-only(4)
	}
	ACCESS read-write
	STATUS mandatory
	DESCRIPTION
		"&<caiW2kOs.174>If set to 'disabled', the agent no more retrieves the mount information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigMntGroup 2 }


w2kConfigMntAutoPollInterval OBJECT-TYPE
	SYNTAX INTEGER
	ACCESS read-write
	STATUS mandatory
	DESCRIPTION
		"&<caiW2kOs.175>The time (in minutes), when a new auto discovery process is started. Valid values are greater than or equal to 30 or set to -1. If set to -1, auto discovery of mounts will no more be made."
	DEFVAL { 60 }
	::= { w2kConfigMntGroup 3 }


w2kConfigMntName OBJECT-TYPE
	SYNTAX DisplayString
	ACCESS read-write
	STATUS mandatory
	DESCRIPTION
		"&<caiW2kOs.176>Name of the watcher to be added/removed, monitoring a mount with this name. If adding an auto discovery watcher, this name can be a wildcarded mount name filtering the mounts to be auto discovered (any backslash in the wildcarded name must be doubled). For each auto discovered mount a watcher will be created. Important: This name is case insensitive."
	::= { w2kConfigMntGroup 4 }


w2kConfigMntDescription OBJECT-TYPE
	SYNTAX DisplayString
	ACCESS read-write
	STATUS mandatory
	DESCRIPTION
		"&<caiW2kOs.136>Any description for this watcher."
	::= { w2kConfigMntGroup 5 }


w2kConfigMntAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigMntGroup 6 }


w2kConfigMntRelToMonitor OBJECT-TYPE
	SYNTAX INTEGER {
		do-not-monitor(1),
		down-warning(2),
		down-critical(3)
	}
	ACCESS read-write
	STATUS mandatory
	DESCRIPTION
		"&<caiW2kOs.179>Flag indicating whether a change of the logical volume, mounted by this mount, should be monitored and if so, the level of alert to raise. Note: A change will not occur if the related logical volume is lossed. In that case the mount itself becomes lossed."
	DEFVAL { 2 }
	::= { w2kConfigMntGroup 7 }


w2kConfigMntLossAction OBJECT-TYPE
	SYNTAX INTEGER {
		remove(1),
		up(2),
		down-warning(3),
		down-critical(4)
	}
	ACCESS read-write
	STATUS mandatory
	DESCRIPTION
		"&<caiW2kOs.180>Flag defining the severity if the loss of the mount is detected or whether to remove this watcher in that case."
	DEFVAL { 4 }
	::= { w2kConfigMntGroup 8 }


w2kConfigMntAutoTableWatcherName OBJECT-TYPE
	SYNTAX DisplayString
	ACCESS read-write
	STATUS mandatory
	DESCRIPTION
		"&<caiW2kOs.151>Name of the watcher to be added in the auto discovery table."
	::= { w2kConfigMntGroup 9 }


w2kConfigMntButton OBJECT-TYPE
	SYNTAX INTEGER {
		none(1),
		add(2),
		remove(3),
		add-auto(4),
		remove-auto(5)
	}
	ACCESS read-write
	STATUS mandatory
	DESCRIPTION
		"&<caiW2kOs.152>This attribute is used to add or remove a watcher with the current value of the watcher name attribute in this group, or to add or remove an auto discovery watcher with the current value of the auto table watcher name attribute in this group."
	::= { w2kConfigMntGroup 10 }


w2kConfigMntAutoTable OBJECT-TYPE
	SYNTAX SEQUENCE OF W2kConfigMntAutoRow
	ACCESS not-accessible
	STATUS mandatory
	DESCRIPTION
		"&<caiW2kOs.183>A table containing all auto discovery watchers for mounts."
	::= { w2kConfigMntGroup 11 }


w2kConfigMntAutoEntry OBJECT-TYPE
	SYNTAX W2kConfigMntAutoRow
	ACCESS not-accessible
	STATUS mandatory
	DESCRIPTION
		"&<caiW2kOs.154>The table entry."
	INDEX { w2kConfigMntAutoWatcherName }
	::= { w2kConfigMntAutoTable 1 }


W2kConfigMntAutoRow ::=
	SEQUENCE {
		w2kConfigMntAutoWatcherName DisplayString,
		w2kConfigMntAutoName DisplayString,
		w2kConfigMntAutoDescription DisplayString,
		w2kConfigMntAutoAggLag INTEGER,
		w2kConfigMntAutoRelToMonitor INTEGER,
		w2kConfigMntAutoLossAction INTEGER,
		w2kConfigMntAutoButton INTEGER
	}


w2kConfigMntAutoWatcherName OBJECT-TYPE
	SYNTAX DisplayString
	ACCESS read-only
	STATUS mandatory
	DESCRIPTION
		"&<caiW2kOs.155>Name of the auto discovery watcher."
	::= { w2kConfigMntAutoEntry 1 }


w2kConfigMntAutoName OBJECT-TYPE
	SYNTAX DisplayString
	ACCESS read-write
	STATUS mandatory
	DESCRIPTION
		"&<caiW2kOs.186>Wildcarded mount name filtering the mounts to be auto discovered (any backslash in the wildcarded name must be doubled). For each auto discovered mount a watcher will be created. Important: This name is case insensitive."
	::= { w2kConfigMntAutoEntry 2 }


w2kConfigMntAutoDescription OBJECT-TYPE
	SYNTAX DisplayString
	ACCESS read-write
	STATUS mandatory
	DESCRIPTION
		"&<caiW2kOs.187>This attribute has the same purpose as the corresponding attribute in the config group (please see there). The difference is that it specifies the default if the mount is automatically discovered (in contrast to manually adding a watcher for the mount)."
	::= { w2kConfigMntAutoEntry 3 }


w2kConfigMntAutoAggLag OBJECT-TYPE
	SYNTAX INTEGER
	ACCESS read-write
	STATUS mandatory
	DESCRIPTION
		"&<caiW2kOs.187>This attribute has the same purpose as the corresponding attribute in the config group (please see there). The difference is that it specifies the default if the mount is automatically discovered (in contrast to manually adding a watcher for the mount)."
	::= { w2kConfigMntAutoEntry 4 }


w2kConfigMntAutoRelToMonitor OBJECT-TYPE
	SYNTAX INTEGER {
		do-not-monitor(1),
		down-warning(2),
		down-critical(3)
	}
	ACCESS read-write
	STATUS mandatory
	DESCRIPTION
		"&<caiW2kOs.187>This attribute has the same purpose as the corresponding attribute in the config group (please see there). The difference is that it specifies the default if the mount is automatically discovered (in contrast to manually adding a watcher for the mount)."
	DEFVAL { 0 }
	::= { w2kConfigMntAutoEntry 5 }


w2kConfigMntAutoLossAction OBJECT-TYPE
	SYNTAX INTEGER {
		remove(1),
		up(2),
		down-warning(3),
		down-critical(4)
	}
	ACCESS read-write
	STATUS mandatory
	DESCRIPTION
		"&<caiW2kOs.187>This attribute has the same purpose as the corresponding attribute in the config group (please see there). The difference is that it specifies the default if the mount is automatically discovered (in contrast to manually adding a watcher for the mount)."
	DEFVAL { 0 }
	::= { w2kConfigMntAutoEntry 6 }


w2kConfigMntAutoButton OBJECT-TYPE
	SYNTAX INTEGER {
		none(1),
		remove(2)
	}
	ACCESS read-write
	STATUS mandatory
	DESCRIPTION
		"&<caiW2kOs.172>This attribute is used to remove this auto discovery watcher."
	::= { w2kConfigMntAutoEntry 9 }




--	------------------------------------------------------------------------
--      Distributed File Systems Config Group
--	------------------------------------------------------------------------


w2kConfigDfsPollInterval OBJECT-TYPE
	SYNTAX INTEGER
	ACCESS read-write
	STATUS mandatory
	DESCRIPTION
		"&<caiW2kOs.192>The time (in seconds) between the polling of the distributed file system link information. Valid values are greater than or equal to 30."
	DEFVAL { 120 }
	::= { w2kConfigDfsGroup 1 }


w2kConfigDfsPollMethod OBJECT-TYPE
	SYNTAX INTEGER {
		disabled(1),
		poll-interval-only(2),
		poll-interval-and-query(3),
		query-only(4)
	}
	ACCESS read-write
	STATUS mandatory
	DESCRIPTION
		"&<caiW2kOs.193>If set to 'disabled', the agent no more retrieves the distributed file system link information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigDfsGroup 2 }


w2kConfigDfsAutoPollInterval OBJECT-TYPE
	SYNTAX INTEGER
	ACCESS read-write
	STATUS mandatory
	DESCRIPTION
		"&<caiW2kOs.194>The time (in minutes), when a new auto discovery process is started. Valid values are greater than or equal to 30 or set to -1. If set to -1, auto discovery of distributed file system links will no more be made."
	DEFVAL { 60 }
	::= { w2kConfigDfsGroup 3 }


w2kConfigDfsName OBJECT-TYPE
	SYNTAX DisplayString
	ACCESS read-write
	STATUS mandatory
	DESCRIPTION
		"&<caiW2kOs.195>Name of the watcher to be added/removed, monitoring a distributed file system link with this name. The name consists of the Dfs root name followed by the Dfs link name. These two names are concatenated by a back-slash. The single Dfs root name (without '\DfsLinkName') can also be used as watcher name, to be able to monitor all Dfs links of a Dfs root. In that case no loss action will be triggered if no Dfs link exists. If adding an auto discovery watcher, this name can be a wildcarded Dfs link name filtering the Dfs links to be auto discovered (any backslash in the wildcarded name must be doubled). For each auto discovered Dfs link a watcher will be created. Important: This name is case insensitive."
	::= { w2kConfigDfsGroup 4 }


w2kConfigDfsDescription OBJECT-TYPE
	SYNTAX DisplayString
	ACCESS read-write
	STATUS mandatory
	DESCRIPTION
		"&<caiW2kOs.136>Any description for this watcher."
	::= { w2kConfigDfsGroup 5 }


w2kConfigDfsAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigDfsGroup 6 }


w2kConfigDfsReplicaWarn OBJECT-TYPE
	SYNTAX INTEGER
	ACCESS read-write
	STATUS mandatory
	DESCRIPTION
		"&<caiW2kOs.198>Warning threshold for the number of unavailable replicas of the distributed file system link. Valid values are greater than 0 and smaller than the critical threshold."
	DEFVAL { 1 }
	::= { w2kConfigDfsGroup 7 }


w2kConfigDfsReplicaCrit OBJECT-TYPE
	SYNTAX INTEGER
	ACCESS read-write
	STATUS mandatory
	DESCRIPTION
		"&<caiW2kOs.199>Critical threshold for the number of unavailable replicas of the distributed file system link. Valid values are greater than 1 and greater than the warning threshold."
	DEFVAL { 2 }
	::= { w2kConfigDfsGroup 8 }


w2kConfigDfsReplicaMonitor OBJECT-TYPE
	SYNTAX INTEGER {
		do-not-monitor(1),
		warning-only(2),
		critical-only(3),
		both(4)
	}
	ACCESS read-write
	STATUS mandatory
	DESCRIPTION
		"&<caiW2kOs.200>Flag indicating whether the unavailable replicas should be monitored and if so, which threshold should be compared with."
	DEFVAL { 4 }
	::= { w2kConfigDfsGroup 9 }


w2kConfigDfsLossAction OBJECT-TYPE
	SYNTAX INTEGER {
		remove(1),
		up(2),
		down-warning(3),
		down-critical(4)
	}
	ACCESS read-write
	STATUS mandatory
	DESCRIPTION
		"&<caiW2kOs.201>Flag defining the severity if the loss of the distributed file system link is detected or whether to remove this watcher in that case."
	DEFVAL { 4 }
	::= { w2kConfigDfsGroup 10 }


w2kConfigDfsAutoTableWatcherName OBJECT-TYPE
	SYNTAX DisplayString
	ACCESS read-write
	STATUS mandatory
	DESCRIPTION
		"&<caiW2kOs.151>Name of the watcher to be added in the auto discovery table."
	::= { w2kConfigDfsGroup 11 }


w2kConfigDfsButton OBJECT-TYPE
	SYNTAX INTEGER {
		none(1),
		add(2),
		remove(3),
		add-auto(4),
		remove-auto(5)
	}
	ACCESS read-write
	STATUS mandatory
	DESCRIPTION
		"&<caiW2kOs.152>This attribute is used to add or remove a watcher with the current value of the watcher name attribute in this group, or to add or remove an auto discovery watcher with the current value of the auto table watcher name attribute in this group."
	::= { w2kConfigDfsGroup 12 }


w2kConfigDfsAutoTable OBJECT-TYPE
	SYNTAX SEQUENCE OF W2kConfigDfsAutoRow
	ACCESS not-accessible
	STATUS mandatory
	DESCRIPTION
		"&<caiW2kOs.204>A table containing all auto discovery watchers for distributed file system links."
	::= { w2kConfigDfsGroup 13 }


w2kConfigDfsAutoEntry OBJECT-TYPE
	SYNTAX W2kConfigDfsAutoRow
	ACCESS not-accessible
	STATUS mandatory
	DESCRIPTION
		"&<caiW2kOs.154>The table entry."
	INDEX { w2kConfigDfsAutoWatcherName }
	::= { w2kConfigDfsAutoTable 1 }


W2kConfigDfsAutoRow ::=
	SEQUENCE {
		w2kConfigDfsAutoWatcherName DisplayString,
		w2kConfigDfsAutoName DisplayString,
		w2kConfigDfsAutoDescription DisplayString,
		w2kConfigDfsAutoAggLag INTEGER,
		w2kConfigDfsAutoReplicaWarn INTEGER,
		w2kConfigDfsAutoReplicaCrit INTEGER,
		w2kConfigDfsAutoReplicaMonitor INTEGER,
		w2kConfigDfsAutoLossAction INTEGER,
		w2kConfigDfsAutoButton INTEGER
	}


w2kConfigDfsAutoWatcherName OBJECT-TYPE
	SYNTAX DisplayString
	ACCESS read-only
	STATUS mandatory
	DESCRIPTION
		"&<caiW2kOs.155>Name of the auto discovery watcher."
	::= { w2kConfigDfsAutoEntry 1 }


w2kConfigDfsAutoName OBJECT-TYPE
	SYNTAX DisplayString
	ACCESS read-write
	STATUS mandatory
	DESCRIPTION
		"&<caiW2kOs.207>Wildcarded distributed file system link name filtering the Dfs links to be auto discovered (any backslash in the wildcarded name must be doubled). For each auto discovered Dfs link a watcher will be created. Important: This name is case insensitive."
	::= { w2kConfigDfsAutoEntry 2 }


w2kConfigDfsAutoDescription OBJECT-TYPE
	SYNTAX DisplayString
	ACCESS read-write
	STATUS mandatory
	DESCRIPTION
		"&<caiW2kOs.208>This attribute has the same purpose as the corresponding attribute in the config group (please see there). The difference is that it specifies the default if the distributed file system link is automatically discovered (in contrast to manually adding a watcher for the distributed file system link)."
	::= { w2kConfigDfsAutoEntry 3 }


w2kConfigDfsAutoAggLag OBJECT-TYPE
	SYNTAX INTEGER
	ACCESS read-write
	STATUS mandatory
	DESCRIPTION
		"&<caiW2kOs.208>This attribute has the same purpose as the corresponding attribute in the config group (please see there). The difference is that it specifies the default if the distributed file system link is automatically discovered (in contrast to manually adding a watcher for the distributed file system link)."
	::= { w2kConfigDfsAutoEntry 4 }


w2kConfigDfsAutoReplicaWarn OBJECT-TYPE
	SYNTAX INTEGER
	ACCESS read-write
	STATUS mandatory
	DESCRIPTION
		"&<caiW2kOs.208>This attribute has the same purpose as the corresponding attribute in the config group (please see there). The difference is that it specifies the default if the distributed file system link is automatically discovered (in contrast to manually adding a watcher for the distributed file system link)."
	::= { w2kConfigDfsAutoEntry 5 }


w2kConfigDfsAutoReplicaCrit OBJECT-TYPE
	SYNTAX INTEGER
	ACCESS read-write
	STATUS mandatory
	DESCRIPTION
		"&<caiW2kOs.208>This attribute has the same purpose as the corresponding attribute in the config group (please see there). The difference is that it specifies the default if the distributed file system link is automatically discovered (in contrast to manually adding a watcher for the distributed file system link)."
	::= { w2kConfigDfsAutoEntry 6 }


w2kConfigDfsAutoReplicaMonitor OBJECT-TYPE
	SYNTAX INTEGER {
		do-not-monitor(1),
		warning-only(2),
		critical-only(3),
		both(4)
	}
	ACCESS read-write
	STATUS mandatory
	DESCRIPTION
		"&<caiW2kOs.208>This attribute has the same purpose as the corresponding attribute in the config group (please see there). The difference is that it specifies the default if the distributed file system link is automatically discovered (in contrast to manually adding a watcher for the distributed file system link)."
	DEFVAL { 0 }
	::= { w2kConfigDfsAutoEntry 7 }


w2kConfigDfsAutoLossAction OBJECT-TYPE
	SYNTAX INTEGER {
		remove(1),
		up(2),
		down-warning(3),
		down-critical(4)
	}
	ACCESS read-write
	STATUS mandatory
	DESCRIPTION
		"&<caiW2kOs.208>This attribute has the same purpose as the corresponding attribute in the config group (please see there). The difference is that it specifies the default if the distributed file system link is automatically discovered (in contrast to manually adding a watcher for the distributed file system link)."
	DEFVAL { 0 }
	::= { w2kConfigDfsAutoEntry 8 }


w2kConfigDfsAutoButton OBJECT-TYPE
	SYNTAX INTEGER {
		none(1),
		remove(2)
	}
	ACCESS read-write
	STATUS mandatory
	DESCRIPTION
		"&<caiW2kOs.172>This attribute is used to remove this auto discovery watcher."
	::= { w2kConfigDfsAutoEntry 9 }




--	------------------------------------------------------------------------
--      Quotas Config Group
--	------------------------------------------------------------------------


w2kConfigQuotPollInterval OBJECT-TYPE
	SYNTAX INTEGER
	ACCESS read-write
	STATUS mandatory
	DESCRIPTION
		"&<caiW2kOs.215>The time (in seconds) between the polling of the quota information. Valid values are greater than or equal to 30."
	DEFVAL { 120 }
	::= { w2kConfigQuotGroup 1 }


w2kConfigQuotPollMethod OBJECT-TYPE
	SYNTAX INTEGER {
		disabled(1),
		poll-interval-only(2),
		poll-interval-and-query(3),
		query-only(4)
	}
	ACCESS read-write
	STATUS mandatory
	DESCRIPTION
		"&<caiW2kOs.216>If set to 'disabled', the agent no more retrieves the quota information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigQuotGroup 2 }


w2kConfigQuotLVolName OBJECT-TYPE
	SYNTAX DisplayString
	ACCESS read-write
	STATUS mandatory
	DESCRIPTION
		"&<caiW2kOs.217>Logical volume name of the watcher to be added/removed, monitoring a quota with this logical volume name. The name specifies the logical volume on which this quota exists. Important: This name is case insensitive."
	::= { w2kConfigQuotGroup 3 }


w2kConfigQuotUserName OBJECT-TYPE
	SYNTAX DisplayString
	ACCESS read-write
	STATUS mandatory
	DESCRIPTION
		"&<caiW2kOs.218>User name of the watcher to be added/removed, monitoring a quota with this user name. The name specifies the user for whom this quota exists and is in the form 'domainName\\userName' or 'userName@domainName'. Important: This name is case insensitive."
	::= { w2kConfigQuotGroup 4 }


w2kConfigQuotDescription OBJECT-TYPE
	SYNTAX DisplayString
	ACCESS read-write
	STATUS mandatory
	DESCRIPTION
		"&<caiW2kOs.136>Any description for this watcher."
	::= { w2kConfigQuotGroup 5 }


w2kConfigQuotAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigQuotGroup 6 }


w2kConfigQuotExist OBJECT-TYPE
	SYNTAX INTEGER {
		should-exist(1),
		should-not-exist(2)
	}
	ACCESS read-write
	STATUS mandatory
	DESCRIPTION
		"&<caiW2kOs.221>Flag indicating whether to raise an alert if a quota is existent or if it is not-existent."
	DEFVAL { 1 }
	::= { w2kConfigQuotGroup 7 }


w2kConfigQuotExistMonitor OBJECT-TYPE
	SYNTAX INTEGER {
		do-not-monitor(1),
		down-warning(2),
		down-critical(3)
	}
	ACCESS read-write
	STATUS mandatory
	DESCRIPTION
		"&<caiW2kOs.222>Flag indicating whether the existence of the quota should be monitored and if so, the level of alert to raise."
	DEFVAL { 3 }
	::= { w2kConfigQuotGroup 8 }


w2kConfigQuotSizeWarn OBJECT-TYPE
	SYNTAX INTEGER
	ACCESS read-write
	STATUS mandatory
	DESCRIPTION
		"&<caiW2kOs.223>Warning threshold for the used quota size in kilobytes. Valid values are greater than 0 and smaller than the critical threshold."
	DEFVAL { 1000 }
	::= { w2kConfigQuotGroup 9 }


w2kConfigQuotSizeCrit OBJECT-TYPE
	SYNTAX INTEGER
	ACCESS read-write
	STATUS mandatory
	DESCRIPTION
		"&<caiW2kOs.224>Critical threshold for the used quota size in kilobytes. Valid values are greater than 1 and greater than the warning threshold."
	DEFVAL { 5000 }
	::= { w2kConfigQuotGroup 10 }


w2kConfigQuotSizeMonitor OBJECT-TYPE
	SYNTAX INTEGER {
		do-not-monitor(1),
		warning-only(2),
		critical-only(3),
		both(4)
	}
	ACCESS read-write
	STATUS mandatory
	DESCRIPTION
		"&<caiW2kOs.225>Flag indicating whether the used quota size should be monitored and if so, which threshold should be compared with."
	DEFVAL { 4 }
	::= { w2kConfigQuotGroup 11 }


w2kConfigQuotButton OBJECT-TYPE
	SYNTAX INTEGER {
		none(1),
		add(2),
		remove(3)
	}
	ACCESS read-write
	STATUS mandatory
	DESCRIPTION
		"&<caiW2kOs.226>This attribute is used to add or remove a watcher with the current value of the watcher name attribute in this group."
	::= { w2kConfigQuotGroup 12 }




--	------------------------------------------------------------------------
--      Directories Config Group
--	------------------------------------------------------------------------


w2kConfigDirPollInterval OBJECT-TYPE
	SYNTAX INTEGER
	ACCESS read-write
	STATUS mandatory
	DESCRIPTION
		"&<caiW2kOs.227>The time (in seconds) between the polling of the directory information. Valid values are greater than or equal to 30."
	DEFVAL { 120 }
	::= { w2kConfigDirGroup 1 }


w2kConfigDirPollMethod OBJECT-TYPE
	SYNTAX INTEGER {
		disabled(1),
		poll-interval-only(2),
		poll-interval-and-query(3),
		query-only(4)
	}
	ACCESS read-write
	STATUS mandatory
	DESCRIPTION
		"&<caiW2kOs.228>If set to 'disabled', the agent no more retrieves the directory information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigDirGroup 2 }


w2kConfigDirName OBJECT-TYPE
	SYNTAX DisplayString
	ACCESS read-write
	STATUS mandatory
	DESCRIPTION
		"&<caiW2kOs.229>Name of the watcher to be added/removed, monitoring a directory with this name. Important: This name is case insensitive."
	::= { w2kConfigDirGroup 3 }


w2kConfigDirDescription OBJECT-TYPE
	SYNTAX DisplayString
	ACCESS read-write
	STATUS mandatory
	DESCRIPTION
		"&<caiW2kOs.136>Any description for this watcher."
	::= { w2kConfigDirGroup 4 }


w2kConfigDirAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigDirGroup 5 }


w2kConfigDirExist OBJECT-TYPE
	SYNTAX INTEGER {
		should-exist(1),
		should-not-exist(2)
	}
	ACCESS read-write
	STATUS mandatory
	DESCRIPTION
		"&<caiW2kOs.232>Flag indicating whether to raise an alert if a directory is existent or if it is not-existent."
	DEFVAL { 1 }
	::= { w2kConfigDirGroup 6 }


w2kConfigDirExistMonitor OBJECT-TYPE
	SYNTAX INTEGER {
		do-not-monitor(1),
		down-warning(2),
		down-critical(3)
	}
	ACCESS read-write
	STATUS mandatory
	DESCRIPTION
		"&<caiW2kOs.233>Flag indicating whether the existence of the directory should be monitored and if so, the level of alert to raise."
	DEFVAL { 3 }
	::= { w2kConfigDirGroup 7 }


w2kConfigDirTimeMonitor OBJECT-TYPE
	SYNTAX INTEGER {
		do-not-monitor(1),
		down-warning(2),
		down-critical(3)
	}
	ACCESS read-write
	STATUS mandatory
	DESCRIPTION
		"&<caiW2kOs.234>Flag indicating whether the latest timestamp (of all files and all subfolders, including the given folder) should be monitored and if so, the level of alert to raise."
	DEFVAL { 2 }
	::= { w2kConfigDirGroup 8 }


w2kConfigDirSizeWarn OBJECT-TYPE
	SYNTAX DisplayString
	ACCESS read-write
	STATUS mandatory
	DESCRIPTION
		"&<caiW2kOs.235>Warning threshold for the total directory size (all files in the given folder and in all subfolders), either in kilobytes or as a percentage value of the original size (by appending a '%'). The original size is the size when this watcher was created. Valid values are greater than 0 and smaller than the critical threshold."
	DEFVAL { "150%" }
	::= { w2kConfigDirGroup 9 }


w2kConfigDirSizeCrit OBJECT-TYPE
	SYNTAX DisplayString
	ACCESS read-write
	STATUS mandatory
	DESCRIPTION
		"&<caiW2kOs.236>Critical threshold for the total directory size (all files in the given folder and in all subfolders), either in kilobytes or as a percentage value of the original size (by appending a '%'). The original size is the size when this watcher was created. Valid values are greater than 1 and greater than the warning threshold."
	DEFVAL { "200%" }
	::= { w2kConfigDirGroup 10 }


w2kConfigDirSizeMonitor OBJECT-TYPE
	SYNTAX INTEGER {
		do-not-monitor(1),
		warning-only(2),
		critical-only(3),
		both(4)
	}
	ACCESS read-write
	STATUS mandatory
	DESCRIPTION
		"&<caiW2kOs.237>Flag indicating whether the total directory size should be monitored and if so, which threshold should be compared with."
	DEFVAL { 4 }
	::= { w2kConfigDirGroup 11 }


w2kConfigDirSizeDWarn OBJECT-TYPE
	SYNTAX DisplayString
	ACCESS read-write
	STATUS mandatory
	DESCRIPTION
		"&<caiW2kOs.238>Warning threshold, either for the growth (by appending a '+') or for the shrinkage (by appending a '-') or for the absolute delta in total directory size monitored in one poll interval. Growth, shrinkage and absolute delta can be given in kilobytes or as a percentage value of the total directory size (by appending a '%'). Valid values are greater than 0 and smaller than the critical threshold."
	DEFVAL { "1%" }
	::= { w2kConfigDirGroup 12 }


w2kConfigDirSizeDCrit OBJECT-TYPE
	SYNTAX DisplayString
	ACCESS read-write
	STATUS mandatory
	DESCRIPTION
		"&<caiW2kOs.239>Critical threshold, either for the growth (by appending a '+') or for the shrinkage (by appending a '-') or for the absolute delta in total directory size monitored in one poll interval. Growth, shrinkage and absolute delta can be given in kilobytes or as a percentage value of the total directory size (by appending a '%'). Valid values are greater than 1 and greater than the warning threshold."
	DEFVAL { "2%" }
	::= { w2kConfigDirGroup 13 }


w2kConfigDirSizeDMonitor OBJECT-TYPE
	SYNTAX INTEGER {
		do-not-monitor(1),
		warning-only(2),
		critical-only(3),
		both(4)
	}
	ACCESS read-write
	STATUS mandatory
	DESCRIPTION
		"&<caiW2kOs.240>Flag indicating whether the delta in total directory size should be monitored and if so, which threshold should be compared with."
	DEFVAL { 4 }
	::= { w2kConfigDirGroup 14 }


w2kConfigDirEntryWarn OBJECT-TYPE
	SYNTAX INTEGER
	ACCESS read-write
	STATUS mandatory
	DESCRIPTION
		"&<caiW2kOs.241>Warning threshold for the number of entries (sum of files and folders in the given folder and in all subfolders). Valid values are greater than 0 and smaller than the critical threshold."
	DEFVAL { 5 }
	::= { w2kConfigDirGroup 15 }


w2kConfigDirEntryCrit OBJECT-TYPE
	SYNTAX INTEGER
	ACCESS read-write
	STATUS mandatory
	DESCRIPTION
		"&<caiW2kOs.242>Critical threshold for the number of entries (sum of files and folders in the given folder and in all subfolders). Valid values are greater than 1 and greater than the warning threshold."
	DEFVAL { 10 }
	::= { w2kConfigDirGroup 16 }


w2kConfigDirEntryMonitor OBJECT-TYPE
	SYNTAX INTEGER {
		do-not-monitor(1),
		warning-only(2),
		critical-only(3),
		both(4)
	}
	ACCESS read-write
	STATUS mandatory
	DESCRIPTION
		"&<caiW2kOs.243>Flag indicating whether the number of entries should be monitored and if so, which threshold should be compared with."
	DEFVAL { 4 }
	::= { w2kConfigDirGroup 17 }


w2kConfigDirButton OBJECT-TYPE
	SYNTAX INTEGER {
		none(1),
		add(2),
		remove(3)
	}
	ACCESS read-write
	STATUS mandatory
	DESCRIPTION
		"&<caiW2kOs.226>This attribute is used to add or remove a watcher with the current value of the watcher name attribute in this group."
	::= { w2kConfigDirGroup 18 }




--	------------------------------------------------------------------------
--      Files Config Group
--	------------------------------------------------------------------------


w2kConfigFilePollInterval OBJECT-TYPE
	SYNTAX INTEGER
	ACCESS read-write
	STATUS mandatory
	DESCRIPTION
		"&<caiW2kOs.245>The time (in seconds) between the polling of the file information. Valid values are greater than or equal to 30."
	DEFVAL { 120 }
	::= { w2kConfigFileGroup 1 }


w2kConfigFilePollMethod OBJECT-TYPE
	SYNTAX INTEGER {
		disabled(1),
		poll-interval-only(2),
		poll-interval-and-query(3),
		query-only(4)
	}
	ACCESS read-write
	STATUS mandatory
	DESCRIPTION
		"&<caiW2kOs.246>If set to 'disabled', the agent no more retrieves the file information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigFileGroup 2 }


w2kConfigFileName OBJECT-TYPE
	SYNTAX DisplayString
	ACCESS read-write
	STATUS mandatory
	DESCRIPTION
		"&<caiW2kOs.247>Name of the watcher to be added/removed, monitoring a file with this name. Important: This name is case insensitive."
	::= { w2kConfigFileGroup 3 }


w2kConfigFileDescription OBJECT-TYPE
	SYNTAX DisplayString
	ACCESS read-write
	STATUS mandatory
	DESCRIPTION
		"&<caiW2kOs.136>Any description for this watcher."
	::= { w2kConfigFileGroup 4 }


w2kConfigFileAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigFileGroup 5 }


w2kConfigFileExist OBJECT-TYPE
	SYNTAX INTEGER {
		should-exist(1),
		should-not-exist(2)
	}
	ACCESS read-write
	STATUS mandatory
	DESCRIPTION
		"&<caiW2kOs.250>Flag indicating whether to raise an alert if a file is existent or if it is not-existent."
	DEFVAL { 1 }
	::= { w2kConfigFileGroup 6 }


w2kConfigFileExistMonitor OBJECT-TYPE
	SYNTAX INTEGER {
		do-not-monitor(1),
		down-warning(2),
		down-critical(3)
	}
	ACCESS read-write
	STATUS mandatory
	DESCRIPTION
		"&<caiW2kOs.251>Flag indicating whether the existence of the file should be monitored and if so, the level of alert to raise."
	DEFVAL { 3 }
	::= { w2kConfigFileGroup 7 }


w2kConfigFileTimeMonitor OBJECT-TYPE
	SYNTAX INTEGER {
		do-not-monitor(1),
		down-warning(2),
		down-critical(3)
	}
	ACCESS read-write
	STATUS mandatory
	DESCRIPTION
		"&<caiW2kOs.252>Flag indicating whether the timestamp of the file should be monitored and if so, the level of alert to raise."
	DEFVAL { 2 }
	::= { w2kConfigFileGroup 8 }


w2kConfigFileSizeWarn OBJECT-TYPE
	SYNTAX DisplayString
	ACCESS read-write
	STATUS mandatory
	DESCRIPTION
		"&<caiW2kOs.253>Warning threshold for the file size, either in kilobytes or as a percentage value of the original size (by appending a '%'). The original size is the size when this watcher was created. Valid values are greater than 0 and smaller than the critical threshold."
	DEFVAL { "150%" }
	::= { w2kConfigFileGroup 9 }


w2kConfigFileSizeCrit OBJECT-TYPE
	SYNTAX DisplayString
	ACCESS read-write
	STATUS mandatory
	DESCRIPTION
		"&<caiW2kOs.254>Critical threshold for the file size, either in kilobytes or as a percentage value of the original size (by appending a '%'). The original size is the size when this watcher was created. Valid values are greater than 1 and greater than the warning threshold."
	DEFVAL { "200%" }
	::= { w2kConfigFileGroup 10 }


w2kConfigFileSizeMonitor OBJECT-TYPE
	SYNTAX INTEGER {
		do-not-monitor(1),
		warning-only(2),
		critical-only(3),
		both(4)
	}
	ACCESS read-write
	STATUS mandatory
	DESCRIPTION
		"&<caiW2kOs.255>Flag indicating whether the file size should be monitored and if so, which threshold should be compared with."
	DEFVAL { 4 }
	::= { w2kConfigFileGroup 11 }


w2kConfigFileSizeDWarn OBJECT-TYPE
	SYNTAX DisplayString
	ACCESS read-write
	STATUS mandatory
	DESCRIPTION
		"&<caiW2kOs.256>Warning threshold, either for the growth (by appending a '+') or for the shrinkage (by appending a '-') or for the absolute delta in file size monitored in one poll interval. Growth, shrinkage and absolute delta can be given in kilobytes or as a percentage value of the file size (by appending a '%'). Valid values are greater than 0 and smaller than the critical threshold."
	DEFVAL { "1%" }
	::= { w2kConfigFileGroup 12 }


w2kConfigFileSizeDCrit OBJECT-TYPE
	SYNTAX DisplayString
	ACCESS read-write
	STATUS mandatory
	DESCRIPTION
		"&<caiW2kOs.257>Critical threshold, either for the growth (by appending a '+') or for the shrinkage (by appending a '-') or for the absolute delta in file size monitored in one poll interval. Growth, shrinkage and absolute delta can be given in kilobytes or as a percentage value of the file size (by appending a '%'). Valid values are greater than 1 and greater than the warning threshold."
	DEFVAL { "2%" }
	::= { w2kConfigFileGroup 13 }


w2kConfigFileSizeDMonitor OBJECT-TYPE
	SYNTAX INTEGER {
		do-not-monitor(1),
		warning-only(2),
		critical-only(3),
		both(4)
	}
	ACCESS read-write
	STATUS mandatory
	DESCRIPTION
		"&<caiW2kOs.258>Flag indicating whether the delta in file size should be monitored and if so, which threshold should be compared with."
	DEFVAL { 4 }
	::= { w2kConfigFileGroup 14 }


w2kConfigFileButton OBJECT-TYPE
	SYNTAX INTEGER {
		none(1),
		add(2),
		remove(3)
	}
	ACCESS read-write
	STATUS mandatory
	DESCRIPTION
		"&<caiW2kOs.226>This attribute is used to add or remove a watcher with the current value of the watcher name attribute in this group."
	::= { w2kConfigFileGroup 15 }




--	------------------------------------------------------------------------
--      Processes Config Group
--	------------------------------------------------------------------------


w2kConfigProcPollInterval OBJECT-TYPE
	SYNTAX INTEGER
	ACCESS read-write
	STATUS mandatory
	DESCRIPTION
		"&<caiW2kOs.260>The time (in seconds) between the polling of the process information. Valid values are greater than or equal to 30."
	DEFVAL { 120 }
	::= { w2kConfigProcGroup 1 }


w2kConfigProcPollMethod OBJECT-TYPE
	SYNTAX INTEGER {
		disabled(1),
		poll-interval-only(2),
		poll-interval-and-query(3),
		query-only(4)
	}
	ACCESS read-write
	STATUS mandatory
	DESCRIPTION
		"&<caiW2kOs.261>If set to 'disabled', the agent no more retrieves the process information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigProcGroup 2 }


w2kConfigProcProcName OBJECT-TYPE
	SYNTAX DisplayString
	ACCESS read-write
	STATUS mandatory
	DESCRIPTION
		"&<caiW2kOs.262>Process name of the watcher to be added/removed, monitoring a process with this process name. An asterisk '*' can be used as process name or can be prepended/appended to it, in order to widen the scope of processes this watcher monitors. Important: This name is case insensitive."
	::= { w2kConfigProcGroup 3 }


w2kConfigProcPathName OBJECT-TYPE
	SYNTAX DisplayString
	ACCESS read-write
	STATUS mandatory
	DESCRIPTION
		"&<caiW2kOs.263>Path name of the watcher to be added/removed, monitoring a process with this path name. An asterisk '*' can be used as path name or can be prepended/appended to it, in order to widen the scope of processes this watcher monitors. Important: This name is case insensitive."
	::= { w2kConfigProcGroup 4 }


w2kConfigProcUserName OBJECT-TYPE
	SYNTAX DisplayString
	ACCESS read-write
	STATUS mandatory
	DESCRIPTION
		"&<caiW2kOs.264>User name of the watcher to be added/removed, monitoring a process started by this user. An asterisk '*' can be used as user name or can be prepended/appended to it, in order to widen the scope of processes this watcher monitors. Important: This name is case insensitive."
	::= { w2kConfigProcGroup 5 }


w2kConfigProcDescription OBJECT-TYPE
	SYNTAX DisplayString
	ACCESS read-write
	STATUS mandatory
	DESCRIPTION
		"&<caiW2kOs.136>Any description for this watcher."
	::= { w2kConfigProcGroup 6 }


w2kConfigProcAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigProcGroup 7 }


w2kConfigProcInstMin OBJECT-TYPE
	SYNTAX INTEGER
	ACCESS read-write
	STATUS mandatory
	DESCRIPTION
		"&<caiW2kOs.267>Minimum threshold for the number of process instances. Valid values are greater than or equal to -1 and smaller than or equal to the maximum threshold. Setting to -1 disables the monitoring of the minimum."
	DEFVAL { 1 }
	::= { w2kConfigProcGroup 8 }


w2kConfigProcInstMax OBJECT-TYPE
	SYNTAX INTEGER
	ACCESS read-write
	STATUS mandatory
	DESCRIPTION
		"&<caiW2kOs.268>Maximum threshold for the number of process instances. Valid values are greater than or equal to -1 and greater than or equal to the minimum threshold. Setting to -1 disables the monitoring of the maximum."
	DEFVAL { 1 }
	::= { w2kConfigProcGroup 9 }


w2kConfigProcInstMonitor OBJECT-TYPE
	SYNTAX INTEGER {
		do-not-monitor(1),
		down-warning(2),
		down-critical(3)
	}
	ACCESS read-write
	STATUS mandatory
	DESCRIPTION
		"&<caiW2kOs.269>Flag indicating whether the number of process instances should be monitored and if so, the level of alert to raise."
	DEFVAL { 3 }
	::= { w2kConfigProcGroup 10 }


w2kConfigProcChildMin OBJECT-TYPE
	SYNTAX INTEGER
	ACCESS read-write
	STATUS mandatory
	DESCRIPTION
		"&<caiW2kOs.270>Minimum threshold for the number of childprocesses of the process. If there is more than one process instance, the minimum of all instances is compared with this value. Valid values are greater than or equal to -1 and smaller than or equal to the maximum threshold. Setting to -1 disables the monitoring of the minimum."
	DEFVAL { 0 }
	::= { w2kConfigProcGroup 11 }


w2kConfigProcChildMax OBJECT-TYPE
	SYNTAX INTEGER
	ACCESS read-write
	STATUS mandatory
	DESCRIPTION
		"&<caiW2kOs.271>Maximum threshold for the number of childprocesses of the process. If there is more than one process instance, the maximum of all instances is compared with this value. Valid values are greater than or equal to -1 and greater than or equal to the minimum threshold. Setting to -1 disables the monitoring of the maximum."
	DEFVAL { 1 }
	::= { w2kConfigProcGroup 12 }


w2kConfigProcChildMonitor OBJECT-TYPE
	SYNTAX INTEGER {
		do-not-monitor(1),
		down-warning(2),
		down-critical(3)
	}
	ACCESS read-write
	STATUS mandatory
	DESCRIPTION
		"&<caiW2kOs.272>Flag indicating whether the number of childprocesses of the process should be monitored and if so, the level of alert to raise. Note: This metric decreases agent performance much more than any other metric. For this reason the default is 'do-not-monitor'."
	DEFVAL { 1 }
	::= { w2kConfigProcGroup 13 }


w2kConfigProcThreadMin OBJECT-TYPE
	SYNTAX INTEGER
	ACCESS read-write
	STATUS mandatory
	DESCRIPTION
		"&<caiW2kOs.273>Minimum threshold for the number of threads of the process. If there is more than one process instance, the minimum of all instances is compared with this value. Valid values are greater than or equal to -1 and smaller than or equal to the maximum threshold. Setting to -1 disables the monitoring of the minimum."
	DEFVAL { 1 }
	::= { w2kConfigProcGroup 14 }


w2kConfigProcThreadMax OBJECT-TYPE
	SYNTAX INTEGER
	ACCESS read-write
	STATUS mandatory
	DESCRIPTION
		"&<caiW2kOs.274>Maximum threshold for the number of threads of the process. If there is more than one process instance, the maximum of all instances is compared with this value. Valid values are greater than or equal to -1 and greater than or equal to the minimum threshold. Setting to -1 disables the monitoring of the maximum."
	DEFVAL { 10 }
	::= { w2kConfigProcGroup 15 }


w2kConfigProcThreadMonitor OBJECT-TYPE
	SYNTAX INTEGER {
		do-not-monitor(1),
		down-warning(2),
		down-critical(3)
	}
	ACCESS read-write
	STATUS mandatory
	DESCRIPTION
		"&<caiW2kOs.275>Flag indicating whether the number of threads of the process should be monitored and if so, the level of alert to raise."
	DEFVAL { 2 }
	::= { w2kConfigProcGroup 16 }


w2kConfigProcMemoryWarn OBJECT-TYPE
	SYNTAX INTEGER
	ACCESS read-write
	STATUS mandatory
	DESCRIPTION
		"&<caiW2kOs.276>Warning threshold for the memory usage of the process (in kilobytes). If there is more than one process instance, the maximum of all instances is compared with this value. Valid values are greater than 0 and smaller than the critical threshold."
	DEFVAL { 20000 }
	::= { w2kConfigProcGroup 17 }


w2kConfigProcMemoryCrit OBJECT-TYPE
	SYNTAX INTEGER
	ACCESS read-write
	STATUS mandatory
	DESCRIPTION
		"&<caiW2kOs.277>Critical threshold for the memory usage of the process (in kilobytes). If there is more than one process instance, the maximum of all instances is compared with this value. Valid values are greater than 1 and greater than the warning threshold."
	DEFVAL { 40000 }
	::= { w2kConfigProcGroup 18 }


w2kConfigProcMemoryMonitor OBJECT-TYPE
	SYNTAX INTEGER {
		do-not-monitor(1),
		warning-only(2),
		critical-only(3),
		both(4)
	}
	ACCESS read-write
	STATUS mandatory
	DESCRIPTION
		"&<caiW2kOs.278>Flag indicating whether the memory usage of the process should be monitored and if so, which threshold should be compared with."
	DEFVAL { 4 }
	::= { w2kConfigProcGroup 19 }


w2kConfigProcCpuWarn OBJECT-TYPE
	SYNTAX INTEGER
	ACCESS read-write
	STATUS mandatory
	DESCRIPTION
		"&<caiW2kOs.279>Warning threshold for the CPU usage of the process (as percentage value of 100). If there is more than one process instance, the maximum of all instances is compared with this value. Valid values are 1 to 99 and smaller than the critical threshold."
	DEFVAL { 10 }
	::= { w2kConfigProcGroup 20 }


w2kConfigProcCpuCrit OBJECT-TYPE
	SYNTAX INTEGER
	ACCESS read-write
	STATUS mandatory
	DESCRIPTION
		"&<caiW2kOs.280>Critical threshold for the CPU usage of the process (as percentage value of 100). If there is more than one process instance, the maximum of all instances is compared with this value. Valid values are 2 to 100 and greater than the warning threshold."
	DEFVAL { 20 }
	::= { w2kConfigProcGroup 21 }


w2kConfigProcCpuMonitor OBJECT-TYPE
	SYNTAX INTEGER {
		do-not-monitor(1),
		warning-only(2),
		critical-only(3),
		both(4)
	}
	ACCESS read-write
	STATUS mandatory
	DESCRIPTION
		"&<caiW2kOs.281>Flag indicating whether the CPU usage of the process should be monitored and if so, which threshold should be compared with."
	DEFVAL { 4 }
	::= { w2kConfigProcGroup 22 }


w2kConfigProcButton OBJECT-TYPE
	SYNTAX INTEGER {
		none(1),
		add(2),
		remove(3)
	}
	ACCESS read-write
	STATUS mandatory
	DESCRIPTION
		"&<caiW2kOs.226>This attribute is used to add or remove a watcher with the current value of the watcher name attribute in this group."
	::= { w2kConfigProcGroup 23 }




--	------------------------------------------------------------------------
--      Services Config Group
--	------------------------------------------------------------------------


w2kConfigSrvcPollInterval OBJECT-TYPE
	SYNTAX INTEGER
	ACCESS read-write
	STATUS mandatory
	DESCRIPTION
		"&<caiW2kOs.283>The time (in seconds) between the polling of the service information. Valid values are greater than or equal to 30."
	DEFVAL { 120 }
	::= { w2kConfigSrvcGroup 1 }


w2kConfigSrvcPollMethod OBJECT-TYPE
	SYNTAX INTEGER {
		disabled(1),
		poll-interval-only(2),
		poll-interval-and-query(3),
		query-only(4)
	}
	ACCESS read-write
	STATUS mandatory
	DESCRIPTION
		"&<caiW2kOs.284>If set to 'disabled', the agent no more retrieves the service information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigSrvcGroup 2 }


w2kConfigSrvcAutoPollInterval OBJECT-TYPE
	SYNTAX INTEGER
	ACCESS read-write
	STATUS mandatory
	DESCRIPTION
		"&<caiW2kOs.285>The time (in minutes), when a new auto discovery process is started. Valid values are greater than or equal to 30 or set to -1. If set to -1, auto discovery of services will no more be made."
	DEFVAL { 60 }
	::= { w2kConfigSrvcGroup 3 }


w2kConfigSrvcName OBJECT-TYPE
	SYNTAX DisplayString
	ACCESS read-write
	STATUS mandatory
	DESCRIPTION
		"&<caiW2kOs.286>Name of the watcher to be added/removed, monitoring a service with this name. If adding an auto discovery watcher, this name can be a wildcarded service name filtering the services to be auto discovered (any backslash in the wildcarded name must be doubled). For each auto discovered service a watcher will be created. Important: This name is case insensitive."
	::= { w2kConfigSrvcGroup 4 }


w2kConfigSrvcDescription OBJECT-TYPE
	SYNTAX DisplayString
	ACCESS read-write
	STATUS mandatory
	DESCRIPTION
		"&<caiW2kOs.136>Any description for this watcher."
	::= { w2kConfigSrvcGroup 5 }


w2kConfigSrvcAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigSrvcGroup 6 }


w2kConfigSrvcExist OBJECT-TYPE
	SYNTAX INTEGER {
		should-exist(1),
		should-not-exist(2)
	}
	ACCESS read-write
	STATUS mandatory
	DESCRIPTION
		"&<caiW2kOs.289>Flag indicating whether to raise an alert if a service is existent or if it is not-existent."
	DEFVAL { 1 }
	::= { w2kConfigSrvcGroup 7 }


w2kConfigSrvcExistMonitor OBJECT-TYPE
	SYNTAX INTEGER {
		do-not-monitor(1),
		down-warning(2),
		down-critical(3)
	}
	ACCESS read-write
	STATUS mandatory
	DESCRIPTION
		"&<caiW2kOs.290>Flag indicating whether the existence of the service should be monitored and if so, the level of alert to raise."
	DEFVAL { 3 }
	::= { w2kConfigSrvcGroup 8 }


w2kConfigSrvcActive OBJECT-TYPE
	SYNTAX INTEGER {
		should-be-active(1),
		should-not-be-active(2)
	}
	ACCESS read-write
	STATUS mandatory
	DESCRIPTION
		"&<caiW2kOs.291>Flag indicating whether to raise an alert if an existent service is active or if it is inactive."
	DEFVAL { 1 }
	::= { w2kConfigSrvcGroup 9 }


w2kConfigSrvcActiveMonitor OBJECT-TYPE
	SYNTAX INTEGER {
		do-not-monitor(1),
		down-warning(2),
		down-critical(3)
	}
	ACCESS read-write
	STATUS mandatory
	DESCRIPTION
		"&<caiW2kOs.292>Flag indicating whether the activity of the service should be monitored and if so, the level of alert to raise."
	DEFVAL { 2 }
	::= { w2kConfigSrvcGroup 10 }


w2kConfigSrvcAutoTableWatcherName OBJECT-TYPE
	SYNTAX DisplayString
	ACCESS read-write
	STATUS mandatory
	DESCRIPTION
		"&<caiW2kOs.151>Name of the watcher to be added in the auto discovery table."
	::= { w2kConfigSrvcGroup 11 }


w2kConfigSrvcButton OBJECT-TYPE
	SYNTAX INTEGER {
		none(1),
		add(2),
		remove(3),
		add-auto(4),
		remove-auto(5)
	}
	ACCESS read-write
	STATUS mandatory
	DESCRIPTION
		"&<caiW2kOs.152>This attribute is used to add or remove a watcher with the current value of the watcher name attribute in this group, or to add or remove an auto discovery watcher with the current value of the auto table watcher name attribute in this group."
	::= { w2kConfigSrvcGroup 12 }


w2kConfigSrvcAutoTable OBJECT-TYPE
	SYNTAX SEQUENCE OF W2kConfigSrvcAutoRow
	ACCESS not-accessible
	STATUS mandatory
	DESCRIPTION
		"&<caiW2kOs.295>A table containing all auto discovery watchers for services."
	::= { w2kConfigSrvcGroup 13 }


w2kConfigSrvcAutoEntry OBJECT-TYPE
	SYNTAX W2kConfigSrvcAutoRow
	ACCESS not-accessible
	STATUS mandatory
	DESCRIPTION
		"&<caiW2kOs.154>The table entry."
	INDEX { w2kConfigSrvcAutoWatcherName }
	::= { w2kConfigSrvcAutoTable 1 }


W2kConfigSrvcAutoRow ::=
	SEQUENCE {
		w2kConfigSrvcAutoWatcherName DisplayString,
		w2kConfigSrvcAutoName DisplayString,
		w2kConfigSrvcAutoDescription DisplayString,
		w2kConfigSrvcAutoAggLag INTEGER,
		w2kConfigSrvcAutoExist INTEGER,
		w2kConfigSrvcAutoExistMonitor INTEGER,
		w2kConfigSrvcAutoActive INTEGER,
		w2kConfigSrvcAutoActiveMonitor INTEGER,
		w2kConfigSrvcAutoButton INTEGER
	}


w2kConfigSrvcAutoWatcherName OBJECT-TYPE
	SYNTAX DisplayString
	ACCESS read-only
	STATUS mandatory
	DESCRIPTION
		"&<caiW2kOs.155>Name of the auto discovery watcher."
	::= { w2kConfigSrvcAutoEntry 1 }


w2kConfigSrvcAutoName OBJECT-TYPE
	SYNTAX DisplayString
	ACCESS read-write
	STATUS mandatory
	DESCRIPTION
		"&<caiW2kOs.298>Wildcarded service name filtering the services to be auto discovered (any backslash in the wildcarded name must be doubled). For each auto discovered service a watcher will be created. Important: This name is case insensitive."
	::= { w2kConfigSrvcAutoEntry 2 }


w2kConfigSrvcAutoDescription OBJECT-TYPE
	SYNTAX DisplayString
	ACCESS read-write
	STATUS mandatory
	DESCRIPTION
		"&<caiW2kOs.299>This attribute has the same purpose as the corresponding attribute in the config group (please see there). The difference is that it specifies the default if the service is automatically discovered (in contrast to manually adding a watcher for the service)."
	::= { w2kConfigSrvcAutoEntry 3 }


w2kConfigSrvcAutoAggLag OBJECT-TYPE
	SYNTAX INTEGER
	ACCESS read-write
	STATUS mandatory
	DESCRIPTION
		"&<caiW2kOs.299>This attribute has the same purpose as the corresponding attribute in the config group (please see there). The difference is that it specifies the default if the service is automatically discovered (in contrast to manually adding a watcher for the service)."
	::= { w2kConfigSrvcAutoEntry 4 }


w2kConfigSrvcAutoExist OBJECT-TYPE
	SYNTAX INTEGER {
		should-exist(1),
		should-not-exist(2)
	}
	ACCESS read-write
	STATUS mandatory
	DESCRIPTION
		"&<caiW2kOs.299>This attribute has the same purpose as the corresponding attribute in the config group (please see there). The difference is that it specifies the default if the service is automatically discovered (in contrast to manually adding a watcher for the service)."
	DEFVAL { 0 }
	::= { w2kConfigSrvcAutoEntry 5 }


w2kConfigSrvcAutoExistMonitor OBJECT-TYPE
	SYNTAX INTEGER {
		do-not-monitor(1),
		down-warning(2),
		down-critical(3)
	}
	ACCESS read-write
	STATUS mandatory
	DESCRIPTION
		"&<caiW2kOs.299>This attribute has the same purpose as the corresponding attribute in the config group (please see there). The difference is that it specifies the default if the service is automatically discovered (in contrast to manually adding a watcher for the service)."
	DEFVAL { 0 }
	::= { w2kConfigSrvcAutoEntry 6 }


w2kConfigSrvcAutoActive OBJECT-TYPE
	SYNTAX INTEGER {
		should-be-active(1),
		should-not-be-active(2)
	}
	ACCESS read-write
	STATUS mandatory
	DESCRIPTION
		"&<caiW2kOs.299>This attribute has the same purpose as the corresponding attribute in the config group (please see there). The difference is that it specifies the default if the service is automatically discovered (in contrast to manually adding a watcher for the service)."
	DEFVAL { 0 }
	::= { w2kConfigSrvcAutoEntry 7 }


w2kConfigSrvcAutoActiveMonitor OBJECT-TYPE
	SYNTAX INTEGER {
		do-not-monitor(1),
		down-warning(2),
		down-critical(3)
	}
	ACCESS read-write
	STATUS mandatory
	DESCRIPTION
		"&<caiW2kOs.299>This attribute has the same purpose as the corresponding attribute in the config group (please see there). The difference is that it specifies the default if the service is automatically discovered (in contrast to manually adding a watcher for the service)."
	DEFVAL { 0 }
	::= { w2kConfigSrvcAutoEntry 8 }


w2kConfigSrvcAutoButton OBJECT-TYPE
	SYNTAX INTEGER {
		none(1),
		remove(2)
	}
	ACCESS read-write
	STATUS mandatory
	DESCRIPTION
		"&<caiW2kOs.172>This attribute is used to remove this auto discovery watcher."
	::= { w2kConfigSrvcAutoEntry 9 }




--	------------------------------------------------------------------------
--      Jobs Config Group
--	------------------------------------------------------------------------


w2kConfigJobPollInterval OBJECT-TYPE
	SYNTAX INTEGER
	ACCESS read-write
	STATUS mandatory
	DESCRIPTION
		"&<caiW2kOs.306>The time (in seconds) between the polling of the job information. Valid values are greater than or equal to 30."
	DEFVAL { 120 }
	::= { w2kConfigJobGroup 1 }


w2kConfigJobPollMethod OBJECT-TYPE
	SYNTAX INTEGER {
		disabled(1),
		poll-interval-only(2),
		poll-interval-and-query(3),
		query-only(4)
	}
	ACCESS read-write
	STATUS mandatory
	DESCRIPTION
		"&<caiW2kOs.307>If set to 'disabled', the agent no more retrieves the job information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigJobGroup 2 }


w2kConfigJobName OBJECT-TYPE
	SYNTAX DisplayString
	ACCESS read-write
	STATUS mandatory
	DESCRIPTION
		"&<caiW2kOs.308>Name of the watcher to be added/removed, monitoring a job with this name. Important: This name is case insensitive."
	::= { w2kConfigJobGroup 3 }


w2kConfigJobDescription OBJECT-TYPE
	SYNTAX DisplayString
	ACCESS read-write
	STATUS mandatory
	DESCRIPTION
		"&<caiW2kOs.136>Any description for this watcher."
	::= { w2kConfigJobGroup 4 }


w2kConfigJobAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigJobGroup 5 }


w2kConfigJobExist OBJECT-TYPE
	SYNTAX INTEGER {
		should-exist(1),
		should-not-exist(2)
	}
	ACCESS read-write
	STATUS mandatory
	DESCRIPTION
		"&<caiW2kOs.311>Flag indicating whether to raise an alert if a job is existent or if it is not-existent."
	DEFVAL { 1 }
	::= { w2kConfigJobGroup 6 }


w2kConfigJobExistMonitor OBJECT-TYPE
	SYNTAX INTEGER {
		do-not-monitor(1),
		down-warning(2),
		down-critical(3)
	}
	ACCESS read-write
	STATUS mandatory
	DESCRIPTION
		"&<caiW2kOs.312>Flag indicating whether the existence of the job should be monitored and if so, the level of alert to raise."
	DEFVAL { 3 }
	::= { w2kConfigJobGroup 7 }


w2kConfigJobProcessMin OBJECT-TYPE
	SYNTAX INTEGER
	ACCESS read-write
	STATUS mandatory
	DESCRIPTION
		"&<caiW2kOs.313>Minimum threshold for the number of active processes associated with the job. Valid values are greater than or equal to -1 and smaller than or equal to the maximum threshold. Setting to -1 disables the monitoring of the minimum."
	DEFVAL { 1 }
	::= { w2kConfigJobGroup 8 }


w2kConfigJobProcessMax OBJECT-TYPE
	SYNTAX INTEGER
	ACCESS read-write
	STATUS mandatory
	DESCRIPTION
		"&<caiW2kOs.314>Maximum threshold for the number of active processes associated with the job. Valid values are greater than or equal to -1 and greater than or equal to the minimum threshold. Setting to -1 disables the monitoring of the maximum."
	DEFVAL { 10 }
	::= { w2kConfigJobGroup 9 }


w2kConfigJobProcessMonitor OBJECT-TYPE
	SYNTAX INTEGER {
		do-not-monitor(1),
		down-warning(2),
		down-critical(3)
	}
	ACCESS read-write
	STATUS mandatory
	DESCRIPTION
		"&<caiW2kOs.315>Flag indicating whether the number of active processes associated with the job should be monitored and if so, the level of alert to raise."
	DEFVAL { 2 }
	::= { w2kConfigJobGroup 10 }


w2kConfigJobCpuWarn OBJECT-TYPE
	SYNTAX INTEGER
	ACCESS read-write
	STATUS mandatory
	DESCRIPTION
		"&<caiW2kOs.316>Warning threshold for the CPU usage of the job (as percentage value of 100). Valid values are 1 to 99 and smaller than the critical threshold."
	DEFVAL { 10 }
	::= { w2kConfigJobGroup 11 }


w2kConfigJobCpuCrit OBJECT-TYPE
	SYNTAX INTEGER
	ACCESS read-write
	STATUS mandatory
	DESCRIPTION
		"&<caiW2kOs.317>Critical threshold for the CPU usage of the job (as percentage value of 100). Valid values are 2 to 100 and greater than the warning threshold."
	DEFVAL { 20 }
	::= { w2kConfigJobGroup 12 }


w2kConfigJobCpuMonitor OBJECT-TYPE
	SYNTAX INTEGER {
		do-not-monitor(1),
		warning-only(2),
		critical-only(3),
		both(4)
	}
	ACCESS read-write
	STATUS mandatory
	DESCRIPTION
		"&<caiW2kOs.318>Flag indicating whether the CPU usage of the job should be monitored and if so, which threshold should be compared with."
	DEFVAL { 4 }
	::= { w2kConfigJobGroup 13 }


w2kConfigJobButton OBJECT-TYPE
	SYNTAX INTEGER {
		none(1),
		add(2),
		remove(3)
	}
	ACCESS read-write
	STATUS mandatory
	DESCRIPTION
		"&<caiW2kOs.226>This attribute is used to add or remove a watcher with the current value of the watcher name attribute in this group."
	::= { w2kConfigJobGroup 14 }




--	------------------------------------------------------------------------
--      Sessions Config Group
--	------------------------------------------------------------------------


w2kConfigSessPollInterval OBJECT-TYPE
	SYNTAX INTEGER
	ACCESS read-write
	STATUS mandatory
	DESCRIPTION
		"&<caiW2kOs.320>The time (in seconds) between the polling of the session information. Valid values are greater than or equal to 30."
	DEFVAL { 120 }
	::= { w2kConfigSessGroup 1 }


w2kConfigSessPollMethod OBJECT-TYPE
	SYNTAX INTEGER {
		disabled(1),
		poll-interval-only(2),
		poll-interval-and-query(3),
		query-only(4)
	}
	ACCESS read-write
	STATUS mandatory
	DESCRIPTION
		"&<caiW2kOs.321>If set to 'disabled', the agent no more retrieves the session information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigSessGroup 2 }


w2kConfigSessClientName OBJECT-TYPE
	SYNTAX DisplayString
	ACCESS read-write
	STATUS mandatory
	DESCRIPTION
		"&<caiW2kOs.322>Client name of the watcher to be added/removed, monitoring a session with this client name. The client name is the name of the host, from where this session was initiated. An asterisk '*' can be used as client name or can be prepended/appended to it, in order to widen the scope of sessions this watcher monitors. Important: This name is case insensitive."
	::= { w2kConfigSessGroup 3 }


w2kConfigSessUserName OBJECT-TYPE
	SYNTAX DisplayString
	ACCESS read-write
	STATUS mandatory
	DESCRIPTION
		"&<caiW2kOs.323>User name of the watcher to be added/removed, monitoring a session with this user name. The user name specifies the user, who logged in and is in the form 'domainName\\userName'. An asterisk '*' can be used as user name or can be prepended/appended to it, in order to widen the scope of sessions this watcher monitors. Important: This name is case insensitive."
	::= { w2kConfigSessGroup 4 }


w2kConfigSessDescription OBJECT-TYPE
	SYNTAX DisplayString
	ACCESS read-write
	STATUS mandatory
	DESCRIPTION
		"&<caiW2kOs.136>Any description for this watcher."
	::= { w2kConfigSessGroup 5 }


w2kConfigSessAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigSessGroup 6 }


w2kConfigSessInstMin OBJECT-TYPE
	SYNTAX INTEGER
	ACCESS read-write
	STATUS mandatory
	DESCRIPTION
		"&<caiW2kOs.326>Minimum threshold for the number of session instances. Valid values are greater than or equal to -1 and smaller than or equal to the maximum threshold. Setting to -1 disables the monitoring of the minimum."
	DEFVAL { 0 }
	::= { w2kConfigSessGroup 7 }


w2kConfigSessInstMax OBJECT-TYPE
	SYNTAX INTEGER
	ACCESS read-write
	STATUS mandatory
	DESCRIPTION
		"&<caiW2kOs.327>Maximum threshold for the number of session instances. Valid values are greater than or equal to -1 and greater than or equal to the minimum threshold. Setting to -1 disables the monitoring of the maximum."
	DEFVAL { 2 }
	::= { w2kConfigSessGroup 8 }


w2kConfigSessInstMonitor OBJECT-TYPE
	SYNTAX INTEGER {
		do-not-monitor(1),
		down-warning(2),
		down-critical(3)
	}
	ACCESS read-write
	STATUS mandatory
	DESCRIPTION
		"&<caiW2kOs.328>Flag indicating whether the number of session instances should be monitored and if so, the level of alert to raise."
	DEFVAL { 3 }
	::= { w2kConfigSessGroup 9 }


w2kConfigSessMemoryWarn OBJECT-TYPE
	SYNTAX INTEGER
	ACCESS read-write
	STATUS mandatory
	DESCRIPTION
		"&<caiW2kOs.329>Warning threshold for the memory usage of the session (in kilobytes). If there is more than one session instance, the maximum of all instances is compared with this value. Valid values are greater than 0 and smaller than the critical threshold."
	DEFVAL { 20000 }
	::= { w2kConfigSessGroup 10 }


w2kConfigSessMemoryCrit OBJECT-TYPE
	SYNTAX INTEGER
	ACCESS read-write
	STATUS mandatory
	DESCRIPTION
		"&<caiW2kOs.330>Critical threshold for the memory usage of the session (in kilobytes). If there is more than one session instance, the maximum of all instances is compared with this value. Valid values are greater than 1 and greater than the warning threshold."
	DEFVAL { 40000 }
	::= { w2kConfigSessGroup 11 }


w2kConfigSessMemoryMonitor OBJECT-TYPE
	SYNTAX INTEGER {
		do-not-monitor(1),
		warning-only(2),
		critical-only(3),
		both(4)
	}
	ACCESS read-write
	STATUS mandatory
	DESCRIPTION
		"&<caiW2kOs.331>Flag indicating whether the memory usage of the session should be monitored and if so, which threshold should be compared with."
	DEFVAL { 4 }
	::= { w2kConfigSessGroup 12 }


w2kConfigSessCpuWarn OBJECT-TYPE
	SYNTAX INTEGER
	ACCESS read-write
	STATUS mandatory
	DESCRIPTION
		"&<caiW2kOs.332>Warning threshold for the CPU usage of the session (as percentage value of 100). If there is more than one session instance, the maximum of all instances is compared with this value. Valid values are 1 to 99 and smaller than the critical threshold."
	DEFVAL { 10 }
	::= { w2kConfigSessGroup 13 }


w2kConfigSessCpuCrit OBJECT-TYPE
	SYNTAX INTEGER
	ACCESS read-write
	STATUS mandatory
	DESCRIPTION
		"&<caiW2kOs.333>Critical threshold for the CPU usage of the session (as percentage value of 100). If there is more than one session instance, the maximum of all instances is compared with this value. Valid values are 2 to 100 and greater than the warning threshold."
	DEFVAL { 20 }
	::= { w2kConfigSessGroup 14 }


w2kConfigSessCpuMonitor OBJECT-TYPE
	SYNTAX INTEGER {
		do-not-monitor(1),
		warning-only(2),
		critical-only(3),
		both(4)
	}
	ACCESS read-write
	STATUS mandatory
	DESCRIPTION
		"&<caiW2kOs.334>Flag indicating whether the CPU usage of the session should be monitored and if so, which threshold should be compared with."
	DEFVAL { 4 }
	::= { w2kConfigSessGroup 15 }


w2kConfigSessButton OBJECT-TYPE
	SYNTAX INTEGER {
		none(1),
		add(2),
		remove(3)
	}
	ACCESS read-write
	STATUS mandatory
	DESCRIPTION
		"&<caiW2kOs.226>This attribute is used to add or remove a watcher with the current value of the watcher name attribute in this group."
	::= { w2kConfigSessGroup 16 }




--	------------------------------------------------------------------------
--      Printers Config Group
--	------------------------------------------------------------------------


w2kConfigPrnPollInterval OBJECT-TYPE
	SYNTAX INTEGER
	ACCESS read-write
	STATUS mandatory
	DESCRIPTION
		"&<caiW2kOs.336>The time (in seconds) between the polling of the printer information. Valid values are greater than or equal to 30."
	DEFVAL { 120 }
	::= { w2kConfigPrnGroup 1 }


w2kConfigPrnPollMethod OBJECT-TYPE
	SYNTAX INTEGER {
		disabled(1),
		poll-interval-only(2),
		poll-interval-and-query(3),
		query-only(4)
	}
	ACCESS read-write
	STATUS mandatory
	DESCRIPTION
		"&<caiW2kOs.337>If set to 'disabled', the agent no more retrieves the printer information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigPrnGroup 2 }


w2kConfigPrnAutoPollInterval OBJECT-TYPE
	SYNTAX INTEGER
	ACCESS read-write
	STATUS mandatory
	DESCRIPTION
		"&<caiW2kOs.338>The time (in minutes), when a new auto discovery process is started. Valid values are greater than or equal to 30 or set to -1. If set to -1, auto discovery of printers will no more be made."
	DEFVAL { 60 }
	::= { w2kConfigPrnGroup 3 }


w2kConfigPrnName OBJECT-TYPE
	SYNTAX DisplayString
	ACCESS read-write
	STATUS mandatory
	DESCRIPTION
		"&<caiW2kOs.339>Name of the watcher to be added/removed, monitoring a local printer with this name. If adding an auto discovery watcher, this name can be a wildcarded printer name filtering the printers to be auto discovered (any backslash in the wildcarded name must be doubled). For each auto discovered printer a watcher will be created. Important: This name is case insensitive."
	::= { w2kConfigPrnGroup 4 }


w2kConfigPrnDescription OBJECT-TYPE
	SYNTAX DisplayString
	ACCESS read-write
	STATUS mandatory
	DESCRIPTION
		"&<caiW2kOs.136>Any description for this watcher."
	::= { w2kConfigPrnGroup 5 }


w2kConfigPrnAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigPrnGroup 6 }


w2kConfigPrnEventMonitor OBJECT-TYPE
	SYNTAX INTEGER {
		do-not-monitor(1),
		down-warning(2),
		down-critical(3)
	}
	ACCESS read-write
	STATUS mandatory
	DESCRIPTION
		"&<caiW2kOs.342>Flag indicating whether the occurence of printer events should be monitored and if so, the level of alert to raise."
	DEFVAL { 2 }
	::= { w2kConfigPrnGroup 7 }


w2kConfigPrnQueueWarn OBJECT-TYPE
	SYNTAX INTEGER
	ACCESS read-write
	STATUS mandatory
	DESCRIPTION
		"&<caiW2kOs.343>Warning threshold for the number of jobs in the printer's queue. Valid values are greater than 0 and smaller than the critical threshold."
	DEFVAL { 5 }
	::= { w2kConfigPrnGroup 8 }


w2kConfigPrnQueueCrit OBJECT-TYPE
	SYNTAX INTEGER
	ACCESS read-write
	STATUS mandatory
	DESCRIPTION
		"&<caiW2kOs.344>Critical threshold for the number of jobs in the printer's queue. Valid values are greater than 1 and greater than the warning threshold."
	DEFVAL { 10 }
	::= { w2kConfigPrnGroup 9 }


w2kConfigPrnQueueMonitor OBJECT-TYPE
	SYNTAX INTEGER {
		do-not-monitor(1),
		warning-only(2),
		critical-only(3),
		both(4)
	}
	ACCESS read-write
	STATUS mandatory
	DESCRIPTION
		"&<caiW2kOs.345>Flag indicating whether the printer's job queue should be monitored and if so, which threshold should be compared with."
	DEFVAL { 4 }
	::= { w2kConfigPrnGroup 10 }


w2kConfigPrnLossAction OBJECT-TYPE
	SYNTAX INTEGER {
		remove(1),
		up(2),
		down-warning(3),
		down-critical(4)
	}
	ACCESS read-write
	STATUS mandatory
	DESCRIPTION
		"&<caiW2kOs.346>Flag defining the severity if the loss of the printer is detected or whether to remove this watcher in that case."
	DEFVAL { 4 }
	::= { w2kConfigPrnGroup 11 }


w2kConfigPrnAutoTableWatcherName OBJECT-TYPE
	SYNTAX DisplayString
	ACCESS read-write
	STATUS mandatory
	DESCRIPTION
		"&<caiW2kOs.151>Name of the watcher to be added in the auto discovery table."
	::= { w2kConfigPrnGroup 12 }


w2kConfigPrnButton OBJECT-TYPE
	SYNTAX INTEGER {
		none(1),
		add(2),
		remove(3),
		add-auto(4),
		remove-auto(5)
	}
	ACCESS read-write
	STATUS mandatory
	DESCRIPTION
		"&<caiW2kOs.152>This attribute is used to add or remove a watcher with the current value of the watcher name attribute in this group, or to add or remove an auto discovery watcher with the current value of the auto table watcher name attribute in this group."
	::= { w2kConfigPrnGroup 13 }


w2kConfigPrnAutoTable OBJECT-TYPE
	SYNTAX SEQUENCE OF W2kConfigPrnAutoRow
	ACCESS not-accessible
	STATUS mandatory
	DESCRIPTION
		"&<caiW2kOs.349>A table containing all auto discovery watchers for printers."
	::= { w2kConfigPrnGroup 14 }


w2kConfigPrnAutoEntry OBJECT-TYPE
	SYNTAX W2kConfigPrnAutoRow
	ACCESS not-accessible
	STATUS mandatory
	DESCRIPTION
		"&<caiW2kOs.154>The table entry."
	INDEX { w2kConfigPrnAutoWatcherName }
	::= { w2kConfigPrnAutoTable 1 }


W2kConfigPrnAutoRow ::=
	SEQUENCE {
		w2kConfigPrnAutoWatcherName DisplayString,
		w2kConfigPrnAutoName DisplayString,
		w2kConfigPrnAutoDescription DisplayString,
		w2kConfigPrnAutoAggLag INTEGER,
		w2kConfigPrnAutoEventMonitor INTEGER,
		w2kConfigPrnAutoQueueWarn INTEGER,
		w2kConfigPrnAutoQueueCrit INTEGER,
		w2kConfigPrnAutoQueueMonitor INTEGER,
		w2kConfigPrnAutoLossAction INTEGER,
		w2kConfigPrnAutoButton INTEGER
	}


w2kConfigPrnAutoWatcherName OBJECT-TYPE
	SYNTAX DisplayString
	ACCESS read-only
	STATUS mandatory
	DESCRIPTION
		"&<caiW2kOs.155>Name of the auto discovery watcher."
	::= { w2kConfigPrnAutoEntry 1 }


w2kConfigPrnAutoName OBJECT-TYPE
	SYNTAX DisplayString
	ACCESS read-write
	STATUS mandatory
	DESCRIPTION
		"&<caiW2kOs.352>Wildcarded printer name filtering the printers to be auto discovered (any backslash in the wildcarded name must be doubled). For each auto discovered printer a watcher will be created. Important: This name is case insensitive."
	::= { w2kConfigPrnAutoEntry 2 }


w2kConfigPrnAutoDescription OBJECT-TYPE
	SYNTAX DisplayString
	ACCESS read-write
	STATUS mandatory
	DESCRIPTION
		"&<caiW2kOs.353>This attribute has the same purpose as the corresponding attribute in the config group (please see there). The difference is that it specifies the default if the printer is automatically discovered (in contrast to manually adding a watcher for the printer)."
	::= { w2kConfigPrnAutoEntry 3 }


w2kConfigPrnAutoAggLag OBJECT-TYPE
	SYNTAX INTEGER
	ACCESS read-write
	STATUS mandatory
	DESCRIPTION
		"&<caiW2kOs.353>This attribute has the same purpose as the corresponding attribute in the config group (please see there). The difference is that it specifies the default if the printer is automatically discovered (in contrast to manually adding a watcher for the printer)."
	::= { w2kConfigPrnAutoEntry 4 }


w2kConfigPrnAutoEventMonitor OBJECT-TYPE
	SYNTAX INTEGER {
		do-not-monitor(1),
		down-warning(2),
		down-critical(3)
	}
	ACCESS read-write
	STATUS mandatory
	DESCRIPTION
		"&<caiW2kOs.353>This attribute has the same purpose as the corresponding attribute in the config group (please see there). The difference is that it specifies the default if the printer is automatically discovered (in contrast to manually adding a watcher for the printer)."
	DEFVAL { 0 }
	::= { w2kConfigPrnAutoEntry 5 }


w2kConfigPrnAutoQueueWarn OBJECT-TYPE
	SYNTAX INTEGER
	ACCESS read-write
	STATUS mandatory
	DESCRIPTION
		"&<caiW2kOs.353>This attribute has the same purpose as the corresponding attribute in the config group (please see there). The difference is that it specifies the default if the printer is automatically discovered (in contrast to manually adding a watcher for the printer)."
	::= { w2kConfigPrnAutoEntry 6 }


w2kConfigPrnAutoQueueCrit OBJECT-TYPE
	SYNTAX INTEGER
	ACCESS read-write
	STATUS mandatory
	DESCRIPTION
		"&<caiW2kOs.353>This attribute has the same purpose as the corresponding attribute in the config group (please see there). The difference is that it specifies the default if the printer is automatically discovered (in contrast to manually adding a watcher for the printer)."
	::= { w2kConfigPrnAutoEntry 7 }


w2kConfigPrnAutoQueueMonitor OBJECT-TYPE
	SYNTAX INTEGER {
		do-not-monitor(1),
		warning-only(2),
		critical-only(3),
		both(4)
	}
	ACCESS read-write
	STATUS mandatory
	DESCRIPTION
		"&<caiW2kOs.353>This attribute has the same purpose as the corresponding attribute in the config group (please see there). The difference is that it specifies the default if the printer is automatically discovered (in contrast to manually adding a watcher for the printer)."
	DEFVAL { 0 }
	::= { w2kConfigPrnAutoEntry 8 }


w2kConfigPrnAutoLossAction OBJECT-TYPE
	SYNTAX INTEGER {
		remove(1),
		up(2),
		down-warning(3),
		down-critical(4)
	}
	ACCESS read-write
	STATUS mandatory
	DESCRIPTION
		"&<caiW2kOs.353>This attribute has the same purpose as the corresponding attribute in the config group (please see there). The difference is that it specifies the default if the printer is automatically discovered (in contrast to manually adding a watcher for the printer)."
	DEFVAL { 0 }
	::= { w2kConfigPrnAutoEntry 9 }


w2kConfigPrnAutoButton OBJECT-TYPE
	SYNTAX INTEGER {
		none(1),
		remove(2)
	}
	ACCESS read-write
	STATUS mandatory
	DESCRIPTION
		"&<caiW2kOs.172>This attribute is used to remove this auto discovery watcher."
	::= { w2kConfigPrnAutoEntry 10 }




--	------------------------------------------------------------------------
--      Network Interfaces Config Group
--	------------------------------------------------------------------------


w2kConfigNetPollInterval OBJECT-TYPE
	SYNTAX INTEGER
	ACCESS read-write
	STATUS mandatory
	DESCRIPTION
		"&<caiW2kOs.361>The time (in seconds) between the polling of the network interface information. Valid values are greater than or equal to 30."
	DEFVAL { 120 }
	::= { w2kConfigNetGroup 1 }


w2kConfigNetPollMethod OBJECT-TYPE
	SYNTAX INTEGER {
		disabled(1),
		poll-interval-only(2),
		poll-interval-and-query(3),
		query-only(4)
	}
	ACCESS read-write
	STATUS mandatory
	DESCRIPTION
		"&<caiW2kOs.362>If set to 'disabled', the agent no more retrieves the network interface information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigNetGroup 2 }


w2kConfigNetAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigNetGroup 3 }


w2kConfigNetInPktWarn OBJECT-TYPE
	SYNTAX INTEGER
	ACCESS read-write
	STATUS mandatory
	DESCRIPTION
		"&<caiW2kOs.364>Warning threshold for the rate of received packets over TCP/IP connections (packets per second). Valid values are greater than 0 and smaller than the critical threshold."
	DEFVAL { 200 }
	::= { w2kConfigNetGroup 4 }


w2kConfigNetInPktCrit OBJECT-TYPE
	SYNTAX INTEGER
	ACCESS read-write
	STATUS mandatory
	DESCRIPTION
		"&<caiW2kOs.365>Critical threshold for the rate of received packets over TCP/IP connections (packets per second). Valid values are greater than 1 and greater than the warning threshold."
	DEFVAL { 400 }
	::= { w2kConfigNetGroup 5 }


w2kConfigNetInPktMonitor OBJECT-TYPE
	SYNTAX INTEGER {
		do-not-monitor(1),
		warning-only(2),
		critical-only(3),
		both(4)
	}
	ACCESS read-write
	STATUS mandatory
	DESCRIPTION
		"&<caiW2kOs.366>Flag indicating whether the received packets rate should be monitored and if so, which threshold should be compared with."
	DEFVAL { 4 }
	::= { w2kConfigNetGroup 6 }


w2kConfigNetOutPktWarn OBJECT-TYPE
	SYNTAX INTEGER
	ACCESS read-write
	STATUS mandatory
	DESCRIPTION
		"&<caiW2kOs.367>Warning threshold for the rate of sent packets over TCP/IP connections (packets per second). Valid values are greater than 0 and smaller than the critical threshold."
	DEFVAL { 200 }
	::= { w2kConfigNetGroup 7 }


w2kConfigNetOutPktCrit OBJECT-TYPE
	SYNTAX INTEGER
	ACCESS read-write
	STATUS mandatory
	DESCRIPTION
		"&<caiW2kOs.368>Critical threshold for the rate of sent packets over TCP/IP connections (packets per second). Valid values are greater than 1 and greater than the warning threshold."
	DEFVAL { 400 }
	::= { w2kConfigNetGroup 8 }


w2kConfigNetOutPktMonitor OBJECT-TYPE
	SYNTAX INTEGER {
		do-not-monitor(1),
		warning-only(2),
		critical-only(3),
		both(4)
	}
	ACCESS read-write
	STATUS mandatory
	DESCRIPTION
		"&<caiW2kOs.369>Flag indicating whether the sent packets rate should be monitored and if so, which threshold should be compared with."
	DEFVAL { 4 }
	::= { w2kConfigNetGroup 9 }


w2kConfigNetInErrDWarn OBJECT-TYPE
	SYNTAX INTEGER
	ACCESS read-write
	STATUS mandatory
	DESCRIPTION
		"&<caiW2kOs.370>Warning threshold for the rate of received errors over TCP/IP connections (errors per poll interval). Valid values are greater than 0 and smaller than the critical threshold."
	DEFVAL { 20 }
	::= { w2kConfigNetGroup 10 }


w2kConfigNetInErrDCrit OBJECT-TYPE
	SYNTAX INTEGER
	ACCESS read-write
	STATUS mandatory
	DESCRIPTION
		"&<caiW2kOs.371>Critical threshold for the rate of received errors over TCP/IP connections (errors per poll interval). Valid values are greater than 1 and greater than the warning threshold."
	DEFVAL { 40 }
	::= { w2kConfigNetGroup 11 }


w2kConfigNetInErrDMonitor OBJECT-TYPE
	SYNTAX INTEGER {
		do-not-monitor(1),
		warning-only(2),
		critical-only(3),
		both(4)
	}
	ACCESS read-write
	STATUS mandatory
	DESCRIPTION
		"&<caiW2kOs.372>Flag indicating whether the received errors rate should be monitored and if so, which threshold should be compared with."
	DEFVAL { 4 }
	::= { w2kConfigNetGroup 12 }


w2kConfigNetOutErrDWarn OBJECT-TYPE
	SYNTAX INTEGER
	ACCESS read-write
	STATUS mandatory
	DESCRIPTION
		"&<caiW2kOs.373>Warning threshold for the rate of sent errors over TCP/IP connections (errors per poll interval). Valid values are greater than 0 and smaller than the critical threshold."
	DEFVAL { 20 }
	::= { w2kConfigNetGroup 13 }


w2kConfigNetOutErrDCrit OBJECT-TYPE
	SYNTAX INTEGER
	ACCESS read-write
	STATUS mandatory
	DESCRIPTION
		"&<caiW2kOs.374>Critical threshold for the rate of sent errors over TCP/IP connections (errors per poll interval). Valid values are greater than 1 and greater than the warning threshold."
	DEFVAL { 40 }
	::= { w2kConfigNetGroup 14 }


w2kConfigNetOutErrDMonitor OBJECT-TYPE
	SYNTAX INTEGER {
		do-not-monitor(1),
		warning-only(2),
		critical-only(3),
		both(4)
	}
	ACCESS read-write
	STATUS mandatory
	DESCRIPTION
		"&<caiW2kOs.375>Flag indicating whether the sent errors rate should be monitored and if so, which threshold should be compared with."
	DEFVAL { 4 }
	::= { w2kConfigNetGroup 15 }


w2kConfigNetLossAction OBJECT-TYPE
	SYNTAX INTEGER {
		remove(1),
		up(2),
		down-warning(3),
		down-critical(4)
	}
	ACCESS read-write
	STATUS mandatory
	DESCRIPTION
		"&<caiW2kOs.376>Flag defining the severity if the loss of the network interface is detected or whether to remove this watcher in that case."
	DEFVAL { 1 }
	::= { w2kConfigNetGroup 16 }




--	------------------------------------------------------------------------
--      Registry Entries Config Group
--	------------------------------------------------------------------------


w2kConfigRegPollInterval OBJECT-TYPE
	SYNTAX INTEGER
	ACCESS read-write
	STATUS mandatory
	DESCRIPTION
		"&<caiW2kOs.377>The time (in seconds) between the polling of the registry entry information. Valid values are greater than or equal to 30."
	DEFVAL { 120 }
	::= { w2kConfigRegGroup 1 }


w2kConfigRegPollMethod OBJECT-TYPE
	SYNTAX INTEGER {
		disabled(1),
		poll-interval-only(2),
		poll-interval-and-query(3),
		query-only(4)
	}
	ACCESS read-write
	STATUS mandatory
	DESCRIPTION
		"&<caiW2kOs.378>If set to 'disabled', the agent no more retrieves the registry entry information (not by polling, nor by get request) and sets all statuses to ok. If set to 'poll-interval-only', the agent only retrieves the information by polling, but not by get request. If set to 'poll-interval-and-query', the agent retrieves the information in both cases (polling and get request). If set to 'query-only', the agent retrieves the information for get requests only."
	DEFVAL { 2 }
	::= { w2kConfigRegGroup 2 }


w2kConfigRegName OBJECT-TYPE
	SYNTAX DisplayString
	ACCESS read-write
	STATUS mandatory
	DESCRIPTION
		"&<caiW2kOs.379>Name of the watcher to be added/removed, monitoring a registry entry with this name. The name is the complete registry path ending with the registry leaf name. If the leaf name contains a backslash, the leaf name must be quoted with double quotes. Important: This name is case insensitive."
	::= { w2kConfigRegGroup 3 }


w2kConfigRegDescription OBJECT-TYPE
	SYNTAX DisplayString
	ACCESS read-write
	STATUS mandatory
	DESCRIPTION
		"&<caiW2kOs.136>Any description for this watcher."
	::= { w2kConfigRegGroup 4 }


w2kConfigRegAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kConfigRegGroup 5 }


w2kConfigRegExist OBJECT-TYPE
	SYNTAX INTEGER {
		should-exist(1),
		should-not-exist(2)
	}
	ACCESS read-write
	STATUS mandatory
	DESCRIPTION
		"&<caiW2kOs.382>Flag indicating whether to raise an alert if a registry entry is existent or if it is not-existent."
	DEFVAL { 1 }
	::= { w2kConfigRegGroup 6 }


w2kConfigRegExistMonitor OBJECT-TYPE
	SYNTAX INTEGER {
		do-not-monitor(1),
		down-warning(2),
		down-critical(3)
	}
	ACCESS read-write
	STATUS mandatory
	DESCRIPTION
		"&<caiW2kOs.383>Flag indicating whether the existence of the registry entry should be monitored and if so, the level of alert to raise."
	DEFVAL { 3 }
	::= { w2kConfigRegGroup 7 }


w2kConfigRegValueRef OBJECT-TYPE
	SYNTAX DisplayString
	ACCESS read-write
	STATUS mandatory
	DESCRIPTION
		"&<caiW2kOs.384>This attribute is used as the reference value the registry entry is compared with. If the condition is one of 'should-be-equal', 'should-not-be-equal', 'should-be-below' or 'should-be-above', this reference value must be set by the user. In case of 'should-not-change', by setting the status button attribute to 'reset-value', the reference value is set to the current value of the registry entry."
	DEFVAL { "0" }
	::= { w2kConfigRegGroup 8 }


w2kConfigRegValueCond OBJECT-TYPE
	SYNTAX INTEGER {
		should-be-equal(1),
		should-not-be-equal(2),
		should-be-below(3),
		should-be-above(4),
		should-not-change(5)
	}
	ACCESS read-write
	STATUS mandatory
	DESCRIPTION
		"&<caiW2kOs.385>Flag indicating whether to raise an alert if a registry entry does not fullfill the given condition compared with the reference value attribute. 'should-be-below' and 'should-be-above' is only allowed for entries with type DWORD. For entries with type Binary 'should-not-change' is the only possible value."
	DEFVAL { 5 }
	::= { w2kConfigRegGroup 9 }


w2kConfigRegValueMonitor OBJECT-TYPE
	SYNTAX INTEGER {
		do-not-monitor(1),
		down-warning(2),
		down-critical(3)
	}
	ACCESS read-write
	STATUS mandatory
	DESCRIPTION
		"&<caiW2kOs.386>Flag indicating whether the value of the registry entry should be monitored and if so, the level of alert to raise."
	DEFVAL { 2 }
	::= { w2kConfigRegGroup 10 }


w2kConfigRegButton OBJECT-TYPE
	SYNTAX INTEGER {
		none(1),
		add(2),
		remove(3)
	}
	ACCESS read-write
	STATUS mandatory
	DESCRIPTION
		"&<caiW2kOs.226>This attribute is used to add or remove a watcher with the current value of the watcher name attribute in this group."
	::= { w2kConfigRegGroup 11 }




--	------------------------------------------------------------------------
--      General Status Group
--	------------------------------------------------------------------------


w2kStatusGeneralTotalCount OBJECT-TYPE
	SYNTAX INTEGER
	ACCESS read-only
	STATUS mandatory
	DESCRIPTION
		"&<caiW2kOs.388>The number of all monitored resources."
	::= { w2kStatusGeneralGroup 1 }


w2kStatusGeneralTotalWarn OBJECT-TYPE
	SYNTAX INTEGER
	ACCESS read-only
	STATUS mandatory
	DESCRIPTION
		"&<caiW2kOs.389>The number of all monitored resources in a warning status."
	::= { w2kStatusGeneralGroup 2 }


w2kStatusGeneralTotalCrit OBJECT-TYPE
	SYNTAX INTEGER
	ACCESS read-only
	STATUS mandatory
	DESCRIPTION
		"&<caiW2kOs.390>The number of all monitored resources in a critical status."
	::= { w2kStatusGeneralGroup 3 }


w2kStatusGeneralCpuCount OBJECT-TYPE
	SYNTAX INTEGER
	ACCESS read-only
	STATUS mandatory
	DESCRIPTION
		"&<caiW2kOs.391>The number of monitored processors (including the processors total value)."
	::= { w2kStatusGeneralGroup 4 }


w2kStatusGeneralCpuWarn OBJECT-TYPE
	SYNTAX INTEGER
	ACCESS read-only
	STATUS mandatory
	DESCRIPTION
		"&<caiW2kOs.392>The number of monitored processors in a warning state."
	::= { w2kStatusGeneralGroup 5 }


w2kStatusGeneralCpuCrit OBJECT-TYPE
	SYNTAX INTEGER
	ACCESS read-only
	STATUS mandatory
	DESCRIPTION
		"&<caiW2kOs.393>The number of monitored processors in a critical state."
	::= { w2kStatusGeneralGroup 6 }


w2kStatusGeneralMemCount OBJECT-TYPE
	SYNTAX INTEGER
	ACCESS read-only
	STATUS mandatory
	DESCRIPTION
		"&<caiW2kOs.394>The number of monitored memory resources."
	::= { w2kStatusGeneralGroup 7 }


w2kStatusGeneralMemWarn OBJECT-TYPE
	SYNTAX INTEGER
	ACCESS read-only
	STATUS mandatory
	DESCRIPTION
		"&<caiW2kOs.395>The number of monitored memory resources in a warning state."
	::= { w2kStatusGeneralGroup 8 }


w2kStatusGeneralMemCrit OBJECT-TYPE
	SYNTAX INTEGER
	ACCESS read-only
	STATUS mandatory
	DESCRIPTION
		"&<caiW2kOs.396>The number of monitored memory resources in a critical state."
	::= { w2kStatusGeneralGroup 9 }


w2kStatusGeneralLVolCount OBJECT-TYPE
	SYNTAX INTEGER
	ACCESS read-only
	STATUS mandatory
	DESCRIPTION
		"&<caiW2kOs.397>The number of monitored logical volumes."
	::= { w2kStatusGeneralGroup 10 }


w2kStatusGeneralLVolWarn OBJECT-TYPE
	SYNTAX INTEGER
	ACCESS read-only
	STATUS mandatory
	DESCRIPTION
		"&<caiW2kOs.398>The number of monitored logical volumes in a warning state."
	::= { w2kStatusGeneralGroup 11 }


w2kStatusGeneralLVolCrit OBJECT-TYPE
	SYNTAX INTEGER
	ACCESS read-only
	STATUS mandatory
	DESCRIPTION
		"&<caiW2kOs.399>The number of monitored logical volumes in a critical state."
	::= { w2kStatusGeneralGroup 12 }


w2kStatusGeneralMntCount OBJECT-TYPE
	SYNTAX INTEGER
	ACCESS read-only
	STATUS mandatory
	DESCRIPTION
		"&<caiW2kOs.400>The number of monitored mounts."
	::= { w2kStatusGeneralGroup 13 }


w2kStatusGeneralMntWarn OBJECT-TYPE
	SYNTAX INTEGER
	ACCESS read-only
	STATUS mandatory
	DESCRIPTION
		"&<caiW2kOs.401>The number of monitored mounts in a warning state."
	::= { w2kStatusGeneralGroup 14 }


w2kStatusGeneralMntCrit OBJECT-TYPE
	SYNTAX INTEGER
	ACCESS read-only
	STATUS mandatory
	DESCRIPTION
		"&<caiW2kOs.402>The number of monitored mounts in a critical state."
	::= { w2kStatusGeneralGroup 15 }


w2kStatusGeneralDfsCount OBJECT-TYPE
	SYNTAX INTEGER
	ACCESS read-only
	STATUS mandatory
	DESCRIPTION
		"&<caiW2kOs.403>The number of monitored distributed file system links."
	::= { w2kStatusGeneralGroup 16 }


w2kStatusGeneralDfsWarn OBJECT-TYPE
	SYNTAX INTEGER
	ACCESS read-only
	STATUS mandatory
	DESCRIPTION
		"&<caiW2kOs.404>The number of monitored distributed file system links in a warning state."
	::= { w2kStatusGeneralGroup 17 }


w2kStatusGeneralDfsCrit OBJECT-TYPE
	SYNTAX INTEGER
	ACCESS read-only
	STATUS mandatory
	DESCRIPTION
		"&<caiW2kOs.405>The number of monitored distributed file system links in a critical state."
	::= { w2kStatusGeneralGroup 18 }


w2kStatusGeneralQuotCount OBJECT-TYPE
	SYNTAX INTEGER
	ACCESS read-only
	STATUS mandatory
	DESCRIPTION
		"&<caiW2kOs.406>The number of monitored quotas."
	::= { w2kStatusGeneralGroup 19 }


w2kStatusGeneralQuotWarn OBJECT-TYPE
	SYNTAX INTEGER
	ACCESS read-only
	STATUS mandatory
	DESCRIPTION
		"&<caiW2kOs.407>The number of monitored quotas in a warning state."
	::= { w2kStatusGeneralGroup 20 }


w2kStatusGeneralQuotCrit OBJECT-TYPE
	SYNTAX INTEGER
	ACCESS read-only
	STATUS mandatory
	DESCRIPTION
		"&<caiW2kOs.408>The number of monitored quotas in a critical state."
	::= { w2kStatusGeneralGroup 21 }


w2kStatusGeneralDirCount OBJECT-TYPE
	SYNTAX INTEGER
	ACCESS read-only
	STATUS mandatory
	DESCRIPTION
		"&<caiW2kOs.409>The number of monitored directories."
	::= { w2kStatusGeneralGroup 22 }


w2kStatusGeneralDirWarn OBJECT-TYPE
	SYNTAX INTEGER
	ACCESS read-only
	STATUS mandatory
	DESCRIPTION
		"&<caiW2kOs.410>The number of monitored directories in a warning state."
	::= { w2kStatusGeneralGroup 23 }


w2kStatusGeneralDirCrit OBJECT-TYPE
	SYNTAX INTEGER
	ACCESS read-only
	STATUS mandatory
	DESCRIPTION
		"&<caiW2kOs.411>The number of monitored directories in a critical state."
	::= { w2kStatusGeneralGroup 24 }


w2kStatusGeneralFileCount OBJECT-TYPE
	SYNTAX INTEGER
	ACCESS read-only
	STATUS mandatory
	DESCRIPTION
		"&<caiW2kOs.412>The number of monitored files."
	::= { w2kStatusGeneralGroup 25 }


w2kStatusGeneralFileWarn OBJECT-TYPE
	SYNTAX INTEGER
	ACCESS read-only
	STATUS mandatory
	DESCRIPTION
		"&<caiW2kOs.413>The number of monitored files in a warning state."
	::= { w2kStatusGeneralGroup 26 }


w2kStatusGeneralFileCrit OBJECT-TYPE
	SYNTAX INTEGER
	ACCESS read-only
	STATUS mandatory
	DESCRIPTION
		"&<caiW2kOs.414>The number of monitored files in a critical state."
	::= { w2kStatusGeneralGroup 27 }


w2kStatusGeneralProcCount OBJECT-TYPE
	SYNTAX INTEGER
	ACCESS read-only
	STATUS mandatory
	DESCRIPTION
		"&<caiW2kOs.415>The number of monitored processes."
	::= { w2kStatusGeneralGroup 28 }


w2kStatusGeneralProcWarn OBJECT-TYPE
	SYNTAX INTEGER
	ACCESS read-only
	STATUS mandatory
	DESCRIPTION
		"&<caiW2kOs.416>The number of monitored processes in a warning state."
	::= { w2kStatusGeneralGroup 29 }


w2kStatusGeneralProcCrit OBJECT-TYPE
	SYNTAX INTEGER
	ACCESS read-only
	STATUS mandatory
	DESCRIPTION
		"&<caiW2kOs.417>The number of monitored processes in a critical state."
	::= { w2kStatusGeneralGroup 30 }


w2kStatusGeneralSrvcCount OBJECT-TYPE
	SYNTAX INTEGER
	ACCESS read-only
	STATUS mandatory
	DESCRIPTION
		"&<caiW2kOs.418>The number of monitored services."
	::= { w2kStatusGeneralGroup 31 }


w2kStatusGeneralSrvcWarn OBJECT-TYPE
	SYNTAX INTEGER
	ACCESS read-only
	STATUS mandatory
	DESCRIPTION
		"&<caiW2kOs.419>The number of monitored services in a warning state."
	::= { w2kStatusGeneralGroup 32 }


w2kStatusGeneralSrvcCrit OBJECT-TYPE
	SYNTAX INTEGER
	ACCESS read-only
	STATUS mandatory
	DESCRIPTION
		"&<caiW2kOs.420>The number of monitored services in a critical state."
	::= { w2kStatusGeneralGroup 33 }


w2kStatusGeneralJobCount OBJECT-TYPE
	SYNTAX INTEGER
	ACCESS read-only
	STATUS mandatory
	DESCRIPTION
		"&<caiW2kOs.421>The number of monitored jobs."
	::= { w2kStatusGeneralGroup 34 }


w2kStatusGeneralJobWarn OBJECT-TYPE
	SYNTAX INTEGER
	ACCESS read-only
	STATUS mandatory
	DESCRIPTION
		"&<caiW2kOs.422>The number of monitored jobs in a warning state."
	::= { w2kStatusGeneralGroup 35 }


w2kStatusGeneralJobCrit OBJECT-TYPE
	SYNTAX INTEGER
	ACCESS read-only
	STATUS mandatory
	DESCRIPTION
		"&<caiW2kOs.423>The number of monitored jobs in a critical state."
	::= { w2kStatusGeneralGroup 36 }


w2kStatusGeneralSessCount OBJECT-TYPE
	SYNTAX INTEGER
	ACCESS read-only
	STATUS mandatory
	DESCRIPTION
		"&<caiW2kOs.424>The number of monitored sessions."
	::= { w2kStatusGeneralGroup 37 }


w2kStatusGeneralSessWarn OBJECT-TYPE
	SYNTAX INTEGER
	ACCESS read-only
	STATUS mandatory
	DESCRIPTION
		"&<caiW2kOs.425>The number of monitored sessions in a warning state."
	::= { w2kStatusGeneralGroup 38 }


w2kStatusGeneralSessCrit OBJECT-TYPE
	SYNTAX INTEGER
	ACCESS read-only
	STATUS mandatory
	DESCRIPTION
		"&<caiW2kOs.426>The number of monitored sessions in a critical state."
	::= { w2kStatusGeneralGroup 39 }


w2kStatusGeneralPrnCount OBJECT-TYPE
	SYNTAX INTEGER
	ACCESS read-only
	STATUS mandatory
	DESCRIPTION
		"&<caiW2kOs.427>The number of monitored printers."
	::= { w2kStatusGeneralGroup 40 }


w2kStatusGeneralPrnWarn OBJECT-TYPE
	SYNTAX INTEGER
	ACCESS read-only
	STATUS mandatory
	DESCRIPTION
		"&<caiW2kOs.428>The number of monitored printers in a warning state."
	::= { w2kStatusGeneralGroup 41 }


w2kStatusGeneralPrnCrit OBJECT-TYPE
	SYNTAX INTEGER
	ACCESS read-only
	STATUS mandatory
	DESCRIPTION
		"&<caiW2kOs.429>The number of monitored printers in a critical state."
	::= { w2kStatusGeneralGroup 42 }


w2kStatusGeneralNetCount OBJECT-TYPE
	SYNTAX INTEGER
	ACCESS read-only
	STATUS mandatory
	DESCRIPTION
		"&<caiW2kOs.430>The number of monitored network interfaces (including the network interfaces total value)."
	::= { w2kStatusGeneralGroup 43 }


w2kStatusGeneralNetWarn OBJECT-TYPE
	SYNTAX INTEGER
	ACCESS read-only
	STATUS mandatory
	DESCRIPTION
		"&<caiW2kOs.431>The number of monitored network interfaces in a warning state."
	::= { w2kStatusGeneralGroup 44 }


w2kStatusGeneralNetCrit OBJECT-TYPE
	SYNTAX INTEGER
	ACCESS read-only
	STATUS mandatory
	DESCRIPTION
		"&<caiW2kOs.432>The number of monitored network interfaces in a critical state."
	::= { w2kStatusGeneralGroup 45 }


w2kStatusGeneralRegCount OBJECT-TYPE
	SYNTAX INTEGER
	ACCESS read-only
	STATUS mandatory
	DESCRIPTION
		"&<caiW2kOs.433>The number of monitored registry entries."
	::= { w2kStatusGeneralGroup 46 }


w2kStatusGeneralRegWarn OBJECT-TYPE
	SYNTAX INTEGER
	ACCESS read-only
	STATUS mandatory
	DESCRIPTION
		"&<caiW2kOs.434>The number of monitored registry entries in a warning state."
	::= { w2kStatusGeneralGroup 47 }


w2kStatusGeneralRegCrit OBJECT-TYPE
	SYNTAX INTEGER
	ACCESS read-only
	STATUS mandatory
	DESCRIPTION
		"&<caiW2kOs.435>The number of monitored registry entries in a critical state."
	::= { w2kStatusGeneralGroup 48 }




--	------------------------------------------------------------------------
--      Processor Status Group
--	------------------------------------------------------------------------


w2kStatusCpuTotalLoadValue OBJECT-TYPE
	SYNTAX INTEGER
	ACCESS read-only
	STATUS mandatory
	DESCRIPTION
		"&<caiW2kOs.436>The current total utilization of all processors (as percentage value of 100)."
	::= { w2kStatusCpuGroup 1 }


w2kStatusCpuTotalLoadLagValue OBJECT-TYPE
	SYNTAX INTEGER
	ACCESS read-only
	STATUS mandatory
	DESCRIPTION
		"&<caiW2kOs.437>The number of consecutive poll intervals that the threshold had been (b)reached."
	::= { w2kStatusCpuGroup 2 }


w2kStatusCpuTotalLoadLag OBJECT-TYPE
	SYNTAX INTEGER
	ACCESS read-write
	STATUS mandatory
	DESCRIPTION
		"&<caiW2kOs.124>The number of consecutive poll intervals that the threshold has to be (b)reached before the status changes. Valid values are greater than 0."
	DEFVAL { 3 }
	::= { w2kStatusCpuGroup 3 }


w2kStatusCpuTotalLoadWarn OBJECT-TYPE
	SYNTAX INTEGER
	ACCESS read-write
	STATUS mandatory
	DESCRIPTION
		"&<caiW2kOs.439>Warning threshold for the total utilization of all processors (as percentage value of 100). Valid values are 1 to 99 and smaller than the critical threshold."
	DEFVAL { 70 }
	::= { w2kStatusCpuGroup 4 }


w2kStatusCpuTotalLoadCrit OBJECT-TYPE
	SYNTAX INTEGER
	ACCESS read-write
	STATUS mandatory
	DESCRIPTION
		"&<caiW2kOs.440>Critical threshold for the total utilization of all processors (as percentage value of 100). Valid values are 2 to 100 and greater than the warning threshold."
	DEFVAL { 90 }
	::= { w2kStatusCpuGroup 5 }


w2kStatusCpuTotalLoadMonitor OBJECT-TYPE
	SYNTAX INTEGER {
		do-not-monitor(1),
		warning-only(2),
		critical-only(3),
		both(4)
	}
	ACCESS read-write
	STATUS mandatory
	DESCRIPTION
		"&<caiW2kOs.441>Flag indicating whether the total utilization of all processors should be monitored and if so, which threshold should be compared with."
	DEFVAL { 4 }
	::= { w2kStatusCpuGroup 6 }


w2kStatusCpuTotalLoadStatus OBJECT-TYPE
	SYNTAX INTEGER {
		unknown(1),
		ok(2),
		warning(3),
		critical(4)
	}
	ACCESS read-only
	STATUS mandatory
	DESCRIPTION
		"&<caiW2kOs.442>The current status of the total utilization of all processors as determined by the thresholds. The status 'unknown' means that the current value could not be retrieved from the system."
	::= { w2kStatusCpuGroup 7 }


w2kStatusCpuTotalCallBackRef OBJECT-TYPE
	SYNTAX DisplayString
	ACCESS read-only
	STATUS mandatory
	DESCRIPTION
		"&<caiW2kOs.443>The name of the Call-Back reference that should be invoked in case of a status change."
	::= { w2kStatusCpuGroup 8 }


w2kStatusCpuCount OBJECT-TYPE
	SYNTAX INTEGER
	ACCESS read-only
	STATUS mandatory
	DESCRIPTION
		"&<caiW2kOs.444>The number of entries in the w2kStatusCpuTable."
	::= { w2kStatusCpuGroup 9 }


w2kStatusCpuTable OBJECT-TYPE
	SYNTAX SEQUENCE OF W2kStatusCpuRow
	ACCESS not-accessible
	STATUS mandatory
	DESCRIPTION
		"&<caiW2kOs.445>A table containing information about all monitored processors."
	::= { w2kStatusCpuGroup 10 }


w2kStatusCpuEntry OBJECT-TYPE
	SYNTAX W2kStatusCpuRow
	ACCESS not-accessible
	STATUS mandatory
	DESCRIPTION
		"&<caiW2kOs.154>The table entry."
	INDEX { w2kStatusCpuName }
	::= { w2kStatusCpuTable 1 }


W2kStatusCpuRow ::=
	SEQUENCE {
		w2kStatusCpuName DisplayString,
		w2kStatusCpuType DisplayString,
		w2kStatusCpuAggStatus INTEGER,
		w2kStatusCpuLoadValue INTEGER,
		w2kStatusCpuLoadLagValue INTEGER,
		w2kStatusCpuLoadLag INTEGER,
		w2kStatusCpuLoadWarn INTEGER,
		w2kStatusCpuLoadCrit INTEGER,
		w2kStatusCpuLoadMonitor INTEGER,
		w2kStatusCpuLoadStatus INTEGER,
		w2kStatusCpuLossAction INTEGER,
		w2kStatusCpuLossStatus INTEGER,
		w2kStatusCpuCallBackRef DisplayString
	}


w2kStatusCpuName OBJECT-TYPE
	SYNTAX DisplayString
	ACCESS read-only
	STATUS mandatory
	DESCRIPTION
		"&<caiW2kOs.447>Name of the watcher, monitoring a processor with the processor identification number contained in this dummy name."
	::= { w2kStatusCpuEntry 1 }


w2kStatusCpuType OBJECT-TYPE
	SYNTAX DisplayString
	ACCESS read-only
	STATUS mandatory
	DESCRIPTION
		"&<caiW2kOs.448>The type of the processor."
	::= { w2kStatusCpuEntry 2 }


w2kStatusCpuAggStatus OBJECT-TYPE
	SYNTAX INTEGER {
		unknown(1),
		ok(2),
		warning(3),
		critical(4)
	}
	ACCESS read-only
	STATUS mandatory
	DESCRIPTION
		"&<caiW2kOs.449>The current status of the processor as a 'worst case' aggregate of all its statuses."
	::= { w2kStatusCpuEntry 3 }


w2kStatusCpuLoadValue OBJECT-TYPE
	SYNTAX INTEGER
	ACCESS read-only
	STATUS mandatory
	DESCRIPTION
		"&<caiW2kOs.450>The current processor utilization (as percentage value of 100)."
	::= { w2kStatusCpuEntry 4 }


w2kStatusCpuLoadLagValue OBJECT-TYPE
	SYNTAX INTEGER
	ACCESS read-only
	STATUS mandatory
	DESCRIPTION
		"&<caiW2kOs.437>The number of consecutive poll intervals that the threshold had been (b)reached."
	::= { w2kStatusCpuEntry 5 }


w2kStatusCpuLoadLag OBJECT-TYPE
	SYNTAX INTEGER
	ACCESS read-write
	STATUS mandatory
	DESCRIPTION
		"&<caiW2kOs.124>The number of consecutive poll intervals that the threshold has to be (b)reached before the status changes. Valid values are greater than 0."
	::= { w2kStatusCpuEntry 6 }


w2kStatusCpuLoadWarn OBJECT-TYPE
	SYNTAX INTEGER
	ACCESS read-write
	STATUS mandatory
	DESCRIPTION
		"&<caiW2kOs.125>Warning threshold for the utilization of the processor (as percentage value of 100). Valid values are 1 to 99 and smaller than the critical threshold."
	::= { w2kStatusCpuEntry 7 }


w2kStatusCpuLoadCrit OBJECT-TYPE
	SYNTAX INTEGER
	ACCESS read-write
	STATUS mandatory
	DESCRIPTION
		"&<caiW2kOs.126>Critical threshold for the utilization of the processor (as percentage value of 100). Valid values are 2 to 100 and greater than the warning threshold."
	::= { w2kStatusCpuEntry 8 }


w2kStatusCpuLoadMonitor OBJECT-TYPE
	SYNTAX INTEGER {
		do-not-monitor(1),
		warning-only(2),
		critical-only(3),
		both(4)
	}
	ACCESS read-write
	STATUS mandatory
	DESCRIPTION
		"&<caiW2kOs.127>Flag indicating whether the utilization of the processor should be monitored and if so, which threshold should be compared with."
	DEFVAL { 0 }
	::= { w2kStatusCpuEntry 9 }


w2kStatusCpuLoadStatus OBJECT-TYPE
	SYNTAX INTEGER {
		unknown(1),
		ok(2),
		warning(3),
		critical(4)
	}
	ACCESS read-only
	STATUS mandatory
	DESCRIPTION
		"&<caiW2kOs.456>The current status of the processor utilization as determined by the thresholds. The status 'unknown' means that the current value could not be retrieved from the system."
	::= { w2kStatusCpuEntry 10 }


w2kStatusCpuLossAction OBJECT-TYPE
	SYNTAX INTEGER {
		remove(1),
		up(2),
		down-warning(3),
		down-critical(4)
	}
	ACCESS read-write
	STATUS mandatory
	DESCRIPTION
		"&<caiW2kOs.128>Flag defining the severity if the loss of the processor is detected or whether to remove this watcher in that case."
	DEFVAL { 0 }
	::= { w2kStatusCpuEntry 11 }


w2kStatusCpuLossStatus OBJECT-TYPE
	SYNTAX INTEGER {
		unknown(1),
		up(2),
		down-warning(3),
		down-critical(4)
	}
	ACCESS read-only
	STATUS mandatory
	DESCRIPTION
		"&<caiW2kOs.458>The current status of the processor's loss as determined by the loss action."
	::= { w2kStatusCpuEntry 12 }


w2kStatusCpuCallBackRef OBJECT-TYPE
	SYNTAX DisplayString
	ACCESS read-only
	STATUS mandatory
	DESCRIPTION
		"&<caiW2kOs.443>The name of the Call-Back reference that should be invoked in case of a status change."
	::= { w2kStatusCpuEntry 13 }




--	------------------------------------------------------------------------
--      Memory Status Group
--	------------------------------------------------------------------------


w2kStatusMemVirtTotal OBJECT-TYPE
	SYNTAX INTEGER
	ACCESS read-only
	STATUS mandatory
	DESCRIPTION
		"&<caiW2kOs.460>The total size of the virtual memory on the system that can be committed (in kilobytes). The virtual memory comprises the physical and the paging memory."
	::= { w2kStatusMemGroup 1 }


w2kStatusMemVirtValue OBJECT-TYPE
	SYNTAX INTEGER
	ACCESS read-only
	STATUS mandatory
	DESCRIPTION
		"&<caiW2kOs.461>The size of the currently committed virtual memory (in kilobytes)."
	::= { w2kStatusMemGroup 2 }


w2kStatusMemVirtLagValue OBJECT-TYPE
	SYNTAX INTEGER
	ACCESS read-only
	STATUS mandatory
	DESCRIPTION
		"&<caiW2kOs.437>The number of consecutive poll intervals that the threshold had been (b)reached."
	::= { w2kStatusMemGroup 3 }


w2kStatusMemVirtLag OBJECT-TYPE
	SYNTAX INTEGER
	ACCESS read-write
	STATUS mandatory
	DESCRIPTION
		"&<caiW2kOs.124>The number of consecutive poll intervals that the threshold has to be (b)reached before the status changes. Valid values are greater than 0."
	DEFVAL { 3 }
	::= { w2kStatusMemGroup 4 }


w2kStatusMemVirtWarnValue OBJECT-TYPE
	SYNTAX INTEGER
	ACCESS read-only
	STATUS mandatory
	DESCRIPTION
		"&<caiW2kOs.464>The actual warning threshold in committed kilobytes derived from the configured warning threshold."
	::= { w2kStatusMemGroup 5 }


w2kStatusMemVirtCritValue OBJECT-TYPE
	SYNTAX INTEGER
	ACCESS read-only
	STATUS mandatory
	DESCRIPTION
		"&<caiW2kOs.465>The actual critical threshold in committed kilobytes derived from the configured critical threshold."
	::= { w2kStatusMemGroup 6 }


w2kStatusMemVirtWarn OBJECT-TYPE
	SYNTAX DisplayString
	ACCESS read-write
	STATUS mandatory
	DESCRIPTION
		"&<caiW2kOs.466>Warning threshold in kilobytes, either for the free (by appending a 'F') or for the committed virtual memory. The committed value can also be defined as a percentage value of the total size (by appending a '%'). Valid values are greater than 0 and smaller (in case of 'free' greater) critical threshold."
	DEFVAL { "70%" }
	::= { w2kStatusMemGroup 7 }


w2kStatusMemVirtCrit OBJECT-TYPE
	SYNTAX DisplayString
	ACCESS read-write
	STATUS mandatory
	DESCRIPTION
		"&<caiW2kOs.467>Critical threshold in kilobytes, either for the free (by appending a 'F') or for the committed virtual memory. The committed value can also be defined as a percentage value of the total size (by appending a '%'). Valid values are greater than 1 and greater (in case of 'free' smaller) warning threshold."
	DEFVAL { "90%" }
	::= { w2kStatusMemGroup 8 }


w2kStatusMemVirtMonitor OBJECT-TYPE
	SYNTAX INTEGER {
		do-not-monitor(1),
		warning-only(2),
		critical-only(3),
		both(4)
	}
	ACCESS read-write
	STATUS mandatory
	DESCRIPTION
		"&<caiW2kOs.468>Flag indicating whether the virtual memory should be monitored and if so, which threshold should be compared with."
	DEFVAL { 4 }
	::= { w2kStatusMemGroup 9 }


w2kStatusMemVirtStatus OBJECT-TYPE
	SYNTAX INTEGER {
		unknown(1),
		ok(2),
		warning(3),
		critical(4)
	}
	ACCESS read-only
	STATUS mandatory
	DESCRIPTION
		"&<caiW2kOs.469>The current status of the virtual memory as determined by the thresholds. The status 'unknown' means that the current value could not be retrieved from the system."
	::= { w2kStatusMemGroup 10 }


w2kStatusMemPhysTotal OBJECT-TYPE
	SYNTAX INTEGER
	ACCESS read-only
	STATUS mandatory
	DESCRIPTION
		"&<caiW2kOs.470>The total size of the physical memory on the system (in kilobytes)."
	::= { w2kStatusMemGroup 11 }


w2kStatusMemPhysValue OBJECT-TYPE
	SYNTAX INTEGER
	ACCESS read-only
	STATUS mandatory
	DESCRIPTION
		"&<caiW2kOs.471>The size of the currently used physical memory (in kilobytes)."
	::= { w2kStatusMemGroup 12 }


w2kStatusMemPhysLagValue OBJECT-TYPE
	SYNTAX INTEGER
	ACCESS read-only
	STATUS mandatory
	DESCRIPTION
		"&<caiW2kOs.437>The number of consecutive poll intervals that the threshold had been (b)reached."
	::= { w2kStatusMemGroup 13 }


w2kStatusMemPhysLag OBJECT-TYPE
	SYNTAX INTEGER
	ACCESS read-write
	STATUS mandatory
	DESCRIPTION
		"&<caiW2kOs.124>The number of consecutive poll intervals that the threshold has to be (b)reached before the status changes. Valid values are greater than 0."
	DEFVAL { 3 }
	::= { w2kStatusMemGroup 14 }


w2kStatusMemPhysWarnValue OBJECT-TYPE
	SYNTAX INTEGER
	ACCESS read-only
	STATUS mandatory
	DESCRIPTION
		"&<caiW2kOs.474>The actual warning threshold in used kilobytes derived from the configured warning threshold."
	::= { w2kStatusMemGroup 15 }


w2kStatusMemPhysCritValue OBJECT-TYPE
	SYNTAX INTEGER
	ACCESS read-only
	STATUS mandatory
	DESCRIPTION
		"&<caiW2kOs.475>The actual critical threshold in used kilobytes derived from the configured critical threshold."
	::= { w2kStatusMemGroup 16 }


w2kStatusMemPhysWarn OBJECT-TYPE
	SYNTAX DisplayString
	ACCESS read-write
	STATUS mandatory
	DESCRIPTION
		"&<caiW2kOs.476>Warning threshold in kilobytes, either for the free (by appending a 'F') or for the used physical memory. The used value can also be defined as a percentage value of the total size (by appending a '%'). Valid values are greater than 0 and smaller (in case of 'free' greater) critical threshold."
	DEFVAL { "70%" }
	::= { w2kStatusMemGroup 17 }


w2kStatusMemPhysCrit OBJECT-TYPE
	SYNTAX DisplayString
	ACCESS read-write
	STATUS mandatory
	DESCRIPTION
		"&<caiW2kOs.477>Critical threshold in kilobytes, either for the free (by appending a 'F') or for the used physical memory. The used value can also be defined as a percentage value of the total size (by appending a '%'). Valid values are greater than 1 and greater (in case of 'free' smaller) warning threshold."
	DEFVAL { "90%" }
	::= { w2kStatusMemGroup 18 }


w2kStatusMemPhysMonitor OBJECT-TYPE
	SYNTAX INTEGER {
		do-not-monitor(1),
		warning-only(2),
		critical-only(3),
		both(4)
	}
	ACCESS read-write
	STATUS mandatory
	DESCRIPTION
		"&<caiW2kOs.478>Flag indicating whether the physical memory should be monitored and if so, which threshold should be compared with."
	DEFVAL { 4 }
	::= { w2kStatusMemGroup 19 }


w2kStatusMemPhysStatus OBJECT-TYPE
	SYNTAX INTEGER {
		unknown(1),
		ok(2),
		warning(3),
		critical(4)
	}
	ACCESS read-only
	STATUS mandatory
	DESCRIPTION
		"&<caiW2kOs.479>The current status of the physical memory as determined by the thresholds. The status 'unknown' means that the current value could not be retrieved from the system."
	::= { w2kStatusMemGroup 20 }


w2kStatusMemPageTotal OBJECT-TYPE
	SYNTAX INTEGER
	ACCESS read-only
	STATUS mandatory
	DESCRIPTION
		"&<caiW2kOs.480>The total size of the paging memory on the system (in kilobytes)."
	::= { w2kStatusMemGroup 21 }


w2kStatusMemPageValue OBJECT-TYPE
	SYNTAX INTEGER
	ACCESS read-only
	STATUS mandatory
	DESCRIPTION
		"&<caiW2kOs.481>The size of the currently used paging memory (in kilobytes)."
	::= { w2kStatusMemGroup 22 }


w2kStatusMemPageLagValue OBJECT-TYPE
	SYNTAX INTEGER
	ACCESS read-only
	STATUS mandatory
	DESCRIPTION
		"&<caiW2kOs.437>The number of consecutive poll intervals that the threshold had been (b)reached."
	::= { w2kStatusMemGroup 23 }


w2kStatusMemPageLag OBJECT-TYPE
	SYNTAX INTEGER
	ACCESS read-write
	STATUS mandatory
	DESCRIPTION
		"&<caiW2kOs.124>The number of consecutive poll intervals that the threshold has to be (b)reached before the status changes. Valid values are greater than 0."
	DEFVAL { 3 }
	::= { w2kStatusMemGroup 24 }


w2kStatusMemPageWarnValue OBJECT-TYPE
	SYNTAX INTEGER
	ACCESS read-only
	STATUS mandatory
	DESCRIPTION
		"&<caiW2kOs.474>The actual warning threshold in used kilobytes derived from the configured warning threshold."
	::= { w2kStatusMemGroup 25 }


w2kStatusMemPageCritValue OBJECT-TYPE
	SYNTAX INTEGER
	ACCESS read-only
	STATUS mandatory
	DESCRIPTION
		"&<caiW2kOs.475>The actual critical threshold in used kilobytes derived from the configured critical threshold."
	::= { w2kStatusMemGroup 26 }


w2kStatusMemPageWarn OBJECT-TYPE
	SYNTAX DisplayString
	ACCESS read-write
	STATUS mandatory
	DESCRIPTION
		"&<caiW2kOs.486>Warning threshold in kilobytes, either for the free (by appending a 'F') or for the used paging memory. The used value can also be defined as a percentage value of the total size (by appending a '%'). Valid values are greater than 0 and smaller (in case of 'free' greater) critical threshold."
	DEFVAL { "70%" }
	::= { w2kStatusMemGroup 27 }


w2kStatusMemPageCrit OBJECT-TYPE
	SYNTAX DisplayString
	ACCESS read-write
	STATUS mandatory
	DESCRIPTION
		"&<caiW2kOs.487>Critical threshold in kilobytes, either for the free (by appending a 'F') or for the used paging memory. The used value can also be defined as a percentage value of the total size (by appending a '%'). Valid values are greater than 1 and greater (in case of 'free' smaller) warning threshold."
	DEFVAL { "90%" }
	::= { w2kStatusMemGroup 28 }


w2kStatusMemPageMonitor OBJECT-TYPE
	SYNTAX INTEGER {
		do-not-monitor(1),
		warning-only(2),
		critical-only(3),
		both(4)
	}
	ACCESS read-write
	STATUS mandatory
	DESCRIPTION
		"&<caiW2kOs.488>Flag indicating whether the paging memory should be monitored and if so, which threshold should be compared with."
	DEFVAL { 4 }
	::= { w2kStatusMemGroup 29 }


w2kStatusMemPageStatus OBJECT-TYPE
	SYNTAX INTEGER {
		unknown(1),
		ok(2),
		warning(3),
		critical(4)
	}
	ACCESS read-only
	STATUS mandatory
	DESCRIPTION
		"&<caiW2kOs.489>The current status of the paging memory as determined by the thresholds. The status 'unknown' means that the current value could not be retrieved from the system."
	::= { w2kStatusMemGroup 30 }


w2kStatusMemCallBackRef OBJECT-TYPE
	SYNTAX DisplayString
	ACCESS read-only
	STATUS mandatory
	DESCRIPTION
		"&<caiW2kOs.443>The name of the Call-Back reference that should be invoked in case of a status change."
	::= { w2kStatusMemGroup 31 }




--	------------------------------------------------------------------------
--      Logical Volumes Status Group
--	------------------------------------------------------------------------


w2kStatusLVolCount OBJECT-TYPE
	SYNTAX INTEGER
	ACCESS read-only
	STATUS mandatory
	DESCRIPTION
		"&<caiW2kOs.491>The number of entries in the w2kStatusLVolTable."
	::= { w2kStatusLVolGroup 1 }


w2kStatusLVolTable OBJECT-TYPE
	SYNTAX SEQUENCE OF W2kStatusLVolRow
	ACCESS not-accessible
	STATUS mandatory
	DESCRIPTION
		"&<caiW2kOs.492>A table containing information about all monitored logical volumes."
	::= { w2kStatusLVolGroup 2 }


w2kStatusLVolEntry OBJECT-TYPE
	SYNTAX W2kStatusLVolRow
	ACCESS not-accessible
	STATUS mandatory
	DESCRIPTION
		"&<caiW2kOs.154>The table entry."
	INDEX { w2kStatusLVolName }
	::= { w2kStatusLVolTable 1 }


W2kStatusLVolRow ::=
	SEQUENCE {
		w2kStatusLVolName DisplayString,
		w2kStatusLVolDescription DisplayString,
		w2kStatusLVolMounts DisplayString,
		w2kStatusLVolInfo DisplayString,
		w2kStatusLVolAutoWatcherName DisplayString,
		w2kStatusLVolAggLagValue INTEGER,
		w2kStatusLVolAggLag INTEGER,
		w2kStatusLVolAggStatus INTEGER,
		w2kStatusLVolSizeTotal INTEGER,
		w2kStatusLVolSizeValue INTEGER,
		w2kStatusLVolSizeWarnValue INTEGER,
		w2kStatusLVolSizeCritValue INTEGER,
		w2kStatusLVolSizeWarn DisplayString,
		w2kStatusLVolSizeCrit DisplayString,
		w2kStatusLVolSizeMonitor INTEGER,
		w2kStatusLVolSizeStatus INTEGER,
		w2kStatusLVolSizeDValue INTEGER,
		w2kStatusLVolSizeDWarnValue DisplayString,
		w2kStatusLVolSizeDCritValue DisplayString,
		w2kStatusLVolSizeDWarn DisplayString,
		w2kStatusLVolSizeDCrit DisplayString,
		w2kStatusLVolSizeDMonitor INTEGER,
		w2kStatusLVolSizeDStatus INTEGER,
		w2kStatusLVolTPutValue INTEGER,
		w2kStatusLVolTPutWarn INTEGER,
		w2kStatusLVolTPutCrit INTEGER,
		w2kStatusLVolTPutMonitor INTEGER,
		w2kStatusLVolTPutStatus INTEGER,
		w2kStatusLVolFragValue INTEGER,
		w2kStatusLVolFragWarn INTEGER,
		w2kStatusLVolFragCrit INTEGER,
		w2kStatusLVolFragMonitor INTEGER,
		w2kStatusLVolFragStatus INTEGER,
		w2kStatusLVolLossAction INTEGER,
		w2kStatusLVolLossStatus INTEGER,
		w2kStatusLVolCallBackRef DisplayString,
		w2kStatusLVolButton INTEGER
	}


w2kStatusLVolName OBJECT-TYPE
	SYNTAX DisplayString
	ACCESS read-only
	STATUS mandatory
	DESCRIPTION
		"&<caiW2kOs.494>Name of the watcher, monitoring a logical volume with this name. Important: This name is case insensitive."
	::= { w2kStatusLVolEntry 1 }


w2kStatusLVolDescription OBJECT-TYPE
	SYNTAX DisplayString
	ACCESS read-write
	STATUS mandatory
	DESCRIPTION
		"&<caiW2kOs.136>Any description for this watcher."
	::= { w2kStatusLVolEntry 2 }


w2kStatusLVolMounts OBJECT-TYPE
	SYNTAX DisplayString
	ACCESS read-only
	STATUS mandatory
	DESCRIPTION
		"&<caiW2kOs.496>A list of the mount points, where this logical volume is mounted on."
	::= { w2kStatusLVolEntry 3 }


w2kStatusLVolInfo OBJECT-TYPE
	SYNTAX DisplayString
	ACCESS read-only
	STATUS mandatory
	DESCRIPTION
		"&<caiW2kOs.497>Information about the format (e.g. NTFS), the alternate name (e.g. used in PerfMon) and the label of the logical volume. The alternate name may be empty. The single values are delimited by a pipe sign."
	::= { w2kStatusLVolEntry 4 }


w2kStatusLVolAutoWatcherName OBJECT-TYPE
	SYNTAX DisplayString
	ACCESS read-only
	STATUS mandatory
	DESCRIPTION
		"&<caiW2kOs.498>Name of the auto discovery watcher, which created this watcher."
	::= { w2kStatusLVolEntry 5 }


w2kStatusLVolAggLagValue OBJECT-TYPE
	SYNTAX INTEGER
	ACCESS read-only
	STATUS mandatory
	DESCRIPTION
		"&<caiW2kOs.499>The number of consecutive poll intervals on which any status was not in the Ok or Up state."
	::= { w2kStatusLVolEntry 6 }


w2kStatusLVolAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusLVolEntry 7 }


w2kStatusLVolAggStatus OBJECT-TYPE
	SYNTAX INTEGER {
		unknown(1),
		ok(2),
		warning(3),
		critical(4)
	}
	ACCESS read-only
	STATUS mandatory
	DESCRIPTION
		"&<caiW2kOs.501>The current status of the logical volume as a 'worst case' aggregate of all its statuses."
	::= { w2kStatusLVolEntry 8 }


w2kStatusLVolSizeTotal OBJECT-TYPE
	SYNTAX INTEGER
	ACCESS read-only
	STATUS mandatory
	DESCRIPTION
		"&<caiW2kOs.502>The total size of the logical volume (in megabytes)."
	::= { w2kStatusLVolEntry 9 }


w2kStatusLVolSizeValue OBJECT-TYPE
	SYNTAX INTEGER
	ACCESS read-only
	STATUS mandatory
	DESCRIPTION
		"&<caiW2kOs.503>The current value of the used logical volume size (in megabytes)."
	::= { w2kStatusLVolEntry 10 }


w2kStatusLVolSizeWarnValue OBJECT-TYPE
	SYNTAX INTEGER
	ACCESS read-only
	STATUS mandatory
	DESCRIPTION
		"&<caiW2kOs.504>The actual warning threshold in used megabytes derived from the configured warning threshold."
	::= { w2kStatusLVolEntry 11 }


w2kStatusLVolSizeCritValue OBJECT-TYPE
	SYNTAX INTEGER
	ACCESS read-only
	STATUS mandatory
	DESCRIPTION
		"&<caiW2kOs.505>The actual critical threshold in used megabytes derived from the configured critical threshold."
	::= { w2kStatusLVolEntry 12 }


w2kStatusLVolSizeWarn OBJECT-TYPE
	SYNTAX DisplayString
	ACCESS read-write
	STATUS mandatory
	DESCRIPTION
		"&<caiW2kOs.138>Warning threshold in megabytes, either for the free (by appending a 'F') or for the used logical volume size. The used size can also be defined as a percentage value of the total logical volume size (by appending a '%'). Valid values are greater than 0 and smaller (in case of 'free' greater) than the critical threshold."
	::= { w2kStatusLVolEntry 13 }


w2kStatusLVolSizeCrit OBJECT-TYPE
	SYNTAX DisplayString
	ACCESS read-write
	STATUS mandatory
	DESCRIPTION
		"&<caiW2kOs.139>Critical threshold in megabytes, either for the free (by appending a 'F') or for the used logical volume size. The used size can also be defined as a percentage value of the total logical volume size (by appending a '%'). Valid values are greater than 1 and greater (in case of 'free' smaller) than the warning threshold."
	::= { w2kStatusLVolEntry 14 }


w2kStatusLVolSizeMonitor OBJECT-TYPE
	SYNTAX INTEGER {
		do-not-monitor(1),
		warning-only(2),
		critical-only(3),
		both(4)
	}
	ACCESS read-write
	STATUS mandatory
	DESCRIPTION
		"&<caiW2kOs.140>Flag indicating whether the used logical volume size should be monitored and if so, which threshold should be compared with."
	DEFVAL { 0 }
	::= { w2kStatusLVolEntry 15 }


w2kStatusLVolSizeStatus OBJECT-TYPE
	SYNTAX INTEGER {
		unknown(1),
		ok(2),
		warning(3),
		critical(4)
	}
	ACCESS read-only
	STATUS mandatory
	DESCRIPTION
		"&<caiW2kOs.509>The current status of the used logical volume size as determined by the thresholds. The status 'unknown' means that the current value could not be retrieved from the system."
	::= { w2kStatusLVolEntry 16 }


w2kStatusLVolSizeDValue OBJECT-TYPE
	SYNTAX INTEGER
	ACCESS read-only
	STATUS mandatory
	DESCRIPTION
		"&<caiW2kOs.510>The current value of the delta in used logical volume size monitored in the last polling interval (in megabytes). In case of shrinkage this is a negative number."
	::= { w2kStatusLVolEntry 17 }


w2kStatusLVolSizeDWarnValue OBJECT-TYPE
	SYNTAX DisplayString
	ACCESS read-only
	STATUS mandatory
	DESCRIPTION
		"&<caiW2kOs.511>The actual warning threshold in megabytes derived from the configured warning threshold."
	::= { w2kStatusLVolEntry 18 }


w2kStatusLVolSizeDCritValue OBJECT-TYPE
	SYNTAX DisplayString
	ACCESS read-only
	STATUS mandatory
	DESCRIPTION
		"&<caiW2kOs.512>The actual critical threshold in megabytes derived from the configured critical threshold."
	::= { w2kStatusLVolEntry 19 }


w2kStatusLVolSizeDWarn OBJECT-TYPE
	SYNTAX DisplayString
	ACCESS read-write
	STATUS mandatory
	DESCRIPTION
		"&<caiW2kOs.141>Warning threshold, either for the growth (by appending a '+') or for the shrinkage (by appending a '-') or for the absolute delta in used logical volume size monitored in one poll interval. Growth, shrinkage and absolute delta can be given in megabytes or as a percentage value of the total logical volume size (by appending a '%'). Valid values are greater than 0 and smaller than the critical threshold."
	::= { w2kStatusLVolEntry 20 }


w2kStatusLVolSizeDCrit OBJECT-TYPE
	SYNTAX DisplayString
	ACCESS read-write
	STATUS mandatory
	DESCRIPTION
		"&<caiW2kOs.142>Critical threshold, either for the growth (by appending a '+') or for the shrinkage (by appending a '-') or for the absolute delta in used logical volume size monitored in one poll interval. Growth, shrinkage and absolute delta can be given in megabytes or as a percentage value of the total logical volume size (by appending a '%'). Valid values are greater than 1 and greater than the warning threshold."
	::= { w2kStatusLVolEntry 21 }


w2kStatusLVolSizeDMonitor OBJECT-TYPE
	SYNTAX INTEGER {
		do-not-monitor(1),
		warning-only(2),
		critical-only(3),
		both(4)
	}
	ACCESS read-write
	STATUS mandatory
	DESCRIPTION
		"&<caiW2kOs.143>Flag indicating whether the delta in used logical volume size should be monitored and if so, which threshold should be compared with."
	DEFVAL { 0 }
	::= { w2kStatusLVolEntry 22 }


w2kStatusLVolSizeDStatus OBJECT-TYPE
	SYNTAX INTEGER {
		unknown(1),
		ok(2),
		warning(3),
		critical(4)
	}
	ACCESS read-only
	STATUS mandatory
	DESCRIPTION
		"&<caiW2kOs.516>The current status of delta in used logical volume size as determined by the thresholds. The status 'unknown' means that the current value could not be retrieved from the system."
	::= { w2kStatusLVolEntry 23 }


w2kStatusLVolTPutValue OBJECT-TYPE
	SYNTAX INTEGER
	ACCESS read-only
	STATUS mandatory
	DESCRIPTION
		"&<caiW2kOs.517>The current value of the throughput rate (kilobytes per second)."
	::= { w2kStatusLVolEntry 24 }


w2kStatusLVolTPutWarn OBJECT-TYPE
	SYNTAX INTEGER
	ACCESS read-write
	STATUS mandatory
	DESCRIPTION
		"&<caiW2kOs.144>Warning threshold for the throughput rate (kilobytes per second). Valid values are greater than 0 and smaller than the critical threshold."
	::= { w2kStatusLVolEntry 25 }


w2kStatusLVolTPutCrit OBJECT-TYPE
	SYNTAX INTEGER
	ACCESS read-write
	STATUS mandatory
	DESCRIPTION
		"&<caiW2kOs.145>Critical threshold for the throughput rate (kilobytes per second). Valid values are greater than 1 and greater than the warning threshold."
	::= { w2kStatusLVolEntry 26 }


w2kStatusLVolTPutMonitor OBJECT-TYPE
	SYNTAX INTEGER {
		do-not-monitor(1),
		warning-only(2),
		critical-only(3),
		both(4)
	}
	ACCESS read-write
	STATUS mandatory
	DESCRIPTION
		"&<caiW2kOs.146>Flag indicating whether the throughput rate should be monitored and if so, which threshold should be compared with."
	DEFVAL { 0 }
	::= { w2kStatusLVolEntry 27 }


w2kStatusLVolTPutStatus OBJECT-TYPE
	SYNTAX INTEGER {
		unknown(1),
		ok(2),
		warning(3),
		critical(4)
	}
	ACCESS read-only
	STATUS mandatory
	DESCRIPTION
		"&<caiW2kOs.521>The current status of the throughput rate as determined by the thresholds. The status 'unknown' means that the current value could not be retrieved from the system."
	::= { w2kStatusLVolEntry 28 }


w2kStatusLVolFragValue OBJECT-TYPE
	SYNTAX INTEGER
	ACCESS read-only
	STATUS mandatory
	DESCRIPTION
		"&<caiW2kOs.522>The current value of the file fragmentation (as percentage value of 100)."
	::= { w2kStatusLVolEntry 29 }


w2kStatusLVolFragWarn OBJECT-TYPE
	SYNTAX INTEGER
	ACCESS read-write
	STATUS mandatory
	DESCRIPTION
		"&<caiW2kOs.147>Warning threshold for the file fragmentation (as percentage value of 100). Valid values are 1 to 99 and smaller than the critical threshold."
	::= { w2kStatusLVolEntry 30 }


w2kStatusLVolFragCrit OBJECT-TYPE
	SYNTAX INTEGER
	ACCESS read-write
	STATUS mandatory
	DESCRIPTION
		"&<caiW2kOs.148>Critical threshold for the file fragmentation (as percentage value of 100). Valid values are 2 to 100 and greater than the warning threshold."
	::= { w2kStatusLVolEntry 31 }


w2kStatusLVolFragMonitor OBJECT-TYPE
	SYNTAX INTEGER {
		do-not-monitor(1),
		warning-only(2),
		critical-only(3),
		both(4)
	}
	ACCESS read-write
	STATUS mandatory
	DESCRIPTION
		"&<caiW2kOs.149>Flag indicating whether the file fragmentation should be monitored and if so, which threshold should be compared with."
	DEFVAL { 0 }
	::= { w2kStatusLVolEntry 32 }


w2kStatusLVolFragStatus OBJECT-TYPE
	SYNTAX INTEGER {
		unknown(1),
		ok(2),
		warning(3),
		critical(4)
	}
	ACCESS read-only
	STATUS mandatory
	DESCRIPTION
		"&<caiW2kOs.526>The current status of the file fragmentation as determined by the thresholds. The status 'unknown' means that the current value could not be retrieved from the system."
	::= { w2kStatusLVolEntry 33 }


w2kStatusLVolLossAction OBJECT-TYPE
	SYNTAX INTEGER {
		remove(1),
		up(2),
		down-warning(3),
		down-critical(4)
	}
	ACCESS read-write
	STATUS mandatory
	DESCRIPTION
		"&<caiW2kOs.150>Flag defining the severity if the loss of the logical volume is detected or whether to remove this watcher in that case."
	DEFVAL { 0 }
	::= { w2kStatusLVolEntry 34 }


w2kStatusLVolLossStatus OBJECT-TYPE
	SYNTAX INTEGER {
		unknown(1),
		up(2),
		down-warning(3),
		down-critical(4)
	}
	ACCESS read-only
	STATUS mandatory
	DESCRIPTION
		"&<caiW2kOs.528>The current status of the logical volume's loss as determined by the loss action."
	::= { w2kStatusLVolEntry 35 }


w2kStatusLVolCallBackRef OBJECT-TYPE
	SYNTAX DisplayString
	ACCESS read-only
	STATUS mandatory
	DESCRIPTION
		"&<caiW2kOs.443>The name of the Call-Back reference that should be invoked in case of a status change."
	::= { w2kStatusLVolEntry 36 }


w2kStatusLVolButton OBJECT-TYPE
	SYNTAX INTEGER {
		none(1),
		remove(2)
	}
	ACCESS read-write
	STATUS mandatory
	DESCRIPTION
		"&<caiW2kOs.530>This attribute is used to remove this watcher."
	::= { w2kStatusLVolEntry 37 }




--	------------------------------------------------------------------------
--      Mounts Status Group
--	------------------------------------------------------------------------


w2kStatusMntCount OBJECT-TYPE
	SYNTAX INTEGER
	ACCESS read-only
	STATUS mandatory
	DESCRIPTION
		"&<caiW2kOs.531>The number of entries in the w2kStatusMntTable."
	::= { w2kStatusMntGroup 1 }


w2kStatusMntTable OBJECT-TYPE
	SYNTAX SEQUENCE OF W2kStatusMntRow
	ACCESS not-accessible
	STATUS mandatory
	DESCRIPTION
		"&<caiW2kOs.532>A table containing information about all monitored mounts."
	::= { w2kStatusMntGroup 2 }


w2kStatusMntEntry OBJECT-TYPE
	SYNTAX W2kStatusMntRow
	ACCESS not-accessible
	STATUS mandatory
	DESCRIPTION
		"&<caiW2kOs.154>The table entry."
	INDEX { w2kStatusMntName }
	::= { w2kStatusMntTable 1 }


W2kStatusMntRow ::=
	SEQUENCE {
		w2kStatusMntName DisplayString,
		w2kStatusMntDescription DisplayString,
		w2kStatusMntAutoWatcherName DisplayString,
		w2kStatusMntAggLagValue INTEGER,
		w2kStatusMntAggLag INTEGER,
		w2kStatusMntAggStatus INTEGER,
		w2kStatusMntRelToValue DisplayString,
		w2kStatusMntRelToRef DisplayString,
		w2kStatusMntRelToMonitor INTEGER,
		w2kStatusMntRelToStatus INTEGER,
		w2kStatusMntLossAction INTEGER,
		w2kStatusMntLossStatus INTEGER,
		w2kStatusMntCallBackRef DisplayString,
		w2kStatusMntButton INTEGER
	}


w2kStatusMntName OBJECT-TYPE
	SYNTAX DisplayString
	ACCESS read-only
	STATUS mandatory
	DESCRIPTION
		"&<caiW2kOs.534>Name of the watcher, monitoring a mount with this name. Important: This name is case insensitive."
	::= { w2kStatusMntEntry 1 }


w2kStatusMntDescription OBJECT-TYPE
	SYNTAX DisplayString
	ACCESS read-write
	STATUS mandatory
	DESCRIPTION
		"&<caiW2kOs.136>Any description for this watcher."
	::= { w2kStatusMntEntry 2 }


w2kStatusMntAutoWatcherName OBJECT-TYPE
	SYNTAX DisplayString
	ACCESS read-only
	STATUS mandatory
	DESCRIPTION
		"&<caiW2kOs.498>Name of the auto discovery watcher, which created this watcher."
	::= { w2kStatusMntEntry 3 }


w2kStatusMntAggLagValue OBJECT-TYPE
	SYNTAX INTEGER
	ACCESS read-only
	STATUS mandatory
	DESCRIPTION
		"&<caiW2kOs.499>The number of consecutive poll intervals on which any status was not in the Ok or Up state."
	::= { w2kStatusMntEntry 4 }


w2kStatusMntAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusMntEntry 5 }


w2kStatusMntAggStatus OBJECT-TYPE
	SYNTAX INTEGER {
		unknown(1),
		ok(2),
		warning(3),
		critical(4)
	}
	ACCESS read-only
	STATUS mandatory
	DESCRIPTION
		"&<caiW2kOs.539>The current status of the mount as a 'worst case' aggregate of all its statuses."
	::= { w2kStatusMntEntry 6 }


w2kStatusMntRelToValue OBJECT-TYPE
	SYNTAX DisplayString
	ACCESS read-only
	STATUS mandatory
	DESCRIPTION
		"&<caiW2kOs.540>The name of the current logical volume, which this mount is mounting."
	::= { w2kStatusMntEntry 7 }


w2kStatusMntRelToRef OBJECT-TYPE
	SYNTAX DisplayString
	ACCESS read-only
	STATUS mandatory
	DESCRIPTION
		"&<caiW2kOs.541>The reference name, which is the name of the logical volume, mounted by this mount when this watcher was created or when the last 'reset-relTo' has been made."
	::= { w2kStatusMntEntry 8 }


w2kStatusMntRelToMonitor OBJECT-TYPE
	SYNTAX INTEGER {
		do-not-monitor(1),
		down-warning(2),
		down-critical(3)
	}
	ACCESS read-write
	STATUS mandatory
	DESCRIPTION
		"&<caiW2kOs.179>Flag indicating whether a change of the logical volume, mounted by this mount, should be monitored and if so, the level of alert to raise. Note: A change will not occur if the related logical volume is lossed. In that case the mount itself becomes lossed."
	DEFVAL { 0 }
	::= { w2kStatusMntEntry 9 }


w2kStatusMntRelToStatus OBJECT-TYPE
	SYNTAX INTEGER {
		unknown(1),
		up(2),
		down-warning(3),
		down-critical(4)
	}
	ACCESS read-only
	STATUS mandatory
	DESCRIPTION
		"&<caiW2kOs.543>The current status of the mount's relation. The status 'unknown' means that the current value could not be retrieved from the system."
	::= { w2kStatusMntEntry 10 }


w2kStatusMntLossAction OBJECT-TYPE
	SYNTAX INTEGER {
		remove(1),
		up(2),
		down-warning(3),
		down-critical(4)
	}
	ACCESS read-write
	STATUS mandatory
	DESCRIPTION
		"&<caiW2kOs.180>Flag defining the severity if the loss of the mount is detected or whether to remove this watcher in that case."
	DEFVAL { 0 }
	::= { w2kStatusMntEntry 11 }


w2kStatusMntLossStatus OBJECT-TYPE
	SYNTAX INTEGER {
		unknown(1),
		up(2),
		down-warning(3),
		down-critical(4)
	}
	ACCESS read-only
	STATUS mandatory
	DESCRIPTION
		"&<caiW2kOs.545>The current status of the mount's loss as determined by the loss action."
	::= { w2kStatusMntEntry 12 }


w2kStatusMntCallBackRef OBJECT-TYPE
	SYNTAX DisplayString
	ACCESS read-only
	STATUS mandatory
	DESCRIPTION
		"&<caiW2kOs.443>The name of the Call-Back reference that should be invoked in case of a status change."
	::= { w2kStatusMntEntry 13 }


w2kStatusMntButton OBJECT-TYPE
	SYNTAX INTEGER {
		none(1),
		remove(2),
		reset-relTo(3)
	}
	ACCESS read-write
	STATUS mandatory
	DESCRIPTION
		"&<caiW2kOs.547>This attribute is used to remove this watcher or to reset the 'related to' reference to the current value of the mount."
	::= { w2kStatusMntEntry 14 }




--	------------------------------------------------------------------------
--      Distributed File Systems Status Group
--	------------------------------------------------------------------------


w2kStatusDfsCount OBJECT-TYPE
	SYNTAX INTEGER
	ACCESS read-only
	STATUS mandatory
	DESCRIPTION
		"&<caiW2kOs.548>The number of entries in the w2kStatusDfsTable."
	::= { w2kStatusDfsGroup 1 }


w2kStatusDfsTable OBJECT-TYPE
	SYNTAX SEQUENCE OF W2kStatusDfsRow
	ACCESS not-accessible
	STATUS mandatory
	DESCRIPTION
		"&<caiW2kOs.549>A table containing information about all monitored distributed file system links."
	::= { w2kStatusDfsGroup 2 }


w2kStatusDfsEntry OBJECT-TYPE
	SYNTAX W2kStatusDfsRow
	ACCESS not-accessible
	STATUS mandatory
	DESCRIPTION
		"&<caiW2kOs.154>The table entry."
	INDEX { w2kStatusDfsName }
	::= { w2kStatusDfsTable 1 }


W2kStatusDfsRow ::=
	SEQUENCE {
		w2kStatusDfsName DisplayString,
		w2kStatusDfsDescription DisplayString,
		w2kStatusDfsIds DisplayString,
		w2kStatusDfsAutoWatcherName DisplayString,
		w2kStatusDfsAggLagValue INTEGER,
		w2kStatusDfsAggLag INTEGER,
		w2kStatusDfsAggStatus INTEGER,
		w2kStatusDfsReplicaTotal INTEGER,
		w2kStatusDfsReplicaValue INTEGER,
		w2kStatusDfsReplicaWarn INTEGER,
		w2kStatusDfsReplicaCrit INTEGER,
		w2kStatusDfsReplicaMonitor INTEGER,
		w2kStatusDfsReplicaStatus INTEGER,
		w2kStatusDfsLossAction INTEGER,
		w2kStatusDfsLossStatus INTEGER,
		w2kStatusDfsCallBackRef DisplayString,
		w2kStatusDfsButton INTEGER
	}


w2kStatusDfsName OBJECT-TYPE
	SYNTAX DisplayString
	ACCESS read-only
	STATUS mandatory
	DESCRIPTION
		"&<caiW2kOs.551>Name of the watcher, monitoring a distributed file system link with this name. The name consists of the Dfs root name followed by the Dfs link name. These two names are concatenated by a back-slash. The single Dfs root name (without '\DfsLinkName') can also be used as watcher name, to be able to monitor all Dfs links of a Dfs root. In that case no loss action will be triggered if no Dfs link exists. Important: This name is case insensitive."
	::= { w2kStatusDfsEntry 1 }


w2kStatusDfsDescription OBJECT-TYPE
	SYNTAX DisplayString
	ACCESS read-write
	STATUS mandatory
	DESCRIPTION
		"&<caiW2kOs.136>Any description for this watcher."
	::= { w2kStatusDfsEntry 2 }


w2kStatusDfsIds OBJECT-TYPE
	SYNTAX DisplayString
	ACCESS read-only
	STATUS mandatory
	DESCRIPTION
		"&<caiW2kOs.553>A pipe sign separated list of those replicas of the distributed file system link, that are unavailable."
	::= { w2kStatusDfsEntry 3 }


w2kStatusDfsAutoWatcherName OBJECT-TYPE
	SYNTAX DisplayString
	ACCESS read-only
	STATUS mandatory
	DESCRIPTION
		"&<caiW2kOs.498>Name of the auto discovery watcher, which created this watcher."
	::= { w2kStatusDfsEntry 4 }


w2kStatusDfsAggLagValue OBJECT-TYPE
	SYNTAX INTEGER
	ACCESS read-only
	STATUS mandatory
	DESCRIPTION
		"&<caiW2kOs.499>The number of consecutive poll intervals on which any status was not in the Ok or Up state."
	::= { w2kStatusDfsEntry 5 }


w2kStatusDfsAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusDfsEntry 6 }


w2kStatusDfsAggStatus OBJECT-TYPE
	SYNTAX INTEGER {
		unknown(1),
		ok(2),
		warning(3),
		critical(4)
	}
	ACCESS read-only
	STATUS mandatory
	DESCRIPTION
		"&<caiW2kOs.557>The current status of the distributed file system link as a 'worst case' aggregate of all its statuses."
	::= { w2kStatusDfsEntry 7 }


w2kStatusDfsReplicaTotal OBJECT-TYPE
	SYNTAX INTEGER
	ACCESS read-only
	STATUS mandatory
	DESCRIPTION
		"&<caiW2kOs.558>The total number of replicas of the distributed file system link."
	::= { w2kStatusDfsEntry 8 }


w2kStatusDfsReplicaValue OBJECT-TYPE
	SYNTAX INTEGER
	ACCESS read-only
	STATUS mandatory
	DESCRIPTION
		"&<caiW2kOs.559>The current value of the unavailable replicas number. Replicas set to 'offline' are also counted as being unavailable."
	::= { w2kStatusDfsEntry 9 }


w2kStatusDfsReplicaWarn OBJECT-TYPE
	SYNTAX INTEGER
	ACCESS read-write
	STATUS mandatory
	DESCRIPTION
		"&<caiW2kOs.198>Warning threshold for the number of unavailable replicas of the distributed file system link. Valid values are greater than 0 and smaller than the critical threshold."
	::= { w2kStatusDfsEntry 10 }


w2kStatusDfsReplicaCrit OBJECT-TYPE
	SYNTAX INTEGER
	ACCESS read-write
	STATUS mandatory
	DESCRIPTION
		"&<caiW2kOs.199>Critical threshold for the number of unavailable replicas of the distributed file system link. Valid values are greater than 1 and greater than the warning threshold."
	::= { w2kStatusDfsEntry 11 }


w2kStatusDfsReplicaMonitor OBJECT-TYPE
	SYNTAX INTEGER {
		do-not-monitor(1),
		warning-only(2),
		critical-only(3),
		both(4)
	}
	ACCESS read-write
	STATUS mandatory
	DESCRIPTION
		"&<caiW2kOs.200>Flag indicating whether the unavailable replicas should be monitored and if so, which threshold should be compared with."
	DEFVAL { 0 }
	::= { w2kStatusDfsEntry 12 }


w2kStatusDfsReplicaStatus OBJECT-TYPE
	SYNTAX INTEGER {
		unknown(1),
		ok(2),
		warning(3),
		critical(4)
	}
	ACCESS read-only
	STATUS mandatory
	DESCRIPTION
		"&<caiW2kOs.563>The current status of the unavailable replicas number as determined by the thresholds. The status 'unknown' means that the current value could not be retrieved from the system."
	::= { w2kStatusDfsEntry 13 }


w2kStatusDfsLossAction OBJECT-TYPE
	SYNTAX INTEGER {
		remove(1),
		up(2),
		down-warning(3),
		down-critical(4)
	}
	ACCESS read-write
	STATUS mandatory
	DESCRIPTION
		"&<caiW2kOs.201>Flag defining the severity if the loss of the distributed file system link is detected or whether to remove this watcher in that case."
	DEFVAL { 0 }
	::= { w2kStatusDfsEntry 14 }


w2kStatusDfsLossStatus OBJECT-TYPE
	SYNTAX INTEGER {
		unknown(1),
		up(2),
		down-warning(3),
		down-critical(4)
	}
	ACCESS read-only
	STATUS mandatory
	DESCRIPTION
		"&<caiW2kOs.565>The current status of the distributed file system link's loss as determined by the loss action."
	::= { w2kStatusDfsEntry 15 }


w2kStatusDfsCallBackRef OBJECT-TYPE
	SYNTAX DisplayString
	ACCESS read-only
	STATUS mandatory
	DESCRIPTION
		"&<caiW2kOs.443>The name of the Call-Back reference that should be invoked in case of a status change."
	::= { w2kStatusDfsEntry 16 }


w2kStatusDfsButton OBJECT-TYPE
	SYNTAX INTEGER {
		none(1),
		remove(2)
	}
	ACCESS read-write
	STATUS mandatory
	DESCRIPTION
		"&<caiW2kOs.530>This attribute is used to remove this watcher."
	::= { w2kStatusDfsEntry 17 }




--	------------------------------------------------------------------------
--      Quotas Status Group
--	------------------------------------------------------------------------


w2kStatusQuotCount OBJECT-TYPE
	SYNTAX INTEGER
	ACCESS read-only
	STATUS mandatory
	DESCRIPTION
		"&<caiW2kOs.568>The number of entries in the w2kStatusQuotTable."
	::= { w2kStatusQuotGroup 1 }


w2kStatusQuotTable OBJECT-TYPE
	SYNTAX SEQUENCE OF W2kStatusQuotRow
	ACCESS not-accessible
	STATUS mandatory
	DESCRIPTION
		"&<caiW2kOs.569>A table containing information about all monitored quotas."
	::= { w2kStatusQuotGroup 2 }


w2kStatusQuotEntry OBJECT-TYPE
	SYNTAX W2kStatusQuotRow
	ACCESS not-accessible
	STATUS mandatory
	DESCRIPTION
		"&<caiW2kOs.154>The table entry."
	INDEX { w2kStatusQuotLVolName, w2kStatusQuotUserName }
	::= { w2kStatusQuotTable 1 }


W2kStatusQuotRow ::=
	SEQUENCE {
		w2kStatusQuotLVolName DisplayString,
		w2kStatusQuotUserName DisplayString,
		w2kStatusQuotDescription DisplayString,
		w2kStatusQuotAggLagValue INTEGER,
		w2kStatusQuotAggLag INTEGER,
		w2kStatusQuotAggStatus INTEGER,
		w2kStatusQuotExist INTEGER,
		w2kStatusQuotExistMonitor INTEGER,
		w2kStatusQuotExistStatus INTEGER,
		w2kStatusQuotSizeValue INTEGER,
		w2kStatusQuotSizeWarn INTEGER,
		w2kStatusQuotSizeCrit INTEGER,
		w2kStatusQuotSizeMonitor INTEGER,
		w2kStatusQuotSizeStatus INTEGER,
		w2kStatusQuotCallBackRef DisplayString,
		w2kStatusQuotButton INTEGER
	}


w2kStatusQuotLVolName OBJECT-TYPE
	SYNTAX DisplayString
	ACCESS read-only
	STATUS mandatory
	DESCRIPTION
		"&<caiW2kOs.571>Logical volume name of the watcher, monitoring a quota with this logical volume name. The name specifies the logical volume on which this quota exists. Important: This name is case insensitive."
	::= { w2kStatusQuotEntry 1 }


w2kStatusQuotUserName OBJECT-TYPE
	SYNTAX DisplayString
	ACCESS read-only
	STATUS mandatory
	DESCRIPTION
		"&<caiW2kOs.572>User name of the watcher, monitoring a quota with this user name. The name specifies the user for whom this quota exists and is in the form 'domainName\\userName' or 'userName@domainName'. Important: This name is case insensitive."
	::= { w2kStatusQuotEntry 2 }


w2kStatusQuotDescription OBJECT-TYPE
	SYNTAX DisplayString
	ACCESS read-write
	STATUS mandatory
	DESCRIPTION
		"&<caiW2kOs.136>Any description for this watcher."
	::= { w2kStatusQuotEntry 3 }


w2kStatusQuotAggLagValue OBJECT-TYPE
	SYNTAX INTEGER
	ACCESS read-only
	STATUS mandatory
	DESCRIPTION
		"&<caiW2kOs.499>The number of consecutive poll intervals on which any status was not in the Ok or Up state."
	::= { w2kStatusQuotEntry 4 }


w2kStatusQuotAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusQuotEntry 5 }


w2kStatusQuotAggStatus OBJECT-TYPE
	SYNTAX INTEGER {
		unknown(1),
		ok(2),
		warning(3),
		critical(4)
	}
	ACCESS read-only
	STATUS mandatory
	DESCRIPTION
		"&<caiW2kOs.576>The current status of the quota as a 'worst case' aggregate of all its statuses."
	::= { w2kStatusQuotEntry 6 }


w2kStatusQuotExist OBJECT-TYPE
	SYNTAX INTEGER {
		should-exist(1),
		should-not-exist(2)
	}
	ACCESS read-write
	STATUS mandatory
	DESCRIPTION
		"&<caiW2kOs.221>Flag indicating whether to raise an alert if a quota is existent or if it is not-existent."
	DEFVAL { 0 }
	::= { w2kStatusQuotEntry 7 }


w2kStatusQuotExistMonitor OBJECT-TYPE
	SYNTAX INTEGER {
		do-not-monitor(1),
		down-warning(2),
		down-critical(3)
	}
	ACCESS read-write
	STATUS mandatory
	DESCRIPTION
		"&<caiW2kOs.222>Flag indicating whether the existence of the quota should be monitored and if so, the level of alert to raise."
	DEFVAL { 0 }
	::= { w2kStatusQuotEntry 8 }


w2kStatusQuotExistStatus OBJECT-TYPE
	SYNTAX INTEGER {
		unknown(1),
		up(2),
		down-warning(3),
		down-critical(4)
	}
	ACCESS read-only
	STATUS mandatory
	DESCRIPTION
		"&<caiW2kOs.579>The current status of the quota existence."
	::= { w2kStatusQuotEntry 9 }


w2kStatusQuotSizeValue OBJECT-TYPE
	SYNTAX INTEGER
	ACCESS read-only
	STATUS mandatory
	DESCRIPTION
		"&<caiW2kOs.580>The current value of the used quota size (in kilobytes)."
	::= { w2kStatusQuotEntry 10 }


w2kStatusQuotSizeWarn OBJECT-TYPE
	SYNTAX INTEGER
	ACCESS read-write
	STATUS mandatory
	DESCRIPTION
		"&<caiW2kOs.581>Warning threshold for the used quota size (in kilobytes). Initial this equals the warning level of the Windows 2000 quota management. Valid values are greater than 0 and smaller than the critical threshold."
	::= { w2kStatusQuotEntry 11 }


w2kStatusQuotSizeCrit OBJECT-TYPE
	SYNTAX INTEGER
	ACCESS read-write
	STATUS mandatory
	DESCRIPTION
		"&<caiW2kOs.582>Critical threshold for the used quota size (in kilobytes). Initial this equals the quota limit of the Windows 2000 quota management. Valid values are greater than 1 and graeter warning threshold."
	::= { w2kStatusQuotEntry 12 }


w2kStatusQuotSizeMonitor OBJECT-TYPE
	SYNTAX INTEGER {
		do-not-monitor(1),
		warning-only(2),
		critical-only(3),
		both(4)
	}
	ACCESS read-write
	STATUS mandatory
	DESCRIPTION
		"&<caiW2kOs.225>Flag indicating whether the used quota size should be monitored and if so, which threshold should be compared with."
	DEFVAL { 0 }
	::= { w2kStatusQuotEntry 13 }


w2kStatusQuotSizeStatus OBJECT-TYPE
	SYNTAX INTEGER {
		unknown(1),
		ok(2),
		warning(3),
		critical(4)
	}
	ACCESS read-only
	STATUS mandatory
	DESCRIPTION
		"&<caiW2kOs.584>The current status of the used quota size as determined by the thresholds. The status 'unknown' means that the current value could not be retrieved from the system."
	::= { w2kStatusQuotEntry 14 }


w2kStatusQuotCallBackRef OBJECT-TYPE
	SYNTAX DisplayString
	ACCESS read-only
	STATUS mandatory
	DESCRIPTION
		"&<caiW2kOs.443>The name of the Call-Back reference that should be invoked in case of a status change."
	::= { w2kStatusQuotEntry 15 }


w2kStatusQuotButton OBJECT-TYPE
	SYNTAX INTEGER {
		none(1),
		remove(2)
	}
	ACCESS read-write
	STATUS mandatory
	DESCRIPTION
		"&<caiW2kOs.530>This attribute is used to remove this watcher."
	::= { w2kStatusQuotEntry 16 }




--	------------------------------------------------------------------------
--      Directories Status Group
--	------------------------------------------------------------------------


w2kStatusDirCount OBJECT-TYPE
	SYNTAX INTEGER
	ACCESS read-only
	STATUS mandatory
	DESCRIPTION
		"&<caiW2kOs.587>The number of entries in the w2kStatusDirTable."
	::= { w2kStatusDirGroup 1 }


w2kStatusDirTable OBJECT-TYPE
	SYNTAX SEQUENCE OF W2kStatusDirRow
	ACCESS not-accessible
	STATUS mandatory
	DESCRIPTION
		"&<caiW2kOs.588>A table containing information about all monitored directories."
	::= { w2kStatusDirGroup 2 }


w2kStatusDirEntry OBJECT-TYPE
	SYNTAX W2kStatusDirRow
	ACCESS not-accessible
	STATUS mandatory
	DESCRIPTION
		"&<caiW2kOs.154>The table entry."
	INDEX { w2kStatusDirName }
	::= { w2kStatusDirTable 1 }


W2kStatusDirRow ::=
	SEQUENCE {
		w2kStatusDirName DisplayString,
		w2kStatusDirDescription DisplayString,
		w2kStatusDirAggLagValue INTEGER,
		w2kStatusDirAggLag INTEGER,
		w2kStatusDirAggStatus INTEGER,
		w2kStatusDirExist INTEGER,
		w2kStatusDirExistMonitor INTEGER,
		w2kStatusDirExistStatus INTEGER,
		w2kStatusDirTimeValue DisplayString,
		w2kStatusDirTimeRef DisplayString,
		w2kStatusDirTimeMonitor INTEGER,
		w2kStatusDirTimeStatus INTEGER,
		w2kStatusDirSizeRef INTEGER,
		w2kStatusDirSizeValue INTEGER,
		w2kStatusDirSizeWarnValue INTEGER,
		w2kStatusDirSizeCritValue INTEGER,
		w2kStatusDirSizeWarn DisplayString,
		w2kStatusDirSizeCrit DisplayString,
		w2kStatusDirSizeMonitor INTEGER,
		w2kStatusDirSizeStatus INTEGER,
		w2kStatusDirSizeDValue INTEGER,
		w2kStatusDirSizeDWarnValue DisplayString,
		w2kStatusDirSizeDCritValue DisplayString,
		w2kStatusDirSizeDWarn DisplayString,
		w2kStatusDirSizeDCrit DisplayString,
		w2kStatusDirSizeDMonitor INTEGER,
		w2kStatusDirSizeDStatus INTEGER,
		w2kStatusDirEntryValue INTEGER,
		w2kStatusDirEntryWarn INTEGER,
		w2kStatusDirEntryCrit INTEGER,
		w2kStatusDirEntryMonitor INTEGER,
		w2kStatusDirEntryStatus INTEGER,
		w2kStatusDirCallBackRef DisplayString,
		w2kStatusDirButton INTEGER
	}


w2kStatusDirName OBJECT-TYPE
	SYNTAX DisplayString
	ACCESS read-only
	STATUS mandatory
	DESCRIPTION
		"&<caiW2kOs.590>Name of the watcher, monitoring a directory with this name. Important: This name is case insensitive."
	::= { w2kStatusDirEntry 1 }


w2kStatusDirDescription OBJECT-TYPE
	SYNTAX DisplayString
	ACCESS read-write
	STATUS mandatory
	DESCRIPTION
		"&<caiW2kOs.136>Any description for this watcher."
	::= { w2kStatusDirEntry 2 }


w2kStatusDirAggLagValue OBJECT-TYPE
	SYNTAX INTEGER
	ACCESS read-only
	STATUS mandatory
	DESCRIPTION
		"&<caiW2kOs.499>The number of consecutive poll intervals on which any status was not in the Ok or Up state."
	::= { w2kStatusDirEntry 3 }


w2kStatusDirAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusDirEntry 4 }


w2kStatusDirAggStatus OBJECT-TYPE
	SYNTAX INTEGER {
		unknown(1),
		ok(2),
		warning(3),
		critical(4)
	}
	ACCESS read-only
	STATUS mandatory
	DESCRIPTION
		"&<caiW2kOs.594>The current status of the directory as a 'worst case' aggregate of all its statuses."
	::= { w2kStatusDirEntry 5 }


w2kStatusDirExist OBJECT-TYPE
	SYNTAX INTEGER {
		should-exist(1),
		should-not-exist(2)
	}
	ACCESS read-write
	STATUS mandatory
	DESCRIPTION
		"&<caiW2kOs.232>Flag indicating whether to raise an alert if a directory is existent or if it is not-existent."
	DEFVAL { 0 }
	::= { w2kStatusDirEntry 6 }


w2kStatusDirExistMonitor OBJECT-TYPE
	SYNTAX INTEGER {
		do-not-monitor(1),
		down-warning(2),
		down-critical(3)
	}
	ACCESS read-write
	STATUS mandatory
	DESCRIPTION
		"&<caiW2kOs.233>Flag indicating whether the existence of the directory should be monitored and if so, the level of alert to raise."
	DEFVAL { 0 }
	::= { w2kStatusDirEntry 7 }


w2kStatusDirExistStatus OBJECT-TYPE
	SYNTAX INTEGER {
		unknown(1),
		up(2),
		down-warning(3),
		down-critical(4)
	}
	ACCESS read-only
	STATUS mandatory
	DESCRIPTION
		"&<caiW2kOs.597>The current status of the directory existence."
	::= { w2kStatusDirEntry 8 }


w2kStatusDirTimeValue OBJECT-TYPE
	SYNTAX DisplayString
	ACCESS read-only
	STATUS mandatory
	DESCRIPTION
		"&<caiW2kOs.598>The current value of the latest timestamp. If the directory does not exist, the timestamp value is set to '1970-01-01 01:00:00'."
	::= { w2kStatusDirEntry 9 }


w2kStatusDirTimeRef OBJECT-TYPE
	SYNTAX DisplayString
	ACCESS read-only
	STATUS mandatory
	DESCRIPTION
		"&<caiW2kOs.599>The reference timestamp, which is the timestamp of the directory when this watcher was created or when the last 'reset-time' has been made. If the directory does not exist, the reference timestamp is set to '1970-01-01 01:00:00'."
	::= { w2kStatusDirEntry 10 }


w2kStatusDirTimeMonitor OBJECT-TYPE
	SYNTAX INTEGER {
		do-not-monitor(1),
		down-warning(2),
		down-critical(3)
	}
	ACCESS read-write
	STATUS mandatory
	DESCRIPTION
		"&<caiW2kOs.234>Flag indicating whether the latest timestamp (of all files and all subfolders, including the given folder) should be monitored and if so, the level of alert to raise."
	DEFVAL { 0 }
	::= { w2kStatusDirEntry 11 }


w2kStatusDirTimeStatus OBJECT-TYPE
	SYNTAX INTEGER {
		unknown(1),
		up(2),
		down-warning(3),
		down-critical(4)
	}
	ACCESS read-only
	STATUS mandatory
	DESCRIPTION
		"&<caiW2kOs.601>The current status of the latest timestamp. The status 'unknown' means that the current value could not be retrieved from the system."
	::= { w2kStatusDirEntry 12 }


w2kStatusDirSizeRef OBJECT-TYPE
	SYNTAX INTEGER
	ACCESS read-only
	STATUS mandatory
	DESCRIPTION
		"&<caiW2kOs.602>The total size of the directory at the time when this watcher was created (in kilobytes)."
	::= { w2kStatusDirEntry 13 }


w2kStatusDirSizeValue OBJECT-TYPE
	SYNTAX INTEGER
	ACCESS read-only
	STATUS mandatory
	DESCRIPTION
		"&<caiW2kOs.603>The current value of the total directory size (in kilobytes)."
	::= { w2kStatusDirEntry 14 }


w2kStatusDirSizeWarnValue OBJECT-TYPE
	SYNTAX INTEGER
	ACCESS read-only
	STATUS mandatory
	DESCRIPTION
		"&<caiW2kOs.604>The actual warning threshold in kilobytes derived from the configured warning threshold."
	::= { w2kStatusDirEntry 15 }


w2kStatusDirSizeCritValue OBJECT-TYPE
	SYNTAX INTEGER
	ACCESS read-only
	STATUS mandatory
	DESCRIPTION
		"&<caiW2kOs.605>The actual critical threshold in kilobytes derived from the configured critical threshold."
	::= { w2kStatusDirEntry 16 }


w2kStatusDirSizeWarn OBJECT-TYPE
	SYNTAX DisplayString
	ACCESS read-write
	STATUS mandatory
	DESCRIPTION
		"&<caiW2kOs.235>Warning threshold for the total directory size (all files in the given folder and in all subfolders), either in kilobytes or as a percentage value of the original size (by appending a '%'). The original size is the size when this watcher was created. Valid values are greater than 0 and smaller than the critical threshold."
	::= { w2kStatusDirEntry 17 }


w2kStatusDirSizeCrit OBJECT-TYPE
	SYNTAX DisplayString
	ACCESS read-write
	STATUS mandatory
	DESCRIPTION
		"&<caiW2kOs.236>Critical threshold for the total directory size (all files in the given folder and in all subfolders), either in kilobytes or as a percentage value of the original size (by appending a '%'). The original size is the size when this watcher was created. Valid values are greater than 1 and greater than the warning threshold."
	::= { w2kStatusDirEntry 18 }


w2kStatusDirSizeMonitor OBJECT-TYPE
	SYNTAX INTEGER {
		do-not-monitor(1),
		warning-only(2),
		critical-only(3),
		both(4)
	}
	ACCESS read-write
	STATUS mandatory
	DESCRIPTION
		"&<caiW2kOs.237>Flag indicating whether the total directory size should be monitored and if so, which threshold should be compared with."
	DEFVAL { 0 }
	::= { w2kStatusDirEntry 19 }


w2kStatusDirSizeStatus OBJECT-TYPE
	SYNTAX INTEGER {
		unknown(1),
		ok(2),
		warning(3),
		critical(4)
	}
	ACCESS read-only
	STATUS mandatory
	DESCRIPTION
		"&<caiW2kOs.609>The current status of the total directory size as determined by the thresholds. The status 'unknown' means that the current value could not be retrieved from the system."
	::= { w2kStatusDirEntry 20 }


w2kStatusDirSizeDValue OBJECT-TYPE
	SYNTAX INTEGER
	ACCESS read-only
	STATUS mandatory
	DESCRIPTION
		"&<caiW2kOs.610>The current value of the delta in total directory size monitored in the last polling interval (in kilobytes). In case of shrinkage this is a negative number."
	::= { w2kStatusDirEntry 21 }


w2kStatusDirSizeDWarnValue OBJECT-TYPE
	SYNTAX DisplayString
	ACCESS read-only
	STATUS mandatory
	DESCRIPTION
		"&<caiW2kOs.604>The actual warning threshold in kilobytes derived from the configured warning threshold."
	::= { w2kStatusDirEntry 22 }


w2kStatusDirSizeDCritValue OBJECT-TYPE
	SYNTAX DisplayString
	ACCESS read-only
	STATUS mandatory
	DESCRIPTION
		"&<caiW2kOs.605>The actual critical threshold in kilobytes derived from the configured critical threshold."
	::= { w2kStatusDirEntry 23 }


w2kStatusDirSizeDWarn OBJECT-TYPE
	SYNTAX DisplayString
	ACCESS read-write
	STATUS mandatory
	DESCRIPTION
		"&<caiW2kOs.238>Warning threshold, either for the growth (by appending a '+') or for the shrinkage (by appending a '-') or for the absolute delta in total directory size monitored in one poll interval. Growth, shrinkage and absolute delta can be given in kilobytes or as a percentage value of the total directory size (by appending a '%'). Valid values are greater than 0 and smaller than the critical threshold."
	::= { w2kStatusDirEntry 24 }


w2kStatusDirSizeDCrit OBJECT-TYPE
	SYNTAX DisplayString
	ACCESS read-write
	STATUS mandatory
	DESCRIPTION
		"&<caiW2kOs.239>Critical threshold, either for the growth (by appending a '+') or for the shrinkage (by appending a '-') or for the absolute delta in total directory size monitored in one poll interval. Growth, shrinkage and absolute delta can be given in kilobytes or as a percentage value of the total directory size (by appending a '%'). Valid values are greater than 1 and greater than the warning threshold."
	::= { w2kStatusDirEntry 25 }


w2kStatusDirSizeDMonitor OBJECT-TYPE
	SYNTAX INTEGER {
		do-not-monitor(1),
		warning-only(2),
		critical-only(3),
		both(4)
	}
	ACCESS read-write
	STATUS mandatory
	DESCRIPTION
		"&<caiW2kOs.240>Flag indicating whether the delta in total directory size should be monitored and if so, which threshold should be compared with."
	DEFVAL { 0 }
	::= { w2kStatusDirEntry 26 }


w2kStatusDirSizeDStatus OBJECT-TYPE
	SYNTAX INTEGER {
		unknown(1),
		ok(2),
		warning(3),
		critical(4)
	}
	ACCESS read-only
	STATUS mandatory
	DESCRIPTION
		"&<caiW2kOs.616>The current status of the delta in total directory size as determined by the thresholds. The status 'unknown' means that the current value could not be retrieved from the system."
	::= { w2kStatusDirEntry 27 }


w2kStatusDirEntryValue OBJECT-TYPE
	SYNTAX INTEGER
	ACCESS read-only
	STATUS mandatory
	DESCRIPTION
		"&<caiW2kOs.617>The current value of the number of files."
	::= { w2kStatusDirEntry 28 }


w2kStatusDirEntryWarn OBJECT-TYPE
	SYNTAX INTEGER
	ACCESS read-write
	STATUS mandatory
	DESCRIPTION
		"&<caiW2kOs.241>Warning threshold for the number of entries (sum of files and folders in the given folder and in all subfolders). Valid values are greater than 0 and smaller than the critical threshold."
	::= { w2kStatusDirEntry 29 }


w2kStatusDirEntryCrit OBJECT-TYPE
	SYNTAX INTEGER
	ACCESS read-write
	STATUS mandatory
	DESCRIPTION
		"&<caiW2kOs.242>Critical threshold for the number of entries (sum of files and folders in the given folder and in all subfolders). Valid values are greater than 1 and greater than the warning threshold."
	::= { w2kStatusDirEntry 30 }


w2kStatusDirEntryMonitor OBJECT-TYPE
	SYNTAX INTEGER {
		do-not-monitor(1),
		warning-only(2),
		critical-only(3),
		both(4)
	}
	ACCESS read-write
	STATUS mandatory
	DESCRIPTION
		"&<caiW2kOs.243>Flag indicating whether the number of entries should be monitored and if so, which threshold should be compared with."
	DEFVAL { 0 }
	::= { w2kStatusDirEntry 31 }


w2kStatusDirEntryStatus OBJECT-TYPE
	SYNTAX INTEGER {
		unknown(1),
		ok(2),
		warning(3),
		critical(4)
	}
	ACCESS read-only
	STATUS mandatory
	DESCRIPTION
		"&<caiW2kOs.621>The current status of the number of entries as determined by the thresholds. The status 'unknown' means that the current value could not be retrieved from the system."
	::= { w2kStatusDirEntry 32 }


w2kStatusDirCallBackRef OBJECT-TYPE
	SYNTAX DisplayString
	ACCESS read-only
	STATUS mandatory
	DESCRIPTION
		"&<caiW2kOs.443>The name of the Call-Back reference that should be invoked in case of a status change."
	::= { w2kStatusDirEntry 33 }


w2kStatusDirButton OBJECT-TYPE
	SYNTAX INTEGER {
		none(1),
		remove(2),
		reset-time(3)
	}
	ACCESS read-write
	STATUS mandatory
	DESCRIPTION
		"&<caiW2kOs.623>This attribute is used to remove this watcher or to reset the time reference to the current value."
	::= { w2kStatusDirEntry 34 }




--	------------------------------------------------------------------------
--      Files Status Group
--	------------------------------------------------------------------------


w2kStatusFileCount OBJECT-TYPE
	SYNTAX INTEGER
	ACCESS read-only
	STATUS mandatory
	DESCRIPTION
		"&<caiW2kOs.624>The number of entries in the w2kStatusFileTable."
	::= { w2kStatusFileGroup 1 }


w2kStatusFileTable OBJECT-TYPE
	SYNTAX SEQUENCE OF W2kStatusFileRow
	ACCESS not-accessible
	STATUS mandatory
	DESCRIPTION
		"&<caiW2kOs.625>A table containing information about all monitored files."
	::= { w2kStatusFileGroup 2 }


w2kStatusFileEntry OBJECT-TYPE
	SYNTAX W2kStatusFileRow
	ACCESS not-accessible
	STATUS mandatory
	DESCRIPTION
		"&<caiW2kOs.154>The table entry."
	INDEX { w2kStatusFileName }
	::= { w2kStatusFileTable 1 }


W2kStatusFileRow ::=
	SEQUENCE {
		w2kStatusFileName DisplayString,
		w2kStatusFileDescription DisplayString,
		w2kStatusFileAggLagValue INTEGER,
		w2kStatusFileAggLag INTEGER,
		w2kStatusFileAggStatus INTEGER,
		w2kStatusFileExist INTEGER,
		w2kStatusFileExistMonitor INTEGER,
		w2kStatusFileExistStatus INTEGER,
		w2kStatusFileTimeValue DisplayString,
		w2kStatusFileTimeRef DisplayString,
		w2kStatusFileTimeMonitor INTEGER,
		w2kStatusFileTimeStatus INTEGER,
		w2kStatusFileSizeRef INTEGER,
		w2kStatusFileSizeValue INTEGER,
		w2kStatusFileSizeWarnValue INTEGER,
		w2kStatusFileSizeCritValue INTEGER,
		w2kStatusFileSizeWarn DisplayString,
		w2kStatusFileSizeCrit DisplayString,
		w2kStatusFileSizeMonitor INTEGER,
		w2kStatusFileSizeStatus INTEGER,
		w2kStatusFileSizeDValue INTEGER,
		w2kStatusFileSizeDWarnValue DisplayString,
		w2kStatusFileSizeDCritValue DisplayString,
		w2kStatusFileSizeDWarn DisplayString,
		w2kStatusFileSizeDCrit DisplayString,
		w2kStatusFileSizeDMonitor INTEGER,
		w2kStatusFileSizeDStatus INTEGER,
		w2kStatusFileCallBackRef DisplayString,
		w2kStatusFileButton INTEGER
	}


w2kStatusFileName OBJECT-TYPE
	SYNTAX DisplayString
	ACCESS read-only
	STATUS mandatory
	DESCRIPTION
		"&<caiW2kOs.627>Name of the watcher, monitoring a file with this name. Important: This name is case insensitive."
	::= { w2kStatusFileEntry 1 }


w2kStatusFileDescription OBJECT-TYPE
	SYNTAX DisplayString
	ACCESS read-write
	STATUS mandatory
	DESCRIPTION
		"&<caiW2kOs.136>Any description for this watcher."
	::= { w2kStatusFileEntry 2 }


w2kStatusFileAggLagValue OBJECT-TYPE
	SYNTAX INTEGER
	ACCESS read-only
	STATUS mandatory
	DESCRIPTION
		"&<caiW2kOs.499>The number of consecutive poll intervals on which any status was not in the Ok or Up state."
	::= { w2kStatusFileEntry 3 }


w2kStatusFileAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusFileEntry 4 }


w2kStatusFileAggStatus OBJECT-TYPE
	SYNTAX INTEGER {
		unknown(1),
		ok(2),
		warning(3),
		critical(4)
	}
	ACCESS read-only
	STATUS mandatory
	DESCRIPTION
		"&<caiW2kOs.631>The current status of the file as a 'worst case' aggregate of all its statuses."
	::= { w2kStatusFileEntry 5 }


w2kStatusFileExist OBJECT-TYPE
	SYNTAX INTEGER {
		should-exist(1),
		should-not-exist(2)
	}
	ACCESS read-write
	STATUS mandatory
	DESCRIPTION
		"&<caiW2kOs.250>Flag indicating whether to raise an alert if a file is existent or if it is not-existent."
	DEFVAL { 0 }
	::= { w2kStatusFileEntry 6 }


w2kStatusFileExistMonitor OBJECT-TYPE
	SYNTAX INTEGER {
		do-not-monitor(1),
		down-warning(2),
		down-critical(3)
	}
	ACCESS read-write
	STATUS mandatory
	DESCRIPTION
		"&<caiW2kOs.251>Flag indicating whether the existence of the file should be monitored and if so, the level of alert to raise."
	DEFVAL { 0 }
	::= { w2kStatusFileEntry 7 }


w2kStatusFileExistStatus OBJECT-TYPE
	SYNTAX INTEGER {
		unknown(1),
		up(2),
		down-warning(3),
		down-critical(4)
	}
	ACCESS read-only
	STATUS mandatory
	DESCRIPTION
		"&<caiW2kOs.634>The current status of the file existence."
	::= { w2kStatusFileEntry 8 }


w2kStatusFileTimeValue OBJECT-TYPE
	SYNTAX DisplayString
	ACCESS read-only
	STATUS mandatory
	DESCRIPTION
		"&<caiW2kOs.635>The current value of the latest timestamp. If the file does not exist, the timestamp value is set to '1970-01-01 01:00:00'."
	::= { w2kStatusFileEntry 9 }


w2kStatusFileTimeRef OBJECT-TYPE
	SYNTAX DisplayString
	ACCESS read-only
	STATUS mandatory
	DESCRIPTION
		"&<caiW2kOs.636>The reference timestamp, which is the timestamp of the file when this watcher was created or when the last 'reset-time' has been made. If the file does not exist, the reference timestamp is set to '1970-01-01 01:00:00'."
	::= { w2kStatusFileEntry 10 }


w2kStatusFileTimeMonitor OBJECT-TYPE
	SYNTAX INTEGER {
		do-not-monitor(1),
		down-warning(2),
		down-critical(3)
	}
	ACCESS read-write
	STATUS mandatory
	DESCRIPTION
		"&<caiW2kOs.252>Flag indicating whether the timestamp of the file should be monitored and if so, the level of alert to raise."
	DEFVAL { 0 }
	::= { w2kStatusFileEntry 11 }


w2kStatusFileTimeStatus OBJECT-TYPE
	SYNTAX INTEGER {
		unknown(1),
		up(2),
		down-warning(3),
		down-critical(4)
	}
	ACCESS read-only
	STATUS mandatory
	DESCRIPTION
		"&<caiW2kOs.601>The current status of the latest timestamp. The status 'unknown' means that the current value could not be retrieved from the system."
	::= { w2kStatusFileEntry 12 }


w2kStatusFileSizeRef OBJECT-TYPE
	SYNTAX INTEGER
	ACCESS read-only
	STATUS mandatory
	DESCRIPTION
		"&<caiW2kOs.639>The size of the file at the time when this watcher was created (in kilobytes)."
	::= { w2kStatusFileEntry 13 }


w2kStatusFileSizeValue OBJECT-TYPE
	SYNTAX INTEGER
	ACCESS read-only
	STATUS mandatory
	DESCRIPTION
		"&<caiW2kOs.640>The current value of the file size (in kilobytes)."
	::= { w2kStatusFileEntry 14 }


w2kStatusFileSizeWarnValue OBJECT-TYPE
	SYNTAX INTEGER
	ACCESS read-only
	STATUS mandatory
	DESCRIPTION
		"&<caiW2kOs.604>The actual warning threshold in kilobytes derived from the configured warning threshold."
	::= { w2kStatusFileEntry 15 }


w2kStatusFileSizeCritValue OBJECT-TYPE
	SYNTAX INTEGER
	ACCESS read-only
	STATUS mandatory
	DESCRIPTION
		"&<caiW2kOs.605>The actual critical threshold in kilobytes derived from the configured critical threshold."
	::= { w2kStatusFileEntry 16 }


w2kStatusFileSizeWarn OBJECT-TYPE
	SYNTAX DisplayString
	ACCESS read-write
	STATUS mandatory
	DESCRIPTION
		"&<caiW2kOs.253>Warning threshold for the file size, either in kilobytes or as a percentage value of the original size (by appending a '%'). The original size is the size when this watcher was created. Valid values are greater than 0 and smaller than the critical threshold."
	::= { w2kStatusFileEntry 17 }


w2kStatusFileSizeCrit OBJECT-TYPE
	SYNTAX DisplayString
	ACCESS read-write
	STATUS mandatory
	DESCRIPTION
		"&<caiW2kOs.254>Critical threshold for the file size, either in kilobytes or as a percentage value of the original size (by appending a '%'). The original size is the size when this watcher was created. Valid values are greater than 1 and greater than the warning threshold."
	::= { w2kStatusFileEntry 18 }


w2kStatusFileSizeMonitor OBJECT-TYPE
	SYNTAX INTEGER {
		do-not-monitor(1),
		warning-only(2),
		critical-only(3),
		both(4)
	}
	ACCESS read-write
	STATUS mandatory
	DESCRIPTION
		"&<caiW2kOs.255>Flag indicating whether the file size should be monitored and if so, which threshold should be compared with."
	DEFVAL { 0 }
	::= { w2kStatusFileEntry 19 }


w2kStatusFileSizeStatus OBJECT-TYPE
	SYNTAX INTEGER {
		unknown(1),
		ok(2),
		warning(3),
		critical(4)
	}
	ACCESS read-only
	STATUS mandatory
	DESCRIPTION
		"&<caiW2kOs.646>The current status of the file size as determined by the thresholds. The status 'unknown' means that the current value could not be retrieved from the system."
	::= { w2kStatusFileEntry 20 }


w2kStatusFileSizeDValue OBJECT-TYPE
	SYNTAX INTEGER
	ACCESS read-only
	STATUS mandatory
	DESCRIPTION
		"&<caiW2kOs.647>The current value of the delta in file size monitored in the last polling interval (in kilobytes). In case of shrinkage this is a negative number."
	::= { w2kStatusFileEntry 21 }


w2kStatusFileSizeDWarnValue OBJECT-TYPE
	SYNTAX DisplayString
	ACCESS read-only
	STATUS mandatory
	DESCRIPTION
		"&<caiW2kOs.604>The actual warning threshold in kilobytes derived from the configured warning threshold."
	::= { w2kStatusFileEntry 22 }


w2kStatusFileSizeDCritValue OBJECT-TYPE
	SYNTAX DisplayString
	ACCESS read-only
	STATUS mandatory
	DESCRIPTION
		"&<caiW2kOs.605>The actual critical threshold in kilobytes derived from the configured critical threshold."
	::= { w2kStatusFileEntry 23 }


w2kStatusFileSizeDWarn OBJECT-TYPE
	SYNTAX DisplayString
	ACCESS read-write
	STATUS mandatory
	DESCRIPTION
		"&<caiW2kOs.256>Warning threshold, either for the growth (by appending a '+') or for the shrinkage (by appending a '-') or for the absolute delta in file size monitored in one poll interval. Growth, shrinkage and absolute delta can be given in kilobytes or as a percentage value of the file size (by appending a '%'). Valid values are greater than 0 and smaller than the critical threshold."
	::= { w2kStatusFileEntry 24 }


w2kStatusFileSizeDCrit OBJECT-TYPE
	SYNTAX DisplayString
	ACCESS read-write
	STATUS mandatory
	DESCRIPTION
		"&<caiW2kOs.257>Critical threshold, either for the growth (by appending a '+') or for the shrinkage (by appending a '-') or for the absolute delta in file size monitored in one poll interval. Growth, shrinkage and absolute delta can be given in kilobytes or as a percentage value of the file size (by appending a '%'). Valid values are greater than 1 and greater than the warning threshold."
	::= { w2kStatusFileEntry 25 }


w2kStatusFileSizeDMonitor OBJECT-TYPE
	SYNTAX INTEGER {
		do-not-monitor(1),
		warning-only(2),
		critical-only(3),
		both(4)
	}
	ACCESS read-write
	STATUS mandatory
	DESCRIPTION
		"&<caiW2kOs.258>Flag indicating whether the delta in file size should be monitored and if so, which threshold should be compared with."
	DEFVAL { 0 }
	::= { w2kStatusFileEntry 26 }


w2kStatusFileSizeDStatus OBJECT-TYPE
	SYNTAX INTEGER {
		unknown(1),
		ok(2),
		warning(3),
		critical(4)
	}
	ACCESS read-only
	STATUS mandatory
	DESCRIPTION
		"&<caiW2kOs.653>The current status of the delta in file size as determined by the thresholds. The status 'unknown' means that the current value could not be retrieved from the system."
	::= { w2kStatusFileEntry 27 }


w2kStatusFileCallBackRef OBJECT-TYPE
	SYNTAX DisplayString
	ACCESS read-only
	STATUS mandatory
	DESCRIPTION
		"&<caiW2kOs.443>The name of the Call-Back reference that should be invoked in case of a status change."
	::= { w2kStatusFileEntry 28 }


w2kStatusFileButton OBJECT-TYPE
	SYNTAX INTEGER {
		none(1),
		remove(2),
		reset-time(3)
	}
	ACCESS read-write
	STATUS mandatory
	DESCRIPTION
		"&<caiW2kOs.623>This attribute is used to remove this watcher or to reset the time reference to the current value."
	::= { w2kStatusFileEntry 29 }




--	------------------------------------------------------------------------
--      Processes Status Group
--	------------------------------------------------------------------------


w2kStatusProcCount OBJECT-TYPE
	SYNTAX INTEGER
	ACCESS read-only
	STATUS mandatory
	DESCRIPTION
		"&<caiW2kOs.656>The number of entries in the w2kStatusProcTable."
	::= { w2kStatusProcGroup 1 }


w2kStatusProcTable OBJECT-TYPE
	SYNTAX SEQUENCE OF W2kStatusProcRow
	ACCESS not-accessible
	STATUS mandatory
	DESCRIPTION
		"&<caiW2kOs.657>A table containing information about all monitored processes."
	::= { w2kStatusProcGroup 2 }


w2kStatusProcEntry OBJECT-TYPE
	SYNTAX W2kStatusProcRow
	ACCESS not-accessible
	STATUS mandatory
	DESCRIPTION
		"&<caiW2kOs.154>The table entry."
	INDEX { w2kStatusProcProcName, w2kStatusProcPathName, w2kStatusProcUserName }
	::= { w2kStatusProcTable 1 }


W2kStatusProcRow ::=
	SEQUENCE {
		w2kStatusProcProcName DisplayString,
		w2kStatusProcPathName DisplayString,
		w2kStatusProcUserName DisplayString,
		w2kStatusProcDescription DisplayString,
		w2kStatusProcIds DisplayString,
		w2kStatusProcAggLagValue INTEGER,
		w2kStatusProcAggLag INTEGER,
		w2kStatusProcAggStatus INTEGER,
		w2kStatusProcInstValue INTEGER,
		w2kStatusProcInstMin INTEGER,
		w2kStatusProcInstMax INTEGER,
		w2kStatusProcInstMonitor INTEGER,
		w2kStatusProcInstStatus INTEGER,
		w2kStatusProcChildMinValue INTEGER,
		w2kStatusProcChildMaxValue INTEGER,
		w2kStatusProcChildMin INTEGER,
		w2kStatusProcChildMax INTEGER,
		w2kStatusProcChildMonitor INTEGER,
		w2kStatusProcChildStatus INTEGER,
		w2kStatusProcThreadMinValue INTEGER,
		w2kStatusProcThreadMaxValue INTEGER,
		w2kStatusProcThreadMin INTEGER,
		w2kStatusProcThreadMax INTEGER,
		w2kStatusProcThreadMonitor INTEGER,
		w2kStatusProcThreadStatus INTEGER,
		w2kStatusProcMemoryValue INTEGER,
		w2kStatusProcMemoryWarn INTEGER,
		w2kStatusProcMemoryCrit INTEGER,
		w2kStatusProcMemoryMonitor INTEGER,
		w2kStatusProcMemoryStatus INTEGER,
		w2kStatusProcCpuValue INTEGER,
		w2kStatusProcCpuWarn INTEGER,
		w2kStatusProcCpuCrit INTEGER,
		w2kStatusProcCpuMonitor INTEGER,
		w2kStatusProcCpuStatus INTEGER,
		w2kStatusProcCallBackRef DisplayString,
		w2kStatusProcButton INTEGER
	}


w2kStatusProcProcName OBJECT-TYPE
	SYNTAX DisplayString
	ACCESS read-only
	STATUS mandatory
	DESCRIPTION
		"&<caiW2kOs.659>Process name of the watcher, monitoring a process with this process name. An asterisk '*' can be used as process name or can be prepended/appended to it, in order to widen the scope of processes this watcher monitors. Important: This name is case insensitive."
	::= { w2kStatusProcEntry 1 }


w2kStatusProcPathName OBJECT-TYPE
	SYNTAX DisplayString
	ACCESS read-only
	STATUS mandatory
	DESCRIPTION
		"&<caiW2kOs.660>Path name of the watcher, monitoring a process with this path name. An asterisk '*' can be used as path name or can be prepended/appended to it, in order to widen the scope of processes this watcher monitors. Important: This name is case insensitive."
	::= { w2kStatusProcEntry 2 }


w2kStatusProcUserName OBJECT-TYPE
	SYNTAX DisplayString
	ACCESS read-only
	STATUS mandatory
	DESCRIPTION
		"&<caiW2kOs.661>User name of the watcher, monitoring a process started by this user. An asterisk '*' can be used as user name or can be prepended/appended to it, in order to widen the scope of processes this watcher monitors. Important: This name is case insensitive."
	::= { w2kStatusProcEntry 3 }


w2kStatusProcDescription OBJECT-TYPE
	SYNTAX DisplayString
	ACCESS read-write
	STATUS mandatory
	DESCRIPTION
		"&<caiW2kOs.136>Any description for this watcher."
	::= { w2kStatusProcEntry 4 }


w2kStatusProcIds OBJECT-TYPE
	SYNTAX DisplayString
	ACCESS read-only
	STATUS mandatory
	DESCRIPTION
		"&<caiW2kOs.663>A pipe sign separated list of the ids of those processes, that (b)reach any threshold (except instance metric)."
	::= { w2kStatusProcEntry 5 }


w2kStatusProcAggLagValue OBJECT-TYPE
	SYNTAX INTEGER
	ACCESS read-only
	STATUS mandatory
	DESCRIPTION
		"&<caiW2kOs.499>The number of consecutive poll intervals on which any status was not in the Ok or Up state."
	::= { w2kStatusProcEntry 6 }


w2kStatusProcAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusProcEntry 7 }


w2kStatusProcAggStatus OBJECT-TYPE
	SYNTAX INTEGER {
		unknown(1),
		ok(2),
		warning(3),
		critical(4)
	}
	ACCESS read-only
	STATUS mandatory
	DESCRIPTION
		"&<caiW2kOs.666>The current status of the process as a 'worst case' aggregate of all its statuses."
	::= { w2kStatusProcEntry 8 }


w2kStatusProcInstValue OBJECT-TYPE
	SYNTAX INTEGER
	ACCESS read-only
	STATUS mandatory
	DESCRIPTION
		"&<caiW2kOs.667>The current value of the process instances number."
	::= { w2kStatusProcEntry 9 }


w2kStatusProcInstMin OBJECT-TYPE
	SYNTAX INTEGER
	ACCESS read-write
	STATUS mandatory
	DESCRIPTION
		"&<caiW2kOs.267>Minimum threshold for the number of process instances. Valid values are greater than or equal to -1 and smaller than or equal to the maximum threshold. Setting to -1 disables the monitoring of the minimum."
	DEFVAL { -2 }
	::= { w2kStatusProcEntry 10 }


w2kStatusProcInstMax OBJECT-TYPE
	SYNTAX INTEGER
	ACCESS read-write
	STATUS mandatory
	DESCRIPTION
		"&<caiW2kOs.268>Maximum threshold for the number of process instances. Valid values are greater than or equal to -1 and greater than or equal to the minimum threshold. Setting to -1 disables the monitoring of the maximum."
	DEFVAL { -2 }
	::= { w2kStatusProcEntry 11 }


w2kStatusProcInstMonitor OBJECT-TYPE
	SYNTAX INTEGER {
		do-not-monitor(1),
		down-warning(2),
		down-critical(3)
	}
	ACCESS read-write
	STATUS mandatory
	DESCRIPTION
		"&<caiW2kOs.269>Flag indicating whether the number of process instances should be monitored and if so, the level of alert to raise."
	DEFVAL { 0 }
	::= { w2kStatusProcEntry 12 }


w2kStatusProcInstStatus OBJECT-TYPE
	SYNTAX INTEGER {
		unknown(1),
		up(2),
		down-warning(3),
		down-critical(4)
	}
	ACCESS read-only
	STATUS mandatory
	DESCRIPTION
		"&<caiW2kOs.671>The current status of the process instances number as determined by the thresholds. The status 'unknown' means that the current value could not be retrieved from the system."
	::= { w2kStatusProcEntry 13 }


w2kStatusProcChildMinValue OBJECT-TYPE
	SYNTAX INTEGER
	ACCESS read-only
	STATUS mandatory
	DESCRIPTION
		"&<caiW2kOs.672>The current minimum value of the number of childprocesses of the process. If there is more than one process instance, this value is the minimum of all instances."
	::= { w2kStatusProcEntry 14 }


w2kStatusProcChildMaxValue OBJECT-TYPE
	SYNTAX INTEGER
	ACCESS read-only
	STATUS mandatory
	DESCRIPTION
		"&<caiW2kOs.673>The current maximum value of the number of childprocesses of the process. If there is more than one process instance, this value is the maximum of all instances."
	::= { w2kStatusProcEntry 15 }


w2kStatusProcChildMin OBJECT-TYPE
	SYNTAX INTEGER
	ACCESS read-write
	STATUS mandatory
	DESCRIPTION
		"&<caiW2kOs.270>Minimum threshold for the number of childprocesses of the process. If there is more than one process instance, the minimum of all instances is compared with this value. Valid values are greater than or equal to -1 and smaller than or equal to the maximum threshold. Setting to -1 disables the monitoring of the minimum."
	DEFVAL { -2 }
	::= { w2kStatusProcEntry 16 }


w2kStatusProcChildMax OBJECT-TYPE
	SYNTAX INTEGER
	ACCESS read-write
	STATUS mandatory
	DESCRIPTION
		"&<caiW2kOs.271>Maximum threshold for the number of childprocesses of the process. If there is more than one process instance, the maximum of all instances is compared with this value. Valid values are greater than or equal to -1 and greater than or equal to the minimum threshold. Setting to -1 disables the monitoring of the maximum."
	DEFVAL { -2 }
	::= { w2kStatusProcEntry 17 }


w2kStatusProcChildMonitor OBJECT-TYPE
	SYNTAX INTEGER {
		do-not-monitor(1),
		down-warning(2),
		down-critical(3)
	}
	ACCESS read-write
	STATUS mandatory
	DESCRIPTION
		"&<caiW2kOs.272>Flag indicating whether the number of childprocesses of the process should be monitored and if so, the level of alert to raise. Note: This metric decreases agent performance much more than any other metric. For this reason the default is 'do-not-monitor'."
	DEFVAL { 0 }
	::= { w2kStatusProcEntry 18 }


w2kStatusProcChildStatus OBJECT-TYPE
	SYNTAX INTEGER {
		unknown(1),
		up(2),
		down-warning(3),
		down-critical(4)
	}
	ACCESS read-only
	STATUS mandatory
	DESCRIPTION
		"&<caiW2kOs.677>The current status of the childprocesses number as determined by the thresholds. The status 'unknown' means that the current value could not be retrieved from the system."
	::= { w2kStatusProcEntry 19 }


w2kStatusProcThreadMinValue OBJECT-TYPE
	SYNTAX INTEGER
	ACCESS read-only
	STATUS mandatory
	DESCRIPTION
		"&<caiW2kOs.678>The current minimum value of the number of threads of the process. If there is more than one process instance, this value is the minimum of all instances."
	::= { w2kStatusProcEntry 20 }


w2kStatusProcThreadMaxValue OBJECT-TYPE
	SYNTAX INTEGER
	ACCESS read-only
	STATUS mandatory
	DESCRIPTION
		"&<caiW2kOs.679>The current maximum value of the number of threads of the process. If there is more than one process instance, this value is the maximum of all instances."
	::= { w2kStatusProcEntry 21 }


w2kStatusProcThreadMin OBJECT-TYPE
	SYNTAX INTEGER
	ACCESS read-write
	STATUS mandatory
	DESCRIPTION
		"&<caiW2kOs.273>Minimum threshold for the number of threads of the process. If there is more than one process instance, the minimum of all instances is compared with this value. Valid values are greater than or equal to -1 and smaller than or equal to the maximum threshold. Setting to -1 disables the monitoring of the minimum."
	DEFVAL { -2 }
	::= { w2kStatusProcEntry 22 }


w2kStatusProcThreadMax OBJECT-TYPE
	SYNTAX INTEGER
	ACCESS read-write
	STATUS mandatory
	DESCRIPTION
		"&<caiW2kOs.274>Maximum threshold for the number of threads of the process. If there is more than one process instance, the maximum of all instances is compared with this value. Valid values are greater than or equal to -1 and greater than or equal to the minimum threshold. Setting to -1 disables the monitoring of the maximum."
	DEFVAL { -2 }
	::= { w2kStatusProcEntry 23 }


w2kStatusProcThreadMonitor OBJECT-TYPE
	SYNTAX INTEGER {
		do-not-monitor(1),
		down-warning(2),
		down-critical(3)
	}
	ACCESS read-write
	STATUS mandatory
	DESCRIPTION
		"&<caiW2kOs.275>Flag indicating whether the number of threads of the process should be monitored and if so, the level of alert to raise."
	DEFVAL { 0 }
	::= { w2kStatusProcEntry 24 }


w2kStatusProcThreadStatus OBJECT-TYPE
	SYNTAX INTEGER {
		unknown(1),
		up(2),
		down-warning(3),
		down-critical(4)
	}
	ACCESS read-only
	STATUS mandatory
	DESCRIPTION
		"&<caiW2kOs.683>The current status of the threads number as determined by the thresholds. The status 'unknown' means that the current value could not be retrieved from the system."
	::= { w2kStatusProcEntry 25 }


w2kStatusProcMemoryValue OBJECT-TYPE
	SYNTAX INTEGER
	ACCESS read-only
	STATUS mandatory
	DESCRIPTION
		"&<caiW2kOs.684>The current value of the memory usage of the process (sum of 'Working Set Size' and 'Used Page File' in kilobytes), build as the maximum over all process instances."
	::= { w2kStatusProcEntry 26 }


w2kStatusProcMemoryWarn OBJECT-TYPE
	SYNTAX INTEGER
	ACCESS read-write
	STATUS mandatory
	DESCRIPTION
		"&<caiW2kOs.276>Warning threshold for the memory usage of the process (in kilobytes). If there is more than one process instance, the maximum of all instances is compared with this value. Valid values are greater than 0 and smaller than the critical threshold."
	::= { w2kStatusProcEntry 27 }


w2kStatusProcMemoryCrit OBJECT-TYPE
	SYNTAX INTEGER
	ACCESS read-write
	STATUS mandatory
	DESCRIPTION
		"&<caiW2kOs.277>Critical threshold for the memory usage of the process (in kilobytes). If there is more than one process instance, the maximum of all instances is compared with this value. Valid values are greater than 1 and greater than the warning threshold."
	::= { w2kStatusProcEntry 28 }


w2kStatusProcMemoryMonitor OBJECT-TYPE
	SYNTAX INTEGER {
		do-not-monitor(1),
		warning-only(2),
		critical-only(3),
		both(4)
	}
	ACCESS read-write
	STATUS mandatory
	DESCRIPTION
		"&<caiW2kOs.278>Flag indicating whether the memory usage of the process should be monitored and if so, which threshold should be compared with."
	DEFVAL { 0 }
	::= { w2kStatusProcEntry 29 }


w2kStatusProcMemoryStatus OBJECT-TYPE
	SYNTAX INTEGER {
		unknown(1),
		ok(2),
		warning(3),
		critical(4)
	}
	ACCESS read-only
	STATUS mandatory
	DESCRIPTION
		"&<caiW2kOs.688>The current status of the process memory usage as determined by the thresholds. The status 'unknown' means that the current value could not be retrieved from the system."
	::= { w2kStatusProcEntry 30 }


w2kStatusProcCpuValue OBJECT-TYPE
	SYNTAX INTEGER
	ACCESS read-only
	STATUS mandatory
	DESCRIPTION
		"&<caiW2kOs.689>The current value of the CPU usage of the process (as percentage value of 100), build as the maximum over all process instances."
	::= { w2kStatusProcEntry 31 }


w2kStatusProcCpuWarn OBJECT-TYPE
	SYNTAX INTEGER
	ACCESS read-write
	STATUS mandatory
	DESCRIPTION
		"&<caiW2kOs.279>Warning threshold for the CPU usage of the process (as percentage value of 100). If there is more than one process instance, the maximum of all instances is compared with this value. Valid values are 1 to 99 and smaller than the critical threshold."
	::= { w2kStatusProcEntry 32 }


w2kStatusProcCpuCrit OBJECT-TYPE
	SYNTAX INTEGER
	ACCESS read-write
	STATUS mandatory
	DESCRIPTION
		"&<caiW2kOs.280>Critical threshold for the CPU usage of the process (as percentage value of 100). If there is more than one process instance, the maximum of all instances is compared with this value. Valid values are 2 to 100 and greater than the warning threshold."
	::= { w2kStatusProcEntry 33 }


w2kStatusProcCpuMonitor OBJECT-TYPE
	SYNTAX INTEGER {
		do-not-monitor(1),
		warning-only(2),
		critical-only(3),
		both(4)
	}
	ACCESS read-write
	STATUS mandatory
	DESCRIPTION
		"&<caiW2kOs.281>Flag indicating whether the CPU usage of the process should be monitored and if so, which threshold should be compared with."
	DEFVAL { 0 }
	::= { w2kStatusProcEntry 34 }


w2kStatusProcCpuStatus OBJECT-TYPE
	SYNTAX INTEGER {
		unknown(1),
		ok(2),
		warning(3),
		critical(4)
	}
	ACCESS read-only
	STATUS mandatory
	DESCRIPTION
		"&<caiW2kOs.693>The current status of the process CPU usage as determined by the thresholds. The status 'unknown' means that the current value could not be retrieved from the system."
	::= { w2kStatusProcEntry 35 }


w2kStatusProcCallBackRef OBJECT-TYPE
	SYNTAX DisplayString
	ACCESS read-only
	STATUS mandatory
	DESCRIPTION
		"&<caiW2kOs.443>The name of the Call-Back reference that should be invoked in case of a status change."
	::= { w2kStatusProcEntry 36 }


w2kStatusProcButton OBJECT-TYPE
	SYNTAX INTEGER {
		none(1),
		remove(2)
	}
	ACCESS read-write
	STATUS mandatory
	DESCRIPTION
		"&<caiW2kOs.530>This attribute is used to remove this watcher."
	::= { w2kStatusProcEntry 37 }




--	------------------------------------------------------------------------
--      Services Status Group
--	------------------------------------------------------------------------


w2kStatusSrvcCount OBJECT-TYPE
	SYNTAX INTEGER
	ACCESS read-only
	STATUS mandatory
	DESCRIPTION
		"&<caiW2kOs.696>The number of entries in the w2kStatusSrvcTable."
	::= { w2kStatusSrvcGroup 1 }


w2kStatusSrvcTable OBJECT-TYPE
	SYNTAX SEQUENCE OF W2kStatusSrvcRow
	ACCESS not-accessible
	STATUS mandatory
	DESCRIPTION
		"&<caiW2kOs.697>A table containing information about all monitored services."
	::= { w2kStatusSrvcGroup 2 }


w2kStatusSrvcEntry OBJECT-TYPE
	SYNTAX W2kStatusSrvcRow
	ACCESS not-accessible
	STATUS mandatory
	DESCRIPTION
		"&<caiW2kOs.154>The table entry."
	INDEX { w2kStatusSrvcName }
	::= { w2kStatusSrvcTable 1 }


W2kStatusSrvcRow ::=
	SEQUENCE {
		w2kStatusSrvcName DisplayString,
		w2kStatusSrvcDescription DisplayString,
		w2kStatusSrvcDescr DisplayString,
		w2kStatusSrvcAutoWatcherName DisplayString,
		w2kStatusSrvcAggLagValue INTEGER,
		w2kStatusSrvcAggLag INTEGER,
		w2kStatusSrvcAggStatus INTEGER,
		w2kStatusSrvcExist INTEGER,
		w2kStatusSrvcExistMonitor INTEGER,
		w2kStatusSrvcExistStatus INTEGER,
		w2kStatusSrvcActiveValue INTEGER,
		w2kStatusSrvcActive INTEGER,
		w2kStatusSrvcActiveMonitor INTEGER,
		w2kStatusSrvcActiveStatus INTEGER,
		w2kStatusSrvcCallBackRef DisplayString,
		w2kStatusSrvcButton INTEGER
	}


w2kStatusSrvcName OBJECT-TYPE
	SYNTAX DisplayString
	ACCESS read-only
	STATUS mandatory
	DESCRIPTION
		"&<caiW2kOs.699>Name of the watcher, monitoring a service with this name. Important: This name is case insensitive."
	::= { w2kStatusSrvcEntry 1 }


w2kStatusSrvcDescription OBJECT-TYPE
	SYNTAX DisplayString
	ACCESS read-write
	STATUS mandatory
	DESCRIPTION
		"&<caiW2kOs.136>Any description for this watcher."
	::= { w2kStatusSrvcEntry 2 }


w2kStatusSrvcDescr OBJECT-TYPE
	SYNTAX DisplayString
	ACCESS read-only
	STATUS mandatory
	DESCRIPTION
		"&<caiW2kOs.701>The description of the service."
::= { w2kStatusSrvcEntry 3 }


w2kStatusSrvcAutoWatcherName OBJECT-TYPE
	SYNTAX DisplayString
	ACCESS read-only
	STATUS mandatory
	DESCRIPTION
		"&<caiW2kOs.498>Name of the auto discovery watcher, which created this watcher."
	::= { w2kStatusSrvcEntry 4 }


w2kStatusSrvcAggLagValue OBJECT-TYPE
	SYNTAX INTEGER
	ACCESS read-only
	STATUS mandatory
	DESCRIPTION
		"&<caiW2kOs.499>The number of consecutive poll intervals on which any status was not in the Ok or Up state."
	::= { w2kStatusSrvcEntry 5 }


w2kStatusSrvcAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusSrvcEntry 6 }


w2kStatusSrvcAggStatus OBJECT-TYPE
	SYNTAX INTEGER {
		unknown(1),
		ok(2),
		warning(3),
		critical(4)
	}
	ACCESS read-only
	STATUS mandatory
	DESCRIPTION
		"&<caiW2kOs.705>The current status of the service as a 'worst case' aggregate of all its statuses."
	::= { w2kStatusSrvcEntry 7 }


w2kStatusSrvcExist OBJECT-TYPE
	SYNTAX INTEGER {
		should-exist(1),
		should-not-exist(2)
	}
	ACCESS read-write
	STATUS mandatory
	DESCRIPTION
		"&<caiW2kOs.289>Flag indicating whether to raise an alert if a service is existent or if it is not-existent."
	DEFVAL { 0 }
	::= { w2kStatusSrvcEntry 8 }


w2kStatusSrvcExistMonitor OBJECT-TYPE
	SYNTAX INTEGER {
		do-not-monitor(1),
		down-warning(2),
		down-critical(3)
	}
	ACCESS read-write
	STATUS mandatory
	DESCRIPTION
		"&<caiW2kOs.290>Flag indicating whether the existence of the service should be monitored and if so, the level of alert to raise."
	DEFVAL { 0 }
	::= { w2kStatusSrvcEntry 9 }


w2kStatusSrvcExistStatus OBJECT-TYPE
	SYNTAX INTEGER {
		unknown(1),
		up(2),
		down-warning(3),
		down-critical(4)
	}
	ACCESS read-only
	STATUS mandatory
	DESCRIPTION
		"&<caiW2kOs.708>The current status of the service existence."
	::= { w2kStatusSrvcEntry 10 }


w2kStatusSrvcActiveValue OBJECT-TYPE
	SYNTAX INTEGER {
		unknown(1),
		active-running(2),
		active-pausePending(3),
		active-stopPending(4),
		notActive-stopped(5),
		notActive-paused(6),
		notActive-continuePending(7),
		notActive-startPending(8)
	}
	ACCESS read-only
	STATUS mandatory
	DESCRIPTION
		"&<caiW2kOs.709>The current value of the service activity."
	::= { w2kStatusSrvcEntry 11 }


w2kStatusSrvcActive OBJECT-TYPE
	SYNTAX INTEGER {
		should-be-active(1),
		should-not-be-active(2)
	}
	ACCESS read-write
	STATUS mandatory
	DESCRIPTION
		"&<caiW2kOs.291>Flag indicating whether to raise an alert if an existent service is active or if it is inactive."
	DEFVAL { 0 }
	::= { w2kStatusSrvcEntry 12 }


w2kStatusSrvcActiveMonitor OBJECT-TYPE
	SYNTAX INTEGER {
		do-not-monitor(1),
		down-warning(2),
		down-critical(3)
	}
	ACCESS read-write
	STATUS mandatory
	DESCRIPTION
		"&<caiW2kOs.292>Flag indicating whether the activity of the service should be monitored and if so, the level of alert to raise."
	DEFVAL { 0 }
	::= { w2kStatusSrvcEntry 13 }


w2kStatusSrvcActiveStatus OBJECT-TYPE
	SYNTAX INTEGER {
		unknown(1),
		up(2),
		down-warning(3),
		down-critical(4)
	}
	ACCESS read-only
	STATUS mandatory
	DESCRIPTION
		"&<caiW2kOs.712>The current status of the service activity as determined by the condition. The status 'unknown' means that the current value could not be retrieved from the system."
	::= { w2kStatusSrvcEntry 14 }


w2kStatusSrvcCallBackRef OBJECT-TYPE
	SYNTAX DisplayString
	ACCESS read-only
	STATUS mandatory
	DESCRIPTION
		"&<caiW2kOs.443>The name of the Call-Back reference that should be invoked in case of a status change."
	::= { w2kStatusSrvcEntry 15 }


w2kStatusSrvcButton OBJECT-TYPE
	SYNTAX INTEGER {
		none(1),
		remove(2)
	}
	ACCESS read-write
	STATUS mandatory
	DESCRIPTION
		"&<caiW2kOs.530>This attribute is used to remove this watcher."
	::= { w2kStatusSrvcEntry 16 }




--	------------------------------------------------------------------------
--      Jobs Status Group
--	------------------------------------------------------------------------


w2kStatusJobCount OBJECT-TYPE
	SYNTAX INTEGER
	ACCESS read-only
	STATUS mandatory
	DESCRIPTION
		"&<caiW2kOs.715>The number of entries in the w2kStatusJobTable."
	::= { w2kStatusJobGroup 1 }


w2kStatusJobTable OBJECT-TYPE
	SYNTAX SEQUENCE OF W2kStatusJobRow
	ACCESS not-accessible
	STATUS mandatory
	DESCRIPTION
		"&<caiW2kOs.716>A table containing information about all monitored jobs."
	::= { w2kStatusJobGroup 2 }


w2kStatusJobEntry OBJECT-TYPE
	SYNTAX W2kStatusJobRow
	ACCESS not-accessible
	STATUS mandatory
	DESCRIPTION
		"&<caiW2kOs.154>The table entry."
	INDEX { w2kStatusJobName }
	::= { w2kStatusJobTable 1 }


W2kStatusJobRow ::=
	SEQUENCE {
		w2kStatusJobName DisplayString,
		w2kStatusJobDescription DisplayString,
		w2kStatusJobAggLagValue INTEGER,
		w2kStatusJobAggLag INTEGER,
		w2kStatusJobAggStatus INTEGER,
		w2kStatusJobExist INTEGER,
		w2kStatusJobExistMonitor INTEGER,
		w2kStatusJobExistStatus INTEGER,
		w2kStatusJobProcessValue INTEGER,
		w2kStatusJobProcessMin INTEGER,
		w2kStatusJobProcessMax INTEGER,
		w2kStatusJobProcessMonitor INTEGER,
		w2kStatusJobProcessStatus INTEGER,
		w2kStatusJobCpuValue INTEGER,
		w2kStatusJobCpuWarn INTEGER,
		w2kStatusJobCpuCrit INTEGER,
		w2kStatusJobCpuMonitor INTEGER,
		w2kStatusJobCpuStatus INTEGER,
		w2kStatusJobCallBackRef DisplayString,
		w2kStatusJobButton INTEGER
	}


w2kStatusJobName OBJECT-TYPE
	SYNTAX DisplayString
	ACCESS read-only
	STATUS mandatory
	DESCRIPTION
		"&<caiW2kOs.718>Name of the watcher, monitoring a job with this name. Important: This name is case insensitive."
	::= { w2kStatusJobEntry 1 }


w2kStatusJobDescription OBJECT-TYPE
	SYNTAX DisplayString
	ACCESS read-write
	STATUS mandatory
	DESCRIPTION
		"&<caiW2kOs.136>Any description for this watcher."
	::= { w2kStatusJobEntry 2 }


w2kStatusJobAggLagValue OBJECT-TYPE
	SYNTAX INTEGER
	ACCESS read-only
	STATUS mandatory
	DESCRIPTION
		"&<caiW2kOs.499>The number of consecutive poll intervals on which any status was not in the Ok or Up state."
	::= { w2kStatusJobEntry 3 }


w2kStatusJobAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusJobEntry 4 }


w2kStatusJobAggStatus OBJECT-TYPE
	SYNTAX INTEGER {
		unknown(1),
		ok(2),
		warning(3),
		critical(4)
	}
	ACCESS read-only
	STATUS mandatory
	DESCRIPTION
		"&<caiW2kOs.722>The current status of the job as a 'worst case' aggregate of all its statuses."
	::= { w2kStatusJobEntry 5 }


w2kStatusJobExist OBJECT-TYPE
	SYNTAX INTEGER {
		should-exist(1),
		should-not-exist(2)
	}
	ACCESS read-write
	STATUS mandatory
	DESCRIPTION
		"&<caiW2kOs.311>Flag indicating whether to raise an alert if a job is existent or if it is not-existent."
	DEFVAL { 0 }
	::= { w2kStatusJobEntry 6 }


w2kStatusJobExistMonitor OBJECT-TYPE
	SYNTAX INTEGER {
		do-not-monitor(1),
		down-warning(2),
		down-critical(3)
	}
	ACCESS read-write
	STATUS mandatory
	DESCRIPTION
		"&<caiW2kOs.312>Flag indicating whether the existence of the job should be monitored and if so, the level of alert to raise."
	DEFVAL { 0 }
	::= { w2kStatusJobEntry 7 }


w2kStatusJobExistStatus OBJECT-TYPE
	SYNTAX INTEGER {
		unknown(1),
		up(2),
		down-warning(3),
		down-critical(4)
	}
	ACCESS read-only
	STATUS mandatory
	DESCRIPTION
		"&<caiW2kOs.725>The current status of the job existence."
	::= { w2kStatusJobEntry 8 }


w2kStatusJobProcessValue OBJECT-TYPE
	SYNTAX INTEGER
	ACCESS read-only
	STATUS mandatory
	DESCRIPTION
		"&<caiW2kOs.726>The current value of the active processes number."
	::= { w2kStatusJobEntry 9 }


w2kStatusJobProcessMin OBJECT-TYPE
	SYNTAX INTEGER
	ACCESS read-write
	STATUS mandatory
	DESCRIPTION
		"&<caiW2kOs.313>Minimum threshold for the number of active processes associated with the job. Valid values are greater than or equal to -1 and smaller than or equal to the maximum threshold. Setting to -1 disables the monitoring of the minimum."
	DEFVAL { -2 }
	::= { w2kStatusJobEntry 10 }


w2kStatusJobProcessMax OBJECT-TYPE
	SYNTAX INTEGER
	ACCESS read-write
	STATUS mandatory
	DESCRIPTION
		"&<caiW2kOs.314>Maximum threshold for the number of active processes associated with the job. Valid values are greater than or equal to -1 and greater than or equal to the minimum threshold. Setting to -1 disables the monitoring of the maximum."
	DEFVAL { -2 }
	::= { w2kStatusJobEntry 11 }


w2kStatusJobProcessMonitor OBJECT-TYPE
	SYNTAX INTEGER {
		do-not-monitor(1),
		down-warning(2),
		down-critical(3)
	}
	ACCESS read-write
	STATUS mandatory
	DESCRIPTION
		"&<caiW2kOs.315>Flag indicating whether the number of active processes associated with the job should be monitored and if so, the level of alert to raise."
	DEFVAL { 0 }
	::= { w2kStatusJobEntry 12 }


w2kStatusJobProcessStatus OBJECT-TYPE
	SYNTAX INTEGER {
		unknown(1),
		up(2),
		down-warning(3),
		down-critical(4)
	}
	ACCESS read-only
	STATUS mandatory
	DESCRIPTION
		"&<caiW2kOs.730>The current status of the active processes number as determined by the thresholds. The status 'unknown' means that the current value could not be retrieved from the system."
	::= { w2kStatusJobEntry 13 }


w2kStatusJobCpuValue OBJECT-TYPE
	SYNTAX INTEGER
	ACCESS read-only
	STATUS mandatory
	DESCRIPTION
		"&<caiW2kOs.731>The current value of the job's CPU usage (as percentage value of 100)."
	::= { w2kStatusJobEntry 14 }


w2kStatusJobCpuWarn OBJECT-TYPE
	SYNTAX INTEGER
	ACCESS read-write
	STATUS mandatory
	DESCRIPTION
		"&<caiW2kOs.316>Warning threshold for the CPU usage of the job (as percentage value of 100). Valid values are 1 to 99 and smaller than the critical threshold."
	::= { w2kStatusJobEntry 15 }


w2kStatusJobCpuCrit OBJECT-TYPE
	SYNTAX INTEGER
	ACCESS read-write
	STATUS mandatory
	DESCRIPTION
		"&<caiW2kOs.317>Critical threshold for the CPU usage of the job (as percentage value of 100). Valid values are 2 to 100 and greater than the warning threshold."
	::= { w2kStatusJobEntry 16 }


w2kStatusJobCpuMonitor OBJECT-TYPE
	SYNTAX INTEGER {
		do-not-monitor(1),
		warning-only(2),
		critical-only(3),
		both(4)
	}
	ACCESS read-write
	STATUS mandatory
	DESCRIPTION
		"&<caiW2kOs.318>Flag indicating whether the CPU usage of the job should be monitored and if so, which threshold should be compared with."
	DEFVAL { 0 }
	::= { w2kStatusJobEntry 17 }


w2kStatusJobCpuStatus OBJECT-TYPE
	SYNTAX INTEGER {
		unknown(1),
		ok(2),
		warning(3),
		critical(4)
	}
	ACCESS read-only
	STATUS mandatory
	DESCRIPTION
		"&<caiW2kOs.735>The current status of the job's CPU usage as determined by the thresholds. The status 'unknown' means that the current value could not be retrieved from the system."
	::= { w2kStatusJobEntry 18 }


w2kStatusJobCallBackRef OBJECT-TYPE
	SYNTAX DisplayString
	ACCESS read-only
	STATUS mandatory
	DESCRIPTION
		"&<caiW2kOs.443>The name of the Call-Back reference that should be invoked in case of a status change."
	::= { w2kStatusJobEntry 19 }


w2kStatusJobButton OBJECT-TYPE
	SYNTAX INTEGER {
		none(1),
		remove(2)
	}
	ACCESS read-write
	STATUS mandatory
	DESCRIPTION
		"&<caiW2kOs.530>This attribute is used to remove this watcher."
	::= { w2kStatusJobEntry 20 }



--	------------------------------------------------------------------------
--      Sessions Status Group
--	------------------------------------------------------------------------


w2kStatusSessCount OBJECT-TYPE
	SYNTAX INTEGER
	ACCESS read-only
	STATUS mandatory
	DESCRIPTION
		"&<caiW2kOs.738>The number of entries in the w2kStatusSessTable."
	::= { w2kStatusSessGroup 1 }


w2kStatusSessTable OBJECT-TYPE
	SYNTAX SEQUENCE OF W2kStatusSessRow
	ACCESS not-accessible
	STATUS mandatory
	DESCRIPTION
		"&<caiW2kOs.739>A table containing information about all monitored sessions."
	::= { w2kStatusSessGroup 2 }


w2kStatusSessEntry OBJECT-TYPE
	SYNTAX W2kStatusSessRow
	ACCESS not-accessible
	STATUS mandatory
	DESCRIPTION
		"&<caiW2kOs.154>The table entry."
	INDEX { w2kStatusSessClientName, w2kStatusSessUserName }
	::= { w2kStatusSessTable 1 }


W2kStatusSessRow ::=
	SEQUENCE {
		w2kStatusSessClientName DisplayString,
		w2kStatusSessUserName DisplayString,
		w2kStatusSessDescription DisplayString,
		w2kStatusSessIds DisplayString,
		w2kStatusSessAggLagValue INTEGER,
		w2kStatusSessAggLag INTEGER,
		w2kStatusSessAggStatus INTEGER,
		w2kStatusSessInstValue INTEGER,
		w2kStatusSessInstMin INTEGER,
		w2kStatusSessInstMax INTEGER,
		w2kStatusSessInstMonitor INTEGER,
		w2kStatusSessInstStatus INTEGER,
		w2kStatusSessMemoryValue INTEGER,
		w2kStatusSessMemoryWarn INTEGER,
		w2kStatusSessMemoryCrit INTEGER,
		w2kStatusSessMemoryMonitor INTEGER,
		w2kStatusSessMemoryStatus INTEGER,
		w2kStatusSessCpuValue INTEGER,
		w2kStatusSessCpuWarn INTEGER,
		w2kStatusSessCpuCrit INTEGER,
		w2kStatusSessCpuMonitor INTEGER,
		w2kStatusSessCpuStatus INTEGER,
		w2kStatusSessCallBackRef DisplayString,
		w2kStatusSessButton INTEGER
	}


w2kStatusSessClientName OBJECT-TYPE
	SYNTAX DisplayString
	ACCESS read-only
	STATUS mandatory
	DESCRIPTION
		"&<caiW2kOs.741>Client name of the watcher, monitoring a session with this client name. The client name is the name of the host, from where this session was initiated. An asterisk '*' can be used as client name or can be prepended/appended to it, in order to widen the scope of sessions this watcher monitors. Important: This name is case insensitive."
	::= { w2kStatusSessEntry 1 }


w2kStatusSessUserName OBJECT-TYPE
	SYNTAX DisplayString
	ACCESS read-only
	STATUS mandatory
	DESCRIPTION
		"&<caiW2kOs.742>User name of the watcher, monitoring a session with this user name. The user name specifies the user, who logged in and is in the form 'domainName\\userName'. An asterisk '*' can be used as user name or can be prepended/appended to it, in order to widen the scope of sessions this watcher monitors. Important: This name is case insensitive."
	::= { w2kStatusSessEntry 2 }


w2kStatusSessDescription OBJECT-TYPE
	SYNTAX DisplayString
	ACCESS read-write
	STATUS mandatory
	DESCRIPTION
		"&<caiW2kOs.136>Any description for this watcher."
	::= { w2kStatusSessEntry 3 }


w2kStatusSessIds OBJECT-TYPE
	SYNTAX DisplayString
	ACCESS read-only
	STATUS mandatory
	DESCRIPTION
		"&<caiW2kOs.744>A pipe sign separated list of the ids of those sessions, that (b)reach any threshold (except instance metric)."
	::= { w2kStatusSessEntry 4 }


w2kStatusSessAggLagValue OBJECT-TYPE
	SYNTAX INTEGER
	ACCESS read-only
	STATUS mandatory
	DESCRIPTION
		"&<caiW2kOs.499>The number of consecutive poll intervals on which any status was not in the Ok or Up state."
	::= { w2kStatusSessEntry 5 }


w2kStatusSessAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusSessEntry 6 }


w2kStatusSessAggStatus OBJECT-TYPE
	SYNTAX INTEGER {
		unknown(1),
		ok(2),
		warning(3),
		critical(4)
	}
	ACCESS read-only
	STATUS mandatory
	DESCRIPTION
		"&<caiW2kOs.747>The current status of the session as a 'worst case' aggregate of all its statuses."
	::= { w2kStatusSessEntry 7 }


w2kStatusSessInstValue OBJECT-TYPE
	SYNTAX INTEGER
	ACCESS read-only
	STATUS mandatory
	DESCRIPTION
		"&<caiW2kOs.748>The current value of the session instances number."
	::= { w2kStatusSessEntry 8 }


w2kStatusSessInstMin OBJECT-TYPE
	SYNTAX INTEGER
	ACCESS read-write
	STATUS mandatory
	DESCRIPTION
		"&<caiW2kOs.326>Minimum threshold for the number of session instances. Valid values are greater than or equal to -1 and smaller than or equal to the maximum threshold. Setting to -1 disables the monitoring of the minimum."
	DEFVAL { -2 }
	::= { w2kStatusSessEntry 9 }


w2kStatusSessInstMax OBJECT-TYPE
	SYNTAX INTEGER
	ACCESS read-write
	STATUS mandatory
	DESCRIPTION
		"&<caiW2kOs.327>Maximum threshold for the number of session instances. Valid values are greater than or equal to -1 and greater than or equal to the minimum threshold. Setting to -1 disables the monitoring of the maximum."
	DEFVAL { -2 }
	::= { w2kStatusSessEntry 10 }


w2kStatusSessInstMonitor OBJECT-TYPE
	SYNTAX INTEGER {
		do-not-monitor(1),
		down-warning(2),
		down-critical(3)
	}
	ACCESS read-write
	STATUS mandatory
	DESCRIPTION
		"&<caiW2kOs.328>Flag indicating whether the number of session instances should be monitored and if so, the level of alert to raise."
	DEFVAL { 0 }
	::= { w2kStatusSessEntry 11 }


w2kStatusSessInstStatus OBJECT-TYPE
	SYNTAX INTEGER {
		unknown(1),
		up(2),
		down-warning(3),
		down-critical(4)
	}
	ACCESS read-only
	STATUS mandatory
	DESCRIPTION
		"&<caiW2kOs.752>The current status of the session instances number as determined by the thresholds. The status 'unknown' means that the current value could not be retrieved from the system."
	::= { w2kStatusSessEntry 12 }


w2kStatusSessMemoryValue OBJECT-TYPE
	SYNTAX INTEGER
	ACCESS read-only
	STATUS mandatory
	DESCRIPTION
		"&<caiW2kOs.753>The current value of the session's memory usage (sum of 'Working Set Size' and 'Used Page File' in kilobytes), build as the maximum over all session instances."
	::= { w2kStatusSessEntry 13 }


w2kStatusSessMemoryWarn OBJECT-TYPE
	SYNTAX INTEGER
	ACCESS read-write
	STATUS mandatory
	DESCRIPTION
		"&<caiW2kOs.329>Warning threshold for the memory usage of the session (in kilobytes). If there is more than one session instance, the maximum of all instances is compared with this value. Valid values are greater than 0 and smaller than the critical threshold."
	::= { w2kStatusSessEntry 14 }


w2kStatusSessMemoryCrit OBJECT-TYPE
	SYNTAX INTEGER
	ACCESS read-write
	STATUS mandatory
	DESCRIPTION
		"&<caiW2kOs.330>Critical threshold for the memory usage of the session (in kilobytes). If there is more than one session instance, the maximum of all instances is compared with this value. Valid values are greater than 1 and greater than the warning threshold."
	::= { w2kStatusSessEntry 15 }


w2kStatusSessMemoryMonitor OBJECT-TYPE
	SYNTAX INTEGER {
		do-not-monitor(1),
		warning-only(2),
		critical-only(3),
		both(4)
	}
	ACCESS read-write
	STATUS mandatory
	DESCRIPTION
		"&<caiW2kOs.331>Flag indicating whether the memory usage of the session should be monitored and if so, which threshold should be compared with."
	DEFVAL { 0 }
	::= { w2kStatusSessEntry 16 }


w2kStatusSessMemoryStatus OBJECT-TYPE
	SYNTAX INTEGER {
		unknown(1),
		ok(2),
		warning(3),
		critical(4)
	}
	ACCESS read-only
	STATUS mandatory
	DESCRIPTION
		"&<caiW2kOs.757>The current status of the session's memory usage as determined by the thresholds. The status 'unknown' means that the current value could not be retrieved from the system."
	::= { w2kStatusSessEntry 17 }


w2kStatusSessCpuValue OBJECT-TYPE
	SYNTAX INTEGER
	ACCESS read-only
	STATUS mandatory
	DESCRIPTION
		"&<caiW2kOs.758>The current value of the session's CPU usage (as percentage value of 100), build as the maximum over all session instances."
	::= { w2kStatusSessEntry 18 }


w2kStatusSessCpuWarn OBJECT-TYPE
	SYNTAX INTEGER
	ACCESS read-write
	STATUS mandatory
	DESCRIPTION
		"&<caiW2kOs.332>Warning threshold for the CPU usage of the session (as percentage value of 100). If there is more than one session instance, the maximum of all instances is compared with this value. Valid values are 1 to 99 and smaller than the critical threshold."
	::= { w2kStatusSessEntry 19 }


w2kStatusSessCpuCrit OBJECT-TYPE
	SYNTAX INTEGER
	ACCESS read-write
	STATUS mandatory
	DESCRIPTION
		"&<caiW2kOs.333>Critical threshold for the CPU usage of the session (as percentage value of 100). If there is more than one session instance, the maximum of all instances is compared with this value. Valid values are 2 to 100 and greater than the warning threshold."
	::= { w2kStatusSessEntry 20 }


w2kStatusSessCpuMonitor OBJECT-TYPE
	SYNTAX INTEGER {
		do-not-monitor(1),
		warning-only(2),
		critical-only(3),
		both(4)
	}
	ACCESS read-write
	STATUS mandatory
	DESCRIPTION
		"&<caiW2kOs.334>Flag indicating whether the CPU usage of the session should be monitored and if so, which threshold should be compared with."
	DEFVAL { 0 }
	::= { w2kStatusSessEntry 21 }


w2kStatusSessCpuStatus OBJECT-TYPE
	SYNTAX INTEGER {
		unknown(1),
		ok(2),
		warning(3),
		critical(4)
	}
	ACCESS read-only
	STATUS mandatory
	DESCRIPTION
		"&<caiW2kOs.762>The current status of the session's CPU usage as determined by the thresholds. The status 'unknown' means that the current value could not be retrieved from the system."
	::= { w2kStatusSessEntry 22 }


w2kStatusSessCallBackRef OBJECT-TYPE
	SYNTAX DisplayString
	ACCESS read-only
	STATUS mandatory
	DESCRIPTION
		"&<caiW2kOs.443>The name of the Call-Back reference that should be invoked in case of a status change."
	::= { w2kStatusSessEntry 23 }


w2kStatusSessButton OBJECT-TYPE
	SYNTAX INTEGER {
		none(1),
		remove(2)
	}
	ACCESS read-write
	STATUS mandatory
	DESCRIPTION
		"&<caiW2kOs.530>This attribute is used to remove this watcher."
	::= { w2kStatusSessEntry 24 }




--	------------------------------------------------------------------------
-- Printer Status Group
--	------------------------------------------------------------------------


w2kStatusPrnCount OBJECT-TYPE
	SYNTAX INTEGER
	ACCESS read-only
	STATUS mandatory
	DESCRIPTION
		"&<caiW2kOs.765>The number of entries in the w2kStatusPrnTable."
	::= { w2kStatusPrnGroup 1 }


w2kStatusPrnTable OBJECT-TYPE
	SYNTAX SEQUENCE OF W2kStatusPrnRow
	ACCESS not-accessible
	STATUS mandatory
	DESCRIPTION
		"&<caiW2kOs.766>A table containing information about all monitored printers."
	::= { w2kStatusPrnGroup 2 }


w2kStatusPrnEntry OBJECT-TYPE
	SYNTAX W2kStatusPrnRow
	ACCESS not-accessible
	STATUS mandatory
	DESCRIPTION
		"&<caiW2kOs.154>The table entry."
	INDEX { w2kStatusPrnName }
	::= { w2kStatusPrnTable 1 }


W2kStatusPrnRow ::=
	SEQUENCE {
		w2kStatusPrnName DisplayString,
		w2kStatusPrnDescription DisplayString,
		w2kStatusPrnAutoWatcherName DisplayString,
		w2kStatusPrnAggLagValue INTEGER,
		w2kStatusPrnAggLag INTEGER,
		w2kStatusPrnAggStatus INTEGER,
		w2kStatusPrnEventDescr INTEGER,
		w2kStatusPrnEventMonitor INTEGER,
		w2kStatusPrnEventStatus INTEGER,
		w2kStatusPrnQueueValue INTEGER,
		w2kStatusPrnQueueWarn INTEGER,
		w2kStatusPrnQueueCrit INTEGER,
		w2kStatusPrnQueueMonitor INTEGER,
		w2kStatusPrnQueueStatus INTEGER,
		w2kStatusPrnLossAction INTEGER,
		w2kStatusPrnLossStatus INTEGER,
		w2kStatusPrnCallBackRef DisplayString,
		w2kStatusPrnButton INTEGER
	}


w2kStatusPrnName OBJECT-TYPE
	SYNTAX DisplayString
	ACCESS read-only
	STATUS mandatory
	DESCRIPTION
		"&<caiW2kOs.768>Name of the watcher, monitoring a local printer with this name. Important: This name is case insensitive."
	::= { w2kStatusPrnEntry 1 }


w2kStatusPrnDescription OBJECT-TYPE
	SYNTAX DisplayString
	ACCESS read-write
	STATUS mandatory
	DESCRIPTION
		"&<caiW2kOs.136>Any description for this watcher."
	::= { w2kStatusPrnEntry 2 }


w2kStatusPrnAutoWatcherName OBJECT-TYPE
	SYNTAX DisplayString
	ACCESS read-only
	STATUS mandatory
	DESCRIPTION
		"&<caiW2kOs.498>Name of the auto discovery watcher, which created this watcher."
	::= { w2kStatusPrnEntry 3 }


w2kStatusPrnAggLagValue OBJECT-TYPE
	SYNTAX INTEGER
	ACCESS read-only
	STATUS mandatory
	DESCRIPTION
		"&<caiW2kOs.499>The number of consecutive poll intervals on which any status was not in the Ok or Up state."
	::= { w2kStatusPrnEntry 4 }


w2kStatusPrnAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusPrnEntry 5 }


w2kStatusPrnAggStatus OBJECT-TYPE
	SYNTAX INTEGER {
		unknown(1),
		ok(2),
		warning(3),
		critical(4)
	}
	ACCESS read-only
	STATUS mandatory
	DESCRIPTION
		"&<caiW2kOs.773>The current status of the printer as a 'worst case' aggregate of all its statuses."
	::= { w2kStatusPrnEntry 6 }


w2kStatusPrnEventDescr OBJECT-TYPE
	SYNTAX INTEGER {
		unknown-no-print-jobs(1),
		printing(2),
		paper-error(3),
		toner-error(4),
		manual(5),
		offline(6),
		paused(7),
		software-error(8),
		general-error(9)
	}
	ACCESS read-only
	STATUS mandatory
	DESCRIPTION
		"&<caiW2kOs.774>The description of the last printer event. Note: Printer events can only be determined if there is a printing job in the printers queue."
	::= { w2kStatusPrnEntry 7 }


w2kStatusPrnEventMonitor OBJECT-TYPE
	SYNTAX INTEGER {
		do-not-monitor(1),
		down-warning(2),
		down-critical(3)
	}
	ACCESS read-write
	STATUS mandatory
	DESCRIPTION
		"&<caiW2kOs.342>Flag indicating whether the occurence of printer events should be monitored and if so, the level of alert to raise."
	DEFVAL { 0 }
	::= { w2kStatusPrnEntry 8 }


w2kStatusPrnEventStatus OBJECT-TYPE
	SYNTAX INTEGER {
		unknown(1),
		up(2),
		down-warning(3),
		down-critical(4)
	}
	ACCESS read-only
	STATUS mandatory
	DESCRIPTION
		"&<caiW2kOs.776>The current status of the printer event monitoring. Note: Printer events can only be determined if there is a printing job in the printers queue. The status 'unknown' means that the current value could not be retrieved from the system."
	::= { w2kStatusPrnEntry 9 }


w2kStatusPrnQueueValue OBJECT-TYPE
	SYNTAX INTEGER
	ACCESS read-only
	STATUS mandatory
	DESCRIPTION
		"&<caiW2kOs.777>The current value of jobs in the printer's queue."
	::= { w2kStatusPrnEntry 10 }


w2kStatusPrnQueueWarn OBJECT-TYPE
	SYNTAX INTEGER
	ACCESS read-write
	STATUS mandatory
	DESCRIPTION
		"&<caiW2kOs.343>Warning threshold for the number of jobs in the printer's queue. Valid values are greater than 0 and smaller than the critical threshold."
	::= { w2kStatusPrnEntry 11 }


w2kStatusPrnQueueCrit OBJECT-TYPE
	SYNTAX INTEGER
	ACCESS read-write
	STATUS mandatory
	DESCRIPTION
		"&<caiW2kOs.344>Critical threshold for the number of jobs in the printer's queue. Valid values are greater than 1 and greater than the warning threshold."
	::= { w2kStatusPrnEntry 12 }


w2kStatusPrnQueueMonitor OBJECT-TYPE
	SYNTAX INTEGER {
		do-not-monitor(1),
		warning-only(2),
		critical-only(3),
		both(4)
	}
	ACCESS read-write
	STATUS mandatory
	DESCRIPTION
		"&<caiW2kOs.345>Flag indicating whether the printer's job queue should be monitored and if so, which threshold should be compared with."
	DEFVAL { 0 }
	::= { w2kStatusPrnEntry 13 }


w2kStatusPrnQueueStatus OBJECT-TYPE
	SYNTAX INTEGER {
		unknown(1),
		ok(2),
		warning(3),
		critical(4)
	}
	ACCESS read-only
	STATUS mandatory
	DESCRIPTION
		"&<caiW2kOs.781>The current status of the printer queue as determined by the thresholds. The status 'unknown' means that the current value could not be retrieved from the system."
	::= { w2kStatusPrnEntry 14 }


w2kStatusPrnLossAction OBJECT-TYPE
	SYNTAX INTEGER {
		remove(1),
		up(2),
		down-warning(3),
		down-critical(4)
	}
	ACCESS read-write
	STATUS mandatory
	DESCRIPTION
		"&<caiW2kOs.346>Flag defining the severity if the loss of the printer is detected or whether to remove this watcher in that case."
	DEFVAL { 0 }
	::= { w2kStatusPrnEntry 15 }


w2kStatusPrnLossStatus OBJECT-TYPE
	SYNTAX INTEGER {
		unknown(1),
		up(2),
		down-warning(3),
		down-critical(4)
	}
	ACCESS read-only
	STATUS mandatory
	DESCRIPTION
		"&<caiW2kOs.783>The current status of the printer's loss as determined by the loss action."
	::= { w2kStatusPrnEntry 16 }


w2kStatusPrnCallBackRef OBJECT-TYPE
	SYNTAX DisplayString
	ACCESS read-only
	STATUS mandatory
	DESCRIPTION
		"&<caiW2kOs.443>The name of the Call-Back reference that should be invoked in case of a status change."
	::= { w2kStatusPrnEntry 17 }


w2kStatusPrnButton OBJECT-TYPE
	SYNTAX INTEGER {
		none(1),
		remove(2)
	}
	ACCESS read-write
	STATUS mandatory
	DESCRIPTION
		"&<caiW2kOs.530>This attribute is used to remove this watcher."
	::= { w2kStatusPrnEntry 18 }




--	------------------------------------------------------------------------
--      Network Interfaces Status Group
--	------------------------------------------------------------------------


w2kStatusNetTotalAggLagValue OBJECT-TYPE
	SYNTAX INTEGER
	ACCESS read-only
	STATUS mandatory
	DESCRIPTION
		"&<caiW2kOs.499>The number of consecutive poll intervals on which any status was not in the Ok or Up state."
	::= { w2kStatusNetGroup 1 }


w2kStatusNetTotalAggLag OBJECT-TYPE
	SYNTAX INTEGER
	ACCESS read-write
	STATUS mandatory
	DESCRIPTION
		"&<caiW2kOs.137>The number of consecutive poll intervals on which any status is not in the Ok or Up state, before the aggregate status changes. Valid values are greater than 0."
	DEFVAL { 1 }
	::= { w2kStatusNetGroup 2 }


w2kStatusNetTotalAggStatus OBJECT-TYPE
	SYNTAX INTEGER {
		unknown(1),
		ok(2),
		warning(3),
		critical(4)
	}
	ACCESS read-only
	STATUS mandatory
	DESCRIPTION
		"&<caiW2kOs.788>The current status of the network interfaces total as a 'worst case' aggregate of all total statuses."
	::= { w2kStatusNetGroup 3 }


w2kStatusNetTotalInPktValue OBJECT-TYPE
	SYNTAX INTEGER
	ACCESS read-only
	STATUS mandatory
	DESCRIPTION
		"&<caiW2kOs.789>The current total value of the received packets rate (packets per second). The total value is the sum of all network interfaces (except the loopback interface)."
	::= { w2kStatusNetGroup 4 }


w2kStatusNetTotalInPktWarn OBJECT-TYPE
	SYNTAX INTEGER
	ACCESS read-write
	STATUS mandatory
	DESCRIPTION
		"&<caiW2kOs.790>Warning threshold for the total rate of received packets over TCP/IP connections (packets per second). Valid values are greater than 0 and smaller than the critical threshold."
	DEFVAL { 200 }
	::= { w2kStatusNetGroup 5 }


w2kStatusNetTotalInPktCrit OBJECT-TYPE
	SYNTAX INTEGER
	ACCESS read-write
	STATUS mandatory
	DESCRIPTION
		"&<caiW2kOs.791>Critical threshold for the total rate of received packets over TCP/IP connections (packets per second). Valid values are greater than 1 and greater than the warning threshold."
	DEFVAL { 400 }
	::= { w2kStatusNetGroup 6 }


w2kStatusNetTotalInPktMonitor OBJECT-TYPE
	SYNTAX INTEGER {
		do-not-monitor(1),
		warning-only(2),
		critical-only(3),
		both(4)
	}
	ACCESS read-write
	STATUS mandatory
	DESCRIPTION
		"&<caiW2kOs.792>Flag indicating whether the total rate of received packets should be monitored and if so, which threshold should be compared with."
	DEFVAL { 4 }
	::= { w2kStatusNetGroup 7 }


w2kStatusNetTotalInPktStatus OBJECT-TYPE
	SYNTAX INTEGER {
		unknown(1),
		ok(2),
		warning(3),
		critical(4)
	}
	ACCESS read-only
	STATUS mandatory
	DESCRIPTION
		"&<caiW2kOs.793>The current status of the total received packets rate as determined by the thresholds. The status 'unknown' means that the current value could not be retrieved from the system."
	::= { w2kStatusNetGroup 8 }


w2kStatusNetTotalOutPktValue OBJECT-TYPE
	SYNTAX INTEGER
	ACCESS read-only
	STATUS mandatory
	DESCRIPTION
		"&<caiW2kOs.794>The current total value of the sent packets rate (packets per second). The total value is the sum of all network interfaces (except the loopback interface)."
	::= { w2kStatusNetGroup 9 }


w2kStatusNetTotalOutPktWarn OBJECT-TYPE
	SYNTAX INTEGER
	ACCESS read-write
	STATUS mandatory
	DESCRIPTION
		"&<caiW2kOs.795>Warning threshold for the total rate of sent packets over TCP/IP connections (packets per second). Valid values are greater than 0 and smaller than the critical threshold."
	DEFVAL { 200 }
	::= { w2kStatusNetGroup 10 }


w2kStatusNetTotalOutPktCrit OBJECT-TYPE
	SYNTAX INTEGER
	ACCESS read-write
	STATUS mandatory
	DESCRIPTION
		"&<caiW2kOs.796>Critical threshold for the total rate of sent packets over TCP/IP connections (packets per second). Valid values are greater than 1 and greater than the warning threshold."
	DEFVAL { 400 }
	::= { w2kStatusNetGroup 11 }


w2kStatusNetTotalOutPktMonitor OBJECT-TYPE
	SYNTAX INTEGER {
		do-not-monitor(1),
		warning-only(2),
		critical-only(3),
		both(4)
	}
	ACCESS read-write
	STATUS mandatory
	DESCRIPTION
		"&<caiW2kOs.797>Flag indicating whether the total rate of sent packets should be monitored and if so, which threshold should be compared with."
	DEFVAL { 4 }
	::= { w2kStatusNetGroup 12 }


w2kStatusNetTotalOutPktStatus OBJECT-TYPE
	SYNTAX INTEGER {
		unknown(1),
		ok(2),
		warning(3),
		critical(4)
	}
	ACCESS read-only
	STATUS mandatory
	DESCRIPTION
		"&<caiW2kOs.798>The current status of the total sent packets rate as determined by the thresholds. The status 'unknown' means that the current value could not be retrieved from the system."
	::= { w2kStatusNetGroup 13 }


w2kStatusNetTotalInErrDValue OBJECT-TYPE
	SYNTAX INTEGER
	ACCESS read-only
	STATUS mandatory
	DESCRIPTION
		"&<caiW2kOs.799>The current total value of the received errors rate (errors per poll interval). The total value is the sum of all network interfaces (except the loopback interface)."
	::= { w2kStatusNetGroup 14 }


w2kStatusNetTotalInErrDWarn OBJECT-TYPE
	SYNTAX INTEGER
	ACCESS read-write
	STATUS mandatory
	DESCRIPTION
		"&<caiW2kOs.800>Warning threshold for the total rate of received errors over TCP/IP connections (errors per poll interval). Valid values are greater than 0 and smaller than the critical threshold."
	DEFVAL { 20 }
	::= { w2kStatusNetGroup 15 }


w2kStatusNetTotalInErrDCrit OBJECT-TYPE
	SYNTAX INTEGER
	ACCESS read-write
	STATUS mandatory
	DESCRIPTION
		"&<caiW2kOs.801>Critical threshold for the total rate of received errors over TCP/IP connections (errors per poll interval). Valid values are greater than 1 and greater than the warning threshold."
	DEFVAL { 40 }
	::= { w2kStatusNetGroup 16 }


w2kStatusNetTotalInErrDMonitor OBJECT-TYPE
	SYNTAX INTEGER {
		do-not-monitor(1),
		warning-only(2),
		critical-only(3),
		both(4)
	}
	ACCESS read-write
	STATUS mandatory
	DESCRIPTION
		"&<caiW2kOs.802>Flag indicating whether the total rate of received errors should be monitored and if so, which threshold should be compared with."
	DEFVAL { 4 }
	::= { w2kStatusNetGroup 17 }


w2kStatusNetTotalInErrDStatus OBJECT-TYPE
	SYNTAX INTEGER {
		unknown(1),
		ok(2),
		warning(3),
		critical(4)
	}
	ACCESS read-only
	STATUS mandatory
	DESCRIPTION
		"&<caiW2kOs.803>The current status of the total received errors rate as determined by the thresholds. The status 'unknown' means that the current value could not be retrieved from the system."
	::= { w2kStatusNetGroup 18 }


w2kStatusNetTotalOutErrDValue OBJECT-TYPE
	SYNTAX INTEGER
	ACCESS read-only
	STATUS mandatory
	DESCRIPTION
		"&<caiW2kOs.804>The current total value of the sent errors rate (errors per poll interval). The total value is the sum of all network interfaces (except the loopback interface)."
	::= { w2kStatusNetGroup 19 }


w2kStatusNetTotalOutErrDWarn OBJECT-TYPE
	SYNTAX INTEGER
	ACCESS read-write
	STATUS mandatory
	DESCRIPTION
		"&<caiW2kOs.805>Warning threshold for the total rate of sent errors over TCP/IP connections (errors per poll interval). Valid values are greater than 0 and smaller than the critical threshold."
	DEFVAL { 20 }
	::= { w2kStatusNetGroup 20 }


w2kStatusNetTotalOutErrDCrit OBJECT-TYPE
	SYNTAX INTEGER
	ACCESS read-write
	STATUS mandatory
	DESCRIPTION
		"&<caiW2kOs.806>Critical threshold for the total rate of sent errors over TCP/IP connections (errors per poll interval). Valid values are greater than 1 and greater than the warning threshold."
	DEFVAL { 40 }
	::= { w2kStatusNetGroup 21 }


w2kStatusNetTotalOutErrDMonitor OBJECT-TYPE
	SYNTAX INTEGER {
		do-not-monitor(1),
		warning-only(2),
		critical-only(3),
		both(4)
	}
	ACCESS read-write
	STATUS mandatory
	DESCRIPTION
		"&<caiW2kOs.807>Flag indicating whether the total rate of sent errors should be monitored and if so, which threshold should be compared with."
	DEFVAL { 4 }
	::= { w2kStatusNetGroup 22 }


w2kStatusNetTotalOutErrDStatus OBJECT-TYPE
	SYNTAX INTEGER {
		unknown(1),
		ok(2),
		warning(3),
		critical(4)
	}
	ACCESS read-only
	STATUS mandatory
	DESCRIPTION
		"&<caiW2kOs.808>The current status of the total sent errors rate as determined by the thresholds. The status 'unknown' means that the current value could not be retrieved from the system."
	::= { w2kStatusNetGroup 23 }


w2kStatusNetTotalCallBackRef OBJECT-TYPE
	SYNTAX DisplayString
	ACCESS read-only
	STATUS mandatory
	DESCRIPTION
		"&<caiW2kOs.443>The name of the Call-Back reference that should be invoked in case of a status change."
	::= { w2kStatusNetGroup 24 }


w2kStatusNetCount OBJECT-TYPE
	SYNTAX INTEGER
	ACCESS read-only
	STATUS mandatory
	DESCRIPTION
		"&<caiW2kOs.810>The number of entries in the w2kStatusNetTable."
	::= { w2kStatusNetGroup 25 }


w2kStatusNetTable OBJECT-TYPE
	SYNTAX SEQUENCE OF W2kStatusNetRow
	ACCESS not-accessible
	STATUS mandatory
	DESCRIPTION
		"&<caiW2kOs.811>A table containing information about all monitored network interfaces."
	::= { w2kStatusNetGroup 26 }


w2kStatusNetEntry OBJECT-TYPE
	SYNTAX W2kStatusNetRow
	ACCESS not-accessible
	STATUS mandatory
	DESCRIPTION
		"&<caiW2kOs.154>The table entry."
	INDEX { w2kStatusNetName }
	::= { w2kStatusNetTable 1 }


W2kStatusNetRow ::=
	SEQUENCE {
		w2kStatusNetName DisplayString,
		w2kStatusNetAggLagValue INTEGER,
		w2kStatusNetAggLag INTEGER,
		w2kStatusNetAggStatus INTEGER,
		w2kStatusNetInPktValue INTEGER,
		w2kStatusNetInPktWarn INTEGER,
		w2kStatusNetInPktCrit INTEGER,
		w2kStatusNetInPktMonitor INTEGER,
		w2kStatusNetInPktStatus INTEGER,
		w2kStatusNetOutPktValue INTEGER,
		w2kStatusNetOutPktWarn INTEGER,
		w2kStatusNetOutPktCrit INTEGER,
		w2kStatusNetOutPktMonitor INTEGER,
		w2kStatusNetOutPktStatus INTEGER,
		w2kStatusNetInErrDValue INTEGER,
		w2kStatusNetInErrDWarn INTEGER,
		w2kStatusNetInErrDCrit INTEGER,
		w2kStatusNetInErrDMonitor INTEGER,
		w2kStatusNetInErrDStatus INTEGER,
		w2kStatusNetOutErrDValue INTEGER,
		w2kStatusNetOutErrDWarn INTEGER,
		w2kStatusNetOutErrDCrit INTEGER,
		w2kStatusNetOutErrDMonitor INTEGER,
		w2kStatusNetOutErrDStatus INTEGER,
		w2kStatusNetLossAction INTEGER,
		w2kStatusNetLossStatus INTEGER,
		w2kStatusNetCallBackRef DisplayString
	}


w2kStatusNetName OBJECT-TYPE
	SYNTAX DisplayString
	ACCESS read-only
	STATUS mandatory
	DESCRIPTION
		"&<caiW2kOs.813>Name of the watcher, monitoring a network interface with this name."
	::= { w2kStatusNetEntry 1 }


w2kStatusNetAggLagValue OBJECT-TYPE
	SYNTAX INTEGER
	ACCESS read-only
	STATUS mandatory
	DESCRIPTION
		"&<caiW2kOs.499>The number of consecutive poll intervals on which any status was not in the Ok or Up state."
	::= { w2kStatusNetEntry 2 }


w2kStatusNetAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusNetEntry 3 }


w2kStatusNetAggStatus OBJECT-TYPE
	SYNTAX INTEGER {
		unknown(1),
		ok(2),
		warning(3),
		critical(4)
	}
	ACCESS read-only
	STATUS mandatory
	DESCRIPTION
		"&<caiW2kOs.816>The current status of the network interface as a 'worst case' aggregate of all its statuses."
	::= { w2kStatusNetEntry 4 }


w2kStatusNetInPktValue OBJECT-TYPE
	SYNTAX INTEGER
	ACCESS read-only
	STATUS mandatory
	DESCRIPTION
		"&<caiW2kOs.817>The current value of the received packets rate (packets per second)."
	::= { w2kStatusNetEntry 5 }


w2kStatusNetInPktWarn OBJECT-TYPE
	SYNTAX INTEGER
	ACCESS read-write
	STATUS mandatory
	DESCRIPTION
		"&<caiW2kOs.364>Warning threshold for the rate of received packets over TCP/IP connections (packets per second). Valid values are greater than 0 and smaller than the critical threshold."
	::= { w2kStatusNetEntry 6 }


w2kStatusNetInPktCrit OBJECT-TYPE
	SYNTAX INTEGER
	ACCESS read-write
	STATUS mandatory
	DESCRIPTION
		"&<caiW2kOs.365>Critical threshold for the rate of received packets over TCP/IP connections (packets per second). Valid values are greater than 1 and greater than the warning threshold."
	::= { w2kStatusNetEntry 7 }


w2kStatusNetInPktMonitor OBJECT-TYPE
	SYNTAX INTEGER {
		do-not-monitor(1),
		warning-only(2),
		critical-only(3),
		both(4)
	}
	ACCESS read-write
	STATUS mandatory
	DESCRIPTION
		"&<caiW2kOs.366>Flag indicating whether the received packets rate should be monitored and if so, which threshold should be compared with."
	DEFVAL { 0 }
	::= { w2kStatusNetEntry 8 }


w2kStatusNetInPktStatus OBJECT-TYPE
	SYNTAX INTEGER {
		unknown(1),
		ok(2),
		warning(3),
		critical(4)
	}
	ACCESS read-only
	STATUS mandatory
	DESCRIPTION
		"&<caiW2kOs.821>The current status of the received packets rate as determined by the thresholds. The status 'unknown' means that the current value could not be retrieved from the system."
	::= { w2kStatusNetEntry 9 }


w2kStatusNetOutPktValue OBJECT-TYPE
	SYNTAX INTEGER
	ACCESS read-only
	STATUS mandatory
	DESCRIPTION
		"&<caiW2kOs.822>The current value of the sent packets rate (packets per second)."
	::= { w2kStatusNetEntry 10 }


w2kStatusNetOutPktWarn OBJECT-TYPE
	SYNTAX INTEGER
	ACCESS read-write
	STATUS mandatory
	DESCRIPTION
		"&<caiW2kOs.367>Warning threshold for the rate of sent packets over TCP/IP connections (packets per second). Valid values are greater than 0 and smaller than the critical threshold."
	::= { w2kStatusNetEntry 11 }


w2kStatusNetOutPktCrit OBJECT-TYPE
	SYNTAX INTEGER
	ACCESS read-write
	STATUS mandatory
	DESCRIPTION
		"&<caiW2kOs.368>Critical threshold for the rate of sent packets over TCP/IP connections (packets per second). Valid values are greater than 1 and greater than the warning threshold."
	::= { w2kStatusNetEntry 12 }


w2kStatusNetOutPktMonitor OBJECT-TYPE
	SYNTAX INTEGER {
		do-not-monitor(1),
		warning-only(2),
		critical-only(3),
		both(4)
	}
	ACCESS read-write
	STATUS mandatory
	DESCRIPTION
		"&<caiW2kOs.369>Flag indicating whether the sent packets rate should be monitored and if so, which threshold should be compared with."
	DEFVAL { 0 }
	::= { w2kStatusNetEntry 13 }


w2kStatusNetOutPktStatus OBJECT-TYPE
	SYNTAX INTEGER {
		unknown(1),
		ok(2),
		warning(3),
		critical(4)
	}
	ACCESS read-only
	STATUS mandatory
	DESCRIPTION
		"&<caiW2kOs.826>The current status of the sent packets rate as determined by the thresholds. The status 'unknown' means that the current value could not be retrieved from the system."
	::= { w2kStatusNetEntry 14 }


w2kStatusNetInErrDValue OBJECT-TYPE
	SYNTAX INTEGER
	ACCESS read-only
	STATUS mandatory
	DESCRIPTION
		"&<caiW2kOs.827>The current value of the received errors rate (errors per poll interval)."
	::= { w2kStatusNetEntry 15 }


w2kStatusNetInErrDWarn OBJECT-TYPE
	SYNTAX INTEGER
	ACCESS read-write
	STATUS mandatory
	DESCRIPTION
		"&<caiW2kOs.370>Warning threshold for the rate of received errors over TCP/IP connections (errors per poll interval). Valid values are greater than 0 and smaller than the critical threshold."
	::= { w2kStatusNetEntry 16 }


w2kStatusNetInErrDCrit OBJECT-TYPE
	SYNTAX INTEGER
	ACCESS read-write
	STATUS mandatory
	DESCRIPTION
		"&<caiW2kOs.371>Critical threshold for the rate of received errors over TCP/IP connections (errors per poll interval). Valid values are greater than 1 and greater than the warning threshold."
	::= { w2kStatusNetEntry 17 }


w2kStatusNetInErrDMonitor OBJECT-TYPE
	SYNTAX INTEGER {
		do-not-monitor(1),
		warning-only(2),
		critical-only(3),
		both(4)
	}
	ACCESS read-write
	STATUS mandatory
	DESCRIPTION
		"&<caiW2kOs.372>Flag indicating whether the received errors rate should be monitored and if so, which threshold should be compared with."
	DEFVAL { 0 }
	::= { w2kStatusNetEntry 18 }


w2kStatusNetInErrDStatus OBJECT-TYPE
	SYNTAX INTEGER {
		unknown(1),
		ok(2),
		warning(3),
		critical(4)
	}
	ACCESS read-only
	STATUS mandatory
	DESCRIPTION
		"&<caiW2kOs.831>The current status of the received errors rate as determined by the thresholds. The status 'unknown' means that the current value could not be retrieved from the system."
	::= { w2kStatusNetEntry 19 }


w2kStatusNetOutErrDValue OBJECT-TYPE
	SYNTAX INTEGER
	ACCESS read-only
	STATUS mandatory
	DESCRIPTION
		"&<caiW2kOs.832>The current value of the sent errors rate (errors per poll interval)."
	::= { w2kStatusNetEntry 20 }


w2kStatusNetOutErrDWarn OBJECT-TYPE
	SYNTAX INTEGER
	ACCESS read-write
	STATUS mandatory
	DESCRIPTION
		"&<caiW2kOs.373>Warning threshold for the rate of sent errors over TCP/IP connections (errors per poll interval). Valid values are greater than 0 and smaller than the critical threshold."
	::= { w2kStatusNetEntry 21 }


w2kStatusNetOutErrDCrit OBJECT-TYPE
	SYNTAX INTEGER
	ACCESS read-write
	STATUS mandatory
	DESCRIPTION
		"&<caiW2kOs.374>Critical threshold for the rate of sent errors over TCP/IP connections (errors per poll interval). Valid values are greater than 1 and greater than the warning threshold."
	::= { w2kStatusNetEntry 22 }


w2kStatusNetOutErrDMonitor OBJECT-TYPE
	SYNTAX INTEGER {
		do-not-monitor(1),
		warning-only(2),
		critical-only(3),
		both(4)
	}
	ACCESS read-write
	STATUS mandatory
	DESCRIPTION
		"&<caiW2kOs.375>Flag indicating whether the sent errors rate should be monitored and if so, which threshold should be compared with."
	DEFVAL { 0 }
	::= { w2kStatusNetEntry 23 }


w2kStatusNetOutErrDStatus OBJECT-TYPE
	SYNTAX INTEGER {
		unknown(1),
		ok(2),
		warning(3),
		critical(4)
	}
	ACCESS read-only
	STATUS mandatory
	DESCRIPTION
		"&<caiW2kOs.836>The current status of the sent errors rate as determined by the thresholds. The status 'unknown' means that the current value could not be retrieved from the system."
	::= { w2kStatusNetEntry 24 }


w2kStatusNetLossAction OBJECT-TYPE
	SYNTAX INTEGER {
		remove(1),
		up(2),
		down-warning(3),
		down-critical(4)
	}
	ACCESS read-write
	STATUS mandatory
	DESCRIPTION
		"&<caiW2kOs.376>Flag defining the severity if the loss of the network interface is detected or whether to remove this watcher in that case."
	DEFVAL { 0 }
	::= { w2kStatusNetEntry 25 }


w2kStatusNetLossStatus OBJECT-TYPE
	SYNTAX INTEGER {
		unknown(1),
		up(2),
		down-warning(3),
		down-critical(4)
	}
	ACCESS read-only
	STATUS mandatory
	DESCRIPTION
		"&<caiW2kOs.838>The current status of the network interface's loss as determined by the loss action."
	::= { w2kStatusNetEntry 26 }


w2kStatusNetCallBackRef OBJECT-TYPE
	SYNTAX DisplayString
	ACCESS read-only
	STATUS mandatory
	DESCRIPTION
		"&<caiW2kOs.443>The name of the Call-Back reference that should be invoked in case of a status change."
	::= { w2kStatusNetEntry 27 }




--	------------------------------------------------------------------------
--      Registry Entries Status Group
--	------------------------------------------------------------------------


w2kStatusRegCount OBJECT-TYPE
	SYNTAX INTEGER
	ACCESS read-only
	STATUS mandatory
	DESCRIPTION
		"&<caiW2kOs.840>The number of entries in the w2kStatusRegTable."
	::= { w2kStatusRegGroup 1 }


w2kStatusRegTable OBJECT-TYPE
	SYNTAX SEQUENCE OF W2kStatusRegRow
	ACCESS not-accessible
	STATUS mandatory
	DESCRIPTION
		"&<caiW2kOs.841>A table containing information about all monitored registry entries."
	::= { w2kStatusRegGroup 2 }


w2kStatusRegEntry OBJECT-TYPE
	SYNTAX W2kStatusRegRow
	ACCESS not-accessible
	STATUS mandatory
	DESCRIPTION
		"&<caiW2kOs.154>The table entry."
	INDEX { w2kStatusRegName }
	::= { w2kStatusRegTable 1 }


W2kStatusRegRow ::=
	SEQUENCE {
		w2kStatusRegName DisplayString,
		w2kStatusRegDescription DisplayString,
		w2kStatusRegAggLagValue INTEGER,
		w2kStatusRegAggLag INTEGER,
		w2kStatusRegAggStatus INTEGER,
		w2kStatusRegExist INTEGER,
		w2kStatusRegExistMonitor INTEGER,
		w2kStatusRegExistStatus INTEGER,
		w2kStatusRegValueValue DisplayString,
		w2kStatusRegValueType INTEGER,
		w2kStatusRegValueRef DisplayString,
		w2kStatusRegValueCond INTEGER,
		w2kStatusRegValueMonitor INTEGER,
		w2kStatusRegValueStatus INTEGER,
		w2kStatusRegCallBackRef DisplayString,
		w2kStatusRegButton INTEGER
	}


w2kStatusRegName OBJECT-TYPE
	SYNTAX DisplayString
	ACCESS read-only
	STATUS mandatory
	DESCRIPTION
		"&<caiW2kOs.843>Name of the watcher, monitoring a registry entry with this name. The name is the complete registry path ending with the registry leaf name. If the leaf name contains a backslash, the leaf name must be quoted with double quotes. Important: This name is case insensitive."
	::= { w2kStatusRegEntry 1 }


w2kStatusRegDescription OBJECT-TYPE
	SYNTAX DisplayString
	ACCESS read-write
	STATUS mandatory
	DESCRIPTION
		"&<caiW2kOs.136>Any description for this watcher."
	::= { w2kStatusRegEntry 2 }


w2kStatusRegAggLagValue OBJECT-TYPE
	SYNTAX INTEGER
	ACCESS read-only
	STATUS mandatory
	DESCRIPTION
		"&<caiW2kOs.499>The number of consecutive poll intervals on which any status was not in the Ok or Up state."
	::= { w2kStatusRegEntry 3 }


w2kStatusRegAggLag OBJECT-TYPE
	SYNTAX INTEGER
	ACCESS read-write
	STATUS mandatory
	DESCRIPTION
		"&<caiW2kOs.137>The number of consecutive poll intervals on which any status is not in the Ok or Up state, before the aggregate status changes. Valid values are greater than 0."
	::= { w2kStatusRegEntry 4 }


w2kStatusRegAggStatus OBJECT-TYPE
	SYNTAX INTEGER {
		unknown(1),
		ok(2),
		warning(3),
		critical(4)
	}
	ACCESS read-only
	STATUS mandatory
	DESCRIPTION
		"&<caiW2kOs.847>The current status of the registry entry as a 'worst case' aggregate of all its statuses."
	::= { w2kStatusRegEntry 5 }


w2kStatusRegExist OBJECT-TYPE
	SYNTAX INTEGER {
		should-exist(1),
		should-not-exist(2)
	}
	ACCESS read-write
	STATUS mandatory
	DESCRIPTION
		"&<caiW2kOs.382>Flag indicating whether to raise an alert if a registry entry is existent or if it is not-existent."
	DEFVAL { 0 }
	::= { w2kStatusRegEntry 6 }


w2kStatusRegExistMonitor OBJECT-TYPE
	SYNTAX INTEGER {
		do-not-monitor(1),
		down-warning(2),
		down-critical(3)
	}
	ACCESS read-write
	STATUS mandatory
	DESCRIPTION
		"&<caiW2kOs.383>Flag indicating whether the existence of the registry entry should be monitored and if so, the level of alert to raise."
	DEFVAL { 0 }
	::= { w2kStatusRegEntry 7 }


w2kStatusRegExistStatus OBJECT-TYPE
	SYNTAX INTEGER {
		unknown(1),
		up(2),
		down-warning(3),
		down-critical(4)
	}
	ACCESS read-only
	STATUS mandatory
	DESCRIPTION
		"&<caiW2kOs.850>The current status of the registry entry existence."
	::= { w2kStatusRegEntry 8 }


w2kStatusRegValueValue OBJECT-TYPE
	SYNTAX DisplayString
	ACCESS read-only
	STATUS mandatory
	DESCRIPTION
		"&<caiW2kOs.851>The current value of the registry entry."
	::= { w2kStatusRegEntry 9 }


w2kStatusRegValueType OBJECT-TYPE
	SYNTAX INTEGER {
		string(1),
		binary(2),
		dword(3),
		unknown(4)
	}
	ACCESS read-only
	STATUS mandatory
	DESCRIPTION
		"&<caiW2kOs.852>The current type of the registry entry."
	::= { w2kStatusRegEntry 10 }


w2kStatusRegValueRef OBJECT-TYPE
	SYNTAX DisplayString
	ACCESS read-write
	STATUS mandatory
	DESCRIPTION
		"&<caiW2kOs.384>This attribute is used as the reference value the registry entry is compared with. If the condition is one of 'should-be-equal', 'should-not-be-equal', 'should-be-below' or 'should-be-above', this reference value must be set by the user. In case of 'should-not-change', by setting the status button attribute to 'reset-value', the reference value is set to the current value of the registry entry."
	::= { w2kStatusRegEntry 11 }


w2kStatusRegValueCond OBJECT-TYPE
	SYNTAX INTEGER {
		should-be-equal(1),
		should-not-be-equal(2),
		should-be-below(3),
		should-be-above(4),
		should-not-change(5)
	}
	ACCESS read-write
	STATUS mandatory
	DESCRIPTION
		"&<caiW2kOs.385>Flag indicating whether to raise an alert if a registry entry does not fullfill the given condition compared with the reference value attribute. 'should-be-below' and 'should-be-above' is only allowed for entries with type DWORD. For entries with type Binary 'should-not-change' is the only possible value."
	DEFVAL { 0 }
	::= { w2kStatusRegEntry 12 }


w2kStatusRegValueMonitor OBJECT-TYPE
	SYNTAX INTEGER {
		do-not-monitor(1),
		down-warning(2),
		down-critical(3)
	}
	ACCESS read-write
	STATUS mandatory
	DESCRIPTION
		"&<caiW2kOs.386>Flag indicating whether the value of the registry entry should be monitored and if so, the level of alert to raise."
	DEFVAL { 0 }
	::= { w2kStatusRegEntry 13 }


w2kStatusRegValueStatus OBJECT-TYPE
	SYNTAX INTEGER {
		unknown(1),
		up(2),
		down-warning(3),
		down-critical(4)
	}
	ACCESS read-only
	STATUS mandatory
	DESCRIPTION
		"&<caiW2kOs.856>The current status of the registry entry as determined by the thresholds. The status 'unknown' means that the current value could not be retrieved from the system."
	::= { w2kStatusRegEntry 14 }


w2kStatusRegCallBackRef OBJECT-TYPE
	SYNTAX DisplayString
	ACCESS read-only
	STATUS mandatory
	DESCRIPTION
		"&<caiW2kOs.443>The name of the Call-Back reference that should be invoked in case of a status change."
	::= { w2kStatusRegEntry 15 }


w2kStatusRegButton OBJECT-TYPE
	SYNTAX INTEGER {
		none(1),
		remove(2),
		reset-value(3)
	}
	ACCESS read-write
	STATUS mandatory
	DESCRIPTION
		"&<caiW2kOs.858>This attribute is used to remove this watcher or to reset the value reference to the current value of the registry entry. The 'reset-value' is only possible in case the condition is 'should-not-change'."
	::= { w2kStatusRegEntry 16 }




--	------------------------------------------------------------------------
--      Logical Volumes Available Group
--	------------------------------------------------------------------------


w2kAvailLVolRefresh OBJECT-TYPE
	SYNTAX INTEGER {
		none(1),
		refresh(2)
	}
	ACCESS read-write
	STATUS mandatory
	DESCRIPTION
		"&<caiW2kOs.859>Set this value to 'refresh' to let the agent check again for all current logical volumes. The user can not set the value to 'none'."
	::= { w2kAvailLVolGroup 1 }


w2kAvailLVolCount OBJECT-TYPE
	SYNTAX INTEGER
	ACCESS read-only
	STATUS mandatory
	DESCRIPTION
		"&<caiW2kOs.860>The number of currently available logical volumes."
	::= { w2kAvailLVolGroup 2 }


w2kAvailLVolTable OBJECT-TYPE
	SYNTAX SEQUENCE OF W2kAvailLVolRow
	ACCESS not-accessible
	STATUS mandatory
	DESCRIPTION
		"&<caiW2kOs.861>A table containing the logical volumes available for monitoring."
	::= { w2kAvailLVolGroup 3 }


w2kAvailLVolEntry OBJECT-TYPE
	SYNTAX W2kAvailLVolRow
	ACCESS not-accessible
	STATUS mandatory
	DESCRIPTION
		"&<caiW2kOs.154>The table entry."
	INDEX { w2kAvailLVolName }
	::= { w2kAvailLVolTable 1 }


W2kAvailLVolRow ::=
	SEQUENCE {
		w2kAvailLVolName DisplayString,
		w2kAvailLVolMounts DisplayString,
		w2kAvailLVolInfo DisplayString,
		w2kAvailLVolTime DisplayString
	}


w2kAvailLVolName OBJECT-TYPE
	SYNTAX DisplayString
	ACCESS read-only
	STATUS mandatory
	DESCRIPTION
		"&<caiW2kOs.863>The name of the logical volume."
	::= { w2kAvailLVolEntry 1 }


w2kAvailLVolMounts OBJECT-TYPE
	SYNTAX DisplayString
	ACCESS read-only
	STATUS mandatory
	DESCRIPTION
		"&<caiW2kOs.496>A list of the mount points, where this logical volume is mounted on."
	::= { w2kAvailLVolEntry 2 }


w2kAvailLVolInfo OBJECT-TYPE
	SYNTAX DisplayString
	ACCESS read-only
	STATUS mandatory
	DESCRIPTION
		"&<caiW2kOs.497>Information about the format (e.g. NTFS), the alternate name (e.g. used in PerfMon) and the label of the logical volume. The alternate name may be empty. The single values are delimited by a pipe sign."
	::= { w2kAvailLVolEntry 3 }


w2kAvailLVolTime OBJECT-TYPE
	SYNTAX DisplayString
	ACCESS read-only
	STATUS mandatory
	DESCRIPTION
		"&<caiW2kOs.866>The time when the agent discovered this logical volume and put it into this table."
	::= { w2kAvailLVolEntry 4 }




--	------------------------------------------------------------------------
--      Mounts Available Group
--	------------------------------------------------------------------------


w2kAvailMntRefresh OBJECT-TYPE
	SYNTAX INTEGER {
		none(1),
		refresh(2)
	}
	ACCESS read-write
	STATUS mandatory
	DESCRIPTION
		"&<caiW2kOs.867>Set this value to 'refresh' to let the agent check again for all current mounts. The user can not set the value to 'none'."
	::= { w2kAvailMntGroup 1 }


w2kAvailMntCount OBJECT-TYPE
	SYNTAX INTEGER
	ACCESS read-only
	STATUS mandatory
	DESCRIPTION
		"&<caiW2kOs.868>The number of currently available mounts."
	::= { w2kAvailMntGroup 2 }


w2kAvailMntTable OBJECT-TYPE
	SYNTAX SEQUENCE OF W2kAvailMntRow
	ACCESS not-accessible
	STATUS mandatory
	DESCRIPTION
		"&<caiW2kOs.869>A table containing the mounts available for monitoring."
	::= { w2kAvailMntGroup 3 }


w2kAvailMntEntry OBJECT-TYPE
	SYNTAX W2kAvailMntRow
	ACCESS not-accessible
	STATUS mandatory
	DESCRIPTION
		"&<caiW2kOs.154>The table entry."
	INDEX { w2kAvailMntName }
	::= { w2kAvailMntTable 1 }


W2kAvailMntRow ::=
	SEQUENCE {
		w2kAvailMntName DisplayString,
		w2kAvailMntRelTo DisplayString,
		w2kAvailMntTime DisplayString
	}


w2kAvailMntName OBJECT-TYPE
	SYNTAX DisplayString
	ACCESS read-only
	STATUS mandatory
	DESCRIPTION
		"&<caiW2kOs.871>The name of the mount."
	::= { w2kAvailMntEntry 1 }


w2kAvailMntRelTo OBJECT-TYPE
	SYNTAX DisplayString
	ACCESS read-only
	STATUS mandatory
	DESCRIPTION
		"&<caiW2kOs.540>The name of the current logical volume, which this mount is mounting."
	::= { w2kAvailMntEntry 2 }


w2kAvailMntTime OBJECT-TYPE
	SYNTAX DisplayString
	ACCESS read-only
	STATUS mandatory
	DESCRIPTION
		"&<caiW2kOs.873>The time when the agent discovered this mount and put it into this table."
	::= { w2kAvailMntEntry 3 }




--	------------------------------------------------------------------------
--      Distributed File Systems Available Group
--	------------------------------------------------------------------------


w2kAvailDfsRefresh OBJECT-TYPE
	SYNTAX INTEGER {
		none(1),
		refresh(2)
	}
	ACCESS read-write
	STATUS mandatory
	DESCRIPTION
		"&<caiW2kOs.874>Set this value to 'refresh' to let the agent check again for all current distributed file system links. The user can not set the value to 'none'."
	::= { w2kAvailDfsGroup 1 }


w2kAvailDfsCount OBJECT-TYPE
	SYNTAX INTEGER
	ACCESS read-only
	STATUS mandatory
	DESCRIPTION
		"&<caiW2kOs.875>The number of currently available distributed file system links."
	::= { w2kAvailDfsGroup 2 }


w2kAvailDfsTable OBJECT-TYPE
	SYNTAX SEQUENCE OF W2kAvailDfsRow
	ACCESS not-accessible
	STATUS mandatory
	DESCRIPTION
		"&<caiW2kOs.876>A table containing the distributed file system links available for monitoring."
	::= { w2kAvailDfsGroup 3 }


w2kAvailDfsEntry OBJECT-TYPE
	SYNTAX W2kAvailDfsRow
	ACCESS not-accessible
	STATUS mandatory
	DESCRIPTION
		"&<caiW2kOs.154>The table entry."
	INDEX { w2kAvailDfsName }
	::= { w2kAvailDfsTable 1 }


W2kAvailDfsRow ::=
	SEQUENCE {
		w2kAvailDfsName DisplayString,
		w2kAvailDfsTime DisplayString
	}


w2kAvailDfsName OBJECT-TYPE
	SYNTAX DisplayString
	ACCESS read-only
	STATUS mandatory
	DESCRIPTION
		"&<caiW2kOs.878>The name of the distributed file system link. The name consists of the distributed file system root name followed by the Dfs link name. These two names are concatenated by a back-slash."
	::= { w2kAvailDfsEntry 1 }


w2kAvailDfsTime OBJECT-TYPE
	SYNTAX DisplayString
	ACCESS read-only
	STATUS mandatory
	DESCRIPTION
		"&<caiW2kOs.879>The time when the agent discovered this distributed file system link and put it into this table."
	::= { w2kAvailDfsEntry 2 }




--	------------------------------------------------------------------------
--      Quota Available Group
--	------------------------------------------------------------------------


w2kAvailQuotRefresh OBJECT-TYPE
	SYNTAX INTEGER {
		none(1),
		refresh(2)
	}
	ACCESS read-write
	STATUS mandatory
	DESCRIPTION
		"&<caiW2kOs.880>Set this value to 'refresh' to let the agent check again for all current quotas. The user can not set the value to 'none'."
	::= { w2kAvailQuotGroup 1 }


w2kAvailQuotCount OBJECT-TYPE
	SYNTAX INTEGER
	ACCESS read-only
	STATUS mandatory
	DESCRIPTION
		"&<caiW2kOs.881>The number of currently available quotas."
	::= { w2kAvailQuotGroup 2 }


w2kAvailQuotTable OBJECT-TYPE
	SYNTAX SEQUENCE OF W2kAvailQuotRow
	ACCESS not-accessible
	STATUS mandatory
	DESCRIPTION
		"&<caiW2kOs.882>A table containing the quotas available for monitoring."
	::= { w2kAvailQuotGroup 3 }


w2kAvailQuotEntry OBJECT-TYPE
	SYNTAX W2kAvailQuotRow
	ACCESS not-accessible
	STATUS mandatory
	DESCRIPTION
		"&<caiW2kOs.154>The table entry."
	INDEX { w2kAvailQuotLVolName, w2kAvailQuotUserName }
	::= { w2kAvailQuotTable 1 }


W2kAvailQuotRow ::=
	SEQUENCE {
		w2kAvailQuotLVolName DisplayString,
		w2kAvailQuotUserName DisplayString,
		w2kAvailQuotWarnLevel INTEGER,
		w2kAvailQuotLimit INTEGER,
		w2kAvailQuotTime DisplayString
	}


w2kAvailQuotLVolName OBJECT-TYPE
	SYNTAX DisplayString
	ACCESS read-only
	STATUS mandatory
	DESCRIPTION
		"&<caiW2kOs.884>The name of the logical volume on which this quota exists."
	::= { w2kAvailQuotEntry 1 }


w2kAvailQuotUserName OBJECT-TYPE
	SYNTAX DisplayString
	ACCESS read-only
	STATUS mandatory
	DESCRIPTION
		"&<caiW2kOs.885>The user name for whom this quota exists. The name is in the form 'domainName\\userName' or 'userName@domainName'."
	::= { w2kAvailQuotEntry 2 }


w2kAvailQuotWarnLevel OBJECT-TYPE
	SYNTAX INTEGER
	ACCESS read-only
	STATUS mandatory
	DESCRIPTION
		"&<caiW2kOs.886>The quota warning level for this user, as defined in the Windows 2000 quota management. Management applications adding a watcher for this quota should use this value as default warning threshold instead of the value stored in the config group."
	::= { w2kAvailQuotEntry 3 }


w2kAvailQuotLimit OBJECT-TYPE
	SYNTAX INTEGER
	ACCESS read-only
	STATUS mandatory
	DESCRIPTION
		"&<caiW2kOs.887>The quota limit for this user, as defined in the Windows 2000 quota management. Management applications adding a watcher for this quota should use this value as default critical threshold instead of the value stored in the config group."
	::= { w2kAvailQuotEntry 4 }


w2kAvailQuotTime OBJECT-TYPE
	SYNTAX DisplayString
	ACCESS read-only
	STATUS mandatory
	DESCRIPTION
		"&<caiW2kOs.888>The time when the agent discovered this quota and put it into this table."
	::= { w2kAvailQuotEntry 5 }




--	------------------------------------------------------------------------
--      Processes Available Group
--	------------------------------------------------------------------------


w2kAvailProcRefresh OBJECT-TYPE
	SYNTAX INTEGER {
		none(1),
		refresh(2)
	}
	ACCESS read-write
	STATUS mandatory
	DESCRIPTION
		"&<caiW2kOs.889>Set this value to 'refresh' to let the agent check again for all current processes. The user can not set the value to 'none'."
	::= { w2kAvailProcGroup 1 }


w2kAvailProcCount OBJECT-TYPE
	SYNTAX INTEGER
	ACCESS read-only
	STATUS mandatory
	DESCRIPTION
		"&<caiW2kOs.890>The number of currently available processes."
	::= { w2kAvailProcGroup 2 }


w2kAvailProcTable OBJECT-TYPE
	SYNTAX SEQUENCE OF W2kAvailProcRow
	ACCESS not-accessible
	STATUS mandatory
	DESCRIPTION
		"&<caiW2kOs.891>A table containing the processes available for monitoring."
	::= { w2kAvailProcGroup 3 }


w2kAvailProcEntry OBJECT-TYPE
	SYNTAX W2kAvailProcRow
	ACCESS not-accessible
	STATUS mandatory
	DESCRIPTION
		"&<caiW2kOs.154>The table entry."
	INDEX { w2kAvailProcProcName, w2kAvailProcPathName, w2kAvailProcUserName }
	::= { w2kAvailProcTable 1 }


W2kAvailProcRow ::=
	SEQUENCE {
		w2kAvailProcProcName DisplayString,
		w2kAvailProcPathName DisplayString,
		w2kAvailProcUserName DisplayString,
		w2kAvailProcTime DisplayString
	}


w2kAvailProcProcName OBJECT-TYPE
	SYNTAX DisplayString
	ACCESS read-only
	STATUS mandatory
	DESCRIPTION
		"&<caiW2kOs.893>The process name of the process."
	::= { w2kAvailProcEntry 1 }


w2kAvailProcPathName OBJECT-TYPE
	SYNTAX DisplayString
	ACCESS read-only
	STATUS mandatory
	DESCRIPTION
		"&<caiW2kOs.894>The path name of the process."
	::= { w2kAvailProcEntry 2 }


w2kAvailProcUserName OBJECT-TYPE
	SYNTAX DisplayString
	ACCESS read-only
	STATUS mandatory
	DESCRIPTION
		"&<caiW2kOs.895>The user name of the process."
	::= { w2kAvailProcEntry 3 }


w2kAvailProcTime OBJECT-TYPE
	SYNTAX DisplayString
	ACCESS read-only
	STATUS mandatory
	DESCRIPTION
		"&<caiW2kOs.896>The time when the agent discovered this process and put it into this table."
	::= { w2kAvailProcEntry 4 }




--	------------------------------------------------------------------------
--      Services Available Group
--	------------------------------------------------------------------------


w2kAvailSrvcRefresh OBJECT-TYPE
	SYNTAX INTEGER {
		none(1),
		refresh(2)
	}
	ACCESS read-write
	STATUS mandatory
	DESCRIPTION
		"&<caiW2kOs.897>Set this value to 'refresh' to let the agent check again for all current services. The user can not set the value to 'none'."
	::= { w2kAvailSrvcGroup 1 }


w2kAvailSrvcCount OBJECT-TYPE
	SYNTAX INTEGER
	ACCESS read-only
	STATUS mandatory
	DESCRIPTION
		"&<caiW2kOs.898>The number of currently available services."
	::= { w2kAvailSrvcGroup 2 }


w2kAvailSrvcTable OBJECT-TYPE
	SYNTAX SEQUENCE OF W2kAvailSrvcRow
	ACCESS not-accessible
	STATUS mandatory
	DESCRIPTION
		"&<caiW2kOs.899>A table containing the services available for monitoring."
	::= { w2kAvailSrvcGroup 3 }


w2kAvailSrvcEntry OBJECT-TYPE
	SYNTAX W2kAvailSrvcRow
	ACCESS not-accessible
	STATUS mandatory
	DESCRIPTION
		"&<caiW2kOs.154>The table entry."
	INDEX { w2kAvailSrvcName }
	::= { w2kAvailSrvcTable 1 }


W2kAvailSrvcRow ::=
	SEQUENCE {
		w2kAvailSrvcName DisplayString,
		w2kAvailSrvcDescr DisplayString,
		w2kAvailSrvcTime DisplayString
	}


w2kAvailSrvcName OBJECT-TYPE
	SYNTAX DisplayString
	ACCESS read-only
	STATUS mandatory
	DESCRIPTION
		"&<caiW2kOs.901>The name of the service."
	::= { w2kAvailSrvcEntry 1 }


w2kAvailSrvcDescr OBJECT-TYPE
	SYNTAX DisplayString
	ACCESS read-only
	STATUS mandatory
	DESCRIPTION
		"&<caiW2kOs.701>The description of the service."
::= { w2kAvailSrvcEntry 2 }


w2kAvailSrvcTime OBJECT-TYPE
	SYNTAX DisplayString
	ACCESS read-only
	STATUS mandatory
	DESCRIPTION
		"&<caiW2kOs.903>The time when the agent discovered this service and put it into this table."
	::= { w2kAvailSrvcEntry 3 }




--	------------------------------------------------------------------------
--      Jobs Available Group
--	------------------------------------------------------------------------


w2kAvailJobRefresh OBJECT-TYPE
	SYNTAX INTEGER {
		none(1),
		refresh(2)
	}
	ACCESS read-write
	STATUS mandatory
	DESCRIPTION
		"&<caiW2kOs.904>Set this value to 'refresh' to let the agent check again for all current jobs. The user can not set the value to 'none'."
	::= { w2kAvailJobGroup 1 }


w2kAvailJobCount OBJECT-TYPE
	SYNTAX INTEGER
	ACCESS read-only
	STATUS mandatory
	DESCRIPTION
		"&<caiW2kOs.905>The number of currently available jobs."
	::= { w2kAvailJobGroup 2 }


w2kAvailJobTable OBJECT-TYPE
	SYNTAX SEQUENCE OF W2kAvailJobRow
	ACCESS not-accessible
	STATUS mandatory
	DESCRIPTION
		"&<caiW2kOs.906>A table containing the jobs available for monitoring."
	::= { w2kAvailJobGroup 3 }


w2kAvailJobEntry OBJECT-TYPE
	SYNTAX W2kAvailJobRow
	ACCESS not-accessible
	STATUS mandatory
	DESCRIPTION
		"&<caiW2kOs.154>The table entry."
	INDEX { w2kAvailJobName }
	::= { w2kAvailJobTable 1 }


W2kAvailJobRow ::=
	SEQUENCE {
		w2kAvailJobName DisplayString,
		w2kAvailJobTime DisplayString
	}


w2kAvailJobName OBJECT-TYPE
	SYNTAX DisplayString
	ACCESS read-only
	STATUS mandatory
	DESCRIPTION
		"&<caiW2kOs.908>The name of the job."
	::= { w2kAvailJobEntry 1 }


w2kAvailJobTime OBJECT-TYPE
	SYNTAX DisplayString
	ACCESS read-only
	STATUS mandatory
	DESCRIPTION
		"&<caiW2kOs.909>The time when the agent discovered this job and put it into this table."
	::= { w2kAvailJobEntry 2 }




--	------------------------------------------------------------------------
--      Sessions Available Group
--	------------------------------------------------------------------------


w2kAvailSessRefresh OBJECT-TYPE
	SYNTAX INTEGER {
		none(1),
		refresh(2)
	}
	ACCESS read-write
	STATUS mandatory
	DESCRIPTION
		"&<caiW2kOs.910>Set this value to 'refresh' to let the agent check again for all current sessions. The user can not set the value to 'none'."
	::= { w2kAvailSessGroup 1 }


w2kAvailSessCount OBJECT-TYPE
	SYNTAX INTEGER
	ACCESS read-only
	STATUS mandatory
	DESCRIPTION
		"&<caiW2kOs.911>The number of currently available sessions."
	::= { w2kAvailSessGroup 2 }


w2kAvailSessTable OBJECT-TYPE
	SYNTAX SEQUENCE OF W2kAvailSessRow
	ACCESS not-accessible
	STATUS mandatory
	DESCRIPTION
		"&<caiW2kOs.912>A table containing the sessions available for monitoring."
	::= { w2kAvailSessGroup 3 }


w2kAvailSessEntry OBJECT-TYPE
	SYNTAX W2kAvailSessRow
	ACCESS not-accessible
	STATUS mandatory
	DESCRIPTION
		"&<caiW2kOs.154>The table entry."
	INDEX { w2kAvailSessClientName, w2kAvailSessUserName }
	::= { w2kAvailSessTable 1 }


W2kAvailSessRow ::=
	SEQUENCE {
		w2kAvailSessClientName DisplayString,
		w2kAvailSessUserName DisplayString,
		w2kAvailSessTime DisplayString
	}


w2kAvailSessClientName OBJECT-TYPE
	SYNTAX DisplayString
	ACCESS read-only
	STATUS mandatory
	DESCRIPTION
		"&<caiW2kOs.914>Client name of the session, which is the name of the host, from where this session was initiated."
	::= { w2kAvailSessEntry 1 }


w2kAvailSessUserName OBJECT-TYPE
	SYNTAX DisplayString
	ACCESS read-only
	STATUS mandatory
	DESCRIPTION
		"&<caiW2kOs.915>User name of the session, which specifies the user, who logged in and is in the form 'domainName\\userName'."
	::= { w2kAvailSessEntry 2 }


w2kAvailSessTime OBJECT-TYPE
	SYNTAX DisplayString
	ACCESS read-only
	STATUS mandatory
	DESCRIPTION
		"&<caiW2kOs.916>The time when the agent discovered this session and put it into this table."
	::= { w2kAvailSessEntry 3 }




--	------------------------------------------------------------------------
--      Printer Available Group
--	------------------------------------------------------------------------

w2kAvailPrnRefresh OBJECT-TYPE
	SYNTAX INTEGER {
		none(1),
		refresh(2)
	}
	ACCESS read-write
	STATUS mandatory
	DESCRIPTION
		"&<caiW2kOs.917>Set this value to 'refresh' to let the agent check again for all configured printers. The user can not set the value to 'none'."
	::= { w2kAvailPrnGroup 1 }


w2kAvailPrnCount OBJECT-TYPE
	SYNTAX INTEGER
	ACCESS read-only
	STATUS mandatory
	DESCRIPTION
		"&<caiW2kOs.918>The number of currently available printers. This includes all local printers, but not the network printers."
	::= { w2kAvailPrnGroup 2 }


w2kAvailPrnTable OBJECT-TYPE
	SYNTAX SEQUENCE OF W2kAvailPrnRow
	ACCESS not-accessible
	STATUS mandatory
	DESCRIPTION
		"&<caiW2kOs.919>A table containing the local printers available for monitoring."
	::= { w2kAvailPrnGroup 3 }


w2kAvailPrnEntry OBJECT-TYPE
	SYNTAX W2kAvailPrnRow
	ACCESS not-accessible
	STATUS mandatory
	DESCRIPTION
		"&<caiW2kOs.154>The table entry."
	INDEX { w2kAvailPrnName }
	::= { w2kAvailPrnTable 1 }


W2kAvailPrnRow ::=
	SEQUENCE {
		w2kAvailPrnName DisplayString,
		w2kAvailPrnTime DisplayString
	}


w2kAvailPrnName OBJECT-TYPE
	SYNTAX DisplayString
	ACCESS read-only
	STATUS mandatory
	DESCRIPTION
		"&<caiW2kOs.921>The name of the local printer."
	::= { w2kAvailPrnEntry 1 }


w2kAvailPrnTime OBJECT-TYPE
	SYNTAX DisplayString
	ACCESS read-only
	STATUS mandatory
	DESCRIPTION
		"&<caiW2kOs.922>The time when the agent discovered this printer and put it into this table."
	::= { w2kAvailPrnEntry 2 }




--	------------------------------------------------------------------------
--      History Group
--	------------------------------------------------------------------------


w2kHistoryCpuCollect OBJECT-TYPE
	SYNTAX INTEGER {
		no(1),
		yes(2)
	}
	ACCESS read-write
	STATUS mandatory
	DESCRIPTION
		"&<caiW2kOs.923>Set this value to 'yes' to let the agent collect traps of the processor group in the history table. If set to 'no' these traps are not stored in the history table."
	::= { w2kHistoryGroup 1 }


w2kHistoryMemCollect OBJECT-TYPE
	SYNTAX INTEGER {
		no(1),
		yes(2)
	}
	ACCESS read-write
	STATUS mandatory
	DESCRIPTION
		"&<caiW2kOs.924>Set this value to 'yes' to let the agent collect traps of the memory group in the history table. If set to 'no' these traps are not stored in the history table."
	::= { w2kHistoryGroup 2 }


w2kHistoryLVolCollect OBJECT-TYPE
	SYNTAX INTEGER {
		no(1),
		yes(2)
	}
	ACCESS read-write
	STATUS mandatory
	DESCRIPTION
		"&<caiW2kOs.925>Set this value to 'yes' to let the agent collect traps of the logical volume group in the history table. If set to 'no' these traps are not stored in the history table."
	::= { w2kHistoryGroup 3 }


w2kHistoryMntCollect OBJECT-TYPE
	SYNTAX INTEGER {
		no(1),
		yes(2)
	}
	ACCESS read-write
	STATUS mandatory
	DESCRIPTION
		"&<caiW2kOs.926>Set this value to 'yes' to let the agent collect traps of the mount group in the history table. If set to 'no' these traps are not stored in the history table."
	::= { w2kHistoryGroup 4 }


w2kHistoryDfsCollect OBJECT-TYPE
	SYNTAX INTEGER {
		no(1),
		yes(2)
	}
	ACCESS read-write
	STATUS mandatory
	DESCRIPTION
		"&<caiW2kOs.927>Set this value to 'yes' to let the agent collect traps of the distributed file system group in the history table. If set to 'no' these traps are not stored in the history table."
	::= { w2kHistoryGroup 5 }


w2kHistoryQuotCollect OBJECT-TYPE
	SYNTAX INTEGER {
		no(1),
		yes(2)
	}
	ACCESS read-write
	STATUS mandatory
	DESCRIPTION
		"&<caiW2kOs.928>Set this value to 'yes' to let the agent collect traps of the quota group in the history table. If set to 'no' these traps are not stored in the history table."
	::= { w2kHistoryGroup 6 }


w2kHistoryDirCollect OBJECT-TYPE
	SYNTAX INTEGER {
		no(1),
		yes(2)
	}
	ACCESS read-write
	STATUS mandatory
	DESCRIPTION
		"&<caiW2kOs.929>Set this value to 'yes' to let the agent collect traps of the directory group in the history table. If set to 'no' these traps are not stored in the history table."
	::= { w2kHistoryGroup 7 }


w2kHistoryFileCollect OBJECT-TYPE
	SYNTAX INTEGER {
		no(1),
		yes(2)
	}
	ACCESS read-write
	STATUS mandatory
	DESCRIPTION
		"&<caiW2kOs.930>Set this value to 'yes' to let the agent collect traps of the file group in the history table. If set to 'no' these traps are not stored in the history table."
	::= { w2kHistoryGroup 8 }


w2kHistoryProcCollect OBJECT-TYPE
	SYNTAX INTEGER {
		no(1),
		yes(2)
	}
	ACCESS read-write
	STATUS mandatory
	DESCRIPTION
		"&<caiW2kOs.931>Set this value to 'yes' to let the agent collect traps of the processes group in the history table. If set to 'no' these traps are not stored in the history table."
	::= { w2kHistoryGroup 9 }


w2kHistorySrvcCollect OBJECT-TYPE
	SYNTAX INTEGER {
		no(1),
		yes(2)
	}
	ACCESS read-write
	STATUS mandatory
	DESCRIPTION
		"&<caiW2kOs.932>Set this value to 'yes' to let the agent collect traps of the services group in the history table. If set to 'no' these traps are not stored in the history table."
	::= { w2kHistoryGroup 10 }


w2kHistoryJobCollect OBJECT-TYPE
	SYNTAX INTEGER {
		no(1),
		yes(2)
	}
	ACCESS read-write
	STATUS mandatory
	DESCRIPTION
		"&<caiW2kOs.933>Set this value to 'yes' to let the agent collect traps of the jobs group in the history table. If set to 'no' these traps are not stored in the history table."
	::= { w2kHistoryGroup 11 }


w2kHistorySessCollect OBJECT-TYPE
	SYNTAX INTEGER {
		no(1),
		yes(2)
	}
	ACCESS read-write
	STATUS mandatory
	DESCRIPTION
		"&<caiW2kOs.934>Set this value to 'yes' to let the agent collect traps of the sessions group in the history table. If set to 'no' these traps are not stored in the history table."
	::= { w2kHistoryGroup 12 }


w2kHistoryPrnCollect OBJECT-TYPE
	SYNTAX INTEGER {
		no(1),
		yes(2)
	}
	ACCESS read-write
	STATUS mandatory
	DESCRIPTION
		"&<caiW2kOs.935>Set this value to 'yes' to let the agent collect traps of the printers group in the history table. If set to 'no' these traps are not stored in the history table."
	::= { w2kHistoryGroup 13 }


w2kHistoryNetCollect OBJECT-TYPE
	SYNTAX INTEGER {
		no(1),
		yes(2)
	}
	ACCESS read-write
	STATUS mandatory
	DESCRIPTION
		"&<caiW2kOs.936>Set this value to 'yes' to let the agent collect traps of the network interfaces group in the history table. If set to 'no' these traps are not stored in the history table."
	::= { w2kHistoryGroup 14 }


w2kHistoryRegCollect OBJECT-TYPE
	SYNTAX INTEGER {
		no(1),
		yes(2)
	}
	ACCESS read-write
	STATUS mandatory
	DESCRIPTION
		"&<caiW2kOs.937>Set this value to 'yes' to let the agent collect traps of the registry entries group in the history table. If set to 'no' these traps are not stored in the history table."
	::= { w2kHistoryGroup 15 }


w2kHistoryButton OBJECT-TYPE
	SYNTAX INTEGER {
		none(1),
		clear(2)
	}
	ACCESS read-write
	STATUS mandatory
	DESCRIPTION
		"&<caiW2kOs.938>Set this value to 'clear' to let the agent empty the history table. The user can not set the value to 'none'."
	::= { w2kHistoryGroup 16 }


w2kHistoryMaxEntries OBJECT-TYPE
	SYNTAX INTEGER
	ACCESS read-write
	STATUS mandatory
	DESCRIPTION
		"&<caiW2kOs.939>The maximum number of entries to be stored in the history table. Valid values are 0 to 100. If set to 0 no history information of traps is stored."
	::= { w2kHistoryGroup 17 }


w2kHistoryCount OBJECT-TYPE
	SYNTAX INTEGER
	ACCESS read-only
	STATUS mandatory
	DESCRIPTION
		"&<caiW2kOs.940>The number of entries in the history table."
	::= { w2kHistoryGroup 18 }


--w2kHistoryTable OBJECT-TYPE
--	SYNTAX SEQUENCE OF W2kHistoryRow
--	ACCESS not-accessible
--	STATUS mandatory
--	DESCRIPTION
--		"&<caiW2kOs.941>A table containing the last enterprise specific traps the agent arised."
--	::= { w2kHistoryGroup 19 }


--w2kHistoryEntry OBJECT-TYPE
--	SYNTAX W2kHistoryRow
--	ACCESS not-accessible
--	STATUS mandatory
--	DESCRIPTION
--		"&<caiW2kOs.154>The table entry."
--	::= { w2kHistoryTable 1 }


--W2kHistoryRow ::=
--	SEQUENCE {
--		w2kHistoryTrapName DisplayString,
--		w2kHistoryTrapNumber INTEGER,
--		w2kHistoryTrapTime DisplayString,
--		w2kHistoryTrapVarBind DisplayString
--	}


--w2kHistoryTrapName OBJECT-TYPE
--	SYNTAX DisplayString
--	ACCESS read-only
--	STATUS mandatory
--	DESCRIPTION
--		"&<caiW2kOs.943>The name of the trap as defined in the MIB."
--	::= { w2kHistoryEntry 1 }


--w2kHistoryTrapNumber OBJECT-TYPE
--	SYNTAX INTEGER
--	ACCESS read-only
--	STATUS mandatory
--	DESCRIPTION
--		"&<caiW2kOs.944>The enterprise specific trap type number."
--	::= { w2kHistoryEntry 2 }


--w2kHistoryTrapTime OBJECT-TYPE
--	SYNTAX DisplayString
--	ACCESS read-only
--	STATUS mandatory
--	DESCRIPTION
--		"&<caiW2kOs.945>The date and time the trap was sent."
--	::= { w2kHistoryEntry 3 }


--w2kHistoryTrapVarBind OBJECT-TYPE
--	SYNTAX DisplayString
--	ACCESS read-only
--	STATUS mandatory
--	DESCRIPTION
--		"&<caiW2kOs.946>A comma separated list of the varbinds the agent sent with the trap. Each element has the form 'attribute=value'."
--	::= { w2kHistoryEntry 4 }




--	------------------------------------------------------------------------
--      Processor Total Traps
--	------------------------------------------------------------------------


w2kCpuTotalUnknown TRAP-TYPE
	ENTERPRISE caiW2kOs
	DESCRIPTION
		"&<caiW2kOs.947>The watcher monitoring the processor total changed its status to 'unknown'."
	::= 10000


w2kCpuTotalOk TRAP-TYPE
	ENTERPRISE caiW2kOs
	DESCRIPTION
		"&<caiW2kOs.948>The watcher monitoring the processor total changed its status to 'ok'."
	::= 10001


w2kCpuTotalWarning TRAP-TYPE
	ENTERPRISE caiW2kOs
	DESCRIPTION
		"&<caiW2kOs.949>The watcher monitoring the processor total changed its status to 'warning'."
	::= 10002


w2kCpuTotalCritical TRAP-TYPE
	ENTERPRISE caiW2kOs
	DESCRIPTION
		"&<caiW2kOs.950>The watcher monitoring the processor total changed its status to 'critical'."
	::= 10003


w2kCpuTotalModified TRAP-TYPE
	ENTERPRISE caiW2kOs
	DESCRIPTION
		"&<caiW2kOs.951>The watcher configuration for the processor total changed. The varbind list contains the changed attribute with its old value and with its new value."
	::= 10009




--	------------------------------------------------------------------------
--      Processors Traps
--	------------------------------------------------------------------------


w2kCpuUnknown TRAP-TYPE
	ENTERPRISE caiW2kOs
	DESCRIPTION
		"&<caiW2kOs.952>A watcher monitoring a processor changed its status to 'unknown'. The varbind list contains the name of the involved resource."
	::= 10990


w2kCpuOk TRAP-TYPE
	ENTERPRISE caiW2kOs
	DESCRIPTION
		"&<caiW2kOs.953>A watcher monitoring a processor changed its status to 'ok'. The varbind list contains the name of the involved resource."
	::= 10991


w2kCpuWarning TRAP-TYPE
	ENTERPRISE caiW2kOs
	DESCRIPTION
		"&<caiW2kOs.954>A watcher monitoring a processor changed its status to 'warning'. The varbind list contains the name of the involved resource."
	::= 10992


w2kCpuCritical TRAP-TYPE
	ENTERPRISE caiW2kOs
	DESCRIPTION
		"&<caiW2kOs.955>A watcher monitoring a processor changed its status to 'critical'. The varbind list contains the name of the involved resource."
	::= 10993


w2kCpuAdded TRAP-TYPE
	ENTERPRISE caiW2kOs
	DESCRIPTION
		"&<caiW2kOs.956>A watcher monitoring a processor was added. The varbind list contains the name of the involved resource."
	::= 10996


w2kCpuDeleted TRAP-TYPE
	ENTERPRISE caiW2kOs
	DESCRIPTION
		"&<caiW2kOs.957>A watcher monitoring a processor was removed. The varbind list contains the name of the involved resource."
	::= 10997


w2kCpuInfo TRAP-TYPE
	ENTERPRISE caiW2kOs
	DESCRIPTION
		"&<caiW2kOs.1070>A watcher monitoring a processor changed a substatus. The varbind list contains detailed information in one string."
	::= 10998


w2kCpuModified TRAP-TYPE
	ENTERPRISE caiW2kOs
	DESCRIPTION
		"&<caiW2kOs.958>The watcher configuration for a processor changed. The varbind list contains the name of the involved resource, the changed attribute with its old value and with its new value."
	::= 10999




--	------------------------------------------------------------------------
--      Memory Virtual Traps
--	------------------------------------------------------------------------


w2kMemVirtUnknown TRAP-TYPE
	ENTERPRISE caiW2kOs
	DESCRIPTION
		"&<caiW2kOs.959>The watcher monitoring the virtual memory changed its status to 'unknown'."
	::= 11010


w2kMemVirtOk TRAP-TYPE
	ENTERPRISE caiW2kOs
	DESCRIPTION
		"&<caiW2kOs.960>The watcher monitoring the virtual memory changed its status to 'ok'."
	::= 11011


w2kMemVirtWarning TRAP-TYPE
	ENTERPRISE caiW2kOs
	DESCRIPTION
		"&<caiW2kOs.961>The watcher monitoring the virtual memory changed its status to 'warning'."
	::= 11012


w2kMemVirtCritical TRAP-TYPE
	ENTERPRISE caiW2kOs
	DESCRIPTION
		"&<caiW2kOs.962>The watcher monitoring the virtual memory changed its status to 'critical'."
	::= 11013


w2kMemVirtModified TRAP-TYPE
	ENTERPRISE caiW2kOs
	DESCRIPTION
		"&<caiW2kOs.963>The watcher configuration for the virtual memory changed. The varbind list contains the changed attribute with its old value and with its new value."
	::= 11019




--	------------------------------------------------------------------------
--      Memory Physical Traps
--	------------------------------------------------------------------------


w2kMemPhysUnknown TRAP-TYPE
	ENTERPRISE caiW2kOs
	DESCRIPTION
		"&<caiW2kOs.964>The watcher monitoring the physical memory changed its status to 'unknown'."
	::= 11020


w2kMemPhysOk TRAP-TYPE
	ENTERPRISE caiW2kOs
	DESCRIPTION
		"&<caiW2kOs.965>The watcher monitoring the physical memory changed its status to 'ok'."
	::= 11021


w2kMemPhysWarning TRAP-TYPE
	ENTERPRISE caiW2kOs
	DESCRIPTION
		"&<caiW2kOs.966>The watcher monitoring the physical memory changed its status to 'warning'."
	::= 11022


w2kMemPhysCritical TRAP-TYPE
	ENTERPRISE caiW2kOs
	DESCRIPTION
		"&<caiW2kOs.967>The watcher monitoring the physical memory changed its status to 'critical'."
	::= 11023


w2kMemPhysModified TRAP-TYPE
	ENTERPRISE caiW2kOs
	DESCRIPTION
		"&<caiW2kOs.968>The watcher configuration for the physical memory changed. The varbind list contains the changed attribute with its old value and with its new value."
	::= 11029




--	------------------------------------------------------------------------
--      Memory Paging Traps
--	------------------------------------------------------------------------


w2kMemPageUnknown TRAP-TYPE
	ENTERPRISE caiW2kOs
	DESCRIPTION
		"&<caiW2kOs.969>The watcher monitoring the paging memory changed its status to 'unknown'."
	::= 11030


w2kMemPageOk TRAP-TYPE
	ENTERPRISE caiW2kOs
	DESCRIPTION
		"&<caiW2kOs.970>The watcher monitoring the paging memory changed its status to 'ok'."
	::= 11031


w2kMemPageWarning TRAP-TYPE
	ENTERPRISE caiW2kOs
	DESCRIPTION
		"&<caiW2kOs.971>The watcher monitoring the paging memory changed its status to 'warning'."
	::= 11032


w2kMemPageCritical TRAP-TYPE
	ENTERPRISE caiW2kOs
	DESCRIPTION
		"&<caiW2kOs.972>The watcher monitoring the paging memory changed its status to 'critical'."
	::= 11033


w2kMemPageModified TRAP-TYPE
	ENTERPRISE caiW2kOs
	DESCRIPTION
		"&<caiW2kOs.973>The watcher configuration for the paging memory changed. The varbind list contains the changed attribute with its old value and with its new value."
	::= 11039




--	------------------------------------------------------------------------
--      Logical Volumes Traps
--	------------------------------------------------------------------------


w2kLVolUnknown TRAP-TYPE
	ENTERPRISE caiW2kOs
	DESCRIPTION
		"&<caiW2kOs.974>A watcher monitoring a logical volume changed its status to 'unknown'. The varbind list contains the name of the involved resource."
	::= 12980


w2kLVolOk TRAP-TYPE
	ENTERPRISE caiW2kOs
	DESCRIPTION
		"&<caiW2kOs.975>A watcher monitoring a logical volume changed its status to 'ok'. The varbind list contains the name of the involved resource."
	::= 12981


w2kLVolWarning TRAP-TYPE
	ENTERPRISE caiW2kOs
	DESCRIPTION
		"&<caiW2kOs.976>A watcher monitoring a logical volume changed its status to 'warning'. The varbind list contains the name of the involved resource."
	::= 12982


w2kLVolCritical TRAP-TYPE
	ENTERPRISE caiW2kOs
	DESCRIPTION
		"&<caiW2kOs.977>A watcher monitoring a logical volume changed its status to 'critical'. The varbind list contains the name of the involved resource."
	::= 12983


w2kLVolAdded TRAP-TYPE
	ENTERPRISE caiW2kOs
	DESCRIPTION
		"&<caiW2kOs.978>A watcher monitoring a logical volume was added. The varbind list contains the name of the involved resource."
	::= 12986


w2kLVolDeleted TRAP-TYPE
	ENTERPRISE caiW2kOs
	DESCRIPTION
		"&<caiW2kOs.979>A watcher monitoring a logical volume was removed. The varbind list contains the name of the involved resource."
	::= 12987


w2kLVolInfo TRAP-TYPE
	ENTERPRISE caiW2kOs
	DESCRIPTION
		"&<caiW2kOs.1071>A watcher monitoring a logical volume changed a substatus. The varbind list contains detailed information in one string."
	::= 12988


w2kLVolModified TRAP-TYPE
	ENTERPRISE caiW2kOs
	DESCRIPTION
		"&<caiW2kOs.980>The watcher configuration for a logical volume changed. The varbind list contains the name of the involved resource, the changed attribute with its old value and with its new value."
	::= 12989




--	------------------------------------------------------------------------
--      Mount Traps
--	------------------------------------------------------------------------


w2kMntUnknown TRAP-TYPE
	ENTERPRISE caiW2kOs
	DESCRIPTION
		"&<caiW2kOs.981>A watcher monitoring a mount changed its status to 'unknown'. The varbind list contains the name of the involved resource."
	::= 13980


w2kMntOk TRAP-TYPE
	ENTERPRISE caiW2kOs
	DESCRIPTION
		"&<caiW2kOs.982>A watcher monitoring a mount changed its status to 'ok'. The varbind list contains the name of the involved resource."
	::= 13981


w2kMntWarning TRAP-TYPE
	ENTERPRISE caiW2kOs
	DESCRIPTION
		"&<caiW2kOs.983>A watcher monitoring a mount changed its status to 'warning'. The varbind list contains the name of the involved resource."
	::= 13982


w2kMntCritical TRAP-TYPE
	ENTERPRISE caiW2kOs
	DESCRIPTION
		"&<caiW2kOs.984>A watcher monitoring a mount changed its status to 'critical'. The varbind list contains the name of the involved resource."
	::= 13983


w2kMntAdded TRAP-TYPE
	ENTERPRISE caiW2kOs
	DESCRIPTION
		"&<caiW2kOs.985>A watcher monitoring a mount was added. The varbind list contains the name of the involved resource."
	::= 13986


w2kMntDeleted TRAP-TYPE
	ENTERPRISE caiW2kOs
	DESCRIPTION
		"&<caiW2kOs.986>A watcher monitoring a mount was removed. The varbind list contains the name of the involved resource."
	::= 13987


w2kMntInfo TRAP-TYPE
	ENTERPRISE caiW2kOs
	DESCRIPTION
		"&<caiW2kOs.1072>A watcher monitoring a mount changed a substatus. The varbind list contains detailed information in one string."
	::= 13988


w2kMntModified TRAP-TYPE
	ENTERPRISE caiW2kOs
	DESCRIPTION
		"&<caiW2kOs.987>The watcher configuration for a mount changed. The varbind list contains the name of the involved resource, the changed attribute with its old value and with its new value."
	::= 13989




--	------------------------------------------------------------------------
--      Distributed File Systems Traps
--	------------------------------------------------------------------------


w2kDfsUnknown TRAP-TYPE
	ENTERPRISE caiW2kOs
	DESCRIPTION
		"&<caiW2kOs.988>A watcher monitoring a distributed file system link changed its status to 'unknown'. The varbind list contains the name of the involved resource."
	::= 14980


w2kDfsOk TRAP-TYPE
	ENTERPRISE caiW2kOs
	DESCRIPTION
		"&<caiW2kOs.989>A watcher monitoring a distributed file system link changed its status to 'ok'. The varbind list contains the name of the involved resource."
	::= 14981


w2kDfsWarning TRAP-TYPE
	ENTERPRISE caiW2kOs
	DESCRIPTION
		"&<caiW2kOs.990>A watcher monitoring a distributed file system link changed its status to 'warning'. The varbind list contains the name of the involved resource."
	::= 14982


w2kDfsCritical TRAP-TYPE
	ENTERPRISE caiW2kOs
	DESCRIPTION
		"&<caiW2kOs.991>A watcher monitoring a distributed file system link changed its status to 'critical'. The varbind list contains the name of the involved resource."
	::= 14983


w2kDfsAdded TRAP-TYPE
	ENTERPRISE caiW2kOs
	DESCRIPTION
		"&<caiW2kOs.992>A watcher monitoring a distributed file system link was added. The varbind list contains the name of the involved resource."
	::= 14986


w2kDfsDeleted TRAP-TYPE
	ENTERPRISE caiW2kOs
	DESCRIPTION
		"&<caiW2kOs.993>A watcher monitoring a distributed file system link was removed. The varbind list contains the name of the involved resource."
	::= 14987


w2kDfsInfo TRAP-TYPE
	ENTERPRISE caiW2kOs
	DESCRIPTION
		"&<caiW2kOs.1073>A watcher monitoring a distributed file system link changed a substatus. The varbind list contains detailed information in one string."
	::= 14988


w2kDfsModified TRAP-TYPE
	ENTERPRISE caiW2kOs
	DESCRIPTION
		"&<caiW2kOs.994>The watcher configuration for a distributed file system link changed. The varbind list contains the name of the involved resource, the changed attribute with its old value and with its new value."
	::= 14989




--	------------------------------------------------------------------------
--      Quotas Traps
--	------------------------------------------------------------------------


w2kQuotUnknown TRAP-TYPE
	ENTERPRISE caiW2kOs
	DESCRIPTION
		"&<caiW2kOs.995>A watcher monitoring a quota changed its status to 'unknown'. The varbind list contains the name of the involved resource."
	::= 15980


w2kQuotOk TRAP-TYPE
	ENTERPRISE caiW2kOs
	DESCRIPTION
		"&<caiW2kOs.996>A watcher monitoring a quota changed its status to 'ok'. The varbind list contains the name of the involved resource."
	::= 15981


w2kQuotWarning TRAP-TYPE
	ENTERPRISE caiW2kOs
	DESCRIPTION
		"&<caiW2kOs.997>A watcher monitoring a quota changed its status to 'warning'. The varbind list contains the name of the involved resource."
	::= 15982


w2kQuotCritical TRAP-TYPE
	ENTERPRISE caiW2kOs
	DESCRIPTION
		"&<caiW2kOs.998>A watcher monitoring a quota changed its status to 'critical'. The varbind list contains the name of the involved resource."
	::= 15983


w2kQuotAdded TRAP-TYPE
	ENTERPRISE caiW2kOs
	DESCRIPTION
		"&<caiW2kOs.999>A watcher monitoring a quota was added. The varbind list contains the name of the involved resource."
	::= 15986


w2kQuotDeleted TRAP-TYPE
	ENTERPRISE caiW2kOs
	DESCRIPTION
		"&<caiW2kOs.1000>A watcher monitoring a quota was removed. The varbind list contains the name of the involved resource."
	::= 15987


w2kQuotInfo TRAP-TYPE
	ENTERPRISE caiW2kOs
	DESCRIPTION
		"&<caiW2kOs.1074>A watcher monitoring a quota changed a substatus. The varbind list contains detailed information in one string."
	::= 15988


w2kQuotModified TRAP-TYPE
	ENTERPRISE caiW2kOs
	DESCRIPTION
		"&<caiW2kOs.1001>The watcher configuration for a quota changed. The varbind list contains the name of the involved resource, the changed attribute with its old value and with its new value."
	::= 15989




--	------------------------------------------------------------------------
--      Directories Traps
--	------------------------------------------------------------------------


w2kDirUnknown TRAP-TYPE
	ENTERPRISE caiW2kOs
	DESCRIPTION
		"&<caiW2kOs.1002>A watcher monitoring a directory changed its status to 'unknown'. The varbind list contains the name of the involved resource."
	::= 16980


w2kDirOk TRAP-TYPE
	ENTERPRISE caiW2kOs
	DESCRIPTION
		"&<caiW2kOs.1003>A watcher monitoring a directory changed its status to 'ok'. The varbind list contains the name of the involved resource."
	::= 16981


w2kDirWarning TRAP-TYPE
	ENTERPRISE caiW2kOs
	DESCRIPTION
		"&<caiW2kOs.1004>A watcher monitoring a directory changed its status to 'warning'. The varbind list contains the name of the involved resource."
	::= 16982


w2kDirCritical TRAP-TYPE
	ENTERPRISE caiW2kOs
	DESCRIPTION
		"&<caiW2kOs.1005>A watcher monitoring a directory changed its status to 'critical'. The varbind list contains the name of the involved resource."
	::= 16983


w2kDirAdded TRAP-TYPE
	ENTERPRISE caiW2kOs
	DESCRIPTION
		"&<caiW2kOs.1006>A watcher monitoring a directory was added. The varbind list contains the name of the involved resource."
	::= 16986


w2kDirDeleted TRAP-TYPE
	ENTERPRISE caiW2kOs
	DESCRIPTION
		"&<caiW2kOs.1007>A watcher monitoring a directory was removed. The varbind list contains the name of the involved resource."
	::= 16987


w2kDirInfo TRAP-TYPE
	ENTERPRISE caiW2kOs
	DESCRIPTION
		"&<caiW2kOs.1075>A watcher monitoring a directory changed a substatus. The varbind list contains detailed information in one string."
	::= 16988


w2kDirModified TRAP-TYPE
	ENTERPRISE caiW2kOs
	DESCRIPTION
		"&<caiW2kOs.1008>The watcher configuration for a directory changed. The varbind list contains the name of the involved resource, the changed attribute with its old value and with its new value."
	::= 16989




--	------------------------------------------------------------------------
--      Files Traps
--	------------------------------------------------------------------------


w2kFileUnknown TRAP-TYPE
	ENTERPRISE caiW2kOs
	DESCRIPTION
		"&<caiW2kOs.1009>A watcher monitoring a file changed its status to 'unknown'. The varbind list contains the name of the involved resource."
	::= 17980


w2kFileOk TRAP-TYPE
	ENTERPRISE caiW2kOs
	DESCRIPTION
		"&<caiW2kOs.1010>A watcher monitoring a file changed its status to 'ok'. The varbind list contains the name of the involved resource."
	::= 17981


w2kFileWarning TRAP-TYPE
	ENTERPRISE caiW2kOs
	DESCRIPTION
		"&<caiW2kOs.1011>A watcher monitoring a file changed its status to 'warning'. The varbind list contains the name of the involved resource."
	::= 17982


w2kFileCritical TRAP-TYPE
	ENTERPRISE caiW2kOs
	DESCRIPTION
		"&<caiW2kOs.1012>A watcher monitoring a file changed its status to 'critical'. The varbind list contains the name of the involved resource."
	::= 17983


w2kFileAdded TRAP-TYPE
	ENTERPRISE caiW2kOs
	DESCRIPTION
		"&<caiW2kOs.1013>A watcher monitoring a file was added. The varbind list contains the name of the involved resource."
	::= 17986


w2kFileDeleted TRAP-TYPE
	ENTERPRISE caiW2kOs
	DESCRIPTION
		"&<caiW2kOs.1014>A watcher monitoring a file was removed. The varbind list contains the name of the involved resource."
	::= 17987


w2kFileInfo TRAP-TYPE
	ENTERPRISE caiW2kOs
	DESCRIPTION
		"&<caiW2kOs.1076>A watcher monitoring a file changed a substatus. The varbind list contains detailed information in one string."
	::= 17988


w2kFileModified TRAP-TYPE
	ENTERPRISE caiW2kOs
	DESCRIPTION
		"&<caiW2kOs.1015>The watcher configuration for a file changed. The varbind list contains the name of the involved resource, the changed attribute with its old value and with its new value."
	::= 17989




--	------------------------------------------------------------------------
--      Processes Traps
--	------------------------------------------------------------------------


w2kProcUnknown TRAP-TYPE
	ENTERPRISE caiW2kOs
	DESCRIPTION
		"&<caiW2kOs.1016>A watcher monitoring a process changed its status to 'unknown'. The varbind list contains the name of the involved resource."
	::= 18980


w2kProcOk TRAP-TYPE
	ENTERPRISE caiW2kOs
	DESCRIPTION
		"&<caiW2kOs.1017>A watcher monitoring a process changed its status to 'ok'. The varbind list contains the name of the involved resource."
	::= 18981


w2kProcWarning TRAP-TYPE
	ENTERPRISE caiW2kOs
	DESCRIPTION
		"&<caiW2kOs.1018>A watcher monitoring a process changed its status to 'warning'. The varbind list contains the name of the involved resource."
	::= 18982


w2kProcCritical TRAP-TYPE
	ENTERPRISE caiW2kOs
	DESCRIPTION
		"&<caiW2kOs.1019>A watcher monitoring a process changed its status to 'critical'. The varbind list contains the name of the involved resource."
	::= 18983


w2kProcAdded TRAP-TYPE
	ENTERPRISE caiW2kOs
	DESCRIPTION
		"&<caiW2kOs.1020>A watcher monitoring a process was added. The varbind list contains the name of the involved resource."
	::= 18986


w2kProcDeleted TRAP-TYPE
	ENTERPRISE caiW2kOs
	DESCRIPTION
		"&<caiW2kOs.1021>A watcher monitoring a process was removed. The varbind list contains the name of the involved resource."
	::= 18987


w2kProcInfo TRAP-TYPE
	ENTERPRISE caiW2kOs
	DESCRIPTION
		"&<caiW2kOs.1077>A watcher monitoring a process changed a substatus. The varbind list contains detailed information in one string."
	::= 18988


w2kProcModified TRAP-TYPE
	ENTERPRISE caiW2kOs
	DESCRIPTION
		"&<caiW2kOs.1022>The watcher configuration for a process changed. The varbind list contains the name of the involved resource, the changed attribute with its old value and with its new value."
	::= 18989




--	------------------------------------------------------------------------
--      Services Traps
--	------------------------------------------------------------------------


w2kSrvcUnknown TRAP-TYPE
	ENTERPRISE caiW2kOs
	DESCRIPTION
		"&<caiW2kOs.1023>A watcher monitoring a service changed its status to 'unknown'. The varbind list contains the name of the involved resource."
	::= 19980


w2kSrvcOk TRAP-TYPE
	ENTERPRISE caiW2kOs
	DESCRIPTION
		"&<caiW2kOs.1024>A watcher monitoring a service changed its status to 'ok'. The varbind list contains the name of the involved resource."
	::= 19981


w2kSrvcWarning TRAP-TYPE
	ENTERPRISE caiW2kOs
	DESCRIPTION
		"&<caiW2kOs.1025>A watcher monitoring a service changed its status to 'warning'. The varbind list contains the name of the involved resource."
	::= 19982


w2kSrvcCritical TRAP-TYPE
	ENTERPRISE caiW2kOs
	DESCRIPTION
		"&<caiW2kOs.1026>A watcher monitoring a service changed its status to 'critical'. The varbind list contains the name of the involved resource."
	::= 19983


w2kSrvcAdded TRAP-TYPE
	ENTERPRISE caiW2kOs
	DESCRIPTION
		"&<caiW2kOs.1027>A watcher monitoring a service was added. The varbind list contains the name of the involved resource."
	::= 19986


w2kSrvcDeleted TRAP-TYPE
	ENTERPRISE caiW2kOs
	DESCRIPTION
		"&<caiW2kOs.1028>A watcher monitoring a service was removed. The varbind list contains the name of the involved resource."
	::= 19987


w2kSrvcInfo TRAP-TYPE
	ENTERPRISE caiW2kOs
	DESCRIPTION
		"&<caiW2kOs.1078>A watcher monitoring a service changed a substatus. The varbind list contains detailed information in one string."
	::= 19988


w2kSrvcModified TRAP-TYPE
	ENTERPRISE caiW2kOs
	DESCRIPTION
		"&<caiW2kOs.1029>The watcher configuration for a service changed. The varbind list contains the name of the involved resource, the changed attribute with its old value and with its new value."
	::= 19989




--	------------------------------------------------------------------------
--      Jobs Traps
--	------------------------------------------------------------------------


w2kJobUnknown TRAP-TYPE
	ENTERPRISE caiW2kOs
	DESCRIPTION
		"&<caiW2kOs.1030>A watcher monitoring a job changed its status to 'unknown'. The varbind list contains the name of the involved resource."
	::= 20980


w2kJobOk TRAP-TYPE
	ENTERPRISE caiW2kOs
	DESCRIPTION
		"&<caiW2kOs.1031>A watcher monitoring a job changed its status to 'ok'. The varbind list contains the name of the involved resource."
	::= 20981


w2kJobWarning TRAP-TYPE
	ENTERPRISE caiW2kOs
	DESCRIPTION
		"&<caiW2kOs.1032>A watcher monitoring a job changed its status to 'warning'. The varbind list contains the name of the involved resource."
	::= 20982


w2kJobCritical TRAP-TYPE
	ENTERPRISE caiW2kOs
	DESCRIPTION
		"&<caiW2kOs.1033>A watcher monitoring a job changed its status to 'critical'. The varbind list contains the name of the involved resource."
	::= 20983


w2kJobAdded TRAP-TYPE
	ENTERPRISE caiW2kOs
	DESCRIPTION
		"&<caiW2kOs.1034>A watcher monitoring a job was added. The varbind list contains the name of the involved resource."
	::= 20986


w2kJobDeleted TRAP-TYPE
	ENTERPRISE caiW2kOs
	DESCRIPTION
		"&<caiW2kOs.1035>A watcher monitoring a job was removed. The varbind list contains the name of the involved resource."
	::= 20987


w2kJobInfo TRAP-TYPE
	ENTERPRISE caiW2kOs
	DESCRIPTION
		"&<caiW2kOs.1079>A watcher monitoring a job changed a substatus. The varbind list contains detailed information in one string."
	::= 20988


w2kJobModified TRAP-TYPE
	ENTERPRISE caiW2kOs
	DESCRIPTION
		"&<caiW2kOs.1036>The watcher configuration for a job changed. The varbind list contains the name of the involved resource, the changed attribute with its old value and with its new value."
	::= 20989




--	------------------------------------------------------------------------
--      Sessions Traps
--	------------------------------------------------------------------------


w2kSessUnknown TRAP-TYPE
	ENTERPRISE caiW2kOs
	DESCRIPTION
		"&<caiW2kOs.1037>A watcher monitoring a session changed its status to 'unknown'. The varbind list contains the name of the involved resource."
	::= 21980


w2kSessOk TRAP-TYPE
	ENTERPRISE caiW2kOs
	DESCRIPTION
		"&<caiW2kOs.1038>A watcher monitoring a session changed its status to 'ok'. The varbind list contains the name of the involved resource."
	::= 21981


w2kSessWarning TRAP-TYPE
	ENTERPRISE caiW2kOs
	DESCRIPTION
		"&<caiW2kOs.1039>A watcher monitoring a session changed its status to 'warning'. The varbind list contains the name of the involved resource."
	::= 21982


w2kSessCritical TRAP-TYPE
	ENTERPRISE caiW2kOs
	DESCRIPTION
		"&<caiW2kOs.1040>A watcher monitoring a session changed its status to 'critical'. The varbind list contains the name of the involved resource."
	::= 21983


w2kSessAdded TRAP-TYPE
	ENTERPRISE caiW2kOs
	DESCRIPTION
		"&<caiW2kOs.1041>A watcher monitoring a session was added. The varbind list contains the name of the involved resource."
	::= 21986


w2kSessDeleted TRAP-TYPE
	ENTERPRISE caiW2kOs
	DESCRIPTION
		"&<caiW2kOs.1042>A watcher monitoring a session was removed. The varbind list contains the name of the involved resource."
	::= 21987


w2kSessInfo TRAP-TYPE
	ENTERPRISE caiW2kOs
	DESCRIPTION
		"&<caiW2kOs.1080>A watcher monitoring a session changed a substatus. The varbind list contains detailed information in one string."
	::= 21988


w2kSessModified TRAP-TYPE
	ENTERPRISE caiW2kOs
	DESCRIPTION
		"&<caiW2kOs.1043>The watcher configuration for a session changed. The varbind list contains the name of the involved resource, the changed attribute with its old value and with its new value."
	::= 21989




--	------------------------------------------------------------------------
--      Printers Traps
--	------------------------------------------------------------------------


w2kPrnUnknown TRAP-TYPE
	ENTERPRISE caiW2kOs
	DESCRIPTION
		"&<caiW2kOs.1044>A watcher monitoring a printer changed its status to 'unknown'. The varbind list contains the name of the involved resource."
	::= 22980


w2kPrnOk TRAP-TYPE
	ENTERPRISE caiW2kOs
	DESCRIPTION
		"&<caiW2kOs.1045>A watcher monitoring a printer changed its status to 'ok'. The varbind list contains the name of the involved resource."
	::= 22981


w2kPrnWarning TRAP-TYPE
	ENTERPRISE caiW2kOs
	DESCRIPTION
		"&<caiW2kOs.1046>A watcher monitoring a printer changed its status to 'warning'. The varbind list contains the name of the involved resource."
	::= 22982


w2kPrnCritical TRAP-TYPE
	ENTERPRISE caiW2kOs
	DESCRIPTION
		"&<caiW2kOs.1047>A watcher monitoring a printer changed its status to 'critical'. The varbind list contains the name of the involved resource."
	::= 22983


w2kPrnAdded TRAP-TYPE
	ENTERPRISE caiW2kOs
	DESCRIPTION
		"&<caiW2kOs.1048>A watcher monitoring a printer was added. The varbind list contains the name of the involved resource."
	::= 22986


w2kPrnDeleted TRAP-TYPE
	ENTERPRISE caiW2kOs
	DESCRIPTION
		"&<caiW2kOs.1049>A watcher monitoring a printer was removed. The varbind list contains the name of the involved resource."
	::= 22987


w2kPrnInfo TRAP-TYPE
	ENTERPRISE caiW2kOs
	DESCRIPTION
		"&<caiW2kOs.1081>A watcher monitoring a printer changed a substatus. The varbind list contains detailed information in one string."
	::= 22988


w2kPrnModified TRAP-TYPE
	ENTERPRISE caiW2kOs
	DESCRIPTION
		"&<caiW2kOs.1050>The watcher configuration for a printer changed. The varbind list contains the name of the involved resource, the changed attribute with its old value and with its new value."
	::= 22989




--	------------------------------------------------------------------------
--      Network Interfaces Total Traps
--	------------------------------------------------------------------------


w2kNetTotalUnknown TRAP-TYPE
	ENTERPRISE caiW2kOs
	DESCRIPTION
		"&<caiW2kOs.1051>The watcher monitoring the network interfaces total changed its status to 'unknown'."
	::= 23000


w2kNetTotalOk TRAP-TYPE
	ENTERPRISE caiW2kOs
	DESCRIPTION
		"&<caiW2kOs.1052>The watcher monitoring the network interfaces total changed its status to 'ok'."
	::= 23001


w2kNetTotalWarning TRAP-TYPE
	ENTERPRISE caiW2kOs
	DESCRIPTION
		"&<caiW2kOs.1053>The watcher monitoring the network interfaces total changed its status to 'warning'."
	::= 23002


w2kNetTotalCritical TRAP-TYPE
	ENTERPRISE caiW2kOs
	DESCRIPTION
		"&<caiW2kOs.1054>The watcher monitoring the network interfaces total changed its status to 'critical'."
	::= 23003


w2kNetTotalInfo TRAP-TYPE
	ENTERPRISE caiW2kOs
	DESCRIPTION
		"&<caiW2kOs.1082>The watcher monitoring the network interfaces total changed a substatus. The varbind list contains detailed information in one string."
	::= 23008


w2kNetTotalModified TRAP-TYPE
	ENTERPRISE caiW2kOs
	DESCRIPTION
		"&<caiW2kOs.1055>The watcher configuration for the network interfaces total changed. The varbind list contains the changed attribute with its old value and with its new value."
	::= 23009




--	------------------------------------------------------------------------
--      Network Interfaces Traps
--	------------------------------------------------------------------------


w2kNetUnknown TRAP-TYPE
	ENTERPRISE caiW2kOs
	DESCRIPTION
		"&<caiW2kOs.1056>A watcher monitoring a network interface changed its status to 'unknown'. The varbind list contains the name of the involved resource."
	::= 23990


w2kNetOk TRAP-TYPE
	ENTERPRISE caiW2kOs
	DESCRIPTION
		"&<caiW2kOs.1057>A watcher monitoring a network interface changed its status to 'ok'. The varbind list contains the name of the involved resource."
	::= 23991


w2kNetWarning TRAP-TYPE
	ENTERPRISE caiW2kOs
	DESCRIPTION
		"&<caiW2kOs.1058>A watcher monitoring a network interface changed its status to 'warning'. The varbind list contains the name of the involved resource."
	::= 23992


w2kNetCritical TRAP-TYPE
	ENTERPRISE caiW2kOs
	DESCRIPTION
		"&<caiW2kOs.1059>A watcher monitoring a network interface changed its status to 'critical'. The varbind list contains the name of the involved resource."
	::= 23993


w2kNetAdded TRAP-TYPE
	ENTERPRISE caiW2kOs
	DESCRIPTION
		"&<caiW2kOs.1060>A watcher monitoring a network interface was added. The varbind list contains the name of the involved resource."
	::= 23996


w2kNetDeleted TRAP-TYPE
	ENTERPRISE caiW2kOs
	DESCRIPTION
		"&<caiW2kOs.1061>A watcher monitoring a network interface was removed. The varbind list contains the name of the involved resource."
	::= 23997


w2kNetInfo TRAP-TYPE
	ENTERPRISE caiW2kOs
	DESCRIPTION
		"&<caiW2kOs.1083>A watcher monitoring a network interface changed a substatus. The varbind list contains detailed information in one string."
	::= 23998


w2kNetModified TRAP-TYPE
	ENTERPRISE caiW2kOs
	DESCRIPTION
		"&<caiW2kOs.1062>The watcher configuration for a network interface changed. The varbind list contains the name of the involved resource, the changed attribute with its old value and with its new value."
	::= 23999




--	------------------------------------------------------------------------
--      Registry Entries Traps
--	------------------------------------------------------------------------


w2kRegUnknown TRAP-TYPE
	ENTERPRISE caiW2kOs
	DESCRIPTION
		"&<caiW2kOs.1063>A watcher monitoring a registry entry changed its status to 'unknown'. The varbind list contains the name of the involved resource."
	::= 24980


w2kRegOk TRAP-TYPE
	ENTERPRISE caiW2kOs
	DESCRIPTION
		"&<caiW2kOs.1064>A watcher monitoring a registry entry changed its status to 'ok'. The varbind list contains the name of the involved resource."
	::= 24981


w2kRegWarning TRAP-TYPE
	ENTERPRISE caiW2kOs
	DESCRIPTION
		"&<caiW2kOs.1065>A watcher monitoring a registry entry changed its status to 'warning'. The varbind list contains the name of the involved resource."
	::= 24982


w2kRegCritical TRAP-TYPE
	ENTERPRISE caiW2kOs
	DESCRIPTION
		"&<caiW2kOs.1066>A watcher monitoring a registry entry changed its status to 'critical'. The varbind list contains the name of the involved resource."
	::= 24983


w2kRegAdded TRAP-TYPE
	ENTERPRISE caiW2kOs
	DESCRIPTION
		"&<caiW2kOs.1067>A watcher monitoring a registry entry was added. The varbind list contains the name of the involved resource."
	::= 24986


w2kRegDeleted TRAP-TYPE
	ENTERPRISE caiW2kOs
	DESCRIPTION
		"&<caiW2kOs.1068>A watcher monitoring a registry entry was removed. The varbind list contains the name of the involved resource."
	::= 24987


w2kRegInfo TRAP-TYPE
	ENTERPRISE caiW2kOs
	DESCRIPTION
		"&<caiW2kOs.1084>A watcher monitoring a registry entry changed a substatus. The varbind list contains detailed information in one string."
	::= 24988


w2kRegModified TRAP-TYPE
	ENTERPRISE caiW2kOs
	DESCRIPTION
		"&<caiW2kOs.1069>The watcher configuration for a registry entry changed. The varbind list contains the name of the involved resource, the changed attribute with its old value and with its new value."
	::= 24989


--  ========================================================================
--
--  Extension groups of caiW2kOs MIB:
--  ---------------------------------
--  w2kEHGroup added to support reports for Concord eHealth
--
--  ========================================================================
w2kExtensionGroup OBJECT IDENTIFIER ::= { caiW2kOs 5 }

w2kEHGroup OBJECT IDENTIFIER ::= { w2kExtensionGroup 1 }


--  ---------------------------------
--  Poll information
--  ---------------------------------
w2kEHPollMethod OBJECT-TYPE
	SYNTAX INTEGER {
		disabled(1),
		enabled(2)
	}
	ACCESS read-write
	STATUS mandatory
	DESCRIPTION "The poll method for the eHealth group. If set to disabled, polling of this group is not possible."
	DEFVAL { 2 }
	::= { w2kEHGroup 1 }

w2kEHLastPoll OBJECT-TYPE
	SYNTAX TimeTicks
	ACCESS read-only
	STATUS mandatory
	DESCRIPTION "The value of w2kEHSrvSystemUpTime at the point in time the w2kEHSrvGroup group (and all w2kEH tables) was last polled."
	::= { w2kEHGroup 2 }


--  ---------------------------------
--  Server group
--  ---------------------------------
w2kEHSrvGroup OBJECT IDENTIFIER ::= { w2kEHGroup 3 }

w2kEHSrvSystemUpTime OBJECT-TYPE
	SYNTAX TimeTicks
	ACCESS read-only
	STATUS mandatory
	DESCRIPTION "The time (in hundredths of a second) since the system was last started."
	::= { w2kEHSrvGroup 1 }

w2kEHSrvSystemNumUsers OBJECT-TYPE
	SYNTAX Gauge
	ACCESS read-only
	STATUS mandatory
	DESCRIPTION "The number of users."
	::= { w2kEHSrvGroup 2 }

w2kEHSrvSystemProcesses OBJECT-TYPE
	SYNTAX Gauge
	ACCESS read-only
	STATUS mandatory
	DESCRIPTION "The number of processes."
	::= { w2kEHSrvGroup 3 }

w2kEHSrvMemorySize OBJECT-TYPE
	SYNTAX KBytes
	ACCESS read-only
	STATUS mandatory
	DESCRIPTION "The amount of physical main memory contained by the host."
	::= { w2kEHSrvGroup 4 }

w2kEHSrvMemInUse OBJECT-TYPE
	SYNTAX Gauge
	ACCESS read-only
	STATUS mandatory
	DESCRIPTION "The total real KBytes of memory in use."
	::= { w2kEHSrvGroup 5 }

w2kEHSrvTotalSwapSpace OBJECT-TYPE
	SYNTAX INTEGER
	ACCESS read-only
	STATUS mandatory
	DESCRIPTION "Total system swap space in KBytes."
	::= { w2kEHSrvGroup 6 }

w2kEHSrvSwapInUse OBJECT-TYPE
	SYNTAX Gauge
	ACCESS read-only
	STATUS mandatory
	DESCRIPTION "The amount of swap space in KBytes currently in use by the system."
	::= { w2kEHSrvGroup 7 }

w2kEHSrvLoadAverage5Min OBJECT-TYPE
	SYNTAX INTEGER
	ACCESS read-only
	STATUS mandatory
	DESCRIPTION "The load average over the last 5 minutes. The load average represents the average number of jobs in the run queue over the specified time range. The value reported is the load average multiplied by 100."
	::= { w2kEHSrvGroup 8 }

w2kEHSrvNumBreadRequests OBJECT-TYPE
	SYNTAX Counter
	ACCESS read-only
	STATUS mandatory
	DESCRIPTION "The total number of calls to the kernel's bread() function."
	::= { w2kEHSrvGroup 9 }

w2kEHSrvNumBreadHits OBJECT-TYPE
	SYNTAX Counter
	ACCESS read-only
	STATUS mandatory
	DESCRIPTION "The number of kernel buffer cache 'hits'."
	::= { w2kEHSrvGroup 10 }

w2kEHSrvSystemCalls OBJECT-TYPE
	SYNTAX Counter
	ACCESS read-only
	STATUS mandatory
	DESCRIPTION "The number of calls to system service routines."
	::= { w2kEHSrvGroup 11 }

w2kEHSrvInterrupts OBJECT-TYPE
	SYNTAX Counter
	ACCESS read-only
	STATUS mandatory
	DESCRIPTION "The number of hardware interrupts that have occurred."
	::= { w2kEHSrvGroup 12 }

w2kEHSrvPageFaults OBJECT-TYPE
	SYNTAX Counter
	ACCESS read-only
	STATUS mandatory
	DESCRIPTION "Number of page faults in the processor."
	::= { w2kEHSrvGroup 13 }

w2kEHSrvPagesInput OBJECT-TYPE
	SYNTAX Counter
	ACCESS read-only
	STATUS mandatory
	DESCRIPTION "Number of pages read from disk to resolve memory references."
	::= { w2kEHSrvGroup 14 }

w2kEHSrvPagesOutput OBJECT-TYPE
	SYNTAX Counter
	ACCESS read-only
	STATUS mandatory
	DESCRIPTION "Number of pages written to disk because the pages were modified."
	::= { w2kEHSrvGroup 15 }

w2kEHSrvIfNumber OBJECT-TYPE
	SYNTAX INTEGER
	ACCESS read-only
	STATUS mandatory
	DESCRIPTION "The number of network interfaces."
	::= { w2kEHSrvGroup 16 }


--  ---------------------------------
--  Cpu table
--  ---------------------------------
w2kEHCpuTable OBJECT-TYPE
	SYNTAX SEQUENCE OF W2kEHCpuEntry
	ACCESS not-accessible
	STATUS mandatory
	DESCRIPTION ""
	::= { w2kEHGroup 4 }

w2kEHCpuEntry OBJECT-TYPE
	SYNTAX W2kEHCpuEntry
	ACCESS not-accessible
	STATUS mandatory
	DESCRIPTION ""
	INDEX { w2kEHCpuIndex }
	::= { w2kEHCpuTable 1 }

W2kEHCpuEntry ::= SEQUENCE {
	w2kEHCpuIndex INTEGER,
	w2kEHCpuName DisplayString,
	w2kEHCpuIdlePercent INTEGER,
	w2kEHCpuUserPercent INTEGER,
	w2kEHCpuSysPercent INTEGER
}

w2kEHCpuIndex OBJECT-TYPE
	SYNTAX INTEGER (1..2147483647)
	ACCESS read-only
	STATUS mandatory
	DESCRIPTION "The unique index of this table entry."
	::= { w2kEHCpuEntry 1 }

w2kEHCpuName OBJECT-TYPE
	SYNTAX DisplayString
	ACCESS read-only
	STATUS mandatory
	DESCRIPTION "The name of the CPU (in the format 'Cpu-N')."
	::= { w2kEHCpuEntry 2 }

w2kEHCpuIdlePercent OBJECT-TYPE
	SYNTAX INTEGER (0..100)
	ACCESS read-only
	STATUS mandatory
	DESCRIPTION "The percentage of time (over the sample period) that the system's Cpu was idle."
	::= { w2kEHCpuEntry 3 }

w2kEHCpuUserPercent OBJECT-TYPE
	SYNTAX INTEGER (0..100)
	ACCESS read-only
	STATUS mandatory
	DESCRIPTION "The percentage of time (over the sample period) that the system's Cpu was executing in user mode."
	::= { w2kEHCpuEntry 4 }

w2kEHCpuSysPercent OBJECT-TYPE
	SYNTAX INTEGER (0..100)
	ACCESS read-only
	STATUS mandatory
	DESCRIPTION "The percentage of time (over the sample period) that the system's Cpu was executing the kernel or operating system."
	::= { w2kEHCpuEntry 5 }


--  ---------------------------------
--  Disk table
--  ---------------------------------
w2kEHDiskTable OBJECT-TYPE
	SYNTAX SEQUENCE OF W2kEHDiskEntry
	ACCESS not-accessible
	STATUS mandatory
	DESCRIPTION ""
	::= { w2kEHGroup 5 }

w2kEHDiskEntry OBJECT-TYPE
	SYNTAX W2kEHDiskEntry
	ACCESS not-accessible
	STATUS mandatory
	DESCRIPTION ""
	INDEX { w2kEHDiskIndex }
	::= { w2kEHDiskTable 1 }

W2kEHDiskEntry ::= SEQUENCE {
	w2kEHDiskIndex INTEGER,
	w2kEHDiskName DisplayString,
	w2kEHDiskDeviceErrors Counter,
	w2kEHDiskStorageCapacity INTEGER,
	w2kEHDiskQueueLength Gauge,
	w2kEHDiskUtilization INTEGER,
	w2kEHDiskKBytesTransferred Counter,
	w2kEHDiskReads Counter,
	w2kEHDiskWrites Counter
}

w2kEHDiskIndex OBJECT-TYPE
	SYNTAX INTEGER (1..2147483647)
	ACCESS read-only
	STATUS mandatory
	DESCRIPTION "The unique index of this table entry."
	::= { w2kEHDiskEntry 1 }

w2kEHDiskName OBJECT-TYPE
	SYNTAX DisplayString
	ACCESS read-only
	STATUS mandatory
	DESCRIPTION "The name of the disk (in the format 'HarddiskN')."
	::= { w2kEHDiskEntry 2 }

w2kEHDiskDeviceErrors OBJECT-TYPE
	SYNTAX Counter
	ACCESS read-only
	STATUS mandatory
	DESCRIPTION "The number of errors detected on this disk."
	::= { w2kEHDiskEntry 3 }

w2kEHDiskStorageCapacity OBJECT-TYPE
	SYNTAX INTEGER (0..2147483647)
	ACCESS read-only
	STATUS mandatory
	DESCRIPTION "Disk capacity in KB."
	::= { w2kEHDiskEntry 4 }

w2kEHDiskQueueLength OBJECT-TYPE
	SYNTAX Gauge
	ACCESS read-only
	STATUS mandatory
	DESCRIPTION "The average number of operations waiting in the disk's service queue over the last measurement period."
	::= { w2kEHDiskEntry 5 }

w2kEHDiskUtilization OBJECT-TYPE
	SYNTAX INTEGER (0..100)
	ACCESS read-only
	STATUS mandatory
	DESCRIPTION "The utilization rate (percentage) for this disk over the last measurement period."
	::= { w2kEHDiskEntry 6 }

w2kEHDiskKBytesTransferred OBJECT-TYPE
	SYNTAX Counter
	ACCESS read-only
	STATUS mandatory
	DESCRIPTION "The number of KBytes transferred to/from this disk."
	::= { w2kEHDiskEntry 7}

w2kEHDiskReads OBJECT-TYPE
	SYNTAX Counter
	ACCESS read-only
	STATUS mandatory
	DESCRIPTION "The number of read operations from this disk."
	::= { w2kEHDiskEntry 8 }

w2kEHDiskWrites OBJECT-TYPE
	SYNTAX Counter
	ACCESS read-only
	STATUS mandatory
	DESCRIPTION "The number of write operations to this disk."
	::= { w2kEHDiskEntry 9 }


--  ---------------------------------
--  Device (partition) table
--  ---------------------------------
w2kEHDevTable OBJECT-TYPE
	SYNTAX SEQUENCE OF W2kEHDevEntry
	ACCESS not-accessible
	STATUS mandatory
	DESCRIPTION ""
	::= { w2kEHGroup 6 }

w2kEHDevEntry OBJECT-TYPE
	SYNTAX W2kEHDevEntry
	ACCESS not-accessible
	STATUS mandatory
	DESCRIPTION ""
	INDEX { w2kEHDevIndex }
	::= { w2kEHDevTable 1 }

W2kEHDevEntry ::= SEQUENCE {
	w2kEHDevIndex INTEGER,
	w2kEHDevName DisplayString,
	w2kEHDevStorageAllocationUnits INTEGER,
	w2kEHDevStorageSize INTEGER,
	w2kEHDevStorageUsed INTEGER,
	w2kEHDevStorageAllocationFailures Counter
}

w2kEHDevIndex OBJECT-TYPE
	SYNTAX INTEGER (1..2147483647)
	ACCESS read-only
	STATUS mandatory
	DESCRIPTION "The unique index of this table entry."
	::= { w2kEHDevEntry 1 }

w2kEHDevName OBJECT-TYPE
	SYNTAX DisplayString
	ACCESS read-only
	STATUS mandatory
	DESCRIPTION "The name of the device (partition)."
	::= { w2kEHDevEntry 2 }

w2kEHDevStorageAllocationUnits OBJECT-TYPE
	SYNTAX INTEGER (1..2147483647)
	ACCESS read-only
	STATUS mandatory
	DESCRIPTION "The size, in bytes, of the data objects allocated from this device."
	::= { w2kEHDevEntry 3 }

w2kEHDevStorageSize OBJECT-TYPE
	SYNTAX INTEGER (0..2147483647)
	ACCESS read-only
	STATUS mandatory
	DESCRIPTION "The size of the storage represented by this entry, in units of StorageAllocationUnits."
	::= { w2kEHDevEntry 4 }

w2kEHDevStorageUsed OBJECT-TYPE
	SYNTAX INTEGER (0..2147483647)
	ACCESS read-only
	STATUS mandatory
	DESCRIPTION "The amount of the storage represented by this entry that is allocated, in units of StorageAllocationUnits."
	::= { w2kEHDevEntry 5 }

w2kEHDevStorageAllocationFailures OBJECT-TYPE
	SYNTAX Counter
	ACCESS read-only
	STATUS mandatory
	DESCRIPTION "The number of requests for storage represented by this entry that could not be honored due to not enough storage."
	::= { w2kEHDevEntry 6 }


--  ---------------------------------
--  Network interface table
--  ---------------------------------
w2kEHIfTable OBJECT-TYPE
	SYNTAX SEQUENCE OF W2kEHIfEntry
	ACCESS not-accessible
	STATUS mandatory
	DESCRIPTION ""
	::= { w2kEHGroup 7 }

w2kEHIfEntry OBJECT-TYPE
	SYNTAX W2kEHIfEntry
	ACCESS not-accessible
	STATUS mandatory
	DESCRIPTION ""
	INDEX { w2kEHIfIndex }
	::= { w2kEHIfTable 1 }

W2kEHIfEntry ::= SEQUENCE {
	w2kEHIfIndex INTEGER,
	w2kEHIfDescr DisplayString,
	w2kEHIfType INTEGER,
	w2kEHIfSpeed Gauge,
	w2kEHIfPhysAddress PhysAddress,
	w2kEHIfAdminStatus INTEGER,
	w2kEHIfOperStatus INTEGER,
	w2kEHIfLastChange TimeTicks,
	w2kEHIfInOctets Counter,
	w2kEHIfInUcastPkts Counter,
	w2kEHIfInNUcastPkts Counter,
	w2kEHIfInDiscards Counter,
	w2kEHIfInErrors Counter,
	w2kEHIfInUnknownProtos Counter,
	w2kEHIfOutOctets Counter,
	w2kEHIfOutUcastPkts Counter,
	w2kEHIfOutNUcastPkts Counter,
	w2kEHIfOutDiscards Counter,
	w2kEHIfOutErrors Counter,
	w2kEHIfIpAdEntAddr IpAddress
}

w2kEHIfIndex OBJECT-TYPE
	SYNTAX INTEGER (1..2147483647)
	ACCESS read-only
	STATUS mandatory
	DESCRIPTION "The unique index of this table entry."
	::= { w2kEHIfEntry 1 }

w2kEHIfDescr OBJECT-TYPE
	SYNTAX DisplayString
	ACCESS read-only
	STATUS mandatory
	DESCRIPTION "The description of the network interface."
	::= { w2kEHIfEntry 2 }

w2kEHIfType OBJECT-TYPE
	SYNTAX INTEGER
	ACCESS read-only
	STATUS mandatory
	DESCRIPTION "The type of interface."
	::= { w2kEHIfEntry 3 }

w2kEHIfSpeed OBJECT-TYPE
	SYNTAX Gauge
	ACCESS read-only
	STATUS mandatory
	DESCRIPTION "An estimate of the interface's current bandwidth in bits per second."
	::= { w2kEHIfEntry 4 }

w2kEHIfPhysAddress OBJECT-TYPE
	SYNTAX PhysAddress
	ACCESS read-only
	STATUS mandatory
	DESCRIPTION "The interface's address at the protocol layer."
	::= { w2kEHIfEntry 5 }

w2kEHIfAdminStatus OBJECT-TYPE
	SYNTAX INTEGER {
		up(1),
		down(2),
		testing(3),
		unknown(4),
		dormant(5)
	}
	ACCESS read-only
	STATUS mandatory
	DESCRIPTION "The desired state of the interface."
	::= { w2kEHIfEntry 6 }

w2kEHIfOperStatus OBJECT-TYPE
	SYNTAX INTEGER {
		up(1),
		down(2),
		testing(3),
		unknown(4),
		dormant(5)
	}
	ACCESS read-only
	STATUS mandatory
	DESCRIPTION "The current operational state of the interface."
	::= { w2kEHIfEntry 7 }

w2kEHIfLastChange OBJECT-TYPE
	SYNTAX TimeTicks
	ACCESS read-only
	STATUS mandatory
	DESCRIPTION "The value of sysUpTime at the time the interface entered its current operational state."
	::= { w2kEHIfEntry 8 }

w2kEHIfInOctets OBJECT-TYPE
	SYNTAX Counter
	ACCESS read-only
	STATUS mandatory
	DESCRIPTION "The total number of octets received on the interface, including framing characters."
	::= { w2kEHIfEntry 9 }

w2kEHIfInUcastPkts OBJECT-TYPE
	SYNTAX Counter
	ACCESS read-only
	STATUS mandatory
	DESCRIPTION "The number of subnetwork-unicast packets delivered to a higher-layer protocol."
	::= { w2kEHIfEntry 10 }

w2kEHIfInNUcastPkts OBJECT-TYPE
	SYNTAX Counter
	ACCESS read-only
	STATUS mandatory
	DESCRIPTION "The number of non-unicast (i.e., subnetwork-broadcast or subnetwork-multicast) packets delivered to a higher-layer protocol."
	::= { w2kEHIfEntry 11 }

w2kEHIfInDiscards OBJECT-TYPE
	SYNTAX Counter
	ACCESS read-only
	STATUS mandatory
	DESCRIPTION "The number of inbound packets which were chosen to be discarded even though no errors had been detected to prevent their being deliverable to a higher-layer protocol."
	::= { w2kEHIfEntry 12 }

w2kEHIfInErrors OBJECT-TYPE
	SYNTAX Counter
	ACCESS read-only
	STATUS mandatory
	DESCRIPTION "The number of inbound packets that contained errors preventing them from being deliverable to a higher-layer protocol."
	::= { w2kEHIfEntry 13 }

w2kEHIfInUnknownProtos OBJECT-TYPE
	SYNTAX Counter
	ACCESS read-only
	STATUS mandatory
	DESCRIPTION "The number of packets received via the interface which were discarded because of an unknown or unsupported protocol."
	::= { w2kEHIfEntry 14 }

w2kEHIfOutOctets OBJECT-TYPE
	SYNTAX Counter
	ACCESS read-only
	STATUS mandatory
	DESCRIPTION "The total number of octets transmitted out of the interface, including framing characters."
	::= { w2kEHIfEntry 15 }

w2kEHIfOutUcastPkts OBJECT-TYPE
	SYNTAX Counter
	ACCESS read-only
	STATUS mandatory
	DESCRIPTION "The total number of packets that higher-level protocols requested be transmitted to a subnetwork-unicast address, including those that were discarded or not sent."
	::= { w2kEHIfEntry 16 }

w2kEHIfOutNUcastPkts OBJECT-TYPE
	SYNTAX Counter
	ACCESS read-only
	STATUS mandatory
	DESCRIPTION "The total number of packets that higher-level protocols requested be transmitted to a non-unicast (i.e., a subnetwork-broadcast or subnetwork-multicast) address, including those that were discarded or not sent."
	::= { w2kEHIfEntry 17 }

w2kEHIfOutDiscards OBJECT-TYPE
	SYNTAX Counter
	ACCESS read-only
	STATUS mandatory
	DESCRIPTION "The number of outbound packets which were chosen to be discarded even though no errors had been detected to prevent their being transmitted."
	::= { w2kEHIfEntry 18 }

w2kEHIfOutErrors OBJECT-TYPE
	SYNTAX Counter
	ACCESS read-only
	STATUS mandatory
	DESCRIPTION "The number of outbound packets that could not be transmitted because of errors."
	::= { w2kEHIfEntry 19 }

w2kEHIfIpAdEntAddr OBJECT-TYPE
	SYNTAX IpAddress
	ACCESS read-only
	STATUS mandatory
	DESCRIPTION "The IP address."
	::= { w2kEHIfEntry 20 }


--  ---------------------------------
--  Process table
--  ---------------------------------
w2kEHProcTable OBJECT-TYPE
	SYNTAX SEQUENCE OF W2kEHProcEntry
	ACCESS not-accessible
	STATUS mandatory
	DESCRIPTION ""
	::= { w2kEHGroup 8 }

w2kEHProcEntry OBJECT-TYPE
	SYNTAX W2kEHProcEntry
	ACCESS not-accessible
	STATUS mandatory
	DESCRIPTION ""
	INDEX { w2kEHProcName }
	::= { w2kEHProcTable 1 }

W2kEHProcEntry ::= SEQUENCE {
	w2kEHProcName DisplayString,
	w2kEHProcNumber INTEGER,
	w2kEHProcPid DisplayString,
	w2kEHProcState INTEGER,
	w2kEHProcSize Gauge,
	w2kEHProcRSS Gauge,
	w2kEHProcTime INTEGER,
	w2kEHProcNumThreads INTEGER,
	w2kEHProcMajorPgFlts Counter
}

w2kEHProcName OBJECT-TYPE
	SYNTAX DisplayString
	ACCESS read-only
	STATUS mandatory
	DESCRIPTION "The unique index (process name) of this table entry. This name is case-sensitive."
	::= { w2kEHProcEntry 1 }

w2kEHProcNumber OBJECT-TYPE
	SYNTAX INTEGER
	ACCESS read-only
	STATUS mandatory
	DESCRIPTION "The number of processes with this name."
	::= { w2kEHProcEntry 2 }

w2kEHProcPid OBJECT-TYPE
	SYNTAX DisplayString
	ACCESS read-only
	STATUS mandatory
	DESCRIPTION "The process identifier (PID). If w2kEHProcNumber is greater one, this attribute lists all PIDs, delimited by a pipe sign."
	::= { w2kEHProcEntry 3 }

w2kEHProcState OBJECT-TYPE
	SYNTAX INTEGER {
		starting(1),
		runnable(2),
		active(3),
		wait(4),
		sleeping(5),
		swapped(6),
		sleep(7),
		stop(8),
		other(9),
		zombie(10)
	}
	ACCESS read-only
	STATUS deprecated
	DESCRIPTION "The process state. Possible states on Windows are: starting(1), runnable(2), active(3), sleeping(5), other(9) and zombie(10). If w2kEHProcNumber is greater one, this attribute is set to other(9)."
	::= { w2kEHProcEntry 4 }

w2kEHProcSize OBJECT-TYPE
	SYNTAX Gauge
	ACCESS read-only
	STATUS mandatory
	DESCRIPTION "The combined size of the text, data and stack segments in KBytes. If w2kEHProcNumber is greater one, this attribute is the accumulated value."
::= { w2kEHProcEntry 5 }

w2kEHProcRSS OBJECT-TYPE
	SYNTAX Gauge
	ACCESS read-only
	STATUS mandatory
	DESCRIPTION "Real memory (resident set) size of the process in KBytes. If w2kEHProcNumber is greater one, this attribute is the accumulated value."
::= { w2kEHProcEntry 6 }

w2kEHProcTime OBJECT-TYPE
	SYNTAX INTEGER
	ACCESS read-only
	STATUS mandatory
	DESCRIPTION "This process' accumulated CPU time in seconds. If w2kEHProcNumber is greater one, this attribute is the accumulated value."
::= { w2kEHProcEntry 7 }

w2kEHProcNumThreads OBJECT-TYPE
	SYNTAX INTEGER
	ACCESS read-only
	STATUS mandatory
	DESCRIPTION "The number of threads executing within this process. If w2kEHProcNumber is greater one, this attribute is the accumulated value."
	::= { w2kEHProcEntry 8 }

w2kEHProcMajorPgFlts OBJECT-TYPE
	SYNTAX Counter
	ACCESS read-only
	STATUS mandatory
	DESCRIPTION "The number of major page faults incurred by this process. Major faults require I/O to retrieve the page. If w2kEHProcNumber is greater one, this attribute is the accumulated value."
::= { w2kEHProcEntry 9 }


END
