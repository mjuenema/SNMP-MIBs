--
-- $Copyright: 
-- Copyright (C) Fujitsu Siemens Computers GmbH 2005 
-- FSC confidential 
-- All rights reserved 
-- $
--

FSC-RTP-MIB DEFINITIONS ::= BEGIN 

-- **************************************************************************
IMPORTS
    MODULE-IDENTITY, OBJECT-TYPE, OBJECT-IDENTITY, Integer32, enterprises                   
       FROM SNMPv2-SMI
    TEXTUAL-CONVENTION 
       FROM SNMPv2-TC; 
-- **************************************************************************

--
-- Resilient Telco Platform-related MOs
--
    rtp MODULE-IDENTITY
	LAST-UPDATED "200806111500Z"
	ORGANIZATION "Fujitsu Siemens Computers GmbH - EP SW RT 1"
	CONTACT-INFO "Resilient Telco Platform Team
		          Georg Blank
	              Postal: Fujitsu Siemens Computers GmbH
		          EP SW RT1
		          Otto-Hahn-Ring 6
		          D-81739 Munich
		          Tel: +49 89 636 44504
		          Fax: +49 89 636 48976
	              E-mail: Georg.Blank@fujitsu-siemens.com"

	DESCRIPTION
	    "The MIB module describes the top level of the Managed Objects of
	     the Resilient Telco Platform (RTP)

	    $Header: c:\cvsroot/mib_base/siemens/HiPath8000_Mibs_2008/RtpAdm.mib,v 1.1 2008/11/13 21:06:27 qiaxi01 Exp $ "   
	
	REVISION "200806111500Z"
        DESCRIPTION  
            "Updated the MIB to be fully compatible with SNMPv2"   
        
        REVISION "200504211800Z"
	DESCRIPTION
	    "Changed module name to FSC-RTP-MIB to resolve naming conflict
	     with RFC 2959.
	     Module header information updated."
    
        REVISION "200001041800Z"
	DESCRIPTION
	    "Module header information updated."
			
	REVISION "9908061800Z"
	DESCRIPTION
	    "Names of Siemens sub-OIDs changed from admin to iandcAdmin,
	     from products to iandcProducts.
	     OIDs under rtpConfigurationMgmt, rtpFaultMgmt and rtpSystemMgmt 
	     moved into separate MIB modules."

	REVISION "9907221800Z"
	DESCRIPTION
	    "The initial draft version of this MIB module."

	::= { iandcAdmin 1 }
	
--
-- Siemens-specific branch
--

    siemens OBJECT-IDENTITY
	STATUS current
	DESCRIPTION
	    "The authoritative identity of the enterprise Siemens AG."
	::= { enterprises 4329 }

    iandcProducts OBJECT-IDENTITY
	STATUS current
	DESCRIPTION
	    "References to I&C product names in the admin branch."
	::= { siemens 1 }

	reliantTelcoPlatform OBJECT-IDENTITY
	    STATUS  current
	    DESCRIPTION
		"The product entry for the Resilient Telco Platform (named
		 Reliant Telco Platform earlier)."
	    ::= { iandcProducts 2 }

    iandcAdmin OBJECT-IDENTITY
	STATUS current
	DESCRIPTION
	    "The I&C product-specific MIBs."
	::= { siemens 2 }



--
-- Textual conventions used in the RTP MIB:
--

    Boolean ::= TEXTUAL-CONVENTION
	STATUS      current
	DESCRIPTION "Represents a boolean value in the Siemens MIB."
	SYNTAX      INTEGER { false(0), true(1) }


    TimeIntervalMillis ::= TEXTUAL-CONVENTION
	STATUS       current
	DESCRIPTION
		"A period of time, measured in units of milliseconds."
	SYNTAX       Integer32 (0..2147483647)


    TimeStampSeconds ::= TEXTUAL-CONVENTION
	STATUS       current
	DESCRIPTION
		"A timestamp in seconds since 01.Jan.1970, 00:00:00h UTC."
	SYNTAX       Integer32 (0..2147483647)


--
-- The RTP MIB
--

    rtpConfigurationMgmt OBJECT-IDENTITY
	STATUS current
	DESCRIPTION
	    "The RTP Configuration Management MOs."
	::= { rtp 1 }

    rtpFaultMgmt OBJECT-IDENTITY
	STATUS current
	DESCRIPTION
	    "The RTP Fault Management MOs."
	::= { rtp 2 }

    rtpPerformanceMgmt OBJECT-IDENTITY
	STATUS current
	DESCRIPTION
	    "The RTP Performance Management MOs."
	::= { rtp 3 }

    rtpSecurityMgmt OBJECT-IDENTITY
	STATUS current
	DESCRIPTION
	    "The RTP Security Management MOs."
	::= { rtp 4 }

    rtpSystemMgmt OBJECT-IDENTITY
	STATUS current
	DESCRIPTION
	    "The RTP System Management MOs."
	::= { rtp 5 }

    rtpApplicationLevelMgmt OBJECT-IDENTITY
	STATUS current
	DESCRIPTION
	    "The RTP Application-Level Management MOs (not part of the RTP)."
	::= { rtp 6 }

    rtpProductEntry OBJECT-TYPE
	SYNTAX OBJECT IDENTIFIER
	MAX-ACCESS  read-only
	STATUS  current
	DESCRIPTION
	    "A reference to the product entry for the Resilient Telco Platform:
	     iso.org.dod.internet.private.enterprises.siemens.products.
							  reliantTelcoPlatform
	     (This is a requirement from the Siemens-internal MIB
	      administration.)"
	::= { rtp 7 }

END
