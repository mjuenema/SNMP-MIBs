-- file automatically created


TELDAT-TRAP-XN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


xnTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the XN event subsystem."
    REVISION "201401200930Z"
    DESCRIPTION "Initial implementation"
        ::= { telEventTraps 163 }


xnEventsGroup	OBJECT IDENTIFIER	::= { xnTrapsMIB 1 }

xnNotifications	OBJECT IDENTIFIER	::= { xnTrapsMIB 2 }
xnNotificationsPrefix	OBJECT IDENTIFIER	::= { xnNotifications 0 }

xnEventObjects1 OBJECT-IDENTITY
    STATUS current
    DESCRIPTION
        "Event XN.1
        This message is generated when a packet has an XNS packet length
        greater then the packets physical length."
    ::= { xnEventsGroup 1 }

xn1_protocol OBJECT-TYPE
    SYNTAX DisplayString
    MAX-ACCESS accessible-for-notify
    STATUS current
    DESCRIPTION
        "Parameter 'protocol' in event XN.1"
    ::= { xnEventObjects1 1 }

xn1_source_net OBJECT-TYPE
    SYNTAX Integer32
    MAX-ACCESS accessible-for-notify
    STATUS current
    DESCRIPTION
        "Parameter 'source_net' in event XN.1"
    ::= { xnEventObjects1 2 }

xn1_source_node OBJECT-TYPE
    SYNTAX DisplayString
    MAX-ACCESS accessible-for-notify
    STATUS current
    DESCRIPTION
        "Parameter 'source_node' in event XN.1"
    ::= { xnEventObjects1 3 }

xn1_length OBJECT-TYPE
    SYNTAX Integer32
    MAX-ACCESS accessible-for-notify
    STATUS current
    DESCRIPTION
        "Parameter 'length' in event XN.1"
    ::= { xnEventObjects1 4 }

xnEventObjects2 OBJECT-IDENTITY
    STATUS current
    DESCRIPTION
        "Event XN.2
        The reserved bits in the Transport Control field of the
        header were not zero. An Error (checksum) packet will be sent."
    ::= { xnEventsGroup 2 }

xn2_protocol OBJECT-TYPE
    SYNTAX DisplayString
    MAX-ACCESS accessible-for-notify
    STATUS current
    DESCRIPTION
        "Parameter 'protocol' in event XN.2"
    ::= { xnEventObjects2 1 }

xn2_source_net OBJECT-TYPE
    SYNTAX Integer32
    MAX-ACCESS accessible-for-notify
    STATUS current
    DESCRIPTION
        "Parameter 'source_net' in event XN.2"
    ::= { xnEventObjects2 2 }

xn2_source_node OBJECT-TYPE
    SYNTAX DisplayString
    MAX-ACCESS accessible-for-notify
    STATUS current
    DESCRIPTION
        "Parameter 'source_node' in event XN.2"
    ::= { xnEventObjects2 3 }

xn2_TC OBJECT-TYPE
    SYNTAX Integer32
    MAX-ACCESS accessible-for-notify
    STATUS current
    DESCRIPTION
        "Parameter 'TC' in event XN.2"
    ::= { xnEventObjects2 4 }

xnEventObjects3 OBJECT-IDENTITY
    STATUS current
    DESCRIPTION
        "Event XN.3
        This message is generated when the checksum in a packet being
        forwarded does not match the calculated checksum for the packet.
        An Error (checksum) packet will be sent."
    ::= { xnEventsGroup 3 }

xn3_protocol OBJECT-TYPE
    SYNTAX DisplayString
    MAX-ACCESS accessible-for-notify
    STATUS current
    DESCRIPTION
        "Parameter 'protocol' in event XN.3"
    ::= { xnEventObjects3 1 }

xn3_source_net OBJECT-TYPE
    SYNTAX Integer32
    MAX-ACCESS accessible-for-notify
    STATUS current
    DESCRIPTION
        "Parameter 'source_net' in event XN.3"
    ::= { xnEventObjects3 2 }

xn3_source_node OBJECT-TYPE
    SYNTAX DisplayString
    MAX-ACCESS accessible-for-notify
    STATUS current
    DESCRIPTION
        "Parameter 'source_node' in event XN.3"
    ::= { xnEventObjects3 3 }

xn3_cksum OBJECT-TYPE
    SYNTAX Integer32
    MAX-ACCESS accessible-for-notify
    STATUS current
    DESCRIPTION
        "Parameter 'cksum' in event XN.3"
    ::= { xnEventObjects3 4 }

xnEventObjects4 OBJECT-IDENTITY
    STATUS current
    DESCRIPTION
        "Event XN.4
        This message is generated when a packet's hop count counts up
        past 15 and overflows. An Error (hop count) packet will be sent."
    ::= { xnEventsGroup 4 }

xn4_protocol OBJECT-TYPE
    SYNTAX DisplayString
    MAX-ACCESS accessible-for-notify
    STATUS current
    DESCRIPTION
        "Parameter 'protocol' in event XN.4"
    ::= { xnEventObjects4 1 }

xn4_source_net OBJECT-TYPE
    SYNTAX Integer32
    MAX-ACCESS accessible-for-notify
    STATUS current
    DESCRIPTION
        "Parameter 'source_net' in event XN.4"
    ::= { xnEventObjects4 2 }

xn4_source_node OBJECT-TYPE
    SYNTAX DisplayString
    MAX-ACCESS accessible-for-notify
    STATUS current
    DESCRIPTION
        "Parameter 'source_node' in event XN.4"
    ::= { xnEventObjects4 3 }

xn4_destination_net OBJECT-TYPE
    SYNTAX Integer32
    MAX-ACCESS accessible-for-notify
    STATUS current
    DESCRIPTION
        "Parameter 'destination_net' in event XN.4"
    ::= { xnEventObjects4 4 }

xnEventObjects5 OBJECT-IDENTITY
    STATUS current
    DESCRIPTION
        "Event XN.5
        This message is generated when a packet cannot be forwarded
        because there is no gateway to the destination network.
        An Error (unreachable) packet will be sent."
    ::= { xnEventsGroup 5 }

xn5_protocol OBJECT-TYPE
    SYNTAX DisplayString
    MAX-ACCESS accessible-for-notify
    STATUS current
    DESCRIPTION
        "Parameter 'protocol' in event XN.5"
    ::= { xnEventObjects5 1 }

xn5_source_net OBJECT-TYPE
    SYNTAX Integer32
    MAX-ACCESS accessible-for-notify
    STATUS current
    DESCRIPTION
        "Parameter 'source_net' in event XN.5"
    ::= { xnEventObjects5 2 }

xn5_source_node OBJECT-TYPE
    SYNTAX DisplayString
    MAX-ACCESS accessible-for-notify
    STATUS current
    DESCRIPTION
        "Parameter 'source_node' in event XN.5"
    ::= { xnEventObjects5 3 }

xn5_destination_net OBJECT-TYPE
    SYNTAX Integer32
    MAX-ACCESS accessible-for-notify
    STATUS current
    DESCRIPTION
        "Parameter 'destination_net' in event XN.5"
    ::= { xnEventObjects5 4 }

xnEventObjects6 OBJECT-IDENTITY
    STATUS current
    DESCRIPTION
        "Event XN.6
        This packet is generated when a packet is being sent out
        the same network interface it arrived on. This router is
        not the best path off that network to the destination network."
    ::= { xnEventsGroup 6 }

xn6_protocol OBJECT-TYPE
    SYNTAX DisplayString
    MAX-ACCESS accessible-for-notify
    STATUS current
    DESCRIPTION
        "Parameter 'protocol' in event XN.6"
    ::= { xnEventObjects6 1 }

xn6_source_net OBJECT-TYPE
    SYNTAX Integer32
    MAX-ACCESS accessible-for-notify
    STATUS current
    DESCRIPTION
        "Parameter 'source_net' in event XN.6"
    ::= { xnEventObjects6 2 }

xn6_source_node OBJECT-TYPE
    SYNTAX DisplayString
    MAX-ACCESS accessible-for-notify
    STATUS current
    DESCRIPTION
        "Parameter 'source_node' in event XN.6"
    ::= { xnEventObjects6 3 }

xn6_destination_net OBJECT-TYPE
    SYNTAX Integer32
    MAX-ACCESS accessible-for-notify
    STATUS current
    DESCRIPTION
        "Parameter 'destination_net' in event XN.6"
    ::= { xnEventObjects6 4 }

xnEventObjects7 OBJECT-IDENTITY
    STATUS current
    DESCRIPTION
        "Event XN.7
        This message is generated when a packet is addressed to
        node 000000000000. This is an illegal host address.
        An Error (checksum) packet will be sent."
    ::= { xnEventsGroup 7 }

xn7_protocol OBJECT-TYPE
    SYNTAX DisplayString
    MAX-ACCESS accessible-for-notify
    STATUS current
    DESCRIPTION
        "Parameter 'protocol' in event XN.7"
    ::= { xnEventObjects7 1 }

xn7_source_net OBJECT-TYPE
    SYNTAX Integer32
    MAX-ACCESS accessible-for-notify
    STATUS current
    DESCRIPTION
        "Parameter 'source_net' in event XN.7"
    ::= { xnEventObjects7 2 }

xn7_source_node OBJECT-TYPE
    SYNTAX DisplayString
    MAX-ACCESS accessible-for-notify
    STATUS current
    DESCRIPTION
        "Parameter 'source_node' in event XN.7"
    ::= { xnEventObjects7 3 }

xn7_destination_net OBJECT-TYPE
    SYNTAX Integer32
    MAX-ACCESS accessible-for-notify
    STATUS current
    DESCRIPTION
        "Parameter 'destination_net' in event XN.7"
    ::= { xnEventObjects7 4 }

xnEventObjects8 OBJECT-IDENTITY
    STATUS current
    DESCRIPTION
        "Event XN.8
        This message is generated when a packet is forwarded."
    ::= { xnEventsGroup 8 }

xn8_protocol OBJECT-TYPE
    SYNTAX DisplayString
    MAX-ACCESS accessible-for-notify
    STATUS current
    DESCRIPTION
        "Parameter 'protocol' in event XN.8"
    ::= { xnEventObjects8 1 }

xn8_source_net OBJECT-TYPE
    SYNTAX Integer32
    MAX-ACCESS accessible-for-notify
    STATUS current
    DESCRIPTION
        "Parameter 'source_net' in event XN.8"
    ::= { xnEventObjects8 2 }

xn8_source_node OBJECT-TYPE
    SYNTAX DisplayString
    MAX-ACCESS accessible-for-notify
    STATUS current
    DESCRIPTION
        "Parameter 'source_node' in event XN.8"
    ::= { xnEventObjects8 3 }

xn8_dest_net OBJECT-TYPE
    SYNTAX Integer32
    MAX-ACCESS accessible-for-notify
    STATUS current
    DESCRIPTION
        "Parameter 'dest_net' in event XN.8"
    ::= { xnEventObjects8 4 }

xn8_dest_node OBJECT-TYPE
    SYNTAX DisplayString
    MAX-ACCESS accessible-for-notify
    STATUS current
    DESCRIPTION
        "Parameter 'dest_node' in event XN.8"
    ::= { xnEventObjects8 5 }

xnEventObjects9 OBJECT-IDENTITY
    STATUS current
    DESCRIPTION
        "Event XN.9
        The router cannot send out a forwarded packet to the required
        interface because it is too long. An Error (size) packet will be sent."
    ::= { xnEventsGroup 9 }

xn9_protocol OBJECT-TYPE
    SYNTAX DisplayString
    MAX-ACCESS accessible-for-notify
    STATUS current
    DESCRIPTION
        "Parameter 'protocol' in event XN.9"
    ::= { xnEventObjects9 1 }

xn9_pkt_size OBJECT-TYPE
    SYNTAX Integer32
    MAX-ACCESS accessible-for-notify
    STATUS current
    DESCRIPTION
        "Parameter 'pkt_size' in event XN.9"
    ::= { xnEventObjects9 2 }

xn9_max_size OBJECT-TYPE
    SYNTAX Integer32
    MAX-ACCESS accessible-for-notify
    STATUS current
    DESCRIPTION
        "Parameter 'max_size' in event XN.9"
    ::= { xnEventObjects9 3 }

xn9_interface OBJECT-TYPE
    SYNTAX DisplayString
    MAX-ACCESS accessible-for-notify
    STATUS current
    DESCRIPTION
        "Parameter 'interface' in event XN.9"
    ::= { xnEventObjects9 4 }

xn9_source_net OBJECT-TYPE
    SYNTAX Integer32
    MAX-ACCESS accessible-for-notify
    STATUS current
    DESCRIPTION
        "Parameter 'source_net' in event XN.9"
    ::= { xnEventObjects9 5 }

xn9_source_node OBJECT-TYPE
    SYNTAX DisplayString
    MAX-ACCESS accessible-for-notify
    STATUS current
    DESCRIPTION
        "Parameter 'source_node' in event XN.9"
    ::= { xnEventObjects9 6 }

xnEventObjects10 OBJECT-IDENTITY
    STATUS current
    DESCRIPTION
        "Event XN.10
        An outgoing packet was not successfully transmitted for the reason
        indicated by the error code."
    ::= { xnEventsGroup 10 }

xn10_protocol OBJECT-TYPE
    SYNTAX DisplayString
    MAX-ACCESS accessible-for-notify
    STATUS current
    DESCRIPTION
        "Parameter 'protocol' in event XN.10"
    ::= { xnEventObjects10 1 }

xn10_type OBJECT-TYPE
    SYNTAX Integer32
    MAX-ACCESS accessible-for-notify
    STATUS current
    DESCRIPTION
        "Parameter 'type' in event XN.10"
    ::= { xnEventObjects10 2 }

xn10_source_net OBJECT-TYPE
    SYNTAX Integer32
    MAX-ACCESS accessible-for-notify
    STATUS current
    DESCRIPTION
        "Parameter 'source_net' in event XN.10"
    ::= { xnEventObjects10 3 }

xn10_source_node OBJECT-TYPE
    SYNTAX DisplayString
    MAX-ACCESS accessible-for-notify
    STATUS current
    DESCRIPTION
        "Parameter 'source_node' in event XN.10"
    ::= { xnEventObjects10 4 }

xn10_dest_net OBJECT-TYPE
    SYNTAX Integer32
    MAX-ACCESS accessible-for-notify
    STATUS current
    DESCRIPTION
        "Parameter 'dest_net' in event XN.10"
    ::= { xnEventObjects10 5 }

xn10_dest_node OBJECT-TYPE
    SYNTAX DisplayString
    MAX-ACCESS accessible-for-notify
    STATUS current
    DESCRIPTION
        "Parameter 'dest_node' in event XN.10"
    ::= { xnEventObjects10 6 }

xn10_code OBJECT-TYPE
    SYNTAX Integer32
    MAX-ACCESS accessible-for-notify
    STATUS current
    DESCRIPTION
        "Parameter 'code' in event XN.10"
    ::= { xnEventObjects10 7 }

xnEventObjects11 OBJECT-IDENTITY
    STATUS current
    DESCRIPTION
        "Event XN.11
        The specified interface has come up, and has been enabled for
        the specified XNS protocol."
    ::= { xnEventsGroup 11 }

xn11_protocol OBJECT-TYPE
    SYNTAX DisplayString
    MAX-ACCESS accessible-for-notify
    STATUS current
    DESCRIPTION
        "Parameter 'protocol' in event XN.11"
    ::= { xnEventObjects11 1 }

xn11_network OBJECT-TYPE
    SYNTAX Integer32
    MAX-ACCESS accessible-for-notify
    STATUS current
    DESCRIPTION
        "Parameter 'network' in event XN.11"
    ::= { xnEventObjects11 2 }

xn11_node OBJECT-TYPE
    SYNTAX DisplayString
    MAX-ACCESS accessible-for-notify
    STATUS current
    DESCRIPTION
        "Parameter 'node' in event XN.11"
    ::= { xnEventObjects11 3 }

xn11_interface OBJECT-TYPE
    SYNTAX DisplayString
    MAX-ACCESS accessible-for-notify
    STATUS current
    DESCRIPTION
        "Parameter 'interface' in event XN.11"
    ::= { xnEventObjects11 4 }

xnEventObjects12 OBJECT-IDENTITY
    STATUS current
    DESCRIPTION
        "Event XN.12
        The specified route has been deleted because the first hop
        interface for that route has gone down."
    ::= { xnEventsGroup 12 }

xn12_protocol OBJECT-TYPE
    SYNTAX DisplayString
    MAX-ACCESS accessible-for-notify
    STATUS current
    DESCRIPTION
        "Parameter 'protocol' in event XN.12"
    ::= { xnEventObjects12 1 }

xn12_destination_net OBJECT-TYPE
    SYNTAX Integer32
    MAX-ACCESS accessible-for-notify
    STATUS current
    DESCRIPTION
        "Parameter 'destination_net' in event XN.12"
    ::= { xnEventObjects12 2 }

xn12_gateway OBJECT-TYPE
    SYNTAX DisplayString
    MAX-ACCESS accessible-for-notify
    STATUS current
    DESCRIPTION
        "Parameter 'gateway' in event XN.12"
    ::= { xnEventObjects12 3 }

xn12_interface OBJECT-TYPE
    SYNTAX DisplayString
    MAX-ACCESS accessible-for-notify
    STATUS current
    DESCRIPTION
        "Parameter 'interface' in event XN.12"
    ::= { xnEventObjects12 4 }

xnEventObjects13 OBJECT-IDENTITY
    STATUS current
    DESCRIPTION
        "Event XN.13
        This message is generated when a new entry cannot be made to
        routing table because it is already full."
    ::= { xnEventsGroup 13 }

xn13_protocol OBJECT-TYPE
    SYNTAX DisplayString
    MAX-ACCESS accessible-for-notify
    STATUS current
    DESCRIPTION
        "Parameter 'protocol' in event XN.13"
    ::= { xnEventObjects13 1 }

xn13_destination_net OBJECT-TYPE
    SYNTAX Integer32
    MAX-ACCESS accessible-for-notify
    STATUS current
    DESCRIPTION
        "Parameter 'destination_net' in event XN.13"
    ::= { xnEventObjects13 2 }

xnEventObjects14 OBJECT-IDENTITY
    STATUS current
    DESCRIPTION
        "Event XN.14
        A packet of the echo type has been received with the specified
        operation to the specified socket."
    ::= { xnEventsGroup 14 }

xn14_protocol OBJECT-TYPE
    SYNTAX DisplayString
    MAX-ACCESS accessible-for-notify
    STATUS current
    DESCRIPTION
        "Parameter 'protocol' in event XN.14"
    ::= { xnEventObjects14 1 }

xn14_operation OBJECT-TYPE
    SYNTAX Integer32
    MAX-ACCESS accessible-for-notify
    STATUS current
    DESCRIPTION
        "Parameter 'operation' in event XN.14"
    ::= { xnEventObjects14 2 }

xn14_socket OBJECT-TYPE
    SYNTAX Integer32
    MAX-ACCESS accessible-for-notify
    STATUS current
    DESCRIPTION
        "Parameter 'socket' in event XN.14"
    ::= { xnEventObjects14 3 }

xn14_source_net OBJECT-TYPE
    SYNTAX Integer32
    MAX-ACCESS accessible-for-notify
    STATUS current
    DESCRIPTION
        "Parameter 'source_net' in event XN.14"
    ::= { xnEventObjects14 4 }

xn14_source_node OBJECT-TYPE
    SYNTAX DisplayString
    MAX-ACCESS accessible-for-notify
    STATUS current
    DESCRIPTION
        "Parameter 'source_node' in event XN.14"
    ::= { xnEventObjects14 5 }

xnEventObjects15 OBJECT-IDENTITY
    STATUS current
    DESCRIPTION
        "Event XN.15
        A packet was being returned to the sender, but the sender
        node address was a multicast address or the illegal address
        000000000000. This can happen when sending an Echo reply,
        an Error packet, or replying to other queries. The packet
        will be discarded."
    ::= { xnEventsGroup 15 }

xn15_protocol OBJECT-TYPE
    SYNTAX DisplayString
    MAX-ACCESS accessible-for-notify
    STATUS current
    DESCRIPTION
        "Parameter 'protocol' in event XN.15"
    ::= { xnEventObjects15 1 }

xn15_source_net OBJECT-TYPE
    SYNTAX Integer32
    MAX-ACCESS accessible-for-notify
    STATUS current
    DESCRIPTION
        "Parameter 'source_net' in event XN.15"
    ::= { xnEventObjects15 2 }

xn15_source_node OBJECT-TYPE
    SYNTAX DisplayString
    MAX-ACCESS accessible-for-notify
    STATUS current
    DESCRIPTION
        "Parameter 'source_node' in event XN.15"
    ::= { xnEventObjects15 3 }

xn15_interface OBJECT-TYPE
    SYNTAX DisplayString
    MAX-ACCESS accessible-for-notify
    STATUS current
    DESCRIPTION
        "Parameter 'interface' in event XN.15"
    ::= { xnEventObjects15 4 }

xnEventObjects16 OBJECT-IDENTITY
    STATUS current
    DESCRIPTION
        "Event XN.16
        A packet was being returned to the sender, and the source network
        was zero, but the destination network was non-zero. This can
        happen when sending an Echo reply, an Error packet, or replying to
        other queries. The packet will be discarded."
    ::= { xnEventsGroup 16 }

xn16_protocol OBJECT-TYPE
    SYNTAX DisplayString
    MAX-ACCESS accessible-for-notify
    STATUS current
    DESCRIPTION
        "Parameter 'protocol' in event XN.16"
    ::= { xnEventObjects16 1 }

xn16_source_net OBJECT-TYPE
    SYNTAX Integer32
    MAX-ACCESS accessible-for-notify
    STATUS current
    DESCRIPTION
        "Parameter 'source_net' in event XN.16"
    ::= { xnEventObjects16 2 }

xn16_source_node OBJECT-TYPE
    SYNTAX DisplayString
    MAX-ACCESS accessible-for-notify
    STATUS current
    DESCRIPTION
        "Parameter 'source_node' in event XN.16"
    ::= { xnEventObjects16 3 }

xn16_dest_net OBJECT-TYPE
    SYNTAX Integer32
    MAX-ACCESS accessible-for-notify
    STATUS current
    DESCRIPTION
        "Parameter 'dest_net' in event XN.16"
    ::= { xnEventObjects16 4 }

xn16_dest_node OBJECT-TYPE
    SYNTAX DisplayString
    MAX-ACCESS accessible-for-notify
    STATUS current
    DESCRIPTION
        "Parameter 'dest_node' in event XN.16"
    ::= { xnEventObjects16 5 }

xnEventObjects17 OBJECT-IDENTITY
    STATUS current
    DESCRIPTION
        "Event XN.17
        This message is generated when no memory is available to copy the
        offending packet into an Error packet. An Error packet will not be sent."
    ::= { xnEventsGroup 17 }

xn17_protocol OBJECT-TYPE
    SYNTAX DisplayString
    MAX-ACCESS accessible-for-notify
    STATUS current
    DESCRIPTION
        "Parameter 'protocol' in event XN.17"
    ::= { xnEventObjects17 1 }

xnEventObjects18 OBJECT-IDENTITY
    STATUS current
    DESCRIPTION
        "Event XN.18
        This message is generated when a packet has a physical
        length shorter than the minimum 30 byte XNS, IPX, or DDS header length.
        The source_net and source_node may or may not be valid packet
        data, depending on how severe the truncation is."
    ::= { xnEventsGroup 18 }

xn18_protocol OBJECT-TYPE
    SYNTAX DisplayString
    MAX-ACCESS accessible-for-notify
    STATUS current
    DESCRIPTION
        "Parameter 'protocol' in event XN.18"
    ::= { xnEventObjects18 1 }

xn18_length OBJECT-TYPE
    SYNTAX Integer32
    MAX-ACCESS accessible-for-notify
    STATUS current
    DESCRIPTION
        "Parameter 'length' in event XN.18"
    ::= { xnEventObjects18 2 }

xn18_source_net OBJECT-TYPE
    SYNTAX Integer32
    MAX-ACCESS accessible-for-notify
    STATUS current
    DESCRIPTION
        "Parameter 'source_net' in event XN.18"
    ::= { xnEventObjects18 3 }

xn18_source_node OBJECT-TYPE
    SYNTAX DisplayString
    MAX-ACCESS accessible-for-notify
    STATUS current
    DESCRIPTION
        "Parameter 'source_node' in event XN.18"
    ::= { xnEventObjects18 4 }

xn18_interface OBJECT-TYPE
    SYNTAX DisplayString
    MAX-ACCESS accessible-for-notify
    STATUS current
    DESCRIPTION
        "Parameter 'interface' in event XN.18"
    ::= { xnEventObjects18 5 }

xnEventObjects19 OBJECT-IDENTITY
    STATUS current
    DESCRIPTION
        "Event XN.19
        This message is generated when an IPX packet is received with a source
        network number of 0. The router corrects this to be the network
        number of the interface the packet was received on."
    ::= { xnEventsGroup 19 }

xn19_protocol OBJECT-TYPE
    SYNTAX DisplayString
    MAX-ACCESS accessible-for-notify
    STATUS current
    DESCRIPTION
        "Parameter 'protocol' in event XN.19"
    ::= { xnEventObjects19 1 }

xn19_new_source_net OBJECT-TYPE
    SYNTAX Integer32
    MAX-ACCESS accessible-for-notify
    STATUS current
    DESCRIPTION
        "Parameter 'new_source_net' in event XN.19"
    ::= { xnEventObjects19 2 }

xn19_source_net OBJECT-TYPE
    SYNTAX Integer32
    MAX-ACCESS accessible-for-notify
    STATUS current
    DESCRIPTION
        "Parameter 'source_net' in event XN.19"
    ::= { xnEventObjects19 3 }

xn19_source_node OBJECT-TYPE
    SYNTAX DisplayString
    MAX-ACCESS accessible-for-notify
    STATUS current
    DESCRIPTION
        "Parameter 'source_node' in event XN.19"
    ::= { xnEventObjects19 4 }

xn19_dest_net OBJECT-TYPE
    SYNTAX Integer32
    MAX-ACCESS accessible-for-notify
    STATUS current
    DESCRIPTION
        "Parameter 'dest_net' in event XN.19"
    ::= { xnEventObjects19 5 }

xn19_dest_node OBJECT-TYPE
    SYNTAX DisplayString
    MAX-ACCESS accessible-for-notify
    STATUS current
    DESCRIPTION
        "Parameter 'dest_node' in event XN.19"
    ::= { xnEventObjects19 6 }

xnEventObjects20 OBJECT-IDENTITY
    STATUS current
    DESCRIPTION
        "Event XN.20
        This message is generated when an IPX packet is received with a source
        network number of 0, and the hop count (transport control) is non-zero.
        The source network number will not be corrected, since it is
        probably not the network it was received on. The dest_node
        will be unable to reply."
    ::= { xnEventsGroup 20 }

xn20_protocol OBJECT-TYPE
    SYNTAX DisplayString
    MAX-ACCESS accessible-for-notify
    STATUS current
    DESCRIPTION
        "Parameter 'protocol' in event XN.20"
    ::= { xnEventObjects20 1 }

xn20_hop_count OBJECT-TYPE
    SYNTAX Integer32
    MAX-ACCESS accessible-for-notify
    STATUS current
    DESCRIPTION
        "Parameter 'hop_count' in event XN.20"
    ::= { xnEventObjects20 2 }

xn20_source_net OBJECT-TYPE
    SYNTAX Integer32
    MAX-ACCESS accessible-for-notify
    STATUS current
    DESCRIPTION
        "Parameter 'source_net' in event XN.20"
    ::= { xnEventObjects20 3 }

xn20_source_node OBJECT-TYPE
    SYNTAX DisplayString
    MAX-ACCESS accessible-for-notify
    STATUS current
    DESCRIPTION
        "Parameter 'source_node' in event XN.20"
    ::= { xnEventObjects20 4 }

xn20_dest_net OBJECT-TYPE
    SYNTAX Integer32
    MAX-ACCESS accessible-for-notify
    STATUS current
    DESCRIPTION
        "Parameter 'dest_net' in event XN.20"
    ::= { xnEventObjects20 5 }

xn20_dest_node OBJECT-TYPE
    SYNTAX DisplayString
    MAX-ACCESS accessible-for-notify
    STATUS current
    DESCRIPTION
        "Parameter 'dest_node' in event XN.20"
    ::= { xnEventObjects20 6 }

xn20_interface OBJECT-TYPE
    SYNTAX DisplayString
    MAX-ACCESS accessible-for-notify
    STATUS current
    DESCRIPTION
        "Parameter 'interface' in event XN.20"
    ::= { xnEventObjects20 7 }

xnEventObjects21 OBJECT-IDENTITY
    STATUS current
    DESCRIPTION
        "Event XN.21
        This message is generated when a packet has a length field
        in the XNS, IPX or DDS network layer header that is shorter than
        the 30 byte minimum packet length."
    ::= { xnEventsGroup 21 }

xn21_protocol OBJECT-TYPE
    SYNTAX DisplayString
    MAX-ACCESS accessible-for-notify
    STATUS current
    DESCRIPTION
        "Parameter 'protocol' in event XN.21"
    ::= { xnEventObjects21 1 }

xn21_claimed_length OBJECT-TYPE
    SYNTAX Integer32
    MAX-ACCESS accessible-for-notify
    STATUS current
    DESCRIPTION
        "Parameter 'claimed_length' in event XN.21"
    ::= { xnEventObjects21 2 }

xn21_source_net OBJECT-TYPE
    SYNTAX Integer32
    MAX-ACCESS accessible-for-notify
    STATUS current
    DESCRIPTION
        "Parameter 'source_net' in event XN.21"
    ::= { xnEventObjects21 3 }

xn21_source_node OBJECT-TYPE
    SYNTAX DisplayString
    MAX-ACCESS accessible-for-notify
    STATUS current
    DESCRIPTION
        "Parameter 'source_node' in event XN.21"
    ::= { xnEventObjects21 4 }


xnNotification1 NOTIFICATION-TYPE
    OBJECTS { 
              xn1_protocol, 
              xn1_source_net,
              xn1_source_node,
              xn1_length,
              xn1_length 
            }
    STATUS current
    DESCRIPTION
        "Notification of Event XN.1

        Message: '$1 truncated packet from $2/$3; xns $4, physical $5'

        Parameters list:
              $1: xn1_protocol
              $2: xn1_source_net
              $3: xn1_source_node
              $4: xn1_length
              $5: xn1_length

        This message is generated when a packet has an XNS packet length
        greater then the packets physical length."
    ::= { xnNotificationsPrefix 1 }

xnNotification2 NOTIFICATION-TYPE
    OBJECTS { 
              xn2_protocol, 
              xn2_source_net,
              xn2_source_node,
              xn2_TC 
            }
    STATUS current
    DESCRIPTION
        "Notification of Event XN.2

        Message: '$1 non-zero transport control from $2/$3, $4'

        Parameters list:
              $1: xn2_protocol
              $2: xn2_source_net
              $3: xn2_source_node
              $4: xn2_TC

        The reserved bits in the Transport Control field of the
        header were not zero. An Error (checksum) packet will be sent."
    ::= { xnNotificationsPrefix 2 }

xnNotification3 NOTIFICATION-TYPE
    OBJECTS { 
              xn3_protocol, 
              xn3_source_net,
              xn3_source_node,
              xn3_cksum,
              xn3_cksum 
            }
    STATUS current
    DESCRIPTION
        "Notification of Event XN.3

        Message: '$1 bad routing checksum from $2/$3; received $4, compared $5'

        Parameters list:
              $1: xn3_protocol
              $2: xn3_source_net
              $3: xn3_source_node
              $4: xn3_cksum
              $5: xn3_cksum

        This message is generated when the checksum in a packet being
        forwarded does not match the calculated checksum for the packet.
        An Error (checksum) packet will be sent."
    ::= { xnNotificationsPrefix 3 }

xnNotification4 NOTIFICATION-TYPE
    OBJECTS { 
              xn4_protocol, 
              xn4_source_net,
              xn4_source_node,
              xn4_destination_net 
            }
    STATUS current
    DESCRIPTION
        "Notification of Event XN.4

        Message: '$1 hop count overflow from $2/$3 to $4'

        Parameters list:
              $1: xn4_protocol
              $2: xn4_source_net
              $3: xn4_source_node
              $4: xn4_destination_net

        This message is generated when a packet's hop count counts up
        past 15 and overflows. An Error (hop count) packet will be sent."
    ::= { xnNotificationsPrefix 4 }

xnNotification5 NOTIFICATION-TYPE
    OBJECTS { 
              xn5_protocol, 
              xn5_source_net,
              xn5_source_node,
              xn5_destination_net 
            }
    STATUS current
    DESCRIPTION
        "Notification of Event XN.5

        Message: '$1 no gateway from $2/$3 to $4'

        Parameters list:
              $1: xn5_protocol
              $2: xn5_source_net
              $3: xn5_source_node
              $4: xn5_destination_net

        This message is generated when a packet cannot be forwarded
        because there is no gateway to the destination network.
        An Error (unreachable) packet will be sent."
    ::= { xnNotificationsPrefix 5 }

xnNotification6 NOTIFICATION-TYPE
    OBJECTS { 
              xn6_protocol, 
              xn6_source_net,
              xn6_source_node,
              xn6_destination_net 
            }
    STATUS current
    DESCRIPTION
        "Notification of Event XN.6

        Message: '$1 wasted hop from $2/$3 to $4'

        Parameters list:
              $1: xn6_protocol
              $2: xn6_source_net
              $3: xn6_source_node
              $4: xn6_destination_net

        This packet is generated when a packet is being sent out
        the same network interface it arrived on. This router is
        not the best path off that network to the destination network."
    ::= { xnNotificationsPrefix 6 }

xnNotification7 NOTIFICATION-TYPE
    OBJECTS { 
              xn7_protocol, 
              xn7_source_net,
              xn7_source_node,
              xn7_destination_net 
            }
    STATUS current
    DESCRIPTION
        "Notification of Event XN.7

        Message: '$1 destination host 0 from $2/$3 to $4'

        Parameters list:
              $1: xn7_protocol
              $2: xn7_source_net
              $3: xn7_source_node
              $4: xn7_destination_net

        This message is generated when a packet is addressed to
        node 000000000000. This is an illegal host address.
        An Error (checksum) packet will be sent."
    ::= { xnNotificationsPrefix 7 }

xnNotification8 NOTIFICATION-TYPE
    OBJECTS { 
              xn8_protocol, 
              xn8_source_net,
              xn8_source_node,
              xn8_dest_net,
              xn8_dest_node 
            }
    STATUS current
    DESCRIPTION
        "Notification of Event XN.8

        Message: '$1 Packet received from $2/$3 for $4/$5'

        Parameters list:
              $1: xn8_protocol
              $2: xn8_source_net
              $3: xn8_source_node
              $4: xn8_dest_net
              $5: xn8_dest_node

        This message is generated when a packet is forwarded."
    ::= { xnNotificationsPrefix 8 }

xnNotification9 NOTIFICATION-TYPE
    OBJECTS { 
              xn9_protocol, 
              xn9_pkt_size,
              xn9_max_size,
              xn9_interface,
              xn9_source_net,
              xn9_source_node 
            }
    STATUS current
    DESCRIPTION
        "Notification of Event XN.9

        Message: '$1 packet too long to forward $2 > $3 interface $4 from $5/$6'

        Parameters list:
              $1: xn9_protocol
              $2: xn9_pkt_size
              $3: xn9_max_size
              $4: xn9_interface
              $5: xn9_source_net
              $6: xn9_source_node

        The router cannot send out a forwarded packet to the required
        interface because it is too long. An Error (size) packet will be sent."
    ::= { xnNotificationsPrefix 9 }

xnNotification10 NOTIFICATION-TYPE
    OBJECTS { 
              xn10_protocol, 
              xn10_type,
              xn10_source_net,
              xn10_source_node,
              xn10_dest_net,
              xn10_dest_node,
              xn10_code 
            }
    STATUS current
    DESCRIPTION
        "Notification of Event XN.10

        Message: '$1 $2 from $3/$4 for $5/$6 discarded for reason $7'

        Parameters list:
              $1: xn10_protocol
              $2: xn10_type
              $3: xn10_source_net
              $4: xn10_source_node
              $5: xn10_dest_net
              $6: xn10_dest_node
              $7: xn10_code

        An outgoing packet was not successfully transmitted for the reason
        indicated by the error code."
    ::= { xnNotificationsPrefix 10 }

xnNotification11 NOTIFICATION-TYPE
    OBJECTS { 
              xn11_protocol, 
              xn11_network,
              xn11_node,
              xn11_interface 
            }
    STATUS current
    DESCRIPTION
        "Notification of Event XN.11

        Message: '$1 interface $2/$3 interface $4 up'

        Parameters list:
              $1: xn11_protocol
              $2: xn11_network
              $3: xn11_node
              $4: xn11_interface

        The specified interface has come up, and has been enabled for
        the specified XNS protocol."
    ::= { xnNotificationsPrefix 11 }

xnNotification12 NOTIFICATION-TYPE
    OBJECTS { 
              xn12_protocol, 
              xn12_destination_net,
              xn12_gateway,
              xn12_interface 
            }
    STATUS current
    DESCRIPTION
        "Notification of Event XN.12

        Message: '$1 deleted net $2 route via $3 interface $4'

        Parameters list:
              $1: xn12_protocol
              $2: xn12_destination_net
              $3: xn12_gateway
              $4: xn12_interface

        The specified route has been deleted because the first hop
        interface for that route has gone down."
    ::= { xnNotificationsPrefix 12 }

xnNotification13 NOTIFICATION-TYPE
    OBJECTS { 
              xn13_protocol, 
              xn13_destination_net 
            }
    STATUS current
    DESCRIPTION
        "Notification of Event XN.13

        Message: '$1 Table overflow, destination $2'

        Parameters list:
              $1: xn13_protocol
              $2: xn13_destination_net

        This message is generated when a new entry cannot be made to
        routing table because it is already full."
    ::= { xnNotificationsPrefix 13 }

xnNotification14 NOTIFICATION-TYPE
    OBJECTS { 
              xn14_protocol, 
              xn14_operation,
              xn14_socket,
              xn14_source_net,
              xn14_source_node 
            }
    STATUS current
    DESCRIPTION
        "Notification of Event XN.14

        Message: '$1 Echo type $2 to socket $3 from $4/$5'

        Parameters list:
              $1: xn14_protocol
              $2: xn14_operation
              $3: xn14_socket
              $4: xn14_source_net
              $5: xn14_source_node

        A packet of the echo type has been received with the specified
        operation to the specified socket."
    ::= { xnNotificationsPrefix 14 }

xnNotification15 NOTIFICATION-TYPE
    OBJECTS { 
              xn15_protocol, 
              xn15_source_net,
              xn15_source_node,
              xn15_interface 
            }
    STATUS current
    DESCRIPTION
        "Notification of Event XN.15

        Message: '$1 bad source $2/$3 interface $4'

        Parameters list:
              $1: xn15_protocol
              $2: xn15_source_net
              $3: xn15_source_node
              $4: xn15_interface

        A packet was being returned to the sender, but the sender
        node address was a multicast address or the illegal address
        000000000000. This can happen when sending an Echo reply,
        an Error packet, or replying to other queries. The packet
        will be discarded."
    ::= { xnNotificationsPrefix 15 }

xnNotification16 NOTIFICATION-TYPE
    OBJECTS { 
              xn16_protocol, 
              xn16_source_net,
              xn16_source_node,
              xn16_dest_net,
              xn16_dest_node 
            }
    STATUS current
    DESCRIPTION
        "Notification of Event XN.16

        Message: '$1 bad source network 0 from $2/$3 for $4/$5'

        Parameters list:
              $1: xn16_protocol
              $2: xn16_source_net
              $3: xn16_source_node
              $4: xn16_dest_net
              $5: xn16_dest_node

        A packet was being returned to the sender, and the source network
        was zero, but the destination network was non-zero. This can
        happen when sending an Echo reply, an Error packet, or replying to
        other queries. The packet will be discarded."
    ::= { xnNotificationsPrefix 16 }

xnNotification17 NOTIFICATION-TYPE
    OBJECTS { 
              xn17_protocol 
            }
    STATUS current
    DESCRIPTION
        "Notification of Event XN.17

        Message: '$1 No memory for error packet'

        Parameters list:
              $1: xn17_protocol

        This message is generated when no memory is available to copy the
        offending packet into an Error packet. An Error packet will not be sent."
    ::= { xnNotificationsPrefix 17 }

xnNotification18 NOTIFICATION-TYPE
    OBJECTS { 
              xn18_protocol, 
              xn18_length,
              xn18_source_net,
              xn18_source_node,
              xn18_interface 
            }
    STATUS current
    DESCRIPTION
        "Notification of Event XN.18

        Message: '$1 short ($2) packet from $3/$4 (?) interface $5'

        Parameters list:
              $1: xn18_protocol
              $2: xn18_length
              $3: xn18_source_net
              $4: xn18_source_node
              $5: xn18_interface

        This message is generated when a packet has a physical
        length shorter than the minimum 30 byte XNS, IPX, or DDS header length.
        The source_net and source_node may or may not be valid packet
        data, depending on how severe the truncation is."
    ::= { xnNotificationsPrefix 18 }

xnNotification19 NOTIFICATION-TYPE
    OBJECTS { 
              xn19_protocol, 
              xn19_new_source_net,
              xn19_source_net,
              xn19_source_node,
              xn19_dest_net,
              xn19_dest_node 
            }
    STATUS current
    DESCRIPTION
        "Notification of Event XN.19

        Message: '$1 changing source network to $2 on packet received from $3/$4 for $5/$6'

        Parameters list:
              $1: xn19_protocol
              $2: xn19_new_source_net
              $3: xn19_source_net
              $4: xn19_source_node
              $5: xn19_dest_net
              $6: xn19_dest_node

        This message is generated when an IPX packet is received with a source
        network number of 0. The router corrects this to be the network
        number of the interface the packet was received on."
    ::= { xnNotificationsPrefix 19 }

xnNotification20 NOTIFICATION-TYPE
    OBJECTS { 
              xn20_protocol, 
              xn20_hop_count,
              xn20_source_net,
              xn20_source_node,
              xn20_dest_net,
              xn20_dest_node,
              xn20_interface 
            }
    STATUS current
    DESCRIPTION
        "Notification of Event XN.20

        Message: '$1 bad source network 0 with hop count $2 on packet received from $3/$4 for $5/$6 via interface $7'

        Parameters list:
              $1: xn20_protocol
              $2: xn20_hop_count
              $3: xn20_source_net
              $4: xn20_source_node
              $5: xn20_dest_net
              $6: xn20_dest_node
              $7: xn20_interface

        This message is generated when an IPX packet is received with a source
        network number of 0, and the hop count (transport control) is non-zero.
        The source network number will not be corrected, since it is
        probably not the network it was received on. The dest_node
        will be unable to reply."
    ::= { xnNotificationsPrefix 20 }

xnNotification21 NOTIFICATION-TYPE
    OBJECTS { 
              xn21_protocol, 
              xn21_claimed_length,
              xn21_source_net,
              xn21_source_node 
            }
    STATUS current
    DESCRIPTION
        "Notification of Event XN.21

        Message: '$1 invalid length ($2 bytes) from $3/$4'

        Parameters list:
              $1: xn21_protocol
              $2: xn21_claimed_length
              $3: xn21_source_net
              $4: xn21_source_node

        This message is generated when a packet has a length field
        in the XNS, IPX or DDS network layer header that is shorter than
        the 30 byte minimum packet length."
    ::= { xnNotificationsPrefix 21 }


END
