--MibName=iis5Agent
--
--******************************************************************************
--*  WSA 5 Agent MIB prototype for Apache and IIS                              *
--*  edit iis5 to "ap5" prefix                                                   *
--*  edit Iis5 to "Ap5" prefix                                                   *
--*  edit IIS5 to "AP5" prefix                                                   *
--*  edit 77 to OID                                                   	       *
--******************************************************************************

IIS5AGENT-MIB DEFINITIONS ::= BEGIN

IMPORTS
	enterprises   FROM RFC1155-SMI
	OBJECT-TYPE   FROM RFC1155-SMI
	DisplayString FROM RFC1158-MIB;
        
-- Base OID  1.3.6.1.4.1.791.2.10.2.77

    cai         OBJECT IDENTIFIER ::= { enterprises 791 }

    caiSysMgr   OBJECT IDENTIFIER ::= { cai 2 }

    tng         OBJECT IDENTIFIER ::= { caiSysMgr 10 }

    unix-nt      OBJECT IDENTIFIER ::= { tng 2 }
                      
    iis5Agent   OBJECT IDENTIFIER ::= { unix-nt 77 }

    iis5ServerGroup           OBJECT IDENTIFIER   ::=  {  iis5Agent 1   }
    iis5ServiceGroup          OBJECT IDENTIFIER   ::=  {  iis5Agent 2   }
    iis5BadLinkGroup          OBJECT IDENTIFIER   ::=  {  iis5Agent 3   }
    iis5TopURLGroup           OBJECT IDENTIFIER   ::=  {  iis5Agent 4   }
    iis5URLAvailCounterGroup  OBJECT IDENTIFIER   ::=  {  iis5Agent 5   }
    iis5URLMntrGroup          OBJECT IDENTIFIER   ::=  {  iis5Agent 6   }
    iis5DiskGroup             OBJECT IDENTIFIER   ::=  {  iis5Agent 7   }
    iis5AvailCounterGroup     OBJECT IDENTIFIER   ::=  {  iis5Agent 8   }
    iis5PolledCounterGroup    OBJECT IDENTIFIER   ::=  {  iis5Agent 9   }
    iis5EventGroup            OBJECT IDENTIFIER   ::=  {  iis5Agent 10  }
    iis5AgentGroup            OBJECT IDENTIFIER   ::=  {  iis5Agent 11  }
    iis5WCGroup               OBJECT IDENTIFIER   ::=  {  iis5Agent 12  }
    iis5SHGroup               OBJECT IDENTIFIER   ::=  {  iis5Agent 13  }
    iis5LocalActionGroup      OBJECT IDENTIFIER   ::=  {  iis5Agent 14  }
    iis5ServLogGroup          OBJECT IDENTIFIER   ::=  {  iis5Agent 15  }
    iis5ExpressionGroup       OBJECT IDENTIFIER   ::=  {  iis5Agent 16  }
    iis5DetailGroup    	    OBJECT IDENTIFIER   ::=  {  iis5Agent 17  }
    iis5VHGroup    	    OBJECT IDENTIFIER   ::=  {  iis5Agent 18  }
    iis5IISAvailCounterGroup  OBJECT IDENTIFIER   ::=  {  iis5Agent 19  }
    iis5IISPolledCounterGroup OBJECT IDENTIFIER   ::=  {  iis5Agent 20  }

--******************************************************************************
--* ServerGroup - Site and summary information                               *
--******************************************************************************

        iis5ServerName OBJECT-TYPE
                SYNTAX  DisplayString
                ACCESS  read-only
                STATUS  mandatory
                DESCRIPTION
                "The host name of the computer."
                ::=  {  iis5ServerGroup 1   }

        iis5ServerSummaryStatus OBJECT-TYPE
                SYNTAX  INTEGER
                {
                    ok(1),
                    warning(2),
                    critical(3)
                }
                ACCESS  read-only
                STATUS  mandatory
                DESCRIPTION
                "The status of the monitored server."
                ::=  {  iis5ServerGroup 2   }

        iis5ServerPollingInterval OBJECT-TYPE
                SYNTAX  INTEGER
                ACCESS  read-write
                STATUS  mandatory
                DESCRIPTION
                "Poll interval for the server group in seconds."
                ::=  {  iis5ServerGroup 3   }

        iis5ServerResetCounts OBJECT-TYPE
                SYNTAX  INTEGER
                {
                    reset(1)
                }
                ACCESS  read-write
                STATUS  mandatory
                DESCRIPTION
                "Resets all history counts to zero when set."
                ::=  {  iis5ServerGroup 4   }

        iis5ServerResetTS OBJECT-TYPE
                SYNTAX  INTEGER
                ACCESS  read-only
                STATUS  mandatory
                DESCRIPTION
                "Time of last reset in ctime form."
                ::=  {  iis5ServerGroup 5   }

        iis5ServerResetTSEdit OBJECT-TYPE
                SYNTAX  DisplayString
                ACCESS  read-only
                STATUS  mandatory
                DESCRIPTION
                "Time of last reset in display form."
                ::=  {  iis5ServerGroup 6   }

        iis5ServerResetDays OBJECT-TYPE
                SYNTAX  INTEGER
                ACCESS  read-write
                STATUS  mandatory
                DESCRIPTION
                "Number of days between automatic history count resets."
                ::=  {  iis5ServerGroup 7   }

        iis5ServerVersion OBJECT-TYPE
                SYNTAX  DisplayString
                ACCESS  read-only
                STATUS  mandatory
                DESCRIPTION
                "The version of the web server."
                ::=  {  iis5ServerGroup 8   }

        iis5ServerPort OBJECT-TYPE
                SYNTAX  INTEGER
                ACCESS  read-only
                STATUS  mandatory
                DESCRIPTION
                "Port the server is listening on."
                ::=  {  iis5ServerGroup 9   }

        iis5ServerLBHost OBJECT-TYPE
                SYNTAX  DisplayString
                ACCESS  read-write
                STATUS  mandatory
                DESCRIPTION
                "Host name for Agent Collector."
                ::=  {  iis5ServerGroup 10   }

        iis5ServerLBPort OBJECT-TYPE
                SYNTAX  DisplayString
                ACCESS  read-write
                STATUS  mandatory
                DESCRIPTION
                "Agent Collector name."
                ::=  {  iis5ServerGroup 11   }

	iis5ServerLBEnaDis OBJECT-TYPE
		SYNTAX      INTEGER {enable(1), disable(2)}
		ACCESS      read-write
		STATUS      mandatory
		DESCRIPTION "Enable or disable the Agent Collector."
		::= {iis5ServerGroup 12}

        iis5SuperAgentRequest OBJECT-TYPE
                SYNTAX  DisplayString
                ACCESS  read-write
                STATUS  mandatory
                DESCRIPTION
                "Super Agent service request."
                ::=  {  iis5ServerGroup 13   }

        iis5ServerHiLevelVersion OBJECT-TYPE
                SYNTAX  DisplayString
                ACCESS  read-only
                STATUS  mandatory
                DESCRIPTION
                "Oracle server: The high level version number of the web server."
                ::=  {  iis5ServerGroup 14   }

        iis5ServerSetBaseLine OBJECT-TYPE
                SYNTAX  INTEGER {
                                set(1)
                               }
                ACCESS  write-only
                STATUS  mandatory
                DESCRIPTION
                "Immediately set Adaptive Configuration values."
                ::=  {  iis5ServerGroup 15   }

        iis5ServerBaseLineWarnWeight OBJECT-TYPE
                SYNTAX  INTEGER 
                ACCESS  read-write
                STATUS  mandatory
                DESCRIPTION
                "Adaptive Configuration warning weighing factor."
                ::=  {  iis5ServerGroup 16   }

        iis5ServerBaseLineCritWeight OBJECT-TYPE
                SYNTAX  INTEGER 
                ACCESS  read-write
                STATUS  mandatory
                DESCRIPTION
                "Adaptive Configuration critical weighing factor."
                ::=  {  iis5ServerGroup 17   }

	iis5ServerBaseLineEnaDis OBJECT-TYPE
		SYNTAX      INTEGER {disable(1), enable(2)}
		ACCESS      read-write
		STATUS      mandatory
		DESCRIPTION "Enable or disable Active Adaptive Configuration."
		::= {  iis5ServerGroup 18  }

	iis5ServerBaseLineTimer OBJECT-TYPE
		SYNTAX      INTEGER
		ACCESS      read-write
		STATUS      mandatory
		DESCRIPTION "Active Adaptive Configuration timer."
		::= {  iis5ServerGroup 19  }
                
        iis5ServerExportConfigSet OBJECT-TYPE
                SYNTAX  DisplayString
                ACCESS  read-write
                STATUS  mandatory
                DESCRIPTION
                "Name of config to export to."
                ::=  {  iis5ServerGroup 20   }
                
        iis5ServerImportConfigSet OBJECT-TYPE
                SYNTAX  DisplayString
                ACCESS  read-write
                STATUS  mandatory
                DESCRIPTION
                "Name of config to import from."
                ::=  {  iis5ServerGroup 21   }
               
        iis5retVHTableInterval OBJECT-TYPE
               SYNTAX  INTEGER
               ACCESS  read-write
               STATUS  mandatory
               DESCRIPTION
               "Seconds between polls for the VHTable."
               ::=  { iis5ServerGroup 22 }
               

	iis5retVHGPEnaDis OBJECT-TYPE
		SYNTAX      INTEGER {enable(1), disable(2)}
		ACCESS      read-write
		STATUS      mandatory
		DESCRIPTION "Enable or disable for the VHGroup."
		::= { iis5ServerGroup 23 }


--******************************************************************************
--* ServiceGroup - Services                                                  *
--******************************************************************************

        iis5ServiceTableEntries OBJECT-TYPE
                SYNTAX  INTEGER
                ACCESS  read-only
                STATUS  mandatory
                DESCRIPTION
                "The number of entries in the table."
                ::=  {  iis5ServiceGroup 1  }

        iis5ServiceSummaryStatus OBJECT-TYPE
                SYNTAX  INTEGER
                {
                    normal(1),
                    warning(2),
                    critical(3)
                }
                ACCESS  read-only
                STATUS  mandatory
                DESCRIPTION
                "Summary status of the service group."
                ::=  {  iis5ServiceGroup 2  }

        iis5ServicePollingInterval OBJECT-TYPE
                SYNTAX  INTEGER
                ACCESS  read-write
                STATUS  mandatory
                DESCRIPTION
                "Poll interval for the service group in seconds."
                ::=  {  iis5ServiceGroup 3  }

        -- Start, start service
        -- Stop, stop service, don't reset autorestart
        -- Recycle, stop and then restart service
        -- Stop no AutoRestart - stop and turn off autorestart
        iis5ServiceControl OBJECT-TYPE
                SYNTAX  INTEGER
                {
                    start(1),
                    stop(2),
                    recycle(3),
                    stop-noautorestart(4)
                }
                ACCESS  read-write
                STATUS  mandatory
                DESCRIPTION
                "Start and stop all services in the service table."
                ::=  {  iis5ServiceGroup 4  }

        iis5ServiceWarningCount OBJECT-TYPE
                SYNTAX  INTEGER
                ACCESS  read-only
                STATUS  mandatory
                DESCRIPTION
                "Number of services in warning state."
                ::=  {  iis5ServiceGroup 5  }

        iis5ServiceCriticalCount OBJECT-TYPE
                SYNTAX  INTEGER
                ACCESS  read-only
                STATUS  mandatory
                DESCRIPTION
                "Number of services in critical state."
                ::=  {  iis5ServiceGroup 6  }

        iis5NumberOfPolls OBJECT-TYPE
               SYNTAX  INTEGER
               ACCESS  read-only
               STATUS  mandatory
               DESCRIPTION
               "Number of times services have been polled"
               ::=  {  iis5ServiceGroup 7}

        iis5ServiceTable OBJECT-TYPE
                SYNTAX  SEQUENCE OF Iis5ServiceEntry
                ACCESS  not-accessible
                STATUS  mandatory
                DESCRIPTION
                "The list of all monitored services."
                ::=  {  iis5ServiceGroup 8}

	iis5ServiceGPEnaDis OBJECT-TYPE
		SYNTAX      INTEGER {enable(1), disable(2)}
		ACCESS      read-write
		STATUS      mandatory
		DESCRIPTION "Enable or disable for the Group."
		::= { iis5ServiceGroup 9 }
		
        iis5ServiceEntry OBJECT-TYPE
                 SYNTAX  Iis5ServiceEntry
                 ACCESS  not-accessible
                 STATUS  mandatory
                 DESCRIPTION
                 "The ServiceTable entry."
                 INDEX { iis5ServiceName }
                     ::=  { iis5ServiceTable 1 }

        Iis5ServiceEntry ::= SEQUENCE
        {
            iis5ServiceName           DisplayString,
            iis5ServiceState          INTEGER,
            iis5AutoRestart           INTEGER,
            iis5AutoReboot            INTEGER,
            iis5RestartAttempts       INTEGER,
            iis5RestartCount          INTEGER,
            iis5RebootAttempts        INTEGER,
            iis5RebootCount           INTEGER,
            iis5LocalAction           DisplayString,
            iis5TotalRestarts         INTEGER,
            iis5TotalReboots          INTEGER,
            iis5ServiceStateStatus    INTEGER,
            iis5ServiceWarnings       INTEGER,
            iis5ServiceCriticals      INTEGER,
            iis5StateIfStopped        INTEGER,
            iis5ServiceCtrl           INTEGER,
            iis5ServiceAvail          DisplayString,
            iis5ServiceRunningPolls   INTEGER,
	    iis5ServicePorts	      DisplayString,
            iis5ServiceType	      DisplayString,
	    iis5ServiceLagSetting     INTEGER,
	    iis5ServiceLagValue	      INTEGER,
            iis5ServiceInUse          INTEGER
        }

        iis5ServiceName OBJECT-TYPE
                SYNTAX  DisplayString
                ACCESS  read-only
                STATUS  mandatory
                DESCRIPTION
                "The name of the service."
                ::=  {  iis5ServiceEntry 1   }

        iis5ServiceState OBJECT-TYPE
                SYNTAX  INTEGER
                {
                    stopped(1),
                    started(2),
                    notinstalled(3),
                    actionpending(4)
                }
                ACCESS  read-only
                STATUS  mandatory
                DESCRIPTION
                "The state of the service."
                ::=  {  iis5ServiceEntry 2   }

        iis5AutoRestart OBJECT-TYPE
                SYNTAX  INTEGER
                {
                    yes(1),
                    no(2)
                }
                ACCESS  read-write
                STATUS  mandatory
                DESCRIPTION
                "Flag indicating whether to attempt to restart the service if it's down."
                ::=  {  iis5ServiceEntry 3   }

        iis5AutoReboot OBJECT-TYPE
                SYNTAX  INTEGER
                {
                    yes(1),
                    no(2)
                }
                ACCESS  read-write
                STATUS  mandatory
                DESCRIPTION
                "Flag indicating whether to attempt to reboot the host if service is down."
                ::=  {  iis5ServiceEntry 4   }

        iis5RestartAttempts OBJECT-TYPE
                SYNTAX  INTEGER
                ACCESS  read-write
                STATUS  mandatory
                DESCRIPTION
                "Reboot the host after this many restart attempts are unsuccessful."
                ::=  {  iis5ServiceEntry 5   }

        iis5RestartCount OBJECT-TYPE
                SYNTAX  INTEGER
                ACCESS  read-only
                STATUS  mandatory
                DESCRIPTION
                "Number of service restarts attempted since last successful service restart."
                ::=  {  iis5ServiceEntry 6   }

        iis5RebootAttempts OBJECT-TYPE
                SYNTAX  INTEGER
                ACCESS  read-write
                STATUS  mandatory
                DESCRIPTION
                "Execute local action after this many reboot attempts are unsuccessful."
                ::=  {  iis5ServiceEntry 7   }

        iis5RebootCount OBJECT-TYPE
                SYNTAX  INTEGER
                ACCESS  read-only
                STATUS  mandatory
                DESCRIPTION
                "Number of reboots attempted since last successful service restart."
                ::=  {  iis5ServiceEntry 8   }

        iis5LocalAction OBJECT-TYPE
                SYNTAX  DisplayString
                ACCESS  read-write
                STATUS  mandatory
                DESCRIPTION
                "Local action to perform when reboot attempts exceeded."
                ::=  {  iis5ServiceEntry 9   }

        iis5TotalRestarts OBJECT-TYPE
                SYNTAX  INTEGER
                ACCESS  read-only
                STATUS  mandatory
                DESCRIPTION
                "Total number of service restarts attempted."
                ::=  {  iis5ServiceEntry 10   }

        iis5TotalReboots OBJECT-TYPE
                SYNTAX  INTEGER
                ACCESS  read-only
                STATUS  mandatory
                DESCRIPTION
                "Total number of host reboots attempted."
                ::=  {  iis5ServiceEntry 11   }

        iis5ServiceStateStatus OBJECT-TYPE
                SYNTAX  INTEGER
                {
                    normal(1),
                    warning(2),
                    critical(3)
                }
                ACCESS  read-only
                STATUS  mandatory
                DESCRIPTION
                "Status of this service."
                ::=  {  iis5ServiceEntry 12   }

        iis5ServiceWarnings OBJECT-TYPE
                SYNTAX  INTEGER
                ACCESS  read-only
                STATUS  mandatory
                DESCRIPTION
                "Number of warnings generated by this service."
                ::=  {  iis5ServiceEntry 13   }

        iis5ServiceCriticals OBJECT-TYPE
                SYNTAX  INTEGER
                ACCESS  read-only
                STATUS  mandatory
                DESCRIPTION
                "Number of criticals generated by this service."
                ::=  {  iis5ServiceEntry 14   }

        iis5StateIfStopped OBJECT-TYPE
                SYNTAX  INTEGER
                {
                    normal(1),
                    warning(2),
                    critical(3)
                }
                ACCESS  read-write
                STATUS  mandatory
                DESCRIPTION
                "Service status reported if service is stopped."
                ::=  {  iis5ServiceEntry 15   }

        iis5ServiceCtrl OBJECT-TYPE
               SYNTAX  INTEGER {
                                start(1),
                                stop(2),
                                recycle(3),
                                stop-noautorestart(4)
                               }
               ACCESS  read-write
               STATUS  mandatory
               DESCRIPTION
               "Start and stop this service."
               ::=  {  iis5ServiceEntry 16   }

        iis5ServiceAvail OBJECT-TYPE
               SYNTAX  DisplayString
               ACCESS  read-only
               STATUS  mandatory
               DESCRIPTION
               "% of time service available (running) = running/number of polls"
               ::=  {  iis5ServiceEntry 17  }

        iis5ServiceRunningPolls OBJECT-TYPE
                SYNTAX  INTEGER
                ACCESS  read-only
                STATUS  mandatory
                DESCRIPTION
                "Number of polls showing service running(used for availability calc)."
                ::=  {  iis5ServiceEntry 18   }

        iis5ServicePorts OBJECT-TYPE
                SYNTAX  DisplayString
                ACCESS  read-write
                STATUS  mandatory
                DESCRIPTION
                "Additional PORTS to check for the service."
                ::=  {  iis5ServiceEntry 19   }

	 iis5ServiceType OBJECT-TYPE
	        SYNTAX      DisplayString
	        ACCESS      read-only
	        STATUS      mandatory
	        DESCRIPTION "Type of Service (Server, Admin, FTP)."
	        ::= { iis5ServiceEntry 20 }
		
        iis5ServiceLagSetting OBJECT-TYPE
                SYNTAX  INTEGER
                ACCESS  read-write
                STATUS  mandatory
                DESCRIPTION
                "Lag setting for the service."
                ::=  {  iis5ServiceEntry 21   }
		
        iis5ServiceLagValue OBJECT-TYPE
                SYNTAX  INTEGER
                ACCESS  read-only
                STATUS  mandatory
                DESCRIPTION
                "Current Lag value for the service."
                ::=  {  iis5ServiceEntry 22   }

        iis5ServiceInUse OBJECT-TYPE
                SYNTAX  INTEGER
                {
                    false(1),
                    true(2)
                }
                ACCESS  read-only
                STATUS  mandatory
                DESCRIPTION
                "InUse indicator."
                ::=  {  iis5ServiceEntry 23   }

--******************************************************************************
--* BadLinkGroup - URL links not found by requestors                            *
--******************************************************************************

        iis5BLTableEntries OBJECT-TYPE
                SYNTAX  INTEGER
                ACCESS  read-only
                STATUS  mandatory
                DESCRIPTION
                "The number of entries in the table."
                ::=  {  iis5BadLinkGroup 1   }


        iis5BLClearTable OBJECT-TYPE
               SYNTAX  INTEGER {
                                reset(1)
                               }
               ACCESS  read-write
               STATUS  mandatory
               DESCRIPTION
               "Clear the table when set."
               ::=  {  iis5BadLinkGroup 2   }

        iis5BLSummaryStatus OBJECT-TYPE
               SYNTAX  INTEGER {
                                normal(1),
                                warning(2),
                                critical(3)
                               }
               ACCESS  read-only
               STATUS  mandatory
               DESCRIPTION
               "Summary status for bad links."
               ::=  {  iis5BadLinkGroup 3   }

        iis5BLInterval OBJECT-TYPE
               SYNTAX  INTEGER
               ACCESS  read-write
               STATUS  mandatory
               DESCRIPTION
               "Seconds to poll for changes."
               ::=  {  iis5BadLinkGroup 4   }

        iis5BLCircularBuffSize OBJECT-TYPE
               SYNTAX  INTEGER
               ACCESS  read-write
               STATUS  mandatory
               DESCRIPTION
               "Max entries in the table (default 50)(Not a circular buffer)."
               ::=  {  iis5BadLinkGroup 5   }

        iis5BLWarningThreshold OBJECT-TYPE
               SYNTAX  INTEGER
               ACCESS  read-write
               STATUS  mandatory
               DESCRIPTION
               "Number of requests on a row before warning is generated."
               ::=  {  iis5BadLinkGroup 6   }

        iis5BLCriticalThreshold OBJECT-TYPE
               SYNTAX  INTEGER
               ACCESS  read-write
               STATUS  mandatory
               DESCRIPTION
               "Number of requests on a row before critical is generated."
               ::=  {  iis5BadLinkGroup 7   }

        iis5BLWarningCount OBJECT-TYPE
               SYNTAX  INTEGER
               ACCESS  read-only
               STATUS  mandatory
               DESCRIPTION
               "The number of entries in the table with a warning status."
               ::=  {  iis5BadLinkGroup 8   }

        iis5BLCriticalCount OBJECT-TYPE
               SYNTAX  INTEGER
               ACCESS  read-only
               STATUS  mandatory
               DESCRIPTION
               "The number of entries in the table with a critical status."
               ::=  {  iis5BadLinkGroup 9   }

        iis5BLWarningAction OBJECT-TYPE
               SYNTAX  DisplayString
               ACCESS  read-write
               STATUS  mandatory
               DESCRIPTION
               "Command to be executed when warning threshold is crossed on a row."
               ::=  {  iis5BadLinkGroup 10   }

        iis5BLCriticalAction OBJECT-TYPE
               SYNTAX  DisplayString
               ACCESS  read-write
               STATUS  mandatory
               DESCRIPTION
               "Command to be executed when critical threshold is crossed on a row."
               ::=  {  iis5BadLinkGroup 11   }


        iis5BLCreateReportURL OBJECT-TYPE
               SYNTAX  INTEGER {
                                Create(1)
                               }
               ACCESS  read-write
               STATUS  mandatory
               DESCRIPTION
               "When triggered, create report using path and file in BLReportURL."
               ::=  {  iis5BadLinkGroup 12   }

        iis5BLReportURL OBJECT-TYPE
               SYNTAX  DisplayString
               ACCESS  read-write
               STATUS  mandatory
               DESCRIPTION
               "Path and filename for report; Relative to DocumentRoot unless starts with '/'."
               ::=  {  iis5BadLinkGroup 13   }

        iis5BLTable OBJECT-TYPE
               SYNTAX  SEQUENCE OF Iis5BLEntry
               ACCESS  not-accessible
               STATUS  mandatory
               DESCRIPTION
               "This table contains a list bad links."
               ::=  {  iis5BadLinkGroup 14  }

	iis5BLGPEnaDis OBJECT-TYPE
		SYNTAX      INTEGER {enable(1), disable(2)}
		ACCESS      read-write
		STATUS      mandatory
		DESCRIPTION "Enable or disable for the Group."
		::= { iis5BadLinkGroup 15 }

        iis5BLEntry OBJECT-TYPE
               SYNTAX  Iis5BLEntry
               ACCESS  not-accessible
               STATUS  mandatory
               DESCRIPTION
               "This is an entry in the BLTable"
               INDEX { iis5BLURL, iis5BLReferringURL }
               ::=  { iis5BLTable 1 }

        Iis5BLEntry ::= SEQUENCE
        {
           iis5BLURL                              DisplayString,
           iis5BLReferringURL                     DisplayString,
           iis5BLFirstAccessTS                    DisplayString,
           iis5BLlastAccessTS                     DisplayString,
           iis5BLNumRequests                      INTEGER,
           iis5BLStatus                           INTEGER
        }

        iis5BLURL OBJECT-TYPE
               SYNTAX  DisplayString
               ACCESS  read-only
               STATUS  mandatory
               DESCRIPTION
               "Bad URL."
               ::=  {  iis5BLEntry 1   }

        iis5BLReferringURL OBJECT-TYPE
               SYNTAX  DisplayString
               ACCESS  read-only
               STATUS  mandatory
               DESCRIPTION
               "Referring URL to Bad URL."
               ::=  {  iis5BLEntry 2   }

        iis5BLFirstAccessTS OBJECT-TYPE
               SYNTAX  DisplayString
               ACCESS  read-only
               STATUS  mandatory
               DESCRIPTION
               "Time first bad access occurred (time row added to table)."
               ::=  {  iis5BLEntry 3   }

        iis5BLlastAccessTS OBJECT-TYPE
               SYNTAX  DisplayString
               ACCESS  read-only
               STATUS  mandatory
               DESCRIPTION
               "Time of last access to bad URL."
               ::=  {  iis5BLEntry 4   }

        iis5BLNumRequests OBJECT-TYPE
               SYNTAX  INTEGER
               ACCESS  read-only
               STATUS  mandatory
               DESCRIPTION
               "Count of requests."
               ::=  {  iis5BLEntry 5   }

        iis5BLStatus OBJECT-TYPE
               SYNTAX  INTEGER {
                                normal(1),
                                warning(2),
                                critical(3)
                               }
               ACCESS  read-only
               STATUS  mandatory
               DESCRIPTION
               "Summary status for BL."
               ::=  {  iis5BLEntry 6   }


--******************************************************************************
--* TopURLGroup - URLs with highest access rates                             *
--******************************************************************************

        iis5TopURLTableEntries OBJECT-TYPE
               SYNTAX  INTEGER
               ACCESS  read-only
               STATUS  mandatory
               DESCRIPTION
               "The number of entries in the table."
               ::=  {  iis5TopURLGroup 1   }

        iis5TopURLClearTable OBJECT-TYPE
               SYNTAX  INTEGER {
                                reset(1)
                               }
               ACCESS  read-write
               STATUS  mandatory
               DESCRIPTION
               "Clear the table when set."
               ::=  {  iis5TopURLGroup 2   }

        iis5TopURLInterval OBJECT-TYPE
               SYNTAX  INTEGER
               ACCESS  read-write
               STATUS  mandatory
               DESCRIPTION
               "Seconds to poll for changes."
               ::=  {  iis5TopURLGroup 3   }

        iis5TopURLCircularBuffSize OBJECT-TYPE
               SYNTAX  INTEGER
               ACCESS  read-write
               STATUS  mandatory
               DESCRIPTION
               "Max entries in the table (default 50)."
               ::=  {  iis5TopURLGroup 4   }


        iis5TopURLTable OBJECT-TYPE
               SYNTAX  SEQUENCE OF Iis5TopURLEntry
               ACCESS  not-accessible
               STATUS  mandatory
               DESCRIPTION
               "This table contains a list of the top URLs by hit count."
               ::=  {  iis5TopURLGroup 5 }

        iis5TopURLExclude OBJECT-TYPE
               SYNTAX  DisplayString
               ACCESS  read-write
               STATUS  mandatory
               DESCRIPTION
               "Exclude URLs with these extensions."
               ::=  {  iis5TopURLGroup 6   }

        iis5TopURLExcludeReset OBJECT-TYPE
               SYNTAX  INTEGER {
                                reset(1)
                               }
               ACCESS  read-write
               STATUS  mandatory
               DESCRIPTION
               "Reset exclude list to defaults."
               ::=  {  iis5TopURLGroup 7   }

	iis5TopURLGPEnaDis OBJECT-TYPE
		SYNTAX      INTEGER {enable(1), disable(2)}
		ACCESS      read-write
		STATUS      mandatory
		DESCRIPTION "Enable or disable for the Group."
		::= { iis5TopURLGroup 8 }

        iis5TopURLEntry OBJECT-TYPE
               SYNTAX  Iis5TopURLEntry
               ACCESS  not-accessible
               STATUS  mandatory
               DESCRIPTION
               "This is an entry in the TopURLTable"
               INDEX { iis5TopURLURL}
               ::=  { iis5TopURLTable 1 }

        Iis5TopURLEntry ::= SEQUENCE
        {
           iis5TopURLURL          DisplayString,
           iis5TopURLNumHits      INTEGER,
           iis5TopURLRank         INTEGER
        }

        iis5TopURLURL OBJECT-TYPE
               SYNTAX  DisplayString
               ACCESS  read-only
               STATUS  mandatory
               DESCRIPTION
               "URL."
               ::=  {  iis5TopURLEntry 1   }

        iis5TopURLNumHits OBJECT-TYPE
               SYNTAX  INTEGER
               ACCESS  read-only
               STATUS  mandatory
               DESCRIPTION
               "Number of hits."
               ::=  {  iis5TopURLEntry 2   }

        iis5TopURLRank OBJECT-TYPE
               SYNTAX  INTEGER
               ACCESS  read-only
               STATUS  mandatory
               DESCRIPTION
               "For easy sorting in Abrowser."
               ::=  {  iis5TopURLEntry 3   }


--******************************************************************************
--* URLAvailCounterGroup - Counters available for URL monitoring             *
--******************************************************************************

        iis5URLAvailCounterTableEntries OBJECT-TYPE
               SYNTAX  INTEGER
               ACCESS  read-only
               STATUS  mandatory
               DESCRIPTION
               "The number of entries in the table."
               ::=  {  iis5URLAvailCounterGroup 1   }

        iis5URLAvailCounterTable OBJECT-TYPE
           SYNTAX  SEQUENCE OF Iis5URLAvailCounterEntry
           ACCESS  not-accessible
           STATUS  mandatory
           DESCRIPTION
           "This table contains a list of all monitored AvailCounters"
           ::=  {  iis5URLAvailCounterGroup 2}

        iis5URLAvailCounterEntry OBJECT-TYPE
                                SYNTAX  Iis5URLAvailCounterEntry
                                ACCESS  not-accessible
                                STATUS  mandatory
                                DESCRIPTION
                                "This is an entry in the URLAvailCounterTable"
                                INDEX { iis5URLAvailCounterDescription }
                                        ::=  { iis5URLAvailCounterTable 1 }

        Iis5URLAvailCounterEntry ::= SEQUENCE {
                        iis5URLAvailCounterDescription    DisplayString
        }

        iis5URLAvailCounterDescription OBJECT-TYPE
               SYNTAX  DisplayString
               ACCESS  read-only
               STATUS  mandatory
               DESCRIPTION
               "The description of the AvailCounter"
               ::=  {  iis5URLAvailCounterEntry 1   }

--******************************************************************************
--* URLMntrGroup - Monitored URLs                                            *
--******************************************************************************

        iis5URLMntrTableEntries OBJECT-TYPE
               SYNTAX  INTEGER
               ACCESS  read-only
               STATUS  mandatory
               DESCRIPTION
               "The number of entries in the table."
               ::=  {  iis5URLMntrGroup 1   }

        iis5URLMntrInterval OBJECT-TYPE
               SYNTAX  INTEGER
               ACCESS  read-write
               STATUS  mandatory
               DESCRIPTION
               "Seconds between polls for the counter."
               ::=  {  iis5URLMntrGroup 2   }

        iis5URLMntrHitRate OBJECT-TYPE
               SYNTAX  INTEGER
               ACCESS  read-write
               STATUS  mandatory
               DESCRIPTION
               "Interval in seconds over which the counter is measured."
               ::=  {  iis5URLMntrGroup 3   }

--      Add a counter to the table.  The value must include at least the first four of
--      the 6 items listed, separated by commas.
--      <iis5URLAvailCounterDescription> is a value from iis5URLAvailCounterDescription in iis5URLAvailCounterTable.

        iis5URLMntrAdd OBJECT-TYPE
               SYNTAX  DisplayString
               ACCESS  write-only
               STATUS  mandatory
               DESCRIPTION
               "Add this entry to the table: <url>,<URLAvailCounterDescription>,<warning threshold>,<critical threshold>,<warning action>,<critical action>."
               ::=  {  iis5URLMntrGroup 4   }

--      Delete a counter from the table.  The value must include the 2 items listed.
        iis5URLMntrDelete OBJECT-TYPE
               SYNTAX  DisplayString
               ACCESS  write-only
               STATUS  mandatory
               DESCRIPTION
               "Delete entry from the table: <URLMntrDesc>,<url>."
               ::=  {  iis5URLMntrGroup 5   }

        iis5URLMntrUpdate OBJECT-TYPE
               SYNTAX  DisplayString
               ACCESS  write-only
               STATUS  mandatory
	       DESCRIPTION "Update this entry in the table."
               ::=  {  iis5URLMntrGroup 6   }

        iis5URLMntrSummaryStatus OBJECT-TYPE
               SYNTAX  INTEGER {
                                normal(1),
                                warning(2),
                                critical(3)
                               }
               ACCESS  read-only
               STATUS  mandatory
               DESCRIPTION
               "Most severe status of all rows in the table."
               ::=  {  iis5URLMntrGroup 7   }

        iis5URLMntrTable OBJECT-TYPE
               SYNTAX  SEQUENCE OF Iis5URLMntrEntry
               ACCESS  not-accessible
               STATUS  mandatory
               DESCRIPTION
               "This table contains a list of URLs to monitor."
               ::=  {  iis5URLMntrGroup 8}

        iis5URLMntrEntry OBJECT-TYPE
               SYNTAX  Iis5URLMntrEntry
               ACCESS  not-accessible
               STATUS  mandatory
               DESCRIPTION
               "This is an entry in the URLMntrTable"
               INDEX { iis5URLMntrURL, iis5URLMntrDesc}
               ::=  { iis5URLMntrTable 1 }

        Iis5URLMntrEntry ::= SEQUENCE
        {
           iis5URLMntrURL                 DisplayString,
           iis5URLMntrDesc                DisplayString,
           iis5URLMntrValue               DisplayString,
           iis5URLMntrWarningThreshold    INTEGER,
           iis5URLMntrCriticalThreshold   INTEGER,
           iis5URLMntrWarningAction       DisplayString,
           iis5URLMntrCriticalAction      DisplayString,
           iis5URLMntrStatus              INTEGER,
           iis5URLMntrEnableDisable       INTEGER,
           iis5URLMntrDescending          INTEGER,
           iis5URLMntrReset               INTEGER,
           iis5URLMntrResetTime           DisplayString,
	   iis5URLMntrValueReported	INTEGER,
           iis5URLMntrPrevStatus          INTEGER,
	   iis5URLMntrLagSetting		INTEGER,
	   iis5URLMntrLagValue		INTEGER
        }

        iis5URLMntrURL OBJECT-TYPE
               SYNTAX  DisplayString
               ACCESS  read-only
               STATUS  mandatory
               DESCRIPTION
               "URL to monitor."
               ::=  {  iis5URLMntrEntry 1   }

        iis5URLMntrDesc OBJECT-TYPE
               SYNTAX  DisplayString
               ACCESS  read-only
               STATUS  mandatory
               DESCRIPTION
               "Description of the monitored value."
               ::=  {  iis5URLMntrEntry 2   }

        iis5URLMntrValue OBJECT-TYPE
               SYNTAX  DisplayString
               ACCESS  read-only
               STATUS  mandatory
               DESCRIPTION
               "Peak number of hits per URLMntrHitRate seconds."
               ::=  {  iis5URLMntrEntry 3   }

        iis5URLMntrWarningThreshold OBJECT-TYPE
               SYNTAX  INTEGER
               ACCESS  read-write
               STATUS  mandatory
               DESCRIPTION
               "Warning threshold in MS"
               ::=  {  iis5URLMntrEntry 4   }

        iis5URLMntrCriticalThreshold OBJECT-TYPE
               SYNTAX  INTEGER
               ACCESS  read-write
               STATUS  mandatory
               DESCRIPTION
               "Critical threshold in MS"
               ::=  {  iis5URLMntrEntry 5   }

        iis5URLMntrWarningAction OBJECT-TYPE
               SYNTAX  DisplayString
               ACCESS  read-write
               STATUS  mandatory
               DESCRIPTION
               "Command to be executed when warning threshold is exceeded."
               ::=  {  iis5URLMntrEntry 6   }

        iis5URLMntrCriticalAction OBJECT-TYPE
               SYNTAX  DisplayString
               ACCESS  read-write
               STATUS  mandatory
               DESCRIPTION
               "Command to be executed when critical threshold is exceeded."
               ::=  {  iis5URLMntrEntry 7  }

        iis5URLMntrStatus OBJECT-TYPE
               SYNTAX  INTEGER {
                                normal(1),
                                warning(2),
                                critical(3)
                               }
               ACCESS  read-only
               STATUS  mandatory
               DESCRIPTION
               "Status of this URL."
               ::=  {  iis5URLMntrEntry 8 }

        iis5URLMntrEnableDisable OBJECT-TYPE
                SYNTAX  INTEGER
                {
                    enable(1),
                    disable(2)
                }
                ACCESS  read-write
                STATUS  mandatory
                DESCRIPTION
                "Enable or disable alerts for this URL."
                ::=  {  iis5URLMntrEntry 9   }

        iis5URLMntrDescending OBJECT-TYPE
               SYNTAX  INTEGER {
                                no(1),
                                yes(2)
                               }
               ACCESS  read-only
               STATUS  mandatory
               DESCRIPTION
               "Yes if lower value triggers thresholds."
               ::=  {  iis5URLMntrEntry 10 }

        iis5URLMntrReset OBJECT-TYPE
               SYNTAX  INTEGER {
                                reset(1)
                               }
               ACCESS  write-only
               STATUS  mandatory
               DESCRIPTION
               "Reset value for this counter."
               ::=  {  iis5URLMntrEntry 11 }

        iis5URLMntrResetTime OBJECT-TYPE
               SYNTAX  DisplayString
               ACCESS  read-only
               STATUS  mandatory
               DESCRIPTION
               "Time stamp of when this counter was reset."
               ::=  {  iis5URLMntrEntry 12  }
	       

        iis5URLMntrValueReported OBJECT-TYPE
               SYNTAX  INTEGER {
                                summary(1),
                                average(2),
				vhost(3)
                               }
               ACCESS  read-write
               STATUS  mandatory
               DESCRIPTION
               "The reported value of the counter is either a summary or average of all servers, or virtaul host."
               ::=  {  iis5URLMntrEntry 13 }

        iis5URLMntrPrevStatus OBJECT-TYPE
               SYNTAX  INTEGER {
                                normal(1),
                                warning(2),
                                critical(3)
                               }
               ACCESS  read-only
               STATUS  mandatory
               DESCRIPTION
               "Status of this URL."
               ::=  {  iis5URLMntrEntry 14 }
		
        iis5URLMntrLagSetting OBJECT-TYPE
                SYNTAX  INTEGER
                ACCESS  read-write
                STATUS  mandatory
                DESCRIPTION
                "Lag setting for the counter."
                ::=  {  iis5URLMntrEntry 15   }
		
        iis5URLMntrLagValue OBJECT-TYPE
                SYNTAX  INTEGER
                ACCESS  read-only
                STATUS  mandatory
                DESCRIPTION
                "Current Lag value for the counter."
                ::=  {  iis5URLMntrEntry 16   }


        iis5URLMntrDispTableEntries OBJECT-TYPE
               SYNTAX  INTEGER
               ACCESS  read-only
               STATUS  mandatory
               DESCRIPTION
               "The number of entries in the table."
               ::=  {  iis5URLMntrGroup 9   }

        iis5URLMntrDispTable OBJECT-TYPE
               SYNTAX  SEQUENCE OF Iis5URLMntrDispEntry
               ACCESS  not-accessible
               STATUS  mandatory
               DESCRIPTION
               "This table contains a list of URLs to monitor."
               ::=  {  iis5URLMntrGroup 10}

	iis5URLMntrGPEnaDis OBJECT-TYPE
		SYNTAX      INTEGER {enable(1), disable(2)}
		ACCESS      read-write
		STATUS      mandatory
		DESCRIPTION "Enable or disable for the Group."
		::= { iis5URLMntrGroup 11 }
               
        iis5URLMntrResetCmd OBJECT-TYPE
               SYNTAX  DisplayString
               ACCESS  write-only
               STATUS  mandatory
               DESCRIPTION
               "Reset entry from the table: <URLMntrDesc>,<url>."
               ::=  {  iis5URLMntrGroup 12 }

        iis5URLMntrDispEntry OBJECT-TYPE
               SYNTAX  Iis5URLMntrDispEntry
               ACCESS  not-accessible
               STATUS  mandatory
               DESCRIPTION
               "This is an entry in the URLMntrTable"
               INDEX { iis5URLMntrDispURL, iis5URLMntrDispDesc}
               ::=  { iis5URLMntrDispTable 1 }

        Iis5URLMntrDispEntry ::= SEQUENCE
        {
           iis5URLMntrDispURL                     DisplayString,
           iis5URLMntrDispDesc                    DisplayString,
           iis5URLMntrDispValue                   DisplayString,
           iis5URLMntrDispWarningThreshold        INTEGER,
           iis5URLMntrDispCriticalThreshold       INTEGER,
           iis5URLMntrDispWarningAction           DisplayString,
           iis5URLMntrDispCriticalAction          DisplayString,
           iis5URLMntrDispStatus                  INTEGER,
           iis5URLMntrDispEnableDisable           INTEGER,
           iis5URLMntrDispDescending              INTEGER,
           iis5URLMntrDispReset                   INTEGER,
           iis5URLMntrDispResetTime               DisplayString,
	   iis5URLMntrDispValueReported		INTEGER,
	   iis5URLMntrDispLagSetting		INTEGER,
	   iis5URLMntrDispLagValue		INTEGER
        }

        iis5URLMntrDispURL OBJECT-TYPE
               SYNTAX  DisplayString
               ACCESS  read-only
               STATUS  mandatory
               DESCRIPTION
               "URL to monitor."
               ::=  {  iis5URLMntrDispEntry 1   }

        iis5URLMntrDispDesc OBJECT-TYPE
               SYNTAX  DisplayString
               ACCESS  read-only
               STATUS  mandatory
               DESCRIPTION
               "Description of the monitored value."
               ::=  {  iis5URLMntrDispEntry 2   }

        iis5URLMntrDispValue OBJECT-TYPE
               SYNTAX  DisplayString
               ACCESS  read-only
               STATUS  mandatory
               DESCRIPTION
               "Peak number of hits per URLMntrDispHitRate seconds."
               ::=  {  iis5URLMntrDispEntry 3   }

        iis5URLMntrDispWarningThreshold OBJECT-TYPE
               SYNTAX  INTEGER
               ACCESS  read-write
               STATUS  mandatory
               DESCRIPTION
               "Warning threshold in MS"
               ::=  {  iis5URLMntrDispEntry 4   }

        iis5URLMntrDispCriticalThreshold OBJECT-TYPE
               SYNTAX  INTEGER
               ACCESS  read-write
               STATUS  mandatory
               DESCRIPTION
               "Critical threshold in MS"
               ::=  {  iis5URLMntrDispEntry 5   }

        iis5URLMntrDispWarningAction OBJECT-TYPE
               SYNTAX  DisplayString
               ACCESS  read-write
               STATUS  mandatory
               DESCRIPTION
               "Command to be executed when warning threshold is exceeded."
               ::=  {  iis5URLMntrDispEntry 6   }

        iis5URLMntrDispCriticalAction OBJECT-TYPE
               SYNTAX  DisplayString
               ACCESS  read-write
               STATUS  mandatory
               DESCRIPTION
               "Command to be executed when critical threshold is exceeded."
               ::=  {  iis5URLMntrDispEntry 7  }

        iis5URLMntrDispStatus OBJECT-TYPE
               SYNTAX  INTEGER {
                                normal(1),
                                warning(2),
                                critical(3)
                               }
               ACCESS  read-only
               STATUS  mandatory
               DESCRIPTION
               "Status of this URL."
               ::=  {  iis5URLMntrDispEntry 8 }

        iis5URLMntrDispEnableDisable OBJECT-TYPE
                SYNTAX  INTEGER
                {
                    enable(1),
                    disable(2)
                }
                ACCESS  read-write
                STATUS  mandatory
                DESCRIPTION
                "Enable or disable alerts for this URL."
                ::=  {  iis5URLMntrDispEntry 9   }

        iis5URLMntrDispDescending OBJECT-TYPE
               SYNTAX  INTEGER {
                                no(1),
                                yes(2)
                               }
               ACCESS  read-only
               STATUS  mandatory
               DESCRIPTION
               "Yes if lower value triggers thresholds."
               ::=  {  iis5URLMntrDispEntry 10 }

        iis5URLMntrDispReset OBJECT-TYPE
               SYNTAX  INTEGER {
                                reset(1)
                               }
               ACCESS  write-only
               STATUS  mandatory
               DESCRIPTION
               "Reset value for this counter."
               ::=  {  iis5URLMntrDispEntry 11 }

        iis5URLMntrDispResetTime OBJECT-TYPE
               SYNTAX  DisplayString
               ACCESS  read-only
               STATUS  mandatory
               DESCRIPTION
               "Time stamp of when this counter was reset."
               ::=  {  iis5URLMntrDispEntry 12  }
	       

        iis5URLMntrDispValueReported OBJECT-TYPE
               SYNTAX  INTEGER {
                                summary(1),
                                average(2),
				vhost(3)
                               }
               ACCESS  read-write
               STATUS  mandatory
               DESCRIPTION
               "The reported value of the counter is either a summary or average of all servers, or virtaul host."
               ::=  {  iis5URLMntrDispEntry 13 }
		
        iis5URLMntrDispLagSetting OBJECT-TYPE
                SYNTAX  INTEGER
                ACCESS  read-write
                STATUS  mandatory
                DESCRIPTION
                "Lag setting for the counter."
                ::=  {  iis5URLMntrDispEntry 14   }
		
        iis5URLMntrDispLagValue OBJECT-TYPE
                SYNTAX  INTEGER
                ACCESS  read-only
                STATUS  mandatory
                DESCRIPTION
                "Current Lag value for the counter."
                ::=  {  iis5URLMntrDispEntry 15   }


--******************************************************************************
--* DiskGroup - Primary disks used by the web server                         *
--******************************************************************************

        iis5DiskTableEntries OBJECT-TYPE
                SYNTAX  INTEGER
                ACCESS  read-only
                STATUS  mandatory
                DESCRIPTION
                "The number of entries in the table."
                ::=  {  iis5DiskGroup 1   }

        iis5DiskSummaryStatus OBJECT-TYPE
                SYNTAX  INTEGER
                {
                    ok(1),
                    warning(2),
                    critical(3)
                }
                ACCESS  read-only
                STATUS  mandatory
                DESCRIPTION
                "The summary status of all monitored disks."
                ::=  {  iis5DiskGroup 2   }

        iis5DiskPollingInterval OBJECT-TYPE
                SYNTAX  INTEGER
                ACCESS  read-write
                STATUS  mandatory
                DESCRIPTION
                "Poll interval for the disk group in seconds."
                ::=  {  iis5DiskGroup 3   }

        iis5DiskWarningCount OBJECT-TYPE
                SYNTAX  INTEGER
                ACCESS  read-only
                STATUS  mandatory
                DESCRIPTION
                "Number of disks in warning state."
                ::=  {  iis5DiskGroup 4   }

        iis5DiskCriticalCount OBJECT-TYPE
                SYNTAX  INTEGER
                ACCESS  read-only
                STATUS  mandatory
                DESCRIPTION
                "Number of disks in critical state."
                ::=  {  iis5DiskGroup 5  }

        iis5DiskTable OBJECT-TYPE
                SYNTAX  SEQUENCE OF Iis5DiskEntry
                ACCESS  not-accessible
                STATUS  mandatory
                DESCRIPTION
                "The list of all monitored disks."
                ::=  {  iis5DiskGroup 6 }

	iis5DiskGPEnaDis OBJECT-TYPE
		SYNTAX      INTEGER {enable(1), disable(2)}
		ACCESS      read-write
		STATUS      mandatory
		DESCRIPTION "Enable or disable for the Group."
		::= { iis5DiskGroup 7 }

        iis5DiskEntry OBJECT-TYPE
                SYNTAX  Iis5DiskEntry
                ACCESS  not-accessible
                STATUS  mandatory
                DESCRIPTION
                "The DiskTable entry."
                INDEX { iis5DiskID }
                    ::=  { iis5DiskTable 1 }

        Iis5DiskEntry ::= SEQUENCE
        {
            iis5DiskID                 	DisplayString,
            iis5DiskSize               	DisplayString,
            iis5DiskUsed              	DisplayString,
            iis5DiskFree               	DisplayString,
            iis5DiskWarningThreshold   	INTEGER,
            iis5DiskCriticalThreshold  	INTEGER,
            iis5DiskStatus             	INTEGER,
            iis5WarningCounts          	INTEGER,
            iis5CriticalCounts         	INTEGER,
            iis5DiskUsage              	DisplayString,
            iis5PrevWarningCounts      	INTEGER,
            iis5PrevCriticalCounts     	INTEGER,
	    iis5DiskLagSetting		INTEGER,
	    iis5DiskLagValue		INTEGER
        }

        iis5DiskID OBJECT-TYPE
                SYNTAX  DisplayString
                ACCESS  read-only
                STATUS  mandatory
                DESCRIPTION
                "The directory whose disk is measured."
                ::=  {  iis5DiskEntry 1   }

        iis5DiskSize OBJECT-TYPE
                SYNTAX  DisplayString
                ACCESS  read-only
                STATUS  mandatory
                DESCRIPTION
                "Size of the disk in Mbytes."
                ::=  {  iis5DiskEntry 2   }

        iis5DiskUsed OBJECT-TYPE
                SYNTAX  DisplayString
                ACCESS  read-only
                STATUS  mandatory
                DESCRIPTION
                "Space used on the disk in Mbytes"
                ::=  {  iis5DiskEntry 3   }

        iis5DiskFree OBJECT-TYPE
                SYNTAX  DisplayString
                ACCESS  read-only
                STATUS  mandatory
                DESCRIPTION
                "Free space on the disk in Mbytes"
                ::=  {  iis5DiskEntry 4   }

        iis5DiskWarningThreshold OBJECT-TYPE
                SYNTAX  INTEGER
                ACCESS  read-write
                STATUS  mandatory
                DESCRIPTION
                "Percentage of disk used which will trigger warning status."
                ::=  {  iis5DiskEntry 5   }

        iis5DiskCriticalThreshold OBJECT-TYPE
                SYNTAX  INTEGER
                ACCESS  read-write
                STATUS  mandatory
                DESCRIPTION
                "Percentage of disk used which will trigger critical status."
                ::=  {  iis5DiskEntry 6   }

        iis5DiskStatus OBJECT-TYPE
                SYNTAX  INTEGER
                {
                    ok(1),
                    warning(2),
                    critical(3)
                }
                ACCESS  read-only
                STATUS  mandatory
                DESCRIPTION
                "The status of the disk."
                ::=  {  iis5DiskEntry 7   }

        iis5WarningCounts OBJECT-TYPE
                SYNTAX  INTEGER
                ACCESS  read-only
                STATUS  mandatory
                DESCRIPTION
                "Number of times warning alert generated."
                ::=  {  iis5DiskEntry 8   }

        iis5CriticalCounts OBJECT-TYPE
                SYNTAX  INTEGER
                ACCESS  read-only
                STATUS  mandatory
                DESCRIPTION
                "Number of times critical alert generated."
                ::=  {  iis5DiskEntry 9   }

        iis5DiskUsage OBJECT-TYPE
                SYNTAX  DisplayString
                ACCESS  read-only
                STATUS  mandatory
                DESCRIPTION
                "What the web server uses this disk for."
                ::=  {  iis5DiskEntry 10   }

        iis5PrevWarningCounts OBJECT-TYPE
               SYNTAX  INTEGER
               ACCESS  read-only
               STATUS  mandatory
               DESCRIPTION
               "Previous number of times warning alert generated."
               ::=  {  iis5DiskEntry 11  }

        iis5PrevCriticalCounts OBJECT-TYPE
               SYNTAX  INTEGER
               ACCESS  read-only
               STATUS  mandatory
               DESCRIPTION
               "Previous number of times critical alert generated."
               ::=  {  iis5DiskEntry 12   }
		
        iis5DiskLagSetting OBJECT-TYPE
                SYNTAX  INTEGER
                ACCESS  read-write
                STATUS  mandatory
                DESCRIPTION
                "Lag setting for the disk."
                ::=  {  iis5DiskEntry 13   }
		
        iis5DiskLagValue OBJECT-TYPE
                SYNTAX  INTEGER
                ACCESS  read-only
                STATUS  mandatory
                DESCRIPTION
                "Current Lag value for the disk."
                ::=  {  iis5DiskEntry 14   }


--******************************************************************************
--* AvailCounterGroup - Counters currently available                         *
--******************************************************************************

        iis5AvailCounterTableEntries OBJECT-TYPE
                SYNTAX  INTEGER
                ACCESS  read-only
                STATUS  mandatory
                DESCRIPTION
                "The number of entries in the table."
                ::=  {  iis5AvailCounterGroup 1   }

        iis5AvailCounterTable OBJECT-TYPE
                SYNTAX  SEQUENCE OF Iis5AvailCounterEntry
                ACCESS  not-accessible
                STATUS  mandatory
                DESCRIPTION
                "The list of all available counters"
                ::=  {  iis5AvailCounterGroup 2}

        iis5AvailCounterEntry OBJECT-TYPE
                 SYNTAX  Iis5AvailCounterEntry
                 ACCESS  not-accessible
                 STATUS  mandatory
                 DESCRIPTION
                 "The AvailCounterTable entry."
                 INDEX { iis5AvailCounterDescription }
                     ::=  { iis5AvailCounterTable 1 }

        Iis5AvailCounterEntry ::= SEQUENCE
        {
            iis5AvailCounterDescription   DisplayString
        }

        iis5AvailCounterDescription OBJECT-TYPE
                SYNTAX  DisplayString
                ACCESS  read-only
                STATUS  mandatory
                DESCRIPTION
                "The description of the available counter"
                ::=  {  iis5AvailCounterEntry 1   }


--******************************************************************************
--* iis5PolledCounterGroup - Counters being polled                               *
--******************************************************************************

        iis5PolledCounterTableEntries OBJECT-TYPE
                SYNTAX  INTEGER
                ACCESS  read-only
                STATUS  mandatory
                DESCRIPTION
                "The number of entries in the table."
                ::=  {  iis5PolledCounterGroup 1   }

        iis5PolledCounterAdd OBJECT-TYPE
                SYNTAX  DisplayString
                ACCESS  write-only
                STATUS  mandatory
                DESCRIPTION
                "Add this counter to the polled counter table."
                ::=  {  iis5PolledCounterGroup 2   }

        iis5PolledCounterDelete OBJECT-TYPE
                SYNTAX  DisplayString
                ACCESS  write-only
                STATUS  mandatory
                DESCRIPTION
                "Delete this counter from the polled counter table."
                ::=  {  iis5PolledCounterGroup 3   }

        iis5PolledSummaryStatus OBJECT-TYPE
                SYNTAX  INTEGER
                {
                    normal(1),
                    warning(2),
                    critical(3)
                }
                ACCESS  read-only
                STATUS  mandatory
                DESCRIPTION
                "The summary status of all polled counters."
                ::=  {  iis5PolledCounterGroup 4   }

        iis5PollingInterval OBJECT-TYPE
                SYNTAX  INTEGER
                ACCESS  read-write
                STATUS  mandatory
                DESCRIPTION
                "Poll interval for the polled counter group in seconds."
                ::=  {  iis5PolledCounterGroup 5   }

        iis5PolledWarningCount OBJECT-TYPE
                SYNTAX  INTEGER
                ACCESS  read-only
                STATUS  mandatory
                DESCRIPTION
                "Number of polled counters in warning state."
                ::=  {  iis5PolledCounterGroup 6   }

        iis5PolledCriticalCount OBJECT-TYPE
                SYNTAX  INTEGER
                ACCESS  read-only
                STATUS  mandatory
                DESCRIPTION
                "Number of polled counters in critical state."
                ::=  {  iis5PolledCounterGroup 7   }

        iis5PolledCounterTable OBJECT-TYPE
                SYNTAX  SEQUENCE OF Iis5PolledCounterEntry
                ACCESS  not-accessible
                STATUS  mandatory
                DESCRIPTION
                "The list of all polled counters."
                ::=  {  iis5PolledCounterGroup 8}

        iis5PolledCounterEntry OBJECT-TYPE
                 SYNTAX  Iis5PolledCounterEntry
                 ACCESS  not-accessible
                 STATUS  mandatory
                 DESCRIPTION
                 "The PolledCounterTable entry."
                 INDEX { iis5Description }
                     ::=  { iis5PolledCounterTable 1 }

        Iis5PolledCounterEntry ::= SEQUENCE {
            iis5Description               DisplayString,
            iis5Available                 INTEGER,
            iis5WarningThreshold          DisplayString,
            iis5CriticalThreshold         DisplayString,
            iis5Value                     DisplayString,
            iis5WarningCount              INTEGER,
            iis5CriticalCount             INTEGER,
            iis5WarningAction             DisplayString,
            iis5CriticalAction            DisplayString,
            iis5Status                    INTEGER,
            iis5EnableDisable             INTEGER,
            iis5DescendingCounter         INTEGER,
            iis5Minimum                   DisplayString,
            iis5Maximum                   DisplayString,
            iis5Average                   DisplayString,
            iis5StdDev                    DisplayString,
	    iis5ValueReported		INTEGER,
            iis5PrevStatus          	INTEGER,
	    iis5LagSetting		INTEGER,
	    iis5LagValue			INTEGER
        }

        iis5Description OBJECT-TYPE
                SYNTAX  DisplayString
                ACCESS  read-only
                STATUS  mandatory
                DESCRIPTION
                "The description of the polled counter."
                ::=  {  iis5PolledCounterEntry 1   }

        iis5Available OBJECT-TYPE
                SYNTAX  INTEGER
                {
                    available(1),
                    notavailable(2)
                }
                ACCESS  read-only
                STATUS  mandatory
                DESCRIPTION
                "Describes whether this counter is currently available."
                ::=  {  iis5PolledCounterEntry 2   }

        iis5WarningThreshold OBJECT-TYPE
                SYNTAX  DisplayString
                ACCESS  read-write
                STATUS  mandatory
                DESCRIPTION
                "Counter value that will trigger warning status if value exceeds it."
                ::=  {  iis5PolledCounterEntry 3   }

        iis5CriticalThreshold OBJECT-TYPE
                SYNTAX  DisplayString
                ACCESS  read-write
                STATUS  mandatory
                DESCRIPTION
                "Counter value that will trigger critical status if value exceeds it."
                ::=  {  iis5PolledCounterEntry 4   }

        iis5Value OBJECT-TYPE
                SYNTAX  DisplayString
                ACCESS  read-only
                STATUS  mandatory
                DESCRIPTION
                "Value of the polled counter."
                ::=  {  iis5PolledCounterEntry 5   }

        iis5WarningCount OBJECT-TYPE
                SYNTAX  INTEGER
                ACCESS  read-only
                STATUS  mandatory
                DESCRIPTION
                "Number of times warning alert generated."
                ::=  {  iis5PolledCounterEntry 6   }

        iis5CriticalCount OBJECT-TYPE
                SYNTAX  INTEGER
                ACCESS  read-only
                STATUS  mandatory
                DESCRIPTION
                "Number of times critical alert generated."
                ::=  {  iis5PolledCounterEntry 7   }

        iis5WarningAction OBJECT-TYPE
                SYNTAX  DisplayString
                ACCESS  read-write
                STATUS  mandatory
                DESCRIPTION
                "Command to be executed when warning threshold is exceeded."
                ::=  {  iis5PolledCounterEntry 8   }

        iis5CriticalAction OBJECT-TYPE
                SYNTAX  DisplayString
                ACCESS  read-write
                STATUS  mandatory
                DESCRIPTION
                "Command to be executed when critical threshold is exceeded."
                ::=  {  iis5PolledCounterEntry 9   }

        iis5Status OBJECT-TYPE
                SYNTAX  INTEGER
                {
                    normal(1),
                    warning(2),
                    critical(3)
                }
                ACCESS  read-only
                STATUS  mandatory
                DESCRIPTION
                "Status of the polled counter."
                ::=  {  iis5PolledCounterEntry 10   }

        iis5EnableDisable OBJECT-TYPE
                SYNTAX  INTEGER
                {
                    enable(1),
                    disable(2)
                }
                ACCESS  read-write
                STATUS  mandatory
                DESCRIPTION
                "Enable or disable alerts for this counter."
                ::=  {  iis5PolledCounterEntry 11   }

        iis5DescendingCounter OBJECT-TYPE
                SYNTAX  INTEGER
                {
                    no(1),
                    yes(2)
                }
                ACCESS  read-write
                STATUS  mandatory
                DESCRIPTION
                "Yes if lower value triggers thresholds, no if higher value triggers thresholds."
                ::=  {  iis5PolledCounterEntry 12   }

        iis5Minimum OBJECT-TYPE
               SYNTAX  DisplayString
               ACCESS  read-only
               STATUS  mandatory
               DESCRIPTION
               "The minimum reading since the last reset."
               ::=  {  iis5PolledCounterEntry 13   }

        iis5Maximum OBJECT-TYPE
               SYNTAX  DisplayString
               ACCESS  read-only
               STATUS  mandatory
               DESCRIPTION
               "The maximum reading since the last reset."
               ::=  {  iis5PolledCounterEntry 14   }

        iis5Average OBJECT-TYPE
               SYNTAX  DisplayString
               ACCESS  read-only
               STATUS  mandatory
               DESCRIPTION
               "The average reading since the last reset."
               ::=  {  iis5PolledCounterEntry 15   }

        iis5StdDev OBJECT-TYPE
               SYNTAX  DisplayString
               ACCESS  read-only
               STATUS  mandatory
               DESCRIPTION
               "The standard deviation based on the last 100 readings."
               ::=  {  iis5PolledCounterEntry 16   }

        iis5ValueReported OBJECT-TYPE
               SYNTAX  INTEGER {
                                summary(1),
                                average(2),
				vhost(3)
                               }
               ACCESS  read-write
               STATUS  mandatory
               DESCRIPTION
               "The reported value of the counter is either a summary or average of all servers."
               ::=  {  iis5PolledCounterEntry 17 }

        iis5PrevStatus OBJECT-TYPE
                SYNTAX  INTEGER
                {
                    normal(1),
                    warning(2),
                    critical(3)
                }
                ACCESS  read-only
                STATUS  mandatory
                DESCRIPTION
                "Previous status of the polled counter."
                ::=  {  iis5PolledCounterEntry 18   }
		
        iis5LagSetting OBJECT-TYPE
                SYNTAX  INTEGER
                ACCESS  read-write
                STATUS  mandatory
                DESCRIPTION
                "Lag setting for the counter."
                ::=  {  iis5PolledCounterEntry 19   }
		
        iis5LagValue OBJECT-TYPE
                SYNTAX  INTEGER
                ACCESS  read-only
                STATUS  mandatory
                DESCRIPTION
                "Current Lag value for the counter."
                ::=  {  iis5PolledCounterEntry 20   }
	       

        iis5PolledCounterUpdate OBJECT-TYPE
               SYNTAX  DisplayString
               ACCESS  write-only
               STATUS  mandatory
	       DESCRIPTION "Update this entry in the table."
               ::=  {  iis5PolledCounterGroup 9  }
	       
        iis5PolledCounterDispTableEntries OBJECT-TYPE
                SYNTAX  INTEGER
                ACCESS  read-only
                STATUS  mandatory
                DESCRIPTION
                "The number of entries in the table."
                ::=  {  iis5PolledCounterGroup 10   }

        iis5PolledCounterDispTable OBJECT-TYPE
                SYNTAX  SEQUENCE OF Iis5PolledCounterDispEntry
                ACCESS  not-accessible
                STATUS  mandatory
                DESCRIPTION
                "The list of all polled counters."
                ::=  {  iis5PolledCounterGroup 11}

        iis5PolledCounterDispEntry OBJECT-TYPE
                 SYNTAX  Iis5PolledCounterDispEntry
                 ACCESS  not-accessible
                 STATUS  mandatory
                 DESCRIPTION
                 "The PolledCounterTable entry."
                 INDEX { iis5DispDescription }
                     ::=  { iis5PolledCounterDispTable 1 }

        Iis5PolledCounterDispEntry ::= SEQUENCE {
            iis5DispDescription           DisplayString,
            iis5DispAvailable             INTEGER,
            iis5DispWarningThreshold      DisplayString,
            iis5DispCriticalThreshold     DisplayString,
            iis5DispValue                 DisplayString,
            iis5DispWarningCount          INTEGER,
            iis5DispCriticalCount         INTEGER,
            iis5DispWarningAction         DisplayString,
            iis5DispCriticalAction        DisplayString,
            iis5DispStatus                INTEGER,
            iis5DispEnableDisable         INTEGER,
            iis5DispDescendingCounter     INTEGER,
            iis5DispMinimum               DisplayString,
            iis5DispMaximum               DisplayString,
            iis5DispAverage               DisplayString,
            iis5DispStdDev                DisplayString,
	    iis5DispValueReported		INTEGER,
	    iis5DispLagSetting		INTEGER,
	    iis5DispLagValue		INTEGER
        }

        iis5DispDescription OBJECT-TYPE
                SYNTAX  DisplayString
                ACCESS  read-only
                STATUS  mandatory
                DESCRIPTION
                "The description of the polled counter."
                ::=  {  iis5PolledCounterDispEntry 1   }

        iis5DispAvailable OBJECT-TYPE
                SYNTAX  INTEGER
                {
                    available(1),
                    notavailable(2)
                }
                ACCESS  read-only
                STATUS  mandatory
                DESCRIPTION
                "Describes whether this counter is currently available."
                ::=  {  iis5PolledCounterDispEntry 2   }

        iis5DispWarningThreshold OBJECT-TYPE
                SYNTAX  DisplayString
                ACCESS  read-write
                STATUS  mandatory
                DESCRIPTION
                "Counter value that will trigger warning status if value exceeds it."
                ::=  {  iis5PolledCounterDispEntry 3   }

        iis5DispCriticalThreshold OBJECT-TYPE
                SYNTAX  DisplayString
                ACCESS  read-write
                STATUS  mandatory
                DESCRIPTION
                "Counter value that will trigger critical status if value exceeds it."
                ::=  {  iis5PolledCounterDispEntry 4   }

        iis5DispValue OBJECT-TYPE
                SYNTAX  DisplayString
                ACCESS  read-only
                STATUS  mandatory
                DESCRIPTION
                "Value of the polled counter."
                ::=  {  iis5PolledCounterDispEntry 5   }

        iis5DispWarningCount OBJECT-TYPE
                SYNTAX  INTEGER
                ACCESS  read-only
                STATUS  mandatory
                DESCRIPTION
                "Number of times warning alert generated."
                ::=  {  iis5PolledCounterDispEntry 6   }

        iis5DispCriticalCount OBJECT-TYPE
                SYNTAX  INTEGER
                ACCESS  read-only
                STATUS  mandatory
                DESCRIPTION
                "Number of times critical alert generated."
                ::=  {  iis5PolledCounterDispEntry 7   }

        iis5DispWarningAction OBJECT-TYPE
                SYNTAX  DisplayString
                ACCESS  read-write
                STATUS  mandatory
                DESCRIPTION
                "Command to be executed when warning threshold is exceeded."
                ::=  {  iis5PolledCounterDispEntry 8   }

        iis5DispCriticalAction OBJECT-TYPE
                SYNTAX  DisplayString
                ACCESS  read-write
                STATUS  mandatory
                DESCRIPTION
                "Command to be executed when critical threshold is exceeded."
                ::=  {  iis5PolledCounterDispEntry 9   }

        iis5DispStatus OBJECT-TYPE
                SYNTAX  INTEGER
                {
                    normal(1),
                    warning(2),
                    critical(3)
                }
                ACCESS  read-only
                STATUS  mandatory
                DESCRIPTION
                "Status of the polled counter."
                ::=  {  iis5PolledCounterDispEntry 10   }

        iis5DispEnableDisable OBJECT-TYPE
                SYNTAX  INTEGER
                {
                    enable(1),
                    disable(2)
                }
                ACCESS  read-write
                STATUS  mandatory
                DESCRIPTION
                "Enable or disable alerts for this counter."
                ::=  {  iis5PolledCounterDispEntry 11   }

        iis5DispDescendingCounter OBJECT-TYPE
                SYNTAX  INTEGER
                {
                    no(1),
                    yes(2)
                }
                ACCESS  read-write
                STATUS  mandatory
                DESCRIPTION
                "Yes if lower value triggers thresholds, no if higher value triggers thresholds."
                ::=  {  iis5PolledCounterDispEntry 12   }

        iis5DispMinimum OBJECT-TYPE
               SYNTAX  DisplayString
               ACCESS  read-only
               STATUS  mandatory
               DESCRIPTION
               "The minimum reading since the last reset."
               ::=  {  iis5PolledCounterDispEntry 13   }

        iis5DispMaximum OBJECT-TYPE
               SYNTAX  DisplayString
               ACCESS  read-only
               STATUS  mandatory
               DESCRIPTION
               "The maximum reading since the last reset."
               ::=  {  iis5PolledCounterDispEntry 14   }

        iis5DispAverage OBJECT-TYPE
               SYNTAX  DisplayString
               ACCESS  read-only
               STATUS  mandatory
               DESCRIPTION
               "The average reading since the last reset."
               ::=  {  iis5PolledCounterDispEntry 15   }

        iis5DispStdDev OBJECT-TYPE
               SYNTAX  DisplayString
               ACCESS  read-only
               STATUS  mandatory
               DESCRIPTION
               "The standard deviation based on the last 100 readings."
               ::=  {  iis5PolledCounterDispEntry 16   }

        iis5DispValueReported OBJECT-TYPE
               SYNTAX  INTEGER {
                                summary(1),
                                average(2),
				vhost(3)
                               }
               ACCESS  read-write
               STATUS  mandatory
               DESCRIPTION
               "The reported value of the counter is either a summary or average of all servers."
               ::=  {  iis5PolledCounterDispEntry 17 }
		
        iis5DispLagSetting OBJECT-TYPE
                SYNTAX  INTEGER
                ACCESS  read-write
                STATUS  mandatory
                DESCRIPTION
                "Lag setting for the counter."
                ::=  {  iis5PolledCounterDispEntry 18   }
		
        iis5DispLagValue OBJECT-TYPE
                SYNTAX  INTEGER
                ACCESS  read-only
                STATUS  mandatory
                DESCRIPTION
                "Current Lag value for the counter."
                ::=  {  iis5PolledCounterDispEntry 19   }

	iis5PolledGPEnaDis OBJECT-TYPE
		SYNTAX      INTEGER {enable(1), disable(2)}
		ACCESS      read-write
		STATUS      mandatory
		DESCRIPTION "Enable or disable for the Group."
		::= { iis5PolledCounterGroup 12 }



--******************************************************************************
--* iis5EventGroup - user defined event monitoring                               *
--******************************************************************************
--      In this agent, we'll put available events in wsEventTable ahead of time
--      and allow the user to enable them for monitoring.

        iis5EventTableEntries OBJECT-TYPE
                SYNTAX  INTEGER
                ACCESS  read-only
                STATUS  mandatory
                DESCRIPTION
                "The number of entries in the event description table."
                ::=  {  iis5EventGroup 1   }

        iis5EventLogTableEntries OBJECT-TYPE
                SYNTAX  INTEGER
                ACCESS  read-only
                STATUS  mandatory
                DESCRIPTION
                "The number of entries in the event log table."
                ::=  {  iis5EventGroup 2   }

        iis5EventAdd OBJECT-TYPE
                SYNTAX  DisplayString
                ACCESS  write-only
                STATUS  mandatory
                DESCRIPTION
                "Event ID to be added to the event table."
                ::=  {  iis5EventGroup 3   }

        iis5EventDelete OBJECT-TYPE
                SYNTAX  INTEGER
                ACCESS  write-only
                STATUS  mandatory
                DESCRIPTION
                "Event ID to be deleted from the event table."
                ::=  {  iis5EventGroup 4   }

        iis5EventSummaryStatus OBJECT-TYPE
                SYNTAX  INTEGER
                {
                    normal(1),
                    warning(2),
                    critical(3)
                }
                ACCESS  read-write
                STATUS  mandatory
                DESCRIPTION
                "Summary status for events. Not automatic, must be manually reset to normal."
                ::=  {  iis5EventGroup 5   }

        iis5EventInterval OBJECT-TYPE
                SYNTAX  INTEGER
                ACCESS  read-write
                STATUS  mandatory
                DESCRIPTION
                "Poll interval for the Event group in seconds."
                ::=  {  iis5EventGroup 6   }

        iis5EventCircularBuffSize OBJECT-TYPE
                SYNTAX  INTEGER
                ACCESS  read-write
                STATUS  mandatory
                DESCRIPTION
                "Maximum number of entries in the event log table.  When this size is
                exceeded, oldest events are deleted to make room for the newest events."
                ::=  {  iis5EventGroup 7   }

        iis5EventTable OBJECT-TYPE
                SYNTAX  SEQUENCE OF Iis5EventEntry
                ACCESS  not-accessible
                STATUS  mandatory
                DESCRIPTION
                "The table of events being monitored."
                ::=  {  iis5EventGroup 8}

        iis5EventLogTable OBJECT-TYPE
                SYNTAX  SEQUENCE OF Iis5EventLogEntry
                ACCESS  not-accessible
                STATUS  mandatory
                DESCRIPTION
                "The table of events that occurred."
                ::=  {  iis5EventGroup 9}

        iis5EventWarningCount OBJECT-TYPE
                SYNTAX  INTEGER
                ACCESS  read-only
                STATUS  mandatory
                DESCRIPTION
                "Number of warning events since last reset."
                ::=  {  iis5EventGroup 10  }

        iis5EventCriticalCount OBJECT-TYPE
                SYNTAX  INTEGER
                ACCESS  read-only
                STATUS  mandatory
                DESCRIPTION
                "Number of critical events since last reset."
                ::=  {  iis5EventGroup 11 }

	iis5EventCmd OBJECT-TYPE
		SYNTAX      DisplayString
		ACCESS      read-write
		STATUS      mandatory
		DESCRIPTION 
		"Modify,id,severity,enabled.  EnableAll DisableAll"
		::= {iis5EventGroup 12 }

	iis5EventGPEnaDis OBJECT-TYPE
		SYNTAX      INTEGER {enable(1), disable(2)}
		ACCESS      read-write
		STATUS      mandatory
		DESCRIPTION "Enable or disable for the Group."
		::= { iis5EventGroup 13 }
		
        iis5EventEntry OBJECT-TYPE
                 SYNTAX  Iis5EventEntry
                 ACCESS  not-accessible
                 STATUS  mandatory
                 DESCRIPTION
                 "The EventTable entry."
                 INDEX { iis5EventID }
                 ::=  { iis5EventTable 1 }

        Iis5EventEntry ::= SEQUENCE
        {
                iis5EventID                    INTEGER,
                iis5EVDescription              DisplayString,
                iis5EVSeverity                 INTEGER,
                iis5EVSyslogText               DisplayString,
                iis5EVEnable                   INTEGER
        }

        iis5EventID OBJECT-TYPE
                SYNTAX  INTEGER
                ACCESS  read-only
                STATUS  mandatory
                DESCRIPTION
                "ID of the event."
                ::=  {  iis5EventEntry 1   }

        iis5EVDescription OBJECT-TYPE
                SYNTAX  DisplayString
                ACCESS  read-write
                STATUS  mandatory
                DESCRIPTION
                "Description of the event."
                ::=  {  iis5EventEntry 2   }

        iis5EVSeverity OBJECT-TYPE
                SYNTAX  INTEGER
                {
                    warning(1),
                    critical(2)
                }
                ACCESS  read-write
                STATUS  mandatory
                DESCRIPTION
                "Severity level of the event."
                ::=  {  iis5EventEntry 3   }

        iis5EVSyslogText OBJECT-TYPE
                SYNTAX  DisplayString
                ACCESS  read-write
                STATUS  mandatory
                DESCRIPTION
                "Text to search for in the syslog file that indicates this event occurred."
                ::=  {  iis5EventEntry 4   }

        iis5EVEnable OBJECT-TYPE
               SYNTAX  INTEGER {
                                enabled(1),
                                disabled(2)
                               }
               ACCESS  read-write
               STATUS  mandatory
               DESCRIPTION
               "Enable logging of this event."
               ::=  {  iis5EventEntry 5   }


        iis5EventLogEntry OBJECT-TYPE
                 SYNTAX  Iis5EventLogEntry
                 ACCESS  not-accessible
                 STATUS  mandatory
                 DESCRIPTION
                 "The EventTable entry."
                 INDEX { iis5EVLTimestamp, iis5EVLIndex }
                 ::=  { iis5EventLogTable 1 }

        Iis5EventLogEntry ::= SEQUENCE {
           iis5EVLTimestamp               DisplayString,
           iis5EVLID                      INTEGER,
           iis5EVLDescription             DisplayString,
           iis5EVLStatus                  INTEGER,
           iis5EVLIndex                   INTEGER
        }

        iis5EVLTimestamp OBJECT-TYPE
                SYNTAX  DisplayString
                ACCESS  read-only
                STATUS  mandatory
                DESCRIPTION
                "Human-readable timestamp of when the event happened."
                ::=  {  iis5EventLogEntry 1   }

        iis5EVLID OBJECT-TYPE
                SYNTAX  INTEGER
                ACCESS  read-only
                STATUS  mandatory
                DESCRIPTION
                "ID of the event."
                ::=  {  iis5EventLogEntry 2   }

        iis5EVLDescription OBJECT-TYPE
                SYNTAX  DisplayString
                ACCESS  read-only
                STATUS  mandatory
                DESCRIPTION
                "Description of the event."
                ::=  {  iis5EventLogEntry 3   }

        iis5EVLStatus OBJECT-TYPE
                SYNTAX  INTEGER
                {
                    warning(1),
                    critical(2)
                }
                ACCESS  read-only
                STATUS  mandatory
                DESCRIPTION
                "Status caused by the event."
                ::=  {  iis5EventLogEntry 4   }

        iis5EVLIndex OBJECT-TYPE
                SYNTAX  INTEGER
                ACCESS  read-only
                STATUS  mandatory
                DESCRIPTION
                "Index value that ensures uniqueness of events with same ID and timestamp."
                ::=  {  iis5EventLogEntry 5   }


--******************************************************************************
--* iis5AgentGroup - Agent version and update information                        *
--******************************************************************************

        iis5AgentDescription OBJECT-TYPE
                SYNTAX  DisplayString
                ACCESS  read-only
                STATUS  mandatory
                DESCRIPTION
                "Description of the agent."
                ::=  {  iis5AgentGroup 1   }

        iis5AgentVersion OBJECT-TYPE
                SYNTAX  DisplayString
                ACCESS  read-only
                STATUS  mandatory
                DESCRIPTION
                "Version of the agent."
                ::=  {  iis5AgentGroup 2   }

        iis5AgentStartTime OBJECT-TYPE
                SYNTAX  DisplayString
                ACCESS  read-only
                STATUS  mandatory
                DESCRIPTION
                "The time the agent was started."
                ::=  {  iis5AgentGroup 3   }

        iis5ServerLastUpdate OBJECT-TYPE
                SYNTAX  DisplayString
                ACCESS  read-only
                STATUS  mandatory
                DESCRIPTION
                "The time the ServerGroup was last updated"
                ::=  {  iis5AgentGroup 4   }

        iis5ServicesLastUpdate OBJECT-TYPE
                SYNTAX  DisplayString
                ACCESS  read-only
                STATUS  mandatory
                DESCRIPTION
                "The time the ServicesGroup was last updated"
                ::=  {  iis5AgentGroup 5   }

        iis5DiskLastUpdate OBJECT-TYPE
                SYNTAX  DisplayString
                ACCESS  read-only
                STATUS  mandatory
                DESCRIPTION
                "The time the DiskGroup was last updated"
                ::=  {  iis5AgentGroup 6   }

        iis5PolledCounterLastUpdate OBJECT-TYPE
                SYNTAX  DisplayString
                ACCESS  read-only
                STATUS  mandatory
                DESCRIPTION
                "The time the PolledCounterGroup was last updated"
                ::=  {  iis5AgentGroup 7   }

        iis5EventsLastUpdate OBJECT-TYPE
                SYNTAX  DisplayString
                ACCESS  read-only
                STATUS  mandatory
                DESCRIPTION
                "The time the EventGroup was last updated"
                ::=  {  iis5AgentGroup 8   }

        iis5BadLinksLastUpdate OBJECT-TYPE
                SYNTAX  DisplayString
                ACCESS  read-only
                STATUS  mandatory
                DESCRIPTION
                "The time the LinkGroup was last updated"
                ::=  {  iis5AgentGroup 9   }

        iis5WebCrwlrLastUpdate OBJECT-TYPE
                SYNTAX  DisplayString
                ACCESS  read-only
                STATUS  mandatory
                DESCRIPTION
                "The time the WCGroup was last updated"
                ::=  {  iis5AgentGroup 10   }

        iis5URLMntrLastUpdate OBJECT-TYPE
                SYNTAX  DisplayString
                ACCESS  read-only
                STATUS  mandatory
                DESCRIPTION
                "The time the URLMntrGroup was last updated"
                ::=  {  iis5AgentGroup 11   }

        iis5TopURLsLastUpdate OBJECT-TYPE
                SYNTAX  DisplayString
                ACCESS  read-only
                STATUS  mandatory
                DESCRIPTION
                "The time the TopURLGroup was last updated"
                ::=  {  iis5AgentGroup 12   }

        iis5ServerHealthLastUpdate OBJECT-TYPE
               SYNTAX  DisplayString
               ACCESS  read-only
               STATUS  mandatory
               DESCRIPTION
               "The time the ServerHealthGroup was last updated"
               ::=  {  iis5AgentGroup 13   }

        iis5LocalActionLastUpdate OBJECT-TYPE
               SYNTAX  DisplayString
               ACCESS  read-only
               STATUS  mandatory
               DESCRIPTION
               "The last time a local action executed)"
               ::=  {  iis5AgentGroup 14   }

        iis5Iis5LogPath OBJECT-TYPE
               SYNTAX  DisplayString
               ACCESS  read-write
               STATUS  mandatory
               DESCRIPTION
               "OPTIONAL-File name for the Common Log format file"
               ::=  {  iis5AgentGroup 15   }

        iis5ServerRoot OBJECT-TYPE
               SYNTAX  DisplayString
               ACCESS  read-write
               STATUS  mandatory
               DESCRIPTION
               "Server root to prepend to paths in config file."
               ::=  {  iis5AgentGroup 16   }

        iis5ServerConfig OBJECT-TYPE
               SYNTAX  DisplayString
               ACCESS  read-write
               STATUS  mandatory
               DESCRIPTION
               "Server config file path."
               ::=  {  iis5AgentGroup 17   }

        iis5WebServerName OBJECT-TYPE
               SYNTAX  DisplayString
               ACCESS  read-write
               STATUS  mandatory
               DESCRIPTION
               "Service name in NT; command in UNIX; used for start/stop."
               ::=  {  iis5AgentGroup 18   }


        iis5FTPName OBJECT-TYPE
               SYNTAX  DisplayString
               ACCESS  read-write
               STATUS  mandatory
               DESCRIPTION
               "FTP service name in NT; command in UNIX; used for start/stop."
               ::=  {  iis5AgentGroup 19   }


        iis5CGIstrings OBJECT-TYPE
               SYNTAX  DisplayString
               ACCESS  read-write
               STATUS  mandatory
               DESCRIPTION
               "Comma seperated strings used to identify CGI URLs."
               ::=  {  iis5AgentGroup 20   }


        iis5AvailCounterLastUpdate OBJECT-TYPE
               SYNTAX  DisplayString
               ACCESS  read-only
               STATUS  mandatory
               DESCRIPTION
               "The last time a AvailCounter group was updated."
               ::=  {  iis5AgentGroup 21   }


        iis5InstanceName OBJECT-TYPE
               SYNTAX  DisplayString
               ACCESS  read-only
               STATUS  mandatory
               DESCRIPTION
               "The Instance name for this agent."
               ::=  {  iis5AgentGroup 22   }


        iis5ErrorMsg OBJECT-TYPE
               SYNTAX  DisplayString
               ACCESS  read-write
               STATUS  mandatory
               DESCRIPTION
               "The Last Error Message as a result of GET/SET of a MIB value."
               ::=  {  iis5AgentGroup 23   }


        iis5FTPPort OBJECT-TYPE
               SYNTAX  DisplayString
               ACCESS  read-write
               STATUS  mandatory
               DESCRIPTION
               "FTP service port; to change the default (21)."
               ::=  {  iis5AgentGroup 24 }

        iis5ExpressionsLastUpdate OBJECT-TYPE
                SYNTAX  DisplayString
                ACCESS  read-only
                STATUS  mandatory
                DESCRIPTION
                "The time the ExpressionsGroup was last updated"
                ::=  {  iis5AgentGroup 25   }
		
        iis5AdminConfig OBJECT-TYPE
               SYNTAX  DisplayString
               ACCESS  read-write
               STATUS  mandatory
               DESCRIPTION
               "Admin Server config file path."
               ::=  {  iis5AgentGroup 26   }

        iis5WebAdminName OBJECT-TYPE
               SYNTAX  DisplayString
               ACCESS  read-write
               STATUS  mandatory
               DESCRIPTION
               "Admin service name in NT; command qualifier in UNIX; used for start/stop."
               ::=  {  iis5AgentGroup 27   }

        iis5EnableDatabaseUse OBJECT-TYPE
                SYNTAX  INTEGER
                { yes(1), no(2) }
                ACCESS  read-only
                STATUS  mandatory
                DESCRIPTION
                "Domino server: 'Yes' indicates the agent obtains information from Domino Database.
                'No' indicates the agent obtains infomation from Domino generated logfiles."
                ::=  {  iis5AgentGroup 28  }

        iis5DominoName OBJECT-TYPE
                SYNTAX  DisplayString
                ACCESS  read-only
                STATUS  mandatory
                DESCRIPTION
                "Domino server: name for this HTTP server."
                ::=  {  iis5AgentGroup 29   }

        iis5PartitionPath OBJECT-TYPE
                SYNTAX  DisplayString
                ACCESS  read-only
                STATUS  mandatory
                DESCRIPTION
                "Domino server: partition PATH for this HTTP server."
                ::=  {  iis5AgentGroup 30  }

        iis5PartitionNumber OBJECT-TYPE
                SYNTAX  INTEGER
                ACCESS  read-only
                STATUS  mandatory
                DESCRIPTION
                "Domino server: partition number for this HTTP server."
                ::=  {  iis5AgentGroup 31  }
		
        iis5DocPath OBJECT-TYPE
               SYNTAX  DisplayString
               ACCESS  read-write
               STATUS  mandatory
               DESCRIPTION
               "Oracle server: Server doc path."
               ::=  {  iis5AgentGroup 32  }
	       
        iis5ListenerName OBJECT-TYPE
               SYNTAX  DisplayString
               ACCESS  read-write
               STATUS  mandatory
               DESCRIPTION
               "Oracle server: Web listener name."
               ::=  {  iis5AgentGroup 33  }

        iis5ProductRoot OBJECT-TYPE
               SYNTAX  DisplayString
               ACCESS  read-write
               STATUS  mandatory
               DESCRIPTION
               "Oracle server: Product root path."
               ::=  {  iis5AgentGroup 34  }
	       

        iis5IISAvailCounterLastUpdate OBJECT-TYPE
               SYNTAX  DisplayString
               ACCESS  read-only
               STATUS  mandatory
               DESCRIPTION
               "The last time a IISAvailCounter group was updated."
               ::=  {  iis5AgentGroup 35   }

        iis5IISPolledCounterLastUpdate OBJECT-TYPE
               SYNTAX  DisplayString
               ACCESS  read-only
               STATUS  mandatory
               DESCRIPTION
               "The last time a IISPolledCounter group was updated."
               ::=  {  iis5AgentGroup 36   }


--******************************************************************************
--* ServerHealthGroup - overall server performance indicators                  *
--******************************************************************************

        iis5SHSummaryStatus OBJECT-TYPE
               SYNTAX  INTEGER {
                                normal(1),
                                warning(2),
                                critical(3)
                                }
               ACCESS  read-only
               STATUS  mandatory
               DESCRIPTION
               "Summary status for group."
               ::=  {  iis5SHGroup 1   }

        iis5SHPollingInterval OBJECT-TYPE
               SYNTAX  INTEGER
               ACCESS  read-write
               STATUS  mandatory
               DESCRIPTION
               "Seconds to poll for changes."
               ::=  {  iis5SHGroup 2   }

        iis5SHCpuUsage OBJECT-TYPE
               SYNTAX  INTEGER
               ACCESS  read-only
               STATUS  mandatory
               DESCRIPTION
               "CPU usage of the web server."
               ::=  {  iis5SHGroup 3   }

        iis5SHCpuWarningThreshold OBJECT-TYPE
               SYNTAX  INTEGER
               ACCESS  read-write
               STATUS  mandatory
               DESCRIPTION
               "Generate a warning if SHCpuUsage exceeds this."
               ::=  {  iis5SHGroup 4   }

        iis5SHCpuCriticalThreshold OBJECT-TYPE
               SYNTAX  INTEGER
               ACCESS  read-write
               STATUS  mandatory
               DESCRIPTION
               "Generate a critical if SHCpuUsage exceeds this."
               ::=  {  iis5SHGroup 5   }

        iis5SHReqRate OBJECT-TYPE
               SYNTAX  INTEGER
               ACCESS  read-only
               STATUS  mandatory
               DESCRIPTION
               "Requests per second."
               ::=  {  iis5SHGroup 6   }

        iis5SHReqRateWarningThreshold OBJECT-TYPE
               SYNTAX  INTEGER
               ACCESS  read-write
               STATUS  mandatory
               DESCRIPTION
               "Generate a warning if SHReqRate exceeds this."
               ::=  {  iis5SHGroup 7   }

        iis5SHReqRateCriticalThreshold OBJECT-TYPE
               SYNTAX  INTEGER
               ACCESS  read-write
               STATUS  mandatory
               DESCRIPTION
               "Generate a critical if SHReqRate exceeds this."
               ::=  {  iis5SHGroup 8   }

        iis5SHByteRate OBJECT-TYPE
               SYNTAX  INTEGER
               ACCESS  read-only
               STATUS  mandatory
               DESCRIPTION
               "Kilobytes transferred per second."
               ::=  {  iis5SHGroup 9   }

        iis5SHByteRateWarningThreshold OBJECT-TYPE
               SYNTAX  INTEGER
               ACCESS  read-write
               STATUS  mandatory
               DESCRIPTION
               "Generate a warning if SHByteRate exceeds this."
               ::=  {  iis5SHGroup 10   }

        iis5SHByteRateCriticalThreshold OBJECT-TYPE
               SYNTAX  INTEGER
               ACCESS  read-write
               STATUS  mandatory
               DESCRIPTION
               "Generate a critical if SHByteRate exceeds this."
               ::=  {  iis5SHGroup 11   }

        iis5SHWarningAction OBJECT-TYPE
               SYNTAX  DisplayString
               ACCESS  read-write
               STATUS  mandatory
               DESCRIPTION
               "Command to be executed when any warning threshold is exceeded."
               ::=  {  iis5SHGroup 12   }

        iis5SHCriticalAction OBJECT-TYPE
               SYNTAX  DisplayString
               ACCESS  read-write
               STATUS  mandatory
               DESCRIPTION
               "Command to be executed when any critical threshold is exceeded."
               ::=  {  iis5SHGroup 13   }

        iis5SHProcesses OBJECT-TYPE
               SYNTAX  INTEGER
               ACCESS  read-only
               STATUS  mandatory
               DESCRIPTION
               "Number of current server processes."
               ::=  {  iis5SHGroup 14   }

        iis5SHTotalHits OBJECT-TYPE
               SYNTAX  INTEGER
               ACCESS  read-only
               STATUS  mandatory
               DESCRIPTION
               "Totals requests."
               ::=  {  iis5SHGroup 15   }

        iis5SHTotalErrors OBJECT-TYPE
               SYNTAX  INTEGER
               ACCESS  read-only
               STATUS  mandatory
               DESCRIPTION
               "Totals error requests."
               ::=  {  iis5SHGroup 16   }

        iis5SHTotalGETS OBJECT-TYPE
               SYNTAX  INTEGER
               ACCESS  read-only
               STATUS  mandatory
               DESCRIPTION
               "Totals GET requests."
               ::=  {  iis5SHGroup 17   }

        iis5SHTotalPOSTS OBJECT-TYPE
               SYNTAX  INTEGER
               ACCESS  read-only
               STATUS  mandatory
               DESCRIPTION
               "Totals POST requests."
               ::=  {  iis5SHGroup 18   }

        iis5SHTotalHEADS OBJECT-TYPE
               SYNTAX  INTEGER
               ACCESS  read-only
               STATUS  mandatory
               DESCRIPTION
               "Totals HEAD requests."
               ::=  {  iis5SHGroup 19   }

        iis5SHTotalCGI OBJECT-TYPE
               SYNTAX  INTEGER
               ACCESS  read-only
               STATUS  mandatory
               DESCRIPTION
               "Totals CGI requests."
               ::=  {  iis5SHGroup 20   }

        iis5SHServerUptime OBJECT-TYPE
               SYNTAX  INTEGER
               ACCESS  read-only
               STATUS  mandatory
               DESCRIPTION
               "Server uptime in days."
               ::=  {  iis5SHGroup 21   }

        iis5SHMaxReqRate OBJECT-TYPE
               SYNTAX  INTEGER
               ACCESS  read-write
               STATUS  mandatory
               DESCRIPTION
               "Max value for the abrowser max requests scale."
               ::=  {  iis5SHGroup 22   }

        iis5SHMaxByteRate OBJECT-TYPE
               SYNTAX  INTEGER
               ACCESS  read-write
               STATUS  mandatory
               DESCRIPTION
               "Max value for the abrowser max bytes scale."
               ::=  {  iis5SHGroup 23   }

	iis5SHGPEnaDis OBJECT-TYPE
		SYNTAX      INTEGER {enable(1), disable(2)}
		ACCESS      read-write
		STATUS      mandatory
		DESCRIPTION "Enable or disable for the Group."
		::= { iis5SHGroup 24 }
		
        iis5SHCPULagSetting OBJECT-TYPE
                SYNTAX  INTEGER
                ACCESS  read-write
                STATUS  mandatory
                DESCRIPTION
                "Lag setting for the counter."
                ::=  {  iis5SHGroup 25   }
		
        iis5SHCPULagValue OBJECT-TYPE
                SYNTAX  INTEGER
                ACCESS  read-only
                STATUS  mandatory
                DESCRIPTION
                "Current Lag value for the counter."
                ::=  {  iis5SHGroup 26   }
		
        iis5SHRSLagSetting OBJECT-TYPE
                SYNTAX  INTEGER
                ACCESS  read-write
                STATUS  mandatory
                DESCRIPTION
                "Lag setting for the counter."
                ::=  {  iis5SHGroup 27   }
		
        iis5SHRSLagValue OBJECT-TYPE
                SYNTAX  INTEGER
                ACCESS  read-only
                STATUS  mandatory
                DESCRIPTION
                "Current Lag value for the counter."
                ::=  {  iis5SHGroup 28   }
		
        iis5SHKSLagSetting OBJECT-TYPE
                SYNTAX  INTEGER
                ACCESS  read-write
                STATUS  mandatory
                DESCRIPTION
                "Lag setting for the counter."
                ::=  {  iis5SHGroup 29   }
		
        iis5SHKSLagValue OBJECT-TYPE
                SYNTAX  INTEGER
                ACCESS  read-only
                STATUS  mandatory
                DESCRIPTION
                "Current Lag value for the counter."
                ::=  {  iis5SHGroup 30   }


--******************************************************************************
--* Local action log - circular buffer of local actions performed              *
--* Dynamic get, not polled.                                                   *
--******************************************************************************

        iis5LocalActionTableEntries OBJECT-TYPE
               SYNTAX  INTEGER
               ACCESS  read-only
               STATUS  mandatory
               DESCRIPTION
               "The number of entries in the local action log table."
               ::=  {  iis5LocalActionGroup 1   }

        iis5LocalActionCircularBuffSize OBJECT-TYPE
               SYNTAX  INTEGER
               ACCESS  read-write
               STATUS  mandatory
               DESCRIPTION
               "Max entries in the LocalActionLogTable (default 50)."
               ::=  {  iis5LocalActionGroup 2   }

        iis5LocalActionRefresh OBJECT-TYPE
               SYNTAX  INTEGER
               ACCESS  read-write
               STATUS  mandatory
               DESCRIPTION
               "Refresh the table starting with the most recent action."
               ::=  {  iis5LocalActionGroup 3   }

        iis5LocalActionStartDateTime OBJECT-TYPE
               SYNTAX  DisplayString
               ACCESS  read-write
               STATUS  mandatory
               DESCRIPTION
               "Refresh the table starting at the specified date and time."
               ::=  {  iis5LocalActionGroup 4   }

        iis5LocalActionScrollDown OBJECT-TYPE
               SYNTAX  INTEGER
               ACCESS  read-write
               STATUS  mandatory
               DESCRIPTION
               "Read the next older set of log entries into the table."
               ::=  {  iis5LocalActionGroup 5   }

        iis5LocalActionScrollUp OBJECT-TYPE
               SYNTAX  INTEGER
               ACCESS  read-write
               STATUS  mandatory
               DESCRIPTION
               "Read the next newer set of log entries into the table."
               ::=  {  iis5LocalActionGroup 6   }

        iis5LocalActionLogTable OBJECT-TYPE
               SYNTAX  SEQUENCE OF Iis5LocalActionLogEntry
               ACCESS  not-accessible
               STATUS  mandatory
               DESCRIPTION
               "This table contains a list of command actions taken in response to events."
               ::=  {  iis5LocalActionGroup 7 }

        iis5LocalActionLogEntry OBJECT-TYPE
                                SYNTAX  Iis5LocalActionLogEntry
                                ACCESS  not-accessible
                                STATUS  mandatory
                                DESCRIPTION
                                "This is an entry in the LocalActionTable"
                                INDEX { iis5LocalActionSequencer }
                                ::=  { iis5LocalActionLogTable 1 }

        Iis5LocalActionLogEntry ::= SEQUENCE
        {
           iis5LocalActionSequencer               INTEGER,
           iis5LocalActionTimestamp               DisplayString,
           iis5LocalActionSeverity                INTEGER,
           iis5LocalActionReason                  DisplayString,
           iis5LocalActionCommand                 DisplayString
        }

        iis5LocalActionSequencer OBJECT-TYPE
               SYNTAX  INTEGER
               ACCESS  read-only
               STATUS  mandatory
               DESCRIPTION
               "Table sequencer"
               ::=  {  iis5LocalActionLogEntry 1   }

        iis5LocalActionTimestamp OBJECT-TYPE
               SYNTAX  DisplayString
               ACCESS  read-only
               STATUS  mandatory
               DESCRIPTION
               "Time the command was executed (action taken)."
               ::=  {  iis5LocalActionLogEntry 2   }

-- The Warning and Critical values for severity must match CLocalAction::enum Severity.
        iis5LocalActionSeverity OBJECT-TYPE
               SYNTAX  INTEGER
               {
                   normal(1),
                   warning(2),
                   critical(3)
               }
               ACCESS  read-only
               STATUS  mandatory
               DESCRIPTION
               "The severity of the event which triggered the action."
               ::=  {  iis5LocalActionLogEntry 3   }

        iis5LocalActionReason OBJECT-TYPE
               SYNTAX  DisplayString
               ACCESS  read-only
               STATUS  mandatory
               DESCRIPTION
               "The reason the action was taken."
               ::=  {  iis5LocalActionLogEntry 4   }

        iis5LocalActionCommand OBJECT-TYPE
               SYNTAX  DisplayString
               ACCESS  read-only
               STATUS  mandatory
               DESCRIPTION
               "Command executed (action taken)."
               ::=  {  iis5LocalActionLogEntry 5   }


--******************************************************************************
--* iis5ServLogGroup - buffer of server error log                                *
--******************************************************************************

        iis5ServLogTableEntries OBJECT-TYPE
               SYNTAX  INTEGER
               ACCESS  read-only
               STATUS  mandatory
               DESCRIPTION
               "The number of entries in the table."
               ::=  {  iis5ServLogGroup 1   }

        iis5ServLogStartDateTime OBJECT-TYPE
               SYNTAX  DisplayString
               ACCESS  read-write
               STATUS  mandatory
               DESCRIPTION
               "Refresh the table starting at the specified date and time."
               ::=  {  iis5ServLogGroup 2   }

        iis5ServLogReadLog OBJECT-TYPE
               SYNTAX  INTEGER
               ACCESS  read-write
               STATUS  mandatory
               DESCRIPTION
               "Refresh the table starting with the most recent entry."
               ::=  {  iis5ServLogGroup 3   }

        iis5ServLogScrollDown OBJECT-TYPE
               SYNTAX  INTEGER
               ACCESS  read-write
               STATUS  mandatory
               DESCRIPTION
               "Read the next older set of log entries into the table."
               ::=  {  iis5ServLogGroup 4   }

        iis5ServLogScrollUp OBJECT-TYPE
               SYNTAX  INTEGER
               ACCESS  read-write
               STATUS  mandatory
               DESCRIPTION
               "Read the next newer set of log entries into the table."
               ::=  {  iis5ServLogGroup 5   }

        iis5ServLogMaxBuffSize OBJECT-TYPE
               SYNTAX  INTEGER
               ACCESS  read-write
               STATUS  mandatory
               DESCRIPTION
               "Max lines in the wsServLogTable (default 50)."
               ::=  {  iis5ServLogGroup 6   }

        iis5ServLogTable OBJECT-TYPE
               SYNTAX  SEQUENCE OF Iis5ServLogEntry
               ACCESS  not-accessible
               STATUS  mandatory
               DESCRIPTION
               "This table contains the contents of the server log."
               ::=  {  iis5ServLogGroup 7}

        iis5ServLogEntry OBJECT-TYPE
                                SYNTAX  Iis5ServLogEntry
                                ACCESS  not-accessible
                                STATUS  mandatory
                                DESCRIPTION
                                "This is an entry in the ServLogTable"
                                INDEX { iis5ServLogSequencer }
                                ::=  { iis5ServLogTable 1 }

        Iis5ServLogEntry ::= SEQUENCE
        {
           iis5ServLogSequencer           INTEGER,
           iis5ServLogDateTime            DisplayString,
           iis5ServLogMsgType             DisplayString,
           iis5ServLogMsgText             DisplayString
        }

        iis5ServLogSequencer OBJECT-TYPE
               SYNTAX  INTEGER
               ACCESS  read-only
               STATUS  mandatory
               DESCRIPTION
               "Table sequencer"
               ::=  {  iis5ServLogEntry 1   }

        iis5ServLogDateTime OBJECT-TYPE
               SYNTAX  DisplayString
               ACCESS  read-only
               STATUS  mandatory
               DESCRIPTION
               "Log entry data and time"
               ::=  {  iis5ServLogEntry 2   }

        iis5ServLogMsgType OBJECT-TYPE
               SYNTAX  DisplayString
               ACCESS  read-only
               STATUS  mandatory
               DESCRIPTION
               "Log message type"
               ::=  {  iis5ServLogEntry 3   }

        iis5ServLogMsgText OBJECT-TYPE
               SYNTAX  DisplayString
               ACCESS  read-only
               STATUS  mandatory
               DESCRIPTION
               "Log message text."
               ::=  {  iis5ServLogEntry 4   }

--******************************************************************************
--* iis5WCGroup - WebCrawler Group                                               *
--******************************************************************************

        iis5WCSummaryStatus OBJECT-TYPE
                SYNTAX  INTEGER
                {
                    normal(1),
                    warning(2),
                    critical(3)
                }
                ACCESS  read-only
                STATUS  mandatory
                DESCRIPTION
                "Summary status for WebCrawler group."
                ::=  {  iis5WCGroup 1  }

        iis5WCTableEntries OBJECT-TYPE
               SYNTAX  INTEGER
               ACCESS  read-only
               STATUS  mandatory
               DESCRIPTION
               "The number of entries in the table."
               ::=  {  iis5WCGroup 2   }

        iis5WCMaxTableEntries OBJECT-TYPE
               SYNTAX  INTEGER
               ACCESS  read-write
               STATUS  mandatory
               DESCRIPTION
               "The maximum number of table entries allowed."
               ::=  {  iis5WCGroup 3   }

        iis5WCClearTrigger OBJECT-TYPE
               SYNTAX  INTEGER {
                                Execute(1)
                               }
               ACCESS  read-write
               STATUS  mandatory
               DESCRIPTION
               "Clear the data and trigger the WebCrawler."
               ::=  {  iis5WCGroup 4   }

        iis5WCTaskStatus OBJECT-TYPE
               SYNTAX  INTEGER {
                                inactive(1),
                                executing(2),
                                internalerror(3)
                               }
               ACCESS  read-only
               STATUS  mandatory
               DESCRIPTION
               "Current status of the Web crawler process."
               ::=  {  iis5WCGroup 5   }

        iis5WCLastRanTS OBJECT-TYPE
               SYNTAX  DisplayString
               ACCESS  read-only
               STATUS  mandatory
               DESCRIPTION
               "Time WebCrawler was last run."
               ::=  {  iis5WCGroup 6   }

        iis5WCInterval OBJECT-TYPE
               SYNTAX  INTEGER
               ACCESS  read-write
               STATUS  mandatory
               DESCRIPTION
               "Interval between executions of the Web Crawler process."
               ::=  {  iis5WCGroup 7  }

        iis5WCIntervalType OBJECT-TYPE
               SYNTAX  INTEGER {
                                hours(1),
                                days(2),
                                weeks(3)
                               }
               ACCESS  read-write
               STATUS  mandatory
               DESCRIPTION
               "Type of interval to be used in WCInterval."
               ::=  {  iis5WCGroup 8   }

        iis5WCStartTS OBJECT-TYPE
               SYNTAX  DisplayString
               ACCESS  read-write
               STATUS  mandatory
               DESCRIPTION
               "Time to start WebCrawler."
               ::=  {  iis5WCGroup 9   }

        iis5WCNewPageDays OBJECT-TYPE
               SYNTAX  INTEGER
               ACCESS  read-write
               STATUS  mandatory
               DESCRIPTION
               "Days previous to current that will be used by WebCrawler to determine new pages."
               ::=  {  iis5WCGroup 10   }

        iis5WCSlowSize OBJECT-TYPE
               SYNTAX  INTEGER
               ACCESS  read-write
               STATUS  mandatory
               DESCRIPTION
               "Size in bytes that will be used by WebCrawler to determine slow pages."
               ::=  {  iis5WCGroup 11  }

        iis5WCStartURL OBJECT-TYPE
               SYNTAX  DisplayString
               ACCESS  read-write
               STATUS  mandatory
               DESCRIPTION
               "First URL to start parsing with WebCrawler."
               ::=  {  iis5WCGroup 12   }

        iis5WCExecTime OBJECT-TYPE
               SYNTAX  DisplayString
               ACCESS  read-only
               STATUS  mandatory
               DESCRIPTION
               "WebCrawler elapsed execution time(mm:ss)."
               ::=  {  iis5WCGroup 13  }

        iis5WCReport OBJECT-TYPE
               SYNTAX  DisplayString
               ACCESS  read-write
               STATUS  mandatory
               DESCRIPTION
               "Web Crawler process report file path and name."
               ::=  {  iis5WCGroup 14   }

        iis5WCCheckExternal OBJECT-TYPE
               SYNTAX  INTEGER{
                               yes(1),
                               no(2)
                              }
               ACCESS  read-write
               STATUS  mandatory
               DESCRIPTION
               "Check external links in pages."
               ::=  {  iis5WCGroup 15  }

        iis5WCInvalidPages OBJECT-TYPE
               SYNTAX  INTEGER
               ACCESS  read-only
               STATUS  mandatory
               DESCRIPTION
               "Count of invalid pages based verify attributes."
               ::=  {  iis5WCGroup 16  }

        iis5WCIntWarningThreshold OBJECT-TYPE
               SYNTAX  INTEGER
               ACCESS  read-write
               STATUS  mandatory
               DESCRIPTION
               "WCIntStatus is Warning when WCInvalidPages exceeds this value."
               ::=  {  iis5WCGroup 17  }

        iis5WCIntCriticalThreshold OBJECT-TYPE
               SYNTAX  INTEGER
               ACCESS  read-write
               STATUS  mandatory
               DESCRIPTION
               "WCIntStatus is Critical when WCInvalidPages exceeds this value."
               ::=  {  iis5WCGroup 18  }

        iis5WCWarningAction OBJECT-TYPE
               SYNTAX  DisplayString
               ACCESS  read-write
               STATUS  mandatory
               DESCRIPTION
               "Command to be executed when WCSummaryStatus increases to Warning."
               ::=  {  iis5WCGroup 19  }

        iis5WCCriticalAction OBJECT-TYPE
               SYNTAX  DisplayString
               ACCESS  read-write
               STATUS  mandatory
               DESCRIPTION
               "Command to be executed when WCSummaryStatus increases to Critical."
               ::=  {  iis5WCGroup 20   }

        iis5WCVerifyIntLink OBJECT-TYPE
               SYNTAX  INTEGER{
                               yes(1),
                               no(2)
                              }
               ACCESS  read-write
               STATUS  mandatory
               DESCRIPTION
               "Verify internal links for page status."
               ::=  {  iis5WCGroup 21   }

        iis5WCVerifyExtLink OBJECT-TYPE
               SYNTAX  INTEGER{
                               yes(1),
                               no(2)
                              }
               ACCESS  read-write
               STATUS  mandatory
               DESCRIPTION
               "Verify external links for page status."
               ::=  {  iis5WCGroup 22   }

        iis5WCVerifyTitle OBJECT-TYPE
               SYNTAX  INTEGER{
                               yes(1),
                               no(2)
                              }
               ACCESS  read-write
               STATUS  mandatory
               DESCRIPTION
               "Verify title for page status."
               ::=  {  iis5WCGroup 23   }

        iis5WCVerifyAnchors OBJECT-TYPE
               SYNTAX  INTEGER{
                               yes(1),
                               no(2)
                              }
               ACCESS  read-write
               STATUS  mandatory
               DESCRIPTION
               "Verify anchors for page status."
               ::=  {  iis5WCGroup 24   }

        iis5WCVerifyImages OBJECT-TYPE
               SYNTAX  INTEGER{
                               yes(1),
                               no(2)
                              }
               ACCESS  read-write
               STATUS  mandatory
               DESCRIPTION
               "Verify images for page status."
               ::=  {  iis5WCGroup 25   }

        iis5WCPageCount OBJECT-TYPE
               SYNTAX  INTEGER
               ACCESS  read-only
               STATUS  mandatory
               DESCRIPTION
               "Count of pages."
               ::=  {  iis5WCGroup 26  }

        iis5WCNewPageCount OBJECT-TYPE
               SYNTAX  INTEGER
               ACCESS  read-only
               STATUS  mandatory
               DESCRIPTION
               "Count of new pages."
               ::=  {  iis5WCGroup 27  }

        iis5WCSlowPageCount OBJECT-TYPE
               SYNTAX  INTEGER
               ACCESS  read-only
               STATUS  mandatory
               DESCRIPTION
               "Count of slow pages."
               ::=  {  iis5WCGroup 28  }

        iis5WCImageCount OBJECT-TYPE
               SYNTAX  INTEGER
               ACCESS  read-only
               STATUS  mandatory
               DESCRIPTION
               "Count of images."
               ::=  {  iis5WCGroup 29  }

        iis5WCImageRefCount OBJECT-TYPE
               SYNTAX  INTEGER
               ACCESS  read-only
               STATUS  mandatory
               DESCRIPTION
               "Count of image references."
               ::=  {  iis5WCGroup 30  }

        iis5WCMissingImageCount OBJECT-TYPE
               SYNTAX  INTEGER
               ACCESS  read-only
               STATUS  mandatory
               DESCRIPTION
               "Count of missing images."
               ::=  {  iis5WCGroup 31  }

        iis5WCMissingImageRefCount OBJECT-TYPE
               SYNTAX  INTEGER
               ACCESS  read-only
               STATUS  mandatory
               DESCRIPTION
               "Count of missing image references."
               ::=  {  iis5WCGroup 32  }

        iis5WCNamedAnchorCount OBJECT-TYPE
               SYNTAX  INTEGER
               ACCESS  read-only
               STATUS  mandatory
               DESCRIPTION
               "Count of named anchors."
               ::=  {  iis5WCGroup 33  }

        iis5WCNamedAnchorRefCount OBJECT-TYPE
               SYNTAX  INTEGER
               ACCESS  read-only
               STATUS  mandatory
               DESCRIPTION
               "Count of named anchor references."
               ::=  {  iis5WCGroup 34  }

        iis5WCMissingNamedAnchorCount OBJECT-TYPE
               SYNTAX  INTEGER
               ACCESS  read-only
               STATUS  mandatory
               DESCRIPTION
               "Count of missing named anchors."
               ::=  {  iis5WCGroup 35  }

        iis5WCMissingNamedAnchorRefCount OBJECT-TYPE
               SYNTAX  INTEGER
               ACCESS  read-only
               STATUS  mandatory
               DESCRIPTION
               "Count of missing named anchor references."
               ::=  {  iis5WCGroup 36  }

        iis5WCHTTPCount OBJECT-TYPE
               SYNTAX  INTEGER
               ACCESS  read-only
               STATUS  mandatory
               DESCRIPTION
               "Count of HTTP URLs."
               ::=  {  iis5WCGroup 37  }

        iis5WCFTPCount OBJECT-TYPE
               SYNTAX  INTEGER
               ACCESS  read-only
               STATUS  mandatory
               DESCRIPTION
               "Count of FTP URLs."
               ::=  {  iis5WCGroup 38  }

        iis5WCMAILCount OBJECT-TYPE
               SYNTAX  INTEGER
               ACCESS  read-only
               STATUS  mandatory
               DESCRIPTION
               "Count of MAIL URLs."
               ::=  {  iis5WCGroup 39  }

        iis5WCNEWSCount OBJECT-TYPE
               SYNTAX  INTEGER
               ACCESS  read-only
               STATUS  mandatory
               DESCRIPTION
               "Count of NEWS URLs."
               ::=  {  iis5WCGroup 40  }

        iis5WCGOPHERCount OBJECT-TYPE
               SYNTAX  INTEGER
               ACCESS  read-only
               STATUS  mandatory
               DESCRIPTION
               "Count of GOPHER URLs."
               ::=  {  iis5WCGroup 41  }

        iis5WCFILECount OBJECT-TYPE
               SYNTAX  INTEGER
               ACCESS  read-only
               STATUS  mandatory
               DESCRIPTION
               "Count of FILE URLs."
               ::=  {  iis5WCGroup 42  }

        iis5WCThrottle OBJECT-TYPE
               SYNTAX  INTEGER{
                               fast(1),
                               background(2)
                              }
               ACCESS  read-write
               STATUS  mandatory
               DESCRIPTION
               "Control CPU usage."
               ::=  {  iis5WCGroup 43   }

        iis5WCProxy OBJECT-TYPE
               SYNTAX  DisplayString
               ACCESS  read-write
               STATUS  mandatory
               DESCRIPTION
               "Proxy server to use when checking external URLs"
               ::=  {  iis5WCGroup 44  }

        iis5WCReportType OBJECT-TYPE
               SYNTAX  INTEGER{
                               local(1),
                               remote(2)
                              }
               ACCESS  read-write
               STATUS  mandatory
               DESCRIPTION
               "Specify if report is local file or remote browse URL."
               ::=  {  iis5WCGroup 45   }

        iis5WCTimeoutExternal OBJECT-TYPE
               SYNTAX  INTEGER
               ACCESS  read-write
               STATUS  mandatory
               DESCRIPTION
               "Specify time to wait when checking an external URL"
               ::=  {  iis5WCGroup 46   }

        iis5WCOldPageDays OBJECT-TYPE
               SYNTAX  INTEGER
               ACCESS  read-write
               STATUS  mandatory
               DESCRIPTION
               "Days previous to current that will be used by WebCrawler to determine old pages."
               ::=  {  iis5WCGroup 47   }

        iis5WCOldPageCount OBJECT-TYPE
               SYNTAX  INTEGER
               ACCESS  read-only
               STATUS  mandatory
               DESCRIPTION
               "Count of old pages."
               ::=  {  iis5WCGroup 48  }

        iis5WCTable OBJECT-TYPE
               SYNTAX  SEQUENCE OF Iis5WCEntry
               ACCESS  not-accessible
               STATUS  mandatory
               DESCRIPTION
               "This table contains missing URL links found by WebCrawler."
               ::=  {  iis5WCGroup 49  }

        iis5WCReset OBJECT-TYPE
               SYNTAX  INTEGER{
                               reset(1)
                              }
               ACCESS  read-write
               STATUS  mandatory
               DESCRIPTION
               "Count of old pages."
               ::=  { iis5WCGroup 50  }

        iis5WCEntry OBJECT-TYPE
               SYNTAX  Iis5WCEntry
               ACCESS  not-accessible
               STATUS  mandatory
               DESCRIPTION
               "This is an entry in the WCTable"
               INDEX { iis5WCURL }
               ::=  { iis5WCTable 1 }

        Iis5WCEntry ::= SEQUENCE
        {
           iis5WCURL                      DisplayString,
           iis5WCReferences               INTEGER,
           iis5WCBadIntLink               INTEGER,
           iis5WCBadExtLink               INTEGER,
           iis5WCTitle                    INTEGER,
           iis5WCBadAnchors               INTEGER,
           iis5WCBadImages                INTEGER,
           iis5WCAccessTS                 DisplayString
        }

        iis5WCURL OBJECT-TYPE
               SYNTAX  DisplayString
               ACCESS  read-only
               STATUS  mandatory
               DESCRIPTION
               "Bad URL."
               ::=  {  iis5WCEntry 1   }

        iis5WCReferences OBJECT-TYPE
               SYNTAX  INTEGER
               ACCESS  read-only
               STATUS  mandatory
               DESCRIPTION
               "Count of references to this bad URL."
               ::=  {  iis5WCEntry 2   }

        iis5WCBadIntLink OBJECT-TYPE
               SYNTAX  INTEGER
               ACCESS  read-only
               STATUS  mandatory
               DESCRIPTION
               "Count of bad internal Links."
               ::=  {  iis5WCEntry 3   }

        iis5WCBadExtLink OBJECT-TYPE
               SYNTAX  INTEGER
               ACCESS  read-only
               STATUS  mandatory
               DESCRIPTION
               "Count of bad external Links."
               ::=  {  iis5WCEntry 4   }

        iis5WCTitle OBJECT-TYPE
               SYNTAX  INTEGER{
                               ok(1),
                               missing(2)
                              }
               ACCESS  read-only
               STATUS  mandatory
               DESCRIPTION
               "Does page have title."
               ::=  {  iis5WCEntry 5   }

        iis5WCBadAnchors OBJECT-TYPE
               SYNTAX  INTEGER
               ACCESS  read-only
               STATUS  mandatory
               DESCRIPTION
               "Count of bad anchors on page."
               ::=  {  iis5WCEntry 6   }

        iis5WCBadImages OBJECT-TYPE
               SYNTAX  INTEGER
               ACCESS  read-only
               STATUS  mandatory
               DESCRIPTION
               "Count of bad images on page."
               ::=  {  iis5WCEntry 7   }

        iis5WCAccessTS OBJECT-TYPE
               SYNTAX  DisplayString
               ACCESS  read-only
               STATUS  mandatory
               DESCRIPTION
               "Time first access occurred (time row added to table)."
               ::=  {  iis5WCEntry 8   }


--******************************************************************************
--* iis5ExpressionGroup - User defined expressions                               *
--******************************************************************************

        iis5ExpressionTableEntries OBJECT-TYPE
               SYNTAX  INTEGER
               ACCESS  read-only
               STATUS  mandatory
               DESCRIPTION
               "The number of entries in the table."
               ::=  {  iis5ExpressionGroup 1   }

        iis5ExpressionInterval OBJECT-TYPE
               SYNTAX  INTEGER
               ACCESS  read-write
               STATUS  mandatory
               DESCRIPTION
               "Seconds between polls for the counter."
               ::=  {  iis5ExpressionGroup 2   }

        iis5ExpressionCalcInterval OBJECT-TYPE
               SYNTAX  INTEGER
               ACCESS  read-write
               STATUS  mandatory
               DESCRIPTION
               "Interval in seconds over which the counter is measured."
               ::=  {  iis5ExpressionGroup 3   }

--      Update this comment.
--      Add a counter to the table.  The value must include at least the first four of
--      the 6 items listed, separated by commas.
--      <iis5URLAvailCounterDescription> is a value from iis5URLAvailCounterDescription in iis5URLAvailCounterTable.

        iis5ExpressionAdd OBJECT-TYPE
               SYNTAX  DisplayString
               ACCESS  write-only
               STATUS  mandatory
               DESCRIPTION
               "Add this entry to the table."
               ::=  {  iis5ExpressionGroup 4   }

--      Delete a counter from the table.  The value must include the 2 items listed.
        iis5ExpressionDelete OBJECT-TYPE
               SYNTAX  DisplayString
               ACCESS  write-only
               STATUS  mandatory
               DESCRIPTION
               "Delete entry from the table: <ExpressionDesc>,<Expression>."
               ::=  {  iis5ExpressionGroup 5   }

--      For future use with bulk load.  Currently ignored.
        iis5ExpressionUpdate OBJECT-TYPE
               SYNTAX  DisplayString
               ACCESS  write-only
               STATUS  mandatory
               DESCRIPTION
               "Reserved for future use."
               ::=  {  iis5ExpressionGroup 6   }

        iis5ExpressionSummaryStatus OBJECT-TYPE
               SYNTAX  INTEGER {
                                normal(1),
                                warning(2),
                                critical(3)
                               }
               ACCESS  read-only
               STATUS  mandatory
               DESCRIPTION
               "Most severe status of all rows in the table."
               ::=  {  iis5ExpressionGroup 7   }

        iis5ExpressionTable OBJECT-TYPE
               SYNTAX  SEQUENCE OF Iis5ExpressionEntry
               ACCESS  not-accessible
               STATUS  mandatory
               DESCRIPTION
               "This table contains a list of expressions to monitor."
               ::=  {  iis5ExpressionGroup 8}

        iis5ExpressionEntry OBJECT-TYPE
               SYNTAX  Iis5ExpressionEntry
               ACCESS  not-accessible
               STATUS  mandatory
               DESCRIPTION
               "This is an entry in the ExpressionTable"
               INDEX { iis5ExpressionIdentifier}
               ::=  { iis5ExpressionTable 1 }

        Iis5ExpressionEntry ::= SEQUENCE
        {
           iis5Expression                                    DisplayString,
           iis5ExpressionDesc                                DisplayString,
           iis5ExpressionValue                               DisplayString,
           iis5ExpressionWarningThreshold                    INTEGER,
           iis5ExpressionCriticalThreshold                   INTEGER,
           iis5ExpressionWarningAction                       DisplayString,
           iis5ExpressionCriticalAction                      DisplayString,
           iis5ExpressionStatus                              INTEGER,
           iis5ExpressionEnableDisable                       INTEGER,
           iis5ExpressionDescending                          INTEGER,
           iis5ExpressionResultType                          INTEGER,
           iis5ExpressionBooleanAlertLevel                   INTEGER,
           iis5ExpressionEvalErrorAlertLevel                 INTEGER,
           iis5ExpressionNumericMonitor                      INTEGER,
           iis5ExpressionEntryInterval                       INTEGER,
           iis5ExpressionReset                               INTEGER,
           iis5ExpressionResetTime                           DisplayString,
           iis5ExpressionEntryWarningCount                   INTEGER,
           iis5ExpressionEntryCriticalCount                  INTEGER,
           iis5ExpressionIdentifier                          DisplayString,
           iis5ExpressionErrorMsg                            DisplayString,
           iis5ExpressionEvalStatus                          INTEGER,
           iis5ExpressionBoolAlertCondition                  INTEGER,
	   iis5ExpressionLagSetting	                   INTEGER,
	   iis5ExpressionLagValue	                           INTEGER
        }

--     Changed from read only to read write to allow introducing evaluation errors
        iis5Expression OBJECT-TYPE
               SYNTAX  DisplayString
               ACCESS  read-write
               STATUS  mandatory
               DESCRIPTION
               "Expression to be monitored."
               ::=  {  iis5ExpressionEntry 1   }

        iis5ExpressionDesc OBJECT-TYPE
               SYNTAX  DisplayString
               ACCESS  read-write
               STATUS  mandatory
               DESCRIPTION
               "Description of the monitored expression."
               ::=  {  iis5ExpressionEntry 2   }

        iis5ExpressionValue OBJECT-TYPE
               SYNTAX  DisplayString
               ACCESS  read-only
               STATUS  mandatory
               DESCRIPTION
               "Expression evaluation."
               ::=  {  iis5ExpressionEntry 3   }

        iis5ExpressionWarningThreshold OBJECT-TYPE
               SYNTAX  INTEGER
               ACCESS  read-write
               STATUS  mandatory
               DESCRIPTION
               "Warning threshold"
               ::=  {  iis5ExpressionEntry 4   }

        iis5ExpressionCriticalThreshold OBJECT-TYPE
               SYNTAX  INTEGER
               ACCESS  read-write
               STATUS  mandatory
               DESCRIPTION
               "Critical threshold"
               ::=  {  iis5ExpressionEntry 5   }

        iis5ExpressionWarningAction OBJECT-TYPE
               SYNTAX  DisplayString
               ACCESS  read-write
               STATUS  mandatory
               DESCRIPTION
               "Command to be executed when warning threshold is exceeded."
               ::=  {  iis5ExpressionEntry 6   }

        iis5ExpressionCriticalAction OBJECT-TYPE
               SYNTAX  DisplayString
               ACCESS  read-write
               STATUS  mandatory
               DESCRIPTION
               "Command to be executed when critical threshold is exceeded."
               ::=  {  iis5ExpressionEntry 7  }

        iis5ExpressionStatus OBJECT-TYPE
               SYNTAX  INTEGER {
                                normal(1),
                                warning(2),
                                critical(3)
                               }
               ACCESS  read-only
               STATUS  mandatory
               DESCRIPTION
               "Status of this expression."
               ::=  {  iis5ExpressionEntry 8 }

        iis5ExpressionEnableDisable OBJECT-TYPE
                SYNTAX  INTEGER
                {
                    enable(1),
                    disable(2)
                }
                ACCESS  read-write
                STATUS  mandatory
                DESCRIPTION
                "Enable or disable alerts for this expression."
                ::=  {  iis5ExpressionEntry 9   }

        iis5ExpressionDescending OBJECT-TYPE
               SYNTAX  INTEGER {
                                no(1),
                                yes(2)
                               }
               ACCESS  read-only
               STATUS  mandatory
               DESCRIPTION
               "Yes if lower value triggers thresholds."
               ::=  {  iis5ExpressionEntry 10 }


        iis5ExpressionResultType OBJECT-TYPE
               SYNTAX  INTEGER {
                                numeric(1),
                                boolean(2)
                               }
               ACCESS  read-only
               STATUS  mandatory
               DESCRIPTION
               "Result type of expression."
               ::=  {  iis5ExpressionEntry 11 }

        iis5ExpressionBooleanAlertLevel OBJECT-TYPE
                SYNTAX INTEGER {
                                warning-on-false(1),
                                critical-on-false(2)
                               }
                ACCESS read-write
                STATUS mandatory
                DESCRIPTION
                "Flag indicating for boolean expressions the level of alert to raise on false."
                DEFVAL { 2 }
                ::= { iis5ExpressionEntry 12 }

        iis5ExpressionEvalErrorAlertLevel OBJECT-TYPE
                SYNTAX INTEGER {
                                do-not-monitor(1),
                                warning-on-error(2),
                                critical-on-error(3)
                               }
                ACCESS read-write
                STATUS mandatory
                DESCRIPTION
                "Flag indicating the level of alert to raise on an evaluation error."
                DEFVAL { 3 }
                ::= { iis5ExpressionEntry 13 }

        iis5ExpressionNumericMonitor OBJECT-TYPE
                SYNTAX INTEGER {
                                warning-only(1),
                                critical-only(2),
                                both(3)
                               }
                ACCESS read-write
                STATUS mandatory
                DESCRIPTION
                "Flag indicating for numeric expressions which thresholds should be evaluated."
                DEFVAL { 3 }
                ::= { iis5ExpressionEntry 14 }

        iis5ExpressionEntryInterval OBJECT-TYPE
               SYNTAX  INTEGER
               ACCESS  read-write
               STATUS  mandatory
               DESCRIPTION
               "Evaluation interval for expression"
               ::=  {  iis5ExpressionEntry 15   }

        iis5ExpressionReset OBJECT-TYPE
               SYNTAX  INTEGER {
                                reset(1)
                               }
               ACCESS  write-only
               STATUS  mandatory
               DESCRIPTION
               "Reset value for this counter."
               ::=  {  iis5ExpressionEntry 16 }

        iis5ExpressionResetTime OBJECT-TYPE
               SYNTAX  DisplayString
               ACCESS  read-only
               STATUS  mandatory
               DESCRIPTION
               "Time stamp of when this counter was reset."
               ::=  {  iis5ExpressionEntry 17  }

        iis5ExpressionEntryWarningCount OBJECT-TYPE
                SYNTAX  INTEGER
                ACCESS  read-only
                STATUS  mandatory
                DESCRIPTION
                "Number of warning events since last reset."
                ::=  {  iis5ExpressionEntry 18   }

        iis5ExpressionEntryCriticalCount OBJECT-TYPE
                SYNTAX  INTEGER
                ACCESS  read-only
                STATUS  mandatory
                DESCRIPTION
                "Number of critical events since last reset."
                ::=  {  iis5ExpressionEntry 19   }

        iis5ExpressionIdentifier OBJECT-TYPE
               SYNTAX  DisplayString
               ACCESS  read-write
               STATUS  mandatory
               DESCRIPTION
               "Short identifier of the monitored expression."
               ::=  {  iis5ExpressionEntry 20   }

        iis5ExpressionErrorMsg OBJECT-TYPE
               SYNTAX  DisplayString
               ACCESS  read-write
               STATUS  mandatory
               DESCRIPTION
               "Validation or evaluation error message."
               ::=  {  iis5ExpressionEntry 21   }

        iis5ExpressionEvalStatus OBJECT-TYPE
               SYNTAX  INTEGER {
                                normal(1),
                                error(2)
                               }
               ACCESS  read-only
               STATUS  mandatory
               DESCRIPTION
               "Was this expression able to be evaluated."
               ::=  {  iis5ExpressionEntry 22 }

        iis5ExpressionBoolAlertCondition OBJECT-TYPE
               SYNTAX  INTEGER {
                                alertonfalse(1),
                                alertontrue(2)
                               }
               ACCESS  read-write
               STATUS  mandatory
               DESCRIPTION
               "Alert on true or alert on false."
               ::=  {  iis5ExpressionEntry 23 }
		
        iis5ExpressionLagSetting OBJECT-TYPE
                SYNTAX  INTEGER
                ACCESS  read-write
                STATUS  mandatory
                DESCRIPTION
                "Lag setting for the expression."
                ::=  {  iis5ExpressionEntry 24   }
		
        iis5ExpressionLagValue OBJECT-TYPE
                SYNTAX  INTEGER
                ACCESS  read-only
                STATUS  mandatory
                DESCRIPTION
                "Current Lag value for the expression."
                ::=  {  iis5ExpressionEntry 25   }

--******************************************************************************
--*  End of expressions table                                                  *
--******************************************************************************

        iis5ExpressionWarningCount OBJECT-TYPE
                SYNTAX  INTEGER
                ACCESS  read-only
                STATUS  mandatory
                DESCRIPTION
                "Number of expressions in warning state."
                DEFVAL { 0 }
                ::=  {  iis5ExpressionGroup 9   }

        iis5ExpressionCriticalCount OBJECT-TYPE
                SYNTAX  INTEGER
                ACCESS  read-only
                STATUS  mandatory
                DESCRIPTION
                "Number of expressions in critical state."
                DEFVAL { 0 }
                ::=  {  iis5ExpressionGroup 10   }

       iis5ExpressionValidate OBJECT-TYPE
               SYNTAX  DisplayString
               ACCESS  write-only
               STATUS  mandatory
               DESCRIPTION
               "Validate this entry."
               ::=  {  iis5ExpressionGroup 11   }

        iis5ExpressionEvaluate OBJECT-TYPE
               SYNTAX  DisplayString
               ACCESS  write-only
               STATUS  mandatory
               DESCRIPTION
               "Evaluate this expression."
               ::=  {  iis5ExpressionGroup 12   }

        iis5ExpressionTemp OBJECT-TYPE
               SYNTAX  DisplayString
               ACCESS  read-write
               STATUS  mandatory
               DESCRIPTION
               "Temporary storage for expression building."
               ::=  {  iis5ExpressionGroup 13   }

        iis5ExpressionVariableTable OBJECT-TYPE
               SYNTAX  SEQUENCE OF Iis5ExpressionVariableEntry
               ACCESS  not-accessible
               STATUS  mandatory
               DESCRIPTION
               "This table contains a list of expressions to monitor."
               ::=  {  iis5ExpressionGroup 14}

        iis5ExpressionVariableEntry OBJECT-TYPE
               SYNTAX  Iis5ExpressionVariableEntry
               ACCESS  not-accessible
               STATUS  mandatory
               DESCRIPTION
               "This is an entry in the ExpressionVariableTable"
               INDEX { iis5ExpressionVariableDisplayName}
               ::=  { iis5ExpressionVariableTable 1 }

        Iis5ExpressionVariableEntry ::= SEQUENCE
        {
           iis5ExpressionVariableDisplayName        DisplayString,
           iis5ExpressionVariableAccessName         DisplayString,
           iis5ExpressionVariableGroup              DisplayString
        }

       iis5ExpressionVariableDisplayName OBJECT-TYPE
               SYNTAX  DisplayString
               ACCESS  read-only
               STATUS  mandatory
               DESCRIPTION
               "Expression variable displayed in list."
               ::=  {  iis5ExpressionVariableEntry 1   }

       iis5ExpressionVariableAccessName OBJECT-TYPE
               SYNTAX  DisplayString
               ACCESS  read-only
               STATUS  mandatory
               DESCRIPTION
               "Expression variable used to access MIB entry."
               ::=  {  iis5ExpressionVariableEntry 2   }

        iis5ExpressionVariableGroup OBJECT-TYPE
               SYNTAX  DisplayString
               ACCESS  read-only
               STATUS  mandatory
               DESCRIPTION
               "MIB group where the variable is stored."
               ::=  {  iis5ExpressionVariableEntry 3   }

--******************************************************************************
--*  End of expression variables table                                         *
--******************************************************************************

       iis5ExpressionVariableTableEntries OBJECT-TYPE
               SYNTAX  INTEGER
               ACCESS  read-only
               STATUS  mandatory
               DESCRIPTION
               "The number of entries in the variables table."
               ::=  {  iis5ExpressionGroup 15   }

       iis5ExpressionBuild OBJECT-TYPE
               SYNTAX  DisplayString
               ACCESS  write-only
               STATUS  mandatory
               DESCRIPTION
               "Add this variable to the expression."
               ::=  {  iis5ExpressionGroup 16   }

        iis5ExpressionTempValue OBJECT-TYPE
               SYNTAX  DisplayString
               ACCESS  read-write
               STATUS  mandatory
               DESCRIPTION
               "Temporary storage for result of expression validation or evaluation."
               ::=  {  iis5ExpressionGroup 17   }


        iis5ExpressionClear OBJECT-TYPE
               SYNTAX  INTEGER {
                                donotclear(1),
                                clear(2)
                               }
               ACCESS  read-only
               STATUS  mandatory
               DESCRIPTION
               "Clear the variables in the gui"
               ::=  {  iis5ExpressionGroup 18 }

--******************************************************************************
--*  Start of global expression variables table                                *
--******************************************************************************

        iis5ExpressionGlobalVariableTableEntries OBJECT-TYPE
               SYNTAX  INTEGER
               ACCESS  read-only
               STATUS  mandatory
               DESCRIPTION
               "The number of entries in the global variables table."
               ::=  {  iis5ExpressionGroup 19   }

        iis5ExpressionGlobalVariableTableAdd OBJECT-TYPE
               SYNTAX  DisplayString
               ACCESS  write-only
               STATUS  mandatory
               DESCRIPTION
               "Add this entry to the global variables table."
               ::=  {  iis5ExpressionGroup 20   }

--      Delete a counter from the table.  The value must include the 2 items listed.
        iis5ExpressionGlobalVariableTableDelete OBJECT-TYPE
               SYNTAX  DisplayString
               ACCESS  write-only
               STATUS  mandatory
               DESCRIPTION
               "Delete entry from the global varialbles table."
               ::=  {  iis5ExpressionGroup 21   }

        iis5ExpressionGlobalVariableTable OBJECT-TYPE
               SYNTAX  SEQUENCE OF Iis5ExpressionGlobalVariableEntry
               ACCESS  not-accessible
               STATUS  mandatory
               DESCRIPTION
               "This table contains a list of global variables used in expressions."
               ::=  {  iis5ExpressionGroup 22}

        iis5ExpressionGlobalVariableEntry OBJECT-TYPE
               SYNTAX  Iis5ExpressionGlobalVariableEntry
               ACCESS  not-accessible
               STATUS  mandatory
               DESCRIPTION
               "This is an entry in the ExpressionGlobalVariableTable"
               INDEX { iis5ExpressionGlobalVariableName}
               ::=  { iis5ExpressionGlobalVariableTable 1 }

        Iis5ExpressionGlobalVariableEntry ::= SEQUENCE
        {
           iis5ExpressionGlobalVariableName                DisplayString,
           iis5ExpressionGlobalVariableDisplayName         DisplayString,
           iis5ExpressionGlobalVariableDescription         DisplayString,
           iis5ExpressionGlobalVariableAccessKey           DisplayString,
           iis5ExpressionGlobalVariableType                DisplayString,
           iis5ExpressionGlobalVariablePollIntervalPeriod  INTEGER,
           iis5ExpressionGlobalVariableFunctionName        DisplayString,
           iis5ExpressionGlobalVariableFunctionTimePeriod  INTEGER
        }

        iis5ExpressionGlobalVariableName OBJECT-TYPE
               SYNTAX  DisplayString
               ACCESS  read-only
               STATUS  mandatory
               DESCRIPTION
               "Expression global variable name."
               ::=  {  iis5ExpressionGlobalVariableEntry 1   }

        iis5ExpressionGlobalVariableDisplayName OBJECT-TYPE
               SYNTAX  DisplayString
               ACCESS  read-only
               STATUS  mandatory
               DESCRIPTION
               "Expression global variable display name."
               ::=  {  iis5ExpressionGlobalVariableEntry 2   }

        iis5ExpressionGlobalVariableDescription OBJECT-TYPE
               SYNTAX  DisplayString
               ACCESS  read-only
               STATUS  mandatory
               DESCRIPTION
               "Expression global variable description."
               ::=  {  iis5ExpressionGlobalVariableEntry 3   }

        iis5ExpressionGlobalVariableAccessKey OBJECT-TYPE
               SYNTAX  DisplayString
               ACCESS  read-only
               STATUS  mandatory
               DESCRIPTION
               "Expression global variable key to access counter."
               ::=  {  iis5ExpressionGlobalVariableEntry 4   }

        iis5ExpressionGlobalVariableType OBJECT-TYPE
               SYNTAX  DisplayString
               ACCESS  read-only
               STATUS  mandatory
               DESCRIPTION
               "Expression global variable - interval or time variable."
               ::=  {  iis5ExpressionGlobalVariableEntry 5   }

        iis5ExpressionGlobalVariablePollIntervalPeriod OBJECT-TYPE
               SYNTAX  INTEGER
               ACCESS  read-only
               STATUS  mandatory
               DESCRIPTION
               "Expression global variable poll interval for interval type."
               ::=  {  iis5ExpressionGlobalVariableEntry 6   }

        iis5ExpressionGlobalVariableFunctionName OBJECT-TYPE
               SYNTAX  DisplayString
               ACCESS  read-only
               STATUS  mandatory
               DESCRIPTION
               "Expression global variable function name."
               ::=  {  iis5ExpressionGlobalVariableEntry 7   }

        iis5ExpressionGlobalVariableFunctionTimePeriod OBJECT-TYPE
               SYNTAX  INTEGER
               ACCESS  read-only
               STATUS  mandatory
               DESCRIPTION
               "Expression global variable function time period."
               ::=  {  iis5ExpressionGlobalVariableEntry 8   }

--******************************************************************************
--*  End of global expression variables table                                  *
--******************************************************************************

       iis5ExpressionGlobalVariableBuild OBJECT-TYPE
               SYNTAX  DisplayString
               ACCESS  write-only
               STATUS  mandatory
               DESCRIPTION
               "Add an access key to the variable using a friendly name."
               ::=  {  iis5ExpressionGroup 23   }

        iis5ExpressionGlobalVariableClear OBJECT-TYPE
               SYNTAX  INTEGER {
                                donotclear(1),
                                clear(2)
                               }
               ACCESS  read-only
               STATUS  mandatory
               DESCRIPTION
               "Clear the variables in the gui"
               ::=  {  iis5ExpressionGroup 24 }

        iis5ExpressionGlobalVariableTemp OBJECT-TYPE
               SYNTAX  DisplayString
               ACCESS  read-write
               STATUS  mandatory
               DESCRIPTION
               "Temporary storage for variable access key."
               ::=  {  iis5ExpressionGroup 25   }

        iis5ExpressionGlobalVariableTableModify OBJECT-TYPE
               SYNTAX  DisplayString
               ACCESS  write-only
               STATUS  mandatory
               DESCRIPTION
               "Modify entry in the global varialbles table."
               ::=  {  iis5ExpressionGroup 26   }

	iis5ExpressionGPEnaDis OBJECT-TYPE
		SYNTAX      INTEGER {enable(1), disable(2)}
		ACCESS      read-write
		STATUS      mandatory
		DESCRIPTION "Enable or disable for the Group."
		::= { iis5ExpressionGroup 27 }


--******************************************************************************
--* iis5DetailGroup - Detail table                                              *
--******************************************************************************

        iis5DetailTableEntries OBJECT-TYPE
                SYNTAX  INTEGER
                ACCESS  read-only
                STATUS  mandatory
                DESCRIPTION
                "The number of entries in the table."
                ::=  {  iis5DetailGroup 1   }

        iis5DetailRequest OBJECT-TYPE
                SYNTAX  DisplayString
                ACCESS  write-only
                STATUS  mandatory
                DESCRIPTION
                "Generate Detail table for this request."
                ::=  {  iis5DetailGroup 2   }


        iis5DetailTable OBJECT-TYPE
                SYNTAX  SEQUENCE OF Iis5DetailEntry
                ACCESS  not-accessible
                STATUS  mandatory
                DESCRIPTION
                "The list of details."
                ::=  {  iis5DetailGroup 3}

        iis5DetailEntry OBJECT-TYPE
                 SYNTAX  Iis5DetailEntry
                 ACCESS  not-accessible
                 STATUS  mandatory
                 DESCRIPTION
                 "The DetailTable entry."
                 INDEX { iis5DetailServer }
                     ::=  { iis5DetailTable 1 }

        Iis5DetailEntry ::= SEQUENCE {
            iis5DetailServer              DisplayString,
            iis5DetailValue               DisplayString,
            iis5DetailValue2              DisplayString,
            iis5DetailValue3              DisplayString,
            iis5DetailValue4              DisplayString,
            iis5DetailValue5              DisplayString,
            iis5DetailValue6              DisplayString,
            iis5DetailValue7              DisplayString,
            iis5DetailValue8              DisplayString,
            iis5DetailValue9              DisplayString,
            iis5DetailValue10             DisplayString
        }

        iis5DetailServer OBJECT-TYPE
                SYNTAX  DisplayString
                ACCESS  read-only
                STATUS  mandatory
                DESCRIPTION
                "The Server name for the entry."
                ::=  {  iis5DetailEntry 1   }

        iis5DetailValue OBJECT-TYPE
                SYNTAX  DisplayString
                ACCESS  read-only
                STATUS  mandatory
                DESCRIPTION
                "Detail value for the server."
                ::=  {  iis5DetailEntry 2   }

        iis5DetailValue2 OBJECT-TYPE
                SYNTAX  DisplayString
                ACCESS  read-only
                STATUS  mandatory
                DESCRIPTION
                "Detail value for the server."
                ::=  {  iis5DetailEntry 3   }

        iis5DetailValue3 OBJECT-TYPE
                SYNTAX  DisplayString
                ACCESS  read-only
                STATUS  mandatory
                DESCRIPTION
                "Detail value for the server."
                ::=  {  iis5DetailEntry 4   }

        iis5DetailValue4 OBJECT-TYPE
                SYNTAX  DisplayString
                ACCESS  read-only
                STATUS  mandatory
                DESCRIPTION
                "Detail value for the server."
                ::=  {  iis5DetailEntry 5   }

        iis5DetailValue5 OBJECT-TYPE
                SYNTAX  DisplayString
                ACCESS  read-only
                STATUS  mandatory
                DESCRIPTION
                "Detail value for the server."
                ::=  {  iis5DetailEntry 6   }

        iis5DetailValue6 OBJECT-TYPE
                SYNTAX  DisplayString
                ACCESS  read-only
                STATUS  mandatory
                DESCRIPTION
                "Detail value for the server."
                ::=  {  iis5DetailEntry 7   }

        iis5DetailValue7 OBJECT-TYPE
                SYNTAX  DisplayString
                ACCESS  read-only
                STATUS  mandatory
                DESCRIPTION
                "Detail value for the server."
                ::=  {  iis5DetailEntry 8   }

        iis5DetailValue8 OBJECT-TYPE
                SYNTAX  DisplayString
                ACCESS  read-only
                STATUS  mandatory
                DESCRIPTION
                "Detail value for the server."
                ::=  {  iis5DetailEntry 9   }

        iis5DetailValue9 OBJECT-TYPE
                SYNTAX  DisplayString
                ACCESS  read-only
                STATUS  mandatory
                DESCRIPTION
                "Detail value for the server."
                ::=  {  iis5DetailEntry 10   }

        iis5DetailValue10 OBJECT-TYPE
                SYNTAX  DisplayString
                ACCESS  read-only
                STATUS  mandatory
                DESCRIPTION
                "Detail value for the server."
                ::=  {  iis5DetailEntry 11   }

        iis5DetailHeading OBJECT-TYPE
                SYNTAX  DisplayString
                ACCESS  read-only
                STATUS  mandatory
                DESCRIPTION
                "The heading for the table."
                ::=  {  iis5DetailGroup 4   }




--******************************************************************************
--* iis5VHGroup - Virtual Hosts Group                                            *
--******************************************************************************


        iis5VHTableEntries OBJECT-TYPE
                SYNTAX  INTEGER
                ACCESS  read-only
                STATUS  mandatory
                DESCRIPTION
                "The number of entries in the VH table."
                ::=  {  iis5VHGroup 1   }

        iis5VHRequest OBJECT-TYPE
                SYNTAX  DisplayString
                ACCESS  read-write
                STATUS  mandatory
                DESCRIPTION
                "VH request description."
                ::=  {  iis5VHGroup 2   }

--*     List Section

        iis5VHTable OBJECT-TYPE
                SYNTAX  SEQUENCE OF Iis5VHEntry
                ACCESS  not-accessible
                STATUS  mandatory
                DESCRIPTION
                "The list of details."
                ::=  {  iis5VHGroup 3}

        iis5VHEntry OBJECT-TYPE
                 SYNTAX  Iis5VHEntry
                 ACCESS  not-accessible
                 STATUS  mandatory
                 DESCRIPTION
                 "The VHTable entry."
                 INDEX { iis5VHID }
                     ::=  { iis5VHTable 1 }

        Iis5VHEntry ::= SEQUENCE {
            iis5VHID                  INTEGER,
            iis5VHServer              DisplayString,
            iis5VHValue               DisplayString,
            iis5VHValue2              DisplayString,
            iis5VHValue3              DisplayString,
            iis5VHValue4              DisplayString,
            iis5VHValue5              DisplayString,
            iis5VHValue6              DisplayString,
            iis5VHValue7              DisplayString,
            iis5VHValue8              DisplayString,
            iis5VHValue9              DisplayString,
            iis5VHValue10             DisplayString
        }

	iis5VHID OBJECT-TYPE
		SYNTAX      INTEGER
		ACCESS      read-only
		STATUS      mandatory
		DESCRIPTION "A unique ID."
		::= {iis5VHEntry 1}
      
        iis5VHServer OBJECT-TYPE
                SYNTAX  DisplayString
                ACCESS  read-only
                STATUS  mandatory
                DESCRIPTION
                "The Server name for the entry."
                ::=  {  iis5VHEntry 2   }

        iis5VHValue OBJECT-TYPE
                SYNTAX  DisplayString
                ACCESS  read-only
                STATUS  mandatory
                DESCRIPTION
                "VH value for the server."
                ::=  {  iis5VHEntry 3   }

        iis5VHValue2 OBJECT-TYPE
                SYNTAX  DisplayString
                ACCESS  read-only
                STATUS  mandatory
                DESCRIPTION
                "VH value for the server."
                ::=  {  iis5VHEntry 4   }

        iis5VHValue3 OBJECT-TYPE
                SYNTAX  DisplayString
                ACCESS  read-only
                STATUS  mandatory
                DESCRIPTION
                "VH value for the server."
                ::=  {  iis5VHEntry 5   }

        iis5VHValue4 OBJECT-TYPE
                SYNTAX  DisplayString
                ACCESS  read-only
                STATUS  mandatory
                DESCRIPTION
                "VH value for the server."
                ::=  {  iis5VHEntry 6   }

        iis5VHValue5 OBJECT-TYPE
                SYNTAX  DisplayString
                ACCESS  read-only
                STATUS  mandatory
                DESCRIPTION
                "VH value for the server."
                ::=  {  iis5VHEntry 7   }

        iis5VHValue6 OBJECT-TYPE
                SYNTAX  DisplayString
                ACCESS  read-only
                STATUS  mandatory
                DESCRIPTION
                "VH value for the server."
                ::=  {  iis5VHEntry 8   }

        iis5VHValue7 OBJECT-TYPE
                SYNTAX  DisplayString
                ACCESS  read-only
                STATUS  mandatory
                DESCRIPTION
                "VH value for the server."
                ::=  {  iis5VHEntry 9   }

        iis5VHValue8 OBJECT-TYPE
                SYNTAX  DisplayString
                ACCESS  read-only
                STATUS  mandatory
                DESCRIPTION
                "VH value for the server."
                ::=  {  iis5VHEntry 10   }

        iis5VHValue9 OBJECT-TYPE
                SYNTAX  DisplayString
                ACCESS  read-only
                STATUS  mandatory
                DESCRIPTION
                "VH value for the server."
                ::=  {  iis5VHEntry 11   }

        iis5VHValue10 OBJECT-TYPE
                SYNTAX  DisplayString
                ACCESS  read-only
                STATUS  mandatory
                DESCRIPTION
                "VH value for the server."
                ::=  {  iis5VHEntry 12   }


--*     Health section

        iis5VHSHSummaryStatus OBJECT-TYPE
               SYNTAX  INTEGER {
                                normal(1),
                                warning(2),
                                critical(3)
                                }
               ACCESS  read-only
               STATUS  mandatory
               DESCRIPTION
               "Summary status for group."
                ::=  {  iis5VHGroup 4}

        iis5VHSHReqRate OBJECT-TYPE
               SYNTAX  INTEGER
               ACCESS  read-only
               STATUS  mandatory
               DESCRIPTION
               "Requests per second."
                ::=  {  iis5VHGroup 5}

        iis5VHSHReqRateWarningThreshold OBJECT-TYPE
               SYNTAX  INTEGER
               ACCESS  read-write
               STATUS  mandatory
               DESCRIPTION
               "Generate a warning if SHReqRate exceeds this."
                ::=  {  iis5VHGroup 6}

        iis5VHSHReqRateCriticalThreshold OBJECT-TYPE
               SYNTAX  INTEGER
               ACCESS  read-write
               STATUS  mandatory
               DESCRIPTION
               "Generate a critical if SHReqRate exceeds this."
                ::=  {  iis5VHGroup 7}

        iis5VHSHByteRate OBJECT-TYPE
               SYNTAX  INTEGER
               ACCESS  read-only
               STATUS  mandatory
               DESCRIPTION
               "Kilobytes transferred per second."
                ::=  {  iis5VHGroup 8}

        iis5VHSHByteRateWarningThreshold OBJECT-TYPE
               SYNTAX  INTEGER
               ACCESS  read-write
               STATUS  mandatory
               DESCRIPTION
               "Generate a warning if SHByteRate exceeds this."
                ::=  {  iis5VHGroup 9}

        iis5VHSHByteRateCriticalThreshold OBJECT-TYPE
               SYNTAX  INTEGER
               ACCESS  read-write
               STATUS  mandatory
               DESCRIPTION
               "Generate a critical if SHByteRate exceeds this."
                ::=  {  iis5VHGroup 10}

        iis5VHSHWarningAction OBJECT-TYPE
               SYNTAX  DisplayString
               ACCESS  read-write
               STATUS  mandatory
               DESCRIPTION
               "Command to be executed when any warning threshold is exceeded."
                ::=  {  iis5VHGroup 11}

        iis5VHSHCriticalAction OBJECT-TYPE
               SYNTAX  DisplayString
               ACCESS  read-write
               STATUS  mandatory
               DESCRIPTION
               "Command to be executed when any critical threshold is exceeded."
                ::=  {  iis5VHGroup 12}

        iis5VHSHTotalHits OBJECT-TYPE
               SYNTAX  INTEGER
               ACCESS  read-only
               STATUS  mandatory
               DESCRIPTION
               "Totals requests."
                ::=  {  iis5VHGroup 13}

        iis5VHSHTotalErrors OBJECT-TYPE
               SYNTAX  INTEGER
               ACCESS  read-only
               STATUS  mandatory
               DESCRIPTION
               "Totals error requests."
                ::=  {  iis5VHGroup 14}

        iis5VHSHTotalGETS OBJECT-TYPE
               SYNTAX  INTEGER
               ACCESS  read-only
               STATUS  mandatory
               DESCRIPTION
               "Totals GET requests."
                ::=  {  iis5VHGroup 15}

        iis5VHSHTotalPOSTS OBJECT-TYPE
               SYNTAX  INTEGER
               ACCESS  read-only
               STATUS  mandatory
               DESCRIPTION
               "Totals POST requests."
                ::=  {  iis5VHGroup 16}

        iis5VHSHTotalHEADS OBJECT-TYPE
               SYNTAX  INTEGER
               ACCESS  read-only
               STATUS  mandatory
               DESCRIPTION
               "Totals HEAD requests."
                ::=  {  iis5VHGroup 17}

        iis5VHSHTotalCGI OBJECT-TYPE
               SYNTAX  INTEGER
               ACCESS  read-only
               STATUS  mandatory
               DESCRIPTION
               "Totals CGI requests."
                ::=  {  iis5VHGroup 18}

        iis5VHSHMaxReqRate OBJECT-TYPE
               SYNTAX  INTEGER
               ACCESS  read-write
               STATUS  mandatory
               DESCRIPTION
               "Max value for the abrowser max requests scale."
                ::=  {  iis5VHGroup 19}

        iis5VHSHMaxByteRate OBJECT-TYPE
               SYNTAX  INTEGER
               ACCESS  read-write
               STATUS  mandatory
               DESCRIPTION
               "Max value for the abrowser max bytes scale."
                ::=  {  iis5VHGroup 20}
	     
   
--*     Top URL section
 

        iis5VHTopURLCircularBuffSize OBJECT-TYPE
               SYNTAX  INTEGER
               ACCESS  read-write
               STATUS  mandatory
               DESCRIPTION
               "Max entries in the table (default 50)."
               ::=  {  iis5VHGroup 21   }

        iis5VHTopURLExclude OBJECT-TYPE
               SYNTAX  DisplayString
               ACCESS  read-write
               STATUS  mandatory
               DESCRIPTION
               "Exclude URLs with these extensions."
               ::=  {  iis5VHGroup 22   }

        iis5VHTopURLTable OBJECT-TYPE
               SYNTAX  SEQUENCE OF Iis5VHTopURLEntry
               ACCESS  not-accessible
               STATUS  mandatory
               DESCRIPTION
               "This table contains a list of the top URLs by hit count."
               ::=  {  iis5VHGroup 23}

        iis5VHTopURLEntry OBJECT-TYPE
               SYNTAX  Iis5VHTopURLEntry
               ACCESS  not-accessible
               STATUS  mandatory
               DESCRIPTION
               "This is an entry in the VHTopURLTable"
               INDEX { iis5VHTopURLID}
               ::=  { iis5VHTopURLTable 1 }

        Iis5VHTopURLEntry ::= SEQUENCE
        {
           iis5VHTopURLID           INTEGER,
           iis5VHTopURLURL          DisplayString,
           iis5VHTopURLNumHits      INTEGER
        }

	iis5VHTopURLID OBJECT-TYPE
		SYNTAX      INTEGER
		ACCESS      read-only
		STATUS      mandatory
		DESCRIPTION "A unique ID."
		::= {iis5VHTopURLEntry 1}
		
        iis5VHTopURLURL OBJECT-TYPE
               SYNTAX  DisplayString
               ACCESS  read-only
               STATUS  mandatory
               DESCRIPTION
               "URL."
               ::=  {  iis5VHTopURLEntry 2   }

        iis5VHTopURLNumHits OBJECT-TYPE
               SYNTAX  INTEGER
               ACCESS  read-only
               STATUS  mandatory
               DESCRIPTION
               "Number of hits."
               ::=  {  iis5VHTopURLEntry 3   }


        iis5VHTopURLTableEntries OBJECT-TYPE
               SYNTAX  INTEGER
               ACCESS  read-only
               STATUS  mandatory
               DESCRIPTION
               "The number of entries in the table."
               ::=  {  iis5VHGroup 24   }

        iis5VHTopURLClearTable OBJECT-TYPE
               SYNTAX  INTEGER {
                                reset(1)
                               }
               ACCESS  read-write
               STATUS  mandatory
               DESCRIPTION
               "Clear the table when set."
               ::=  {  iis5VHGroup 25   }

        iis5VHTopURLExcludeReset OBJECT-TYPE
               SYNTAX  INTEGER {
                                reset(1)
                               }
               ACCESS  read-write
               STATUS  mandatory
               DESCRIPTION
               "Reset exclude list to defaults."
               ::=  {  iis5VHGroup 26   }
	       

--* BadLink section

        iis5VHBLTableEntries OBJECT-TYPE
                SYNTAX  INTEGER
                ACCESS  read-only
                STATUS  mandatory
                DESCRIPTION
                "The number of entries in the table."
                ::=  {  iis5VHGroup 27   }


        iis5VHBLClearTable OBJECT-TYPE
               SYNTAX  INTEGER {
                                reset(1)
                               }
               ACCESS  read-write
               STATUS  mandatory
               DESCRIPTION
               "Clear the table when set."
               ::=  {  iis5VHGroup 28   }

        iis5VHBLSummaryStatus OBJECT-TYPE
               SYNTAX  INTEGER {
                                normal(1),
                                warning(2),
                                critical(3)
                               }
               ACCESS  read-only
               STATUS  mandatory
               DESCRIPTION
               "Summary status for bad links."
               ::=  {  iis5VHGroup 29   }

        iis5VHBLCircularBuffSize OBJECT-TYPE
               SYNTAX  INTEGER
               ACCESS  read-write
               STATUS  mandatory
               DESCRIPTION
               "Max entries in the table (default 50)(Not a circular buffer)."
               ::=  {  iis5VHGroup 30   }

        iis5VHBLWarningThreshold OBJECT-TYPE
               SYNTAX  INTEGER
               ACCESS  read-write
               STATUS  mandatory
               DESCRIPTION
               "Number of requests on a row before warning is generated."
               ::=  {  iis5VHGroup 31   }

        iis5VHBLCriticalThreshold OBJECT-TYPE
               SYNTAX  INTEGER
               ACCESS  read-write
               STATUS  mandatory
               DESCRIPTION
               "Number of requests on a row before critical is generated."
               ::=  {  iis5VHGroup 32   }

        iis5VHBLWarningCount OBJECT-TYPE
               SYNTAX  INTEGER
               ACCESS  read-only
               STATUS  mandatory
               DESCRIPTION
               "The number of entries in the table with a warning status."
               ::=  {  iis5VHGroup 33   }

        iis5VHBLCriticalCount OBJECT-TYPE
               SYNTAX  INTEGER
               ACCESS  read-only
               STATUS  mandatory
               DESCRIPTION
               "The number of entries in the table with a critical status."
               ::=  {  iis5VHGroup 34   }

        iis5VHBLWarningAction OBJECT-TYPE
               SYNTAX  DisplayString
               ACCESS  read-write
               STATUS  mandatory
               DESCRIPTION
               "Command to be executed when warning threshold is crossed on a row."
               ::=  {  iis5VHGroup 35   }

        iis5VHBLCriticalAction OBJECT-TYPE
               SYNTAX  DisplayString
               ACCESS  read-write
               STATUS  mandatory
               DESCRIPTION
               "Command to be executed when critical threshold is crossed on a row."
               ::=  {  iis5VHGroup 36   }

        iis5VHBLCreateReportURL OBJECT-TYPE
               SYNTAX  INTEGER {
                                Create(1)
                               }
               ACCESS  read-write
               STATUS  mandatory
               DESCRIPTION
               "When triggered, create report using path and file in BLReportURL."
               ::=  {  iis5VHGroup 37   }

        iis5VHBLReportURL OBJECT-TYPE
               SYNTAX  DisplayString
               ACCESS  read-write
               STATUS  mandatory
               DESCRIPTION
               "Path and filename for report; Relative to DocumentRoot unless starts with '/'."
               ::=  {  iis5VHGroup 38   }

        iis5VHBLTable OBJECT-TYPE
               SYNTAX  SEQUENCE OF Iis5VHBLEntry
               ACCESS  not-accessible
               STATUS  mandatory
               DESCRIPTION
               "This table contains a list bad links."
               ::=  {  iis5VHGroup 39  }

        iis5VHBLEntry OBJECT-TYPE
               SYNTAX  Iis5VHBLEntry
               ACCESS  not-accessible
               STATUS  mandatory
               DESCRIPTION
               "This is an entry in the BLTable"
               INDEX { iis5VHBLID }
               ::=  { iis5VHBLTable 1 }

        Iis5VHBLEntry ::= SEQUENCE
        {
	   iis5VHBLID				  INTEGER,
           iis5VHBLURL                              DisplayString,
           iis5VHBLReferringURL                     DisplayString,
           iis5VHBLFirstAccessTS                    DisplayString,
           iis5VHBLlastAccessTS                     DisplayString,
           iis5VHBLNumRequests                      INTEGER,
           iis5VHBLStatus                           INTEGER
        }

	iis5VHBLID OBJECT-TYPE
		SYNTAX      INTEGER
		ACCESS      read-only
		STATUS      mandatory
		DESCRIPTION "A unique ID."
		::= {iis5VHBLEntry 1}
		
        iis5VHBLURL OBJECT-TYPE
               SYNTAX  DisplayString
               ACCESS  read-only
               STATUS  mandatory
               DESCRIPTION
               "Bad URL."
               ::=  {  iis5VHBLEntry 2   }

        iis5VHBLReferringURL OBJECT-TYPE
               SYNTAX  DisplayString
               ACCESS  read-only
               STATUS  mandatory
               DESCRIPTION
               "Referring URL to Bad URL."
               ::=  {  iis5VHBLEntry 3   }

        iis5VHBLFirstAccessTS OBJECT-TYPE
               SYNTAX  DisplayString
               ACCESS  read-only
               STATUS  mandatory
               DESCRIPTION
               "Time first bad access occurred (time row added to table)."
               ::=  {  iis5VHBLEntry 4   }

        iis5VHBLlastAccessTS OBJECT-TYPE
               SYNTAX  DisplayString
               ACCESS  read-only
               STATUS  mandatory
               DESCRIPTION
               "Time of last access to bad URL."
               ::=  {  iis5VHBLEntry 5   }

        iis5VHBLNumRequests OBJECT-TYPE
               SYNTAX  INTEGER
               ACCESS  read-only
               STATUS  mandatory
               DESCRIPTION
               "Count of requests."
               ::=  {  iis5VHBLEntry 6   }

        iis5VHBLStatus OBJECT-TYPE
               SYNTAX  INTEGER {
                                normal(1),
                                warning(2),
                                critical(3)
                               }
               ACCESS  read-only
               STATUS  mandatory
               DESCRIPTION
               "Summary status for BL."
               ::=  {  iis5VHBLEntry 7   }


--* VHost settings table


        iis5VHOPTTable OBJECT-TYPE
               SYNTAX  SEQUENCE OF Iis5VHOPTEntry
               ACCESS  not-accessible
               STATUS  mandatory
               DESCRIPTION
               "This table contains a list of vhost options."
               ::=  {  iis5VHGroup 40  }

        iis5VHOPTEntry OBJECT-TYPE
               SYNTAX  Iis5VHOPTEntry
               ACCESS  not-accessible
               STATUS  mandatory
               DESCRIPTION
               "This is an entry in the BLTable"
               INDEX { iis5VHOPTID }
               ::=  { iis5VHOPTTable 1 }

        Iis5VHOPTEntry ::= SEQUENCE
        {
	   iis5VHOPTID				DisplayString,
           iis5VHOPTSummaryStatus                 INTEGER,
           iis5VHOPTSHSummaryStatus               INTEGER,
           iis5VHOPTBLSummaryStatus               INTEGER,
           iis5VHOPTPUSummaryStatus               INTEGER,
           iis5VHOPTPCSummaryStatus               INTEGER,
           iis5VHOPTSHReqRateWarningThreshold     INTEGER,
           iis5VHOPTSHReqRateCriticalThreshold    INTEGER,
	   iis5VHOPTSHByteRateWarningThreshold	INTEGER,
	   iis5VHOPTSHByteRateCriticalThreshold	INTEGER,
	   iis5VHOPTSHWarningAction		DisplayString,
	   iis5VHOPTSHCriticalAction		DisplayString,
	   iis5VHOPTSHMaxReqRate			INTEGER,
	   iis5VHOPTSHMaxByteRate			INTEGER,
	   iis5VHOPTTopURLCircularBuffSize 	INTEGER,
	   iis5VHOPTTopURLExclude			DisplayString,
	   iis5VHOPTBLCircularBuffSize		INTEGER,
	   iis5VHOPTBLWarningThreshold		INTEGER,
	   iis5VHOPTBLCriticalThreshold		INTEGER,
	   iis5VHOPTBLWarningAction		DisplayString,
	   iis5VHOPTBLCriticalAction		DisplayString,
	   iis5VHOPTBLReportURL			DisplayString,
	   iis5VHOPTBLTableEntries		INTEGER,
	   iis5VHOPTBLWarningCount		INTEGER,
	   iis5VHOPTBLCriticalCount		INTEGER,
	   iis5VHOPTURLMntrTableEntries		INTEGER,
	   iis5VHOPTURLMntrHitRate		INTEGER,
	   iis5VHOPTPolledCounterTableEntries	INTEGER,
           iis5VHOPTIISPCSummaryStatus            INTEGER,
	   iis5VHOPTIISPolledCounterTableEntries	INTEGER,
	   iis5VHOPTSHRSLagSetting		INTEGER,
	   iis5VHOPTSHRSLagValue			INTEGER,
	   iis5VHOPTSHKSLagSetting		INTEGER,
	   iis5VHOPTSHKSLagValue			INTEGER
        }

	iis5VHOPTID OBJECT-TYPE
               SYNTAX  DisplayString
               ACCESS  read-only
               STATUS  mandatory
               DESCRIPTION
               "Vhost name."
               ::=  {  iis5VHOPTEntry 1   }

        iis5VHOPTSummaryStatus OBJECT-TYPE
               SYNTAX  INTEGER {
                                normal(1),
                                warning(2),
                                critical(3)
                               }
               ACCESS  read-only
               STATUS  mandatory
               DESCRIPTION
               "Overall status for Vhost."
               ::=  {  iis5VHOPTEntry 2   }

        iis5VHOPTSHSummaryStatus OBJECT-TYPE
               SYNTAX  INTEGER {
                                normal(1),
                                warning(2),
                                critical(3)
                               }
               ACCESS  read-only
               STATUS  mandatory
               DESCRIPTION
               "Health status for Vhost."
               ::=  {  iis5VHOPTEntry 3   }

        iis5VHOPTBLSummaryStatus OBJECT-TYPE
               SYNTAX  INTEGER {
                                normal(1),
                                warning(2),
                                critical(3)
                               }
               ACCESS  read-only
               STATUS  mandatory
               DESCRIPTION
               "Bad Urls status for Vhost."
               ::=  {  iis5VHOPTEntry 4   }

        iis5VHOPTPUSummaryStatus OBJECT-TYPE
               SYNTAX  INTEGER {
                                normal(1),
                                warning(2),
                                critical(3)
                               }
               ACCESS  read-only
               STATUS  mandatory
               DESCRIPTION
               "Polled URL status for Vhost."
               ::=  {  iis5VHOPTEntry 5   }

        iis5VHOPTPCSummaryStatus OBJECT-TYPE
               SYNTAX  INTEGER {
                                normal(1),
                                warning(2),
                                critical(3)
                               }
               ACCESS  read-only
               STATUS  mandatory
               DESCRIPTION
               "Polled Counter status for Vhost."
               ::=  {  iis5VHOPTEntry 6   }

        iis5VHOPTSHReqRateWarningThreshold OBJECT-TYPE
               SYNTAX  INTEGER
               ACCESS  read-write
               STATUS  mandatory
               DESCRIPTION
               "Generate a warning if SHReqRate exceeds this."
                ::=  {  iis5VHOPTEntry 7}

        iis5VHOPTSHReqRateCriticalThreshold OBJECT-TYPE
               SYNTAX  INTEGER
               ACCESS  read-write
               STATUS  mandatory
               DESCRIPTION
               "Generate a critical if SHReqRate exceeds this."
                ::=  {  iis5VHOPTEntry 8}

        iis5VHOPTSHByteRateWarningThreshold OBJECT-TYPE
               SYNTAX  INTEGER
               ACCESS  read-write
               STATUS  mandatory
               DESCRIPTION
               "Generate a warning if SHByteRate exceeds this."
                ::=  {  iis5VHOPTEntry 9}

        iis5VHOPTSHByteRateCriticalThreshold OBJECT-TYPE
               SYNTAX  INTEGER
               ACCESS  read-write
               STATUS  mandatory
               DESCRIPTION
               "Generate a critical if SHByteRate exceeds this."
                ::=  {  iis5VHOPTEntry 10}

        iis5VHOPTSHWarningAction OBJECT-TYPE
               SYNTAX  DisplayString
               ACCESS  read-write
               STATUS  mandatory
               DESCRIPTION
               "Command to be executed when any warning threshold is exceeded."
                ::=  {  iis5VHOPTEntry 11}

        iis5VHOPTSHCriticalAction OBJECT-TYPE
               SYNTAX  DisplayString
               ACCESS  read-write
               STATUS  mandatory
               DESCRIPTION
               "Command to be executed when any critical threshold is exceeded."
                ::=  {  iis5VHOPTEntry 12}
		
        iis5VHOPTSHMaxReqRate OBJECT-TYPE
               SYNTAX  INTEGER
               ACCESS  read-write
               STATUS  mandatory
               DESCRIPTION
               "Max value for the abrowser max requests scale."
                ::=  {  iis5VHOPTEntry 13}

        iis5VHOPTSHMaxByteRate OBJECT-TYPE
               SYNTAX  INTEGER
               ACCESS  read-write
               STATUS  mandatory
               DESCRIPTION
               "Max value for the abrowser max bytes scale."
                ::=  {  iis5VHOPTEntry 14}
		
        iis5VHOPTTopURLCircularBuffSize OBJECT-TYPE
               SYNTAX  INTEGER
               ACCESS  read-write
               STATUS  mandatory
               DESCRIPTION
               "Max entries in the table (default 50)."
               ::=  {  iis5VHOPTEntry 15   }

        iis5VHOPTTopURLExclude OBJECT-TYPE
               SYNTAX  DisplayString
               ACCESS  read-write
               STATUS  mandatory
               DESCRIPTION
               "Exclude URLs with these extensions."
               ::=  {  iis5VHOPTEntry 16   }
	       
        iis5VHOPTBLCircularBuffSize OBJECT-TYPE
               SYNTAX  INTEGER
               ACCESS  read-write
               STATUS  mandatory
               DESCRIPTION
               "Max entries in the table (default 50)(Not a circular buffer)."
               ::=  {  iis5VHOPTEntry 17   }

        iis5VHOPTBLWarningThreshold OBJECT-TYPE
               SYNTAX  INTEGER
               ACCESS  read-write
               STATUS  mandatory
               DESCRIPTION
               "Number of requests on a row before warning is generated."
               ::=  {  iis5VHOPTEntry 18   }

        iis5VHOPTBLCriticalThreshold OBJECT-TYPE
               SYNTAX  INTEGER
               ACCESS  read-write
               STATUS  mandatory
               DESCRIPTION
               "Number of requests on a row before critical is generated."
               ::=  {  iis5VHOPTEntry 19   }
	       
        iis5VHOPTBLWarningAction OBJECT-TYPE
               SYNTAX  DisplayString
               ACCESS  read-write
               STATUS  mandatory
               DESCRIPTION
               "Command to be executed when warning threshold is crossed on a row."
               ::=  {  iis5VHOPTEntry 20   }

        iis5VHOPTBLCriticalAction OBJECT-TYPE
               SYNTAX  DisplayString
               ACCESS  read-write
               STATUS  mandatory
               DESCRIPTION
               "Command to be executed when critical threshold is crossed on a row."
               ::=  {  iis5VHOPTEntry 21   }
	       
        iis5VHOPTBLReportURL OBJECT-TYPE
               SYNTAX  DisplayString
               ACCESS  read-write
               STATUS  mandatory
               DESCRIPTION
               "Path and filename for report; Relative to DocumentRoot unless starts with '/'."
               ::=  {  iis5VHOPTEntry 22   }

        iis5VHOPTBLTableEntries OBJECT-TYPE
                SYNTAX  INTEGER
                ACCESS  read-only
                STATUS  mandatory
                DESCRIPTION
                "The number of entries in the BL table."
                ::=  {  iis5VHOPTEntry 23   }

        iis5VHOPTBLWarningCount OBJECT-TYPE
               SYNTAX  INTEGER
               ACCESS  read-only
               STATUS  mandatory
               DESCRIPTION
               "The number of entries in the table with a warning status."
               ::=  {  iis5VHOPTEntry 24   }
	       
        iis5VHOPTBLCriticalCount OBJECT-TYPE
               SYNTAX  INTEGER
               ACCESS  read-only
               STATUS  mandatory
               DESCRIPTION
               "The number of entries in the table with a critical status."
               ::=  {  iis5VHOPTEntry 25   }
	       
        iis5VHOPTURLMntrTableEntries OBJECT-TYPE
               SYNTAX  INTEGER
               ACCESS  read-only
               STATUS  mandatory
               DESCRIPTION
               "The number of entries in the Mntr URL table."
               ::=  {  iis5VHOPTEntry 26   }

        iis5VHOPTURLMntrHitRate OBJECT-TYPE
               SYNTAX  INTEGER
               ACCESS  read-write
               STATUS  mandatory
               DESCRIPTION
               "Interval in seconds over which the counter is measured."
               ::=  {  iis5VHOPTEntry 27   }

        iis5VHOPTPolledCounterTableEntries OBJECT-TYPE
                SYNTAX  INTEGER
                ACCESS  read-only
                STATUS  mandatory
                DESCRIPTION
                "The number of entries in the table."
                ::=  { iis5VHOPTEntry 28 }

        iis5VHOPTIISPCSummaryStatus OBJECT-TYPE
               SYNTAX  INTEGER {
                                normal(1),
                                warning(2),
                                critical(3)
                               }
               ACCESS  read-only
               STATUS  mandatory
               DESCRIPTION
               "IIS Polled Counter status for Vhost."
               ::=  {  iis5VHOPTEntry 29   }

        iis5VHOPTIISPolledCounterTableEntries OBJECT-TYPE
                SYNTAX  INTEGER
                ACCESS  read-only
                STATUS  mandatory
                DESCRIPTION
                "The number of entries in the table."
                ::=  { iis5VHOPTEntry 30 }
		

        iis5VHOPTSHRSLagSetting OBJECT-TYPE
                SYNTAX  INTEGER
                ACCESS  read-only
                STATUS  mandatory
                DESCRIPTION
                "Lag setting for the counter."
                ::=  {  iis5VHOPTEntry 31   }
		
        iis5VHOPTSHRSLagValue OBJECT-TYPE
                SYNTAX  INTEGER
                ACCESS  read-only
                STATUS  mandatory
                DESCRIPTION
                "Current Lag value for the counter."
                ::=  {  iis5VHOPTEntry 32   }

        iis5VHOPTSHKSLagSetting OBJECT-TYPE
                SYNTAX  INTEGER
                ACCESS  read-only
                STATUS  mandatory
                DESCRIPTION
                "Lag setting for the counter."
                ::=  {  iis5VHOPTEntry 33   }
		
        iis5VHOPTSHKSLagValue OBJECT-TYPE
                SYNTAX  INTEGER
                ACCESS  read-only
                STATUS  mandatory
                DESCRIPTION
                "Current Lag value for the counter."
                ::=  {  iis5VHOPTEntry 34   }



--*	Global section

        iis5VHSummaryStatus OBJECT-TYPE
               SYNTAX  INTEGER
               ACCESS  read-only
               STATUS  mandatory
               DESCRIPTION
               "The Summary status of the Virtual Host."
               ::=  {  iis5VHGroup 41   }
	       

--*	MntrUrls section

        iis5VHURLMntrTableEntries OBJECT-TYPE
               SYNTAX  INTEGER
               ACCESS  read-only
               STATUS  mandatory
               DESCRIPTION
               "The number of entries in the table."
               ::=  {  iis5VHGroup 42   }

        iis5VHURLMntrHitRate OBJECT-TYPE
               SYNTAX  INTEGER
               ACCESS  read-write
               STATUS  mandatory
               DESCRIPTION
               "Interval in seconds over which the counter is measured."
               ::=  {  iis5VHGroup 43   }

        iis5VHURLMntrSummaryStatus OBJECT-TYPE
               SYNTAX  INTEGER {
                                normal(1),
                                warning(2),
                                critical(3)
                               }
               ACCESS  read-only
               STATUS  mandatory
               DESCRIPTION
               "Most severe status of all rows in the table."
               ::=  {  iis5VHGroup 44   }

        iis5VHURLMntrTable OBJECT-TYPE
               SYNTAX  SEQUENCE OF Iis5VHURLMntrEntry
               ACCESS  not-accessible
               STATUS  mandatory
               DESCRIPTION
               "This table contains a list of URLs to monitor."
               ::=  {  iis5VHGroup 45 }

        iis5VHURLMntrEntry OBJECT-TYPE
               SYNTAX  Iis5VHURLMntrEntry
               ACCESS  not-accessible
               STATUS  mandatory
               DESCRIPTION
               "This is an entry in the URLMntrTable"
               INDEX { iis5VHURLMntrID }
               ::=  { iis5VHURLMntrTable 1 }

        Iis5VHURLMntrEntry ::= SEQUENCE
        {
           iis5VHURLMntrID				INTEGER,
           iis5VHURLMntrURL                               DisplayString,
           iis5VHURLMntrDesc                              DisplayString,
           iis5VHURLMntrValue                             DisplayString,
           iis5VHURLMntrWarningThreshold                  INTEGER,
           iis5VHURLMntrCriticalThreshold                 INTEGER,
           iis5VHURLMntrWarningAction                     DisplayString,
           iis5VHURLMntrCriticalAction                    DisplayString,
           iis5VHURLMntrStatus                            INTEGER,
           iis5VHURLMntrEnableDisable                     INTEGER,
           iis5VHURLMntrDescending                        INTEGER,
           iis5VHURLMntrReset                             INTEGER,
           iis5VHURLMntrResetTime                         DisplayString,
	   iis5VHURLMntrLagSetting			INTEGER,
	   iis5VHURLMntrLagValue				INTEGER
        }

	iis5VHURLMntrID OBJECT-TYPE
		SYNTAX      INTEGER
		ACCESS      read-only
		STATUS      mandatory
		DESCRIPTION "A unique ID."
		::= {iis5VHURLMntrEntry 1}
		
        iis5VHURLMntrURL OBJECT-TYPE
               SYNTAX  DisplayString
               ACCESS  read-only
               STATUS  mandatory
               DESCRIPTION
               "URL to monitor."
               ::=  {  iis5VHURLMntrEntry 2   }

        iis5VHURLMntrDesc OBJECT-TYPE
               SYNTAX  DisplayString
               ACCESS  read-only
               STATUS  mandatory
               DESCRIPTION
               "Description of the monitored value."
               ::=  {  iis5VHURLMntrEntry 3   }

        iis5VHURLMntrValue OBJECT-TYPE
               SYNTAX  DisplayString
               ACCESS  read-only
               STATUS  mandatory
               DESCRIPTION
               "Peak number of hits per URLMntrHitRate seconds."
               ::=  {  iis5VHURLMntrEntry 4   }

        iis5VHURLMntrWarningThreshold OBJECT-TYPE
               SYNTAX  INTEGER
               ACCESS  read-write
               STATUS  mandatory
               DESCRIPTION
               "Warning threshold in MS"
               ::=  {  iis5VHURLMntrEntry 5   }

        iis5VHURLMntrCriticalThreshold OBJECT-TYPE
               SYNTAX  INTEGER
               ACCESS  read-write
               STATUS  mandatory
               DESCRIPTION
               "Critical threshold in MS"
               ::=  {  iis5VHURLMntrEntry 6   }

        iis5VHURLMntrWarningAction OBJECT-TYPE
               SYNTAX  DisplayString
               ACCESS  read-write
               STATUS  mandatory
               DESCRIPTION
               "Command to be executed when warning threshold is exceeded."
               ::=  {  iis5VHURLMntrEntry 7   }

        iis5VHURLMntrCriticalAction OBJECT-TYPE
               SYNTAX  DisplayString
               ACCESS  read-write
               STATUS  mandatory
               DESCRIPTION
               "Command to be executed when critical threshold is exceeded."
               ::=  {  iis5VHURLMntrEntry 8  }

        iis5VHURLMntrStatus OBJECT-TYPE
               SYNTAX  INTEGER {
                                normal(1),
                                warning(2),
                                critical(3)
                               }
               ACCESS  read-only
               STATUS  mandatory
               DESCRIPTION
               "Status of this URL."
               ::=  {  iis5VHURLMntrEntry 9 }

        iis5VHURLMntrEnableDisable OBJECT-TYPE
                SYNTAX  INTEGER
                {
                    enable(1),
                    disable(2)
                }
                ACCESS  read-write
                STATUS  mandatory
                DESCRIPTION
                "Enable or disable alerts for this URL."
                ::=  {  iis5VHURLMntrEntry 10   }

        iis5VHURLMntrDescending OBJECT-TYPE
               SYNTAX  INTEGER {
                                no(1),
                                yes(2)
                               }
               ACCESS  read-only
               STATUS  mandatory
               DESCRIPTION
               "Yes if lower value triggers thresholds."
               ::=  {  iis5VHURLMntrEntry 11 }

        iis5VHURLMntrReset OBJECT-TYPE
               SYNTAX  INTEGER {
                                reset(1)
                               }
               ACCESS  write-only
               STATUS  mandatory
               DESCRIPTION
               "Reset value for this counter."
               ::=  {  iis5VHURLMntrEntry 12 }

        iis5VHURLMntrResetTime OBJECT-TYPE
               SYNTAX  DisplayString
               ACCESS  read-only
               STATUS  mandatory
               DESCRIPTION
               "Time stamp of when this counter was reset."
               ::=  {  iis5VHURLMntrEntry 13  }
		
        iis5VHURLMntrLagSetting OBJECT-TYPE
                SYNTAX  INTEGER
                ACCESS  read-write
                STATUS  mandatory
                DESCRIPTION
                "Lag setting for the counter."
                ::=  {  iis5VHURLMntrEntry 14   }
		
        iis5VHURLMntrLagValue OBJECT-TYPE
                SYNTAX  INTEGER
                ACCESS  read-only
                STATUS  mandatory
                DESCRIPTION
                "Current Lag value for the counter."
                ::=  {  iis5VHURLMntrEntry 15   }


--* 	Global section    

        iis5VHGroupSummaryStatus OBJECT-TYPE
               SYNTAX  INTEGER {
                                normal(1),
                                warning(2),
                                critical(3)
                                }
               ACCESS  read-only
               STATUS  mandatory
               DESCRIPTION
               "Summary status for group."
                ::=  {  iis5VHGroup 46 }

        iis5VHTableInterval OBJECT-TYPE
               SYNTAX  INTEGER
               ACCESS  read-write
               STATUS  mandatory
               DESCRIPTION
               "Seconds between polls for the VHTable."
               ::=  { iis5VHGroup 47 }

--*	Polled Counter section

        iis5VHPolledCounterTableEntries OBJECT-TYPE
                SYNTAX  INTEGER
                ACCESS  read-only
                STATUS  mandatory
                DESCRIPTION
                "The number of entries in the table."
                ::=  { iis5VHGroup 48 }

        iis5VHPolledSummaryStatus OBJECT-TYPE
                SYNTAX  INTEGER
                {
                    normal(1),
                    warning(2),
                    critical(3)
                }
                ACCESS  read-only
                STATUS  mandatory
                DESCRIPTION
                "The summary status of all polled counters."
                ::=  {  iis5VHGroup 49   }

        iis5VHPolledWarningCount OBJECT-TYPE
                SYNTAX  INTEGER
                ACCESS  read-only
                STATUS  mandatory
                DESCRIPTION
                "Number of polled counters in warning state."
                ::=  {  iis5VHGroup 50  }

        iis5VHPolledCriticalCount OBJECT-TYPE
                SYNTAX  INTEGER
                ACCESS  read-only
                STATUS  mandatory
                DESCRIPTION
                "Number of polled counters in critical state."
                ::=  {  iis5VHGroup 51  }

        iis5VHPolledCounterTable OBJECT-TYPE
                SYNTAX  SEQUENCE OF Iis5VHPolledCounterEntry
                ACCESS  not-accessible
                STATUS  mandatory
                DESCRIPTION
                "The list of all polled counters."
                ::=  {  iis5VHGroup 52 }

        iis5VHPolledCounterEntry OBJECT-TYPE
                 SYNTAX  Iis5VHPolledCounterEntry
                 ACCESS  not-accessible
                 STATUS  mandatory
                 DESCRIPTION
                 "The PolledCounterTable entry."
                 INDEX { iis5VHPolledID }
                     ::=  { iis5VHPolledCounterTable 1 }

        Iis5VHPolledCounterEntry ::= SEQUENCE {
	    iis5VHPolledID		  INTEGER,
            iis5VHDescription               DisplayString,
            iis5VHAvailable                 INTEGER,
            iis5VHWarningThreshold          DisplayString,
            iis5VHCriticalThreshold         DisplayString,
            iis5VHPCValue                   DisplayString,
            iis5VHWarningCount              INTEGER,
            iis5VHCriticalCount             INTEGER,
            iis5VHWarningAction             DisplayString,
            iis5VHCriticalAction            DisplayString,
            iis5VHStatus                    INTEGER,
            iis5VHEnableDisable             INTEGER,
            iis5VHDescendingCounter         INTEGER,
            iis5VHMinimum                   DisplayString,
            iis5VHMaximum                   DisplayString,
            iis5VHAverage                   DisplayString,
            iis5VHStdDev                    DisplayString,
	    iis5VHLagSetting		  INTEGER,
	    iis5VHLagValue		  INTEGER
        }


	iis5VHPolledID OBJECT-TYPE
		SYNTAX      INTEGER
		ACCESS      read-only
		STATUS      mandatory
		DESCRIPTION "A unique ID."
		::= {iis5VHPolledCounterEntry 1}
		
        iis5VHDescription OBJECT-TYPE
                SYNTAX  DisplayString
                ACCESS  read-only
                STATUS  mandatory
                DESCRIPTION
                "The description of the polled counter."
                ::=  {  iis5VHPolledCounterEntry 2   }

        iis5VHAvailable OBJECT-TYPE
                SYNTAX  INTEGER
                {
                    available(1),
                    notavailable(2)
                }
                ACCESS  read-only
                STATUS  mandatory
                DESCRIPTION
                "Describes whether this counter is currently available."
                ::=  {  iis5VHPolledCounterEntry 3   }

        iis5VHWarningThreshold OBJECT-TYPE
                SYNTAX  DisplayString
                ACCESS  read-write
                STATUS  mandatory
                DESCRIPTION
                "Counter value that will trigger warning status if value exceeds it."
                ::=  {  iis5VHPolledCounterEntry 4   }

        iis5VHCriticalThreshold OBJECT-TYPE
                SYNTAX  DisplayString
                ACCESS  read-write
                STATUS  mandatory
                DESCRIPTION
                "Counter value that will trigger critical status if value exceeds it."
                ::=  {  iis5VHPolledCounterEntry 5   }

        iis5VHPCValue OBJECT-TYPE
                SYNTAX  DisplayString
                ACCESS  read-only
                STATUS  mandatory
                DESCRIPTION
                "Value of the polled counter."
                ::=  {  iis5VHPolledCounterEntry 6   }

        iis5VHWarningCount OBJECT-TYPE
                SYNTAX  INTEGER
                ACCESS  read-only
                STATUS  mandatory
                DESCRIPTION
                "Number of times warning alert generated."
                ::=  {  iis5VHPolledCounterEntry 7   }

        iis5VHCriticalCount OBJECT-TYPE
                SYNTAX  INTEGER
                ACCESS  read-only
                STATUS  mandatory
                DESCRIPTION
                "Number of times critical alert generated."
                ::=  {  iis5VHPolledCounterEntry 8   }

        iis5VHWarningAction OBJECT-TYPE
                SYNTAX  DisplayString
                ACCESS  read-write
                STATUS  mandatory
                DESCRIPTION
                "Command to be executed when warning threshold is exceeded."
                ::=  {  iis5VHPolledCounterEntry 9   }

        iis5VHCriticalAction OBJECT-TYPE
                SYNTAX  DisplayString
                ACCESS  read-write
                STATUS  mandatory
                DESCRIPTION
                "Command to be executed when critical threshold is exceeded."
                ::=  {  iis5VHPolledCounterEntry 10   }

        iis5VHStatus OBJECT-TYPE
                SYNTAX  INTEGER
                {
                    normal(1),
                    warning(2),
                    critical(3)
                }
                ACCESS  read-only
                STATUS  mandatory
                DESCRIPTION
                "Status of the polled counter."
                ::=  {  iis5VHPolledCounterEntry 11   }

        iis5VHEnableDisable OBJECT-TYPE
                SYNTAX  INTEGER
                {
                    enable(1),
                    disable(2)
                }
                ACCESS  read-write
                STATUS  mandatory
                DESCRIPTION
                "Enable or disable alerts for this counter."
                ::=  {  iis5VHPolledCounterEntry 12   }

        iis5VHDescendingCounter OBJECT-TYPE
                SYNTAX  INTEGER
                {
                    no(1),
                    yes(2)
                }
                ACCESS  read-write
                STATUS  mandatory
                DESCRIPTION
                "Yes if lower value triggers thresholds, no if higher value triggers thresholds."
                ::=  {  iis5VHPolledCounterEntry 13   }

        iis5VHMinimum OBJECT-TYPE
               SYNTAX  DisplayString
               ACCESS  read-only
               STATUS  mandatory
               DESCRIPTION
               "The minimum reading since the last reset."
               ::=  {  iis5VHPolledCounterEntry 14   }

        iis5VHMaximum OBJECT-TYPE
               SYNTAX  DisplayString
               ACCESS  read-only
               STATUS  mandatory
               DESCRIPTION
               "The maximum reading since the last reset."
               ::=  {  iis5VHPolledCounterEntry 15   }

        iis5VHAverage OBJECT-TYPE
               SYNTAX  DisplayString
               ACCESS  read-only
               STATUS  mandatory
               DESCRIPTION
               "The average reading since the last reset."
               ::=  {  iis5VHPolledCounterEntry 16   }

        iis5VHStdDev OBJECT-TYPE
               SYNTAX  DisplayString
               ACCESS  read-only
               STATUS  mandatory
               DESCRIPTION
               "The standard deviation based on the last 100 readings."
               ::=  {  iis5VHPolledCounterEntry 17   }
		
        iis5VHLagSetting OBJECT-TYPE
                SYNTAX  INTEGER
                ACCESS  read-write
                STATUS  mandatory
                DESCRIPTION
                "Lag setting for the counter."
                ::=  {  iis5VHPolledCounterEntry 18   }
		
        iis5VHLagValue OBJECT-TYPE
                SYNTAX  INTEGER
                ACCESS  read-only
                STATUS  mandatory
                DESCRIPTION
                "Current Lag value for the counter."
                ::=  {  iis5VHPolledCounterEntry 19   }
	       

--*	IIS Polled Counter section

        iis5VHIISPolledCounterTableEntries OBJECT-TYPE
                SYNTAX  INTEGER
                ACCESS  read-only
                STATUS  mandatory
                DESCRIPTION
                "The number of entries in the table."
                ::=  { iis5VHGroup 53 }

        iis5VHIISPolledSummaryStatus OBJECT-TYPE
                SYNTAX  INTEGER
                {
                    normal(1),
                    warning(2),
                    critical(3)
                }
                ACCESS  read-only
                STATUS  mandatory
                DESCRIPTION
                "The summary status of all polled counters."
                ::=  {  iis5VHGroup 54   }

        iis5VHIISPolledWarningCount OBJECT-TYPE
                SYNTAX  INTEGER
                ACCESS  read-only
                STATUS  mandatory
                DESCRIPTION
                "Number of polled counters in warning state."
                ::=  {  iis5VHGroup 55  }

        iis5VHIISPolledCriticalCount OBJECT-TYPE
                SYNTAX  INTEGER
                ACCESS  read-only
                STATUS  mandatory
                DESCRIPTION
                "Number of polled counters in critical state."
                ::=  {  iis5VHGroup 56  }

        iis5VHIISPolledCounterTable OBJECT-TYPE
                SYNTAX  SEQUENCE OF Iis5VHIISPolledCounterEntry
                ACCESS  not-accessible
                STATUS  mandatory
                DESCRIPTION
                "The list of all polled counters."
                ::=  {  iis5VHGroup 57 }

	iis5VHGPEnaDis OBJECT-TYPE
		SYNTAX      INTEGER {enable(1), disable(2)}
		ACCESS      read-write
		STATUS      mandatory
		DESCRIPTION "Enable or disable for the Group."
		::= { iis5VHGroup 58 }

        iis5VHIISPolledCounterEntry OBJECT-TYPE
                 SYNTAX  Iis5VHIISPolledCounterEntry
                 ACCESS  not-accessible
                 STATUS  mandatory
                 DESCRIPTION
                 "The IISPolledCounterTable entry."
                 INDEX { iis5VHIISPolledID }
                     ::=  { iis5VHIISPolledCounterTable 1 }

        Iis5VHIISPolledCounterEntry ::= SEQUENCE {
	    iis5VHIISPolledID		INTEGER,
            iis5VHIISDescription          DisplayString,
            iis5VHIISAvailable            INTEGER,
            iis5VHIISWarningThreshold     DisplayString,
            iis5VHIISCriticalThreshold    DisplayString,
            iis5VHIISPCValue              DisplayString,
            iis5VHIISWarningCount         INTEGER,
            iis5VHIISCriticalCount        INTEGER,
            iis5VHIISWarningAction        DisplayString,
            iis5VHIISCriticalAction       DisplayString,
            iis5VHIISStatus               INTEGER,
            iis5VHIISEnableDisable        INTEGER,
            iis5VHIISDescendingCounter    INTEGER,
            iis5VHIISMinimum              DisplayString,
            iis5VHIISMaximum              DisplayString,
            iis5VHIISAverage              DisplayString,
            iis5VHIISStdDev               DisplayString,
	    iis5VHIISLagSetting		INTEGER,
	    iis5VHIISLagValue		INTEGER
        }


	iis5VHIISPolledID OBJECT-TYPE
		SYNTAX      INTEGER
		ACCESS      read-only
		STATUS      mandatory
		DESCRIPTION "A unique ID."
		::= {iis5VHIISPolledCounterEntry 1}
		
        iis5VHIISDescription OBJECT-TYPE
                SYNTAX  DisplayString
                ACCESS  read-only
                STATUS  mandatory
                DESCRIPTION
                "The description of the polled counter."
                ::=  {  iis5VHIISPolledCounterEntry 2   }

        iis5VHIISAvailable OBJECT-TYPE
                SYNTAX  INTEGER
                {
                    available(1),
                    notavailable(2)
                }
                ACCESS  read-only
                STATUS  mandatory
                DESCRIPTION
                "Describes whether this counter is currently available."
                ::=  {  iis5VHIISPolledCounterEntry 3   }

        iis5VHIISWarningThreshold OBJECT-TYPE
                SYNTAX  DisplayString
                ACCESS  read-write
                STATUS  mandatory
                DESCRIPTION
                "Counter value that will trigger warning status if value exceeds it."
                ::=  {  iis5VHIISPolledCounterEntry 4   }

        iis5VHIISCriticalThreshold OBJECT-TYPE
                SYNTAX  DisplayString
                ACCESS  read-write
                STATUS  mandatory
                DESCRIPTION
                "Counter value that will trigger critical status if value exceeds it."
                ::=  {  iis5VHIISPolledCounterEntry 5   }

        iis5VHIISPCValue OBJECT-TYPE
                SYNTAX  DisplayString
                ACCESS  read-only
                STATUS  mandatory
                DESCRIPTION
                "Value of the polled counter."
                ::=  {  iis5VHIISPolledCounterEntry 6   }

        iis5VHIISWarningCount OBJECT-TYPE
                SYNTAX  INTEGER
                ACCESS  read-only
                STATUS  mandatory
                DESCRIPTION
                "Number of times warning alert generated."
                ::=  {  iis5VHIISPolledCounterEntry 7   }

        iis5VHIISCriticalCount OBJECT-TYPE
                SYNTAX  INTEGER
                ACCESS  read-only
                STATUS  mandatory
                DESCRIPTION
                "Number of times critical alert generated."
                ::=  {  iis5VHIISPolledCounterEntry 8   }

        iis5VHIISWarningAction OBJECT-TYPE
                SYNTAX  DisplayString
                ACCESS  read-write
                STATUS  mandatory
                DESCRIPTION
                "Command to be executed when warning threshold is exceeded."
                ::=  {  iis5VHIISPolledCounterEntry 9   }

        iis5VHIISCriticalAction OBJECT-TYPE
                SYNTAX  DisplayString
                ACCESS  read-write
                STATUS  mandatory
                DESCRIPTION
                "Command to be executed when critical threshold is exceeded."
                ::=  {  iis5VHIISPolledCounterEntry 10   }

        iis5VHIISStatus OBJECT-TYPE
                SYNTAX  INTEGER
                {
                    normal(1),
                    warning(2),
                    critical(3)
                }
                ACCESS  read-only
                STATUS  mandatory
                DESCRIPTION
                "Status of the polled counter."
                ::=  {  iis5VHIISPolledCounterEntry 11   }

        iis5VHIISEnableDisable OBJECT-TYPE
                SYNTAX  INTEGER
                {
                    enable(1),
                    disable(2)
                }
                ACCESS  read-write
                STATUS  mandatory
                DESCRIPTION
                "Enable or disable alerts for this counter."
                ::=  {  iis5VHIISPolledCounterEntry 12   }

        iis5VHIISDescendingCounter OBJECT-TYPE
                SYNTAX  INTEGER
                {
                    no(1),
                    yes(2)
                }
                ACCESS  read-write
                STATUS  mandatory
                DESCRIPTION
                "Yes if lower value triggers thresholds, no if higher value triggers thresholds."
                ::=  {  iis5VHIISPolledCounterEntry 13   }

        iis5VHIISMinimum OBJECT-TYPE
               SYNTAX  DisplayString
               ACCESS  read-only
               STATUS  mandatory
               DESCRIPTION
               "The minimum reading since the last reset."
               ::=  {  iis5VHIISPolledCounterEntry 14   }

        iis5VHIISMaximum OBJECT-TYPE
               SYNTAX  DisplayString
               ACCESS  read-only
               STATUS  mandatory
               DESCRIPTION
               "The maximum reading since the last reset."
               ::=  {  iis5VHIISPolledCounterEntry 15   }

        iis5VHIISAverage OBJECT-TYPE
               SYNTAX  DisplayString
               ACCESS  read-only
               STATUS  mandatory
               DESCRIPTION
               "The average reading since the last reset."
               ::=  {  iis5VHIISPolledCounterEntry 16   }

        iis5VHIISStdDev OBJECT-TYPE
               SYNTAX  DisplayString
               ACCESS  read-only
               STATUS  mandatory
               DESCRIPTION
               "The standard deviation based on the last 100 readings."
               ::=  {  iis5VHIISPolledCounterEntry 17   }
		
        iis5VHIISLagSetting OBJECT-TYPE
                SYNTAX  INTEGER
                ACCESS  read-write
                STATUS  mandatory
                DESCRIPTION
                "Lag setting for the counter."
                ::=  {  iis5VHIISPolledCounterEntry 18   }
		
        iis5VHIISLagValue OBJECT-TYPE
                SYNTAX  INTEGER
                ACCESS  read-only
                STATUS  mandatory
                DESCRIPTION
                "Current Lag value for the counter."
                ::=  {  iis5VHIISPolledCounterEntry 19   }


--*	Lag values

		
        iis5VHSHRSLagSetting OBJECT-TYPE
                SYNTAX  INTEGER
                ACCESS  read-write
                STATUS  mandatory
                DESCRIPTION
                "Lag setting for the counter."
                ::=  {  iis5VHGroup 59   }
		
        iis5VHSHRSLagValue OBJECT-TYPE
                SYNTAX  INTEGER
                ACCESS  read-only
                STATUS  mandatory
                DESCRIPTION
                "Current Lag value for the counter."
                ::=  {  iis5VHGroup 60   }

        iis5VHSHKSLagSetting OBJECT-TYPE
                SYNTAX  INTEGER
                ACCESS  read-write
                STATUS  mandatory
                DESCRIPTION
                "Lag setting for the counter."
                ::=  {  iis5VHGroup 61   }
		
        iis5VHSHKSLagValue OBJECT-TYPE
                SYNTAX  INTEGER
                ACCESS  read-only
                STATUS  mandatory
                DESCRIPTION
                "Current Lag value for the counter."
                ::=  {  iis5VHGroup 62   }


--******************************************************************************
--* IISAvailCounterGroup - Counters currently available
--******************************************************************************

   iis5IISAvailCounterTableEntries OBJECT-TYPE
      SYNTAX      INTEGER
      ACCESS      read-only
      STATUS      mandatory
      DESCRIPTION "The number of entries in the table."
      ::= {iis5IISAvailCounterGroup 1}

   iis5IISAvailCounterTable OBJECT-TYPE
      SYNTAX      SEQUENCE OF iis5IISAvailCounterEntryS
      ACCESS      not-accessible
      STATUS      mandatory
      DESCRIPTION "This table contains a list of all monitored AvailCounters"
      ::= {iis5IISAvailCounterGroup 2}

   iis5IISAvailCounterEntry OBJECT-TYPE
      SYNTAX      iis5IISAvailCounterEntryS
      ACCESS      not-accessible
      STATUS      mandatory
      DESCRIPTION "This is an entry in the AvailCounterTable"
      INDEX       { iis5IISAvailCounterDescription }
      ::= { iis5IISAvailCounterTable 1 }

   iis5IISAvailCounterEntryS ::= SEQUENCE
   {
      iis5IISAvailCounterDescription  DisplayString
   }

   iis5IISAvailCounterDescription OBJECT-TYPE
      SYNTAX      DisplayString
      ACCESS      read-only
      STATUS      mandatory
      DESCRIPTION "The description of the AvailCounter"
      ::= {iis5IISAvailCounterEntry 1}

   iis5IISAvailCounterTableEntriesVH OBJECT-TYPE
      SYNTAX      INTEGER
      ACCESS      read-only
      STATUS      mandatory
      DESCRIPTION "The number of entries in the table."
      ::= {iis5IISAvailCounterGroup 3}

   iis5IISAvailCounterTableVH OBJECT-TYPE
      SYNTAX      SEQUENCE OF is5IISAvailCounterEntryVH
      ACCESS      not-accessible
      STATUS      mandatory
      DESCRIPTION "This table contains a list of all monitored AvailCounters"
      ::= {iis5IISAvailCounterGroup 4}

   iis5IISAvailCounterEntryVH OBJECT-TYPE
      SYNTAX      is5IISAvailCounterEntryVH
      ACCESS      not-accessible
      STATUS      mandatory
      DESCRIPTION "This is an entry in the AvailCounterTable"
      INDEX       { iis5IISAvailCounterDescriptionVH }
      ::= { iis5IISAvailCounterTableVH 1 }

   is5IISAvailCounterEntryVH ::= SEQUENCE
   {
      iis5IISAvailCounterDescriptionVH  DisplayString
   }

   iis5IISAvailCounterDescriptionVH OBJECT-TYPE
      SYNTAX      DisplayString
      ACCESS      read-only
      STATUS      mandatory
      DESCRIPTION "The description of the AvailCounter"
      ::= {iis5IISAvailCounterEntryVH 1}


--******************************************************************************
--* IISPolledCounterGroup - Counters being polled
--******************************************************************************

   iis5IISPolledCounterTableEntries OBJECT-TYPE
      SYNTAX      INTEGER
      ACCESS      read-only
      STATUS      mandatory
      DESCRIPTION "The number of entries in the table."
      ::= {iis5IISPolledCounterGroup 1}

   iis5IISPolledCounterAdd OBJECT-TYPE
      SYNTAX      DisplayString
      ACCESS      write-only
      STATUS      mandatory
      DESCRIPTION "Add this entry to the polled group."
      ::= {iis5IISPolledCounterGroup 2}

   iis5IISPolledCounterDelete OBJECT-TYPE
      SYNTAX      DisplayString
      ACCESS      write-only
      STATUS      mandatory
      DESCRIPTION "Delete this entry from the polled group."
      ::= {iis5IISPolledCounterGroup 3}

   iis5IISPolledCounterStatus OBJECT-TYPE
      SYNTAX      INTEGER {normal(1), warning(2), critical(3)}
      ACCESS      read-only
      STATUS      mandatory
      DESCRIPTION "Summary status for counters."
      ::= {iis5IISPolledCounterGroup 4}

   iis5IISPolledCounterInterval OBJECT-TYPE
      SYNTAX      INTEGER
      ACCESS      read-write
      STATUS      mandatory
      DESCRIPTION "Seconds to poll for changes."
      ::= {iis5IISPolledCounterGroup 5}

   iis5IISPolledCounterTable OBJECT-TYPE
      SYNTAX      SEQUENCE OF iis5IISPolledCounterEntryS
      ACCESS      not-accessible
      STATUS      mandatory
      DESCRIPTION "This table contains a list of all monitored PolledCounters"
      ::= {iis5IISPolledCounterGroup 6}

   iis5IISPolledCounterWarningCount OBJECT-TYPE
      SYNTAX      INTEGER
      ACCESS      read-only
      STATUS      mandatory
      DESCRIPTION "Times warning threshold exceeded."
      ::= {iis5IISPolledCounterGroup 7}

   iis5IISPolledCounterCriticalCount OBJECT-TYPE
      SYNTAX      INTEGER
      ACCESS      read-only
      STATUS      mandatory
      DESCRIPTION "Times critical threshold exceeded."
      ::= {iis5IISPolledCounterGroup 8}

   iis5IISPolledCounterCmd OBJECT-TYPE
      SYNTAX      DisplayString
      ACCESS      read-write
      STATUS      mandatory
      DESCRIPTION "Modify,desc,warn_thrsh,crit_thrsh,warn_act, crit_act,enabled,descend"
      ::= {iis5IISPolledCounterGroup 9}

   iis5IISPolledCounterEntry OBJECT-TYPE
      SYNTAX      iis5IISPolledCounterEntryS
      ACCESS      not-accessible
      STATUS      mandatory
      DESCRIPTION "This is an entry in the IISPolledCounterTable"
      INDEX       { iis5IISRecDescription }
      ::= { iis5IISPolledCounterTable 1 }

   iis5IISPolledCounterEntryS ::= SEQUENCE
   {
	iis5IISRecDescription           	DisplayString,
	iis5IISRecAvailable             	INTEGER,
	iis5IISRecWarningThreshold      	DisplayString,
	iis5IISRecCriticalThreshold     	DisplayString,
	iis5IISRecValue                 	DisplayString,
	iis5IISRecWarningCount          	INTEGER,
	iis5IISRecCriticalCount         	INTEGER,
	iis5IISRecWarningAction         	DisplayString,
	iis5IISRecCriticalAction        	DisplayString,
	iis5IISRecStatus                	INTEGER,
	iis5IISRecEnableDisable         	INTEGER,
	iis5IISRecMinimum               	DisplayString,
	iis5IISRecMaximum               	DisplayString,
	iis5IISRecAverage               	DisplayString,
	iis5IISRecStdDev               	DisplayString,
	iis5IISRecDescendingCounter     	INTEGER,
	iis5IISRecPrevStatus            	INTEGER,
	iis5IISRecLagSetting		INTEGER,
	iis5IISRecLagValue		INTEGER
   }

   iis5IISRecDescription OBJECT-TYPE
      SYNTAX      DisplayString
      ACCESS      read-only
      STATUS      mandatory
      DESCRIPTION "The description of the PolledCounter"
      ::= {iis5IISPolledCounterEntry 1}

   iis5IISRecAvailable OBJECT-TYPE
      SYNTAX      INTEGER {available(1), notavailable(2)}
      ACCESS      read-only
      STATUS      mandatory
      DESCRIPTION "Describes whether this counter is currently available."
      ::= {iis5IISPolledCounterEntry 2}

   iis5IISRecWarningThreshold OBJECT-TYPE
      SYNTAX      DisplayString
      ACCESS      read-write
      STATUS      mandatory
      DESCRIPTION "Generate a warning if value exceeds this."
      ::= {iis5IISPolledCounterEntry 3}

   iis5IISRecCriticalThreshold OBJECT-TYPE
      SYNTAX      DisplayString
      ACCESS      read-write
      STATUS      mandatory
      DESCRIPTION "Generate a critical if value exceeds this."
      ::= {iis5IISPolledCounterEntry 4}

   iis5IISRecValue OBJECT-TYPE
      SYNTAX      DisplayString
      ACCESS      read-only
      STATUS      mandatory
      DESCRIPTION "Value of the counter."
      ::= {iis5IISPolledCounterEntry 5}

   iis5IISRecWarningCount OBJECT-TYPE
      SYNTAX      INTEGER
      ACCESS      read-only
      STATUS      mandatory
      DESCRIPTION "Times warning threshold exceeded."
      ::= {iis5IISPolledCounterEntry 6}

   iis5IISRecCriticalCount OBJECT-TYPE
      SYNTAX      INTEGER
      ACCESS      read-only
      STATUS      mandatory
      DESCRIPTION "Times critical threshold exceeded."
      ::= {iis5IISPolledCounterEntry 7}

   iis5IISRecWarningAction OBJECT-TYPE
      SYNTAX      DisplayString
      ACCESS      read-write
      STATUS      mandatory
      DESCRIPTION "Command to be executed when warning threshold is exceeded."
      ::= {iis5IISPolledCounterEntry 8}

   iis5IISRecCriticalAction OBJECT-TYPE
      SYNTAX      DisplayString
      ACCESS      read-write
      STATUS      mandatory
      DESCRIPTION "Command to be executed when critical threshold is exceeded."
      ::= {iis5IISPolledCounterEntry 9}

   iis5IISRecStatus OBJECT-TYPE
      SYNTAX      INTEGER {normal(1), warning(2), critical(3)}
      ACCESS      read-only
      STATUS      mandatory
      DESCRIPTION "Status of this counter."
      ::= {iis5IISPolledCounterEntry 10}

   iis5IISRecEnableDisable OBJECT-TYPE
      SYNTAX      INTEGER {enable(1), disable(2)}
      ACCESS      read-write
      STATUS      mandatory
      DESCRIPTION "Enable or disable alerts for this counter."
      ::= {iis5IISPolledCounterEntry 11}

   iis5IISRecMinimum OBJECT-TYPE
      SYNTAX      DisplayString
      ACCESS      read-only
      STATUS      mandatory
      DESCRIPTION "The minimum reading since the last reset."
      ::= {iis5IISPolledCounterEntry 12}

   iis5IISRecMaximum OBJECT-TYPE
      SYNTAX      DisplayString
      ACCESS      read-only
      STATUS      mandatory
      DESCRIPTION "The maximum reading since the last reset."
      ::= {iis5IISPolledCounterEntry 13}

   iis5IISRecAverage OBJECT-TYPE
      SYNTAX      DisplayString
      ACCESS      read-only
      STATUS      mandatory
      DESCRIPTION "The average reading since the last reset."
      ::= {iis5IISPolledCounterEntry 14}

   iis5IISRecStdDev OBJECT-TYPE
      SYNTAX      DisplayString
      ACCESS      read-only
      STATUS      mandatory
      DESCRIPTION "The standard deviation based on the last 100 readings."
      ::= {iis5IISPolledCounterEntry 15}

   iis5IISRecDescendingCounter OBJECT-TYPE
      SYNTAX      INTEGER {no(1), yes(2)}
      ACCESS      read-write
      STATUS      mandatory
      DESCRIPTION "Yes if lower value triggers thresholds."
      ::= {iis5IISPolledCounterEntry 16}

   iis5IISRecPrevStatus OBJECT-TYPE
      SYNTAX      INTEGER {normal(1), warning(2), critical(3)}
      ACCESS      read-only
      STATUS      mandatory
      DESCRIPTION "Status of this counter."
      ::= {iis5IISPolledCounterEntry 17}
		
   iis5IISRecLagSetting OBJECT-TYPE
	SYNTAX  INTEGER
	ACCESS  read-write
	STATUS  mandatory
	DESCRIPTION
	"Lag setting for the counter."
	::=  {  iis5IISPolledCounterEntry 18   }
		
   iis5IISRecLagValue OBJECT-TYPE
	SYNTAX  INTEGER
	ACCESS  read-only
	STATUS  mandatory
	DESCRIPTION
	"Current Lag value for the counter."
	::=  {  iis5IISPolledCounterEntry 19   }
	       
   iis5IISPolledCounterDispTableEntries OBJECT-TYPE
	SYNTAX  INTEGER
	ACCESS  read-only
	STATUS  mandatory
	DESCRIPTION
	"The number of entries in the table."
	::=  {  iis5IISPolledCounterGroup 10   }

   iis5IISPolledCounterDispTable OBJECT-TYPE
	SYNTAX  SEQUENCE OF Iis5IISPolledCounterDispEntry
	ACCESS  not-accessible
	STATUS  mandatory
	DESCRIPTION
	"The list of all polled counters."
	::=  {  iis5IISPolledCounterGroup 11}

  iis5IISPolledGPEnaDis OBJECT-TYPE
	SYNTAX      INTEGER {enable(1), disable(2)}
	ACCESS      read-write
	STATUS      mandatory
	DESCRIPTION "Enable or disable for the Group."
	::= { iis5IISPolledCounterGroup 12 }

  iis5IISPolledCounterDispEntry OBJECT-TYPE
	 SYNTAX  Iis5IISPolledCounterDispEntry
	 ACCESS  not-accessible
	 STATUS  mandatory
	 DESCRIPTION
	 "The IISPolledCounterTable entry."
	 INDEX { iis5IISDispDescription }
	     ::=  { iis5IISPolledCounterDispTable 1 }
 
   Iis5IISPolledCounterDispEntry ::= SEQUENCE {
	iis5IISDispDescription            DisplayString,
	iis5IISDispAvailable              INTEGER,
	iis5IISDispWarningThreshold       DisplayString,
	iis5IISDispCriticalThreshold      DisplayString,
	iis5IISDispValue                  DisplayString,
	iis5IISDispWarningCount           INTEGER,
	iis5IISDispCriticalCount          INTEGER,
	iis5IISDispWarningAction          DisplayString,
	iis5IISDispCriticalAction         DisplayString,
	iis5IISDispStatus                 INTEGER,
	iis5IISDispEnableDisable          INTEGER,
	iis5IISDispDescendingCounter      INTEGER,
	iis5IISDispMinimum                DisplayString,
	iis5IISDispMaximum                DisplayString,
	iis5IISDispAverage                DisplayString,
	iis5IISDispStdDev                 DisplayString,
	iis5IISDispValueReported		INTEGER,
	iis5IISDispLagSetting		INTEGER,
	iis5IISDispLagValue		INTEGER
   }

   iis5IISDispDescription OBJECT-TYPE
	SYNTAX  DisplayString
	ACCESS  read-only
	STATUS  mandatory
	DESCRIPTION
	"The description of the polled counter."
	::=  {  iis5IISPolledCounterDispEntry 1   }

   iis5IISDispAvailable OBJECT-TYPE
	SYNTAX  INTEGER
	{
	    available(1),
	    notavailable(2)
	}
	ACCESS  read-only
	STATUS  mandatory
	DESCRIPTION
	"Describes whether this counter is currently available."
	::=  {  iis5IISPolledCounterDispEntry 2   }

   iis5IISDispWarningThreshold OBJECT-TYPE
	SYNTAX  DisplayString
	ACCESS  read-write
	STATUS  mandatory
	DESCRIPTION
	"Counter value that will trigger warning status if value exceeds it."
	::=  {  iis5IISPolledCounterDispEntry 3   }

   iis5IISDispCriticalThreshold OBJECT-TYPE
	SYNTAX  DisplayString
	ACCESS  read-write
	STATUS  mandatory
	DESCRIPTION
	"Counter value that will trigger critical status if value exceeds it."
	::=  {  iis5IISPolledCounterDispEntry 4   }

   iis5IISDispValue OBJECT-TYPE
	SYNTAX  DisplayString
	ACCESS  read-only
	STATUS  mandatory
	DESCRIPTION
	"Value of the polled counter."
	::=  {  iis5IISPolledCounterDispEntry 5   }

   iis5IISDispWarningCount OBJECT-TYPE
	SYNTAX  INTEGER
	ACCESS  read-only
	STATUS  mandatory
	DESCRIPTION
	"Number of times warning alert generated."
	::=  {  iis5IISPolledCounterDispEntry 6   }

   iis5IISDispCriticalCount OBJECT-TYPE
	SYNTAX  INTEGER
	ACCESS  read-only
	STATUS  mandatory
	DESCRIPTION
	"Number of times critical alert generated."
	::=  {  iis5IISPolledCounterDispEntry 7   }

   iis5IISDispWarningAction OBJECT-TYPE
	SYNTAX  DisplayString
	ACCESS  read-write
	STATUS  mandatory
	DESCRIPTION
	"Command to be executed when warning threshold is exceeded."
	::=  {  iis5IISPolledCounterDispEntry 8   }

   iis5IISDispCriticalAction OBJECT-TYPE
	SYNTAX  DisplayString
	ACCESS  read-write
	STATUS  mandatory
	DESCRIPTION
	"Command to be executed when critical threshold is exceeded."
	::=  {  iis5IISPolledCounterDispEntry 9   }

   iis5IISDispStatus OBJECT-TYPE
	SYNTAX  INTEGER
	{
	    normal(1),
	    warning(2),
	    critical(3)
	}
	ACCESS  read-only
	STATUS  mandatory
	DESCRIPTION
	"Status of the polled counter."
	::=  {  iis5IISPolledCounterDispEntry 10   }

   iis5IISDispEnableDisable OBJECT-TYPE
	SYNTAX  INTEGER
	{
	    enable(1),
	    disable(2)
	}
	ACCESS  read-write
	STATUS  mandatory
	DESCRIPTION
	"Enable or disable alerts for this counter."
	::=  {  iis5IISPolledCounterDispEntry 11   }

   iis5IISDispDescendingCounter OBJECT-TYPE
	SYNTAX  INTEGER
	{
	    no(1),
	    yes(2)
	}
	ACCESS  read-write
	STATUS  mandatory
	DESCRIPTION
	"Yes if lower value triggers thresholds, no if higher value triggers thresholds."
	::=  {  iis5IISPolledCounterDispEntry 12   }

   iis5IISDispMinimum OBJECT-TYPE
       SYNTAX  DisplayString
       ACCESS  read-only
       STATUS  mandatory
       DESCRIPTION
       "The minimum reading since the last reset."
       ::=  {  iis5IISPolledCounterDispEntry 13   }

   iis5IISDispMaximum OBJECT-TYPE
       SYNTAX  DisplayString
       ACCESS  read-only
       STATUS  mandatory
       DESCRIPTION
       "The maximum reading since the last reset."
       ::=  {  iis5IISPolledCounterDispEntry 14   }

   iis5IISDispAverage OBJECT-TYPE
       SYNTAX  DisplayString
       ACCESS  read-only
       STATUS  mandatory
       DESCRIPTION
       "The average reading since the last reset."
       ::=  {  iis5IISPolledCounterDispEntry 15   }

   iis5IISDispStdDev OBJECT-TYPE
       SYNTAX  DisplayString
       ACCESS  read-only
       STATUS  mandatory
       DESCRIPTION
       "The standard deviation based on the last 100 readings."
       ::=  {  iis5IISPolledCounterDispEntry 16   }

   iis5IISDispValueReported OBJECT-TYPE
       SYNTAX  INTEGER {
			summary(1),
			average(2),
			vhost(3)
		       }
       ACCESS  read-write
       STATUS  mandatory
       DESCRIPTION
       "The reported value of the counter is either a summary or average of all servers."
       ::=  {  iis5IISPolledCounterDispEntry 17 }
		
   iis5IISDispLagSetting OBJECT-TYPE
	SYNTAX  INTEGER
	ACCESS  read-write
	STATUS  mandatory
	DESCRIPTION
	"Lag setting for the counter."
	::=  {  iis5IISPolledCounterDispEntry 18   }
	
   iis5IISDispLagValue OBJECT-TYPE
	SYNTAX  INTEGER
	ACCESS  read-only
	STATUS  mandatory
	DESCRIPTION
	"Current Lag value for the counter."
	::=  {  iis5IISPolledCounterDispEntry 19   }


--******************************************************************************
--*  Traps                                                                     *
--******************************************************************************

    statusNormal TRAP-TYPE
        ENTERPRISE iis5Agent
        DESCRIPTION "Set status to normal"
        ::= 1

    statusWarning TRAP-TYPE
        ENTERPRISE iis5Agent
        DESCRIPTION "Set status to warning"
        ::= 2

    statusCritical TRAP-TYPE
        ENTERPRISE iis5Agent
        DESCRIPTION "Set status to critical"
        ::= 3

    statusDetailTrap TRAP-TYPE
        ENTERPRISE iis5Agent
--        VARIABLES   {szStatus}
        DESCRIPTION "Status of group or table (row) changed"
        ::= 4
END
