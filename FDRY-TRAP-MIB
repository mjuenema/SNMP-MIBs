FDRY-TRAP-MIB DEFINITIONS ::= BEGIN

IMPORTS
	MODULE-IDENTITY, OBJECT-TYPE,
			Integer32, Unsigned32	   	FROM SNMPv2-SMI	  			-- [RFC2578]
	RowStatus, TEXTUAL-CONVENTION		FROM SNMPv2-TC 				-- [RFC2579]

	InetAddressType, InetAddress		FROM INET-ADDRESS-MIB
	fdryTrap	 					   	FROM FOUNDRY-SN-ROOT-MIB	-- [snroo101]
	;

fdryTrapMIB MODULE-IDENTITY
    LAST-UPDATED "201006020000Z"  -- 04 June 2010
    ORGANIZATION "Brocade Communications Systems, Inc."
    CONTACT-INFO
             "Technical Support Center
              130 Holger Way,
              San Jose, CA  95134
              Email:  ipsupport@brocade.com
              Phone: 1-800-752-8061
              URL:  www.brocade.com"
    DESCRIPTION
             "The Brocade proprietary MIB module for Traps.
              It has new table combines Ipv4 and Ipv6 configuration of
              trap Receiver/managers which to send traps.

              Copyright 1996-2010 Brocade Communications Systems, Inc.
              All rights reserved.
              This Brocade Communications Systems SNMP Management Information Base Specification
              embodies Brocade Communications Systems' confidential and proprietary
              intellectual property. Brocade Communications Systems retains all
              title and ownership in the Specification, including any revisions.

              This Specification is supplied AS IS, and Brocade Communications Systems makes
              no warranty, either express or implied, as to the use,
              operation, condition, or performance of the specification, and any unintended
              consequence it may on the user environment."

    REVISION        "201006020000Z"  -- 04 June 2010
    DESCRIPTION
        "Changed the ORGANIZATION, CONTACT-INFO and DESCRIPTION fields."

	REVISION 	"200802250000Z"  -- 25 February 2008
	DESCRIPTION	"Initial version, obsoletes the earlier snAgTrpRcvrTable."

	::= { fdryTrap 1 }

--
-- Textual Conventions
--
SecurityModel ::= TEXTUAL-CONVENTION
	STATUS	  current
	DESCRIPTION
		"Represents version of trap format to be used."
	SYNTAX	INTEGER{
		v1(1),
		v2c(2),
		usm(3)
		}

SecurityLevel ::= TEXTUAL-CONVENTION
	STATUS	  current
	DESCRIPTION
		"Represents security levels to be used."
	SYNTAX	INTEGER {
		noAuth(1),
		auth(2),
		authPriv(3)
		}

--
-- Top level components of this MIB.
--

fdryTrapReceiver OBJECT IDENTIFIER ::= { fdryTrapMIB 1 }

--
-- Ipv4/Ipv6  trap receiver table
--

	fdryTrapReceiverTable 	   OBJECT-TYPE
		SYNTAX	SEQUENCE OF FdryTrapReceiverEntry
		MAX-ACCESS	not-accessible
		STATUS	current
		DESCRIPTION
			"Trap Receiver table."
		::= { fdryTrapReceiver 1 }

	fdryTrapReceiverEntry 	   OBJECT-TYPE
		SYNTAX	FdryTrapReceiverEntry
		MAX-ACCESS	not-accessible
		STATUS	current
		DESCRIPTION
			"An entry in the Trap Receiver table. This table uses running index as the Index to the table.
			  Reasons to go for running index Scheme than IP addresses:
			  1.  The table will be Virtual Routing and Forwarding(VRF) independent
				  that multiple VRFs could share the same address type and address.
			  2.  Index with address type and address could be potentially 17 unsigned integer, parsing and finding next index takes CPU time.
				  The PDU gets to be huge too!
			  3.  IP address is just another attribute, they are supposed to be list of servers."
		INDEX	{ fdryTrapReceiverIndex }
		::= { fdryTrapReceiverTable 1 }

	FdryTrapReceiverEntry ::= SEQUENCE {
		fdryTrapReceiverIndex
			Unsigned32,
		fdryTrapReceiverAddrType
			InetAddressType,
		fdryTrapReceiverAddr
			InetAddress,
		fdryTrapReceiverCommunityOrSecurityName
			OCTET STRING,
		fdryTrapReceiverUDPPort
			Integer32,
		fdryTrapReceiverSecurityModel
			SecurityModel,
		fdryTrapReceiverSecurityLevel
			SecurityLevel,
		fdryTrapReceiverRowStatus
			RowStatus
		}

	fdryTrapReceiverIndex OBJECT-TYPE
		SYNTAX  Unsigned32
		MAX-ACCESS  not-accessible
		STATUS  current
		DESCRIPTION
		"The index to the Trap Receiver Table."
		::= { fdryTrapReceiverEntry 1 }

	fdryTrapReceiverAddrType 			 OBJECT-TYPE
		SYNTAX  InetAddressType
		MAX-ACCESS  read-create
		STATUS  current
		DESCRIPTION
			  "Trap Receiver IP address Type. Supported address types are ipv4(1) and ipv6(2)"
		DEFVAL	{ ipv4 }
		::= { fdryTrapReceiverEntry 2 }

	fdryTrapReceiverAddr 			 OBJECT-TYPE
		SYNTAX  InetAddress
		MAX-ACCESS  read-create
		STATUS  current
		DESCRIPTION
			  "Trap Receiver IP address."
		::= { fdryTrapReceiverEntry 3 }

	fdryTrapReceiverCommunityOrSecurityName OBJECT-TYPE
		SYNTAX	OCTET STRING (SIZE(0..32))
		MAX-ACCESS	read-create
		STATUS	current
		DESCRIPTION
			"Community string to use. In case of USM (SNMPv3) security model,
			this object is used to provide the security name."
		::= { fdryTrapReceiverEntry 4 }

	fdryTrapReceiverUDPPort		 OBJECT-TYPE
		SYNTAX	Integer32  (0..65535)
		MAX-ACCESS	read-create
		STATUS	current
		DESCRIPTION
			"UDP port number of the trap receiver."
		DEFVAL { 162 }
		::= { fdryTrapReceiverEntry 5 }

	fdryTrapReceiverSecurityModel	   OBJECT-TYPE
		SYNTAX	SecurityModel
		MAX-ACCESS	read-create
		STATUS	current
		DESCRIPTION
			"Version of trap format to be used."
		DEFVAL { v1 }
		::= { fdryTrapReceiverEntry 6 }

	fdryTrapReceiverSecurityLevel	   OBJECT-TYPE
		SYNTAX	SecurityLevel
		MAX-ACCESS	read-create
		STATUS	current
		DESCRIPTION
			"Used for USM (SNMPv3) security model to specify the level of security.
			The security name is provided by fdryTrapReceiverCommunityOrSecurityName."
		DEFVAL { noAuth }
		::= { fdryTrapReceiverEntry 7 }

	fdryTrapReceiverRowStatus    OBJECT-TYPE
		SYNTAX	RowStatus
		MAX-ACCESS	read-create
		STATUS	current
		DESCRIPTION
			"This variable is used to create, modify, or
			delete a row in this table. When a row in this
			table is in active(1) state, no objects in that row
			can be modified except this object.
			 "
		::= { fdryTrapReceiverEntry 8 }


	END
