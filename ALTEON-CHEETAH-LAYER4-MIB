-- COPYRIGHT NOTICE
-- Copyright (c) Radware Ltd. 2009
-- All rights reserved

ALTEON-CHEETAH-LAYER4-MIB DEFINITIONS ::= BEGIN

IMPORTS
    MODULE-IDENTITY, OBJECT-TYPE, Integer32, Counter32, Gauge32, Counter64,
    IpAddress, Unsigned32
        FROM SNMPv2-SMI
    DisplayString, PhysAddress
        FROM SNMPv2-TC
    aws-switch 
        FROM ALTEON-ROOT-MIB;

layer4 MODULE-IDENTITY
    LAST-UPDATED "201207120000Z" --  12 July, 2012
    ORGANIZATION "Radware Ltd"
    CONTACT-INFO "Lobby 1 (Visitors) and Lobby 2 (Deliveries)
                  575 Corporate Drive
                  Mahwah, NJ 07430
                  support@radware.com"
    DESCRIPTION
        "The MIB module for the Alteon OS Layer 4 configuration, statistics
         and information ."
    REVISION "200908050000Z"     -- 5 August, 2009
    DESCRIPTION
        "Added revision clause for SMIv2 compliance."
    ::= { aws-switch 4 }

layer4Configs     OBJECT IDENTIFIER ::= { layer4 1 }
layer4Stats       OBJECT IDENTIFIER ::= { layer4 2 }
layer4Info        OBJECT IDENTIFIER ::= { layer4 3 }
layer4Oper        OBJECT IDENTIFIER ::= { layer4 4 }

slbCfg  	  OBJECT IDENTIFIER ::= { layer4Configs 1 }
filterCfg  	  OBJECT IDENTIFIER ::= { layer4Configs 2 }
gslbCfg           OBJECT IDENTIFIER ::= { layer4Configs 3 }
layer4TableSize   OBJECT IDENTIFIER ::= { layer4Configs 4 }
wlmCfg            OBJECT IDENTIFIER ::= { layer4Configs 6 }

slbGeneralCfg  	  OBJECT IDENTIFIER ::= { slbCfg 1 }
realServerCfg  	  OBJECT IDENTIFIER ::= { slbCfg 2 }
realServerGroupCfg OBJECT IDENTIFIER ::= { slbCfg 3 }
virtualServerCfg  OBJECT IDENTIFIER ::= { slbCfg 4 }
portCfg           OBJECT IDENTIFIER ::= { slbCfg 5 }
syncCfg           OBJECT IDENTIFIER ::= { slbCfg 6 }
wapCfg            OBJECT IDENTIFIER ::= { slbCfg 7 }
waphcCfg          OBJECT IDENTIFIER ::= { slbCfg 8 }
synAttackDetCfg   OBJECT IDENTIFIER ::= { slbCfg 9 }
hcsCfg            OBJECT IDENTIFIER ::= { slbCfg 13 }
snmphcCfg         OBJECT IDENTIFIER ::= { slbCfg 14 }
pipTblCfg         OBJECT IDENTIFIER ::= { slbCfg 15 }
linklbCfg         OBJECT IDENTIFIER ::= { slbCfg 16 }
smtportCfg        OBJECT IDENTIFIER ::= { slbCfg 17 }
acclCfg           OBJECT IDENTIFIER ::= { slbCfg 18 }
caching           OBJECT IDENTIFIER ::= { acclCfg 1}
compression       OBJECT IDENTIFIER ::= { acclCfg 2}

sslCfg            OBJECT IDENTIFIER ::= { slbCfg 19 }
sslPol            OBJECT IDENTIFIER ::= { sslCfg 3}
authPol           OBJECT IDENTIFIER ::= { sslCfg 4 }
certs             OBJECT IDENTIFIER ::= { sslCfg 5 }

sapCfg            OBJECT IDENTIFIER ::= { slbCfg 20 }
peerpipTblCfg     OBJECT IDENTIFIER ::= { slbCfg 21 }

nwclssCfg         OBJECT IDENTIFIER ::= { slbCfg 22 }

syncGeneralCfg    OBJECT IDENTIFIER ::= { syncCfg 1 }

gslbGeneralCfg    OBJECT IDENTIFIER ::= { gslbCfg 1 }
gslbSitesCfg      OBJECT IDENTIFIER ::= { gslbCfg 2 }
gslbEnhNetworkCfg OBJECT IDENTIFIER ::= { gslbCfg 4 }
gslbRuleCfg       OBJECT IDENTIFIER ::= { gslbCfg 5 }
gslbDnsSecCfg     OBJECT IDENTIFIER ::= { gslbCfg 6 }
gslbDnsResVipCfg  OBJECT IDENTIFIER ::= { gslbCfg 7 }

gslbDnsSecGlobalCfg    OBJECT IDENTIFIER ::= { gslbDnsSecCfg 1 }
gslbDnsSecKeyCfg       OBJECT IDENTIFIER ::= { gslbDnsSecCfg 2 }
gslbDnsSecZoneCfg      OBJECT IDENTIFIER ::= { gslbDnsSecCfg 3 }
gslbDnsSecImportExport OBJECT IDENTIFIER ::= { gslbDnsSecCfg 4 }


slbSpStats  	  OBJECT IDENTIFIER ::= { layer4Stats  1 }
slbMaintStats     OBJECT IDENTIFIER ::= { layer4Stats  5 }
filterStats  	  OBJECT IDENTIFIER ::= { layer4Stats  6 }
gslbStats  	  OBJECT IDENTIFIER ::= { layer4Stats  7 }
wapStats          OBJECT IDENTIFIER ::= { layer4Stats  8 }
ftpStats          OBJECT IDENTIFIER ::= { layer4Stats  10 }
rtspStats	  OBJECT IDENTIFIER ::= { layer4Stats  11 }
tcpLimitStats     OBJECT IDENTIFIER ::= { layer4Stats  12 }
dnsSlbStats       OBJECT IDENTIFIER ::= { layer4Stats  13 }
sslSlbStats       OBJECT IDENTIFIER ::= { layer4Stats  16 }
sipStats	  OBJECT IDENTIFIER ::= { layer4Stats  20 }
sessMirrorStats          OBJECT IDENTIFIER ::= { layer4Stats  22 }

accelStats           OBJECT IDENTIFIER ::= { layer4Stats  23 } 
cachStats            OBJECT IDENTIFIER ::= { accelStats  1 }
compStats            OBJECT IDENTIFIER ::= { accelStats  2 }
httpStats            OBJECT IDENTIFIER ::= { layer4Stats 24 }
connmngStats         OBJECT IDENTIFIER ::= { httpStats 17 }

sapStats            OBJECT IDENTIFIER ::= { layer4Stats 25 }

-- Real Server Table - Current Configuration

slbRealServerMaxSize OBJECT-TYPE
    SYNTAX Integer32 
    MAX-ACCESS read-only 
    STATUS current 
    DESCRIPTION 
        "The maximum number of entries in SLB RealServerTable." 
    ::= { realServerCfg 1 }

slbCurCfgRealServerTable OBJECT-TYPE
    SYNTAX SEQUENCE OF SlbCurCfgRealServerEntry
    MAX-ACCESS not-accessible
    STATUS current
    DESCRIPTION
        "The table of Real Server configuration in the current_config."
    ::= { realServerCfg 2 }

slbCurCfgRealServerEntry OBJECT-TYPE
    SYNTAX SlbCurCfgRealServerEntry
    MAX-ACCESS not-accessible
    STATUS current
    DESCRIPTION
        "Information about a particular Real Server configuration."
    INDEX { slbCurCfgRealServerIndex }
    ::= { slbCurCfgRealServerTable 1 }
 
SlbCurCfgRealServerEntry ::= SEQUENCE {
    slbCurCfgRealServerIndex           Integer32,
    slbCurCfgRealServerIpAddr          IpAddress,
    slbCurCfgRealServerWeight          INTEGER,
    slbCurCfgRealServerMaxConns        INTEGER,
    slbCurCfgRealServerTimeOut         INTEGER,
    slbCurCfgRealServerBackUp          Integer32,
    slbCurCfgRealServerPingInterval    INTEGER,
    slbCurCfgRealServerFailRetry       INTEGER,
    slbCurCfgRealServerSuccRetry       INTEGER,
    slbCurCfgRealServerState           INTEGER,
    slbCurCfgRealServerType            INTEGER,
    slbCurCfgRealServerName            DisplayString,
    slbCurCfgRealServerUrlBmap         OCTET STRING,
    slbCurCfgRealServerCookie          INTEGER,
    slbCurCfgRealServerExcludeStr      INTEGER,
    slbCurCfgRealServerSubmac          INTEGER,
    slbCurCfgRealServerProxy           INTEGER,
    slbCurCfgRealServerLdapwr          INTEGER,
    slbCurCfgRealServerOid             DisplayString,
    slbCurCfgRealServerCommString      DisplayString,
    slbCurCfgRealServerIdsvlan         INTEGER,
    slbCurCfgRealServerIdsport         Integer32,
    slbCurCfgRealServerAvail           INTEGER,
    slbCurCfgRealServerFastHealthCheck INTEGER,
    slbCurCfgRealServerSubdmac         INTEGER,
    slbCurCfgRealServerBkpPreempt      INTEGER,
    slbCurCfgRealServerOverflow        INTEGER,
    slbCurCfgRealServerIpVer           INTEGER,
    slbCurCfgRealServerIpv6Addr        DisplayString
    }

slbCurCfgRealServerIndex OBJECT-TYPE
    SYNTAX  Integer32
    MAX-ACCESS  read-only
    STATUS  current
    DESCRIPTION
        "The real server number" 
    ::= { slbCurCfgRealServerEntry 1 }

slbCurCfgRealServerIpAddr OBJECT-TYPE
    SYNTAX  IpAddress
    MAX-ACCESS  read-only
    STATUS  current
    DESCRIPTION
        "IP address of the real server identified by the instance of the 
         slbRealServerIndex." 
    ::= { slbCurCfgRealServerEntry 2 }

slbCurCfgRealServerWeight OBJECT-TYPE
    SYNTAX  INTEGER (1..48)
    MAX-ACCESS  read-only
    STATUS  current
    DESCRIPTION
        "The server weight." 
    ::= { slbCurCfgRealServerEntry 3 }

slbCurCfgRealServerMaxConns OBJECT-TYPE
    SYNTAX  INTEGER (0..200000)
    MAX-ACCESS  read-only
    STATUS  current
    DESCRIPTION
        "The maximum number of connections that are allowed." 
    ::= { slbCurCfgRealServerEntry 4 }

slbCurCfgRealServerTimeOut OBJECT-TYPE
    SYNTAX  INTEGER (2..32768)
    MAX-ACCESS  read-only
    STATUS  current
    DESCRIPTION
        "The maximum number of minutes an inactive connection remains open." 
    ::= { slbCurCfgRealServerEntry 5 }

slbCurCfgRealServerBackUp OBJECT-TYPE
    SYNTAX Integer32
    MAX-ACCESS  read-only
    STATUS  current
    DESCRIPTION
        "The backup server number for this server." 
    ::= { slbCurCfgRealServerEntry 6 }

slbCurCfgRealServerPingInterval OBJECT-TYPE
    SYNTAX  INTEGER (0..60)
    MAX-ACCESS  read-only
    STATUS  current
    DESCRIPTION
	"The interval between keep-alive (ping) attempts in number of seconds.
         Zero means disabling ping attempt."
    ::= { slbCurCfgRealServerEntry 7 }

slbCurCfgRealServerFailRetry OBJECT-TYPE
    SYNTAX  INTEGER  (1..63)
    MAX-ACCESS  read-only
    STATUS  current
    DESCRIPTION
        "The number of failed attempts to declare this server DOWN." 
    ::= { slbCurCfgRealServerEntry 8 }

slbCurCfgRealServerSuccRetry OBJECT-TYPE
    SYNTAX  INTEGER (1..63)
    MAX-ACCESS  read-only
    STATUS  current
    DESCRIPTION
        "The number of successful attempts to declare a server UP." 
    ::= { slbCurCfgRealServerEntry 9 }

slbCurCfgRealServerState OBJECT-TYPE
    SYNTAX  INTEGER {
	enabled(2),
	disabled(3),
	disabled-with-fastage(4)
	}
    MAX-ACCESS  read-only
    STATUS  current
    DESCRIPTION
        "Enable or disable the server and remove the existing sessions using disabled-with-fastage option." 
    ::= { slbCurCfgRealServerEntry 10 }

slbCurCfgRealServerType OBJECT-TYPE
    SYNTAX  INTEGER {
	local-server(1),
	remote-server(2)
	}
    MAX-ACCESS  read-only
    STATUS  current
    DESCRIPTION
        "The server type.  It participates in global server
	 load balancing when it is configured as remote-server." 
    ::= { slbCurCfgRealServerEntry 11 }

slbCurCfgRealServerName OBJECT-TYPE 
    SYNTAX  DisplayString (SIZE(0..31))
    MAX-ACCESS  read-only 
    STATUS  current 
    DESCRIPTION 
        "The name of the real server."  
    ::= { slbCurCfgRealServerEntry 12 }

slbCurCfgRealServerUrlBmap OBJECT-TYPE
    SYNTAX  OCTET STRING
    MAX-ACCESS  read-only
    STATUS  current
    DESCRIPTION
        "The URL Pathes selected for URL load balancing for by the real 
         server.  The selected URL Pathes are presented in a bitmap format.
         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

             where x : 1 - The represented URL Path is selected
                       0 - The represented URL Path is not selected"
    ::= { slbCurCfgRealServerEntry 13 }

slbCurCfgRealServerCookie OBJECT-TYPE
    SYNTAX  INTEGER {
        enabled(1),
        disabled(2)
        }
    MAX-ACCESS  read-only
    STATUS  current
    DESCRIPTION
        "The real server that will handle client requests that doesn't 
         contain an URL cookie if Cookie loadbalance is enabled." 
    ::= { slbCurCfgRealServerEntry 14 }

slbCurCfgRealServerExcludeStr OBJECT-TYPE
    SYNTAX  INTEGER {
	enabled(1),
	disabled(2)
	}
    MAX-ACCESS  read-only
    STATUS  current
    DESCRIPTION
        "The real server will handle requests that don't match the 
         loadbalance string if it is enabled."
    ::= { slbCurCfgRealServerEntry 15 }

slbCurCfgRealServerSubmac OBJECT-TYPE
    SYNTAX  INTEGER {
	enabled(1),
	disabled(2)
	}
    MAX-ACCESS  read-only
    STATUS  current
    DESCRIPTION
        "The real server config to enable/disable MAC SA substitution for 
         L4 traffic. If disabled (the default) we will NOT substitute the 
         MAC SA of client-to-server frames.  If enabled, we will substitute 
         the MAC SA."
    ::= { slbCurCfgRealServerEntry 16 }

slbCurCfgRealServerProxy OBJECT-TYPE
    SYNTAX  INTEGER {
	enabled(1),
	disabled(2)
	}
    MAX-ACCESS  read-only
    STATUS  current
    DESCRIPTION
        "The real server config to enable/disable client proxy operation."
    ::= { slbCurCfgRealServerEntry 17 }

slbCurCfgRealServerLdapwr OBJECT-TYPE
    SYNTAX  INTEGER {
        enabled(1),
        disabled(2)
        }
    MAX-ACCESS  read-only
    STATUS  current
    DESCRIPTION
        "The real server config to enable/disable LDAP write server."
    ::= { slbCurCfgRealServerEntry 18 }

slbCurCfgRealServerOid OBJECT-TYPE
    SYNTAX DisplayString (SIZE(0..128))
    MAX-ACCESS read-only
    STATUS current
    DESCRIPTION
        "The OID to be sent in the SNMP get request packet."
    ::= { slbCurCfgRealServerEntry 19 }

slbCurCfgRealServerCommString OBJECT-TYPE
    SYNTAX DisplayString (SIZE(0..32))
    MAX-ACCESS read-only
    STATUS current
    DESCRIPTION
        "The community string to be used in the SNMP get request packet."
    ::= { slbCurCfgRealServerEntry 20 }

slbCurCfgRealServerIdsvlan OBJECT-TYPE
    SYNTAX  INTEGER (0..4090)
    MAX-ACCESS  read-only
    STATUS  current
    DESCRIPTION
        "The VLAN to be associated with the IDS server."
    ::= { slbCurCfgRealServerEntry 21 }

slbCurCfgRealServerIdsport OBJECT-TYPE
    SYNTAX  Integer32
    MAX-ACCESS  read-only
    STATUS  current
    DESCRIPTION
        "The port to be connected to the IDS server."
    ::= { slbCurCfgRealServerEntry 22 }

slbCurCfgRealServerAvail OBJECT-TYPE
    SYNTAX  INTEGER (1..48)
    MAX-ACCESS  read-only
    STATUS  current
    DESCRIPTION
        "The remote real server Global SLB availability."
    ::= { slbCurCfgRealServerEntry 23 }

slbCurCfgRealServerFastHealthCheck OBJECT-TYPE
    SYNTAX  INTEGER {
        enabled(1),
        disabled(2)
        }
    MAX-ACCESS  read-only
    STATUS  current
    DESCRIPTION
        "The real server config to enable/disable Fast Health Check Operation."
    ::= { slbCurCfgRealServerEntry 24 }

slbCurCfgRealServerSubdmac OBJECT-TYPE
    SYNTAX  INTEGER {
        enabled(1),
        disabled(2)
        }
    MAX-ACCESS  read-only
    STATUS  current
    DESCRIPTION
        "The real server config to enable/disable MAC DA substitution for
         L4 traffic. If disabled, we will NOT substitute the MAC DA of
         client-to-server frames.  If enabled(default), we will substitute
         the MAC DA."
    ::= { slbCurCfgRealServerEntry 25 }

slbCurCfgRealServerOverflow OBJECT-TYPE
    SYNTAX  INTEGER {
        enabled(1),
        disabled(2)
        }
    MAX-ACCESS  read-only
    STATUS  current
    DESCRIPTION
        "The real server config to enable/disable Overflow. If enabled(default)
         allows Backup server to kick in if real server reaches maximum
         connections."
    ::= { slbCurCfgRealServerEntry 26 }

slbCurCfgRealServerBkpPreempt OBJECT-TYPE
    SYNTAX  INTEGER {
        enabled(1),
        disabled(2)
        }
    MAX-ACCESS  read-only
    STATUS  current
    DESCRIPTION
        "The real server config to enable/disable backup preemption. If enabled
         (default)allows to preempt the backup server when the primary server 
         comes up. If disabled the backup server will continue to serve the 
         traffic even when primary server comes up." 
    ::= { slbCurCfgRealServerEntry 27 }
slbCurCfgRealServerIpVer OBJECT-TYPE
    SYNTAX  INTEGER{
        ipv4(1),
        ipv6(2)
        }
    MAX-ACCESS  read-only
    STATUS  current
    DESCRIPTION
        "The type of IP address."
    ::= { slbCurCfgRealServerEntry 28 }

slbCurCfgRealServerIpv6Addr OBJECT-TYPE
   SYNTAX DisplayString (SIZE(0..40))
    MAX-ACCESS  read-only
    STATUS  current
    DESCRIPTION
    "  IPV6 address of the real server identified by the instance of the slbRealServerIndex.
       Address should be 4-byte haxadecimal colon notation. Valid IPv6 address should be in
       any of the following forms xxxx:xxxx:xxxx:xxxx:xxxx:xxxx:xxxx:xxxx or xxxx::xxxx:xxxx:xxxx:xxxx or ::xxxx "
   ::= { slbCurCfgRealServerEntry 29 }


-- Real Server Table - New Configuration

slbNewCfgRealServerTable OBJECT-TYPE
    SYNTAX  SEQUENCE OF SlbNewCfgRealServerEntry
    MAX-ACCESS  not-accessible
    STATUS  current
    DESCRIPTION
        "The table of Real Server configuration in the new_config."
    ::= { realServerCfg 3 }

slbNewCfgRealServerEntry OBJECT-TYPE
    SYNTAX  SlbNewCfgRealServerEntry
    MAX-ACCESS  not-accessible
    STATUS  current
    DESCRIPTION
        "Information about a particular Real Server configuration."
    INDEX   { slbNewCfgRealServerIndex }
    ::= { slbNewCfgRealServerTable 1 }
 
SlbNewCfgRealServerEntry ::= SEQUENCE {
    slbNewCfgRealServerIndex           Integer32,
    slbNewCfgRealServerIpAddr          IpAddress,
    slbNewCfgRealServerWeight          INTEGER,
    slbNewCfgRealServerMaxConns        INTEGER,
    slbNewCfgRealServerTimeOut         INTEGER,
    slbNewCfgRealServerBackUp          Integer32,
    slbNewCfgRealServerPingInterval    INTEGER,
    slbNewCfgRealServerFailRetry       INTEGER,
    slbNewCfgRealServerSuccRetry       INTEGER,
    slbNewCfgRealServerState           INTEGER,
    slbNewCfgRealServerDelete          INTEGER,
    slbNewCfgRealServerType            INTEGER,
    slbNewCfgRealServerName            DisplayString,
    slbNewCfgRealServerUrlBmap         OCTET STRING,
    slbNewCfgRealServerAddUrl          Integer32,
    slbNewCfgRealServerRemUrl          Integer32,
    slbNewCfgRealServerCookie          INTEGER,
    slbNewCfgRealServerExcludeStr      INTEGER,
    slbNewCfgRealServerSubmac          INTEGER,
    slbNewCfgRealServerProxy           INTEGER,
    slbNewCfgRealServerLdapwr          INTEGER,
    slbNewCfgRealServerOid             DisplayString,
    slbNewCfgRealServerCommString      DisplayString,
    slbNewCfgRealServerIdsvlan         INTEGER,
    slbNewCfgRealServerIdsport         Integer32,
    slbNewCfgRealServerAvail           INTEGER,
    slbNewCfgRealServerFastHealthCheck INTEGER,
    slbNewCfgRealServerSubdmac         INTEGER,
    slbNewCfgRealServerBkpPreempt      INTEGER,
    slbNewCfgRealServerOverflow        INTEGER,
    slbNewCfgRealServerIpVer           INTEGER,
    slbNewCfgRealServerIpv6Addr        DisplayString,
    slbNewCfgRealServerNxtRportIdx     INTEGER,
    slbNewCfgRealServerNxtBuddyIdx     INTEGER
    }

slbNewCfgRealServerIndex OBJECT-TYPE
    SYNTAX  Integer32
    MAX-ACCESS  read-only
    STATUS  current
    DESCRIPTION
        "The real server number" 
    ::= { slbNewCfgRealServerEntry 1 }

slbNewCfgRealServerIpAddr OBJECT-TYPE
    SYNTAX  IpAddress
    MAX-ACCESS  read-create
    STATUS  current
    DESCRIPTION
        "IP address of the real server identified by the instance of 
         slbRealServerIndex." 
    ::= { slbNewCfgRealServerEntry 2 }

slbNewCfgRealServerWeight OBJECT-TYPE
    SYNTAX  INTEGER (1..48)
    MAX-ACCESS  read-create
    STATUS  current
    DESCRIPTION
        "The server weight." 
    ::= { slbNewCfgRealServerEntry 3 }

slbNewCfgRealServerMaxConns OBJECT-TYPE
    SYNTAX  INTEGER (0..200000)
    MAX-ACCESS  read-create
    STATUS  current
    DESCRIPTION
        "The maximum number of connections that are allowed." 
    ::= { slbNewCfgRealServerEntry 4 }

slbNewCfgRealServerTimeOut OBJECT-TYPE
    SYNTAX  INTEGER (2..32768)
    MAX-ACCESS  read-create
    STATUS  current
    DESCRIPTION
        "The maximum number of minutes an inactive connection remains open." 
    ::= { slbNewCfgRealServerEntry 5 }

slbNewCfgRealServerBackUp OBJECT-TYPE
    SYNTAX Integer32
    MAX-ACCESS  read-create
    STATUS  current
    DESCRIPTION
        "The backup server number for this server." 
    ::= { slbNewCfgRealServerEntry 6 }

slbNewCfgRealServerPingInterval OBJECT-TYPE
    SYNTAX  INTEGER (0..60)
    MAX-ACCESS  read-create
    STATUS  current
    DESCRIPTION
        "The interval between keep-alive (ping) attempts in number of 
         seconds. Zero means disabling ping attempt."
    ::= { slbNewCfgRealServerEntry 7 }

slbNewCfgRealServerFailRetry OBJECT-TYPE
    SYNTAX  INTEGER  (1..63)
    MAX-ACCESS  read-create
    STATUS  current
    DESCRIPTION
        "The number of failed attempts to declare this server DOWN." 
    ::= { slbNewCfgRealServerEntry 8 }

slbNewCfgRealServerSuccRetry OBJECT-TYPE
    SYNTAX  INTEGER (1..63)
    MAX-ACCESS  read-create
    STATUS  current
    DESCRIPTION
        "The number of successful attempts to declare a server UP." 
    ::= { slbNewCfgRealServerEntry 9 }

slbNewCfgRealServerState OBJECT-TYPE
    SYNTAX  INTEGER {
	enabled(2),
	disabled(3),
	disabled-with-fastage(4)
	}
    MAX-ACCESS  read-create
    STATUS  current
    DESCRIPTION
        "Enable or disable the server and remove the existing sessions using disabled-with-fastage option." 
    ::= { slbNewCfgRealServerEntry 10 }

slbNewCfgRealServerDelete OBJECT-TYPE
    SYNTAX  INTEGER {
        other(1),
        delete(2)
        }
    MAX-ACCESS  read-create
    STATUS  current
    DESCRIPTION
        "By setting the value to delete(2), the entire row is deleted."
    ::= { slbNewCfgRealServerEntry 11 }

slbNewCfgRealServerType OBJECT-TYPE
    SYNTAX  INTEGER {
        local-server(1),
	remote-server(2)
	}
    MAX-ACCESS  read-create
    STATUS  current
    DESCRIPTION
        "The server type.  It participates in global server load balancing 
         when it is configured as remote-server." 
    ::= { slbNewCfgRealServerEntry 12 }

slbNewCfgRealServerName OBJECT-TYPE 
    SYNTAX  DisplayString (SIZE(0..31))
    MAX-ACCESS  read-create 
    STATUS  current 
    DESCRIPTION 
        "The name of the real server."  
    ::= { slbNewCfgRealServerEntry 13 }

slbNewCfgRealServerUrlBmap OBJECT-TYPE
    SYNTAX  OCTET STRING
    MAX-ACCESS  read-only
    STATUS  current
    DESCRIPTION
        "The URL Pathes selected for URL load balancing for by the
	 real server.  The selected URL Pathes are presented in 
	 a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL Path is selected
                   0 - The represented URL Path is not selected"
    ::= { slbNewCfgRealServerEntry 14 }

slbNewCfgRealServerAddUrl OBJECT-TYPE
    SYNTAX  Integer32
    MAX-ACCESS  read-create
    STATUS  current
    DESCRIPTION
        "The URL Path (slbCurCfgUrlLbPathIndex) to be added to the 
         real server. A zero is returned when read."
    ::= { slbNewCfgRealServerEntry 15 }

slbNewCfgRealServerRemUrl OBJECT-TYPE
    SYNTAX  Integer32
    MAX-ACCESS  read-create
    STATUS  current
    DESCRIPTION
        "The URL Path (slbCurCfgUrlLbPathIndex) to be removed from 
         the real server. A zero is returned when read."
    ::= { slbNewCfgRealServerEntry 16 }

slbNewCfgRealServerCookie OBJECT-TYPE
    SYNTAX  INTEGER {
	enabled(1),
	disabled(2)
	}
    MAX-ACCESS  read-create
    STATUS  current
    DESCRIPTION
        "Enable or disable real server to handle client requests
         that don't contain a cookie if cookie loadbalance is enabled." 
    ::= { slbNewCfgRealServerEntry 17 }

slbNewCfgRealServerExcludeStr OBJECT-TYPE
    SYNTAX  INTEGER {
	enabled(1),
	disabled(2)
	}
    MAX-ACCESS  read-create
    STATUS  current
    DESCRIPTION
        "Enable or disable exclusionary matching string on real server."
    ::= { slbNewCfgRealServerEntry 18 }

slbNewCfgRealServerSubmac OBJECT-TYPE
    SYNTAX  INTEGER {
	enabled(1),
	disabled(2)
	}
    MAX-ACCESS  read-create
    STATUS  current
    DESCRIPTION
        "The real server config to enable/disable MAC SA substitution for 
         L4 traffic. If disabled (the default) we will NOT substitute the 
         MAC SA of client-to-server frames.  If enabled, we will substitute 
         the MAC SA."
    ::= { slbNewCfgRealServerEntry 19 }

slbNewCfgRealServerProxy OBJECT-TYPE
    SYNTAX  INTEGER {
	enabled(1),
	disabled(2)
	}
    MAX-ACCESS  read-create
    STATUS  current
    DESCRIPTION
        "The real server config to enable/disable client proxy operation."
    ::= { slbNewCfgRealServerEntry 20 }

slbNewCfgRealServerLdapwr OBJECT-TYPE
    SYNTAX  INTEGER {
        enabled(1),
        disabled(2)
        }
    MAX-ACCESS  read-create
    STATUS  current
    DESCRIPTION
        "The real server config to enable/disable LDAP write server."
    ::= { slbNewCfgRealServerEntry 21 }

slbNewCfgRealServerOid OBJECT-TYPE
    SYNTAX DisplayString (SIZE(0..128))
    MAX-ACCESS read-create
    STATUS current
    DESCRIPTION
        "The OID to be sent in the SNMP get request packet."
    ::= { slbNewCfgRealServerEntry 22 }

slbNewCfgRealServerCommString OBJECT-TYPE
    SYNTAX DisplayString (SIZE(0..32))
    MAX-ACCESS read-create
    STATUS current
    DESCRIPTION
        "The community string to be used in the SNMP get request packet."
    ::= { slbNewCfgRealServerEntry 23 }

slbNewCfgRealServerIdsvlan OBJECT-TYPE
    SYNTAX  INTEGER (0..4090)
    MAX-ACCESS  read-create
    STATUS  current
    DESCRIPTION
        "The VLAN to be associated with IDS server."
    ::= { slbNewCfgRealServerEntry 24 }

slbNewCfgRealServerIdsport OBJECT-TYPE
    SYNTAX  Integer32
    MAX-ACCESS  read-create
    STATUS  current
    DESCRIPTION
        "The port to be connected to IDS server."
    ::= { slbNewCfgRealServerEntry 25 }

slbNewCfgRealServerAvail OBJECT-TYPE
    SYNTAX  INTEGER (1..48)
    MAX-ACCESS  read-create
    STATUS  current
    DESCRIPTION
        "The remote real server Global SLB availability."
    ::= { slbNewCfgRealServerEntry 26 }

slbNewCfgRealServerFastHealthCheck OBJECT-TYPE
    SYNTAX  INTEGER {
        enabled(1),
        disabled(2)
        }
    MAX-ACCESS  read-create
    STATUS  current
    DESCRIPTION
        "The real server config to enable/disable Fast Health Check Operation."
    ::= { slbNewCfgRealServerEntry 27 }

slbNewCfgRealServerSubdmac OBJECT-TYPE
    SYNTAX  INTEGER {
        enabled(1),
        disabled(2)
        }
    MAX-ACCESS  read-create
    STATUS  current
    DESCRIPTION
        "The real server config to enable/disable MAC DA substitution for
         L4 traffic. If disabled, we will NOT substitute the MAC DA of
         client-to-server frames.  If enabled(default), we will substitute
         the MAC DA."
    ::= { slbNewCfgRealServerEntry 28 }

slbNewCfgRealServerOverflow OBJECT-TYPE
    SYNTAX  INTEGER {
        enabled(1),
        disabled(2)
        }
    MAX-ACCESS  read-create
    STATUS  current
    DESCRIPTION
        "The real server config to enable/disable Overflow. If enabled(default)
         allows Backup server to kick in if real server reaches maximum
         connections."
    ::= { slbNewCfgRealServerEntry 29 }

slbNewCfgRealServerBkpPreempt OBJECT-TYPE
    SYNTAX  INTEGER {
        enabled(1),
        disabled(2)
        }
    MAX-ACCESS  read-create
    STATUS  current
    DESCRIPTION
        "The real server config to enable/disable backup preemption. If enabled
         (default)allows to preempt the backup server when the primary server
         comes up. If disabled the backup server will continue to serve the
         traffic even when primary server comes up."
    ::= { slbNewCfgRealServerEntry 30 }

slbNewCfgRealServerIpVer OBJECT-TYPE
    SYNTAX  INTEGER{
        ipv4(1),
        ipv6(2)
        }
    MAX-ACCESS  read-create
    STATUS  current
    DESCRIPTION
        "The type of IP address."
    ::= { slbNewCfgRealServerEntry 31 }

slbNewCfgRealServerIpv6Addr OBJECT-TYPE
   SYNTAX DisplayString (SIZE(0..40))
    MAX-ACCESS  read-create
    STATUS  current
    DESCRIPTION
    "  IPV6 address of the real server identified by the instance of the slbRealServerIndex.
       Address should be 4-byte haxadecimal colon notation. Valid IPv6 address should be in
       any of the following forms xxxx:xxxx:xxxx:xxxx:xxxx:xxxx:xxxx:xxxx or xxxx::xxxx:xxxx:xxxx:xxxx or ::xxxx "
   ::= { slbNewCfgRealServerEntry 32 }

slbNewCfgRealServerNxtRportIdx OBJECT-TYPE
    SYNTAX  INTEGER (0..64)
    MAX-ACCESS  read-only
    STATUS  current
    DESCRIPTION
        "The next available free slot index number, to add the real port
         to the server. Value 0 will be returned if no free slot available."
    ::= { slbNewCfgRealServerEntry 33 }

slbNewCfgRealServerNxtBuddyIdx OBJECT-TYPE
    SYNTAX  INTEGER (0..4)
    MAX-ACCESS  read-only
    STATUS  current
    DESCRIPTION
    "The next available free slot Buddy index number, to add the Buddy Server
    to the Real server. Value 0 will be returned if no free slot available."
    ::= { slbNewCfgRealServerEntry 34 }

 
-- Real Server Multiple Port Table

slbRealServPortTableMaxSize OBJECT-TYPE
    SYNTAX  Integer32 
    MAX-ACCESS  read-only 
    STATUS  current 
    DESCRIPTION 
        "The maximum number of entries in SLB RealServPortTable." 
    ::= { realServerCfg 4 }

slbCurCfgRealServPortTable OBJECT-TYPE
    SYNTAX  SEQUENCE OF SlbCurCfgRealServPortEntry
    MAX-ACCESS  not-accessible
    STATUS  current
    DESCRIPTION
        "The table of real server service ports."
    ::= { realServerCfg 5 }

slbCurCfgRealServPortEntry OBJECT-TYPE
    SYNTAX  SlbCurCfgRealServPortEntry
    MAX-ACCESS  not-accessible
    STATUS  current
    DESCRIPTION
        "A row in the real server service ports table."
    INDEX   { slbCurCfgRealServIndex, slbCurCfgRealServPortIndex }
    ::= { slbCurCfgRealServPortTable 1 }

SlbCurCfgRealServPortEntry ::= SEQUENCE {
    slbCurCfgRealServIndex         Integer32,
    slbCurCfgRealServPortIndex     Integer32,
    slbCurCfgRealServRealPort      INTEGER
    }

slbCurCfgRealServIndex OBJECT-TYPE
    SYNTAX  Integer32
    MAX-ACCESS  read-only
    STATUS  current
    DESCRIPTION
        "The number of the real server." 
    ::= { slbCurCfgRealServPortEntry 1 }

slbCurCfgRealServPortIndex OBJECT-TYPE 
    SYNTAX  Integer32 
    MAX-ACCESS  read-only 
    STATUS  current 
    DESCRIPTION 
        "The port index. This has no external meaning" 
    ::= { slbCurCfgRealServPortEntry 2 }

slbCurCfgRealServRealPort OBJECT-TYPE  
    SYNTAX  INTEGER (2..65534)
    MAX-ACCESS  read-only  
    STATUS  current  
    DESCRIPTION 
        "The layer4 real service port number."  
    ::= { slbCurCfgRealServPortEntry 3 } 

slbNewCfgRealServPortTable OBJECT-TYPE
    SYNTAX  SEQUENCE OF SlbNewCfgRealServPortEntry
    MAX-ACCESS  not-accessible
    STATUS  current
    DESCRIPTION
        "The table of real server service ports."
    ::= { realServerCfg 6 }

slbNewCfgRealServPortEntry OBJECT-TYPE
    SYNTAX  SlbNewCfgRealServPortEntry
    MAX-ACCESS  not-accessible
    STATUS  current
    DESCRIPTION
        "A row in the real server service ports table."
    INDEX   { slbNewCfgRealServIndex, slbNewCfgRealServPortIndex }
    ::= { slbNewCfgRealServPortTable 1 }

SlbNewCfgRealServPortEntry ::= SEQUENCE {
    slbNewCfgRealServIndex           Integer32,
    slbNewCfgRealServPortIndex       Integer32,
    slbNewCfgRealServRealPort        INTEGER,
    slbNewCfgRealServPortDelete      INTEGER,
    slbNewCfgRealServRealPortFreeIdx INTEGER
    }

slbNewCfgRealServIndex OBJECT-TYPE
    SYNTAX  Integer32
    MAX-ACCESS  read-only
    STATUS  current
    DESCRIPTION
        "The number of the real server." 
    ::= { slbNewCfgRealServPortEntry 1 }

slbNewCfgRealServPortIndex OBJECT-TYPE 
    SYNTAX  Integer32 
    MAX-ACCESS  read-only 
    STATUS  current 
    DESCRIPTION 
        "The port index. This has no external meaning" 
    ::= { slbNewCfgRealServPortEntry 2 }

slbNewCfgRealServRealPort OBJECT-TYPE  
    SYNTAX  INTEGER (2..65534)
    MAX-ACCESS  read-create  
    STATUS  current  
    DESCRIPTION 
        "The layer4 real service port number."  
    ::= { slbNewCfgRealServPortEntry 3 } 

slbNewCfgRealServPortDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { slbNewCfgRealServPortEntry 4 }

slbNewCfgRealServRealPortFreeIdx OBJECT-TYPE
    SYNTAX  INTEGER(0..64)
    MAX-ACCESS  read-create
    STATUS  current
    DESCRIPTION
        "The first free port index number of the real server.
         Value 0 will be returned when all 64 ports are 
         configured for a real server."
    ::= { slbNewCfgRealServPortEntry 5 }

slbBuddyTableMaxSize OBJECT-TYPE
    SYNTAX  Integer32
    MAX-ACCESS  read-only
    STATUS  current
    DESCRIPTION
        "The maximum number of entries in SLB real buddy server table."
    ::= { realServerCfg 7 }

slbCurCfgBuddyTable OBJECT-TYPE
    SYNTAX  SEQUENCE OF SlbCurCfgBuddyEntry
    MAX-ACCESS  not-accessible
    STATUS  current
    DESCRIPTION
        "The table of buddy information."
    ::= { realServerCfg 8 }

slbCurCfgBuddyEntry OBJECT-TYPE
    SYNTAX  SlbCurCfgBuddyEntry
    MAX-ACCESS  not-accessible
    STATUS  current
    DESCRIPTION
        "A row in the buddy server table."
    INDEX   { slbCurCfgRealSerIndex, slbCurCfgBuddyIndex }
    ::= { slbCurCfgBuddyTable 1 }

SlbCurCfgBuddyEntry ::= SEQUENCE {
    slbCurCfgRealSerIndex       Integer32,
    slbCurCfgBuddyIndex         Integer32,
    slbCurCfgBuddyRealIndex     Integer32, 
    slbCurCfgBuddyGroupIndex    Integer32,
    slbCurCfgBuddyService       INTEGER 
    }

slbCurCfgRealSerIndex OBJECT-TYPE
    SYNTAX  Integer32
    MAX-ACCESS  read-only
    STATUS  current
    DESCRIPTION
        "The number of the real server."
    ::= { slbCurCfgBuddyEntry 1 }

slbCurCfgBuddyIndex OBJECT-TYPE
    SYNTAX  Integer32
    MAX-ACCESS  read-only
    STATUS  current
    DESCRIPTION
    "The buddy index. This has no external meaning"
    ::= { slbCurCfgBuddyEntry 2 }

slbCurCfgBuddyRealIndex OBJECT-TYPE
    SYNTAX  Integer32
    MAX-ACCESS  read-only
    STATUS  current
    DESCRIPTION
        "The buddy server's real server number."
    ::= { slbCurCfgBuddyEntry 3 }

slbCurCfgBuddyGroupIndex OBJECT-TYPE
    SYNTAX  Integer32
    MAX-ACCESS  read-only
    STATUS  current
    DESCRIPTION
        "The buddy server's real group number."
    ::= { slbCurCfgBuddyEntry 4 }

slbCurCfgBuddyService OBJECT-TYPE
    SYNTAX   INTEGER (9..65534)
    MAX-ACCESS  read-only
    STATUS  current
    DESCRIPTION
        "The buddy server's service."
    ::= { slbCurCfgBuddyEntry 5 }

slbNewCfgBuddyTable OBJECT-TYPE
    SYNTAX  SEQUENCE OF SlbNewCfgBuddyEntry
    MAX-ACCESS  not-accessible
    STATUS  current
    DESCRIPTION
        "The table of buddy servers."
    ::= { realServerCfg 9 }

slbNewCfgBuddyEntry OBJECT-TYPE
    SYNTAX  SlbNewCfgBuddyEntry
    MAX-ACCESS  not-accessible
    STATUS  current
    DESCRIPTION
        "A row in the real server buddy table."
    INDEX   { slbNewCfgRealSerIndex, slbNewCfgBuddyIndex  }
    ::= { slbNewCfgBuddyTable 1 }

SlbNewCfgBuddyEntry      ::= SEQUENCE {
    slbNewCfgRealSerIndex         Integer32,
    slbNewCfgBuddyIndex           Integer32,
    slbNewCfgBuddyRealIndex       Integer32,
    slbNewCfgBuddyGroupIndex      Integer32,
    slbNewCfgBuddyService         INTEGER,
    slbNewCfgBuddyDelete          INTEGER
    }

slbNewCfgRealSerIndex OBJECT-TYPE
    SYNTAX  Integer32
    MAX-ACCESS  read-only
    STATUS  current
    DESCRIPTION
        "The number of the real server."
    ::= { slbNewCfgBuddyEntry 1 }

slbNewCfgBuddyIndex OBJECT-TYPE
    SYNTAX  Integer32
    MAX-ACCESS  read-only
    STATUS  current
    DESCRIPTION
        "The buddy index. This has no external meaning"
    ::= { slbNewCfgBuddyEntry 2 }

slbNewCfgBuddyRealIndex OBJECT-TYPE
    SYNTAX  Integer32 
    MAX-ACCESS  read-create
    STATUS  current
    DESCRIPTION
        "The buddy server's real server number."
    ::= { slbNewCfgBuddyEntry 3 }

slbNewCfgBuddyGroupIndex OBJECT-TYPE
    SYNTAX  Integer32
    MAX-ACCESS  read-create
    STATUS  current
    DESCRIPTION
        "The buddy server's real group number."
    ::= { slbNewCfgBuddyEntry 4 }

slbNewCfgBuddyService OBJECT-TYPE
    SYNTAX  INTEGER (9..65534) 
    MAX-ACCESS  read-create
    STATUS  current
    DESCRIPTION
        "The buddy server's service."
    ::= { slbNewCfgBuddyEntry 5 }

slbNewCfgBuddyDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { slbNewCfgBuddyEntry 6 }

-- Server load balancing - Group Table
slbGroupTableMaxSize OBJECT-TYPE
    SYNTAX  Integer32
    MAX-ACCESS  read-only
    STATUS  current
    DESCRIPTION
        "The maximum number of entries in SLB group tables."
    ::= { realServerGroupCfg 1 }

slbGroupMaxIdsSize OBJECT-TYPE
    SYNTAX  Integer32
    MAX-ACCESS  read-only
    STATUS  current
    DESCRIPTION
        "The maximum number of groups IDS can be enabled on."
    ::= { realServerGroupCfg 2 }

slbCurCfgGroupTable OBJECT-TYPE
    SYNTAX  SEQUENCE OF SlbCurCfgGroupEntry
    MAX-ACCESS  not-accessible
    STATUS  current
    DESCRIPTION
        "The table of groups"
    ::= { realServerGroupCfg 3 }

slbCurCfgGroupEntry OBJECT-TYPE
    SYNTAX  SlbCurCfgGroupEntry
    MAX-ACCESS  not-accessible
    STATUS  current
    DESCRIPTION
        "A row in the slbCurCfgGroupTable "
    INDEX   { slbCurCfgGroupIndex }
    ::= { slbCurCfgGroupTable 1 }

SlbCurCfgGroupEntry ::= SEQUENCE {
    slbCurCfgGroupIndex              Integer32,
    slbCurCfgGroupRealServers        OCTET STRING,
    slbCurCfgGroupMetric             INTEGER,
    slbCurCfgGroupBackupServer       Integer32,
    slbCurCfgGroupBackupGroup        Integer32,
    slbCurCfgGroupHealthCheckUrl     DisplayString,
    slbCurCfgGroupHealthCheckLayer   INTEGER,
    slbCurCfgGroupRealThreshold      INTEGER,
    slbCurCfgGroupVipHealthCheck     INTEGER,
    slbCurCfgGroupIdsState           INTEGER,
    slbCurCfgGroupIdsPort            INTEGER,
    slbCurCfgGroupIdsFlood           INTEGER,
    slbCurCfgGroupMinmissHash        INTEGER,
    slbCurCfgGroupPhashMask          IpAddress,
    slbCurCfgGroupRmetric            INTEGER,
    slbCurCfgGroupHealthCheckFormula DisplayString,
    slbCurCfgGroupWlm                Integer32,
    slbCurCfgGroupRadiusAuthenString DisplayString,
    slbCurCfgGroupOperatorAccess     INTEGER,
    slbCurCfgGroupSecBackupGroup     Integer32,
    slbCurCfgGroupSlowstart          Integer32,
    slbCurCfgGroupMinThreshold       Integer32,
    slbCurCfgGroupMaxThreshold       Integer32,

    slbCurCfgGroupName               DisplayString,
    slbCurCfgGroupIpVer              INTEGER,
    slbCurCfgGroupBackup             DisplayString
    }

slbCurCfgGroupIndex OBJECT-TYPE
    SYNTAX  Integer32
    MAX-ACCESS  read-only
    STATUS  current
    DESCRIPTION
        "The group number for which the information pertains."
    ::= { slbCurCfgGroupEntry 1 }

slbCurCfgGroupRealServers    OBJECT-TYPE
    SYNTAX  OCTET STRING
    MAX-ACCESS  read-only
    STATUS  current
    DESCRIPTION
        "The Real servers in the group. The servers are presented in 
         bitmap format.

         in receiving order:

             OCTET 1  OCTET 2  .....
             xxxxxxxx xxxxxxxx ..... 
             |     || |_ server 9
             |     ||  
             |     ||___ server 8
             |     |____ server 7
             |       .    .   .
             |__________ server 1
 
         where x : 1 - The represented server belongs to the group
                   0 - The represented server does not belong to the group"
    ::= { slbCurCfgGroupEntry 2 }

slbCurCfgGroupMetric OBJECT-TYPE
    SYNTAX  INTEGER {
	roundRobin(1),
	leastConnections(2),
	minMisses(3),
	hash(4),
	response(5),
	bandwidth(6),
        phash(7)
        , svcLeast(8)
	}
    MAX-ACCESS  read-only
    STATUS  current
    DESCRIPTION
        "The metric used to select next server in group."
    ::= { slbCurCfgGroupEntry 3 }

slbCurCfgGroupBackupServer OBJECT-TYPE
    SYNTAX Integer32
    MAX-ACCESS  read-only
    STATUS  current
    DESCRIPTION
        "The backup real server for this group."
    ::= { slbCurCfgGroupEntry 4 }

slbCurCfgGroupBackupGroup OBJECT-TYPE
    SYNTAX  Integer32
    MAX-ACCESS  read-only
    STATUS  current
    DESCRIPTION
        "The backup real server group for this group."
    ::= { slbCurCfgGroupEntry 5 }

slbCurCfgGroupHealthCheckUrl OBJECT-TYPE
    SYNTAX  DisplayString (SIZE(0..127))
    MAX-ACCESS  read-only
    STATUS  current
    DESCRIPTION
        "The specific content which is examined during health checks.
         The content depends on the type of health check."
    ::= { slbCurCfgGroupEntry 6 }

slbCurCfgGroupHealthCheckLayer OBJECT-TYPE
    SYNTAX  INTEGER {
	icmp(1),
	tcp(2),
	http(3),
	httphead(44),
	dns(4),
	smtp(5),
	pop3(6),
	nntp(7),
	ftp(8),
	imap(9),
	radius(10),
	sslh(11),
	script1(12),
	script2(13),
	script3(14),
	script4(15),
	script5(16),
	script6(17),
	script7(18),
	script8(19),
	script9(20),
	script10(21),
	script11(22),
	script12(23),
	script13(24),
	script14(25),
	script15(26),
	script16(27),
	link(28),
	wsp(29),
	wtls(30),
	ldap(31),
	udpdns(32),
	arp(33),
	snmp1(34),
	snmp2(35),
	snmp3(36),
	snmp4(37),
	snmp5(38),
        radiusacs(39),
        tftp(40),
        wtp(41),
        rtsp(42),
        sipping(43),
        sipoptions(45),
        wts(46),
        dhcp(47),
        radiusaa(48),
        sslv3(49),
        script17(116),
        script18(117),
        script19(118),
        script20(119),
        script21(120),
        script22(121),
        script23(122),
        script24(123),
        script25(124),
        script26(125),
        script27(126),
        script28(127),
        script29(128),
        script30(129),
        script31(130),
        script32(131),
        script33(132),
        script34(133),
        script35(134),
        script36(135),
        script37(136),
        script38(137),
        script39(138),
        script40(139),
        script41(140),
        script42(141),
        script43(142),
        script44(143),
        script45(144),
        script46(145),
        script47(146),
        script48(147),
        script49(148),
        script50(149),
        script51(150),
        script52(151),
        script53(152),
        script54(153),
        script55(154),
        script56(155),
        script57(156),
        script58(157),
        script59(158),
        script60(159),
        script61(160),
        script62(161),
        script63(162),
        script64(163)
	}
    MAX-ACCESS  read-only
    STATUS  current
    DESCRIPTION
        "The OSI layer at which servers are health checked."
    ::= { slbCurCfgGroupEntry 7 }

slbCurCfgGroupName OBJECT-TYPE 
    SYNTAX  DisplayString (SIZE(0..31))
    MAX-ACCESS  read-only 
    STATUS  current 
    DESCRIPTION 
        "The name of the real server group."  
    ::= { slbCurCfgGroupEntry 8 }

slbCurCfgGroupRealThreshold OBJECT-TYPE 
    SYNTAX  INTEGER (0..15)
    MAX-ACCESS  read-only 
    STATUS  current 
    DESCRIPTION 
        "The minimum number of real servers available. If at any time, the 
         number reaches this minimum limit, a SYSLOG ALERT message is send to 
         to the configured syslog servers stating that the real server 
         threshold has been reached for the concerned group."  
    ::= { slbCurCfgGroupEntry 9 }

slbCurCfgGroupVipHealthCheck OBJECT-TYPE
    SYNTAX  INTEGER {
	enabled(1),
	disabled(2)
	}
    MAX-ACCESS  read-only
    STATUS  current
    DESCRIPTION
        "Enable or disable VIP health checking in DSR mode." 
    ::= { slbCurCfgGroupEntry 10 }

slbCurCfgGroupIdsState OBJECT-TYPE
    SYNTAX  INTEGER {
	enabled(1),
	disabled(2)
	}
    MAX-ACCESS  read-only
    STATUS  current
    DESCRIPTION
        "Enable or disable intrusion detection."
    ::= { slbCurCfgGroupEntry 11 }

slbCurCfgGroupIdsPort OBJECT-TYPE
    SYNTAX  INTEGER (0..65534)
    MAX-ACCESS  read-only
    STATUS  current
    DESCRIPTION
        "The intrusion detection port. A value of 1 is invalid."
    ::= { slbCurCfgGroupEntry 12 }

slbCurCfgGroupIdsFlood OBJECT-TYPE
    SYNTAX  INTEGER {
	enabled(1),
	disabled(2)
	}
    MAX-ACCESS  read-only
    STATUS  current
    DESCRIPTION
        "Enable or disable intrusion detection group flood."
    ::= { slbCurCfgGroupEntry 13 }

slbCurCfgGroupMinmissHash OBJECT-TYPE
    SYNTAX  INTEGER {
        minmiss-24(1),
        minmiss-32(2)
        }
    MAX-ACCESS  read-only
    STATUS  current
    DESCRIPTION
        "24|32 number of ip bits used for minmisses hash in the
         current_configuration block."
    ::= { slbCurCfgGroupEntry 14 }

slbCurCfgGroupPhashMask OBJECT-TYPE
    SYNTAX  IpAddress
    MAX-ACCESS  read-only
    STATUS  current
    DESCRIPTION
        "IP address mask used by the persistent hash metric."
    ::= { slbCurCfgGroupEntry 15 }

slbCurCfgGroupRmetric OBJECT-TYPE
    SYNTAX  INTEGER {
	roundRobin(1),
	hash(2),
        leastConnections(3)
	}
    MAX-ACCESS  read-only
    STATUS  current
    DESCRIPTION
        "The metric used to select next rport in server."
    ::= { slbCurCfgGroupEntry 16 }

slbCurCfgGroupHealthCheckFormula OBJECT-TYPE
    SYNTAX  DisplayString (SIZE(0..31))
    MAX-ACCESS  read-only
    STATUS  current
    DESCRIPTION
        "The formula used to state the actual health of a virtual service.
         It allows user to use the symbols of '(', ')', '|', '&' to 
         construct a formula to state the health of the server group.
         This string can take the following formats :
             '(1&2|3..)', '128' or 'none'
         Example: Consider a group with 4 reals 1, 2, 3, 4.  An example of  
         a formuala to mark the server group failed for the virtual server 
         if 1 and 2 FAILED or 3 and 4 FAILED is (1|2)&(3|4)
         This formula will mark the virtual server UP, if 1 or 2 and 3 or 4
         are health checked sucessfully."
    ::= { slbCurCfgGroupEntry 17 }

slbCurCfgGroupOperatorAccess OBJECT-TYPE
    SYNTAX  INTEGER {
	enabled(1),
	disabled(2)
	}
    MAX-ACCESS  read-only
    STATUS  current
    DESCRIPTION
        "Enable or disable access to this group for operator."
    ::= { slbCurCfgGroupEntry 18 }

slbCurCfgGroupWlm OBJECT-TYPE
    SYNTAX  Integer32
    MAX-ACCESS  read-only
    STATUS  current
    DESCRIPTION
        "The Workload Manager for this Group."
    ::= { slbCurCfgGroupEntry 19 }

slbCurCfgGroupRadiusAuthenString OBJECT-TYPE
    SYNTAX  DisplayString (SIZE(0..32))
    MAX-ACCESS  read-only
    STATUS  current
    DESCRIPTION
        "The group RADIUS authentication string. The string is used for
         generating encrypted authentication string while doing RADIUS
         health check for this group radius servers."
    ::= { slbCurCfgGroupEntry 20 }

slbCurCfgGroupSecBackupGroup OBJECT-TYPE
    SYNTAX  Integer32
    MAX-ACCESS  read-only
    STATUS  current
    DESCRIPTION
        "The Secondary backup real server group for this group."
    ::= { slbCurCfgGroupEntry 21 }

slbCurCfgGroupSlowstart OBJECT-TYPE
    SYNTAX  Integer32
    MAX-ACCESS  read-only
    STATUS  current
    DESCRIPTION
        "The slow-start time for this group."
    ::= { slbCurCfgGroupEntry 22 }

slbCurCfgGroupMinThreshold OBJECT-TYPE
    SYNTAX  Integer32
    MAX-ACCESS  read-only
    STATUS  current
    DESCRIPTION
        "The minimum threshold value for this group."
    ::= { slbCurCfgGroupEntry 23 }

slbCurCfgGroupMaxThreshold OBJECT-TYPE
    SYNTAX  Integer32
    MAX-ACCESS  read-only
    STATUS  current
    DESCRIPTION
        "The maximum threshold value for this group."
    ::= { slbCurCfgGroupEntry 24 }


slbCurCfgGroupIpVer OBJECT-TYPE
    SYNTAX  INTEGER{
        ipv4(1),
        ipv6(2),
        mixed(3)
        }
    MAX-ACCESS  read-only
    STATUS  current
    DESCRIPTION
        "The type of real server group IP address."
    ::= { slbCurCfgGroupEntry 25 }

slbCurCfgGroupBackup OBJECT-TYPE
    SYNTAX  DisplayString (SIZE(0..255))
    MAX-ACCESS  read-only
    STATUS  current
    DESCRIPTION
        "The backup real group or real server for this group."
    ::= { slbCurCfgGroupEntry 26 }

-- Server load balancing - Group Table - New Configuration
slbNewCfgGroupTable OBJECT-TYPE
    SYNTAX  SEQUENCE OF SlbNewCfgGroupEntry
    MAX-ACCESS  not-accessible
    STATUS  current
    DESCRIPTION
        "The table of groups"
    ::= { realServerGroupCfg 4 }

slbNewCfgGroupEntry OBJECT-TYPE
    SYNTAX  SlbNewCfgGroupEntry
    MAX-ACCESS  not-accessible
    STATUS  current
    DESCRIPTION
        "A row in the slbNewCfgGroupTable "
    INDEX   { slbNewCfgGroupIndex }
    ::= { slbNewCfgGroupTable 1 }

SlbNewCfgGroupEntry ::= SEQUENCE {
    slbNewCfgGroupIndex              Integer32,
    slbNewCfgGroupRealServers        OCTET STRING,
    slbNewCfgGroupAddServer          Integer32,
    slbNewCfgGroupRemoveServer       Integer32,
    slbNewCfgGroupMetric             INTEGER,
    slbNewCfgGroupBackupServer       Integer32,
    slbNewCfgGroupBackupGroup	     Integer32,
    slbNewCfgGroupHealthCheckUrl     DisplayString,
    slbNewCfgGroupHealthCheckLayer   INTEGER,
    slbNewCfgGroupRealThreshold	     INTEGER,
    slbNewCfgGroupVipHealthCheck     INTEGER,
    slbNewCfgGroupIdsState           INTEGER,
    slbNewCfgGroupIdsPort            INTEGER,
    slbNewCfgGroupDelete             INTEGER,
    slbNewCfgGroupIdsFlood           INTEGER,
    slbNewCfgGroupMinmissHash        INTEGER,
    slbNewCfgGroupPhashMask          IpAddress,
    slbNewCfgGroupRmetric            INTEGER,
    slbNewCfgGroupHealthCheckFormula DisplayString,
    slbNewCfgGroupWlm                Integer32,
    slbNewCfgGroupRadiusAuthenString DisplayString,
    slbNewCfgGroupOperatorAccess     INTEGER,
    slbNewCfgGroupSecBackupGroup     Integer32,
    slbNewCfgGroupSlowstart          Integer32,
    slbNewCfgGroupName               DisplayString,
    slbNewCfgGroupIpVer              INTEGER,
    slbNewCfgGroupBackup             DisplayString
    ,
    slbNewCfgGroupMinThreshold       Integer32,
    slbNewCfgGroupMaxThreshold       Integer32,
    slbNewCfgGroupBackupType         INTEGER
    }

slbNewCfgGroupIndex OBJECT-TYPE
    SYNTAX  Integer32
    MAX-ACCESS  read-only
    STATUS  current
    DESCRIPTION
        "The group number for which the information pertains."
    ::= { slbNewCfgGroupEntry 1 }

slbNewCfgGroupRealServers    OBJECT-TYPE
    SYNTAX  OCTET STRING
    MAX-ACCESS  read-only
    STATUS  current
    DESCRIPTION
        "The Real servers in the group.  The servers are presented
         in bitmap format.

         in receiving order:

             OCTET 1  OCTET 2  .....
             xxxxxxxx xxxxxxxx ..... 
             |     || |_ server 9
             |     ||  
             |     ||___ server 8
             |     |____ server 7
             |       .    .   .
             |__________ server 1
 
         where x : 1 - The represented server belongs to the group
                   0 - The represented server does not belong to the group"
    ::= { slbNewCfgGroupEntry 2 }

slbNewCfgGroupAddServer OBJECT-TYPE
    SYNTAX  Integer32
    MAX-ACCESS  read-create
    STATUS  current
    DESCRIPTION
        "The real server to be added to the group. When read, 0 is returned."
    ::= { slbNewCfgGroupEntry 3 }

slbNewCfgGroupRemoveServer OBJECT-TYPE 
    SYNTAX  Integer32 
    MAX-ACCESS  read-create 
    STATUS  current
    DESCRIPTION
        "The real server to be removed from the group. When read, 
         0 is returned."
    ::= { slbNewCfgGroupEntry 4 }
  
slbNewCfgGroupMetric OBJECT-TYPE
    SYNTAX  INTEGER {  
	roundRobin(1),
	leastConnections(2),
	minMisses(3),
	hash(4),
	response(5),
	bandwidth(6),
        phash(7)
        , svcLeast(8)
        }
    MAX-ACCESS  read-create
    STATUS  current
    DESCRIPTION
        "The metric used to select next server in group."
    ::= { slbNewCfgGroupEntry 5 }

slbNewCfgGroupBackupServer OBJECT-TYPE
    SYNTAX  Integer32
    MAX-ACCESS  read-create
    STATUS  current
    DESCRIPTION
        "The backup real server for this group."
    ::= { slbNewCfgGroupEntry 6 }

slbNewCfgGroupBackupGroup OBJECT-TYPE
    SYNTAX  Integer32
    MAX-ACCESS  read-create
    STATUS  current
    DESCRIPTION
        "The backup real server group for this group."
    ::= { slbNewCfgGroupEntry 7 }

slbNewCfgGroupHealthCheckUrl OBJECT-TYPE
    SYNTAX  DisplayString (SIZE(0..127))
    MAX-ACCESS  read-create
    STATUS  current
    DESCRIPTION
        "The specific content which is examined during health checks.
         The content depends on the type of health check."
    ::= { slbNewCfgGroupEntry 8 }

slbNewCfgGroupHealthCheckLayer OBJECT-TYPE
    SYNTAX  INTEGER {
	icmp(1),
	tcp(2),
	http(3),
	httphead(44),
	dns(4),
	smtp(5),
	pop3(6),
	nntp(7),
	ftp(8),
	imap(9),
	radius(10),
	sslh(11),
	script1(12),
	script2(13),
	script3(14),
	script4(15),
	script5(16),
	script6(17),
	script7(18),
	script8(19),
	script9(20),
	script10(21),
	script11(22),
	script12(23),
	script13(24),
	script14(25),
	script15(26),
	script16(27),
	link(28),
	wsp(29),
	wtls(30),
	ldap(31),
	udpdns(32),
	arp(33),
	snmp1(34),
	snmp2(35),
	snmp3(36),
	snmp4(37),
	snmp5(38),
        radiusacs(39),
        tftp(40),
        wtp(41),
        rtsp(42),
        sipping(43),
        sipoptions(45),
        wts(46),
        dhcp(47),
        radiusaa(48),
        sslv3(49),
        script17(116),
	script18(117),
	script19(118),
	script20(119),
	script21(120),
	script22(121),
	script23(122),
	script24(123),
	script25(124),
	script26(125),
	script27(126),
	script28(127),
	script29(128),
	script30(129),
	script31(130),
	script32(131),
        script33(132),
	script34(133),
	script35(134),
	script36(135),
	script37(136),
	script38(137),
	script39(138),
	script40(139),
	script41(140),
	script42(141),
	script43(142),
	script44(143),
	script45(144),
	script46(145),
	script47(146),
	script48(147),
        script49(148),
	script50(149),
	script51(150),
	script52(151),
	script53(152),
	script54(153),
	script55(154),
	script56(155),
	script57(156),
	script58(157),
	script59(158),
	script60(159),
	script61(160),
	script62(161),
	script63(162),
	script64(163)
	}
    MAX-ACCESS  read-create
    STATUS  current
    DESCRIPTION
        "The OSI layer at which servers are health checked."
    ::= { slbNewCfgGroupEntry 9 }

slbNewCfgGroupName OBJECT-TYPE 
    SYNTAX  DisplayString (SIZE(0..31))
    MAX-ACCESS  read-create 
    STATUS  current 
    DESCRIPTION 
        "The name of the real server group."  
    ::= { slbNewCfgGroupEntry 10 }

slbNewCfgGroupRealThreshold OBJECT-TYPE 
    SYNTAX  INTEGER (0..15)
    MAX-ACCESS  read-create 
    STATUS  current 
    DESCRIPTION 
        "The minimum number of real servers available. If at any time, the 
         number reaches this minimum limit, a SYSLOG ALERT message is send to 
         to the configured syslog servers stating that the real server 
         threshold has been reached for the concerned group."  
    ::= { slbNewCfgGroupEntry 11 }

slbNewCfgGroupVipHealthCheck OBJECT-TYPE
    SYNTAX  INTEGER {
	enabled(1),
	disabled(2)
	}
    MAX-ACCESS  read-create
    STATUS  current
    DESCRIPTION
        "Enable or disable VIP health checking in DSR mode." 
    ::= { slbNewCfgGroupEntry 12 }

slbNewCfgGroupIdsState OBJECT-TYPE
    SYNTAX  INTEGER {
	enabled(1),
	disabled(2)
	}
    MAX-ACCESS  read-create
    STATUS  current
    DESCRIPTION
        "Enable or disable intrusion detection."
    ::= { slbNewCfgGroupEntry 13 }

slbNewCfgGroupIdsPort OBJECT-TYPE
    SYNTAX  INTEGER (0..65534)
    MAX-ACCESS  read-create
    STATUS  current
    DESCRIPTION
        "The intrusion detection port. A value of 1 is invalid."
    ::= { slbNewCfgGroupEntry 14 }

slbNewCfgGroupDelete OBJECT-TYPE
    SYNTAX  INTEGER {
	other(1),
	delete(2)
	}
    MAX-ACCESS  read-create
    STATUS  current
    DESCRIPTION
        "By setting the value to delete(2), the entire group is deleted."
    ::= { slbNewCfgGroupEntry 15 }

slbNewCfgGroupIdsFlood OBJECT-TYPE
    SYNTAX  INTEGER {
	enabled(1),
	disabled(2)
	}
    MAX-ACCESS  read-create
    STATUS  current
    DESCRIPTION
        "Enable or disable intrusion detection group flood."
    ::= { slbNewCfgGroupEntry 16 }

slbNewCfgGroupMinmissHash OBJECT-TYPE
    SYNTAX  INTEGER {
        minmiss-24(1),
        minmiss-32(2)
        }
    MAX-ACCESS  read-create
    STATUS  current
    DESCRIPTION
        "24|32 number of sip bits used for minmisses hash in the
         new_configuration block."
    ::= { slbNewCfgGroupEntry 17 }

slbNewCfgGroupPhashMask OBJECT-TYPE
    SYNTAX  IpAddress
    MAX-ACCESS  read-create
    STATUS  current
    DESCRIPTION
        "IP address mask used by the persistent hash metric."
    ::= { slbNewCfgGroupEntry 18 }

slbNewCfgGroupRmetric OBJECT-TYPE
    SYNTAX  INTEGER {  
	roundRobin(1),
	hash(2),
        leastConnections(3)
        }
    MAX-ACCESS  read-create
    STATUS  current
    DESCRIPTION
        "The metric used to select next rport in server."
    ::= { slbNewCfgGroupEntry 19 }

slbNewCfgGroupHealthCheckFormula OBJECT-TYPE
    SYNTAX  DisplayString (SIZE(0..31))
    MAX-ACCESS  read-create 
    STATUS  current
    DESCRIPTION
        "The formula used to state the actual health of a virtual service.
         It allows user to use the symbols of '(', ')', '|', '&' to 
         construct a formula to state the health of the server group.
         This string can take the following formats :
             '(1&2|3..)', '128' or 'none'
         Example: Consider a group with 4 reals 1, 2, 3, 4.  An example of  
         a formuala to mark the server group failed for the virtual server 
         if 1 and 2 FAILED or 3 and 4 FAILED is (1|2)&(3|4)
         This formula will mark the virtual server UP, if 1 or 2 and 3 or 4
         are health checked sucessfully."
    ::= { slbNewCfgGroupEntry 20 }

slbNewCfgGroupOperatorAccess OBJECT-TYPE
    SYNTAX  INTEGER {
	enabled(1),
	disabled(2)
	}
    MAX-ACCESS  read-create
    STATUS  current
    DESCRIPTION
        "Enable or disable access to this group for operator."
    ::= { slbNewCfgGroupEntry 21 }

slbNewCfgGroupWlm OBJECT-TYPE
    SYNTAX  Integer32
    MAX-ACCESS  read-create
    STATUS  current
    DESCRIPTION
        "The Workload Manager for this Group."
    ::= { slbNewCfgGroupEntry 22 }

slbNewCfgGroupRadiusAuthenString OBJECT-TYPE
    SYNTAX  DisplayString (SIZE(0..32))
    MAX-ACCESS  read-write
    STATUS  current
    DESCRIPTION
        "The group RADIUS authentication string. The string is used for
         generating encrypted authentication string while doing RADIUS
         health check for this group radius servers."
    ::= { slbNewCfgGroupEntry 23 }

slbNewCfgGroupSecBackupGroup OBJECT-TYPE
    SYNTAX  Integer32
    MAX-ACCESS  read-create
    STATUS  current
    DESCRIPTION
        "The Secondary backup real server group for this group."
    ::= { slbNewCfgGroupEntry 24 }

slbNewCfgGroupSlowstart OBJECT-TYPE
    SYNTAX  Integer32
    MAX-ACCESS  read-create
    STATUS  current
    DESCRIPTION
        "The slow-start time for this group."
    ::= { slbNewCfgGroupEntry 25 }

slbNewCfgGroupMinThreshold OBJECT-TYPE
    SYNTAX  Integer32
    MAX-ACCESS  read-create
    STATUS  current
    DESCRIPTION
        "The minimum threshold value for this group."
    ::= { slbNewCfgGroupEntry 26 }

slbNewCfgGroupMaxThreshold OBJECT-TYPE
    SYNTAX  Integer32
    MAX-ACCESS  read-create
    STATUS  current
    DESCRIPTION
        "The maximum threshold value for this group."
    ::= { slbNewCfgGroupEntry 27 }


slbNewCfgGroupIpVer OBJECT-TYPE
    SYNTAX  INTEGER{
        ipv4(1),
        ipv6(2),
        mixed(3)
        }
    MAX-ACCESS  read-create
    STATUS  current
    DESCRIPTION
        "The type of real server group IP address."
    ::= { slbNewCfgGroupEntry 28 }

slbNewCfgGroupBackup OBJECT-TYPE
    SYNTAX  DisplayString (SIZE(0..255))
    MAX-ACCESS  read-only
    STATUS  current
    DESCRIPTION
        "The backup real group or real server for this group."
    ::= { slbNewCfgGroupEntry 29 }

slbNewCfgGroupBackupType OBJECT-TYPE
    SYNTAX  INTEGER {
        none(1),
        server(2),
        group(3)
        }
    MAX-ACCESS  read-create
    STATUS  current
    DESCRIPTION
        "Backup type of the real server group."
    ::= { slbNewCfgGroupEntry 30 }

-- SLB - Group Real Server Table
slbCurCfgGroupRealServerTable OBJECT-TYPE
    SYNTAX  SEQUENCE OF SlbCurCfgGroupRealServerEntry
    MAX-ACCESS  not-accessible
    STATUS  current
    DESCRIPTION
        "The table of real servers per group."
    ::= { realServerGroupCfg 5 }

slbCurCfgGroupRealServerEntry OBJECT-TYPE
    SYNTAX  SlbCurCfgGroupRealServerEntry
    MAX-ACCESS  not-accessible
    STATUS  current
    DESCRIPTION
        "A row in the Real server group table."
    INDEX   { slbCurCfgRealServGroupIndex, slbCurCfgGroupRealServIndex }
    ::= { slbCurCfgGroupRealServerTable 1 }

SlbCurCfgGroupRealServerEntry ::= SEQUENCE {
    slbCurCfgRealServGroupIndex       Integer32,
    slbCurCfgGroupRealServIndex       Integer32,
    slbCurCfgGroupRealServerState     INTEGER
    }

slbCurCfgRealServGroupIndex OBJECT-TYPE
    SYNTAX  Integer32
    MAX-ACCESS  read-only
    STATUS  current
    DESCRIPTION
        "The real server group index." 
    ::= { slbCurCfgGroupRealServerEntry 1 }

slbCurCfgGroupRealServIndex OBJECT-TYPE
    SYNTAX  Integer32
    MAX-ACCESS  read-only
    STATUS  current
    DESCRIPTION
        "The real server index." 
    ::= { slbCurCfgGroupRealServerEntry 2 }

slbCurCfgGroupRealServerState OBJECT-TYPE
    SYNTAX  INTEGER {
	enabled(1),
	disabled(2)
	}
    MAX-ACCESS  read-only
    STATUS  current
    DESCRIPTION
        "Enable/disable a real server gracefully on a per group basis." 
    ::= { slbCurCfgGroupRealServerEntry 3 }

slbNewCfgGroupRealServerTable OBJECT-TYPE
    SYNTAX  SEQUENCE OF SlbNewCfgGroupRealServerEntry
    MAX-ACCESS  not-accessible
    STATUS  current
    DESCRIPTION
        "The table of real server per group."
    ::= { realServerGroupCfg 6 }

slbNewCfgGroupRealServerEntry OBJECT-TYPE
    SYNTAX  SlbNewCfgGroupRealServerEntry
    MAX-ACCESS  not-accessible
    STATUS  current
    DESCRIPTION
        "A row in the Real server group table."
    INDEX   { slbNewCfgRealServGroupIndex, slbNewCfgGroupRealServIndex}
    ::= { slbNewCfgGroupRealServerTable 1 }

SlbNewCfgGroupRealServerEntry ::= SEQUENCE {
    slbNewCfgRealServGroupIndex        Integer32,
    slbNewCfgGroupRealServIndex        Integer32,
    slbNewCfgGroupRealServerState      INTEGER
    }

slbNewCfgRealServGroupIndex OBJECT-TYPE
    SYNTAX  Integer32
    MAX-ACCESS  read-only
    STATUS  current
    DESCRIPTION
        "The real server group index." 
    ::= { slbNewCfgGroupRealServerEntry 1 }

slbNewCfgGroupRealServIndex OBJECT-TYPE
    SYNTAX  Integer32
    MAX-ACCESS  read-only
    STATUS  current
    DESCRIPTION
        "The real server index." 
    ::= { slbNewCfgGroupRealServerEntry 2 }

slbNewCfgGroupRealServerState OBJECT-TYPE
    SYNTAX  INTEGER {
	enabled(1),
	disabled(2)
	}
    MAX-ACCESS  read-create
    STATUS  current
    DESCRIPTION
        "Enable/disable a real server gracefully on a per group basis." 
    ::= { slbNewCfgGroupRealServerEntry 3 }

-- Server load balancing - Virtual Server Table
slbVirtServerTableMaxSize OBJECT-TYPE
    SYNTAX  Integer32
    MAX-ACCESS  read-only
    STATUS  current
    DESCRIPTION
        "The maximum number of entries in SLB VirtServerTable."
    ::= { virtualServerCfg 1 }

slbCurCfgVirtServerTable OBJECT-TYPE
    SYNTAX  SEQUENCE OF SlbCurCfgVirtualServerEntry
    MAX-ACCESS  not-accessible
    STATUS  current
    DESCRIPTION
        "The table of virtual Servers."
    ::= { virtualServerCfg 2 }
 
slbCurCfgVirtualServerEntry OBJECT-TYPE
    SYNTAX  SlbCurCfgVirtualServerEntry
    MAX-ACCESS  not-accessible
    STATUS  current
    DESCRIPTION
        "A row in the virtual server table."
    INDEX   { slbCurCfgVirtServerIndex }
    ::= { slbCurCfgVirtServerTable 1 }
 
SlbCurCfgVirtualServerEntry ::= SEQUENCE {
    slbCurCfgVirtServerIndex     	Integer32,
    slbCurCfgVirtServerIpAddress 	IpAddress,
    slbCurCfgVirtServerLayer3Only    	INTEGER,
    slbCurCfgVirtServerState     	INTEGER,
    slbCurCfgVirtServerDname     	DisplayString,
    slbCurCfgVirtServerBwmContract	Integer32,
    slbCurCfgVirtServerWeight           INTEGER,
    slbCurCfgVirtServerAvail            INTEGER,
    slbCurCfgVirtServerRule             OCTET STRING,
    slbCurCfgVirtServerIpVer            INTEGER,
    slbCurCfgVirtServerIpv6Addr         DisplayString,
    slbCurCfgVirtServerVname     	DisplayString,
    slbCurCfgVirtServerCReset           INTEGER
    }

slbCurCfgVirtServerIndex OBJECT-TYPE
    SYNTAX  Integer32
    MAX-ACCESS  read-only
    STATUS  current
    DESCRIPTION
        "Virtual Server Number" 
    ::= { slbCurCfgVirtualServerEntry 1 }

slbCurCfgVirtServerIpAddress OBJECT-TYPE
    SYNTAX  IpAddress
    MAX-ACCESS  read-only
    STATUS  current
    DESCRIPTION
        "IP address of the virtual server." 
    ::= { slbCurCfgVirtualServerEntry 2 }

slbCurCfgVirtServerLayer3Only OBJECT-TYPE 
    SYNTAX  INTEGER {
	layer3Only(1),
	disabled(2)
	}
    MAX-ACCESS  read-only 
    STATUS  current 
    DESCRIPTION 
        "Enable or disable layer3 only balancing."  
    ::= { slbCurCfgVirtualServerEntry 3 }

slbCurCfgVirtServerState OBJECT-TYPE 
    SYNTAX  INTEGER {
	enabled(2),
	disabled(3)
	}
    MAX-ACCESS  read-only 
    STATUS  current 
    DESCRIPTION 
        "Enable or disable the virtual server."  
    ::= { slbCurCfgVirtualServerEntry 4 }

slbCurCfgVirtServerDname OBJECT-TYPE 
    SYNTAX  DisplayString (SIZE(0..64))
    MAX-ACCESS  read-only 
    STATUS  current 
    DESCRIPTION 
        "The domain name of the virtual server."  
    ::= { slbCurCfgVirtualServerEntry 5 }

slbCurCfgVirtServerBwmContract OBJECT-TYPE
    SYNTAX  Integer32
    MAX-ACCESS  read-only
    STATUS  current
    DESCRIPTION
        "The default BW contract of virtual server."
    ::= { slbCurCfgVirtualServerEntry 6 }

slbCurCfgVirtServerWeight OBJECT-TYPE
    SYNTAX  INTEGER (1..48)
    MAX-ACCESS  read-only
    STATUS  current
    DESCRIPTION
        "The virtual server Global SLB weight."
    ::= { slbCurCfgVirtualServerEntry 7 }

slbCurCfgVirtServerAvail OBJECT-TYPE
    SYNTAX  INTEGER (1..48)
    MAX-ACCESS  read-only
    STATUS  current
    DESCRIPTION
        "The virtual server Global SLB availability."
    ::= { slbCurCfgVirtualServerEntry 8 }

slbCurCfgVirtServerRule OBJECT-TYPE
    SYNTAX OCTET STRING
    MAX-ACCESS read-only
    STATUS current
    DESCRIPTION
        "The Global SLB rules for the domain.
         The rules are presented in bitmap format.

         in receiving order:

             OCTET 1  OCTET 2  .....
             xxxxxxxx xxxxxxxx .....
             |     || |_ server 9
             |     ||
             |     ||___ server 8
             |     |____ server 7
             |       .    .   .
             |__________ server 1

         where x : 1 - The represented rule belongs to the domain
                   0 - The represented rule does not belong to the domain"
    ::= { slbCurCfgVirtualServerEntry 9 }

slbCurCfgVirtServerVname OBJECT-TYPE 
    SYNTAX  DisplayString (SIZE(0..32))
    MAX-ACCESS  read-only 
    STATUS  current 
    DESCRIPTION 
        "The name of the virtual server."  
    ::= { slbCurCfgVirtualServerEntry 10 }


slbCurCfgVirtServerIpVer OBJECT-TYPE
    SYNTAX  INTEGER{
        ipv4(1),
        ipv6(2)
        }
    MAX-ACCESS  read-only
    STATUS  current
    DESCRIPTION
        "The type of IP address."
    ::= { slbCurCfgVirtualServerEntry 11 }

slbCurCfgVirtServerIpv6Addr OBJECT-TYPE
    SYNTAX   DisplayString (SIZE(0..40))
    MAX-ACCESS  read-only
    STATUS  current
    DESCRIPTION
        "The IPv6 address of the virtual server. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { slbCurCfgVirtualServerEntry 12 }


slbCurCfgVirtServerCReset OBJECT-TYPE
    SYNTAX  INTEGER{
        enabled(1),
        disabled(2)
        }
    MAX-ACCESS  read-only
    STATUS  current
    DESCRIPTION
        "Enable/disable client connection reset for invalid VPORT."
    ::= { slbCurCfgVirtualServerEntry 13 }

-- Server load balancing - Virtual Server Table

slbNewCfgVirtServerTable OBJECT-TYPE
    SYNTAX  SEQUENCE OF SlbNewCfgVirtualServerEntry
    MAX-ACCESS  not-accessible
    STATUS  current
    DESCRIPTION
        "The table of virtual Servers."
    ::= { virtualServerCfg 3 }

slbNewCfgVirtualServerEntry OBJECT-TYPE
    SYNTAX  SlbNewCfgVirtualServerEntry
    MAX-ACCESS  not-accessible
    STATUS  current
    DESCRIPTION
        "A row in the virtual server table."
    INDEX   { slbNewCfgVirtServerIndex }
    ::= { slbNewCfgVirtServerTable 1 }
 
SlbNewCfgVirtualServerEntry ::= SEQUENCE {
    slbNewCfgVirtServerIndex   		Integer32,
    slbNewCfgVirtServerIpAddress 	IpAddress,
    slbNewCfgVirtServerLayer3Only   	INTEGER,
    slbNewCfgVirtServerState     	INTEGER,
    slbNewCfgVirtServerDname     	DisplayString,
    slbNewCfgVirtServerBwmContract	Integer32,
    slbNewCfgVirtServerDelete    	INTEGER,
    slbNewCfgVirtServerWeight           INTEGER,
    slbNewCfgVirtServerAvail            INTEGER,
    slbNewCfgVirtServerRule             OCTET STRING,
    slbNewCfgVirtServerAddRule          Integer32,
    slbNewCfgVirtServerRemoveRule       Integer32,
    slbNewCfgVirtServerIpVer            INTEGER,
    slbNewCfgVirtServerIpv6Addr         DisplayString,
    slbNewCfgVirtServerVname     	DisplayString,
    slbNewCfgVirtServerFreeServiceIdx   INTEGER,
    slbNewCfgVirtServerCReset           INTEGER
    }

slbNewCfgVirtServerIndex OBJECT-TYPE
    SYNTAX  Integer32
    MAX-ACCESS  read-only
    STATUS  current
    DESCRIPTION
        "The Virtual Server Number" 
    ::= { slbNewCfgVirtualServerEntry 1 }

slbNewCfgVirtServerIpAddress OBJECT-TYPE
    SYNTAX  IpAddress
    MAX-ACCESS  read-create
    STATUS  current
    DESCRIPTION
        "IP address of the virtual server." 
    ::= { slbNewCfgVirtualServerEntry 2 }

slbNewCfgVirtServerLayer3Only OBJECT-TYPE 
    SYNTAX  INTEGER {
        layer3Only(1),
	disabled(2)
	}
    MAX-ACCESS  read-create 
    STATUS  current 
    DESCRIPTION 
        "Enable or disable layer3 only balancing."  
    ::= { slbNewCfgVirtualServerEntry 3 }

slbNewCfgVirtServerState OBJECT-TYPE 
    SYNTAX  INTEGER {
	enabled(2),
	disabled(3)
	}
    MAX-ACCESS  read-create 
    STATUS  current 
    DESCRIPTION 
        "Enable or disable the virtual server."  
    ::= { slbNewCfgVirtualServerEntry 4 }

slbNewCfgVirtServerDname OBJECT-TYPE 
    SYNTAX  DisplayString (SIZE(0..64))
    MAX-ACCESS  read-create 
    STATUS  current 
    DESCRIPTION 
        "The domain name of the virtual server."  
    ::= { slbNewCfgVirtualServerEntry 6 }

slbNewCfgVirtServerBwmContract OBJECT-TYPE 
    SYNTAX  Integer32
    MAX-ACCESS  read-create 
    STATUS  current 
    DESCRIPTION 
        "The default BW contract number of the virtual server."
    ::= { slbNewCfgVirtualServerEntry 7 }

slbNewCfgVirtServerDelete OBJECT-TYPE
    SYNTAX  INTEGER {
        other(1),
        delete(2)
        }
    MAX-ACCESS  read-create
    STATUS  current
    DESCRIPTION
        "By setting the value to delete(2), the entire row is deleted."
    ::= { slbNewCfgVirtualServerEntry 8 }

slbNewCfgVirtServerWeight OBJECT-TYPE
    SYNTAX  INTEGER (1..48)
    MAX-ACCESS  read-create
    STATUS  current
    DESCRIPTION
        "The virtual server Global SLB weight."
    ::= { slbNewCfgVirtualServerEntry 9 }

slbNewCfgVirtServerAvail OBJECT-TYPE
    SYNTAX  INTEGER (1..48)
    MAX-ACCESS  read-create
    STATUS  current
    DESCRIPTION
        "The virtual server Global SLB availability."
    ::= { slbNewCfgVirtualServerEntry 10 }

slbNewCfgVirtServerRule OBJECT-TYPE
    SYNTAX OCTET STRING
    MAX-ACCESS read-only
    STATUS current
    DESCRIPTION
        "The Global SLB rules for the domain.
         The rules are presented in bitmap format.

         in receiving order:

             OCTET 1  OCTET 2  .....
             xxxxxxxx xxxxxxxx .....
             |     || |_ server 9
             |     ||
             |     ||___ server 8
             |     |____ server 7
             |       .    .   .
             |__________ server 1

         where x : 1 - The represented rule belongs to the domain
                   0 - The represented rule does not belong to the domain"
    ::= { slbNewCfgVirtualServerEntry 11 }

slbNewCfgVirtServerAddRule OBJECT-TYPE
    SYNTAX  Integer32
    MAX-ACCESS  read-create
    STATUS  current
    DESCRIPTION
        "The rule to be added to the domain. When read, 0 is returned."
    ::= { slbNewCfgVirtualServerEntry 12 }

slbNewCfgVirtServerRemoveRule OBJECT-TYPE
    SYNTAX  Integer32
    MAX-ACCESS  read-create
    STATUS  current
    DESCRIPTION
        "The rule to be removed from the domain. When read, 0 is returned."
    ::= { slbNewCfgVirtualServerEntry 13 }

slbNewCfgVirtServerVname OBJECT-TYPE 
    SYNTAX  DisplayString (SIZE(0..32))
    MAX-ACCESS  read-create 
    STATUS  current 
    DESCRIPTION 
        "The name of the virtual server."  
    ::= { slbNewCfgVirtualServerEntry 14 }


slbNewCfgVirtServerIpVer OBJECT-TYPE
    SYNTAX  INTEGER{
        ipv4(1),
        ipv6(2)
        }
    MAX-ACCESS read-create
    STATUS  current
    DESCRIPTION
        "The type of IP address."
    ::= { slbNewCfgVirtualServerEntry 15 }

slbNewCfgVirtServerIpv6Addr OBJECT-TYPE
    SYNTAX  DisplayString  (SIZE(0..40))
    MAX-ACCESS read-create
    STATUS  current
    DESCRIPTION
        "The IPv6 address of the virtual server. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { slbNewCfgVirtualServerEntry 16 }


slbNewCfgVirtServerFreeServiceIdx OBJECT-TYPE
    SYNTAX  INTEGER(0..8)
    MAX-ACCESS  read-only
    STATUS  current
    DESCRIPTION
        "The first free service index number of the virtual server.
         Value 0 will be returned when all 8 virtual services are 
         configured for a virtual server."
    ::= { slbNewCfgVirtualServerEntry 17 }

slbNewCfgVirtServerCReset OBJECT-TYPE
    SYNTAX  INTEGER{
        enabled(1),
        disabled(2)
        }
    MAX-ACCESS  read-create
    STATUS  current
    DESCRIPTION
        "Enable/disable client connection reset for invalid VPORT."
    ::= { slbNewCfgVirtualServerEntry 18 }

-- Server load balancing - Virtual Services Table 
slbVirtServicesTableMaxSize OBJECT-TYPE
    SYNTAX  Integer32 
    MAX-ACCESS  read-only 
    STATUS  current 
    DESCRIPTION 
        "The maximum number of entries in SLB Virtual Services Table." 
    ::= { virtualServerCfg 4 }

slbCurCfgVirtServicesTable OBJECT-TYPE
    SYNTAX  SEQUENCE OF SlbCurCfgVirtServicesEntry
    MAX-ACCESS  not-accessible
    STATUS  current
    DESCRIPTION
        "The table of virtual services."
    ::= { virtualServerCfg 5 }

slbCurCfgVirtServicesEntry OBJECT-TYPE
    SYNTAX  SlbCurCfgVirtServicesEntry
    MAX-ACCESS  not-accessible
    STATUS  current
    DESCRIPTION
        "A row in the virtual services table."
    INDEX   { slbCurCfgVirtServIndex, slbCurCfgVirtServiceIndex }
    ::= { slbCurCfgVirtServicesTable 1 }

SlbCurCfgVirtServicesEntry ::= SEQUENCE {
    slbCurCfgVirtServIndex            Integer32,
    slbCurCfgVirtServiceIndex         Integer32,
    slbCurCfgVirtServiceVirtPort      INTEGER,
    slbCurCfgVirtServiceRealGroup     Integer32,
    slbCurCfgVirtServiceRealPort      INTEGER,
    slbCurCfgVirtServiceUDPBalance    INTEGER,
    slbCurCfgVirtServiceHname         DisplayString,
    slbCurCfgVirtServiceBwmContract   Integer32,
    slbCurCfgVirtServiceDirServerRtn  INTEGER,
    slbCurCfgVirtServiceRtspUrlParse  INTEGER,
    slbCurCfgVirtServiceFtpParsing    INTEGER,
    slbCurCfgVirtServiceRemapUDPFrags INTEGER,
    slbCurCfgVirtServiceDnsSlb        INTEGER,
    slbCurCfgVirtServiceResponseCount INTEGER,
    slbCurCfgVirtServicePBind         INTEGER,
    slbCurCfgVirtServiceCname         DisplayString,
    slbCurCfgVirtServiceCoffset       INTEGER,
    slbCurCfgVirtServiceClength       INTEGER,
    slbCurCfgVirtServiceUriCookie     INTEGER,
    slbCurCfgVirtServiceCExpire       DisplayString,
    slbCurCfgVirtServiceCookieMode    INTEGER,
    slbCurCfgVirtServiceDBind         INTEGER,
    slbCurCfgVirtServiceHttpSlb       INTEGER,
    slbCurCfgVirtServiceHttpSlbOption INTEGER,
    slbCurCfgVirtServiceHttpSlb2      INTEGER,
    slbCurCfgVirtServiceHttpHdrName   DisplayString,
    slbCurCfgVirtServiceUrlHashLen    INTEGER,
    slbCurCfgVirtServiceCookieDname   INTEGER,
    slbCurCfgVirtServiceClsRST        INTEGER,
    slbCurCfgVirtServiceDirect        INTEGER,
    slbCurCfgVirtServiceThash         INTEGER,
    slbCurCfgVirtServiceLdapreset     INTEGER,
    slbCurCfgVirtServiceLdapslb       INTEGER,
    slbCurCfgVirtServiceSip           INTEGER,
    slbCurCfgVirtServiceXForwardedFor INTEGER,
    slbCurCfgVirtServiceHttpRedir     INTEGER,
    slbCurCfgVirtServicePbindRport    INTEGER,
    slbCurCfgVirtServiceEgressPip     INTEGER,
    slbCurCfgVirtServiceWts           INTEGER,
    slbCurCfgVirtServiceTimeOut       INTEGER,
    slbCurCfgVirtServiceSoftGrid      INTEGER,
    slbCurCfgVirtServiceSessionMirror INTEGER,
    slbCurCfgVirtServiceSdpNat        INTEGER,
    slbCurCfgVirtServiceConnPooling   INTEGER,
    slbCurCfgVirtPersistentTimeOut    INTEGER,
    slbCurCfgVirtServiceUhash         INTEGER
}

slbCurCfgVirtServIndex OBJECT-TYPE
    SYNTAX  Integer32
    MAX-ACCESS  read-only
    STATUS  current
    DESCRIPTION
        "The number of the virtual server." 
    ::= { slbCurCfgVirtServicesEntry 1 }

slbCurCfgVirtServiceIndex OBJECT-TYPE 
    SYNTAX  Integer32 
    MAX-ACCESS  read-only 
    STATUS  current 
    DESCRIPTION 
        "The service index. This has no external meaning" 
    ::= { slbCurCfgVirtServicesEntry 2 }


slbCurCfgVirtServiceVirtPort OBJECT-TYPE  
    SYNTAX  INTEGER (9..65534)
    MAX-ACCESS  read-only  
    STATUS  current  
    DESCRIPTION 
        "The layer4 virtual port number of the service."  
    ::= { slbCurCfgVirtServicesEntry 3 } 

slbCurCfgVirtServiceRealGroup OBJECT-TYPE   
    SYNTAX  Integer32   
    MAX-ACCESS  read-only   
    STATUS  current   
    DESCRIPTION 
        "The real server group number for this service."   
    ::= { slbCurCfgVirtServicesEntry 4 }

slbCurCfgVirtServiceRealPort OBJECT-TYPE   
    SYNTAX  INTEGER (0..65534)
    MAX-ACCESS  read-only   
    STATUS  current   
    DESCRIPTION 
        "The layer4 real port number of the service."   
    ::= { slbCurCfgVirtServicesEntry 5 }

slbCurCfgVirtServiceUDPBalance OBJECT-TYPE   
    SYNTAX  INTEGER    {
	udp(2),
	tcp(3),
	stateless(4),
        tcpAndUdp(5)
	}
    MAX-ACCESS  read-only   
    STATUS  current   
    DESCRIPTION 
        "Set protocol for the virtual service to
         UDP or TCP or tcpAndUdp or stateless.
         tcpAndUdp is applicable only to ip service."
    ::= { slbCurCfgVirtServicesEntry 6 }

slbCurCfgVirtServiceHname OBJECT-TYPE 
    SYNTAX  DisplayString (SIZE(0..34))
    MAX-ACCESS  read-only 
    STATUS  current 
    DESCRIPTION 
        "The host name of the virtual service."  
    ::= { slbCurCfgVirtServicesEntry 7 }

slbCurCfgVirtServiceBwmContract OBJECT-TYPE   
    SYNTAX  Integer32   
    MAX-ACCESS  read-only   
    STATUS  current   
    DESCRIPTION 
        "The BWM contract number for this service."   
    ::= { slbCurCfgVirtServicesEntry 8 }

slbCurCfgVirtServiceDirServerRtn OBJECT-TYPE   
    SYNTAX  INTEGER {
	enabled(1),
	disabled(2)
	}
    MAX-ACCESS  read-only   
    STATUS  current   
    DESCRIPTION 
        "Enable or disable direct server return feature. To translate only 
         MAC addresses in performing server load balancing when enabled.
         This allow servers to return directly to client since IP addresses 
         have not been changed."
    ::= { slbCurCfgVirtServicesEntry 9 }

slbCurCfgVirtServiceRtspUrlParse OBJECT-TYPE   
    SYNTAX  INTEGER {
        none(1),
        l4hash(2),
        hash(3),
        patternMatch(4)
	}
    MAX-ACCESS  read-only
    STATUS  current   
    DESCRIPTION 
        "Select RTSP URL load balancing type."
    ::= { slbCurCfgVirtServicesEntry 10 }


slbCurCfgVirtServiceDBind OBJECT-TYPE   
    SYNTAX  INTEGER {
	enabled(1),
	disabled(2),
	forceproxy(3)
	}
    MAX-ACCESS  read-only
    STATUS  current   
    DESCRIPTION 
        "Enable/disable/forceproxy delayed binding."
    ::= { slbCurCfgVirtServicesEntry 11 }


slbCurCfgVirtServiceFtpParsing OBJECT-TYPE
    SYNTAX  INTEGER {
	enabled(1),
	disabled(2)
	}
    MAX-ACCESS  read-only
    STATUS  current
    DESCRIPTION
        "Enable or Disable the ftp parsing for the virtual service."
    ::= { slbCurCfgVirtServicesEntry 12 }

slbCurCfgVirtServiceRemapUDPFrags OBJECT-TYPE   
    SYNTAX INTEGER {
        enabled(1),
        disabled(2)
        }
    MAX-ACCESS read-only   
    STATUS current   
    DESCRIPTION 
        "Enable or disable remapping UDP server fragments"   
    ::= { slbCurCfgVirtServicesEntry 13 }

slbCurCfgVirtServiceDnsSlb OBJECT-TYPE   
    SYNTAX  INTEGER {
        enabled(1),
	disabled(2)
	}
    MAX-ACCESS  read-only   
    STATUS  current   
    DESCRIPTION 
        "Enable or disable DNS query load balancing."
    ::= { slbCurCfgVirtServicesEntry 14 }

slbCurCfgVirtServiceResponseCount OBJECT-TYPE 
    SYNTAX  INTEGER (1..16)
    MAX-ACCESS  read-only 
    STATUS  current 
    DESCRIPTION 
        "The number of cookie search response count."
    ::= { slbCurCfgVirtServicesEntry 15 }

slbCurCfgVirtServicePBind OBJECT-TYPE   
    SYNTAX  INTEGER {
	clientip(2),
	disabled(3),
	sslid(4),
        cookie(5)
	}
    MAX-ACCESS  read-only   
    STATUS  current   
    DESCRIPTION 
        "Enable or disable persistent bindings for the virtual port."
    ::= { slbCurCfgVirtServicesEntry 16 }

slbCurCfgVirtServiceCname OBJECT-TYPE 
    SYNTAX  DisplayString (SIZE(0..20))
    MAX-ACCESS  read-only 
    STATUS  current 
    DESCRIPTION 
        "The cookie name of the virtual server used for cookie load balance."  
    ::= { slbCurCfgVirtServicesEntry 17 }

slbCurCfgVirtServiceCoffset OBJECT-TYPE
    SYNTAX  INTEGER (1..64)
    MAX-ACCESS  read-only 
    STATUS  current
    DESCRIPTION
        "The starting byte offset of the cookie value." 
    ::= { slbCurCfgVirtServicesEntry 18 }

slbCurCfgVirtServiceClength OBJECT-TYPE
    SYNTAX  INTEGER (1..64)
    MAX-ACCESS  read-only
    STATUS  current
    DESCRIPTION
        "The number of bytes to extract from the cookie value." 
    ::= { slbCurCfgVirtServicesEntry 19 }

slbCurCfgVirtServiceUriCookie OBJECT-TYPE 
    SYNTAX  INTEGER {
	enabled(1),
	disabled(2)
	}
    MAX-ACCESS  read-only 
    STATUS  current 
    DESCRIPTION 
        "Enable or disable cookie search in URI"  
    ::= { slbCurCfgVirtServicesEntry 20}

slbCurCfgVirtServiceCExpire OBJECT-TYPE 
    SYNTAX  DisplayString (SIZE(0..20))
    MAX-ACCESS  read-only 
    STATUS  current 
    DESCRIPTION 
        "The cookie expire of the virtual server used for insert cookie load
         balance depending on the mode it has the following format 
         <MM/dd/yy[@hh:mm]> absolute mode or <days[:hours[:minutes]]>
         for relative mode."  
    ::= { slbCurCfgVirtServicesEntry 21 }

slbCurCfgVirtServiceCookieMode OBJECT-TYPE   
    SYNTAX INTEGER {
        rewrite(1),
        passive(2),
	insert(3),
	disabled(4)
        }
    MAX-ACCESS read-only 
    STATUS current   
    DESCRIPTION 
        "Select cookie persistence mode."
    ::= { slbCurCfgVirtServicesEntry 22 }

slbCurCfgVirtServiceHttpSlb OBJECT-TYPE   
    SYNTAX  INTEGER {
	disabled(1),
        urlslb(2),
        urlhash(3),
        cookie(4),
        host(5),
        browser(6),
        others(7),
        headerhash(8),
	version(9)
	}
    MAX-ACCESS  read-only   
    STATUS  current   
    DESCRIPTION 
        "Select HTTP server loadbalancing for the virtual port."   
    ::= { slbCurCfgVirtServicesEntry 23 }

slbCurCfgVirtServiceHttpSlbOption OBJECT-TYPE   
    SYNTAX  INTEGER {
	and(1),
        or(2),
        none(3)
	}
    MAX-ACCESS  read-only   
    STATUS  current   
    DESCRIPTION 
        "Select HTTP server loadbalancing for the virtual port."   
    ::= { slbCurCfgVirtServicesEntry 24 }

slbCurCfgVirtServiceHttpSlb2 OBJECT-TYPE   
    SYNTAX  INTEGER {
	disabled(1),
        urlslb(2),
        urlhash(3),
        cookie(4),
        host(5),
        browser(6),
        others(7),
        headerhash(8),
	version(9)
	}
    MAX-ACCESS  read-only   
    STATUS  current   
    DESCRIPTION 
        "Select HTTP server loadbalancing for the virtual port."   
    ::= { slbCurCfgVirtServicesEntry 25 }

slbCurCfgVirtServiceHttpHdrName OBJECT-TYPE 
    SYNTAX  DisplayString  (SIZE(0..32))
    MAX-ACCESS  read-only 
    STATUS  current 
    DESCRIPTION 
        "The HTTP header name of the virtual server."
    ::= { slbCurCfgVirtServicesEntry 26 }

slbCurCfgVirtServiceUrlHashLen OBJECT-TYPE 
    SYNTAX  INTEGER (0..255)
    MAX-ACCESS  read-only 
    STATUS  current 
    DESCRIPTION 
        "The number of bytes used to hash onto server, A zero means
         URL hashing disabled."
    ::= { slbCurCfgVirtServicesEntry 27}

slbCurCfgVirtServiceDirect OBJECT-TYPE   
    SYNTAX  INTEGER {
        enabled(1),
	disabled(2)
	}
    MAX-ACCESS  read-only   
    STATUS  current   
    DESCRIPTION 
        "Enable or disable DAM for this service." 
    ::= { slbCurCfgVirtServicesEntry 28 }

slbCurCfgVirtServiceThash OBJECT-TYPE   
    SYNTAX  INTEGER {
        sip(1),
        sip-sport(2)
        }
    MAX-ACCESS  read-only
    STATUS  current   
    DESCRIPTION 
        "Set hash parameter."
    ::= { slbCurCfgVirtServicesEntry 29 }

slbCurCfgVirtServiceLdapreset OBJECT-TYPE 
    SYNTAX  INTEGER {
        enabled(1),
        disabled(2)
        }
    MAX-ACCESS  read-only 
    STATUS  current 
    DESCRIPTION 
        "Enable or disable LDAP Server Reset"  
    ::= { slbCurCfgVirtServicesEntry 30 }

slbCurCfgVirtServiceLdapslb OBJECT-TYPE 
    SYNTAX  INTEGER {
        enabled(1),
        disabled(2)
        }
    MAX-ACCESS  read-only 
    STATUS  current 
    DESCRIPTION 
        "Enable or disable LDAP Server load balancing"  
    ::= { slbCurCfgVirtServicesEntry 31 }

slbCurCfgVirtServiceSip OBJECT-TYPE   
    SYNTAX  INTEGER {
        enabled(1),
	disabled(2)
	}
    MAX-ACCESS  read-only   
    STATUS  current   
    DESCRIPTION 
        "Enable/disable SIP load balancing."
    ::= { slbCurCfgVirtServicesEntry 32 }

slbCurCfgVirtServiceXForwardedFor OBJECT-TYPE   
    SYNTAX  INTEGER {
        enabled(1),
	disabled(2)
	}
    MAX-ACCESS  read-only
    STATUS  current   
    DESCRIPTION 
        "Enable/disable X-Forwarded-For for proxy mode."
    ::= { slbCurCfgVirtServicesEntry 33 }

slbCurCfgVirtServiceHttpRedir OBJECT-TYPE
    SYNTAX  INTEGER {
        enabled(1),
        disabled(2)
        }
    MAX-ACCESS  read-only
    STATUS  current
    DESCRIPTION
        "Enable/disable HTTP/HTTPS redirect for GSLB."
    ::= { slbCurCfgVirtServicesEntry 34 }

slbCurCfgVirtServicePbindRport OBJECT-TYPE   
    SYNTAX  INTEGER {
        enabled(1),
	disabled(2)
	}
    MAX-ACCESS  read-only
    STATUS  current   
    DESCRIPTION 
        "Enable or disable use of rport in the session lookup for a persistent
         session."
    ::= { slbCurCfgVirtServicesEntry 35 }
    
slbCurCfgVirtServiceEgressPip OBJECT-TYPE   
    SYNTAX  INTEGER {
        enabled(1),
	disabled(2)
	}
    MAX-ACCESS  read-only
    STATUS  current   
    DESCRIPTION 
        "Enable/disable pip selection based on egress port/vlan."
    ::= { slbCurCfgVirtServicesEntry 36 }

slbCurCfgVirtServiceCookieDname OBJECT-TYPE
    SYNTAX INTEGER {
        enabled(1),
        disabled(2)
        }
    MAX-ACCESS read-only
    STATUS current
    DESCRIPTION
        "Select dname for insert cookie persistence mode."
    ::= { slbCurCfgVirtServicesEntry 37 }
    
slbCurCfgVirtServiceWts OBJECT-TYPE
    SYNTAX INTEGER {
        enabled(1),
        disabled(2)
        }
    MAX-ACCESS read-only
    STATUS current
    DESCRIPTION
        "Enable or disable WTS loadbalancing and persistence."
    ::= { slbCurCfgVirtServicesEntry 38 }

slbCurCfgVirtServiceUhash OBJECT-TYPE
    SYNTAX INTEGER {
        enabled(1),
        disabled(2)
        }
    MAX-ACCESS read-only
    STATUS current
    DESCRIPTION
        "Enable when there is no Session Directory server."
    ::= { slbCurCfgVirtServicesEntry 39 }


slbCurCfgVirtServiceTimeOut OBJECT-TYPE
    SYNTAX  INTEGER (0..32768)
    MAX-ACCESS  read-only
    STATUS  current
    DESCRIPTION
        "The maximum number of minutes an inactive connection remains open."
    ::= { slbCurCfgVirtServicesEntry 40 }

slbCurCfgVirtServiceSessionMirror OBJECT-TYPE
    SYNTAX  INTEGER {
        enabled(1),
        disabled(2)
        }
    MAX-ACCESS  read-only
    STATUS  current
    DESCRIPTION
        "Enable/disable session mirroring."
    ::= { slbCurCfgVirtServicesEntry 42 }

slbCurCfgVirtServiceSoftGrid OBJECT-TYPE
    SYNTAX  INTEGER {
        enabled(1),
        disabled(2)
        }
    MAX-ACCESS  read-only
    STATUS  current
    DESCRIPTION
        "Enable/disable softgrid load balancing."
    ::= { slbCurCfgVirtServicesEntry 43 }

slbCurCfgVirtServiceSdpNat OBJECT-TYPE
    SYNTAX  INTEGER {
        enabled(1),
        disabled(2)
        }
    MAX-ACCESS  read-only
    STATUS  current
    DESCRIPTION
        "Enable/disable SIP Media portal NAT."
    ::= { slbCurCfgVirtServicesEntry 41 }

slbCurCfgVirtServiceConnPooling OBJECT-TYPE
    SYNTAX  INTEGER {
        enabled(1),
            disabled(2)
    }
    MAX-ACCESS  read-only
    STATUS  current
    DESCRIPTION
        "Enable/disable connection pooling for HTTP traffic."
    ::= { slbCurCfgVirtServicesEntry 44 }

slbCurCfgVirtPersistentTimeOut OBJECT-TYPE
    SYNTAX  INTEGER (0..32768)
    MAX-ACCESS  read-only
    STATUS  current
    DESCRIPTION
        "The maximum number of minutes a persistent session should exist."
    ::= { slbCurCfgVirtServicesEntry 45 }

slbCurCfgVirtServiceClsRST OBJECT-TYPE   
    SYNTAX  INTEGER {
	enabled(1),
	disabled(2)
	}
    MAX-ACCESS  read-only
    STATUS  current   
    DESCRIPTION 
        "Enable or disable Send RST on connection close."
    ::= { slbCurCfgVirtServicesEntry 47 }


slbCurCfgVirtServicesSecondPartTable OBJECT-TYPE
    SYNTAX  SEQUENCE OF SlbCurCfgVirtServicesSecondPartEntry
    MAX-ACCESS  not-accessible
    STATUS  current
    DESCRIPTION
        "The table of virtual Services."
    ::= { virtualServerCfg 12 }

slbCurCfgVirtServicesSecondPartEntry OBJECT-TYPE
    SYNTAX  SlbCurCfgVirtServicesSecondPartEntry
    MAX-ACCESS  not-accessible
    STATUS  current
    DESCRIPTION
        "A row in the virtual services table."
    INDEX   { slbCurCfgVirtServSecondPartIndex, slbCurCfgVirtServiceSecondPartIndex }
    ::= { slbCurCfgVirtServicesSecondPartTable 1 }

SlbCurCfgVirtServicesSecondPartEntry ::= SEQUENCE {
    slbCurCfgVirtServSecondPartIndex            Integer32,
    slbCurCfgVirtServiceSecondPartIndex         Integer32,

    slbCurCfgVirtServiceConnmgtStatus  INTEGER,
    slbCurCfgVirtServiceConnmgtTimeout INTEGER,
    slbCurCfgVirtServiceCachepol      DisplayString,
    slbCurCfgVirtServiceComppol       DisplayString,
    slbCurCfgVirtServiceSSLpol        DisplayString,
    slbCurCfgVirtServiceServCert      DisplayString,
    slbCurCfgVirtServiceHttpmodList   DisplayString,
    slbCurCfgVirtServiceCloaksrv      INTEGER,

    slbCurCfgVirtServErrcodeStatus    INTEGER,
    slbCurCfgVirtServErrcodeMatch     DisplayString,
    slbCurCfgVirtServErrcodeHttpRedir INTEGER,
    slbCurCfgVirtServErrcodeUrl       DisplayString,
    slbCurCfgVirtServErrcode          DisplayString,
    slbCurCfgVirtServErrcodeNew       DisplayString,
    slbCurCfgVirtServErrcodeReason    DisplayString,
    slbCurCfgVirtServUrlchangStatus     INTEGER,
    slbCurCfgVirtServUrlchangHostType   INTEGER
}

slbCurCfgVirtServSecondPartIndex OBJECT-TYPE
    SYNTAX  Integer32
    MAX-ACCESS  read-only
    STATUS  current
    DESCRIPTION
        "The number of the virtual server." 
    ::= { slbCurCfgVirtServicesSecondPartEntry 1 }

slbCurCfgVirtServiceSecondPartIndex OBJECT-TYPE 
    SYNTAX  Integer32 
    MAX-ACCESS  read-only 
    STATUS  current 
    DESCRIPTION 
        "The service index. This has no external meaning" 
    ::= { slbCurCfgVirtServicesSecondPartEntry 2 }


slbCurCfgVirtServiceConnmgtStatus OBJECT-TYPE
    SYNTAX  INTEGER {
        disabled(0),
        pooling(1),
        muxenabled(2)
        }
    MAX-ACCESS  read-only
    STATUS  current
    DESCRIPTION
        "Connection management configuration for HTTP traffic(Enable/disable/pooling) [Default: Disable]."
    ::= { slbCurCfgVirtServicesSecondPartEntry 3 }

slbCurCfgVirtServiceConnmgtTimeout OBJECT-TYPE
    SYNTAX  INTEGER (0..32768)
    MAX-ACCESS  read-only
    STATUS  current
    DESCRIPTION
        "Connection management server side connection idle timeout in minutes [0-32768] [Default: 10]."
    ::= { slbCurCfgVirtServicesSecondPartEntry 4 }

slbCurCfgVirtServiceCachepol OBJECT-TYPE
    SYNTAX  DisplayString  (SIZE(0..32))
    MAX-ACCESS  read-only
    STATUS  current
    DESCRIPTION
        "Cache policy name associated with this virtual service."
    ::= { slbCurCfgVirtServicesSecondPartEntry 5 }

slbCurCfgVirtServiceComppol OBJECT-TYPE
    SYNTAX  DisplayString  (SIZE(0..32))
    MAX-ACCESS  read-only
    STATUS  current
    DESCRIPTION
        "Compression policy name associated with this virtual service."
    ::= { slbCurCfgVirtServicesSecondPartEntry 6 }

slbCurCfgVirtServiceSSLpol OBJECT-TYPE
    SYNTAX  DisplayString  (SIZE(0..32))
    MAX-ACCESS  read-only
    STATUS  current
    DESCRIPTION
        "SSL policy name associated with this virtual service."
    ::= { slbCurCfgVirtServicesSecondPartEntry 7 }

slbCurCfgVirtServiceServCert OBJECT-TYPE
    SYNTAX  DisplayString  (SIZE(0..32))
    MAX-ACCESS  read-only
    STATUS  current
    DESCRIPTION
        "Server Certificate name associated with this virtual service."
    ::= { slbCurCfgVirtServicesSecondPartEntry 8 }

slbCurCfgVirtServiceHttpmodList OBJECT-TYPE
    SYNTAX  DisplayString  (SIZE(0..32))
    MAX-ACCESS  read-only
    STATUS  current
    DESCRIPTION
        "HTTP Content Modifications Rule-list associated with this virtual service."
    ::= { slbCurCfgVirtServicesSecondPartEntry 9 }

slbCurCfgVirtServiceCloaksrv OBJECT-TYPE
    SYNTAX  INTEGER {
        enabled(1),
        disabled(2)
        }
    MAX-ACCESS  read-only
    STATUS  current
    DESCRIPTION
        "Enable/disable server cloaking."
    ::= { slbCurCfgVirtServicesSecondPartEntry 10 }

slbCurCfgVirtServErrcodeStatus OBJECT-TYPE
    SYNTAX  INTEGER {
        enabled(1),
        disabled(2),
        clear(3)
        }
    MAX-ACCESS  read-only
    STATUS  current
    DESCRIPTION
        "Enable/disable/clear error-code configuration."
    ::= { slbCurCfgVirtServicesSecondPartEntry 11 }

slbCurCfgVirtServErrcodeMatch OBJECT-TYPE
    SYNTAX  DisplayString (SIZE (0..64))
    MAX-ACCESS  read-only
    STATUS  current
    DESCRIPTION
        "Match error-code(s), e.g 203,204 ."
    ::= { slbCurCfgVirtServicesSecondPartEntry 12 }

slbCurCfgVirtServErrcodeHttpRedir OBJECT-TYPE
    SYNTAX  INTEGER {
        yes(1),
        no(2)
    }
    MAX-ACCESS  read-only
    STATUS  current
    DESCRIPTION
        "Use http redirection [yes/no] [Default: yes]."
    ::= { slbCurCfgVirtServicesSecondPartEntry 13 }

slbCurCfgVirtServErrcodeUrl OBJECT-TYPE
    SYNTAX  DisplayString (SIZE(0..240))
    MAX-ACCESS  read-only
    STATUS  current
    DESCRIPTION
        "URL for redirection."
    ::= { slbCurCfgVirtServicesSecondPartEntry 14 }


slbCurCfgVirtServErrcode OBJECT-TYPE
    SYNTAX  DisplayString (SIZE(0..3))
    MAX-ACCESS  read-only
    STATUS  current
    DESCRIPTION
        "Set error code [Default: 302]."
    ::= { slbCurCfgVirtServicesSecondPartEntry 15 }

slbCurCfgVirtServErrcodeNew OBJECT-TYPE
    SYNTAX  DisplayString (SIZE(0..3))
    MAX-ACCESS  read-only
    STATUS  current
    DESCRIPTION
        "Enter Cur error code [Default: 302]."
    ::= { slbCurCfgVirtServicesSecondPartEntry 16 }

slbCurCfgVirtServErrcodeReason OBJECT-TYPE
    SYNTAX  DisplayString (SIZE(0..128))
    MAX-ACCESS  read-only
    STATUS  current
    DESCRIPTION
        "Enter error reason."
    ::= { slbCurCfgVirtServicesSecondPartEntry 17 }

slbCurCfgVirtServUrlchangStatus OBJECT-TYPE
    SYNTAX  INTEGER {
        enable(1),
        disable(2),
        clear(3)
    }
    MAX-ACCESS  read-only
    STATUS  current
    DESCRIPTION
        "Enter enabled/disabled/clear [Default: clear]."
    ::= { slbCurCfgVirtServicesSecondPartEntry 18 }

slbCurCfgVirtServUrlchangHostType OBJECT-TYPE
    SYNTAX  INTEGER {
        sufx(1),
        prefx(2),
        eq(3),
        incl(4),
        any(5)
    }
    MAX-ACCESS  read-only
    STATUS  current
    DESCRIPTION
        "Enter hostname match type [sufx|prefx|eq|incl|any] [Default: any]"
    ::= { slbCurCfgVirtServicesSecondPartEntry 19 }


slbCurCfgVirtServicesThirdPartTable OBJECT-TYPE
    SYNTAX  SEQUENCE OF SlbCurCfgVirtServicesThirdPartEntry
    MAX-ACCESS  not-accessible
    STATUS  current
    DESCRIPTION
        "The table of virtual Services."
    ::= { virtualServerCfg 13 }

slbCurCfgVirtServicesThirdPartEntry OBJECT-TYPE
    SYNTAX  SlbCurCfgVirtServicesThirdPartEntry
    MAX-ACCESS  not-accessible
    STATUS  current
    DESCRIPTION
        "A row in the virtual services table."
    INDEX   { slbCurCfgVirtServThirdPartIndex, slbCurCfgVirtServiceThirdPartIndex }
    ::= { slbCurCfgVirtServicesThirdPartTable 1 }

SlbCurCfgVirtServicesThirdPartEntry ::= SEQUENCE {
    slbCurCfgVirtServThirdPartIndex            Integer32,
    slbCurCfgVirtServiceThirdPartIndex         Integer32,

    slbCurCfgVirtServUrlchangHostName   DisplayString,
    slbCurCfgVirtServUrlchangPathType   INTEGER,
    slbCurCfgVirtServUrlchangPathMatch  DisplayString,
    slbCurCfgVirtServUrlchangPageName   DisplayString,
    slbCurCfgVirtServUrlchangPageType   DisplayString,
    slbCurCfgVirtServUrlchangActnType   INTEGER,
    slbCurCfgVirtServUrlchangPathInsrt  DisplayString,
    slbCurCfgVirtServUrlchangInsrtPostn INTEGER
}


slbCurCfgVirtServThirdPartIndex OBJECT-TYPE
    SYNTAX  Integer32
    MAX-ACCESS  read-only
    STATUS  current
    DESCRIPTION
        "The number of the virtual server." 
    ::= { slbCurCfgVirtServicesThirdPartEntry 1 }

slbCurCfgVirtServiceThirdPartIndex OBJECT-TYPE 
    SYNTAX  Integer32 
    MAX-ACCESS  read-only 
    STATUS  current 
    DESCRIPTION 
        "The service index. This has no external meaning" 
    ::= { slbCurCfgVirtServicesThirdPartEntry 2 }

slbCurCfgVirtServUrlchangHostName OBJECT-TYPE
    SYNTAX  DisplayString (SIZE(0..250))
    MAX-ACCESS  read-only
    STATUS  current
    DESCRIPTION
        "Enter hostname to match."
    ::= { slbCurCfgVirtServicesThirdPartEntry 3 }

slbCurCfgVirtServUrlchangPathType OBJECT-TYPE
    SYNTAX  INTEGER {
        sufx(1),
        prefx(2),
        eq(3),
        incl(4),
        any(5),
        none(6)
    }
    MAX-ACCESS  read-only
    STATUS  current
    DESCRIPTION
        "Enter path match type [sufx|prefx|eq|incl|any]."
    ::= { slbCurCfgVirtServicesThirdPartEntry 4 }

slbCurCfgVirtServUrlchangPathMatch OBJECT-TYPE
    SYNTAX  DisplayString (SIZE(0..250))
    MAX-ACCESS  read-only
    STATUS  current
    DESCRIPTION
        "Enter path to match."
    ::= { slbCurCfgVirtServicesThirdPartEntry 5 }

slbCurCfgVirtServUrlchangPageName OBJECT-TYPE
    SYNTAX  DisplayString (SIZE(0..64))
    MAX-ACCESS  read-only
    STATUS  current
    DESCRIPTION
        "Enter page name to match or none."
    ::= { slbCurCfgVirtServicesThirdPartEntry 6 }

slbCurCfgVirtServUrlchangPageType OBJECT-TYPE
    SYNTAX  DisplayString (SIZE(0..64))
    MAX-ACCESS  read-only
    STATUS  current
    DESCRIPTION
        "Enter page type to match or none."
    ::= { slbCurCfgVirtServicesThirdPartEntry 7 }

slbCurCfgVirtServUrlchangActnType OBJECT-TYPE
    SYNTAX  INTEGER {
        insert(1),
        replace(2),
        remove(3),
        none(4)
    }
    MAX-ACCESS  read-only
    STATUS  current
    DESCRIPTION
        "Enter path action type."
    ::= { slbCurCfgVirtServicesThirdPartEntry 8 }

slbCurCfgVirtServUrlchangPathInsrt OBJECT-TYPE
    SYNTAX  DisplayString (SIZE(0..250))
    MAX-ACCESS  read-only
    STATUS  current
    DESCRIPTION
        "Enter path to insert."
    ::= { slbCurCfgVirtServicesThirdPartEntry 9 }


slbCurCfgVirtServUrlchangInsrtPostn OBJECT-TYPE
    SYNTAX  INTEGER {
        before(1),
        after(2)
    }
    MAX-ACCESS  read-only
    STATUS  current
    DESCRIPTION
        "Insert the specified path before or after the matched section?"
    ::= { slbCurCfgVirtServicesThirdPartEntry 10 }



slbCurCfgVirtServicesFourthPartTable OBJECT-TYPE
    SYNTAX  SEQUENCE OF SlbCurCfgVirtServicesFourthPartEntry
    MAX-ACCESS  not-accessible
    STATUS  current
    DESCRIPTION
        "The table of virtual Services."
    ::= { virtualServerCfg 14 }

slbCurCfgVirtServicesFourthPartEntry OBJECT-TYPE
    SYNTAX  SlbCurCfgVirtServicesFourthPartEntry
    MAX-ACCESS  not-accessible
    STATUS  current
    DESCRIPTION
        "A row in the virtual services table."
    INDEX   { slbCurCfgVirtServFourthPartIndex, slbCurCfgVirtServiceFourthPartIndex }
    ::= { slbCurCfgVirtServicesFourthPartTable 1 }

SlbCurCfgVirtServicesFourthPartEntry ::= SEQUENCE {
    slbCurCfgVirtServFourthPartIndex            Integer32,
    slbCurCfgVirtServiceFourthPartIndex         Integer32,

    slbCurCfgVirtServUrlchangNewPgName  DisplayString,
    slbCurCfgVirtServUrlchangNewPgType  DisplayString,

    slbCurCfgVirtServPathHideStatus     INTEGER,
    slbCurCfgVirtServPathHideHostType   INTEGER,
    slbCurCfgVirtServPathHideHostName   DisplayString,
    slbCurCfgVirtServPathHidePathType   INTEGER,
    slbCurCfgVirtServPathHidePathName   DisplayString,

    slbCurCfgVirtServTextrepStatus      INTEGER,
    slbCurCfgVirtServTextrepAction      INTEGER
}

slbCurCfgVirtServFourthPartIndex OBJECT-TYPE
    SYNTAX  Integer32
    MAX-ACCESS  read-only
    STATUS  current
    DESCRIPTION
        "The number of the virtual server." 
    ::= { slbCurCfgVirtServicesFourthPartEntry 1 }

slbCurCfgVirtServiceFourthPartIndex OBJECT-TYPE 
    SYNTAX  Integer32 
    MAX-ACCESS  read-only 
    STATUS  current 
    DESCRIPTION 
        "The service index. This has no external meaning" 
    ::= { slbCurCfgVirtServicesFourthPartEntry 2 }

slbCurCfgVirtServUrlchangNewPgName OBJECT-TYPE
    SYNTAX  DisplayString (SIZE(0..64))
    MAX-ACCESS  read-only
    STATUS  current
    DESCRIPTION
        "Enter Cur page name or none."
    ::= { slbCurCfgVirtServicesFourthPartEntry 3 }

slbCurCfgVirtServUrlchangNewPgType OBJECT-TYPE
    SYNTAX  DisplayString (SIZE(0..64))
    MAX-ACCESS  read-only
    STATUS  current
    DESCRIPTION
        "Enter Cur page type or none."
    ::= { slbCurCfgVirtServicesFourthPartEntry 4 }

slbCurCfgVirtServPathHideStatus OBJECT-TYPE
    SYNTAX  INTEGER {
        enable(1),
        disable(2),
        clear(3)
    }
    MAX-ACCESS  read-only
    STATUS  current
    DESCRIPTION
        "Enter enabled/disabled/clear [Default: clear]."
    ::= { slbCurCfgVirtServicesFourthPartEntry 5 }

slbCurCfgVirtServPathHideHostType OBJECT-TYPE
    SYNTAX  INTEGER {
        sufx(1),
        prefx(2),
        eq(3),
        incl(4),
        any(5)
    }
    MAX-ACCESS  read-only
    STATUS  current
    DESCRIPTION
        "Enter hostname type [sufx|prefx|eq|incl|any] [Default: any]."
    ::= { slbCurCfgVirtServicesFourthPartEntry 6 }

slbCurCfgVirtServPathHideHostName OBJECT-TYPE
    SYNTAX  DisplayString (SIZE(0..250))
    MAX-ACCESS  read-only
    STATUS  current
    DESCRIPTION
        "Enter hostname to match."
    ::= { slbCurCfgVirtServicesFourthPartEntry 7 }

slbCurCfgVirtServPathHidePathType OBJECT-TYPE
    SYNTAX  INTEGER {
        sufx(1),
        prefx(2),
        eq(3),
        none(4)
    }
    MAX-ACCESS  read-only
    STATUS  current
    DESCRIPTION
        "Enter path match type [sufx|prefx|eq|none]."
    ::= { slbCurCfgVirtServicesFourthPartEntry 8 }

slbCurCfgVirtServPathHidePathName OBJECT-TYPE
    SYNTAX  DisplayString (SIZE(0..250))
    MAX-ACCESS  read-only
    STATUS  current
    DESCRIPTION
        "Enter path to remove."
    ::= { slbCurCfgVirtServicesFourthPartEntry 9 }

slbCurCfgVirtServTextrepStatus OBJECT-TYPE
    SYNTAX  INTEGER {
        enable(1),
        disable(2),
        clear(3)
    }
    MAX-ACCESS  read-only
    STATUS  current
    DESCRIPTION
        "Enter enabled/disabled/clear [Default: clear]."
    ::= { slbCurCfgVirtServicesFourthPartEntry 10 }

slbCurCfgVirtServTextrepAction OBJECT-TYPE
    SYNTAX  INTEGER {
        none(0),
        replace(1),
        remove(2)
    }
    MAX-ACCESS  read-only
    STATUS  current
    DESCRIPTION
        "Enter action [replace|remove|none]."
    ::= { slbCurCfgVirtServicesFourthPartEntry 11 }




slbCurCfgVirtServicesFifthPartTable OBJECT-TYPE
    SYNTAX  SEQUENCE OF SlbCurCfgVirtServicesFifthPartEntry
    MAX-ACCESS  not-accessible
    STATUS  current
    DESCRIPTION
        "The table of virtual Services."
    ::= { virtualServerCfg 15 }

slbCurCfgVirtServicesFifthPartEntry OBJECT-TYPE
    SYNTAX  SlbCurCfgVirtServicesFifthPartEntry
    MAX-ACCESS  not-accessible
    STATUS  current
    DESCRIPTION
        "A row in the virtual services table."
    INDEX   { slbCurCfgVirtServFifthPartIndex, slbCurCfgVirtServiceFifthPartIndex }
    ::= { slbCurCfgVirtServicesFifthPartTable 1 }

SlbCurCfgVirtServicesFifthPartEntry ::= SEQUENCE {

    slbCurCfgVirtServFifthPartIndex            Integer32,
    slbCurCfgVirtServiceFifthPartIndex         Integer32,

    slbCurCfgVirtServTextrepMatchText   DisplayString,
    slbCurCfgVirtServTextrepReplacTxt   DisplayString,

    slbCurCfgVirtServApplicationType    INTEGER,
    slbCurCfgVirtServiceName          DisplayString,
    slbCurCfgVirtServiceAction        INTEGER,
    slbCurCfgVirtServiceRedirect      DisplayString,

    slbCurCfgVirtServiceServCertGrpMark INTEGER,
    slbCurCfgVirtServiceDnsType         INTEGER,
    slbCurCfgVirtServiceClntproxType    INTEGER,
    slbCurCfgVirtServiceZerowinSize     INTEGER,
    slbCurCfgVirtServiceCookiePath    DisplayString,
    slbCurCfgVirtServiceCookieSecure    INTEGER,
    slbCurCfgVirtServiceNoRtsp          INTEGER,
    slbCurCfgVirtServiceCkRebind        INTEGER,
    slbCurCfgVirtServiceParseLimit      INTEGER,
    slbCurCfgVirtServiceParseLength     INTEGER,
    slbCurCfgVirtServiceUriNorm         INTEGER
}

slbCurCfgVirtServFifthPartIndex OBJECT-TYPE
    SYNTAX  Integer32
    MAX-ACCESS  read-only
    STATUS  current
    DESCRIPTION
        "The number of the virtual server." 
    ::= { slbCurCfgVirtServicesFifthPartEntry 1 }

slbCurCfgVirtServiceFifthPartIndex OBJECT-TYPE 
    SYNTAX  Integer32 
    MAX-ACCESS  read-only 
    STATUS  current 
    DESCRIPTION 
        "The service index. This has no external meaning" 
    ::= { slbCurCfgVirtServicesFifthPartEntry 2 }

slbCurCfgVirtServTextrepMatchText OBJECT-TYPE
    SYNTAX  DisplayString (SIZE(0..128))
    MAX-ACCESS  read-only
    STATUS  current
    DESCRIPTION
        "Enter text to be replaced."
    ::= { slbCurCfgVirtServicesFifthPartEntry 3 }

slbCurCfgVirtServTextrepReplacTxt OBJECT-TYPE
    SYNTAX  DisplayString (SIZE(0..128))
    MAX-ACCESS  read-only
    STATUS  current
    DESCRIPTION
        "Enter Cur text/ text to remove."
    ::= { slbCurCfgVirtServicesFifthPartEntry 4 }

slbCurCfgVirtServApplicationType OBJECT-TYPE
    SYNTAX  INTEGER {
      basic-slb(1),
      dns(2),
      ftp(3),
      ftp-data(4),
      ldap(5),
      http(6),
      https(7),
      ssl(8),
      rtsp(9),
      sip(10),
      wts(11),
      tftp(12)
    }
    MAX-ACCESS  read-only
    STATUS  current
    DESCRIPTION
        "Application Type for virtual service."
    ::= { slbCurCfgVirtServicesFifthPartEntry 5 }

slbCurCfgVirtServiceName OBJECT-TYPE
    SYNTAX  DisplayString (SIZE(0..32))
    MAX-ACCESS  read-only
    STATUS  current
    DESCRIPTION
        "The name of the virtual service."
    ::= { slbCurCfgVirtServicesFifthPartEntry 6 }

slbCurCfgVirtServiceAction OBJECT-TYPE
    SYNTAX  INTEGER    {
    group(1),
    redirect(2),
    discard(3)
    }
    MAX-ACCESS  read-only
    STATUS  current
    DESCRIPTION
        "Action type of the service.If we set value as group(1)
         it will Load balance the traffic between the servers
         defined in the group field after performing all other
         services actions.when set to a value of redirect(2)
         for http/https services, an http/s redirection will be
         performed with the values set in the application
         redirection.If we set value as discard(3) it will drop the session."
    ::= { slbCurCfgVirtServicesFifthPartEntry 7 }

slbCurCfgVirtServiceRedirect OBJECT-TYPE
    SYNTAX  DisplayString  (SIZE(0..255))
    MAX-ACCESS  read-only
    STATUS  current
    DESCRIPTION
        "application redirection location.We need to provide this
         value When action type is set to redirect(2)."
    ::= { slbCurCfgVirtServicesFifthPartEntry 8 }

slbCurCfgVirtServiceServCertGrpMark OBJECT-TYPE
    SYNTAX  INTEGER    {
    cert(1),
    group(2)
    }
    MAX-ACCESS  read-only
    STATUS  current
    DESCRIPTION
        "Group Mark for Server Certificate. If we set value as cert(0)
         It will denote that the server certificate (name) associated with 
         this virtual service, represents a certificate. Otherwise, a value of group(1), denotes that the server    
         certificate (name) represents a group."
    ::= { slbCurCfgVirtServicesFifthPartEntry 9}

slbCurCfgVirtServiceDnsType OBJECT-TYPE
    SYNTAX  INTEGER {
        dns(1),
        dnssec(2),
        both(3)
        }
    MAX-ACCESS  read-only
    STATUS  current
    DESCRIPTION
        "Set DNS type for this service (DNS, DNSSEC)."
    ::= { slbCurCfgVirtServicesFifthPartEntry 10 }

slbCurCfgVirtServiceClntproxType OBJECT-TYPE
    SYNTAX  INTEGER {
        none(1),
        http(2),
        https(3)
        }
    MAX-ACCESS  read-only
    STATUS  current
    DESCRIPTION
        "Set client proximity type for this service."
    ::= { slbCurCfgVirtServicesFifthPartEntry 11 }

slbCurCfgVirtServiceZerowinSize OBJECT-TYPE
    SYNTAX  INTEGER {
        enabled(1),
        disabled(2)
        }
    MAX-ACCESS  read-only
    STATUS  current
    DESCRIPTION
        "Enable or disable zero window size in SYN+ACK for this service."
    ::= { slbCurCfgVirtServicesFifthPartEntry 12 }

slbCurCfgVirtServiceCookiePath OBJECT-TYPE
    SYNTAX  DisplayString (SIZE(0..32))
    MAX-ACCESS  read-only
    STATUS  current
    DESCRIPTION
        "The cookie path name of the virtual server used for cookie load balance."
    ::= { slbCurCfgVirtServicesFifthPartEntry 13 }

slbCurCfgVirtServiceCookieSecure OBJECT-TYPE
    SYNTAX  INTEGER {
	yes(1),
        no(2)
        }
    MAX-ACCESS  read-only
    STATUS  current
    DESCRIPTION
        "Is cookie secure [yes/no] [Default: no]."
    ::= { slbCurCfgVirtServicesFifthPartEntry 14 }

slbCurCfgVirtServiceNoRtsp OBJECT-TYPE
    SYNTAX  INTEGER {
	enabled(1),
        disabled(2)
        }
    MAX-ACCESS  read-only
    STATUS  current
    DESCRIPTION
        "Enable or disable only rtsp SLB for this service."
    ::= { slbCurCfgVirtServicesFifthPartEntry 15 }

slbCurCfgVirtServiceCkRebind OBJECT-TYPE
    SYNTAX  INTEGER {
        enabled(1),
        disabled(2)
        }
    MAX-ACCESS  read-only
    STATUS  current
    DESCRIPTION
        "Server rebalancing when cookie is absent.
         When enabled, server load balancing will happen 
         for subsequent request comes without cookie."
    ::= { slbCurCfgVirtServicesFifthPartEntry 16 }

slbCurCfgVirtServiceParseLimit OBJECT-TYPE
    SYNTAX  INTEGER {
        enabled(1),
        disabled(2)
        }
    MAX-ACCESS  read-only
    STATUS  current
    DESCRIPTION
        "Enable or disable buffer limit for content based selection."
    ::= { slbCurCfgVirtServicesFifthPartEntry 17 }

slbCurCfgVirtServiceParseLength OBJECT-TYPE
    SYNTAX  INTEGER (0..18200)
    MAX-ACCESS  read-only
    STATUS  current
    DESCRIPTION
        "The buffer length for content based selection."
    ::= { slbCurCfgVirtServicesFifthPartEntry 18 }

slbCurCfgVirtServiceUriNorm OBJECT-TYPE
    SYNTAX  INTEGER {
        enabled(1),
        disabled(2)
        }
    MAX-ACCESS  read-only
    STATUS  current
    DESCRIPTION
        "Enable or disable URI normalization for HTTP content matching."
    ::= { slbCurCfgVirtServicesFifthPartEntry 19 }

-- Server load balancing - Virtual Services Table 

slbNewCfgVirtServicesTable OBJECT-TYPE
    SYNTAX  SEQUENCE OF SlbNewCfgVirtServicesEntry
    MAX-ACCESS  not-accessible
    STATUS  current
    DESCRIPTION
        "The table of virtual Services."
    ::= { virtualServerCfg 6 }

slbNewCfgVirtServicesEntry OBJECT-TYPE
    SYNTAX  SlbNewCfgVirtServicesEntry
    MAX-ACCESS  not-accessible
    STATUS  current
    DESCRIPTION
        "A row in the virtual services table."
    INDEX   { slbNewCfgVirtServIndex, slbNewCfgVirtServiceIndex }
    ::= { slbNewCfgVirtServicesTable 1 }

SlbNewCfgVirtServicesEntry ::= SEQUENCE {
    slbNewCfgVirtServIndex            Integer32,
    slbNewCfgVirtServiceIndex         Integer32,

    slbNewCfgVirtServiceVirtPort      INTEGER,
    slbNewCfgVirtServiceRealGroup     Integer32,
    slbNewCfgVirtServiceRealPort      INTEGER,
    slbNewCfgVirtServiceUDPBalance    INTEGER,
    slbNewCfgVirtServiceHname         DisplayString,
    slbNewCfgVirtServiceBwmContract   Integer32,
    slbNewCfgVirtServiceDirServerRtn  INTEGER,
    slbNewCfgVirtServiceRtspUrlParse  INTEGER,
    slbNewCfgVirtServiceFtpParsing    INTEGER,
    slbNewCfgVirtServiceRemapUDPFrags INTEGER,
    slbNewCfgVirtServiceDnsSlb        INTEGER,
    slbNewCfgVirtServiceResponseCount INTEGER,
    slbNewCfgVirtServicePBind         INTEGER,
    slbNewCfgVirtServiceCname         DisplayString,
    slbNewCfgVirtServiceCoffset       INTEGER,
    slbNewCfgVirtServiceClength       INTEGER, 
    slbNewCfgVirtServiceUriCookie     INTEGER,
    slbNewCfgVirtServiceCExpire       DisplayString,
    slbNewCfgVirtServiceCookieMode    INTEGER,
    slbNewCfgVirtServiceDBind         INTEGER,
    slbNewCfgVirtServiceHttpSlb       INTEGER,
    slbNewCfgVirtServiceHttpSlbOption INTEGER,
    slbNewCfgVirtServiceHttpSlb2      INTEGER,
    slbNewCfgVirtServiceHttpHdrName   DisplayString,
    slbNewCfgVirtServiceUrlHashLen    INTEGER,
    slbNewCfgVirtServiceCookieDname   INTEGER,
    slbNewCfgVirtServiceClsRST        INTEGER,
    slbNewCfgVirtServiceDelete        INTEGER, 
    slbNewCfgVirtServiceDirect        INTEGER,
    slbNewCfgVirtServiceThash         INTEGER,
    slbNewCfgVirtServiceLdapreset     INTEGER,
    slbNewCfgVirtServiceLdapslb       INTEGER,
    slbNewCfgVirtServiceSip           INTEGER,
    slbNewCfgVirtServiceXForwardedFor INTEGER,
    slbNewCfgVirtServiceHttpRedir     INTEGER,
    slbNewCfgVirtServicePbindRport    INTEGER,
    slbNewCfgVirtServiceEgressPip     INTEGER,
    slbNewCfgVirtServiceWts           INTEGER,
    slbNewCfgVirtServiceTimeOut       INTEGER,
    slbNewCfgVirtServiceSoftGrid      INTEGER,
    slbNewCfgVirtServiceSessionMirror INTEGER,
    slbNewCfgVirtServiceSdpNat        INTEGER,
    slbNewCfgVirtServiceConnPooling   INTEGER,
    slbNewCfgVirtPersistentTimeOut    INTEGER,
    slbNewCfgVirtServiceUhash         INTEGER
}

slbNewCfgVirtServIndex OBJECT-TYPE
    SYNTAX  Integer32
    MAX-ACCESS  read-only
    STATUS  current
    DESCRIPTION
        "The number of the virtual server." 
    ::= { slbNewCfgVirtServicesEntry 1 }

slbNewCfgVirtServiceIndex OBJECT-TYPE 
    SYNTAX  Integer32 (1..8)
    MAX-ACCESS  read-only 
    STATUS  current 
    DESCRIPTION 
        "The service index. This has no external meaning" 
    ::= { slbNewCfgVirtServicesEntry 2 }


slbNewCfgVirtServiceVirtPort OBJECT-TYPE  
    SYNTAX  INTEGER (9..65534)
    MAX-ACCESS  read-create  
    STATUS  current  
    DESCRIPTION 
        "The layer4 virtual port number of the service."  
    ::= { slbNewCfgVirtServicesEntry 3 } 

slbNewCfgVirtServiceRealGroup OBJECT-TYPE   
    SYNTAX  Integer32   
    MAX-ACCESS  read-create   
    STATUS  current   
    DESCRIPTION 
        "The real server group number for this service."   
    ::= { slbNewCfgVirtServicesEntry 4 }

slbNewCfgVirtServiceRealPort OBJECT-TYPE   
    SYNTAX  INTEGER (0..65534)
    MAX-ACCESS  read-create   
    STATUS  current   
    DESCRIPTION 
        "The layer4 real port number of the service."   
    ::= { slbNewCfgVirtServicesEntry 5 }

slbNewCfgVirtServiceUDPBalance OBJECT-TYPE   
    SYNTAX  INTEGER {
	udp(2),
	tcp(3),
	stateless(4),
        tcpAndUdp(5)
	}
    MAX-ACCESS  read-create   
    STATUS  current   
    DESCRIPTION 
        "Set protocol for the virtual service to
         UDP or TCP or tcpAndUdp or stateless.
         tcpAndUdp is applicable only to ip service."
    ::= { slbNewCfgVirtServicesEntry 6 }

slbNewCfgVirtServiceHname OBJECT-TYPE 
    SYNTAX  DisplayString (SIZE(0..34))
    MAX-ACCESS  read-create 
    STATUS  current 
    DESCRIPTION 
        "The host name of the virtual service."  
    ::= { slbNewCfgVirtServicesEntry 7 }

slbNewCfgVirtServiceBwmContract OBJECT-TYPE   
    SYNTAX  Integer32   
    MAX-ACCESS  read-create
    STATUS  current   
    DESCRIPTION 
        "The BWM contract number for this service."   
    ::= { slbNewCfgVirtServicesEntry 8 }

slbNewCfgVirtServiceDirServerRtn OBJECT-TYPE
    SYNTAX  INTEGER {
        enabled(1),
        disabled(2)
        }
    MAX-ACCESS  read-create
    STATUS  current   
    DESCRIPTION 
        "Enable or disable direct server return feature. To translate only 
         MAC addresses in performing server load balancing when enabled.  
         This allow servers to return directly to client since IP addresses 
         have not been changed."
    ::= { slbNewCfgVirtServicesEntry 9 }

slbNewCfgVirtServiceRtspUrlParse OBJECT-TYPE   
    SYNTAX  INTEGER {
        none(1),
        l4hash(2),
        hash(3),
        patternMatch(4)
	}
    MAX-ACCESS  read-create
    STATUS  current   
    DESCRIPTION 
        "Select RTSP URL load balancing type."
    ::= { slbNewCfgVirtServicesEntry 10 }

slbNewCfgVirtServiceDBind OBJECT-TYPE   
    SYNTAX  INTEGER {
	enabled(1),
	disabled(2),
	forceproxy(3)
	}
    MAX-ACCESS  read-create
    STATUS  current   
    DESCRIPTION 
        "Enable/disable/forceproxy delayed binding."
    ::= { slbNewCfgVirtServicesEntry 11 }


slbNewCfgVirtServiceFtpParsing OBJECT-TYPE
    SYNTAX  INTEGER {
	enabled(1),
	disabled(2)
	}
    MAX-ACCESS  read-create
    STATUS  current
    DESCRIPTION
        "Enable or Disable the ftp parsing for the virtual service."
    ::= { slbNewCfgVirtServicesEntry 12 }

slbNewCfgVirtServiceRemapUDPFrags OBJECT-TYPE   
    SYNTAX INTEGER {
        enabled(1),
        disabled(2)
        }
    MAX-ACCESS read-create   
    STATUS current   
    DESCRIPTION 
        "Enable or disable remapping UDP server fragments"   
    ::= { slbNewCfgVirtServicesEntry 13 }
slbNewCfgVirtServiceDnsSlb OBJECT-TYPE   
    SYNTAX  INTEGER {
        enabled(1),
	disabled(2)
	}
    MAX-ACCESS  read-create   
    STATUS  current   
    DESCRIPTION 
        "Enable or disable DNS query load balancing."
    ::= { slbNewCfgVirtServicesEntry 14 }

slbNewCfgVirtServiceResponseCount OBJECT-TYPE 
    SYNTAX  INTEGER (1..16)
    MAX-ACCESS  read-create 
    STATUS  current 
    DESCRIPTION 
        "The number of cookie search response count."
    ::= { slbNewCfgVirtServicesEntry 15 }

slbNewCfgVirtServicePBind OBJECT-TYPE   
    SYNTAX  INTEGER {
	clientip(2),
	disabled(3),
	sslid(4),
        cookie(5)
	}
    MAX-ACCESS  read-create   
    STATUS  current   
    DESCRIPTION 
        "Enable or disable persistent bindings for the virtual port."
    ::= { slbNewCfgVirtServicesEntry 16 }

slbNewCfgVirtServiceCname OBJECT-TYPE 
    SYNTAX  DisplayString (SIZE(0..20))
    MAX-ACCESS  read-create 
    STATUS  current 
    DESCRIPTION 
        "The cookie name of the virtual server used for cookie load balance."  
    ::= { slbNewCfgVirtServicesEntry 17 }

slbNewCfgVirtServiceCoffset OBJECT-TYPE
    SYNTAX  INTEGER (1..64)
    MAX-ACCESS  read-create 
    STATUS  current
    DESCRIPTION
        "The starting byte offset of the cookie value." 
    ::= { slbNewCfgVirtServicesEntry 18 }

slbNewCfgVirtServiceClength OBJECT-TYPE
    SYNTAX  INTEGER (1..64)
    MAX-ACCESS  read-create
    STATUS  current
    DESCRIPTION
        "The number of bytes to extract from the cookie value." 
    ::= { slbNewCfgVirtServicesEntry 19 }

slbNewCfgVirtServiceUriCookie OBJECT-TYPE 
    SYNTAX  INTEGER {
	enabled(1),
	disabled(2)
	}
    MAX-ACCESS  read-create 
    STATUS  current 
    DESCRIPTION 
        "Enable or disable cookie search in URI"  
    ::= { slbNewCfgVirtServicesEntry 20}

slbNewCfgVirtServiceCExpire OBJECT-TYPE 
    SYNTAX  DisplayString (SIZE(0..20))
    MAX-ACCESS  read-create 
    STATUS  current 
    DESCRIPTION 
        "The cookie expire of the virtual server used for insert cookie load
         balance depending on the mode it has the following format 
         <MM/dd/yy[@hh:mm]> absolute mode or <days[:hours[:minutes]]>
         for relative mode."  
    ::= { slbNewCfgVirtServicesEntry 21 }

slbNewCfgVirtServiceCookieMode OBJECT-TYPE   
    SYNTAX INTEGER {
        rewrite(1),
        passive(2),
	insert(3)
        }
    MAX-ACCESS read-create 
    STATUS current   
    DESCRIPTION 
        "Select cookie persistence mode."
    ::= { slbNewCfgVirtServicesEntry 22 }

slbNewCfgVirtServiceHttpSlb OBJECT-TYPE   
    SYNTAX  INTEGER {
	disabled(1),
        urlslb(2),
        urlhash(3),
        cookie(4),
        host(5),
        browser(6),
        others(7),
        headerhash(8),
	version(9)
	}
    MAX-ACCESS  read-create   
    STATUS  current   
    DESCRIPTION 
        "Select HTTP server loadbalancing for the virtual port."   
    ::= { slbNewCfgVirtServicesEntry 23 }

slbNewCfgVirtServiceHttpSlbOption OBJECT-TYPE   
    SYNTAX  INTEGER {
	and(1),
        or(2),
        none(3)
	}
    MAX-ACCESS  read-create   
    STATUS  current   
    DESCRIPTION 
        "Select HTTP server loadbalancing for the virtual port."   
    ::= { slbNewCfgVirtServicesEntry 24 }

slbNewCfgVirtServiceHttpSlb2 OBJECT-TYPE   
    SYNTAX  INTEGER {
	disabled(1),
        urlslb(2),
        urlhash(3),
        cookie(4),
        host(5),
        browser(6),
        others(7),
        headerhash(8),
	version(9)
	}
    MAX-ACCESS  read-create   
    STATUS  current   
    DESCRIPTION 
        "Select HTTP server loadbalancing for the virtual port."   
    ::= { slbNewCfgVirtServicesEntry 25 }

slbNewCfgVirtServiceHttpHdrName OBJECT-TYPE 
    SYNTAX  DisplayString  (SIZE(0..32))
    MAX-ACCESS  read-create 
    STATUS  current 
    DESCRIPTION 
        "The HTTP header name of the virtual server."
    ::= { slbNewCfgVirtServicesEntry 26 }

slbNewCfgVirtServiceUrlHashLen OBJECT-TYPE 
    SYNTAX  INTEGER (0..255)
    MAX-ACCESS  read-create 
    STATUS  current 
    DESCRIPTION 
        "The number of bytes used to hash onto server, A zero means
         URL hashing disabled."
    ::= { slbNewCfgVirtServicesEntry 27}

slbNewCfgVirtServiceDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { slbNewCfgVirtServicesEntry 28 }

slbNewCfgVirtServiceDirect OBJECT-TYPE   
    SYNTAX  INTEGER {
        enabled(1),
	disabled(2)
	}
    MAX-ACCESS  read-create   
    STATUS  current   
    DESCRIPTION 
        "Enable or disable DAM for this service." 
    ::= { slbNewCfgVirtServicesEntry 29 }

slbNewCfgVirtServiceThash OBJECT-TYPE   
    SYNTAX  INTEGER {
        sip(1),
        sip-sport(2)
        }
    MAX-ACCESS  read-create
    STATUS  current   
    DESCRIPTION 
        "Set hash parameter."
    ::= { slbNewCfgVirtServicesEntry 30 }

slbNewCfgVirtServiceLdapreset OBJECT-TYPE 
    SYNTAX  INTEGER {
        enabled(1),
        disabled(2)
        }
    MAX-ACCESS  read-create 
    STATUS  current 
    DESCRIPTION 
        "Enable or disable LDAP Server Reset"  
    ::= { slbNewCfgVirtServicesEntry 31 }

slbNewCfgVirtServiceLdapslb OBJECT-TYPE 
    SYNTAX  INTEGER {
        enabled(1),
        disabled(2)
        }
    MAX-ACCESS  read-create 
    STATUS  current 
    DESCRIPTION 
        "Enable or disable LDAP Server load balancing"  
    ::= { slbNewCfgVirtServicesEntry 32 }

slbNewCfgVirtServiceSip OBJECT-TYPE   
    SYNTAX  INTEGER {
        enabled(1),
	disabled(2)
	}
    MAX-ACCESS  read-create   
    STATUS  current   
    DESCRIPTION 
        "Enable/disable SIP load balancing."
    ::= { slbNewCfgVirtServicesEntry 33 }

slbNewCfgVirtServiceXForwardedFor OBJECT-TYPE   
    SYNTAX  INTEGER {
        enabled(1),
	disabled(2)
	}
    MAX-ACCESS  read-create
    STATUS  current   
    DESCRIPTION 
        "Enable/disable X-Forwarded-For for proxy mode."
    ::= { slbNewCfgVirtServicesEntry 34 }

slbNewCfgVirtServiceHttpRedir OBJECT-TYPE
    SYNTAX  INTEGER {
        enabled(1),
        disabled(2)
        }
    MAX-ACCESS  read-create
    STATUS  current
    DESCRIPTION
        "Enable/disable HTTP/HTTPS redirect for GSLB."
    ::= { slbNewCfgVirtServicesEntry 35 }

slbNewCfgVirtServicePbindRport OBJECT-TYPE   
    SYNTAX  INTEGER {
        enabled(1),
	disabled(2)
	}
    MAX-ACCESS  read-create
    STATUS  current   
    DESCRIPTION 
        "Enable or disable use of rport in the session lookup for a persistent
         session."
    ::= { slbNewCfgVirtServicesEntry 36 }
    
slbNewCfgVirtServiceEgressPip OBJECT-TYPE   
    SYNTAX  INTEGER {
        enabled(1),
	disabled(2)
	}
    MAX-ACCESS  read-create
    STATUS  current   
    DESCRIPTION 
        "Enable/disable pip selection based on egress port/vlan."
    ::= { slbNewCfgVirtServicesEntry 37 }

slbNewCfgVirtServiceCookieDname OBJECT-TYPE
    SYNTAX INTEGER {
        enabled(1),
        disabled(2)
        }
    MAX-ACCESS read-create
    STATUS current
    DESCRIPTION
        "Select dname for insert cookie persistence mode."
    ::= { slbNewCfgVirtServicesEntry 38 }
    
slbNewCfgVirtServiceWts OBJECT-TYPE
    SYNTAX INTEGER {
        enabled(1),
        disabled(2)
        }
    MAX-ACCESS read-create
    STATUS current
    DESCRIPTION
        "Enable or disable WTS loadbalancing and persistence."
    ::= { slbNewCfgVirtServicesEntry 39 }

slbNewCfgVirtServiceUhash OBJECT-TYPE
    SYNTAX INTEGER {
        enabled(1),
        disabled(2)
        }
    MAX-ACCESS read-create
    STATUS current
    DESCRIPTION
        "Enable when there is no Session Directory server."
    ::= { slbNewCfgVirtServicesEntry 40 }


slbNewCfgVirtServiceTimeOut OBJECT-TYPE
    SYNTAX  INTEGER (0..32768)
    MAX-ACCESS  read-create
    STATUS  current
    DESCRIPTION
        "The maximum number of minutes an inactive connection remains open."
    ::= { slbNewCfgVirtServicesEntry 41 }

slbNewCfgVirtServiceSessionMirror OBJECT-TYPE
    SYNTAX  INTEGER {
        enabled(1),
        disabled(2)
        }
    MAX-ACCESS  read-create
    STATUS  current
    DESCRIPTION
        "Enable/disable session mirroring."
    ::= { slbNewCfgVirtServicesEntry 43 }

slbNewCfgVirtServiceSoftGrid OBJECT-TYPE
    SYNTAX  INTEGER {
        enabled(1),
        disabled(2)
        }
    MAX-ACCESS  read-create
    STATUS  current
    DESCRIPTION
        "Enable/disable softgrid load balancing."
    ::= { slbNewCfgVirtServicesEntry 44 }

slbNewCfgVirtServiceSdpNat OBJECT-TYPE
    SYNTAX  INTEGER {
        enabled(1),
        disabled(2)
        }
    MAX-ACCESS  read-create
    STATUS  current
    DESCRIPTION
        "Enable/disable SIP Media portal NAT."
    ::= { slbNewCfgVirtServicesEntry 42 }

slbNewCfgVirtServiceConnPooling OBJECT-TYPE
    SYNTAX  INTEGER {
        enabled(1),
            disabled(2)
    }
    MAX-ACCESS  read-create
    STATUS  current
    DESCRIPTION
        "Enable/disable connection pooling for HTTP traffic."
    ::= { slbNewCfgVirtServicesEntry 45 }

slbNewCfgVirtPersistentTimeOut OBJECT-TYPE
    SYNTAX  INTEGER (0..32768)
    MAX-ACCESS  read-create
    STATUS  current
    DESCRIPTION
        "The maximum number of minutes a persistent session should exist."
    ::= { slbNewCfgVirtServicesEntry 46 }

slbNewCfgVirtServiceClsRST OBJECT-TYPE   
    SYNTAX  INTEGER {
	enabled(1),
	disabled(2)
	}
    MAX-ACCESS  read-create
    STATUS  current   
    DESCRIPTION 
        "Enable or disable Delayed Binding."
    ::= { slbNewCfgVirtServicesEntry 47 }


slbNewCfgVirtServicesSecondPartTable OBJECT-TYPE
    SYNTAX  SEQUENCE OF SlbNewCfgVirtServicesSecondPartEntry
    MAX-ACCESS  not-accessible
    STATUS  current
    DESCRIPTION
        "The table of virtual Services."
    ::= { virtualServerCfg 16 }

slbNewCfgVirtServicesSecondPartEntry OBJECT-TYPE
    SYNTAX  SlbNewCfgVirtServicesSecondPartEntry
    MAX-ACCESS  not-accessible
    STATUS  current
    DESCRIPTION
        "A row in the virtual services table."
    INDEX   { slbNewCfgVirtServSecondPartIndex, slbNewCfgVirtServiceSecondPartIndex }
    ::= { slbNewCfgVirtServicesSecondPartTable 1 }

SlbNewCfgVirtServicesSecondPartEntry ::= SEQUENCE {
    slbNewCfgVirtServSecondPartIndex            Integer32,
    slbNewCfgVirtServiceSecondPartIndex         Integer32,

    slbNewCfgVirtServiceConnmgtStatus  INTEGER,
    slbNewCfgVirtServiceConnmgtTimeout INTEGER,
    slbNewCfgVirtServiceCachepol      DisplayString,
    slbNewCfgVirtServiceComppol       DisplayString,
    slbNewCfgVirtServiceSSLpol        DisplayString,
    slbNewCfgVirtServiceServCert      DisplayString,
    slbNewCfgVirtServiceHttpmodList   DisplayString,
    slbNewCfgVirtServiceCloaksrv      INTEGER,

    slbNewCfgVirtServErrcodeStatus    INTEGER,
    slbNewCfgVirtServErrcodeMatch     DisplayString,
    slbNewCfgVirtServErrcodeHttpRedir INTEGER,
    slbNewCfgVirtServErrcodeUrl       DisplayString,
    slbNewCfgVirtServErrcode          DisplayString,
    slbNewCfgVirtServErrcodeNew       DisplayString,
    slbNewCfgVirtServErrcodeReason    DisplayString,
    slbNewCfgVirtServUrlchangStatus     INTEGER,
    slbNewCfgVirtServUrlchangHostType   INTEGER
}

slbNewCfgVirtServSecondPartIndex OBJECT-TYPE
    SYNTAX  Integer32
    MAX-ACCESS  read-only
    STATUS  current
    DESCRIPTION
        "The number of the virtual server." 
    ::= { slbNewCfgVirtServicesSecondPartEntry 1 }

slbNewCfgVirtServiceSecondPartIndex OBJECT-TYPE 
    SYNTAX  Integer32 
    MAX-ACCESS  read-only 
    STATUS  current 
    DESCRIPTION 
        "The service index. This has no external meaning" 
    ::= { slbNewCfgVirtServicesSecondPartEntry 2 }


slbNewCfgVirtServiceConnmgtStatus OBJECT-TYPE
    SYNTAX  INTEGER {
        disabled(0),
        pooling(1),
        muxenabled(2)
        }
    MAX-ACCESS  read-create
    STATUS  current
    DESCRIPTION
        "Connection management configuration for HTTP traffic(Enable/disable/pooling) [Default: Disable]."
    ::= { slbNewCfgVirtServicesSecondPartEntry 3 }

slbNewCfgVirtServiceConnmgtTimeout OBJECT-TYPE
    SYNTAX  INTEGER (0..32768)
    MAX-ACCESS  read-create
    STATUS  current
    DESCRIPTION
        "Connection management server side connection idle timeout in minutes [0-32768] [Default: 10]."
    ::= { slbNewCfgVirtServicesSecondPartEntry 4 }

slbNewCfgVirtServiceCachepol OBJECT-TYPE
    SYNTAX  DisplayString  (SIZE(0..32))
    MAX-ACCESS  read-create
    STATUS  current
    DESCRIPTION
        "Cache policy name associated with this virtual service.Set none to delete entry"
    ::= { slbNewCfgVirtServicesSecondPartEntry 5 }

slbNewCfgVirtServiceComppol OBJECT-TYPE
    SYNTAX  DisplayString  (SIZE(0..32))
    MAX-ACCESS  read-create
    STATUS  current
    DESCRIPTION
        "Compression policy name associated with this virtual service.Set none to delete entry"
    ::= { slbNewCfgVirtServicesSecondPartEntry 6 }

slbNewCfgVirtServiceSSLpol OBJECT-TYPE
    SYNTAX  DisplayString  (SIZE(0..32))
    MAX-ACCESS  read-create
    STATUS  current
    DESCRIPTION
        "SSL policy name associated with this virtual service.Set none to delete entry"
    ::= { slbNewCfgVirtServicesSecondPartEntry 7 }

slbNewCfgVirtServiceServCert OBJECT-TYPE
    SYNTAX  DisplayString  (SIZE(0..32))
    MAX-ACCESS  read-create
    STATUS  current
    DESCRIPTION
        "Server Certificate name associated with this virtual service."
    ::= { slbNewCfgVirtServicesSecondPartEntry 8 }

slbNewCfgVirtServiceHttpmodList OBJECT-TYPE
    SYNTAX  DisplayString  (SIZE(0..32))
    MAX-ACCESS  read-create
    STATUS  current
    DESCRIPTION
        "HTTP Content Modifications Rule-list associated with this virtual service.Set none to delete entry"
    ::= { slbNewCfgVirtServicesSecondPartEntry 9 }

slbNewCfgVirtServiceCloaksrv OBJECT-TYPE
    SYNTAX  INTEGER {
        enabled(1),
        disabled(2)
        }
    MAX-ACCESS  read-create
    STATUS  current
    DESCRIPTION
        "Enable/disable server cloaking."
    ::= { slbNewCfgVirtServicesSecondPartEntry 10 }

slbNewCfgVirtServErrcodeStatus OBJECT-TYPE
    SYNTAX  INTEGER {
        enabled(1),
        disabled(2),
        clear(3)
        }
    MAX-ACCESS  read-create
    STATUS  current
    DESCRIPTION
        "Enable/disable/clear error-code configuration."
    ::= { slbNewCfgVirtServicesSecondPartEntry 11 }

slbNewCfgVirtServErrcodeMatch OBJECT-TYPE
    SYNTAX  DisplayString (SIZE (0..64))
    MAX-ACCESS  read-create
    STATUS  current
    DESCRIPTION
        "Match error-code(s), e.g 203,204 ."
    ::= { slbNewCfgVirtServicesSecondPartEntry 12 }

slbNewCfgVirtServErrcodeHttpRedir OBJECT-TYPE
    SYNTAX  INTEGER {
        yes(1),
        no(2)
    }
    MAX-ACCESS  read-create
    STATUS  current
    DESCRIPTION
        "Use http redirection [yes/no] [Default: yes]."
    ::= { slbNewCfgVirtServicesSecondPartEntry 13 }

slbNewCfgVirtServErrcodeUrl OBJECT-TYPE
    SYNTAX  DisplayString (SIZE(0..240))
    MAX-ACCESS  read-create
    STATUS  current
    DESCRIPTION
        "URL for redirection."
    ::= { slbNewCfgVirtServicesSecondPartEntry 14 }


slbNewCfgVirtServErrcode OBJECT-TYPE
    SYNTAX  DisplayString (SIZE(0..3))
    MAX-ACCESS  read-create
    STATUS  current
    DESCRIPTION
        "set error code [Default: 302]."
    ::= { slbNewCfgVirtServicesSecondPartEntry 15 }

slbNewCfgVirtServErrcodeNew OBJECT-TYPE
    SYNTAX  DisplayString (SIZE(0..3))
    MAX-ACCESS  read-create
    STATUS  current
    DESCRIPTION
        "Enter new error code [Default: 302]."
    ::= { slbNewCfgVirtServicesSecondPartEntry 16 }

slbNewCfgVirtServErrcodeReason OBJECT-TYPE
    SYNTAX  DisplayString (SIZE(0..128))
    MAX-ACCESS  read-create
    STATUS  current
    DESCRIPTION
        "Enter error reason."
    ::= { slbNewCfgVirtServicesSecondPartEntry 17 }

slbNewCfgVirtServUrlchangStatus OBJECT-TYPE
    SYNTAX  INTEGER {
        enable(1),
        disable(2),
        clear(3)
    }
    MAX-ACCESS  read-create
    STATUS  current
    DESCRIPTION
        "Enter enabled/disabled/clear [Default: clear]."
    ::= { slbNewCfgVirtServicesSecondPartEntry 18 }

slbNewCfgVirtServUrlchangHostType OBJECT-TYPE
    SYNTAX  INTEGER {
        sufx(1),
        prefx(2),
        eq(3),
        incl(4),
        any(5)
    }
    MAX-ACCESS  read-create
    STATUS  current
    DESCRIPTION
        "Enter hostname match type [sufx|prefx|eq|incl|any] [Default: any]"
    ::= { slbNewCfgVirtServicesSecondPartEntry 19 }



slbNewCfgVirtServicesThirdPartTable OBJECT-TYPE
    SYNTAX  SEQUENCE OF SlbNewCfgVirtServicesThirdPartEntry
    MAX-ACCESS  not-accessible
    STATUS  current
    DESCRIPTION
        "The table of virtual Services."
    ::= { virtualServerCfg 17 }

slbNewCfgVirtServicesThirdPartEntry OBJECT-TYPE
    SYNTAX  SlbNewCfgVirtServicesThirdPartEntry
    MAX-ACCESS  not-accessible
    STATUS  current
    DESCRIPTION
        "A row in the virtual services table."
    INDEX   { slbNewCfgVirtServThirdPartIndex, slbNewCfgVirtServiceThirdPartIndex }
    ::= { slbNewCfgVirtServicesThirdPartTable 1 }

SlbNewCfgVirtServicesThirdPartEntry ::= SEQUENCE {
    slbNewCfgVirtServThirdPartIndex            Integer32,
    slbNewCfgVirtServiceThirdPartIndex         Integer32,

    slbNewCfgVirtServUrlchangHostName   DisplayString,
    slbNewCfgVirtServUrlchangPathType   INTEGER,
    slbNewCfgVirtServUrlchangPathMatch  DisplayString,
    slbNewCfgVirtServUrlchangPageName   DisplayString,
    slbNewCfgVirtServUrlchangPageType   DisplayString,
    slbNewCfgVirtServUrlchangActnType   INTEGER,
    slbNewCfgVirtServUrlchangPathInsrt  DisplayString,
    slbNewCfgVirtServUrlchangInsrtPostn INTEGER
}


slbNewCfgVirtServThirdPartIndex OBJECT-TYPE
    SYNTAX  Integer32
    MAX-ACCESS  read-only
    STATUS  current
    DESCRIPTION
        "The number of the virtual server." 
    ::= { slbNewCfgVirtServicesThirdPartEntry 1 }

slbNewCfgVirtServiceThirdPartIndex OBJECT-TYPE 
    SYNTAX  Integer32 
    MAX-ACCESS  read-only 
    STATUS  current 
    DESCRIPTION 
        "The service index. This has no external meaning" 
    ::= { slbNewCfgVirtServicesThirdPartEntry 2 }

slbNewCfgVirtServUrlchangHostName OBJECT-TYPE
    SYNTAX  DisplayString (SIZE(0..250))
    MAX-ACCESS  read-create
    STATUS  current
    DESCRIPTION
        "Enter hostname to match."
    ::= { slbNewCfgVirtServicesThirdPartEntry 3 }

slbNewCfgVirtServUrlchangPathType OBJECT-TYPE
    SYNTAX  INTEGER {
        sufx(1),
        prefx(2),
        eq(3),
        incl(4),
        any(5),
        none(6)
    }
    MAX-ACCESS  read-create
    STATUS  current
    DESCRIPTION
        "Enter path match type [sufx|prefx|eq|incl|any|none]."
    ::= { slbNewCfgVirtServicesThirdPartEntry 4 }

slbNewCfgVirtServUrlchangPathMatch OBJECT-TYPE
    SYNTAX  DisplayString (SIZE(0..250))
    MAX-ACCESS  read-create
    STATUS  current
    DESCRIPTION
        "Enter path to match."
    ::= { slbNewCfgVirtServicesThirdPartEntry 5 }

slbNewCfgVirtServUrlchangPageName OBJECT-TYPE
    SYNTAX  DisplayString (SIZE(0..64))
    MAX-ACCESS  read-create
    STATUS  current
    DESCRIPTION
        "Enter page name to match or none."
    ::= { slbNewCfgVirtServicesThirdPartEntry 6 }

slbNewCfgVirtServUrlchangPageType OBJECT-TYPE
    SYNTAX  DisplayString (SIZE(0..64))
    MAX-ACCESS  read-create
    STATUS  current
    DESCRIPTION
        "Enter page type to match or none."
    ::= { slbNewCfgVirtServicesThirdPartEntry 7 }

slbNewCfgVirtServUrlchangActnType OBJECT-TYPE
    SYNTAX  INTEGER {
        insert(1),
        replace(2),
        remove(3),
        none(4)
    }
    MAX-ACCESS  read-create
    STATUS  current
    DESCRIPTION
        "Enter path action type."
    ::= { slbNewCfgVirtServicesThirdPartEntry 8 }

slbNewCfgVirtServUrlchangPathInsrt OBJECT-TYPE
    SYNTAX  DisplayString (SIZE(0..250))
    MAX-ACCESS  read-create
    STATUS  current
    DESCRIPTION
        "Enter path to insert."
    ::= { slbNewCfgVirtServicesThirdPartEntry 9 }


slbNewCfgVirtServUrlchangInsrtPostn OBJECT-TYPE
    SYNTAX  INTEGER {
        before(1),
        after(2)
    }
    MAX-ACCESS  read-create
    STATUS  current
    DESCRIPTION
        "Insert the specified path before or after the matched section?"
    ::= { slbNewCfgVirtServicesThirdPartEntry 10 }



slbNewCfgVirtServicesFourthPartTable OBJECT-TYPE
    SYNTAX  SEQUENCE OF SlbNewCfgVirtServicesFourthPartEntry
    MAX-ACCESS  not-accessible
    STATUS  current
    DESCRIPTION
        "The table of virtual Services."
    ::= { virtualServerCfg 18 }

slbNewCfgVirtServicesFourthPartEntry OBJECT-TYPE
    SYNTAX  SlbNewCfgVirtServicesFourthPartEntry
    MAX-ACCESS  not-accessible
    STATUS  current
    DESCRIPTION
        "A row in the virtual services table."
    INDEX   { slbNewCfgVirtServFourthPartIndex, slbNewCfgVirtServiceFourthPartIndex }
    ::= { slbNewCfgVirtServicesFourthPartTable 1 }

SlbNewCfgVirtServicesFourthPartEntry ::= SEQUENCE {
    slbNewCfgVirtServFourthPartIndex            Integer32,
    slbNewCfgVirtServiceFourthPartIndex         Integer32,

    slbNewCfgVirtServUrlchangNewPgName  DisplayString,
    slbNewCfgVirtServUrlchangNewPgType  DisplayString,

    slbNewCfgVirtServPathHideStatus     INTEGER,
    slbNewCfgVirtServPathHideHostType   INTEGER,
    slbNewCfgVirtServPathHideHostName   DisplayString,
    slbNewCfgVirtServPathHidePathType   INTEGER,
    slbNewCfgVirtServPathHidePathName   DisplayString,

    slbNewCfgVirtServTextrepStatus      INTEGER,
    slbNewCfgVirtServTextrepAction      INTEGER
}

slbNewCfgVirtServFourthPartIndex OBJECT-TYPE
    SYNTAX  Integer32
    MAX-ACCESS  read-only
    STATUS  current
    DESCRIPTION
        "The number of the virtual server." 
    ::= { slbNewCfgVirtServicesFourthPartEntry 1 }

slbNewCfgVirtServiceFourthPartIndex OBJECT-TYPE 
    SYNTAX  Integer32 
    MAX-ACCESS  read-only 
    STATUS  current 
    DESCRIPTION 
        "The service index. This has no external meaning" 
    ::= { slbNewCfgVirtServicesFourthPartEntry 2 }

slbNewCfgVirtServUrlchangNewPgName OBJECT-TYPE
    SYNTAX  DisplayString (SIZE(0..64))
    MAX-ACCESS  read-create
    STATUS  current
    DESCRIPTION
        "Enter new page name or none."
    ::= { slbNewCfgVirtServicesFourthPartEntry 3 }

slbNewCfgVirtServUrlchangNewPgType OBJECT-TYPE
    SYNTAX  DisplayString (SIZE(0..64))
    MAX-ACCESS  read-create
    STATUS  current
    DESCRIPTION
        "Enter new page type or none."
    ::= { slbNewCfgVirtServicesFourthPartEntry 4 }

slbNewCfgVirtServPathHideStatus OBJECT-TYPE
    SYNTAX  INTEGER {
        enable(1),
        disable(2),
        clear(3)
    }
    MAX-ACCESS  read-create
    STATUS  current
    DESCRIPTION
        "Enter enabled/disabled/clear [Default: clear]."
    ::= { slbNewCfgVirtServicesFourthPartEntry 5 }

slbNewCfgVirtServPathHideHostType OBJECT-TYPE
    SYNTAX  INTEGER {
        sufx(1),
        prefx(2),
        eq(3),
        incl(4),
        any(5)
    }
    MAX-ACCESS  read-create
    STATUS  current
    DESCRIPTION
        "Enter hostname type [sufx|prefx|eq|incl|any] [Default: any]."
    ::= { slbNewCfgVirtServicesFourthPartEntry 6 }

slbNewCfgVirtServPathHideHostName OBJECT-TYPE
    SYNTAX  DisplayString (SIZE(0..250))
    MAX-ACCESS  read-create
    STATUS  current
    DESCRIPTION
        "Enter hostname to match."
    ::= { slbNewCfgVirtServicesFourthPartEntry 7 }

slbNewCfgVirtServPathHidePathType OBJECT-TYPE
    SYNTAX  INTEGER {
        sufx(1),
        prefx(2),
        eq(3),
        none(4)
    }
    MAX-ACCESS  read-create
    STATUS  current
    DESCRIPTION
        "Enter path match type [sufx|prefx|eq|none]."
    ::= { slbNewCfgVirtServicesFourthPartEntry 8 }

slbNewCfgVirtServPathHidePathName OBJECT-TYPE
    SYNTAX  DisplayString (SIZE(0..250))
    MAX-ACCESS  read-create
    STATUS  current
    DESCRIPTION
        "Enter path to remove."
    ::= { slbNewCfgVirtServicesFourthPartEntry 9 }

slbNewCfgVirtServTextrepStatus OBJECT-TYPE
    SYNTAX  INTEGER {
        enable(1),
        disable(2),
        clear(3)
    }
    MAX-ACCESS  read-create
    STATUS  current
    DESCRIPTION
        "Enter enabled/disabled/clear [Default: clear]."
    ::= { slbNewCfgVirtServicesFourthPartEntry 10 }

slbNewCfgVirtServTextrepAction OBJECT-TYPE
    SYNTAX  INTEGER {
        none(0),
        replace(1),
        remove(2)
    }
    MAX-ACCESS  read-create
    STATUS  current
    DESCRIPTION
        "Enter action [replace|remove|none]."
    ::= { slbNewCfgVirtServicesFourthPartEntry 11 }

slbNewCfgVirtServicesFifthPartTable OBJECT-TYPE
    SYNTAX  SEQUENCE OF SlbNewCfgVirtServicesFifthPartEntry
    MAX-ACCESS  not-accessible
    STATUS  current
    DESCRIPTION
        "The table of virtual Services."
    ::= { virtualServerCfg 19 }

slbNewCfgVirtServicesFifthPartEntry OBJECT-TYPE
    SYNTAX  SlbNewCfgVirtServicesFifthPartEntry
    MAX-ACCESS  not-accessible
    STATUS  current
    DESCRIPTION
        "A row in the virtual services table."
    INDEX   { slbNewCfgVirtServFifthPartIndex, slbNewCfgVirtServiceFifthPartIndex }
    ::= { slbNewCfgVirtServicesFifthPartTable 1 }

SlbNewCfgVirtServicesFifthPartEntry ::= SEQUENCE {

    slbNewCfgVirtServFifthPartIndex            Integer32,
    slbNewCfgVirtServiceFifthPartIndex         Integer32,

    slbNewCfgVirtServTextrepMatchText   DisplayString,
    slbNewCfgVirtServTextrepReplacTxt   DisplayString,

    slbNewCfgVirtServApplicationType    INTEGER,
    slbNewCfgVirtServiceName          DisplayString,
    slbNewCfgVirtServiceAction        INTEGER,
    slbNewCfgVirtServiceRedirect      DisplayString,

    slbNewCfgVirtServiceServCertGrpMark INTEGER,
    slbNewCfgVirtServiceDnsType         INTEGER,
    slbNewCfgVirtServiceClntproxType    INTEGER,
    slbNewCfgVirtServiceZerowinSize     INTEGER,
    slbNewCfgVirtServiceCookiePath    DisplayString,
    slbNewCfgVirtServiceCookieSecure    INTEGER,
    slbNewCfgVirtServiceNoRtsp          INTEGER,
    slbNewCfgVirtServiceCkRebind        INTEGER,
    slbNewCfgVirtServiceParseLimit      INTEGER,
    slbNewCfgVirtServiceParseLength     INTEGER,
    slbNewCfgVirtServiceUriNorm         INTEGER
}

slbNewCfgVirtServFifthPartIndex OBJECT-TYPE
    SYNTAX  Integer32
    MAX-ACCESS  read-only
    STATUS  current
    DESCRIPTION
        "The number of the virtual server." 
    ::= { slbNewCfgVirtServicesFifthPartEntry 1 }

slbNewCfgVirtServiceFifthPartIndex OBJECT-TYPE 
    SYNTAX  Integer32 
    MAX-ACCESS  read-only 
    STATUS  current 
    DESCRIPTION 
        "The service index. This has no external meaning" 
    ::= { slbNewCfgVirtServicesFifthPartEntry 2 }

slbNewCfgVirtServTextrepMatchText OBJECT-TYPE
    SYNTAX  DisplayString (SIZE(0..128))
    MAX-ACCESS  read-create
    STATUS  current
    DESCRIPTION
        "Enter text to be replaced."
    ::= { slbNewCfgVirtServicesFifthPartEntry 3 }

slbNewCfgVirtServTextrepReplacTxt OBJECT-TYPE
    SYNTAX  DisplayString (SIZE(0..128))
    MAX-ACCESS  read-create
    STATUS  current
    DESCRIPTION
        "Enter new text/ text to remove."
    ::= { slbNewCfgVirtServicesFifthPartEntry 4 }

slbNewCfgVirtServApplicationType OBJECT-TYPE
    SYNTAX  INTEGER {
      basic-slb(1),
      dns(2),
      ftp(3),
      ftp-data(4),
      ldap(5),
      http(6),
      https(7),
      ssl(8),
      rtsp(9),
      sip(10),
      wts(11),
      tftp(12),
      smtp(13),
      pop3(14)
    }
    MAX-ACCESS  read-create
    STATUS  current
    DESCRIPTION
        "Application Type for virtual service."
    ::= { slbNewCfgVirtServicesFifthPartEntry 5 }

slbNewCfgVirtServiceName OBJECT-TYPE
    SYNTAX  DisplayString (SIZE(0..32))
    MAX-ACCESS  read-create
    STATUS  current
    DESCRIPTION
        "The name of the virtual service."
    ::= { slbNewCfgVirtServicesFifthPartEntry 6 }

slbNewCfgVirtServiceAction OBJECT-TYPE
    SYNTAX  INTEGER    {
    group(1),
    redirect(2),
    discard(3)
    }
    MAX-ACCESS  read-create
    STATUS  current
    DESCRIPTION
        "Action type of the service.If we set value as group(1)
         it will Load balance the traffic between the servers
         defined in the group field after performing all other
         services actions.when set to a value of redirect(2)
         for http/https services, an http/s redirection will be
         performed with the values set in the application
         redirection.If we set value as discard(3) it will drop the session."
    ::= { slbNewCfgVirtServicesFifthPartEntry 7 }

slbNewCfgVirtServiceRedirect OBJECT-TYPE
    SYNTAX  DisplayString  (SIZE(0..255))
    MAX-ACCESS  read-create
    STATUS  current
    DESCRIPTION
        "application redirection location.We need to provide this
         value When action type is set to redirect(2)."
    ::= { slbNewCfgVirtServicesFifthPartEntry 8 }

slbNewCfgVirtServiceServCertGrpMark OBJECT-TYPE
    SYNTAX  INTEGER    {
    cert(1),
    group(2)
    }
    MAX-ACCESS  read-create
    STATUS  current
    DESCRIPTION
        "Group Mark for Server Certificate. If we set value as cert(0)
         It will denote that the server certificate (name) associated with 
         this virtual service, represents a certificate. Otherwise, a value of group(1), denotes that the server    
         certificate (name) represents a group."
    ::= { slbNewCfgVirtServicesFifthPartEntry 9}

slbNewCfgVirtServiceDnsType OBJECT-TYPE
    SYNTAX  INTEGER {
        dns(1),
        dnssec(2),
        both(3)
        }
    MAX-ACCESS  read-create
    STATUS  current
    DESCRIPTION
        "Set DNS type for this service (DNS, DNSSEC)."
    ::= { slbNewCfgVirtServicesFifthPartEntry 10 }

slbNewCfgVirtServiceClntproxType OBJECT-TYPE
    SYNTAX  INTEGER {
        none(1),
        http(2),
        https(3)
        }
    MAX-ACCESS  read-create
    STATUS  current
    DESCRIPTION
        "Set client proximity type for this service."
    ::= { slbNewCfgVirtServicesFifthPartEntry 11 }

slbNewCfgVirtServiceZerowinSize OBJECT-TYPE
    SYNTAX  INTEGER {
        enabled(1),
        disabled(2)
        }
    MAX-ACCESS  read-create
    STATUS  current
    DESCRIPTION
        "Enable or disable zero window size in SYN+ACK for this service."
    ::= { slbNewCfgVirtServicesFifthPartEntry 12 }

slbNewCfgVirtServiceCookiePath OBJECT-TYPE
    SYNTAX  DisplayString (SIZE(0..32))
    MAX-ACCESS  read-create
    STATUS  current
    DESCRIPTION
        "The cookie path name of the virtual server used for cookie load balance."
    ::= { slbNewCfgVirtServicesFifthPartEntry 13 }

slbNewCfgVirtServiceCookieSecure OBJECT-TYPE
    SYNTAX  INTEGER {
	yes(1),
        no(2)
        }
    MAX-ACCESS  read-create
    STATUS  current
    DESCRIPTION
        "Is cookie secure [yes/no] [Default: no]."
    ::= { slbNewCfgVirtServicesFifthPartEntry 14 }

slbNewCfgVirtServiceNoRtsp OBJECT-TYPE
    SYNTAX  INTEGER {
	enabled(1),
        disabled(2)
        }
    MAX-ACCESS  read-create
    STATUS  current
    DESCRIPTION
        "Enable or disable only rtsp SLB for this service."
    ::= { slbNewCfgVirtServicesFifthPartEntry 15 }

slbNewCfgVirtServiceCkRebind OBJECT-TYPE
    SYNTAX  INTEGER {
        enabled(1),
        disabled(2)
        }
    MAX-ACCESS  read-create
    STATUS  current
    DESCRIPTION
        "Enable or disable server rebalancing when cookie is absent.
        When enabled, server load balancing will happen
        for subsequent request comes without cookie."
    ::= { slbNewCfgVirtServicesFifthPartEntry 16 }

slbNewCfgVirtServiceParseLimit OBJECT-TYPE
    SYNTAX  INTEGER {
        enabled(1),
        disabled(2)
        }
    MAX-ACCESS  read-create
    STATUS  current
    DESCRIPTION
        "Enable or disable buffer limit for content based selection."
    ::= { slbNewCfgVirtServicesFifthPartEntry 17 }

slbNewCfgVirtServiceParseLength OBJECT-TYPE
    SYNTAX  INTEGER (0..18200)
    MAX-ACCESS  read-create
    STATUS  current
    DESCRIPTION
        "The buffer length for content based selection."
    ::= { slbNewCfgVirtServicesFifthPartEntry 18 }

slbNewCfgVirtServiceUriNorm OBJECT-TYPE
    SYNTAX  INTEGER {
        enabled(1),
        disabled(2)
        }
    MAX-ACCESS  read-create
    STATUS  current
    DESCRIPTION
        "Enable or disable URI normalization for HTTP content matching."
    ::= { slbNewCfgVirtServicesFifthPartEntry 19 }

-- URL based BWM table for Virtual Services

slbUrlBwmTableMaxSize OBJECT-TYPE
    SYNTAX  Integer32 
    MAX-ACCESS  read-only 
    STATUS  current 
    DESCRIPTION 
        "The maximum number of entries in SLB URL BWM Table." 
    ::= { virtualServerCfg 7}

slbCurCfgUrlBwmTable OBJECT-TYPE
    SYNTAX  SEQUENCE OF SlbCurCfgUrlBwmEntry
    MAX-ACCESS  not-accessible
    STATUS  current
    DESCRIPTION
        "The table of URL based BWM for Virtual Services."
    ::= { virtualServerCfg 8 }

slbCurCfgUrlBwmEntry OBJECT-TYPE
    SYNTAX  SlbCurCfgUrlBwmEntry
    MAX-ACCESS  not-accessible
    STATUS  current
    DESCRIPTION
        "A row in the URL based BWM virtual services table."
    INDEX   { slbCurCfgUrlBwmVirtServIndex, 
              slbCurCfgUrlBwmVirtServiceIndex, 
              slbCurCfgUrlBwmUrlId }
    ::= { slbCurCfgUrlBwmTable 1 }

SlbCurCfgUrlBwmEntry ::= SEQUENCE {
    slbCurCfgUrlBwmVirtServIndex     Integer32,
    slbCurCfgUrlBwmVirtServiceIndex  Integer32,
    slbCurCfgUrlBwmUrlId             Integer32,
    slbCurCfgUrlBwmContract          Integer32
    }

slbCurCfgUrlBwmVirtServIndex OBJECT-TYPE
    SYNTAX  Integer32
    MAX-ACCESS  read-only
    STATUS  current
    DESCRIPTION
        "The number of the virtual server." 
    ::= { slbCurCfgUrlBwmEntry 1 }

slbCurCfgUrlBwmVirtServiceIndex OBJECT-TYPE 
    SYNTAX  Integer32 
    MAX-ACCESS  read-only 
    STATUS  current 
    DESCRIPTION 
        "The service index. This has no external meaning" 
    ::= { slbCurCfgUrlBwmEntry 2 }

slbCurCfgUrlBwmUrlId OBJECT-TYPE  
    SYNTAX  Integer32  
    MAX-ACCESS  read-only  
    STATUS  current  
    DESCRIPTION 
        "The URL Path Identifier."  
    ::= { slbCurCfgUrlBwmEntry 3 } 

slbCurCfgUrlBwmContract OBJECT-TYPE  
    SYNTAX  Integer32  
    MAX-ACCESS  read-only  
    STATUS  current  
    DESCRIPTION 
        "The BW contract number."  
    ::= { slbCurCfgUrlBwmEntry 4 } 

slbNewCfgUrlBwmTable OBJECT-TYPE
    SYNTAX  SEQUENCE OF SlbNewCfgUrlBwmEntry
    MAX-ACCESS  not-accessible
    STATUS  current
    DESCRIPTION
        "The table of URL based BWM for Virtual Services."
    ::= { virtualServerCfg 9 }

slbNewCfgUrlBwmEntry OBJECT-TYPE
    SYNTAX  SlbNewCfgUrlBwmEntry
    MAX-ACCESS  not-accessible
    STATUS  current
    DESCRIPTION
        "A row in the URL based BWM virtual services table."
    INDEX   { slbNewCfgUrlBwmVirtServIndex, 
              slbNewCfgUrlBwmVirtServiceIndex, 
              slbNewCfgUrlBwmUrlId }
    ::= { slbNewCfgUrlBwmTable 1 }

SlbNewCfgUrlBwmEntry ::= SEQUENCE {
    slbNewCfgUrlBwmVirtServIndex     Integer32,
    slbNewCfgUrlBwmVirtServiceIndex  Integer32,
    slbNewCfgUrlBwmUrlId             Integer32,
    slbNewCfgUrlBwmContract          Integer32,
    slbNewCfgUrlBwmDelete            INTEGER
    }

slbNewCfgUrlBwmVirtServIndex OBJECT-TYPE
    SYNTAX  Integer32
    MAX-ACCESS  read-only
    STATUS  current
    DESCRIPTION
        "The number of the virtual server." 
    ::= { slbNewCfgUrlBwmEntry 1 }

slbNewCfgUrlBwmVirtServiceIndex OBJECT-TYPE 
    SYNTAX  Integer32 
    MAX-ACCESS  read-only 
    STATUS  current 
    DESCRIPTION 
        "The service index. This has no external meaning" 
    ::= { slbNewCfgUrlBwmEntry 2 }

slbNewCfgUrlBwmUrlId OBJECT-TYPE  
    SYNTAX  Integer32  
    MAX-ACCESS  read-only  
    STATUS  current  
    DESCRIPTION 
        "The URL Path Identifier."  
    ::= { slbNewCfgUrlBwmEntry 3 } 

slbNewCfgUrlBwmContract OBJECT-TYPE  
    SYNTAX  Integer32  
    MAX-ACCESS  read-create  
    STATUS  current  
    DESCRIPTION 
        "The BW contract number."
    ::= { slbNewCfgUrlBwmEntry 4 } 

slbNewCfgUrlBwmDelete OBJECT-TYPE
    SYNTAX  INTEGER {
        other(1),
        delete(2)
       }
    MAX-ACCESS  read-create
    STATUS  current
    DESCRIPTION
        "When set to the value of 2 (delete), the entire row is deleted. 
         When read, other(1) is returned. Setting the value to anything 
         other than 2(delete) has no effect on the state of the row."
    ::= { slbNewCfgUrlBwmEntry 5 }

--L7 Content based services rule
slbCurCfgContRuleTable OBJECT-TYPE
    SYNTAX  SEQUENCE OF SlbCurCfgContRuleEntry
    MAX-ACCESS  not-accessible
    STATUS  current
    DESCRIPTION
        "The table of Content based Services Rules."
    ::= { virtualServerCfg 10 }

slbCurCfgContRuleEntry OBJECT-TYPE
    SYNTAX  SlbCurCfgContRuleEntry
    MAX-ACCESS  not-accessible
    STATUS  current
    DESCRIPTION
        "A row in the Content Based Services Rules table."
    INDEX  { slbCurCfgContVirtServIndex, slbCurCfgContVirtServiceIndex,
             slbCurCfgContRuleIndex } 
    ::= { slbCurCfgContRuleTable 1 }

SlbCurCfgContRuleEntry ::= SEQUENCE {
    slbCurCfgContVirtServIndex       Integer32,
    slbCurCfgContVirtServiceIndex  Integer32,
    slbCurCfgContRuleIndex   Integer32,
    slbCurCfgContRuleName     DisplayString,
    slbCurCfgContRuleContClass  DisplayString, 
    slbCurCfgContRuleAction    INTEGER,
    slbCurCfgContRuleRealGrpNum       INTEGER,
    slbCurCfgContRuleGotoRuleNum      INTEGER,
    slbCurCfgContRuleRedirection  DisplayString,
    slbCurCfgContRuleState   INTEGER
    }

slbCurCfgContVirtServIndex OBJECT-TYPE
    SYNTAX  Integer32
    MAX-ACCESS  read-only
    STATUS  current
    DESCRIPTION
        "The number of the virtual server." 
    ::= { slbCurCfgContRuleEntry  1 }

slbCurCfgContVirtServiceIndex OBJECT-TYPE 
    SYNTAX  Integer32 
    MAX-ACCESS  read-only 
    STATUS  current 
    DESCRIPTION 
        "The service index. This has no external meaning" 
    ::= { slbCurCfgContRuleEntry  2 }

slbCurCfgContRuleIndex OBJECT-TYPE
    SYNTAX  Integer32
    MAX-ACCESS  read-only
    STATUS  current
    DESCRIPTION
        "The content based service rule index."
    ::= { slbCurCfgContRuleEntry  3 }

slbCurCfgContRuleName OBJECT-TYPE 
    SYNTAX  DisplayString (SIZE(0..32))
    MAX-ACCESS  read-only
    STATUS  current 
    DESCRIPTION 
        "The Content Rule Name."  
    ::= { slbCurCfgContRuleEntry  4 }

slbCurCfgContRuleContClass OBJECT-TYPE 
    SYNTAX  DisplayString (SIZE(0..32))
    MAX-ACCESS  read-only
    STATUS  current 
    DESCRIPTION 
        "The Content Class for the rule."  
    ::= { slbCurCfgContRuleEntry  5 }

slbCurCfgContRuleAction OBJECT-TYPE 
    SYNTAX  INTEGER {
    group(1),
    appredir(2),
    discard(3),
    goto(4)
    }
    MAX-ACCESS  read-only
    STATUS  current 
    DESCRIPTION 
        "Action type of the rule."  
    ::= { slbCurCfgContRuleEntry  6 }

slbCurCfgContRuleRealGrpNum OBJECT-TYPE 
    SYNTAX  INTEGER (1..1024)
    MAX-ACCESS  read-only
    STATUS  current 
    DESCRIPTION 
        "The group number of real server."
    ::= { slbCurCfgContRuleEntry 7 }

slbCurCfgContRuleGotoRuleNum OBJECT-TYPE
    SYNTAX  INTEGER (1..12800)
    MAX-ACCESS  read-only
    STATUS  current
    DESCRIPTION
        "The group number of real server."
    ::= { slbCurCfgContRuleEntry 8 } 

slbCurCfgContRuleRedirection OBJECT-TYPE 
    SYNTAX  DisplayString (SIZE(0..255))
    MAX-ACCESS  read-only
    STATUS  current 
    DESCRIPTION 
        "Application redirection for the rule."  
    ::= { slbCurCfgContRuleEntry  9 }

slbCurCfgContRuleState OBJECT-TYPE   
    SYNTAX INTEGER {
        enabled(1),
    disabled(2)
    }
    MAX-ACCESS  read-only   
    STATUS  current   
    DESCRIPTION 
        "Enable or disable Content Based Services Rule ."
    ::= { slbCurCfgContRuleEntry 10 }

slbNewCfgContRuleTable OBJECT-TYPE
    SYNTAX  SEQUENCE OF SlbNewCfgContRuleEntry
    MAX-ACCESS  not-accessible
    STATUS  current
    DESCRIPTION
        "The table of Content based Services Rules."
    ::= { virtualServerCfg 11 }

slbNewCfgContRuleEntry OBJECT-TYPE
    SYNTAX  SlbNewCfgContRuleEntry
    MAX-ACCESS  not-accessible
    STATUS  current
    DESCRIPTION
        "A row in the Content Based Services Rules table."
    INDEX  { slbNewCfgContVirtServIndex, slbNewCfgContVirtServiceIndex,
             slbNewCfgContRuleIndex } 
    ::= { slbNewCfgContRuleTable 1 }

SlbNewCfgContRuleEntry ::= SEQUENCE {
    slbNewCfgContVirtServIndex       Integer32,
    slbNewCfgContVirtServiceIndex  Integer32,
    slbNewCfgContRuleIndex         Integer32,
    slbNewCfgContRuleName     DisplayString,
    slbNewCfgContRuleContClass  DisplayString, 
    slbNewCfgContRuleAction    INTEGER,
    slbNewCfgContRuleRealGrpNum       INTEGER,
    slbNewCfgContRuleGotoRuleNum INTEGER,
    slbNewCfgContRuleRedirection  DisplayString,
    slbNewCfgContRuleCopy   INTEGER,
    slbNewCfgContRuleState   INTEGER,
    slbNewCfgContRuleDelete   INTEGER   
    }

slbNewCfgContVirtServIndex OBJECT-TYPE
    SYNTAX  Integer32
    MAX-ACCESS  read-only
    STATUS  current
    DESCRIPTION
        "The number of the virtual server." 
    ::= { slbNewCfgContRuleEntry  1 }

slbNewCfgContVirtServiceIndex OBJECT-TYPE 
    SYNTAX  Integer32 
    MAX-ACCESS  read-only 
    STATUS  current 
    DESCRIPTION 
        "The service index. This has no external meaning" 
    ::= { slbNewCfgContRuleEntry  2 }

slbNewCfgContRuleIndex OBJECT-TYPE
    SYNTAX  Integer32
    MAX-ACCESS  read-only
    STATUS  current
    DESCRIPTION
        "The content based service index."
    ::= { slbNewCfgContRuleEntry  3 }

slbNewCfgContRuleName OBJECT-TYPE 
    SYNTAX  DisplayString (SIZE(0..32))
    MAX-ACCESS  read-create
    STATUS  current 
    DESCRIPTION 
        "The Content Rule Name."  
    ::= { slbNewCfgContRuleEntry  4 }

slbNewCfgContRuleContClass OBJECT-TYPE 
    SYNTAX  DisplayString (SIZE(0..32))
    MAX-ACCESS  read-create
    STATUS  current 
    DESCRIPTION 
        "The Content Class for the rule."  
    ::= { slbNewCfgContRuleEntry  5 }

slbNewCfgContRuleAction OBJECT-TYPE 
    SYNTAX  INTEGER {
    group(1),
    appredir(2),
              discard(3),
              goto(4)
    }
    MAX-ACCESS  read-create
    STATUS  current 
    DESCRIPTION 
        "Action type of the rule."  
    ::= { slbNewCfgContRuleEntry  6 }

slbNewCfgContRuleRealGrpNum OBJECT-TYPE 
    SYNTAX  INTEGER (1..1024)
    MAX-ACCESS  read-create
    STATUS  current 
    DESCRIPTION 
        "The group number of real server."
    ::= { slbNewCfgContRuleEntry 7 }

slbNewCfgContRuleGotoRuleNum OBJECT-TYPE
    SYNTAX  INTEGER (1..12800)
    MAX-ACCESS  read-create
    STATUS  current
    DESCRIPTION
        "The group number of real server."
    ::= { slbNewCfgContRuleEntry 8 }


slbNewCfgContRuleRedirection OBJECT-TYPE 
    SYNTAX  DisplayString (SIZE(0..255))
    MAX-ACCESS  read-create
    STATUS  current 
    DESCRIPTION 
        "Application redirection for the rule."  
    ::= { slbNewCfgContRuleEntry  9 }

slbNewCfgContRuleCopy OBJECT-TYPE 
    SYNTAX  INTEGER (1..12800)
    MAX-ACCESS  read-create
    STATUS  current 
    DESCRIPTION 
        "The Number to which current rule is to be copied."
    ::= { slbNewCfgContRuleEntry 10 }


slbNewCfgContRuleState OBJECT-TYPE   
    SYNTAX  INTEGER {
        enabled(1),
        disabled(2)
    }
    MAX-ACCESS  read-create   
    STATUS  current   
    DESCRIPTION 
        "Enable or disable Content Based Services Rule ."
    ::= { slbNewCfgContRuleEntry 11 }


slbNewCfgContRuleDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { slbNewCfgContRuleEntry 12 }



--  SLB Port table

slbPortTableMaxSize OBJECT-TYPE
    SYNTAX  Integer32 
    MAX-ACCESS  read-only 
    STATUS  current 
    DESCRIPTION 
        "The maximum number of entries in SLB Port Table." 
    ::= { portCfg 1 }

slbCurCfgPortTable OBJECT-TYPE
    SYNTAX  SEQUENCE OF SlbCurCfgPortEntry
    MAX-ACCESS  not-accessible
    STATUS  current
    DESCRIPTION
       "The table of ports and their SLB states"
    ::= { portCfg 2 }

slbCurCfgPortEntry OBJECT-TYPE
    SYNTAX  SlbCurCfgPortEntry
    MAX-ACCESS  not-accessible
    STATUS  current
    DESCRIPTION
        "A row in the slbPortTable "
    INDEX   { slbCurCfgPortIndex }
    ::= { slbCurCfgPortTable 1 }

SlbCurCfgPortEntry ::= SEQUENCE {
    slbCurCfgPortIndex              Integer32,
    slbCurCfgPortSlbHotStandby      INTEGER,
    slbCurCfgPortSlbInterSwitch     INTEGER,
    slbCurCfgPortSlbPipState        INTEGER,
    slbCurCfgPortSlbRtsState        INTEGER,
    slbCurCfgPortSlbIdslbState      INTEGER,
    slbCurCfgPortSlbState           INTEGER,
    slbCurCfgPortSlbFilter          INTEGER,
    slbCurCfgPortSlbServState       INTEGER,
    slbCurCfgPortSlbClntState       INTEGER,
    slbCurCfgPortSlbL3Filter        INTEGER,
    slbCurCfgPortSlbFilterBmap      OCTET STRING,
    slbCurCfgPortInterSwitchVlan    INTEGER,
    slbCurCfgPortVlanBmap           OCTET STRING
    }

slbCurCfgPortIndex OBJECT-TYPE
    SYNTAX  Integer32
    MAX-ACCESS  read-only
    STATUS  current
    DESCRIPTION
        "The port number for which the SLB information pertains." 
    ::= { slbCurCfgPortEntry 1 }

slbCurCfgPortSlbState OBJECT-TYPE
    SYNTAX  INTEGER {
	none(1),
	client(2),
	server(3),
	client-server(4)
	}
    MAX-ACCESS  read-only
    STATUS  current
    DESCRIPTION
        "The SLB state of the port.
	 none(1)            - not SLB port
	 client(2)          - SLB client port
	 server(3)          - SLB server port
	 client-server(4)   - SLB client and server port"
    ::= { slbCurCfgPortEntry 2 }

slbCurCfgPortSlbFilter OBJECT-TYPE
    SYNTAX  INTEGER {
        enabled(1),
        disabled(2)
        }
    MAX-ACCESS  read-only
    STATUS  current
    DESCRIPTION
        "Enable or disable Filtering."
    ::= { slbCurCfgPortEntry 9 }

slbCurCfgPortSlbHotStandby OBJECT-TYPE
    SYNTAX  INTEGER {
        enabled(1),
        disabled(2)
        }
    MAX-ACCESS  read-only
    STATUS  current
    DESCRIPTION
        "Enable or disable hot standby processing on the switch port."
    ::= { slbCurCfgPortEntry 3 }

slbCurCfgPortSlbInterSwitch OBJECT-TYPE
    SYNTAX  INTEGER {
        enabled(1),
        disabled(2)
        }
    MAX-ACCESS  read-only
    STATUS  current
    DESCRIPTION
        "Enable or disable inter-switch processing on the switch port."
    ::= { slbCurCfgPortEntry 4 }

slbCurCfgPortSlbPipState OBJECT-TYPE
    SYNTAX  INTEGER {
        enabled(1),
        disabled(2)
        }
    MAX-ACCESS  read-only
    STATUS  current
    DESCRIPTION
        "Enable or disable use of proxy IP address on the switch port."
    ::= { slbCurCfgPortEntry 5 }

slbCurCfgPortSlbRtsState OBJECT-TYPE
    SYNTAX  INTEGER   {
        enabled(1),
        disabled(2)
        }
    MAX-ACCESS  read-only
    STATUS  current
    DESCRIPTION
        "Enable or disable RTS processing on the switch port."
    ::= { slbCurCfgPortEntry 6 }

slbCurCfgPortSlbIdslbState OBJECT-TYPE
    SYNTAX  INTEGER {
        enabled(1),
        disabled(2)
        }
    MAX-ACCESS  read-only
    STATUS  current
    DESCRIPTION
        "Enable or disable Intrusion Detection server load balancing."
    ::= { slbCurCfgPortEntry 7 }


slbCurCfgPortSlbServState OBJECT-TYPE
    SYNTAX  INTEGER {
        enabled(1),
            disabled(2)
    }
    MAX-ACCESS  read-only
    STATUS  current
    DESCRIPTION
        "Enable or disable server processing."
    ::= { slbCurCfgPortEntry 10 }

slbCurCfgPortSlbClntState OBJECT-TYPE
    SYNTAX  INTEGER {
        enabled(1),
        disabled(2)
    }
    MAX-ACCESS  read-only
    STATUS  current
    DESCRIPTION
        "Enable or disable client processing."
    ::= { slbCurCfgPortEntry 11 }

slbCurCfgPortSlbL3Filter OBJECT-TYPE
    SYNTAX  INTEGER {
        enabled(1),
        disabled(2)
        }
    MAX-ACCESS  read-only
    STATUS  current
    DESCRIPTION
        "Enable or disable Layer3 Filtering."
    ::= { slbCurCfgPortEntry 12 }

slbCurCfgPortSlbFilterBmap OBJECT-TYPE
    SYNTAX  OCTET STRING (SIZE(0..256))
    MAX-ACCESS  read-only
    STATUS  current
    DESCRIPTION
	"The filtering rules applied to the port.  The filtering rules are 
         presented in bitmap format.

	 in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltCurCfgTable)

         where x : 1 - The represented filter rule applied to the port
		   0 - The represented filter rule not applied to the port "
    ::= { slbCurCfgPortEntry 13 }

slbCurCfgPortInterSwitchVlan OBJECT-TYPE
    SYNTAX  INTEGER (1..4090)
    MAX-ACCESS read-only
    STATUS  current
    DESCRIPTION
        "VLAN for inter-switch processing."
    ::= { slbCurCfgPortEntry 14 }

slbCurCfgPortVlanBmap  OBJECT-TYPE
    SYNTAX  OCTET STRING
    MAX-ACCESS  read-only
    STATUS  current
    DESCRIPTION
        "VLANs associated with this port.
         The VLANs are presented in a bitmap format.

         OCTET 1  OCTET 2  .....
         xxxxxxxx xxxxxxxx .....
         ||    || |_ VLAN 9
         ||    ||
         ||    ||___ VLAN 8
         ||    |____ VLAN 7
         ||      .    .   .
         ||_________ VLAN 2
         |__________ VLAN 1

         where x : 1 - VLAN is associated
                   0 - VLAN is not associated"
    ::= { slbCurCfgPortEntry 15 }

-- Server load balancing - slb port state table

slbNewCfgPortTable OBJECT-TYPE
    SYNTAX  SEQUENCE OF SlbNewCfgPortEntry
    MAX-ACCESS  not-accessible
    STATUS  current
    DESCRIPTION
        "The table of ports and their SLB states"
    ::= { portCfg 3 }

slbNewCfgPortEntry OBJECT-TYPE
    SYNTAX  SlbNewCfgPortEntry
    MAX-ACCESS  not-accessible
    STATUS  current
    DESCRIPTION
        "A row in the slbPortTable "
    INDEX   { slbNewCfgPortIndex }
    ::= { slbNewCfgPortTable 1 }

SlbNewCfgPortEntry ::= SEQUENCE {
    slbNewCfgPortIndex              Integer32,
    slbNewCfgPortSlbHotStandby      INTEGER,
    slbNewCfgPortSlbInterSwitch     INTEGER,
    slbNewCfgPortSlbPipState        INTEGER,
    slbNewCfgPortSlbRtsState        INTEGER,
    slbNewCfgPortDelete             INTEGER,
    slbNewCfgPortSlbIdslbState      INTEGER,
    slbNewCfgPortSlbState           INTEGER,
    slbNewCfgPortSlbFilter          INTEGER,
    slbNewCfgPortSlbAddFilter       INTEGER,
    slbNewCfgPortSlbRemFilter       INTEGER,
    slbNewCfgPortSlbServState       INTEGER,
    slbNewCfgPortSlbClntState       INTEGER,
    slbNewCfgPortSlbL3Filter        INTEGER,
    slbNewCfgPortSlbFilterBmap      OCTET STRING,
    slbNewCfgPortInterSwitchVlan    INTEGER,
    slbNewCfgPortVlanBmap           OCTET STRING
    }

slbNewCfgPortIndex OBJECT-TYPE
    SYNTAX  Integer32
    MAX-ACCESS  read-only
    STATUS  current
    DESCRIPTION
        "The port number for which the SLB information pertains." 
    ::= { slbNewCfgPortEntry 1 }

slbNewCfgPortSlbState OBJECT-TYPE
    SYNTAX  INTEGER {
	none(1),
	client(2),
	server(3),
	client-server(4)
	}
    MAX-ACCESS  read-write
    STATUS  current
    DESCRIPTION
        "The SLB state of the port.
	 none(1)            - not SLB port
	 client(2)          - SLB client port
	 server(3)          - SLB server port
	 client-server(4)   - SLB client and server port"
    ::= { slbNewCfgPortEntry 2 }

slbNewCfgPortSlbHotStandby OBJECT-TYPE
    SYNTAX  INTEGER   {
        enabled(1),
        disabled(2)
        }
    MAX-ACCESS  read-write
    STATUS  current
    DESCRIPTION
        "Enable or disable hot standby processing on the switch port."
    ::= { slbNewCfgPortEntry 3 }

slbNewCfgPortSlbInterSwitch OBJECT-TYPE
    SYNTAX  INTEGER   {
        enabled(1),
        disabled(2)
        }
    MAX-ACCESS  read-write
    STATUS  current
    DESCRIPTION
        "Enable or disable inter-switch processing on the switch port."
    ::= { slbNewCfgPortEntry 4 }

slbNewCfgPortSlbPipState OBJECT-TYPE
    SYNTAX  INTEGER   {
        enabled(1),
        disabled(2)
        }
    MAX-ACCESS  read-write
    STATUS  current
    DESCRIPTION
        "Enable or disable use of proxy IP address on the switch port."
    ::= { slbNewCfgPortEntry 5 }

slbNewCfgPortSlbRtsState OBJECT-TYPE
    SYNTAX  INTEGER   {
        enabled(1),
        disabled(2)
        }
    MAX-ACCESS  read-write
    STATUS  current
    DESCRIPTION
        "Enable or disable RTS processing on the switch port."
    ::= { slbNewCfgPortEntry 6 }

slbNewCfgPortDelete OBJECT-TYPE
    SYNTAX INTEGER {
        other(1),
        delete(2)
        }
    MAX-ACCESS read-write
    STATUS current
    DESCRIPTION
        "When set to the value of 2 (delete), the entire row is deleted. 
         When read, other(1) is returned. Setting the value to anything 
         other than 2(delete) has no effect on the state of the row."
    ::= { slbNewCfgPortEntry 7 }

slbNewCfgPortSlbIdslbState OBJECT-TYPE
    SYNTAX  INTEGER {
        enabled(1),
        disabled(2)
        }
    MAX-ACCESS  read-write
    STATUS  current
    DESCRIPTION
        "Enable or disable Intrusion Detection server load balancing."
    ::= { slbNewCfgPortEntry 8 }


slbNewCfgPortSlbFilter OBJECT-TYPE
    SYNTAX  INTEGER {
        enabled(1),
        disabled(2)
        }
    MAX-ACCESS  read-write
    STATUS  current
    DESCRIPTION
        "Enable or disable Filtering."
    ::= { slbNewCfgPortEntry 10 }

slbNewCfgPortSlbAddFilter OBJECT-TYPE
    SYNTAX  INTEGER (1..2048)
    MAX-ACCESS  read-write
    STATUS  current
    DESCRIPTION
         "Specify the Filter Number to be added to this Port table." 
    ::= { slbNewCfgPortEntry 11 }

slbNewCfgPortSlbRemFilter OBJECT-TYPE
    SYNTAX  INTEGER (1..2048)
    MAX-ACCESS  read-write
    STATUS  current
    DESCRIPTION
         "Specify the Filter Number to be deleted from this Port table."
    ::= { slbNewCfgPortEntry 12 }

slbNewCfgPortSlbServState OBJECT-TYPE
    SYNTAX  INTEGER {
        enabled(1),
            disabled(2)
    }
    MAX-ACCESS  read-write
    STATUS  current
    DESCRIPTION
        "Enable or disable Server Processing."
    ::= { slbNewCfgPortEntry 13 }

slbNewCfgPortSlbClntState OBJECT-TYPE
    SYNTAX  INTEGER {
        enabled(1),
            disabled(2)
    }
    MAX-ACCESS  read-write
    STATUS  current
    DESCRIPTION
        "Enable or disable Client Processing."
    ::= { slbNewCfgPortEntry 14 }

slbNewCfgPortSlbL3Filter OBJECT-TYPE
    SYNTAX  INTEGER {
        enabled(1),
        disabled(2)
        }
    MAX-ACCESS  read-write
    STATUS  current
    DESCRIPTION
        "Enable or disable Layer3 Filtering."
    ::= { slbNewCfgPortEntry 15 }

slbNewCfgPortSlbFilterBmap OBJECT-TYPE
    SYNTAX  OCTET STRING (SIZE(0..256))
    MAX-ACCESS  read-only
    STATUS  current
    DESCRIPTION
	"The filtering rules applied to the port.  The filtering rules are 
         presented in bitmap format.

	 in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltCurCfgTable)

         where x : 1 - The represented filter rule applied to the port
		   0 - The represented filter rule not applied to the port "
    ::= { slbNewCfgPortEntry 16 }

slbNewCfgPortInterSwitchVlan OBJECT-TYPE
    SYNTAX  INTEGER (1..4090)
    MAX-ACCESS read-write 
    STATUS  current
    DESCRIPTION
        "VLAN for inter-switch processing."
    ::= { slbNewCfgPortEntry 17 }

slbNewCfgPortVlanBmap OBJECT-TYPE
    SYNTAX  OCTET STRING
    MAX-ACCESS  read-only
    STATUS  current
    DESCRIPTION
        "VLANs associated with this port.
         The VLANs are presented in a bitmap format.

         OCTET 1  OCTET 2  .....
         xxxxxxxx xxxxxxxx .....
         ||    || |_ VLAN 9
         ||    ||
         ||    ||___ VLAN 8
         ||    |____ VLAN 7
         ||      .    .   .
         ||_________ VLAN 2
         |__________ VLAN 1

         where x : 1 - VLAN is associated
                   0 - VLAN is not associated"
    ::= { slbNewCfgPortEntry 18 }

-- SLB General Configuration 

slbCurCfgGlobalControl OBJECT-TYPE
    SYNTAX  INTEGER { 
	enabled(2),
	disabled(3)
	}
    MAX-ACCESS  read-only
    STATUS  current
    DESCRIPTION
        "The global state of Server Load Balancing."
    ::= { slbGeneralCfg 1 }

slbNewCfgGlobalControl OBJECT-TYPE
    SYNTAX  INTEGER { 
        enabled(2),
        disabled(3)
        }
    MAX-ACCESS  read-write
    STATUS  current
    DESCRIPTION
        "The global state of Server Load Balancing."
    ::= { slbGeneralCfg 2 }

slbCurCfgImask OBJECT-TYPE
    SYNTAX  IpAddress
    MAX-ACCESS  read-only
    STATUS  current
    DESCRIPTION
        "The virtual and real IP address mask - corresponding to the
	 imask command of the slb configuration menu." 
    ::= { slbGeneralCfg 3 }

slbNewCfgImask OBJECT-TYPE
    SYNTAX  IpAddress
    MAX-ACCESS  read-write
    STATUS  current
    DESCRIPTION
        "The virtual and real IP address mask - corresponding to the
         imask command of the slb configuration menu."
    ::= { slbGeneralCfg 4 }

slbCurCfgMnet OBJECT-TYPE
    SYNTAX  IpAddress
    MAX-ACCESS  read-only
    STATUS  current
    DESCRIPTION
        "The management network - corresponding to the mnet command of 
         the slb configuration menu." 
    ::= { slbGeneralCfg 5 }

slbNewCfgMnet OBJECT-TYPE
    SYNTAX  IpAddress
    MAX-ACCESS  read-write
    STATUS  current
    DESCRIPTION
        "The management network - corresponding to the mnet command of 
         the slb configuration menu." 
    ::= { slbGeneralCfg 6 }

slbCurCfgMmask OBJECT-TYPE
    SYNTAX  IpAddress
    MAX-ACCESS  read-only
    STATUS  current
    DESCRIPTION
        "The management subnet mask - corresponding to the mmask command 
         of the slb configuration menu." 
    ::= { slbGeneralCfg 7 }

slbNewCfgMmask OBJECT-TYPE
    SYNTAX  IpAddress
    MAX-ACCESS  read-write
    STATUS  current
    DESCRIPTION
        "The management subnet mask - corresponding to the mmask command 
         of the slb configuration menu." 
    ::= { slbGeneralCfg 8 }

slbCurCfgRadiusAuthenString OBJECT-TYPE
    SYNTAX  DisplayString (SIZE(0..32))
    MAX-ACCESS  read-only
    STATUS  current
    DESCRIPTION
        "The RADIUS authentication string.  The string is used for 
	 generating encrypted authentication string for RADIUS health check."
    ::= { slbGeneralCfg 9 }

slbNewCfgRadiusAuthenString OBJECT-TYPE
    SYNTAX  DisplayString (SIZE(0..32))
    MAX-ACCESS  read-write
    STATUS  current
    DESCRIPTION
        "The RADIUS authentication string.  The string is used for 
	 generating encrypted authentication string for RADIUS health check."
    ::= { slbGeneralCfg 10 }

slbCurCfgDirectMode OBJECT-TYPE
    SYNTAX  INTEGER {
        enabled(1),
        disabled(2)
        }
    MAX-ACCESS  read-only
    STATUS  current
    DESCRIPTION
        "Enable or disable direct access mode. It allows direct access to 
         real servers and any combination of virtual and real servers 
         when set to enabled(1)."
    ::= { slbGeneralCfg 11 }

slbNewCfgDirectMode OBJECT-TYPE
    SYNTAX  INTEGER {
        enabled(1),
        disabled(2)
        }
    MAX-ACCESS  read-write
    STATUS  current
    DESCRIPTION
        "Enable or disable direct access mode. It allows direct access to 
         real servers and any combination of virtual and real servers 
         when set to enabled(1)."
    ::= { slbGeneralCfg 12 }

slbCurCfgPmask OBJECT-TYPE
    SYNTAX  IpAddress
    MAX-ACCESS  read-only
    STATUS  current
    DESCRIPTION
        "The persistent mask - corresponding to the pmask command of the 
         slb configuration menu." 
    ::= { slbGeneralCfg 13 }

slbNewCfgPmask OBJECT-TYPE
    SYNTAX  IpAddress
    MAX-ACCESS  read-write
    STATUS  current
    DESCRIPTION
        "The persistent mask - corresponding to the pmask command of the 
         slb configuration menu." 
    ::= { slbGeneralCfg 14 }

slbCurCfgGrace OBJECT-TYPE
    SYNTAX  INTEGER {
        enabled(1),
        disabled(2)
        }
    MAX-ACCESS  read-only
    STATUS  current
    DESCRIPTION
        "Enable or disable graceful server failure. It allows to keep the 
         connection to the failure real servers when set to enabled(1)."
    ::= { slbGeneralCfg 15 }

slbNewCfgGrace OBJECT-TYPE
    SYNTAX  INTEGER {
        enabled(1),
        disabled(2)
                }
    MAX-ACCESS  read-write
    STATUS  current
    DESCRIPTION
        "Enable or disable graceful server failure. It allows to keep the 
         connection to the failure real servers when set to enabled(1)."
    ::= { slbGeneralCfg 16 }

slbCurCfgVirtMatrixArch OBJECT-TYPE
    SYNTAX  INTEGER {
        enabled(1),
        disabled(2)
        }
    MAX-ACCESS  read-only
    STATUS  current
    DESCRIPTION
        "Enable or disable Virtual Matrix Architecture."
    ::= { slbGeneralCfg 17 }

slbNewCfgVirtMatrixArch OBJECT-TYPE
    SYNTAX  INTEGER {
        enabled(1),
        disabled(2)
        }
    MAX-ACCESS  read-write
    STATUS  current
    DESCRIPTION
        "Enable or disable Virtual Matrix Architecture."
    ::= { slbGeneralCfg 18 }

slbCurCfgFastage OBJECT-TYPE
    SYNTAX  INTEGER (0..7) 
    MAX-ACCESS  read-only
    STATUS  current 
    DESCRIPTION
        "Session table fast-age (1 sec) period bit shift."
    ::= { slbGeneralCfg 19 }

slbNewCfgFastage OBJECT-TYPE
    SYNTAX  INTEGER (0..7) 
    MAX-ACCESS  read-write
    STATUS  current 
    DESCRIPTION
        "Session table fast-age (1 sec) period bit shift."
    ::= { slbGeneralCfg 20 }

slbCurCfgSlowage OBJECT-TYPE
    SYNTAX  INTEGER (0..15) 
    MAX-ACCESS  read-only
    STATUS  obsolete
    DESCRIPTION
        "Session table slow-age (2 min) period bit shift."
    ::= { slbGeneralCfg 21 }

slbNewCfgSlowage OBJECT-TYPE
    SYNTAX  INTEGER (0..15) 
    MAX-ACCESS  read-write
    STATUS  obsolete
    DESCRIPTION
        "Session table slow-age (2 min) period bit shift."
    ::= { slbGeneralCfg 22 }

slbCurCfgTpcp OBJECT-TYPE
    SYNTAX  INTEGER {
        enabled(1),
        disabled(2)
        }
    MAX-ACCESS  read-only
    STATUS  current
    DESCRIPTION
        "Enable or disable Transparent Proxy Cache Protocol."
    ::= { slbGeneralCfg 23 }

slbNewCfgTpcp OBJECT-TYPE
    SYNTAX  INTEGER {
        enabled(1),
        disabled(2)
        }
    MAX-ACCESS  read-write
    STATUS  current
    DESCRIPTION
        "Enable or disable Transparent Proxy Cache Protocol."
    ::= { slbGeneralCfg 24 }

slbCurCfgMetricInterval OBJECT-TYPE
    SYNTAX  INTEGER (1..256) 
    MAX-ACCESS  read-only
    STATUS  current
    DESCRIPTION
        "The interval of response and bandwidth metric updates."
    ::= { slbGeneralCfg 25 }

slbNewCfgMetricInterval OBJECT-TYPE
    SYNTAX  INTEGER (1..256) 
    MAX-ACCESS  read-write
    STATUS  current
    DESCRIPTION
        "The interval of response and bandwidth metric updates."
    ::= { slbGeneralCfg 26 }

slbCurCfgLdapVersion OBJECT-TYPE
    SYNTAX  INTEGER {
	version2(1),
	version3(2)
    } 
    MAX-ACCESS  read-only
    STATUS  current
    DESCRIPTION
        "The version number for LDAP."
    ::= { slbGeneralCfg 27 }

slbNewCfgLdapVersion OBJECT-TYPE
    SYNTAX  INTEGER {
	version2(1),
	version3(2)
    } 
    MAX-ACCESS  read-write
    STATUS  current
    DESCRIPTION
        "The Version number of LDAP."
    ::= { slbGeneralCfg 28 }

slbCurCfgAllowHttpHc OBJECT-TYPE
    SYNTAX  INTEGER {
	enabled(1),
	disabled(2)
    } 
    MAX-ACCESS  read-only
    STATUS  current
    DESCRIPTION
        "Enable or disable allow HTTP health check on any port.
         If disabled the non-HTTP virtual services will use TCP Health Checks,
         if enabled the HTTP Content Health Check will be sent to any port 
         except HTTPS (443) if properly configured."
    ::= { slbGeneralCfg 29 }

slbNewCfgAllowHttpHc OBJECT-TYPE
    SYNTAX  INTEGER {
	enabled(1),
	disabled(2)
    } 
    MAX-ACCESS  read-write
    STATUS  current
    DESCRIPTION
        "Enable or disable allow HTTP health check on any port.
         If disabled the non-HTTP virtual services will use TCP Health Checks,
         if enabled the HTTP Content Health Check will be sent to any port 
         except HTTPS (443) if properly configured."
    ::= { slbGeneralCfg 30 }

slbCurCfgSubmac OBJECT-TYPE
    SYNTAX  INTEGER {
        enabled(1),
        disabled(2)
        }
    MAX-ACCESS  read-only
    STATUS  current
    DESCRIPTION
        "Enable or disable Source MAC Address substitution.
         Enabling this feature supercedes individual real server
         setting for Source MAC Address substitution."
    ::= { slbGeneralCfg 31 }

slbNewCfgSubmac OBJECT-TYPE
    SYNTAX  INTEGER {
        enabled(1),
        disabled(2)
        }
    MAX-ACCESS  read-write
    STATUS  current
    DESCRIPTION
        "Enable or disable Source MAC Address substitution.
         Enabling this feature supercedes individual real server
         setting for Source MAC Address substitution."
    ::= { slbGeneralCfg 32 }

slbCurCfgProxyGratArp OBJECT-TYPE
    SYNTAX  INTEGER {
        enabled(1),
        disabled(2)
        }
    MAX-ACCESS  read-only
    STATUS  obsolete
    DESCRIPTION
        "Enable or disable Proxy IP Gratuitous ARP."
    ::= { slbGeneralCfg 33 }

slbNewCfgProxyGratArp OBJECT-TYPE
    SYNTAX  INTEGER {
        enabled(1),
        disabled(2)
        }
    MAX-ACCESS  read-write
    STATUS  obsolete
    DESCRIPTION
        "Enable or disable Proxy IP Gratuitous ARP."
    ::= { slbGeneralCfg 34 }

slbCurCfgRtsVlan OBJECT-TYPE
    SYNTAX  INTEGER {
        enabled(1),
        disabled(2)
        }
    MAX-ACCESS  read-only
    STATUS  current
    DESCRIPTION
        "Enable or disable use VLAN info for real server lookup"
    ::= { slbGeneralCfg 35 }

slbNewCfgRtsVlan OBJECT-TYPE
    SYNTAX  INTEGER {
        enabled(1),
        disabled(2)
        }
    MAX-ACCESS  read-write
    STATUS  current
    DESCRIPTION
        "Enable or disable use VLAN info for real server lookup"
    ::= { slbGeneralCfg 36 }

slbCurCfgVirtualServiceStats OBJECT-TYPE
    SYNTAX  INTEGER {
        enabled(1),
        disabled(2)
        }
    MAX-ACCESS  read-only
    STATUS  current
    DESCRIPTION
        "Enable/disable Virtual Service Statistics."
    ::= { slbGeneralCfg 37 }

slbNewCfgVirtualServiceStats OBJECT-TYPE
    SYNTAX  INTEGER {
        enabled(1),
        disabled(2)
                }
    MAX-ACCESS  read-write
    STATUS  current
    DESCRIPTION
        "Enable/disable Virtual Service Statistics."
 ::= { slbGeneralCfg 38 }

slbCurCfgSlbSessAtkIntrval OBJECT-TYPE
    SYNTAX  INTEGER (0..3600)
    MAX-ACCESS  read-only
    STATUS  current
    DESCRIPTION
        "Set SLB session attack inspection interval."
    ::= { slbGeneralCfg 39 }

slbNewCfgSlbSessAtkIntrval OBJECT-TYPE
    SYNTAX  INTEGER (0..3600)
    MAX-ACCESS  read-write
    STATUS  current
    DESCRIPTION
        "Set SLB session attack inspection interval."
 ::= { slbGeneralCfg 40 }

slbCurCfgSlbSessAtkAllowlim OBJECT-TYPE
    SYNTAX  INTEGER (1..11999961)
    MAX-ACCESS  read-only
    STATUS  current
    DESCRIPTION
        "Set SLB session attack alert allowable limit."
    ::= { slbGeneralCfg 41 }

slbNewCfgSlbSessAtkAllowlim OBJECT-TYPE
    SYNTAX  INTEGER (1..11999961)
    MAX-ACCESS  read-write
    STATUS  current
    DESCRIPTION
        "Set SLB session attack alert allowable limit."
 ::= { slbGeneralCfg 42 }

slbCurCfgNewSlowage OBJECT-TYPE
    SYNTAX  INTEGER (0..14) 
    MAX-ACCESS  read-only
    STATUS  current
    DESCRIPTION
        "Session table slow-age (2 min) period bit shift."
    ::= { slbGeneralCfg 43 }

slbNewCfgNewSlowage OBJECT-TYPE
    SYNTAX  INTEGER (0..14) 
    MAX-ACCESS  read-write
    STATUS  current
    DESCRIPTION
        "Session table slow-age (2 min) period bit shift."
    ::= { slbGeneralCfg 44 }
    
slbCurCfgPortBind OBJECT-TYPE
    SYNTAX  INTEGER {
        enabled(1),
        disabled(2)
        }
    MAX-ACCESS  read-only
    STATUS  current
    DESCRIPTION
        "Enable/disable ingress port for session table Binding. SP uses
         ingress port for session lookup when set to enable."
    ::= { slbGeneralCfg 45 }

slbNewCfgPortBind OBJECT-TYPE
    SYNTAX  INTEGER {
        enabled(1),
        disabled(2)
                }
    MAX-ACCESS  read-write
    STATUS  current
    DESCRIPTION
        "Enable/disable ingress port for session table Binding. SP uses
         ingress port for session lookup when set to enable."
 ::= { slbGeneralCfg 46 }

slbCurCfgVmaSrcPort OBJECT-TYPE
    SYNTAX  INTEGER {
        enabled(1),
        disabled(2)
        }
    MAX-ACCESS  read-only
    STATUS  current
    DESCRIPTION
       "Enable/disable VMA source port."  
 ::= { slbGeneralCfg 47 }

slbNewCfgVmaSrcPort OBJECT-TYPE
    SYNTAX  INTEGER {
        enabled(1),
        disabled(2)
        }
    MAX-ACCESS  read-write
    STATUS  current
    DESCRIPTION
        "Enable/disable VMA source port." 
 ::= { slbGeneralCfg 48 }
 
slbCurCfgIpTcpCksum OBJECT-TYPE
    SYNTAX  INTEGER {
        enabled(1),
        disabled(2)
        }
    MAX-ACCESS  read-only
    STATUS  current
    DESCRIPTION
        "Enable/disable Layer 7 IP/TCP Checksum Validation."
    ::= { slbGeneralCfg 49 }

slbNewCfgIpTcpCksum OBJECT-TYPE
    SYNTAX  INTEGER {
        enabled(1),
        disabled(2)
                }
    MAX-ACCESS  read-write
    STATUS  current
    DESCRIPTION
        "Enable/disable Layer 7 IP/TCP Checksum Validation."
 ::= { slbGeneralCfg 50 }

slbCurCfgAuxRipHash OBJECT-TYPE
    SYNTAX  INTEGER {
    	enabled(1),
	disabled(2)
	}
    MAX-ACCESS  read-only
    STATUS  current
    DESCRIPTION
    	"Enable/disable Include RIP in AUX table hashing."
    ::= { slbGeneralCfg 51 }

slbNewCfgAuxRipHash OBJECT-TYPE
    SYNTAX  INTEGER {
	enabled(1),
	disabled(2)
	}
    MAX-ACCESS  read-write
    STATUS  current
    DESCRIPTION
	"Enable/disable Include RIP in AUX table hashing."
    ::= { slbGeneralCfg 52 }

slbCurCfgClearBackup OBJECT-TYPE
    SYNTAX  INTEGER {
        enabled(1),
        disabled(2)
    }
    MAX-ACCESS  read-only
    STATUS  current
    DESCRIPTION
        "Enable/Disable clear backup in the current config."
    ::= { slbGeneralCfg 53 }

slbNewCfgClearBackup OBJECT-TYPE
    SYNTAX  INTEGER {
        enabled(1),
        disabled(2)
    }
    MAX-ACCESS  read-write
    STATUS  current
    DESCRIPTION
        "Enable/Disable clear backup in the new config."
    ::= { slbGeneralCfg 54 }

slbCurCfgmStat OBJECT-TYPE
    SYNTAX  INTEGER (1..3600)
    MAX-ACCESS  read-only
    STATUS  current
    DESCRIPTION
        "Measuring period for Acceleration, HTTP and 
         SSL offloading statistics in the current config."
    ::= { slbGeneralCfg 55 }

slbNewCfgmStat OBJECT-TYPE
    SYNTAX  INTEGER (1..3600)
    MAX-ACCESS  read-write
    STATUS  current
    DESCRIPTION
        "Measuring period for Acceleration, HTTP and
         SSL offloading statistics in the new config."
    ::= { slbGeneralCfg 56 }

slbCurCfgvStat OBJECT-TYPE
    SYNTAX  INTEGER {
        enabled(1),
        disabled(2)
    }
    MAX-ACCESS  read-only
    STATUS  current
    DESCRIPTION
        "Enable/Disable Virtual Service 
         Statistics in the current config."
    ::= { slbGeneralCfg 57 }

slbNewCfgvStat OBJECT-TYPE
    SYNTAX  INTEGER {
        enabled(1),
        disabled(2)
    }
    MAX-ACCESS  read-write
    STATUS  current
    DESCRIPTION
        "Enable/Disable Virtual Service 
         Statistics in the new config."
    ::= { slbGeneralCfg 58 }

slbCurCfgVmaDip OBJECT-TYPE
    SYNTAX  INTEGER {
        enabled(1),
        disabled(2)
    }
    MAX-ACCESS  read-only
    STATUS  current
    DESCRIPTION
        "Enable/Disable VMA with destination IP
         in the current config."
    ::= { slbGeneralCfg 59 }

slbNewCfgVmaDip OBJECT-TYPE
    SYNTAX  INTEGER {
        enabled(1),
        disabled(2)
    }
    MAX-ACCESS  read-write
    STATUS  current
    DESCRIPTION
        "Enable/Disable VMA with destination IP
         in the new config."
    ::= { slbGeneralCfg 60 }

slbCurCfgClsRst OBJECT-TYPE
    SYNTAX  INTEGER {
        enabled(1),
        disabled(2)
    }
    MAX-ACCESS  read-only
    STATUS  current
    DESCRIPTION
        "Enable/Disable Session clear on RST
         in the current config."
    ::= { slbGeneralCfg 61 }

slbNewCfgClsRst OBJECT-TYPE
    SYNTAX  INTEGER {
        enabled(1),
        disabled(2)
    }
    MAX-ACCESS  read-write
    STATUS  current
    DESCRIPTION
        "Enable/Disable Session clear on RST
         in the new config."
    ::= { slbGeneralCfg 62 }

slbCurCfgRtsIpLkp OBJECT-TYPE
    SYNTAX  INTEGER {
        enabled(1),
        disabled(2)
    }
    MAX-ACCESS  read-only
    STATUS  current
    DESCRIPTION
        "Enable/Disable RTS-IP lookup in the current config."
    ::= { slbGeneralCfg 63 }

slbNewCfgRtsIpLkp OBJECT-TYPE
    SYNTAX  INTEGER {
        enabled(1),
        disabled(2)
    }
    MAX-ACCESS  read-write
    STATUS  current
    DESCRIPTION
        "Enable/Disable RTS-IP lookup in the new config."
    ::= { slbGeneralCfg 64 }

slbCurCfgPprefix OBJECT-TYPE
    SYNTAX  INTEGER (1..128)
    MAX-ACCESS  read-only
    STATUS  current
    DESCRIPTION
        "The ipv6 persistent prefix length - corresponding to the pmask command of the 
         slb configuration menu." 
    ::= { slbGeneralCfg 65 }

slbNewCfgPprefix OBJECT-TYPE
    SYNTAX  INTEGER (1..128)
    MAX-ACCESS  read-write
    STATUS  current
    DESCRIPTION
        "The ipv6 persistent prefix length - corresponding to the pmask command of the 
         slb configuration menu." 
    ::= { slbGeneralCfg 66 }

slbCurCfgSubdmac OBJECT-TYPE
    SYNTAX  INTEGER {
        enabled(1),
        disabled(2)
    }
    MAX-ACCESS  read-only
    STATUS  current
    DESCRIPTION
        "Enable or disable DMAC substitution.
         Enabling this feature supercedes individual real server
         setting for DMAC substitution."
    ::= { slbGeneralCfg 67 }

slbNewCfgSubdmac OBJECT-TYPE
    SYNTAX  INTEGER {
        enabled(1),
        disabled(2)
    }
    MAX-ACCESS  read-write
    STATUS  current
    DESCRIPTION
        "Enable or disable DMAC substitution.
         Enabling this feature supercedes individual real server
         setting for DMAC substitution."
    ::= { slbGeneralCfg 68 }

slbCurCfgpVlanTag OBJECT-TYPE
    SYNTAX  INTEGER {
        enabled(1),
        disabled(2)
    }
    MAX-ACCESS  read-only
    STATUS  current
    DESCRIPTION
        "Enable or disable preserving vlan tag during packet forwarding"
    ::= { slbGeneralCfg 69 }

slbNewCfgpVlanTag OBJECT-TYPE
    SYNTAX  INTEGER {
        enabled(1),
        disabled(2)
    }
    MAX-ACCESS  read-write
    STATUS  current
    DESCRIPTION
        "Enable or disable preserving vlan tag during packet forwarding"
    ::= { slbGeneralCfg 70 }

slbCurCfgNmask OBJECT-TYPE
    SYNTAX  IpAddress
    MAX-ACCESS  read-only
    STATUS  current
    DESCRIPTION
        "The session mask in the current config block."
    ::= { slbGeneralCfg 71 }

slbNewCfgNmask OBJECT-TYPE
    SYNTAX  IpAddress
    MAX-ACCESS  read-write
    STATUS  current
    DESCRIPTION
        "The session mask in the new config block."
    ::= { slbGeneralCfg 72 }


-- WAP Health Check configuration

slbCurCfgWaphcWSPPort OBJECT-TYPE   
    SYNTAX INTEGER (0..65534)
    MAX-ACCESS read-only   
    STATUS current   
    DESCRIPTION 
        "The WSP port number to health check."   
    ::= { waphcCfg 1 }

slbNewCfgWaphcWSPPort OBJECT-TYPE   
    SYNTAX INTEGER (0..65534)
    MAX-ACCESS read-write
    STATUS current   
    DESCRIPTION 
        "The WSP port number to health check."   
    ::= { waphcCfg 2 }

slbCurCfgWaphcOffset OBJECT-TYPE   
    SYNTAX INTEGER (0..256)
    MAX-ACCESS read-only   
    STATUS current   
    DESCRIPTION 
        "The offset in received WSP packet."   
    ::= { waphcCfg 3 }

slbNewCfgWaphcOffset OBJECT-TYPE   
    SYNTAX INTEGER (0..256)
    MAX-ACCESS read-write
    STATUS current   
    DESCRIPTION 
        "The offset in received WSP packet."   
    ::= { waphcCfg 4 }

slbCurCfgWaphcSndContent OBJECT-TYPE   
    SYNTAX OCTET STRING (SIZE(0..512))
    MAX-ACCESS read-only   
    STATUS current   
    DESCRIPTION 
        "The content to be sent to the WAP gateway."   
    ::= { waphcCfg 5 }

slbNewCfgWaphcSndContent OBJECT-TYPE   
    SYNTAX OCTET STRING (SIZE(0..512))
    MAX-ACCESS read-write
    STATUS current   
    DESCRIPTION 
        "The content to be sent to the WAP gateway."   
    ::= { waphcCfg 6 }

slbCurCfgWaphcRcvContent OBJECT-TYPE   
    SYNTAX OCTET STRING (SIZE(0..512))
    MAX-ACCESS read-only   
    STATUS current   
    DESCRIPTION 
        "The content to be received from the WAP gateway."   
    ::= { waphcCfg 7 }

slbNewCfgWaphcRcvContent OBJECT-TYPE   
    SYNTAX OCTET STRING (SIZE(0..512))
    MAX-ACCESS read-write
    STATUS current   
    DESCRIPTION 
        "The content to be received from the WAP gateway."   
    ::= { waphcCfg 8 }

slbCurCfgWaphcWTLSPort OBJECT-TYPE   
    SYNTAX INTEGER (0..65534)
    MAX-ACCESS read-only   
    STATUS current   
    DESCRIPTION 
        "The WTLS port number to health check."   
    ::= { waphcCfg 9 }

slbNewCfgWaphcWTLSPort OBJECT-TYPE   
    SYNTAX INTEGER (0..65534)
    MAX-ACCESS read-write
    STATUS current   
    DESCRIPTION 
        "The WTLS port number to health check."   
    ::= { waphcCfg 10 }

slbCurCfgWaphcWTPSndContent OBJECT-TYPE   
    SYNTAX OCTET STRING (SIZE(0..512))
    MAX-ACCESS read-only   
    STATUS current   
    DESCRIPTION 
        "The WTP+WSP content to be sent to the WAP gateway."   
    ::= { waphcCfg 11 }

slbNewCfgWaphcWTPSndContent OBJECT-TYPE   
    SYNTAX OCTET STRING (SIZE(0..512))
    MAX-ACCESS read-write
    STATUS current   
    DESCRIPTION 
        "The WTP+WSP content to be sent to the WAP gateway."   
    ::= { waphcCfg 12 }

slbCurCfgWaphcWTPRcvContent OBJECT-TYPE   
    SYNTAX OCTET STRING (SIZE(0..512))
    MAX-ACCESS read-only   
    STATUS current   
    DESCRIPTION 
        "The WTP+WSP content to be received from the WAP gateway."   
    ::= { waphcCfg 13 }

slbNewCfgWaphcWTPRcvContent OBJECT-TYPE   
    SYNTAX OCTET STRING (SIZE(0..512))
    MAX-ACCESS read-write
    STATUS current   
    DESCRIPTION 
        "The WTP+WSP content to be received from the WAP gateway."   
    ::= { waphcCfg 14 }

slbCurCfgWaphcWTPConnContent OBJECT-TYPE   
    SYNTAX OCTET STRING (SIZE(0..512))
    MAX-ACCESS read-only   
    STATUS current   
    DESCRIPTION 
        "The WTP+WSP CONNECT content to be sent to the WAP gateway."   
    ::= { waphcCfg 15 }

slbNewCfgWaphcWTPConnContent OBJECT-TYPE   
    SYNTAX OCTET STRING (SIZE(0..512))
    MAX-ACCESS read-write
    STATUS current   
    DESCRIPTION 
        "The WTP+WSP CONNECT content to be sent to the WAP gateway."   
    ::= { waphcCfg 16 }

slbCurCfgWaphcWTPPort OBJECT-TYPE   
    SYNTAX INTEGER (0..65534)
    MAX-ACCESS read-only   
    STATUS current   
    DESCRIPTION 
        "The WTP port number to health check."   
    ::= { waphcCfg 17 }

slbNewCfgWaphcWTPPort OBJECT-TYPE   
    SYNTAX INTEGER (0..65534)
    MAX-ACCESS read-write
    STATUS current   
    DESCRIPTION 
        "The WTP port number to health check."   
    ::= { waphcCfg 18 }

slbCurCfgWaphcWTLSWSPPort OBJECT-TYPE   
    SYNTAX INTEGER (0..65534)
    MAX-ACCESS read-only   
    STATUS current   
    DESCRIPTION 
        "The WTLS+WSP port number to health check."   
    ::= { waphcCfg 19 }

slbNewCfgWaphcWTLSWSPPort OBJECT-TYPE   
    SYNTAX INTEGER (0..65534)
    MAX-ACCESS read-write
    STATUS current   
    DESCRIPTION 
        "The WTLS+WSP port number to health check."   
    ::= { waphcCfg 20 }

slbCurCfgWaphcWTPOffset OBJECT-TYPE   
    SYNTAX INTEGER (0..256)
    MAX-ACCESS read-only   
    STATUS current   
    DESCRIPTION 
        "The offset in received WTP packet."   
    ::= { waphcCfg 21 }

slbNewCfgWaphcWTPOffset OBJECT-TYPE   
    SYNTAX INTEGER (0..256)
    MAX-ACCESS read-write
    STATUS current   
    DESCRIPTION 
        "The offset in received WTP packet."   
    ::= { waphcCfg 22 }

slbCurCfgWaphcCouple OBJECT-TYPE
    SYNTAX INTEGER {
        enabled(1),
        disabled(2)
        }
    MAX-ACCESS  read-only
    STATUS  current
    DESCRIPTION
        "Enable or disable coupling of WAP and RADIUS Accounting 
	 health checks."
    ::= { waphcCfg 23 }

slbNewCfgWaphcCouple OBJECT-TYPE
    SYNTAX INTEGER {
        enabled(1),
        disabled(2)
        }
    MAX-ACCESS  read-write
    STATUS  current
    DESCRIPTION
        "Enable or disable coupling of WAP and RADIUS Accounting 
	 health checks."
    ::= { waphcCfg 24 }

slbCurCfgWaphcConnPDU OBJECT-TYPE
    SYNTAX OCTET STRING (SIZE(0..512)) 
    MAX-ACCESS  read-only
    STATUS  current
    DESCRIPTION
        "The CONNECT PDU to be sent to the WAP gateway."
    ::= { waphcCfg 25 }

slbNewCfgWaphcConnPDU OBJECT-TYPE
    SYNTAX OCTET STRING (SIZE(0..512))
    MAX-ACCESS  read-write
    STATUS  current
    DESCRIPTION
        "The CONNECT PDU to be sent to the WAP gateway."
    ::= { waphcCfg 26 }

slbCurCfgWaphcSndPDU OBJECT-TYPE
    SYNTAX OCTET STRING (SIZE(0..512))
    MAX-ACCESS read-only
    STATUS current
    DESCRIPTION
        "The GET PDU to be sent to the WAP gateway."
    ::= { waphcCfg 27 }

slbNewCfgWaphcSndPDU OBJECT-TYPE
    SYNTAX OCTET STRING (SIZE(0..512))
    MAX-ACCESS read-write
    STATUS current
    DESCRIPTION
        "The GET PDU to be sent to the WAP gateway."
    ::= { waphcCfg 28 }

slbCurCfgWaphcRcvPDU OBJECT-TYPE
    SYNTAX OCTET STRING (SIZE(0..512))
    MAX-ACCESS read-only
    STATUS current
    DESCRIPTION
        "The REPLY PDU to be received from the WAP gateway."
    ::= { waphcCfg 29 }

slbNewCfgWaphcRcvPDU OBJECT-TYPE
    SYNTAX OCTET STRING (SIZE(0..512))
    MAX-ACCESS read-write
    STATUS current
    DESCRIPTION
        "The REPLY PDU to be received from the WAP gateway."
    ::= { waphcCfg 30 }

-- WAP Load Balancing Configuration 

slbCurCfgWapTpcp OBJECT-TYPE
    SYNTAX INTEGER {
        enabled(1),
        disabled(2)
        }
    MAX-ACCESS  read-only
    STATUS  current
    DESCRIPTION
        "Enable or disable WAP load balancing. "
    ::= { wapCfg 1 }

slbNewCfgWapTpcp OBJECT-TYPE
    SYNTAX INTEGER {
        enabled(1),
        disabled(2)
        }
    MAX-ACCESS  read-write
    STATUS  current
    DESCRIPTION
        "Enable or disable WAP load balancing. "
    ::= { wapCfg 2 }

slbCurCfgWapDebug OBJECT-TYPE
    SYNTAX  INTEGER  (0..10)
    MAX-ACCESS  read-only
    STATUS  current
    DESCRIPTION
        "WAP Debug level."
    ::= { wapCfg 3 }

slbNewCfgWapDebug OBJECT-TYPE
    SYNTAX  INTEGER  (0..10)
    MAX-ACCESS  read-write
    STATUS  current
    DESCRIPTION
        "WAP Debug level."
    ::= { wapCfg 4 }


-- Synch Peer Switch Configuration
slbPeerTableMaxSize OBJECT-TYPE
    SYNTAX  Integer32 
    MAX-ACCESS  read-only 
    STATUS  current 
    DESCRIPTION 
        "The maximum number of entries in SLB Peer Table." 
    ::= { syncCfg 2 }

slbCurCfgPeerTable OBJECT-TYPE
    SYNTAX SEQUENCE OF SlbCurCfgPeerEntry
    MAX-ACCESS not-accessible
    STATUS current
    DESCRIPTION
        "The table of Synch Peer Switch configuration in the current_config."
    ::= { syncCfg 3 }

slbCurCfgPeerEntry OBJECT-TYPE
    SYNTAX SlbCurCfgPeerEntry
    MAX-ACCESS not-accessible
    STATUS current
    DESCRIPTION
        "Information about Synch Peer Switch configuration."
    INDEX { slbCurCfgPeerIndex }
    ::= { slbCurCfgPeerTable 1 }
 
SlbCurCfgPeerEntry ::= SEQUENCE {
    slbCurCfgPeerIndex          Integer32,
    slbCurCfgPeerIpAddr         IpAddress,
    slbCurCfgPeerState          INTEGER,
    slbCurCfgPeerIpv6Addr      DisplayString,
    slbCurCfgPeerIpVersion     INTEGER
    }
 
slbCurCfgPeerIndex OBJECT-TYPE
    SYNTAX Integer32
    MAX-ACCESS read-only
    STATUS current
    DESCRIPTION
        "The index for synch peer switchs."
    ::= { slbCurCfgPeerEntry 1 }

slbCurCfgPeerIpAddr OBJECT-TYPE
    SYNTAX IpAddress
    MAX-ACCESS read-only
    STATUS current
    DESCRIPTION
        "The IP address of the peer switch."
    ::= { slbCurCfgPeerEntry 2 }
 
slbCurCfgPeerState OBJECT-TYPE
    SYNTAX INTEGER {
        enable(1),
        disable(2)
        }
    MAX-ACCESS  read-only
    STATUS  current
    DESCRIPTION
        "Enable or disable the peer switch."
    ::= { slbCurCfgPeerEntry 3 }

slbCurCfgPeerIpv6Addr OBJECT-TYPE
    SYNTAX DisplayString (SIZE(0..40))
    MAX-ACCESS read-only
    STATUS current
    DESCRIPTION
        "The IPv6 address of the Peer switch.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { slbCurCfgPeerEntry 4 }

slbCurCfgPeerIpVersion OBJECT-TYPE
    SYNTAX INTEGER {
        ipv4(4),
        ipv6(6)
    }
    MAX-ACCESS read-only
    STATUS current
    DESCRIPTION
        "Peer Ip Address Version."
    ::= { slbCurCfgPeerEntry 5 }

slbNewCfgPeerTable OBJECT-TYPE
    SYNTAX SEQUENCE OF SlbNewCfgPeerEntry
    MAX-ACCESS not-accessible
    STATUS current
    DESCRIPTION
        "The table of Synch Peer Switch configuration in the new_config."
    ::= { syncCfg 4 }
 
slbNewCfgPeerEntry OBJECT-TYPE
    SYNTAX SlbNewCfgPeerEntry
    MAX-ACCESS not-accessible
    STATUS current
    DESCRIPTION
        "Information about synch peer switch  configuration."
    INDEX { slbNewCfgPeerIndex }
    ::= { slbNewCfgPeerTable 1 }
 
SlbNewCfgPeerEntry ::= SEQUENCE {
    slbNewCfgPeerIndex          Integer32,
    slbNewCfgPeerIpAddr         IpAddress,
    slbNewCfgPeerState          INTEGER,
    slbNewCfgPeerDelete         INTEGER,
    slbNewCfgPeerIpv6Addr       DisplayString,
    slbNewCfgPeerIpVersion      INTEGER
    }
 
slbNewCfgPeerIndex OBJECT-TYPE
    SYNTAX Integer32
    MAX-ACCESS read-only
    STATUS current
    DESCRIPTION
        "The index number for synch peer switchs."
    ::= { slbNewCfgPeerEntry 1 }
 
slbNewCfgPeerIpAddr OBJECT-TYPE
    SYNTAX IpAddress
    MAX-ACCESS read-create
    STATUS current
    DESCRIPTION
        "The IP address of the peer switch."
    ::= { slbNewCfgPeerEntry 2 }
 
slbNewCfgPeerState OBJECT-TYPE
    SYNTAX INTEGER {
        enable(1),
        disable(2)
        }
    MAX-ACCESS  read-create
    STATUS  current
    DESCRIPTION
        "Enable or disable the peer switch."
    ::= { slbNewCfgPeerEntry 3 }
 
slbNewCfgPeerDelete OBJECT-TYPE
    SYNTAX INTEGER {
        other(1),
        delete(2)
        }
    MAX-ACCESS  read-create
    STATUS  current
    DESCRIPTION
        "By setting the value to delete(2), the entire row is
         deleted."
    ::= { slbNewCfgPeerEntry 4 }

slbNewCfgPeerIpv6Addr OBJECT-TYPE
    SYNTAX DisplayString (SIZE(0..40))
    MAX-ACCESS read-create
    STATUS current
    DESCRIPTION
        "The IPv6 address of the Peer switch.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { slbNewCfgPeerEntry 5 }

slbNewCfgPeerIpVersion OBJECT-TYPE
    SYNTAX INTEGER {
        ipv4(4),
        ipv6(6)
    }
    MAX-ACCESS read-only
    STATUS current
    DESCRIPTION
        "Peer Ip Address Version."
    ::= { slbNewCfgPeerEntry 6 }


slbCurCfgPeerPIPTable OBJECT-TYPE
    SYNTAX SEQUENCE OF SlbCurCfgPeerPIPEntry
    MAX-ACCESS not-accessible
    STATUS current
    DESCRIPTION
        "The table of Peer PIP configuration in the current_config."
    ::= { peerpipTblCfg 1 }

slbCurCfgPeerPIPEntry OBJECT-TYPE
    SYNTAX SlbCurCfgPeerPIPEntry
    MAX-ACCESS not-accessible
    STATUS current
    DESCRIPTION
        "Information about Peer PIP configuration."
    INDEX { slbCurCfgPeerPIPIndex }
    ::= { slbCurCfgPeerPIPTable 1 }

SlbCurCfgPeerPIPEntry ::= SEQUENCE {
    slbCurCfgPeerPIPIndex       Integer32,
    slbCurCfgPeerPIPAddr        IpAddress,
    slbCurCfgPeerPIPv6Addr      DisplayString
    }

slbCurCfgPeerPIPIndex OBJECT-TYPE
    SYNTAX Integer32
    MAX-ACCESS read-only
    STATUS current
    DESCRIPTION
        "The index for peer PIP."
    ::= { slbCurCfgPeerPIPEntry 1 }

slbCurCfgPeerPIPAddr OBJECT-TYPE
    SYNTAX IpAddress
    MAX-ACCESS read-only
    STATUS current
    DESCRIPTION
        "The IP address of the peer PIP."
    ::= { slbCurCfgPeerPIPEntry 2 }

slbCurCfgPeerPIPv6Addr OBJECT-TYPE
    SYNTAX DisplayString (SIZE(0..40))
    MAX-ACCESS read-only
    STATUS current
    DESCRIPTION
        "The IPv6 address of the Peer PIP.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { slbCurCfgPeerPIPEntry 3 }


slbNewCfgPeerPIPTable OBJECT-TYPE
    SYNTAX SEQUENCE OF SlbNewCfgPeerPIPEntry
    MAX-ACCESS not-accessible
    STATUS current
    DESCRIPTION
        "The table of Peer PIP configuration in the new_config."
    ::= { peerpipTblCfg 2 }

slbNewCfgPeerPIPEntry OBJECT-TYPE
    SYNTAX SlbNewCfgPeerPIPEntry
    MAX-ACCESS not-accessible
    STATUS current
    DESCRIPTION
        "Information about Peer PIP configuration."
    INDEX { slbNewCfgPeerPIPIndex }
    ::= { slbNewCfgPeerPIPTable 1 }

SlbNewCfgPeerPIPEntry ::= SEQUENCE {
    slbNewCfgPeerPIPIndex       Integer32,
    slbNewCfgPeerPIPAddr        IpAddress,
    slbNewCfgPeerPIPv6Addr      DisplayString,
    slbNewCfgPeerPIPDelete      INTEGER
    }

slbNewCfgPeerPIPIndex OBJECT-TYPE
    SYNTAX Integer32
    MAX-ACCESS read-only
    STATUS current
    DESCRIPTION
        "The index for peer PIP."
    ::= { slbNewCfgPeerPIPEntry 1 }

slbNewCfgPeerPIPAddr OBJECT-TYPE
    SYNTAX IpAddress
    MAX-ACCESS read-create 
    STATUS current
    DESCRIPTION
        "The IP address of the peer PIP."
    ::= { slbNewCfgPeerPIPEntry 2 }

slbNewCfgPeerPIPv6Addr OBJECT-TYPE
    SYNTAX DisplayString (SIZE(0..40))
    MAX-ACCESS read-create 
    STATUS current
    DESCRIPTION
        "The IPv6 address of the Peer PIP.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { slbNewCfgPeerPIPEntry 3 }

slbNewCfgPeerPIPDelete OBJECT-TYPE
    SYNTAX INTEGER {
        other(1),
        delete(2)
        }
    MAX-ACCESS  read-create
    STATUS  current
    DESCRIPTION
        "By setting the value to delete(2), the entire row is
         deleted."
    ::= { slbNewCfgPeerPIPEntry 4 }

slbCurCfgSyncFilt OBJECT-TYPE
    SYNTAX  INTEGER {
        enabled(1),
        disabled(2)
        }
    MAX-ACCESS  read-only
    STATUS  current
    DESCRIPTION
        "Enable or disable synch filter configuration."
    ::= { syncGeneralCfg 1 }

slbNewCfgSyncFilt OBJECT-TYPE
    SYNTAX  INTEGER {
        enabled(1),
        disabled(2)
        }
    MAX-ACCESS  read-write
    STATUS  current
    DESCRIPTION
        "Enable or disable synch filter configuration."
    ::= { syncGeneralCfg 2 }

slbCurCfgSyncPort OBJECT-TYPE
    SYNTAX  INTEGER {
        enabled(1),
        disabled(2)
        }
    MAX-ACCESS  read-only
    STATUS  current
    DESCRIPTION
        "Enable or disable synch port configuration."
    ::= { syncGeneralCfg 3 }

slbNewCfgSyncPort OBJECT-TYPE
    SYNTAX  INTEGER {
        enabled(1),
        disabled(2)
        }
    MAX-ACCESS  read-write
    STATUS  current
    DESCRIPTION
        "Enable or disable synch port configuration."
    ::= { syncGeneralCfg 4 }

slbCurCfgSyncVrrp OBJECT-TYPE
    SYNTAX  INTEGER {
        enabled(1),
        disabled(2)
        }
    MAX-ACCESS  read-only
    STATUS  current
    DESCRIPTION
        "Enable or disable synch VRRP Priorities."
    ::= { syncGeneralCfg 5 }

slbNewCfgSyncVrrp OBJECT-TYPE
    SYNTAX  INTEGER {
        enabled(1),
        disabled(2)
        }
    MAX-ACCESS  read-write
    STATUS  current
    DESCRIPTION
        "Enable or disable synch VRRP Priorities."
    ::= { syncGeneralCfg 6 }

slbCurCfgSyncPip OBJECT-TYPE
    SYNTAX  INTEGER {
        enabled(1),
        disabled(2)
        }
    MAX-ACCESS  read-only
    STATUS  current
    DESCRIPTION
        "Enable or disable synch proxy IP addresses."
    ::= { syncGeneralCfg 7 }

slbNewCfgSyncPip OBJECT-TYPE
    SYNTAX  INTEGER {
        enabled(1),
        disabled(2)
        }
    MAX-ACCESS  read-write
    STATUS  current
    DESCRIPTION
        "Enable or disable synch proxy IP addresses."
    ::= { syncGeneralCfg 8 }

slbCurCfgSyncSfo OBJECT-TYPE
    SYNTAX  INTEGER {
        enabled(1),
        disabled(2)
        }
    MAX-ACCESS  read-only
    STATUS  current
    DESCRIPTION
        "Enable or disable synch stateful failover."
    ::= { syncGeneralCfg 9 }

slbNewCfgSyncSfo OBJECT-TYPE
    SYNTAX  INTEGER {
        enabled(1),
        disabled(2)
        }
    MAX-ACCESS  read-write
    STATUS  current
    DESCRIPTION
        "Enable or disable synch stateful failover."
    ::= { syncGeneralCfg 10 }

slbCurCfgSyncSfoUpdatePeriod OBJECT-TYPE
    SYNTAX  INTEGER (1..60)
    MAX-ACCESS  read-only
    STATUS  current
    DESCRIPTION
        "The stateful failover update period in seconds."
    ::= { syncGeneralCfg 11 }

slbNewCfgSyncSfoUpdatePeriod OBJECT-TYPE
    SYNTAX  INTEGER (1..60)
    MAX-ACCESS  read-write
    STATUS  current
    DESCRIPTION
        "The stateful failover update period in seconds."
    ::= { syncGeneralCfg 12 }

slbCurCfgSyncBwm OBJECT-TYPE
    SYNTAX  INTEGER {
        enabled(1),
        disabled(2)
        }
    MAX-ACCESS  read-only
    STATUS  current
    DESCRIPTION
        "Enable or disable syncing BWM configuration."
    ::= { syncGeneralCfg 13 }

slbNewCfgSyncBwm OBJECT-TYPE
    SYNTAX  INTEGER {
        enabled(1),
        disabled(2)
        }
    MAX-ACCESS  read-write
    STATUS  current
    DESCRIPTION
        "Enable or disable syncing BWM configuration."
    ::= { syncGeneralCfg 14 }
    
slbCurCfgSyncPeerPip OBJECT-TYPE
    SYNTAX  INTEGER {
        enabled(1),
        disabled(2)
        }
    MAX-ACCESS  read-only
    STATUS  current
    DESCRIPTION
        "Enable or disable synch peer proxy IP addresses."
    ::= { syncGeneralCfg 15 }

slbNewCfgSyncPeerPip OBJECT-TYPE
    SYNTAX  INTEGER {
        enabled(1),
        disabled(2)
        }
    MAX-ACCESS  read-write
    STATUS  current
    DESCRIPTION
        "Enable or disable synch peer proxy IP addresses."
    ::= { syncGeneralCfg 16}

slbCurCfgSyncCerts OBJECT-TYPE
    SYNTAX  INTEGER {
        enabled(1),
        disabled(2)
    }
    MAX-ACCESS  read-only
    STATUS  current
    DESCRIPTION
        "Enable or disable syncing certificate repository components."
    ::= { syncGeneralCfg 17 }

slbNewCfgSyncCerts OBJECT-TYPE
    SYNTAX  INTEGER {
        enabled(1),
        disabled(2)
    }
    MAX-ACCESS  read-write
    STATUS  current
    DESCRIPTION
        "Enable or disable syncing certificate repository components.
         If Enable option is selected then Passphrase to encrypt/decrypt 
         certificates and private keys during configuration sync must be 
         set in all peer switches."
    ::= { syncGeneralCfg 18 }

slbCurCfgSyncCertsPassPhrase OBJECT-TYPE
    SYNTAX  DisplayString (SIZE(0..32))
    MAX-ACCESS  read-only
    STATUS  current
    DESCRIPTION
        "Set passphrase to encrypt/decrypt synced certificates' and
         dnssec private keys."
    ::= { syncGeneralCfg 19 }

slbNewCfgSyncCertsPassPhrase OBJECT-TYPE
    SYNTAX  DisplayString (SIZE(0..32))
    MAX-ACCESS  read-write
    STATUS  current
    DESCRIPTION
        "Set passphrase to encrypt/decrypt synced certificates' and
         dnssec private keys.Same PassPhrase should be set at all
         peer switches."
    ::= { syncGeneralCfg 20 }

slbNewCfgSyncCertsConfPassPhrase OBJECT-TYPE
    SYNTAX  DisplayString (SIZE(0..32))
    MAX-ACCESS  read-write
    STATUS  current
    DESCRIPTION
        "This character string is used to confirm Passphrase 
         which is already entered in slbNewCfgSyncCertsPassPhrase."
    ::= { syncGeneralCfg 21 }

slbCurCfgSyncRoute OBJECT-TYPE
    SYNTAX  INTEGER {
        enabled(1),
        disabled(2)
    }
    MAX-ACCESS  read-only
    STATUS  current
    DESCRIPTION
        "Enable or disable synch static route configuration."
    ::= { syncGeneralCfg 22 }

slbNewCfgSyncRoute OBJECT-TYPE
    SYNTAX  INTEGER {
        enabled(1),
        disabled(2)
    }
    MAX-ACCESS  read-write
    STATUS  current
    DESCRIPTION
        "Enable or disable synch static route configuration."
    ::= { syncGeneralCfg 23 }

-- SYN Attack Detection 

synAttackCurCfgInterval OBJECT-TYPE
    SYNTAX  INTEGER (2..3600)
    MAX-ACCESS  read-only
    STATUS  current
    DESCRIPTION
        "The interval specified in seconds determines how frequently the 
         switch checks for SYN attacks."
    ::= { synAttackDetCfg 1 }

synAttackNewCfgInterval OBJECT-TYPE
    SYNTAX  INTEGER (2..3600)
    MAX-ACCESS  read-write
    STATUS  current
    DESCRIPTION
        "The interval specified in seconds determines how frequently the 
         switch checks for SYN attacks."
    ::= { synAttackDetCfg 2 }

synAttackCurCfgThreshhold OBJECT-TYPE
    SYNTAX  INTEGER (1..100000)
    MAX-ACCESS  read-only
    STATUS  current
    DESCRIPTION
        "The threshhold indicating the number of new half-open sessions
         per second."
    ::= { synAttackDetCfg 3 }

synAttackNewCfgThreshhold OBJECT-TYPE
    SYNTAX  INTEGER (1..100000)
    MAX-ACCESS  read-write
    STATUS  current
    DESCRIPTION
        "The threshhold indicating the number of new half-open sessions
         per second."
    ::= { synAttackDetCfg 4 }

synAttackCurCfgResponseInterval OBJECT-TYPE
    SYNTAX  INTEGER (10..1000)
    MAX-ACCESS  read-only
    STATUS  current
    DESCRIPTION
        "The interval specified in milliseconds determines how frequently the 
         switch generate new SYN cookie value."
    ::= { synAttackDetCfg 5 }

synAttackNewCfgResponseInterval OBJECT-TYPE
    SYNTAX  INTEGER (10..1000)
    MAX-ACCESS  read-write
    STATUS  current
    DESCRIPTION
        "The interval specified in milliseconds determines how frequently the 
         switch generate new SYN cookie value."
    ::= { synAttackDetCfg 6 }

synAttackCurCfgOnOff  OBJECT-TYPE
   SYNTAX  INTEGER { on(1), off(2) }
   MAX-ACCESS  read-only
   STATUS  current
   DESCRIPTION
       "Globally ON or OFF of SYN Protection."
   ::= { synAttackDetCfg 7 }

synAttackNewCfgOnOff  OBJECT-TYPE
   SYNTAX  INTEGER { on(1), off(2) }
   MAX-ACCESS  read-write
   STATUS  current
   DESCRIPTION
       "Globally ON or OFF of SYN Protection."
   ::= { synAttackDetCfg 8 }



-- Filtering Group
 
fltCfgTableMaxSize OBJECT-TYPE
    SYNTAX  Integer32
    MAX-ACCESS  read-only
    STATUS  current
    DESCRIPTION
        "The maximum number of filtering table entries."
    ::= { filterCfg 1 }

-- Current Config Filtering Table

fltCurCfgTable OBJECT-TYPE
    SYNTAX  SEQUENCE OF FltCurCfgTableEntry
    MAX-ACCESS  not-accessible
    STATUS  current
    DESCRIPTION
        "The filtering table in the current configuration block."
    ::= { filterCfg 2 }

fltCurCfgTableEntry OBJECT-TYPE
    SYNTAX  FltCurCfgTableEntry
    MAX-ACCESS  not-accessible
    STATUS  current
    DESCRIPTION
        "A row in the filtering table."
    INDEX   { fltCurCfgIndx }
    ::= { fltCurCfgTable 1 }

FltCurCfgTableEntry ::= SEQUENCE {
    fltCurCfgIndx             Integer32,
    fltCurCfgSrcIpMac         INTEGER,
    fltCurCfgSrcIp            IpAddress,
    fltCurCfgSrcIpMask        IpAddress,
    fltCurCfgDstIpMac         INTEGER,
    fltCurCfgDstIp            IpAddress,
    fltCurCfgDstIpMask        IpAddress,
    fltCurCfgProtocol         INTEGER,
    fltCurCfgRangeLowSrcPort  INTEGER,
    fltCurCfgRangeHighSrcPort INTEGER,
    fltCurCfgRangeLowDstPort  INTEGER,
    fltCurCfgRangeHighDstPort INTEGER,
    fltCurCfgAction           INTEGER,
    fltCurCfgRedirPort        INTEGER,
    fltCurCfgRedirGroup       Integer32,
    fltCurCfgLog              INTEGER,
    fltCurCfgState            INTEGER,
    fltCurCfgNat              INTEGER,
    fltCurCfgCache            INTEGER,
    fltCurCfgInvert           INTEGER,
    fltCurCfgClientProxy      INTEGER,
    fltCurCfgTcpAck           INTEGER,
    fltCurCfgSrcMac           PhysAddress,
    fltCurCfgDstMac           PhysAddress,
    fltCurCfgFtpNatActive     INTEGER,
    fltCurCfgAclTcpUrg        INTEGER, 
    fltCurCfgAclTcpAck        INTEGER, 
    fltCurCfgAclTcpPsh        INTEGER, 
    fltCurCfgAclTcpRst        INTEGER, 
    fltCurCfgAclTcpSyn        INTEGER, 
    fltCurCfgAclTcpFin        INTEGER,
    fltCurCfgAclIcmp	      INTEGER,
    fltCurCfgAclIpOption      INTEGER,
    fltCurCfgBwmContract      Integer32,
    fltCurCfgAclIpTos         INTEGER,
    fltCurCfgAclIpTosMask     INTEGER,
    fltCurCfgAclIpTosNew      INTEGER,
    fltCurCfgFwlb	      INTEGER,
    fltCurCfgNatTimeout       INTEGER,
    fltCurCfgLinklb           INTEGER,
    fltCurCfgWapRadiusSnoop   INTEGER,
    fltCurCfgIdslbHash        INTEGER,
    fltCurCfgVlan             INTEGER,
    fltCurCfgTcpRateLimit     INTEGER,
    fltCurCfgTcpRateMaxConn   INTEGER,
    fltCurCfgHash             INTEGER,
    fltCurCfgLayer7DenyState  INTEGER,
    fltCurCfgLayer7DenyUrlBmap OCTET STRING,
    fltCurCfgGotoFilter       Integer32,
    fltCurCfgRadiusWapPersist INTEGER,
    fltCurCfgPbind            INTEGER,
    fltCurCfgTimeWindow       INTEGER,
    fltCurCfgHoldDuration     INTEGER,
    fltCurCfgProxyIp          IpAddress,
    fltCurCfgPatternMatch     INTEGER,
    fltCurCfgLayer7DenyMatchAll INTEGER,
    fltCurCfgLayer7ParseAll   INTEGER,
    fltCurCfgSecurityParseAll INTEGER,
    fltCurCfgPatternMatchGroupBmap OCTET STRING,
    fltCurCfg8021pBitsValue   INTEGER,
    fltCurCfg8021pBitsMatch   INTEGER,
    fltCurCfgAclIpLength      INTEGER,
    fltCurCfgIdsGroup         Integer32,
    fltCurCfgEgressPip        INTEGER,
    fltCurCfgDbind            INTEGER,
    fltCurCfgReverse          INTEGER,
    fltCurCfgRevBwmContract   Integer32, 
    fltCurCfgParseChn         INTEGER,
    fltCurCfgRtpBwmContract   Integer32,
    fltCurCfgSipParsing       INTEGER,
    fltCurCfgSessionMirror    INTEGER,
    fltCurCfgIpVer            INTEGER,
    fltCurCfgIpv6Sip          DisplayString,
    fltCurCfgIpv6Sprefix      INTEGER,
    fltCurCfgIpv6Dip          DisplayString,
    fltCurCfgIpv6Dprefix      INTEGER,
    fltCurCfgHdrHash          INTEGER,
    fltCurCfgHdrName          DisplayString,
    fltCurCfgHdrHashLen       INTEGER,
    fltCurCfgName             DisplayString,
    fltCurCfgNatIp            IpAddress,
    fltCurCfgIpv6Nip          DisplayString,
    fltCurCfgIpv6Proxy        DisplayString,    
    fltCurCfgL7SipFilt        INTEGER,
    fltCurCfgL3Filter          INTEGER,
    fltCurCfgNatMcastVlan     INTEGER,
    fltCurCfgNbind            INTEGER
    }

fltCurCfgIndx OBJECT-TYPE
    SYNTAX  Integer32
    MAX-ACCESS  read-only
    STATUS  current
    DESCRIPTION
        "The filtering table index."
    ::= { fltCurCfgTableEntry 1 }

fltCurCfgSrcIp OBJECT-TYPE
    SYNTAX  IpAddress
    MAX-ACCESS  read-only
    STATUS  current
    DESCRIPTION
        "The source IP address to be filtered."
    ::= { fltCurCfgTableEntry 2 }

fltCurCfgSrcIpMask OBJECT-TYPE
    SYNTAX  IpAddress
    MAX-ACCESS  read-only
    STATUS  current
    DESCRIPTION
        "The source IP sub-net mask for filtering."
    ::= { fltCurCfgTableEntry 3 }

fltCurCfgDstIp OBJECT-TYPE
    SYNTAX  IpAddress
    MAX-ACCESS  read-only
    STATUS  current
    DESCRIPTION
        "The destination IP address to be filtered."
    ::= { fltCurCfgTableEntry 4 }

fltCurCfgDstIpMask OBJECT-TYPE
    SYNTAX  IpAddress
    MAX-ACCESS  read-only
    STATUS  current
    DESCRIPTION
        "The destination IP sub-net mask for filtering."
    ::= { fltCurCfgTableEntry 5 }

fltCurCfgProtocol OBJECT-TYPE
    SYNTAX  INTEGER (0..255)
    MAX-ACCESS  read-only
    STATUS  current
    DESCRIPTION
        "The protocol to be filtered."
    ::= { fltCurCfgTableEntry 6 }

fltCurCfgRangeHighSrcPort OBJECT-TYPE
    SYNTAX  INTEGER (0..65534)
    MAX-ACCESS  read-only
    STATUS  current
    DESCRIPTION
        "The higher source TCP/UDP port number to be filtered. It applies 
         only when protocol defined in fltCurCfgProtocol is UDP or TCP.
         '0' means no filtering."
    ::= { fltCurCfgTableEntry 7 }

fltCurCfgRangeLowSrcPort OBJECT-TYPE
    SYNTAX  INTEGER (0..65534)
    MAX-ACCESS  read-only
    STATUS  current
    DESCRIPTION
        "The lower source TCP/UDP port number to be filtered. It applies 
         only when protocol defined in fltCurCfgProtocol is UDP or TCP.  
         '0' means no filtering."
    ::= { fltCurCfgTableEntry 8 }

fltCurCfgRangeLowDstPort OBJECT-TYPE
    SYNTAX  INTEGER (0..65534)
    MAX-ACCESS  read-only
    STATUS  current
    DESCRIPTION
        "The lower destination TCP/UDP port number to be filtered. It applies 
         only when protocol defined in fltCurCfgProtocol is UDP or TCP.
         '0' means no filtering."
    ::= { fltCurCfgTableEntry 9 }

fltCurCfgRangeHighDstPort OBJECT-TYPE
    SYNTAX  INTEGER (0..65534)
    MAX-ACCESS  read-only
    STATUS  current
    DESCRIPTION
        "The higher destination TCP/UDP port number to be filtered. It applies
         only when protocol defined in fltCurCfgProtocol is UDP or TCP.
         '0' means no filtering."
    ::= { fltCurCfgTableEntry 10 }

fltCurCfgAction OBJECT-TYPE
    SYNTAX  INTEGER {
        allow(1),
        deny(2),
        redirect(3),
        nat(4),      -- network address translation
        goto(5)
        }
    MAX-ACCESS  read-only
    STATUS  current
    DESCRIPTION
        "The action for the filtering rule."
    ::= { fltCurCfgTableEntry 11 }

fltCurCfgRedirPort OBJECT-TYPE
    SYNTAX  INTEGER (0..65534)
    MAX-ACCESS  read-only
    STATUS  current
    DESCRIPTION
        "The real server port number used for redirection."
    ::= { fltCurCfgTableEntry 12 }

fltCurCfgRedirGroup OBJECT-TYPE
    SYNTAX  Integer32
    MAX-ACCESS  read-only
    STATUS  current
    DESCRIPTION
        "The real server group to be redirected to."
    ::= { fltCurCfgTableEntry 13 }

fltCurCfgLog OBJECT-TYPE
    SYNTAX  INTEGER {
        enabled(1),
        disabled(2)
        }
    MAX-ACCESS  read-only
    STATUS  current
    DESCRIPTION
        "Enable or disable logging."
    ::= { fltCurCfgTableEntry 14 }

fltCurCfgState OBJECT-TYPE
    SYNTAX  INTEGER {
        enabled(1),
        disabled(2)
        }
    MAX-ACCESS  read-only
    STATUS  current
    DESCRIPTION
        "The state of this filtering rule."
    ::= { fltCurCfgTableEntry 15 }

fltCurCfgNat OBJECT-TYPE
    SYNTAX  INTEGER {
        destination-address(1),
        source-address(2),
	multicast-address(3)
        }
    MAX-ACCESS  read-only
    STATUS  current
    DESCRIPTION
        "The selection of destination or source or multicast for
         network address translation."
    ::= { fltCurCfgTableEntry 16 }

fltCurCfgCache OBJECT-TYPE
    SYNTAX  INTEGER {
        enabled(1),
        disabled(2)
        }
    MAX-ACCESS  read-only
    STATUS  current
    DESCRIPTION
        "Enable or disable caching sessions that match filter."
    ::= { fltCurCfgTableEntry 17 }

fltCurCfgInvert OBJECT-TYPE
    SYNTAX  INTEGER {
        enabled(1),
        disabled(2)
        }
    MAX-ACCESS  read-only
    STATUS  current
    DESCRIPTION
        "Turn the invert logic on or off for the filter entry."
    ::= { fltCurCfgTableEntry 18 }

fltCurCfgClientProxy OBJECT-TYPE
    SYNTAX  INTEGER {
        enabled(1),
        disabled(2)
        }
    MAX-ACCESS  read-only
    STATUS  current
    DESCRIPTION
        "Enable or disable client proxy."
    ::= { fltCurCfgTableEntry 19 }

fltCurCfgTcpAck OBJECT-TYPE
    SYNTAX  INTEGER {
        enabled(1),
        disabled(2)
        }
    MAX-ACCESS  read-only
    STATUS  current
    DESCRIPTION
        "Enable or disable filtering on matching TCP ACK and RST flag."
    ::= { fltCurCfgTableEntry 20 }


fltCurCfgSrcMac OBJECT-TYPE
    SYNTAX  PhysAddress 
    MAX-ACCESS  read-only
    STATUS  current
    DESCRIPTION
        "The source MAC address to be filtered."
    ::= { fltCurCfgTableEntry 22 }

fltCurCfgDstMac OBJECT-TYPE
    SYNTAX  PhysAddress 
    MAX-ACCESS  read-only
    STATUS  current
    DESCRIPTION
        "The Destination MAC address to be filtered."
    ::= { fltCurCfgTableEntry 23 }

fltCurCfgFtpNatActive OBJECT-TYPE
    SYNTAX  INTEGER{
	enabled(1),
	disabled(2)
	}
    MAX-ACCESS  read-only
    STATUS  current	
    DESCRIPTION
        "Enable or disable FTP NAT for active ftp only."
    ::= { fltCurCfgTableEntry 24 }

-- Current Config for TCP ACL filtering Table 

fltCurCfgAclTcpUrg OBJECT-TYPE
    SYNTAX  INTEGER {
	enable(1),
	disable(2)
	}
    MAX-ACCESS  read-only
    STATUS  current
    DESCRIPTION
        "Enable or disable TCP URG packet."
    ::= { fltCurCfgTableEntry 25 }	

fltCurCfgAclTcpAck OBJECT-TYPE
    SYNTAX  INTEGER {
	enable(1),
	disable(2)
	}
    MAX-ACCESS  read-only
    STATUS  current
    DESCRIPTION
        "Enable or disable TCP ACK packet."
    ::= { fltCurCfgTableEntry 26 }	

fltCurCfgAclTcpPsh OBJECT-TYPE
    SYNTAX  INTEGER {
	enable(1),
	disable(2)
	}
    MAX-ACCESS  read-only
    STATUS  current
    DESCRIPTION
        "Enable or disable TCP PSH packet."
    ::= { fltCurCfgTableEntry 27 }	

fltCurCfgAclTcpRst OBJECT-TYPE
    SYNTAX  INTEGER {
	enable(1),
	disable(2)
	}
    MAX-ACCESS  read-only
    STATUS  current 
    DESCRIPTION
        "Enable or disable TCP RST packet."
    ::= { fltCurCfgTableEntry 28 }	

fltCurCfgAclTcpSyn OBJECT-TYPE
    SYNTAX  INTEGER {
	enable(1),
	disable(2)
	}
    MAX-ACCESS  read-only
    STATUS  current
    DESCRIPTION
        "Enable or disable TCP SYN packet."
    ::= { fltCurCfgTableEntry 29 }	

fltCurCfgAclTcpFin OBJECT-TYPE
    SYNTAX  INTEGER {
	enable(1),
	disable(2)
	}
    MAX-ACCESS  read-only
    STATUS  current
    DESCRIPTION
	"Enable or disable TCP FIN packet."
    ::= { fltCurCfgTableEntry 30 }	

-- Current Config for ICMP Type ACL filtering Table 

fltCurCfgAclIcmp OBJECT-TYPE
    SYNTAX  INTEGER (0..255)
    MAX-ACCESS  read-only
    STATUS  current
    DESCRIPTION
        "ICMP type to be filtered. A ICMP type of 255 indicates 'any'"
    ::= { fltCurCfgTableEntry 31 }	

-- Current Config IP Option ACL Filtering Table

fltCurCfgAclIpOption OBJECT-TYPE
    SYNTAX  INTEGER {
        enable(1),
	disable(2)
        }
    MAX-ACCESS  read-only
    STATUS  current
    DESCRIPTION
        "Enable or disable IP option matching."
    ::= { fltCurCfgTableEntry 32 }

fltCurCfgBwmContract OBJECT-TYPE
    SYNTAX  Integer32
    MAX-ACCESS  read-only
    STATUS  current
    DESCRIPTION
	"Filt default BW contract number."
    ::= { fltCurCfgTableEntry 33 }	

fltCurCfgAclIpTos OBJECT-TYPE
    SYNTAX  INTEGER (0..255)
    MAX-ACCESS  read-only
    STATUS  current
    DESCRIPTION
        "The IP TOS value to be filtered."
    ::= { fltCurCfgTableEntry 34 }	

fltCurCfgAclIpTosMask OBJECT-TYPE
    SYNTAX  INTEGER (0..255)
    MAX-ACCESS  read-only
    STATUS  current
    DESCRIPTION
        "The IP TOS mask for filtering."
    ::= { fltCurCfgTableEntry 35 }	

fltCurCfgAclIpTosNew OBJECT-TYPE
    SYNTAX  INTEGER (0..255)
    MAX-ACCESS  read-only
    STATUS  current
    DESCRIPTION
        "The new IP TOS value to over-write when filtering fired."
    ::= { fltCurCfgTableEntry 36 }	

fltCurCfgFwlb OBJECT-TYPE
    SYNTAX  INTEGER {
        enabled(1),
        disabled(2)
        }
    MAX-ACCESS  read-only
    STATUS  current
    DESCRIPTION
        "Enable or disable filtering on firewall redirect hash method."
    ::= { fltCurCfgTableEntry 37 }

fltCurCfgNatTimeout OBJECT-TYPE
    SYNTAX  INTEGER (4..32768)
    MAX-ACCESS  read-only
    STATUS  current
    DESCRIPTION
        "The NAT session timeout. The timeout value should be an even number 
         between 4 and 32768."
    ::= { fltCurCfgTableEntry 38 }	

fltCurCfgLinklb OBJECT-TYPE
    SYNTAX  INTEGER {
        enabled(1),
        disabled(2)
        }
    MAX-ACCESS  read-only
    STATUS  current
    DESCRIPTION
        "Enable or disable WAN link load balancing."
    ::= { fltCurCfgTableEntry 39 }

fltCurCfgWapRadiusSnoop OBJECT-TYPE
    SYNTAX  INTEGER {
        enabled(1),
        disabled(2)
        }
    MAX-ACCESS  read-only
    STATUS  current
    DESCRIPTION
        "Enable or disable WAP RADIUS snooping."
    ::= { fltCurCfgTableEntry 40 }

fltCurCfgSrcIpMac OBJECT-TYPE
    SYNTAX  INTEGER {
        ip(1),
        mac(2)
        }
    MAX-ACCESS  read-only
    STATUS  current
    DESCRIPTION
        "Set a flag indicating whether filtering should be based on the 
         source IP address or the source MAC address field."
    ::= { fltCurCfgTableEntry 41 }

fltCurCfgDstIpMac OBJECT-TYPE
    SYNTAX  INTEGER {
        ip(1),
        mac(2)
        }
    MAX-ACCESS  read-only
    STATUS  current
    DESCRIPTION
        "Set a flag indicating whether filtering should be based on the 
         destination IP address or the destination MAC address field."
    ::= { fltCurCfgTableEntry 42 }

fltCurCfgIdslbHash OBJECT-TYPE
    SYNTAX  INTEGER {
        sip(1),
        dip(2),
        both(3)
        }
    MAX-ACCESS  read-only
    STATUS  current
    DESCRIPTION
        "Set hash parameter for intrusion detection server load balancing."
    ::= { fltCurCfgTableEntry 43 }

fltCurCfgVlan OBJECT-TYPE
    SYNTAX  INTEGER (0..4090)
    MAX-ACCESS  read-only
    STATUS  current
    DESCRIPTION
        "Set the VLAN assoicated with the filter."
    ::= { fltCurCfgTableEntry 44 }

fltCurCfgName OBJECT-TYPE
    SYNTAX DisplayString (SIZE(0..31))
    MAX-ACCESS read-only
    STATUS current
    DESCRIPTION
        "The name of the filter."
    ::= { fltCurCfgTableEntry 45 }

fltCurCfgTcpRateLimit OBJECT-TYPE
    SYNTAX  INTEGER {
        enabled(1),
        disabled(2)
        }
    MAX-ACCESS  read-only
    STATUS  current
    DESCRIPTION
        "Enable or disable protocol rate limiting."
    ::= { fltCurCfgTableEntry 46 }

fltCurCfgTcpRateMaxConn OBJECT-TYPE
    SYNTAX  INTEGER (0..255)
    MAX-ACCESS  read-only
    STATUS  current
    DESCRIPTION
        "Set maximum connections (number of connections in units of 10)
         for TCP connection rate limiting.  In the case of ICMP and UDP,
	 this is the maximum packets (number of packets in units of 10)."
    ::= { fltCurCfgTableEntry 47 }

fltCurCfgHash OBJECT-TYPE
    SYNTAX  INTEGER {
	auto(1),
        sip(2),
        dip(3),
        both(4),
	sipsport(5)
        }
    MAX-ACCESS  read-only
    STATUS  current
    DESCRIPTION
        "Set hash parameter for the filter."
    ::= { fltCurCfgTableEntry 48 }


fltCurCfgLayer7DenyState OBJECT-TYPE
    SYNTAX  INTEGER {
        enabled(1),
        disabled(2)
        }
    MAX-ACCESS  read-only
    STATUS  current
    DESCRIPTION
        "Enable or disable layer 7 deny filtering."
    ::= { fltCurCfgTableEntry 50 }

fltCurCfgLayer7DenyUrlBmap OBJECT-TYPE
    SYNTAX  OCTET STRING
    MAX-ACCESS  read-only
    STATUS  current
    DESCRIPTION
        "The URL strings selected for Layer 7 deny filters.
        The selected URL strings are presented in a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL string is selected
                   0 - The represented URL string is not selected"
    ::= { fltCurCfgTableEntry 51 }

fltCurCfgGotoFilter OBJECT-TYPE
    SYNTAX  Integer32
    MAX-ACCESS  read-only
    STATUS  current	
    DESCRIPTION
        "The filter ID for GOTO action in the current config."
    ::= { fltCurCfgTableEntry 52 }

fltCurCfgRadiusWapPersist OBJECT-TYPE
    SYNTAX  INTEGER {
        enabled(1),
        disabled(2)
        }
    MAX-ACCESS  read-only
    STATUS  current	
    DESCRIPTION
        "Enable or disable Radius/WAP persistence."
    ::= { fltCurCfgTableEntry 53 }

fltCurCfgPbind OBJECT-TYPE
    SYNTAX  INTEGER {
        enabled(1),
        disabled(2)
        }
    MAX-ACCESS  read-only
    STATUS  current	
    DESCRIPTION
        "Enable or disable filter persistent binding."
    ::= { fltCurCfgTableEntry 54 }
   
fltCurCfgTimeWindow OBJECT-TYPE
    SYNTAX  INTEGER (1..65535)
    MAX-ACCESS  read-only
    STATUS  current
    DESCRIPTION
        "The time window for protocol rate limiting (in seconds)."
    ::= { fltCurCfgTableEntry 55 }

fltCurCfgHoldDuration OBJECT-TYPE
    SYNTAX  INTEGER (2..65535)
    MAX-ACCESS  read-only
    STATUS  current
    DESCRIPTION
        "The hold down duration for protocol rate limiting (in minutes)."
    ::= { fltCurCfgTableEntry 56 }

fltCurCfgPatternMatch OBJECT-TYPE
    SYNTAX  INTEGER {
        enabled(1),
        disabled(2)
        }
    MAX-ACCESS  read-only
    STATUS  current	
    DESCRIPTION
        "Enable or disable binary pattern matching."
    ::= { fltCurCfgTableEntry 57 }

fltCurCfgLayer7DenyMatchAll OBJECT-TYPE
    SYNTAX  INTEGER {
        enabled(1),
        disabled(2)
        }
    MAX-ACCESS  read-only
    STATUS  current
    DESCRIPTION
        "Enable or disable match-all criteria for L7 deny string matching."
    ::= { fltCurCfgTableEntry 58 }
    
fltCurCfgProxyIp OBJECT-TYPE
    SYNTAX  IpAddress
    MAX-ACCESS  read-only
    STATUS  current
    DESCRIPTION
        "The client proxy IP address for NAT and REDIR filter."
        
    ::= { fltCurCfgTableEntry 59 }
    
fltCurCfgLayer7ParseAll OBJECT-TYPE
    SYNTAX  INTEGER {
        enabled(1),
        disabled(2)
        }
    MAX-ACCESS  read-only
    STATUS  current
    DESCRIPTION
        "Enable or disable layer 7 lookup (parsing) of all packets."
    ::= { fltCurCfgTableEntry 60 }

fltCurCfgSecurityParseAll OBJECT-TYPE
    SYNTAX  INTEGER {
        enabled(1),
        disabled(2)
        }
    MAX-ACCESS  read-only
    STATUS  current
    DESCRIPTION
        "Enable or disable pattern string lookup (parsing) of all packets."
    ::= { fltCurCfgTableEntry 61 }
    
fltCurCfgPatternMatchGroupBmap OBJECT-TYPE
    SYNTAX  OCTET STRING
    MAX-ACCESS  read-only
    STATUS  current
    DESCRIPTION
        "The pattern match group.
        The pattern match groups are presented in a bitmap format.

         in receiving order:

             OCTET 1  OCTET 2  .....
             xxxxxxxx xxxxxxxx .....
             ||    || |_ pattern match group
             ||    ||
             ||    ||___ pattern match group 8
             ||    |____ pattern match group 7
             ||      .    .   .
             ||_________ pattern match group 2
             |__________ pattern match group 1

         where x : 1 - The represented pattern match group is selected
                   0 - The represented pattern match group is not selected"
    ::= { fltCurCfgTableEntry 62 }

fltCurCfg8021pBitsValue OBJECT-TYPE
    SYNTAX  INTEGER (0..7)
    MAX-ACCESS  read-only
    STATUS  current
    DESCRIPTION
        "The 802.1p bits value to match."
    ::= { fltCurCfgTableEntry 63 }

fltCurCfg8021pBitsMatch OBJECT-TYPE
    SYNTAX  INTEGER {
        enabled(1),
        disabled(2)
        }
    MAX-ACCESS  read-only
    STATUS  current
    DESCRIPTION
        "Enable or disable matching on 802.1p bits in the packets."
    ::= { fltCurCfgTableEntry 64 }
 
fltCurCfgAclIpLength OBJECT-TYPE
    SYNTAX  INTEGER (0..65535)
    MAX-ACCESS  read-only
    STATUS  current 
    DESCRIPTION
        "Set the IP maximum packet length in bytes. A value can be either 0 
         which indicates 'any' length or between 64 and 65535."
    ::= { fltCurCfgTableEntry 65 }	

fltCurCfgIdsGroup OBJECT-TYPE
    SYNTAX  Integer32
    MAX-ACCESS  read-only
    STATUS  current
    DESCRIPTION
        "The real server group for IDS load balancing. A value of 0 indicates
	 'none'." 
    ::= { fltCurCfgTableEntry 66 }
    
fltCurCfgEgressPip OBJECT-TYPE
    SYNTAX  INTEGER {
        enabled(1),
        disabled(2)
        }
    MAX-ACCESS  read-only
    STATUS  current
    DESCRIPTION
        "Enable or disable pip selection based on egress port/vlan."
    ::= { fltCurCfgTableEntry 67 }
    
fltCurCfgDbind OBJECT-TYPE
    SYNTAX  INTEGER {
        enabled(1),
        disabled(2)
        }
    MAX-ACCESS  read-only
    STATUS  current	
    DESCRIPTION
        "Enable or disable filter delayed binding."
    ::= { fltCurCfgTableEntry 68 }

fltCurCfgRevBwmContract OBJECT-TYPE
    SYNTAX  Integer32
    MAX-ACCESS  read-only
    STATUS  current
    DESCRIPTION
	"Filt reverse session BWM contract number."
    ::= { fltCurCfgTableEntry 69 }	

fltCurCfgReverse OBJECT-TYPE
    SYNTAX  INTEGER {
        enabled(1),
        disabled(2)
        }
    MAX-ACCESS  read-only
    STATUS  current	
    DESCRIPTION
        "Enable or disable creating session for reverse side traffic."
    ::= { fltCurCfgTableEntry 70 }

fltCurCfgParseChn OBJECT-TYPE
    SYNTAX INTEGER { 
	enabled(1),
	disabled(2)
	}
    MAX-ACCESS  read-only
    STATUS  current
    DESCRIPTION
	"Enable or disable chained pgroup match criteria for l7 filtering."
    ::= { fltCurCfgTableEntry 71 }


fltCurCfgRtpBwmContract OBJECT-TYPE
    SYNTAX  Integer32
    MAX-ACCESS  read-only
    STATUS  current
    DESCRIPTION
        "BWM contract for SIP RTP traffic."
    ::= { fltCurCfgTableEntry 72 }

fltCurCfgSipParsing OBJECT-TYPE
    SYNTAX  INTEGER {
        enabled(1),
        disabled(2)
        }
    MAX-ACCESS  read-only
    STATUS  current
    DESCRIPTION
        "Enable or disable SIP NAT."
    ::= { fltCurCfgTableEntry 73 }


fltCurCfgSessionMirror  OBJECT-TYPE
    SYNTAX  INTEGER {
        enabled(1),
        disabled(2)
        }
    MAX-ACCESS  read-only
    STATUS  current
    DESCRIPTION
        "Enable or disable session mirroring."
    ::= { fltCurCfgTableEntry 74 }


fltCurCfgIpVer OBJECT-TYPE
    SYNTAX  INTEGER{
        ipv4(1),
        ipv6(2)
        }
    MAX-ACCESS  read-only
    STATUS  current
    DESCRIPTION
        "The type of IP address."
    ::= { fltCurCfgTableEntry 75 }

fltCurCfgIpv6Sip   OBJECT-TYPE
    SYNTAX   DisplayString (SIZE(0..40))
    MAX-ACCESS  read-only
    STATUS  current
    DESCRIPTION
        "The source IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltCurCfgTableEntry 76 }

fltCurCfgIpv6Sprefix   OBJECT-TYPE
    SYNTAX  INTEGER(0..128) 
    MAX-ACCESS  read-only
    STATUS  current
    DESCRIPTION
        "The prefix length associated with source IP address ."
    ::= { fltCurCfgTableEntry 77 }

fltCurCfgIpv6Dip     OBJECT-TYPE
    SYNTAX   DisplayString (SIZE(0..40))
    MAX-ACCESS  read-only
    STATUS  current
    DESCRIPTION
        "The destination  IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltCurCfgTableEntry 78 }

fltCurCfgIpv6Dprefix OBJECT-TYPE
    SYNTAX   INTEGER(0..128) 
    MAX-ACCESS  read-only
    STATUS  current
    DESCRIPTION
        "The prefix length associated with destination IP address ."
    ::= { fltCurCfgTableEntry 79 }


fltCurCfgHdrHash OBJECT-TYPE
       SYNTAX  INTEGER {
        none(1),
        headerhash(2)
        }
    MAX-ACCESS read-only
    STATUS current
    DESCRIPTION
        "The header hash filter."
    ::= { fltCurCfgTableEntry 80 }

fltCurCfgHdrName OBJECT-TYPE
    SYNTAX DisplayString (SIZE(0..31))
    MAX-ACCESS read-only
    STATUS current
    DESCRIPTION
        "The header name of the filter."
    ::= { fltCurCfgTableEntry 81 }

fltCurCfgHdrHashLen OBJECT-TYPE
    SYNTAX  INTEGER (0..255)
    MAX-ACCESS  read-only
    STATUS  current
    DESCRIPTION
        "The header hash length of the filter."
    ::= { fltCurCfgTableEntry 82 }

fltCurCfgL3Filter OBJECT-TYPE
    SYNTAX  INTEGER {
        enabled(1),
        disabled(2)
    }
    MAX-ACCESS  read-only
    STATUS  current
    DESCRIPTION
        "The L3 filter processing state for this filter."
    ::= { fltCurCfgTableEntry 83 }


fltCurCfgNatIp OBJECT-TYPE
    SYNTAX  IpAddress
    MAX-ACCESS  read-only
    STATUS  current
    DESCRIPTION
        "The nat IP address to be filtered."
    ::= { fltCurCfgTableEntry 84 }

fltCurCfgIpv6Nip     OBJECT-TYPE
    SYNTAX   DisplayString (SIZE(0..40))
    MAX-ACCESS  read-only
    STATUS  current
    DESCRIPTION
        "The nat IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltCurCfgTableEntry 85 }

fltCurCfgIpv6Proxy  OBJECT-TYPE
    SYNTAX   DisplayString (SIZE(0..40))
    MAX-ACCESS  read-only
    STATUS  current
    DESCRIPTION
        "The proxy IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltCurCfgTableEntry 86 }
    
fltCurCfgL7SipFilt OBJECT-TYPE
    SYNTAX  INTEGER {
        enabled(1),
        disabled(2)
        }
    MAX-ACCESS  read-only
    STATUS  current
    DESCRIPTION
        "Enable/Disable L7 application SIP UDP filtering."
    ::= { fltCurCfgTableEntry 87 }

fltCurCfgNatMcastVlan OBJECT-TYPE
    SYNTAX  INTEGER (0..4090)
    MAX-ACCESS  read-only
    STATUS  current
    DESCRIPTION
        "Multicast VLAN."
    ::= { fltCurCfgTableEntry 88 }

fltCurCfgNbind OBJECT-TYPE
    SYNTAX  INTEGER {
        enabled(1),
        disabled(2)
    }
    MAX-ACCESS  read-only
    STATUS  current
    DESCRIPTION
        "Enable or disable subnet binding for redirection."
    ::= { fltCurCfgTableEntry 89 }

-- New Config Filtering Table

fltNewCfgTable OBJECT-TYPE
    SYNTAX  SEQUENCE OF FltNewCfgTableEntry
    MAX-ACCESS  not-accessible
    STATUS  current
    DESCRIPTION
        "The filtering table in the new configuration block."
    ::= { filterCfg 3 }

fltNewCfgTableEntry OBJECT-TYPE
    SYNTAX  FltNewCfgTableEntry
    MAX-ACCESS  not-accessible
    STATUS  current
    DESCRIPTION
        "A row in the filtering table."
    INDEX   { fltNewCfgIndx }
    ::= { fltNewCfgTable 1 }

FltNewCfgTableEntry ::= SEQUENCE {
    fltNewCfgIndx             Integer32,
    fltNewCfgSrcIpMac         INTEGER,
    fltNewCfgSrcIp            IpAddress,
    fltNewCfgSrcIpMask        IpAddress,
    fltNewCfgDstIpMac         INTEGER,
    fltNewCfgDstIp            IpAddress,
    fltNewCfgDstIpMask        IpAddress,
    fltNewCfgProtocol         INTEGER,
    fltNewCfgRangeLowSrcPort  INTEGER,
    fltNewCfgRangeHighSrcPort INTEGER,
    fltNewCfgRangeLowDstPort  INTEGER,
    fltNewCfgRangeHighDstPort INTEGER,
    fltNewCfgAction           INTEGER,
    fltNewCfgRedirPort        INTEGER,
    fltNewCfgRedirGroup       Integer32,
    fltNewCfgLog              INTEGER,
    fltNewCfgState            INTEGER,
    fltNewCfgNat              INTEGER,
    fltNewCfgCache            INTEGER,
    fltNewCfgInvert           INTEGER,
    fltNewCfgClientProxy      INTEGER,
    fltNewCfgTcpAck           INTEGER,
    fltNewCfgSrcMac           PhysAddress,
    fltNewCfgDstMac           PhysAddress,
    fltNewCfgFtpNatActive     INTEGER,
    fltNewCfgAclTcpUrg        INTEGER,
    fltNewCfgAclTcpAck        INTEGER,
    fltNewCfgAclTcpPsh        INTEGER,
    fltNewCfgAclTcpRst        INTEGER,
    fltNewCfgAclTcpSyn        INTEGER,
    fltNewCfgAclTcpFin        INTEGER,
    fltNewCfgAclIcmp          INTEGER,
    fltNewCfgAclIpOption      INTEGER,
    fltNewCfgBwmContract      Integer32,
    fltNewCfgAclIpTos	      INTEGER,
    fltNewCfgAclIpTosMask     INTEGER,
    fltNewCfgAclIpTosNew      INTEGER,
    fltNewCfgFwlb             INTEGER,
    fltNewCfgNatTimeout	      INTEGER,
    fltNewCfgLinklb           INTEGER,
    fltNewCfgWapRadiusSnoop   INTEGER,
    fltNewCfgIdslbHash        INTEGER,
    fltNewCfgVlan             INTEGER,
    fltNewCfgName             DisplayString,
    fltNewCfgTcpRateLimit     INTEGER,
    fltNewCfgTcpRateMaxConn   INTEGER,
    fltNewCfgHash             INTEGER,
    fltNewCfgLayer7DenyState  INTEGER,
    fltNewCfgLayer7DenyUrlBmap OCTET STRING,
    fltNewCfgLayer7DenyAddUrl Integer32,
    fltNewCfgLayer7DenyRemUrl Integer32,
    fltNewCfgGotoFilter       Integer32,
    fltNewCfgRadiusWapPersist INTEGER,
    fltNewCfgPbind            INTEGER,
    fltNewCfgTimeWindow       INTEGER,
    fltNewCfgHoldDuration     INTEGER,
    fltNewCfgProxyIp          IpAddress,
    fltNewCfgPatternMatch     INTEGER,
    fltNewCfgLayer7DenyMatchAll INTEGER,
    fltNewCfgLayer7ParseAll   INTEGER,
    fltNewCfgSecurityParseAll INTEGER,
    fltNewCfgPatternMatchGroupBmap OCTET STRING,
    fltNewCfgAddPatternMatchGroup  Integer32,
    fltNewCfgRemPatternMatchGroup Integer32,
    fltNewCfg8021pBitsValue   INTEGER,
    fltNewCfg8021pBitsMatch   INTEGER,
    fltNewCfgAclIpLength      INTEGER,
    fltNewCfgIdsGroup         Integer32,
    fltNewCfgEgressPip        INTEGER,
    fltNewCfgDbind            INTEGER,
    fltNewCfgReverse          INTEGER,
    fltNewCfgRevBwmContract   Integer32,
    fltNewCfgParseChn         INTEGER,
    fltNewCfgRtpBwmContract   Integer32,
    fltNewCfgSipParsing       INTEGER,
    fltNewCfgSessionMirror    INTEGER,
    fltNewCfgIpVer            INTEGER,
    fltNewCfgIpv6Sip          DisplayString,
    fltNewCfgIpv6Sprefix      INTEGER,
    fltNewCfgIpv6Dip          DisplayString,
    fltNewCfgIpv6Dprefix      INTEGER,
    fltNewCfgHdrHash          INTEGER,
    fltNewCfgHdrName          DisplayString,
    fltNewCfgHdrHashLen       INTEGER,
    fltNewCfgL3Filter          INTEGER,
    fltNewCfgDelete           INTEGER,
    fltNewCfgNatIp            IpAddress,
    fltNewCfgIpv6Nip          DisplayString,
    fltNewCfgIpv6Proxy        DisplayString,    
    fltNewCfgL7SipFilt        INTEGER,
    fltNewCfgNatMcastVlan     INTEGER,
    fltNewCfgNbind            INTEGER
    }

fltNewCfgIndx OBJECT-TYPE
    SYNTAX  Integer32
    MAX-ACCESS  read-only
    STATUS  current
    DESCRIPTION
        "The filtering table index."
    ::= { fltNewCfgTableEntry 1 }

fltNewCfgSrcIp OBJECT-TYPE
    SYNTAX  IpAddress
    MAX-ACCESS  read-create
    STATUS  current
    DESCRIPTION
        "The source IP address to be filtered."
    ::= { fltNewCfgTableEntry 2 }

fltNewCfgSrcIpMask OBJECT-TYPE
    SYNTAX  IpAddress
    MAX-ACCESS  read-create
    STATUS  current
    DESCRIPTION
        "The source IP sub-net mask for filtering."
    ::= { fltNewCfgTableEntry 3 }

fltNewCfgDstIp OBJECT-TYPE
    SYNTAX  IpAddress
    MAX-ACCESS  read-create
    STATUS  current
    DESCRIPTION
        "The destination IP address to be filtered."
    ::= { fltNewCfgTableEntry 4 }

fltNewCfgDstIpMask OBJECT-TYPE
    SYNTAX  IpAddress
    MAX-ACCESS  read-create
    STATUS  current
    DESCRIPTION
        "The destination IP sub-net mask for filtering."
    ::= { fltNewCfgTableEntry 5 }

fltNewCfgProtocol OBJECT-TYPE
    SYNTAX  INTEGER (0..255)
    MAX-ACCESS  read-create
    STATUS  current
    DESCRIPTION
        "The protocol to be filtered."
    ::= { fltNewCfgTableEntry 6 }

fltNewCfgRangeHighSrcPort OBJECT-TYPE
    SYNTAX  INTEGER (0..65534)
    MAX-ACCESS  read-create
    STATUS  current
    DESCRIPTION
        "The higher source TCP/UDP port number to be filtered. It applies 
         only when protocol defined in fltNewCfgProtocol is UDP or TCP. 
         '0' means no filtering."
    ::= { fltNewCfgTableEntry 7 }

fltNewCfgRangeLowSrcPort OBJECT-TYPE
    SYNTAX  INTEGER (0..65534)
    MAX-ACCESS  read-create
    STATUS  current
    DESCRIPTION
        "The lower source TCP/UDP port number to be filtered. It applies 
         only when protocol defined in fltNewCfgProtocol is UDP or TCP. 
         '0' means no filtering."
    ::= { fltNewCfgTableEntry 8 }

fltNewCfgRangeLowDstPort OBJECT-TYPE
    SYNTAX  INTEGER (0..65534)
    MAX-ACCESS  read-create
    STATUS  current
    DESCRIPTION
        "The lower destination TCP/UDP port number to be filtered.
         It applies only when protocol defined in fltNewCfgProtocol
	 is UDP or TCP.  '0' means no filtering."
    ::= { fltNewCfgTableEntry 9 }

fltNewCfgRangeHighDstPort OBJECT-TYPE
    SYNTAX  INTEGER (0..65534)
    MAX-ACCESS  read-create
    STATUS  current
    DESCRIPTION
        "The higher destination TCP/UDP port number to be filtered.
         It applies only when protocol defined in fltNewCfgProtocol
         is UDP or TCP.  '0' means no filtering."
    ::= { fltNewCfgTableEntry 10 }

fltNewCfgAction OBJECT-TYPE
    SYNTAX  INTEGER {
        allow(1),
        deny(2),
        redirect(3),
        nat(4),      -- network address translation
        goto(5)
        }
    MAX-ACCESS  read-create
    STATUS  current
    DESCRIPTION
        "The action for the filtering rule."
    ::= { fltNewCfgTableEntry 11 }

fltNewCfgRedirPort OBJECT-TYPE
    SYNTAX  INTEGER (0..65534)
    MAX-ACCESS  read-create
    STATUS  current
    DESCRIPTION
        "The real server port number used for redirection."
    ::= { fltNewCfgTableEntry 12 }

fltNewCfgRedirGroup OBJECT-TYPE
    SYNTAX  Integer32
    MAX-ACCESS  read-create
    STATUS  current
    DESCRIPTION
        "The real server group to be redirected to."
    ::= { fltNewCfgTableEntry 13 }

fltNewCfgLog OBJECT-TYPE
    SYNTAX  INTEGER {
        enabled(1),
        disabled(2)
        }
    MAX-ACCESS  read-create
    STATUS  current
    DESCRIPTION
        "Enable or disable logging."
    ::= { fltNewCfgTableEntry 14 }

fltNewCfgState OBJECT-TYPE
    SYNTAX  INTEGER {
        enabled(1),
        disabled(2)
        }
    MAX-ACCESS  read-create
    STATUS  current
    DESCRIPTION
        "The state of this filtering rule."
    ::= { fltNewCfgTableEntry 15 }

fltNewCfgDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { fltNewCfgTableEntry 16 }

fltNewCfgNat OBJECT-TYPE
    SYNTAX  INTEGER {
        destination-address(1),
        source-address(2),
	multicast-address(3)
        }
    MAX-ACCESS  read-create
    STATUS  current
    DESCRIPTION
        "The selection of destination or source or multicast for 
         network address translation."
    ::= { fltNewCfgTableEntry 17 }

fltNewCfgCache OBJECT-TYPE
    SYNTAX  INTEGER {
        enabled(1),
        disabled(2)
        }
    MAX-ACCESS  read-create
    STATUS  current
    DESCRIPTION
        "Enable or disable caching sessions that match filter."
    ::= { fltNewCfgTableEntry 18 }

fltNewCfgInvert OBJECT-TYPE
    SYNTAX  INTEGER {
        enabled(1),
        disabled(2)
        }
    MAX-ACCESS  read-create
    STATUS  current
    DESCRIPTION
        "Turn the invert logic on or off for the filter entry."
    ::= { fltNewCfgTableEntry 19 }

fltNewCfgClientProxy OBJECT-TYPE
    SYNTAX  INTEGER {
        enabled(1),
        disabled(2)
        }
    MAX-ACCESS  read-create
    STATUS  current
    DESCRIPTION
        "Enable or disable client proxy."
    ::= { fltNewCfgTableEntry 20 }

fltNewCfgTcpAck OBJECT-TYPE
    SYNTAX  INTEGER {
        enabled(1),
        disabled(2)
        }
    MAX-ACCESS  read-create
    STATUS  current
    DESCRIPTION
        "Enable or disable filtering on matching TCP ACK and RST flag."
    ::= { fltNewCfgTableEntry 21 }


fltNewCfgSrcMac OBJECT-TYPE
    SYNTAX  PhysAddress 
    MAX-ACCESS  read-create
    STATUS  current
    DESCRIPTION
        "The source MAC address to be filtered."
    ::= { fltNewCfgTableEntry 23 }

fltNewCfgDstMac OBJECT-TYPE
    SYNTAX  PhysAddress 
    MAX-ACCESS  read-create
    STATUS  current
    DESCRIPTION
        "The Destination MAC address to be filtered."
    ::= { fltNewCfgTableEntry 24 }

fltNewCfgFtpNatActive OBJECT-TYPE
    SYNTAX  INTEGER {
        enabled(1),	
	disabled(2)
	}	
    MAX-ACCESS  read-create
    STATUS  current
    DESCRIPTION
        "Enable or disable FTP NAT for active ftp."
    ::= { fltNewCfgTableEntry 25 }	

-- New Config TCP Flag ACL Filtering Table

fltNewCfgAclTcpUrg OBJECT-TYPE
    SYNTAX  INTEGER {
	enable(1),
	disable(2)
	}	
    MAX-ACCESS  read-create
    STATUS  current
    DESCRIPTION
	"Enable or disable TCP URG packet."
    ::= { fltNewCfgTableEntry 26 }	

fltNewCfgAclTcpAck OBJECT-TYPE
    SYNTAX  INTEGER {
	enable(1),
	disable(2)
	}	
    MAX-ACCESS  read-create
    STATUS  current
    DESCRIPTION
        "Enable or disable TCP ACK packet."
    ::= { fltNewCfgTableEntry 27 }	

fltNewCfgAclTcpPsh OBJECT-TYPE
    SYNTAX  INTEGER {
	enable(1),
	disable(2)
	}	
    MAX-ACCESS  read-create
    STATUS  current
    DESCRIPTION
        "Enable or disable TCP PSH packet."
    ::= { fltNewCfgTableEntry 28 }	

fltNewCfgAclTcpRst OBJECT-TYPE
    SYNTAX  INTEGER {
	enable(1),
	disable(2)
	}	
    MAX-ACCESS  read-create
    STATUS  current
    DESCRIPTION
        "Enable or disable TCP RST packet."
    ::= { fltNewCfgTableEntry 29 }	

fltNewCfgAclTcpSyn OBJECT-TYPE
    SYNTAX  INTEGER {
	enable(1),
	disable(2)
	}	
    MAX-ACCESS  read-create
    STATUS  current
    DESCRIPTION
        "Enable or disable TCP SYN packet."
    ::= { fltNewCfgTableEntry 30 }	

fltNewCfgAclTcpFin OBJECT-TYPE
    SYNTAX  INTEGER {
	enable(1),
	disable(2)
	}	
    MAX-ACCESS  read-create
    STATUS  current
    DESCRIPTION
        "Enable or disable TCP FIN packet."
    ::= { fltNewCfgTableEntry 31 }	

-- New Config ICMP Type ACL Filtering Table

fltNewCfgAclIcmp OBJECT-TYPE
    SYNTAX  INTEGER (0..255) 
    MAX-ACCESS  read-create
    STATUS  current
    DESCRIPTION
        "ICMP type to be filtered. A ICMP type of 255 indicates 'any'"
    ::= { fltNewCfgTableEntry 32 }	

-- New Config IP Option ACL Filtering Table

fltNewCfgAclIpOption OBJECT-TYPE
    SYNTAX  INTEGER {
        enable(1),
        disable(2)
        }
    MAX-ACCESS  read-create
    STATUS  current
    DESCRIPTION
        "Enable or disable IP option matching."
    ::= { fltNewCfgTableEntry 33 }

fltNewCfgBwmContract OBJECT-TYPE
    SYNTAX  Integer32 
    MAX-ACCESS  read-create
    STATUS  current
    DESCRIPTION
        "Filt default BW contract number."
    ::= { fltNewCfgTableEntry 34 }	

fltNewCfgAclIpTos OBJECT-TYPE
    SYNTAX  INTEGER (0..255)
    MAX-ACCESS  read-create
    STATUS  current
    DESCRIPTION
        "The IP TOS value to be filtered."
    ::= { fltNewCfgTableEntry 35 }	

fltNewCfgAclIpTosMask OBJECT-TYPE
    SYNTAX  INTEGER (0..255)
    MAX-ACCESS  read-create
    STATUS  current
    DESCRIPTION
        "The IP TOS mask for filtering."
    ::= { fltNewCfgTableEntry 36 }	

fltNewCfgAclIpTosNew OBJECT-TYPE
    SYNTAX  INTEGER (0..255)
    MAX-ACCESS  read-create
    STATUS  current
    DESCRIPTION
        "The new IP TOS value to over-write when filtering fired."
    ::= { fltNewCfgTableEntry 37 }	

fltNewCfgFwlb OBJECT-TYPE
    SYNTAX  INTEGER {
        enabled(1),
        disabled(2)
        }
    MAX-ACCESS  read-create
    STATUS  current
    DESCRIPTION
        "Enable or disable filtering on firewall redirect hash method."
    ::= { fltNewCfgTableEntry 38 }

fltNewCfgNatTimeout OBJECT-TYPE
    SYNTAX  INTEGER (4..32768)
    MAX-ACCESS  read-create
    STATUS  current
    DESCRIPTION
	"The NAT session timeout. The timeout value should be an even
         number between 4 and 32768."
    ::= { fltNewCfgTableEntry 39 }	

fltNewCfgLinklb OBJECT-TYPE
    SYNTAX  INTEGER {
        enabled(1),
        disabled(2)
        }
    MAX-ACCESS  read-create
    STATUS  current
    DESCRIPTION
        "Enable or disable WAN link load balancing."
    ::= { fltNewCfgTableEntry 40 }

fltNewCfgWapRadiusSnoop OBJECT-TYPE
    SYNTAX  INTEGER {
        enabled(1),
        disabled(2)
        }
    MAX-ACCESS  read-create
    STATUS  current
    DESCRIPTION
        "Enable or disable WAP RADIUS snooping."
    ::= { fltNewCfgTableEntry 41 }

fltNewCfgSrcIpMac OBJECT-TYPE
    SYNTAX  INTEGER {
        ip(1),
        mac(2)
        }
    MAX-ACCESS  read-create
    STATUS  current
    DESCRIPTION
        "Set a flag indicating whether filtering should be based on the 
         source IP address or the source MAC address field."
    ::= { fltNewCfgTableEntry 42 }

fltNewCfgDstIpMac OBJECT-TYPE
    SYNTAX  INTEGER {
        ip(1),
        mac(2)
        }
    MAX-ACCESS  read-create
    STATUS  current
    DESCRIPTION
        "Set a flag indicating whether filtering should be based on the 
         destination IP address or the destination MAC address field."
    ::= { fltNewCfgTableEntry 43 }

fltNewCfgIdslbHash OBJECT-TYPE
    SYNTAX  INTEGER {
        sip(1),
        dip(2),
        both(3)
        }
    MAX-ACCESS  read-create
    STATUS  current
    DESCRIPTION
        "Set hash parameter for intrusion detection server load balancing."
    ::= { fltNewCfgTableEntry 44 }

fltNewCfgVlan OBJECT-TYPE
    SYNTAX  INTEGER (0..4090)
    MAX-ACCESS  read-create
    STATUS  current
    DESCRIPTION
        "Set the VLAN assoicated with the filter."
    ::= { fltNewCfgTableEntry 45 }

fltNewCfgName OBJECT-TYPE
    SYNTAX DisplayString (SIZE(0..31))
    MAX-ACCESS read-create
    STATUS current
    DESCRIPTION
        "The name of the filter."
    ::= { fltNewCfgTableEntry 46 }

fltNewCfgTcpRateLimit OBJECT-TYPE
    SYNTAX  INTEGER {
        enabled(1),
        disabled(2)
        }
    MAX-ACCESS  read-create
    STATUS  current
    DESCRIPTION
        "Enable or disable protocol rate limiting."
    ::= { fltNewCfgTableEntry 47 }

fltNewCfgTcpRateMaxConn OBJECT-TYPE
    SYNTAX  INTEGER (0..255)
    MAX-ACCESS  read-create
    STATUS  current
    DESCRIPTION
        "Set maximum connections (number of connections in units of 10)
         for TCP connection rate limiting. In the case of ICMP and UDP,
	 this is the maximum packets (number of packets in units of 10)."
    ::= { fltNewCfgTableEntry 48 }

fltNewCfgHash OBJECT-TYPE
    SYNTAX  INTEGER {
	auto(1),
        sip(2),
        dip(3),
        both(4),
	sipsport(5)
        }
    MAX-ACCESS  read-create
    STATUS  current
    DESCRIPTION
        "Set hash parameter for the filter."
    ::= { fltNewCfgTableEntry 49 }


fltNewCfgLayer7DenyState OBJECT-TYPE
    SYNTAX  INTEGER {
        enabled(1),
        disabled(2)
        }
    MAX-ACCESS  read-create
    STATUS  current
    DESCRIPTION
        "Enable or disable layer 7 deny filtering."
    ::= { fltNewCfgTableEntry 51 }

fltNewCfgLayer7DenyUrlBmap OBJECT-TYPE
    SYNTAX  OCTET STRING
    MAX-ACCESS  read-only
    STATUS  current
    DESCRIPTION
        "The URL strings selected for Layer 7 deny filters.
        The selected URL strings are presented in a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL string is selected
                   0 - The represented URL string is not selected"
    ::= { fltNewCfgTableEntry 52 }

fltNewCfgLayer7DenyAddUrl OBJECT-TYPE
    SYNTAX  Integer32
    MAX-ACCESS  read-create
    STATUS  current
    DESCRIPTION
        "The URL Path (slbCurCfgUrlLbPathIndex) to be added to the 
         Layer 7 deny filter. A zero is returned when read."
    ::= { fltNewCfgTableEntry 53 }

fltNewCfgLayer7DenyRemUrl OBJECT-TYPE
    SYNTAX  Integer32
    MAX-ACCESS  read-create
    STATUS  current
    DESCRIPTION
        "The URL Path (slbCurCfgUrlLbPathIndex) to be removed from 
         the Layer 7 deny filter. A zero is returned when read."
    ::= { fltNewCfgTableEntry 54 }

fltNewCfgGotoFilter OBJECT-TYPE
    SYNTAX  Integer32
    MAX-ACCESS  read-create
    STATUS  current	
    DESCRIPTION
        "The filter ID for GOTO action in the new config."
    ::= { fltNewCfgTableEntry 55 }

fltNewCfgRadiusWapPersist OBJECT-TYPE
    SYNTAX  INTEGER {
        enabled(1),
        disabled(2)
        }
    MAX-ACCESS  read-create
    STATUS  current	
    DESCRIPTION
        "Enable or disable Radius/WAP persistence."
    ::= { fltNewCfgTableEntry 56 }

fltNewCfgPbind OBJECT-TYPE
    SYNTAX  INTEGER {
        enabled(1),
        disabled(2)
        }
    MAX-ACCESS  read-create
    STATUS  current	
    DESCRIPTION
        "Enable or disable filter persistent binding."
    ::= { fltNewCfgTableEntry 57 }

fltNewCfgTimeWindow OBJECT-TYPE
    SYNTAX  INTEGER (1..65535)
    MAX-ACCESS  read-create
    STATUS  current
    DESCRIPTION
        "The time window for protocol rate limiting (in seconds)."
    ::= { fltNewCfgTableEntry 58 }

fltNewCfgHoldDuration OBJECT-TYPE
    SYNTAX  INTEGER (2..65535)
    MAX-ACCESS  read-create
    STATUS  current
    DESCRIPTION
        "The hold down duration for protocol rate limiting (in minutes)."
    ::= { fltNewCfgTableEntry 59 }

fltNewCfgPatternMatch OBJECT-TYPE
    SYNTAX  INTEGER {
        enabled(1),
        disabled(2)
        }
    MAX-ACCESS  read-create
    STATUS  current	
    DESCRIPTION
        "Enable or disable binary pattern matching."
    ::= { fltNewCfgTableEntry 60 }

fltNewCfgLayer7DenyMatchAll OBJECT-TYPE
    SYNTAX  INTEGER {
        enabled(1),
        disabled(2)
        }
    MAX-ACCESS  read-create
    STATUS  current
    DESCRIPTION
        "Enable or disable match-all criteria for L7 deny string matching."
    ::= { fltNewCfgTableEntry 61 }

fltNewCfgProxyIp OBJECT-TYPE
    SYNTAX  IpAddress
    MAX-ACCESS  read-create
    STATUS  current
    DESCRIPTION
        "The client proxy IP address for NAT and REDIR filter."
        
    ::= { fltNewCfgTableEntry 62 }

fltNewCfgLayer7ParseAll OBJECT-TYPE
    SYNTAX  INTEGER {
        enabled(1),
        disabled(2)
        }
    MAX-ACCESS  read-create
    STATUS  current
    DESCRIPTION
        "Enable or disable layer 7 lookup (parsing) of all packets."
    ::= { fltNewCfgTableEntry 63 }

fltNewCfgSecurityParseAll OBJECT-TYPE
    SYNTAX  INTEGER {
        enabled(1),
        disabled(2)
        }
    MAX-ACCESS  read-create
    STATUS  current
    DESCRIPTION
        "Enable or disable pattern string lookup (parsing) of all packets."
    ::= { fltNewCfgTableEntry 64 }

fltNewCfgPatternMatchGroupBmap OBJECT-TYPE
    SYNTAX  OCTET STRING
    MAX-ACCESS  read-only
    STATUS  current
    DESCRIPTION
        "The pattern match group.
        The pattern match groups are presented in a bitmap format.

         in receiving order:

             OCTET 1  OCTET 2  .....
             xxxxxxxx xxxxxxxx .....
             ||    || |_ pattern match group
             ||    ||
             ||    ||___ pattern match group 8
             ||    |____ pattern match group 7
             ||      .    .   .
             ||_________ pattern match group 2
             |__________ pattern match group 1

         where x : 1 - The represented pattern match group is selected
                   0 - The represented pattern match group is not selected"
    ::= { fltNewCfgTableEntry 65 }
    
fltNewCfgAddPatternMatchGroup OBJECT-TYPE
    SYNTAX  Integer32
    MAX-ACCESS  read-create
    STATUS  current
    DESCRIPTION
        "The pattern match group to be added to the 
         security filter. A zero is returned when read."
    ::= { fltNewCfgTableEntry 66 }

fltNewCfgRemPatternMatchGroup OBJECT-TYPE
    SYNTAX  Integer32
    MAX-ACCESS  read-create
    STATUS  current
    DESCRIPTION
        "The pattern match group to be to be removed from 
         the security filter. A zero is returned when read."
    ::= { fltNewCfgTableEntry 67 }

fltNewCfg8021pBitsValue OBJECT-TYPE
    SYNTAX  INTEGER (0..7)
    MAX-ACCESS  read-create
    STATUS  current
    DESCRIPTION
        "The 802.1p bits value to match."
    ::= { fltNewCfgTableEntry 68 }

fltNewCfg8021pBitsMatch OBJECT-TYPE
    SYNTAX  INTEGER {
        enabled(1),
        disabled(2)
        }
    MAX-ACCESS  read-create
    STATUS  current
    DESCRIPTION
        "Enable or disable matching on 802.1p bits in the packets."
    ::= { fltNewCfgTableEntry 69 }
 
fltNewCfgAclIpLength OBJECT-TYPE
    SYNTAX  INTEGER (0..65535)
    MAX-ACCESS  read-create
    STATUS  current 
    DESCRIPTION
        "Set the IP maximum packet length in bytes. A value can be either 0 
         which indicates 'any' length or between 64 and 65535."
    ::= { fltNewCfgTableEntry 70 }	

fltNewCfgIdsGroup OBJECT-TYPE
    SYNTAX  Integer32
    MAX-ACCESS  read-create
    STATUS  current
    DESCRIPTION
        "The real server group for IDS load balancing. A value of 0 indicates
	 'none'." 
    ::= { fltNewCfgTableEntry 71 }
    
fltNewCfgEgressPip OBJECT-TYPE
    SYNTAX  INTEGER {
        enabled(1),
        disabled(2)
        }
    MAX-ACCESS  read-create
    STATUS  current
    DESCRIPTION
        "Enable or disable pip selection based on egress port/vlan."
    ::= { fltNewCfgTableEntry 72 }
    
fltNewCfgDbind OBJECT-TYPE
    SYNTAX  INTEGER {
        enabled(1),
        disabled(2)
        }
    MAX-ACCESS  read-create
    STATUS  current	
    DESCRIPTION
        "Enable or disable filter delayed binding."
    ::= { fltNewCfgTableEntry 73 }

fltNewCfgRevBwmContract OBJECT-TYPE
    SYNTAX  Integer32
    MAX-ACCESS  read-create
    STATUS  current
    DESCRIPTION
	"Filt reverse session BWM contract number."
    ::= { fltNewCfgTableEntry 74 }	

fltNewCfgReverse OBJECT-TYPE
    SYNTAX  INTEGER {
        enabled(1),
        disabled(2)
        }
    MAX-ACCESS  read-create
    STATUS  current	
    DESCRIPTION
        "Enable or disable creating session for reverse side traffic."
    ::= { fltNewCfgTableEntry 75 }

fltNewCfgParseChn OBJECT-TYPE
    SYNTAX  INTEGER {
	enabled(1),
	disabled(2)
	}
    MAX-ACCESS  read-create
    STATUS  current 
    DESCRIPTION
        "Enable or disable chained pgroup match criteria for l7 filtering."	 
    ::= { fltNewCfgTableEntry 76}


fltNewCfgRtpBwmContract OBJECT-TYPE
    SYNTAX  Integer32
    MAX-ACCESS  read-create
    STATUS  current
    DESCRIPTION
        "BWM contract for SIP RTP traffic."
    ::= { fltNewCfgTableEntry 77 }

fltNewCfgSipParsing OBJECT-TYPE
    SYNTAX  INTEGER {
        enabled(1),
        disabled(2)
        }
    MAX-ACCESS  read-create
    STATUS  current
    DESCRIPTION
        "Enable or disable SIP NAT."
    ::= { fltNewCfgTableEntry 78 }


    fltNewCfgSessionMirror  OBJECT-TYPE
    SYNTAX  INTEGER {
        enabled(1),
        disabled(2)
        }
    MAX-ACCESS  read-create
    STATUS  current
    DESCRIPTION
        "Enable or disable session mirroring."
    ::= { fltNewCfgTableEntry 79 }


fltNewCfgIpVer OBJECT-TYPE
    SYNTAX  INTEGER{
        ipv4(1),
        ipv6(2)
        }
    MAX-ACCESS  read-create
    STATUS  current
    DESCRIPTION
        "The type of IP address."
    ::= { fltNewCfgTableEntry 80 }

fltNewCfgIpv6Sip  OBJECT-TYPE
    SYNTAX   DisplayString (SIZE(0..40))
    MAX-ACCESS  read-create
    STATUS  current
    DESCRIPTION
        "The source IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltNewCfgTableEntry 81 }

fltNewCfgIpv6Sprefix   OBJECT-TYPE
    SYNTAX   INTEGER(0..128) 
    MAX-ACCESS  read-create
    STATUS  current
    DESCRIPTION
        "The prefix length associated with source IP address ."
    ::= { fltNewCfgTableEntry 82 }

fltNewCfgIpv6Dip   OBJECT-TYPE
    SYNTAX   DisplayString (SIZE(0..40))
    MAX-ACCESS  read-create
    STATUS  current
    DESCRIPTION
        "The destination  IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltNewCfgTableEntry 83 }

fltNewCfgIpv6Dprefix   OBJECT-TYPE
    SYNTAX  INTEGER(0..128) 
    MAX-ACCESS  read-create
    STATUS  current
    DESCRIPTION
        "The prefix length associated with destination IP address ."
    ::= { fltNewCfgTableEntry 84 }

fltNewCfgHdrHash OBJECT-TYPE
       SYNTAX  INTEGER {
        none(1),
        headerhash(2)
        }
    MAX-ACCESS read-create
    STATUS current
    DESCRIPTION
        "The header hash filter."
    ::= { fltNewCfgTableEntry 85 }

fltNewCfgHdrName OBJECT-TYPE
    SYNTAX DisplayString (SIZE(0..31))
    MAX-ACCESS read-create
    STATUS current
    DESCRIPTION
        "The header name of the filter. Headerhash should be
         enabled before header name is configured."
    ::= { fltNewCfgTableEntry 86 }

fltNewCfgHdrHashLen OBJECT-TYPE
    SYNTAX  INTEGER (1..255)
    MAX-ACCESS  read-create
    STATUS  current
    DESCRIPTION
        "The header hash length of the filter. Headerhash should be
         enabled before hash length is configured."
    ::= { fltNewCfgTableEntry 87 }

fltNewCfgL3Filter OBJECT-TYPE
    SYNTAX  INTEGER {
        enabled(1),
        disabled(2)
    }
    MAX-ACCESS  read-create
    STATUS  current
    DESCRIPTION
        "The L3 filter processing state for this filter."
    ::= { fltNewCfgTableEntry 88}


fltNewCfgNatIp OBJECT-TYPE
    SYNTAX  IpAddress
    MAX-ACCESS  read-write
    STATUS  current
    DESCRIPTION
        "The nat IP address to be filtered."
    ::= { fltNewCfgTableEntry 89 }

fltNewCfgIpv6Nip   OBJECT-TYPE
    SYNTAX   DisplayString (SIZE(0..40))
    MAX-ACCESS  read-write
    STATUS  current
    DESCRIPTION
        "The nat IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltNewCfgTableEntry 90 }

fltNewCfgIpv6Proxy  OBJECT-TYPE
    SYNTAX   DisplayString (SIZE(0..40))
    MAX-ACCESS  read-write
    STATUS  current
    DESCRIPTION
        "The proxy IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltNewCfgTableEntry 91 }
    
fltNewCfgL7SipFilt OBJECT-TYPE
    SYNTAX  INTEGER {
        enabled(1),
        disabled(2)
        }
    MAX-ACCESS  read-write
    STATUS  current
    DESCRIPTION
        "Enable/Disable L7 application SIP UDP filtering."
    ::= { fltNewCfgTableEntry 92 }

fltNewCfgNatMcastVlan OBJECT-TYPE
    SYNTAX  INTEGER (0..4090)
    MAX-ACCESS  read-write
    STATUS  current
    DESCRIPTION
        "Multicast VLAN."
    ::= { fltNewCfgTableEntry 93 }

fltNewCfgNbind OBJECT-TYPE
    SYNTAX  INTEGER {
        enabled(1),
        disabled(2)
    }
    MAX-ACCESS  read-create
    STATUS  current
    DESCRIPTION
        "Enable or disable subnet binding for redirection."
    ::= { fltNewCfgTableEntry 94 }

fltNewCfgExtendedTable OBJECT-TYPE
    SYNTAX  SEQUENCE OF FltNewCfgExtendedTableEntry
    MAX-ACCESS  not-accessible
    STATUS  current
    DESCRIPTION
        "The filtering table in the new configuration block."
    ::= { filterCfg 12 }

fltNewCfgExtendedTableEntry OBJECT-TYPE
    SYNTAX  FltNewCfgExtendedTableEntry
    MAX-ACCESS  not-accessible
    STATUS  current
    DESCRIPTION
        "A row in the filtering table."
    INDEX   { fltNewCfgExtendedIndx }
    ::= { fltNewCfgExtendedTable 1 }

FltNewCfgExtendedTableEntry ::= SEQUENCE {
    fltNewCfgExtendedIndx             Integer32,
    fltNewCfgExtendedLayer7DenyState  INTEGER,
    fltNewCfgExtendedLayer7DenyUrlBmap OCTET STRING,
    fltNewCfgExtendedLayer7DenyAddUrl Integer32,
    fltNewCfgExtendedLayer7DenyRemUrl Integer32,
    fltNewCfgExtendedGotoFilter       Integer32,
    fltNewCfgExtendedRadiusWapPersist INTEGER,
    fltNewCfgExtendedPbind            INTEGER,
    fltNewCfgExtendedTimeWindow       INTEGER,
    fltNewCfgExtendedHoldDuration     INTEGER,
    fltNewCfgExtendedProxyIp          IpAddress,
    fltNewCfgExtendedPatternMatch     INTEGER,
    fltNewCfgExtendedLayer7DenyMatchAll INTEGER,
    fltNewCfgExtendedLayer7ParseAll   INTEGER,
    fltNewCfgExtendedSecurityParseAll INTEGER,
    fltNewCfgExtendedPatternMatchGroupBmap OCTET STRING,
    fltNewCfgExtendedAddPatternMatchGroup  Integer32,
    fltNewCfgExtendedRemPatternMatchGroup Integer32,
    fltNewCfgExtended8021pBitsValue   INTEGER,
    fltNewCfgExtended8021pBitsMatch   INTEGER,
    fltNewCfgExtendedAclIpLength      INTEGER,
    fltNewCfgExtendedIdsGroup         Integer32,
    fltNewCfgExtendedEgressPip        INTEGER,
    fltNewCfgExtendedDbind            INTEGER,
    fltNewCfgExtendedReverse          INTEGER,
    fltNewCfgExtendedRevBwmContract   Integer32,
    fltNewCfgExtendedParseChn         INTEGER,
    fltNewCfgExtendedRtpBwmContract   Integer32,
    fltNewCfgExtendedSipParsing       INTEGER,
    fltNewCfgExtendedSessionMirror    INTEGER,
    fltNewCfgExtendedIpVer            INTEGER,
    fltNewCfgExtendedIpv6Sip          DisplayString,
    fltNewCfgExtendedIpv6Sprefix      INTEGER,
    fltNewCfgExtendedIpv6Dip          DisplayString,
    fltNewCfgExtendedIpv6Dprefix      INTEGER,
    fltNewCfgExtendedHdrHash          INTEGER,
    fltNewCfgExtendedHdrName          DisplayString,
    fltNewCfgExtendedHdrHashLen       INTEGER,
    fltNewCfgExtendedNatIp            IpAddress,
    fltNewCfgExtendedIpv6Nip          DisplayString,
    fltNewCfgExtendedIpv6Proxy        DisplayString,    
    fltNewCfgExtendedL7SipFilt        INTEGER,
    fltNewCfgExtendedL3State          INTEGER,
    fltNewCfgExtendedNatMcastVlan     INTEGER,
    fltNewCfgExtendedNbind            INTEGER
}

fltNewCfgExtendedIndx OBJECT-TYPE
    SYNTAX  Integer32
    MAX-ACCESS  read-only
    STATUS  current
    DESCRIPTION
        "The filtering table index."
    ::= { fltNewCfgExtendedTableEntry 1 }


fltNewCfgExtendedLayer7DenyState OBJECT-TYPE
    SYNTAX  INTEGER {
        enabled(1),
        disabled(2)
        }
    MAX-ACCESS  read-create
    STATUS  current
    DESCRIPTION
        "Enable or disable layer 7 deny filtering."
    ::= { fltNewCfgExtendedTableEntry 3 }

fltNewCfgExtendedLayer7DenyUrlBmap OBJECT-TYPE
    SYNTAX  OCTET STRING
    MAX-ACCESS  read-only
    STATUS  current
    DESCRIPTION
        "The URL strings selected for Layer 7 deny filters.
        The selected URL strings are presented in a bitmap format.

         in receiving order:

             OCTET 1  OCTET 2  .....
             xxxxxxxx xxxxxxxx .....
             ||    || |_ URL Path 9
             ||    ||
             ||    ||___ URL Path 8
             ||    |____ URL Path 7
             ||      .    .   .
             ||_________ URL Path 2
             |__________ URL Path 1

         where x : 1 - The represented URL string is selected
                   0 - The represented URL string is not selected"
    ::= { fltNewCfgExtendedTableEntry 4 }

fltNewCfgExtendedLayer7DenyAddUrl OBJECT-TYPE
    SYNTAX  Integer32
    MAX-ACCESS  read-create
    STATUS  current
    DESCRIPTION
        "The URL Path (slbCurCfgUrlLbPathIndex) to be added to the 
         Layer 7 deny filter. A zero is returned when read."
    ::= { fltNewCfgExtendedTableEntry 5 }

fltNewCfgExtendedLayer7DenyRemUrl OBJECT-TYPE
    SYNTAX  Integer32
    MAX-ACCESS  read-create
    STATUS  current
    DESCRIPTION
        "The URL Path (slbCurCfgUrlLbPathIndex) to be removed from 
         the Layer 7 deny filter. A zero is returned when read."
    ::= { fltNewCfgExtendedTableEntry 6}

fltNewCfgExtendedGotoFilter OBJECT-TYPE
    SYNTAX  Integer32
    MAX-ACCESS  read-create
    STATUS  current	
    DESCRIPTION
        "The filter ID for GOTO action in the new config."
    ::= { fltNewCfgExtendedTableEntry 7 }

fltNewCfgExtendedRadiusWapPersist OBJECT-TYPE
    SYNTAX  INTEGER {
        enabled(1),
        disabled(2)
        }
    MAX-ACCESS  read-create
    STATUS  current	
    DESCRIPTION
        "Enable or disable Radius/WAP persistence."
    ::= { fltNewCfgExtendedTableEntry 8 }

fltNewCfgExtendedPbind OBJECT-TYPE
    SYNTAX  INTEGER {
        enabled(1),
        disabled(2)
        }
    MAX-ACCESS  read-create
    STATUS  current	
    DESCRIPTION
        "Enable or disable filter persistent binding."
    ::= { fltNewCfgExtendedTableEntry 9 }

fltNewCfgExtendedTimeWindow OBJECT-TYPE
    SYNTAX  INTEGER (1..65535)
    MAX-ACCESS  read-create
    STATUS  current
    DESCRIPTION
        "The time window for protocol rate limiting (in seconds)."
    ::= { fltNewCfgExtendedTableEntry 10 }

fltNewCfgExtendedHoldDuration OBJECT-TYPE
    SYNTAX  INTEGER (2..65535)
    MAX-ACCESS  read-create
    STATUS  current
    DESCRIPTION
        "The hold down duration for protocol rate limiting (in minutes)."
    ::= { fltNewCfgExtendedTableEntry 11 }

fltNewCfgExtendedPatternMatch OBJECT-TYPE
    SYNTAX  INTEGER {
        enabled(1),
        disabled(2)
        }
    MAX-ACCESS  read-create
    STATUS  current	
    DESCRIPTION
        "Enable or disable binary pattern matching."
    ::= { fltNewCfgExtendedTableEntry 12 }

fltNewCfgExtendedLayer7DenyMatchAll OBJECT-TYPE
    SYNTAX  INTEGER {
        enabled(1),
        disabled(2)
        }
    MAX-ACCESS  read-create
    STATUS  current
    DESCRIPTION
        "Enable or disable match-all criteria for L7 deny string matching."
    ::= { fltNewCfgExtendedTableEntry 13 }

fltNewCfgExtendedProxyIp OBJECT-TYPE
    SYNTAX  IpAddress
    MAX-ACCESS  read-create
    STATUS  current
    DESCRIPTION
        "The client proxy IP address for NAT and REDIR filter."
        
    ::= { fltNewCfgExtendedTableEntry 14 }

fltNewCfgExtendedLayer7ParseAll OBJECT-TYPE
    SYNTAX  INTEGER {
        enabled(1),
        disabled(2)
        }
    MAX-ACCESS  read-create
    STATUS  current
    DESCRIPTION
        "Enable or disable layer 7 lookup (parsing) of all packets."
    ::= { fltNewCfgExtendedTableEntry 15 }

fltNewCfgExtendedSecurityParseAll OBJECT-TYPE
    SYNTAX  INTEGER {
        enabled(1),
        disabled(2)
        }
    MAX-ACCESS  read-create
    STATUS  current
    DESCRIPTION
        "Enable or disable pattern string lookup (parsing) of all packets."
    ::= { fltNewCfgExtendedTableEntry 16 }

fltNewCfgExtendedPatternMatchGroupBmap OBJECT-TYPE
    SYNTAX  OCTET STRING
    MAX-ACCESS  read-only
    STATUS  current
    DESCRIPTION
        "The pattern match group.
        The pattern match groups are presented in a bitmap format.

         in receiving order:

             OCTET 1  OCTET 2  .....
             xxxxxxxx xxxxxxxx .....
             ||    || |_ pattern match group
             ||    ||
             ||    ||___ pattern match group 8
             ||    |____ pattern match group 7
             ||      .    .   .
             ||_________ pattern match group 2
             |__________ pattern match group 1

         where x : 1 - The represented pattern match group is selected
                   0 - The represented pattern match group is not selected"
    ::= { fltNewCfgExtendedTableEntry 17 }
    
fltNewCfgExtendedAddPatternMatchGroup OBJECT-TYPE
    SYNTAX  Integer32
    MAX-ACCESS  read-create
    STATUS  current
    DESCRIPTION
        "The pattern match group to be added to the 
         security filter. A zero is returned when read."
    ::= { fltNewCfgExtendedTableEntry 18 }

fltNewCfgExtendedRemPatternMatchGroup OBJECT-TYPE
    SYNTAX  Integer32
    MAX-ACCESS  read-create
    STATUS  current
    DESCRIPTION
        "The pattern match group to be to be removed from 
         the security filter. A zero is returned when read."
    ::= { fltNewCfgExtendedTableEntry 19 }

fltNewCfgExtended8021pBitsValue OBJECT-TYPE
    SYNTAX  INTEGER (0..7)
    MAX-ACCESS  read-create
    STATUS  current
    DESCRIPTION
        "The 802.1p bits value to match."
    ::= { fltNewCfgExtendedTableEntry 20 }

fltNewCfgExtended8021pBitsMatch OBJECT-TYPE
    SYNTAX  INTEGER {
        enabled(1),
        disabled(2)
        }
    MAX-ACCESS  read-create
    STATUS  current
    DESCRIPTION
        "Enable or disable matching on 802.1p bits in the packets."
    ::= { fltNewCfgExtendedTableEntry 21 }
 
fltNewCfgExtendedAclIpLength OBJECT-TYPE
    SYNTAX  INTEGER (0..65535)
    MAX-ACCESS  read-create
    STATUS  current 
    DESCRIPTION
        "Set the IP maximum packet length in bytes. A value can be either 0 
         which indicates 'any' length or between 64 and 65535."
    ::= { fltNewCfgExtendedTableEntry 22 }	

fltNewCfgExtendedIdsGroup OBJECT-TYPE
    SYNTAX  Integer32
    MAX-ACCESS  read-create
    STATUS  current
    DESCRIPTION
        "The real server group for IDS load balancing. A value of 0 indicates
	 'none'." 
    ::= { fltNewCfgExtendedTableEntry 23 }
    
fltNewCfgExtendedEgressPip OBJECT-TYPE
    SYNTAX  INTEGER {
        enabled(1),
        disabled(2)
        }
    MAX-ACCESS  read-create
    STATUS  current
    DESCRIPTION
        "Enable or disable pip selection based on egress port/vlan."
    ::= { fltNewCfgExtendedTableEntry 24 }
    
fltNewCfgExtendedDbind OBJECT-TYPE
    SYNTAX  INTEGER {
        enabled(1),
        disabled(2)
        }
    MAX-ACCESS  read-create
    STATUS  current	
    DESCRIPTION
        "Enable or disable filter delayed binding."
    ::= { fltNewCfgExtendedTableEntry 25 }

fltNewCfgExtendedRevBwmContract OBJECT-TYPE
    SYNTAX  Integer32
    MAX-ACCESS  read-create
    STATUS  current
    DESCRIPTION
	"Filt reverse session BWM contract number."
    ::= { fltNewCfgExtendedTableEntry 26 }	

fltNewCfgExtendedReverse OBJECT-TYPE
    SYNTAX  INTEGER {
        enabled(1),
        disabled(2)
        }
    MAX-ACCESS  read-create
    STATUS  current	
    DESCRIPTION
        "Enable or disable creating session for reverse side traffic."
    ::= { fltNewCfgExtendedTableEntry 27 }

fltNewCfgExtendedParseChn OBJECT-TYPE
    SYNTAX  INTEGER {
	enabled(1),
	disabled(2)
	}
    MAX-ACCESS  read-create
    STATUS  current 
    DESCRIPTION
        "Enable or disable chained pgroup match criteria for l7 filtering."	 
    ::= { fltNewCfgExtendedTableEntry 28}


fltNewCfgExtendedRtpBwmContract OBJECT-TYPE
    SYNTAX  Integer32
    MAX-ACCESS  read-create
    STATUS  current
    DESCRIPTION
        "BWM contract for SIP RTP traffic."
    ::= { fltNewCfgExtendedTableEntry 29 }

fltNewCfgExtendedSipParsing OBJECT-TYPE
    SYNTAX  INTEGER {
        enabled(1),
        disabled(2)
        }
    MAX-ACCESS  read-create
    STATUS  current
    DESCRIPTION
        "Enable or disable SIP NAT."
    ::= { fltNewCfgExtendedTableEntry 30 }


    fltNewCfgExtendedSessionMirror  OBJECT-TYPE
    SYNTAX  INTEGER {
        enabled(1),
        disabled(2)
        }
    MAX-ACCESS  read-create
    STATUS  current
    DESCRIPTION
        "Enable or disable session mirroring."
    ::= { fltNewCfgExtendedTableEntry 31 }


fltNewCfgExtendedIpVer OBJECT-TYPE
    SYNTAX  INTEGER{
        ipv4(1),
        ipv6(2)
        }
    MAX-ACCESS  read-create
    STATUS  current
    DESCRIPTION
        "The type of IP address."
    ::= { fltNewCfgExtendedTableEntry 32 }

fltNewCfgExtendedIpv6Sip  OBJECT-TYPE
    SYNTAX   DisplayString (SIZE(0..40))
    MAX-ACCESS  read-create
    STATUS  current
    DESCRIPTION
        "The source IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltNewCfgExtendedTableEntry 33 }

fltNewCfgExtendedIpv6Sprefix   OBJECT-TYPE
    SYNTAX   INTEGER(0..128) 
    MAX-ACCESS  read-create
    STATUS  current
    DESCRIPTION
        "The prefix length associated with source IP address ."
    ::= { fltNewCfgExtendedTableEntry 34 }

fltNewCfgExtendedIpv6Dip   OBJECT-TYPE
    SYNTAX   DisplayString (SIZE(0..40))
    MAX-ACCESS  read-create
    STATUS  current
    DESCRIPTION
        "The destination  IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltNewCfgExtendedTableEntry 35 }

fltNewCfgExtendedIpv6Dprefix   OBJECT-TYPE
    SYNTAX  INTEGER(0..128) 
    MAX-ACCESS  read-create
    STATUS  current
    DESCRIPTION
        "The prefix length associated with destination IP address ."
    ::= {fltNewCfgExtendedTableEntry  36 }

fltNewCfgExtendedHdrHash OBJECT-TYPE
       SYNTAX  INTEGER {
        none(1),
        headerhash(2)
        }
    MAX-ACCESS read-create
    STATUS current
    DESCRIPTION
        "The header hash filter."
    ::= { fltNewCfgExtendedTableEntry 37 }

fltNewCfgExtendedHdrName OBJECT-TYPE
    SYNTAX DisplayString (SIZE(0..31))
    MAX-ACCESS read-create
    STATUS current
    DESCRIPTION
        "The header name of the filter. Headerhash should be
         enabled before header name is configured."
    ::= { fltNewCfgExtendedTableEntry 38 }

fltNewCfgExtendedHdrHashLen OBJECT-TYPE
    SYNTAX  INTEGER (1..255)
    MAX-ACCESS  read-create
    STATUS  current
    DESCRIPTION
        "The header hash length of the filter. Headerhash should be
         enabled before hash length is configured."
    ::= { fltNewCfgExtendedTableEntry 39 }

fltNewCfgExtendedNatIp OBJECT-TYPE
    SYNTAX  IpAddress
    MAX-ACCESS  read-write
    STATUS  current
    DESCRIPTION
        "The nat IP address to be filtered."
    ::= { fltNewCfgExtendedTableEntry 40 }

fltNewCfgExtendedIpv6Nip   OBJECT-TYPE
    SYNTAX   DisplayString (SIZE(0..40))
    MAX-ACCESS  read-write
    STATUS  current
    DESCRIPTION
        "The nat IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltNewCfgExtendedTableEntry 41 }

fltNewCfgExtendedIpv6Proxy  OBJECT-TYPE
    SYNTAX   DisplayString (SIZE(0..40))
    MAX-ACCESS  read-write
    STATUS  current
    DESCRIPTION
        "The proxy IPv6 address to be filtered. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { fltNewCfgExtendedTableEntry 42 }
    
fltNewCfgExtendedL7SipFilt OBJECT-TYPE
    SYNTAX  INTEGER {
        enabled(1),
        disabled(2)
        }
    MAX-ACCESS  read-write
    STATUS  current
    DESCRIPTION
        "Enable/Disable L7 application SIP UDP filtering."
    ::= { fltNewCfgExtendedTableEntry 43 }

fltNewCfgExtendedNatMcastVlan OBJECT-TYPE
    SYNTAX  INTEGER (0..4090)
    MAX-ACCESS  read-write
    STATUS  current
    DESCRIPTION
        "Multicast VLAN."
    ::= { fltNewCfgExtendedTableEntry 44 }

fltNewCfgExtendedNbind OBJECT-TYPE
    SYNTAX  INTEGER {
        enabled(1),
        disabled(2)
    }
    MAX-ACCESS  read-create
    STATUS  current
    DESCRIPTION
        "Enable or disable subnet binding for redirection."
    ::= { fltNewCfgExtendedTableEntry 45 }

fltNewCfgExtendedL3State OBJECT-TYPE
    SYNTAX  INTEGER {
        enabled(1),
        disabled(2)
    }
    MAX-ACCESS  read-create
    STATUS  current
    DESCRIPTION
        "The L3 filter processing state for this filter."
    ::= { fltNewCfgExtendedTableEntry 46 }

-- Filtering Port Table

fltCurCfgPortTable OBJECT-TYPE
    SYNTAX  SEQUENCE OF FltCurCfgPortTableEntry
    MAX-ACCESS  not-accessible
    STATUS  current
    DESCRIPTION
        "The filtering port table in the current configuration block."
    ::= { filterCfg 4 }

fltCurCfgPortTableEntry OBJECT-TYPE
    SYNTAX  FltCurCfgPortTableEntry
    MAX-ACCESS  not-accessible
    STATUS  current
    DESCRIPTION
        "A row in the filtering port table."
    INDEX   { fltCurCfgPortIndx }
    ::= { fltCurCfgPortTable 1 }

FltCurCfgPortTableEntry ::= SEQUENCE {
    fltCurCfgPortIndx         Integer32,
    fltCurCfgPortState        INTEGER,
    fltCurCfgPortFiltBmap     OCTET STRING
    }

fltCurCfgPortIndx OBJECT-TYPE
    SYNTAX  Integer32
    MAX-ACCESS  read-only
    STATUS  current
    DESCRIPTION
        "The port index."
    ::= { fltCurCfgPortTableEntry 1 }

fltCurCfgPortState OBJECT-TYPE
    SYNTAX  INTEGER {
        enabled(1),
        disabled(2)
        }
    MAX-ACCESS  read-only
    STATUS  current
    DESCRIPTION
        "Enable or disable filtering."
    ::= { fltCurCfgPortTableEntry 2 }

fltCurCfgPortFiltBmap OBJECT-TYPE
    SYNTAX  OCTET STRING (SIZE(0..256))
    MAX-ACCESS  read-only
    STATUS  current
    DESCRIPTION
	"The filtering rules applied to the port.  The filtering rules are 
         presented in bitmap format.

	 in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltCurCfgTable)

         where x : 1 - The represented filter rule applied to the port
		   0 - The represented filter rule not applied to the port "
    ::= { fltCurCfgPortTableEntry 3 }

fltNewCfgPortTable OBJECT-TYPE
    SYNTAX  SEQUENCE OF FltNewCfgPortTableEntry
    MAX-ACCESS  not-accessible
    STATUS  current
    DESCRIPTION
        "The filtering port table in the new configuration block."
    ::= { filterCfg 5 }

fltNewCfgPortTableEntry OBJECT-TYPE
    SYNTAX  FltNewCfgPortTableEntry
    MAX-ACCESS  not-accessible
    STATUS  current
    DESCRIPTION
        "A row in the filtering port table."
    INDEX   { fltNewCfgPortIndx }
    ::= { fltNewCfgPortTable 1 }

FltNewCfgPortTableEntry ::= SEQUENCE {
    fltNewCfgPortIndx         Integer32,
    fltNewCfgPortState        INTEGER,
    fltNewCfgPortFiltBmap     OCTET STRING,
    fltNewCfgPortAddFiltRule  Integer32,
    fltNewCfgPortRemFiltRule  Integer32
    }

fltNewCfgPortIndx OBJECT-TYPE
    SYNTAX  Integer32
    MAX-ACCESS  read-only
    STATUS  current
    DESCRIPTION
        "The port index."
    ::= { fltNewCfgPortTableEntry 1 }

fltNewCfgPortState OBJECT-TYPE
    SYNTAX  INTEGER {
        enabled(1),
        disabled(2)
        }
    MAX-ACCESS  read-create
    STATUS  current
    DESCRIPTION
        "Enable or disable filtering."
    ::= { fltNewCfgPortTableEntry 2 }

fltNewCfgPortFiltBmap OBJECT-TYPE
    SYNTAX  OCTET STRING (SIZE(0..256))
    MAX-ACCESS  read-create
    STATUS  current
    DESCRIPTION
        "The filtering rules applied to the port.  The filtering rules
         are presented in bitmap format.

         in receiving order:

	     OCTET 1  OCTET 2  .....
             xxxxxxxx xxxxxxxx ..... 
             ||    || |_ filter 9
             ||    ||  
             ||    ||___ filter 8
             ||    |____ filter 7
             ||      .    .   .
             ||_________ filter 2
             |__________ filter 1 (as index to fltNewCfgTable)

         where x : 1 - The represented filter rule applied to the port
		   0 - The represented filter rule not applied to the port "
    ::= { fltNewCfgPortTableEntry 3 }

fltNewCfgPortAddFiltRule OBJECT-TYPE
    SYNTAX  Integer32
    MAX-ACCESS  read-create
    STATUS  current
    DESCRIPTION
        "This is an action object to add filtering rule to a port. The value 
         specified with this object is the index to the fltNewCfgTable for 
         which filtering rule to be added to the port. The range of the 
         valid index is between 1 and fltCurCfgTableMaxSize. When read, the 
         value '0' is returned always."
    ::= { fltNewCfgPortTableEntry 4 }

fltNewCfgPortRemFiltRule OBJECT-TYPE
    SYNTAX  Integer32
    MAX-ACCESS  read-create
    STATUS  current
    DESCRIPTION
        "This is an action object to remove filtering rule from a port.	The 
         value specified with this object is the index to the fltNewCfgTable 
         for which filtering rule to be removed from the port. The range of 
         the valid index is between 1 and fltCurCfgTableMaxSize.  When read, 
         the value '0' is returned always."
    ::= { fltNewCfgPortTableEntry 5 }

-- URL based BWM filtering table
fltUrlBwmTableMaxSize OBJECT-TYPE
    SYNTAX Integer32
    MAX-ACCESS read-only
    STATUS current
    DESCRIPTION
        "The maximum number of URL based BWM entries."
    ::= { filterCfg 6 }

fltCurCfgUrlBwmTable OBJECT-TYPE
    SYNTAX  SEQUENCE OF FltCurCfgUrlBwmEntry
    MAX-ACCESS  not-accessible
    STATUS  current
    DESCRIPTION
        "The table of URL based BWM for filtering."
    ::= { filterCfg 7 }

fltCurCfgUrlBwmEntry OBJECT-TYPE
    SYNTAX  FltCurCfgUrlBwmEntry
    MAX-ACCESS  not-accessible
    STATUS  current
    DESCRIPTION
        "A row in the URL based BWM filtering table."
    INDEX   { fltCurCfgUrlBwmFltIndex, fltCurCfgUrlBwmUrlId }
    ::= { fltCurCfgUrlBwmTable 1 }

FltCurCfgUrlBwmEntry ::= SEQUENCE {
    fltCurCfgUrlBwmFltIndex        Integer32,
    fltCurCfgUrlBwmUrlId           Integer32,
    fltCurCfgUrlReverseBwmContract Integer32,
    fltCurCfgUrlBwmContract        Integer32  
    }

fltCurCfgUrlBwmFltIndex OBJECT-TYPE
    SYNTAX  Integer32
    MAX-ACCESS  read-only
    STATUS  current
    DESCRIPTION
        "The number of the filter." 
    ::= { fltCurCfgUrlBwmEntry 1 }

fltCurCfgUrlBwmUrlId OBJECT-TYPE  
    SYNTAX  Integer32  
    MAX-ACCESS  read-only  
    STATUS  current  
    DESCRIPTION 
        "The URL Path Identifier."  
    ::= { fltCurCfgUrlBwmEntry 2 } 

fltCurCfgUrlBwmContract OBJECT-TYPE  
    SYNTAX  Integer32  
    MAX-ACCESS  read-only  
    STATUS  current  
    DESCRIPTION 
        "The BW contract."  
    ::= { fltCurCfgUrlBwmEntry 3 } 

fltCurCfgUrlReverseBwmContract OBJECT-TYPE  
    SYNTAX  Integer32  
    MAX-ACCESS  read-only  
    STATUS  current  
    DESCRIPTION 
        "The BWM contract for reverse traffic."  
    ::= { fltCurCfgUrlBwmEntry 4 } 

fltNewCfgUrlBwmTable OBJECT-TYPE
    SYNTAX  SEQUENCE OF FltNewCfgUrlBwmEntry
    MAX-ACCESS  not-accessible
    STATUS  current
    DESCRIPTION
        "The table of URL based BWM for filtering."
    ::= { filterCfg 8 }

fltNewCfgUrlBwmEntry OBJECT-TYPE
    SYNTAX  FltNewCfgUrlBwmEntry
    MAX-ACCESS  not-accessible
    STATUS  current
    DESCRIPTION
        "A row in the URL based BWM filtering table."
    INDEX   { fltNewCfgUrlBwmFltIndex, fltNewCfgUrlBwmUrlId }
    ::= { fltNewCfgUrlBwmTable 1 }

FltNewCfgUrlBwmEntry ::= SEQUENCE {
    fltNewCfgUrlBwmFltIndex        Integer32,
    fltNewCfgUrlBwmUrlId           Integer32,
    fltNewCfgUrlBwmContract        Integer32,
    fltNewCfgUrlReverseBwmContract Integer32,
    fltNewCfgUrlBwmDelete          INTEGER
    }

fltNewCfgUrlBwmFltIndex OBJECT-TYPE
    SYNTAX  Integer32
    MAX-ACCESS  read-only
    STATUS  current
    DESCRIPTION
        "The number of the filter." 
    ::= { fltNewCfgUrlBwmEntry 1 }

fltNewCfgUrlBwmUrlId OBJECT-TYPE  
    SYNTAX  Integer32  
    MAX-ACCESS  read-only  
    STATUS  current  
    DESCRIPTION 
        "The URL Path Identifier."  
    ::= { fltNewCfgUrlBwmEntry 2 } 

fltNewCfgUrlBwmContract OBJECT-TYPE  
    SYNTAX  Integer32  
    MAX-ACCESS  read-create  
    STATUS  current  
    DESCRIPTION 
        "The BW traffic contract."  
    ::= { fltNewCfgUrlBwmEntry 3 } 

fltNewCfgUrlBwmDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { fltNewCfgUrlBwmEntry 4 }

fltNewCfgUrlReverseBwmContract OBJECT-TYPE  
    SYNTAX  Integer32  
    MAX-ACCESS  read-create  
    STATUS  current  
    DESCRIPTION 
        "The BWM contract for reverse traffic."  
    ::= { fltNewCfgUrlBwmEntry 5 }

-- Filter HTTP Redirection Mapping Table

fltCfgHttpRedirMappingTableMaxSize OBJECT-TYPE
    SYNTAX  Integer32 
    MAX-ACCESS  read-only 
    STATUS  current 
    DESCRIPTION 
        "The maximum number of entries in HttpRedirMappingTable." 
    ::= { filterCfg 9 }

fltCurCfgHttpRedirMappingTable OBJECT-TYPE
    SYNTAX  SEQUENCE OF FltCurCfgHttpRedirMappingEntry
    MAX-ACCESS  not-accessible
    STATUS  current
    DESCRIPTION
        "The table of HTTP redirection mapping table."
    ::= { filterCfg 10 }

fltCurCfgHttpRedirMappingEntry OBJECT-TYPE
    SYNTAX  FltCurCfgHttpRedirMappingEntry
    MAX-ACCESS  not-accessible
    STATUS  current
    DESCRIPTION
        "A row in the HTTP redirect mapping table."
    INDEX   { fltCurCfgHttpRedirMappingFilter, 
              fltCurCfgHttpRedirMappingFromStr }
    ::= { fltCurCfgHttpRedirMappingTable 1 }

FltCurCfgHttpRedirMappingEntry ::= SEQUENCE {
    fltCurCfgHttpRedirMappingFilter   Integer32,
    fltCurCfgHttpRedirMappingFromStr  INTEGER,
    fltCurCfgHttpRedirMappingToStr    INTEGER
    }

fltCurCfgHttpRedirMappingFilter OBJECT-TYPE
    SYNTAX  Integer32
    MAX-ACCESS  read-only
    STATUS  current
    DESCRIPTION
        "The filter number."
    ::= { fltCurCfgHttpRedirMappingEntry 1 }

fltCurCfgHttpRedirMappingFromStr OBJECT-TYPE 
    SYNTAX  INTEGER (1..1024)
    MAX-ACCESS  read-only 
    STATUS  current 
    DESCRIPTION 
        "This index is the string ID of Layer7 string table. 
         If HTTP request matches this string, then switch issues 
         a HTTP REDIRECT to client with the 
         fltCurCfgHttpRedirMappingToStr string." 
    ::= { fltCurCfgHttpRedirMappingEntry 2 }

fltCurCfgHttpRedirMappingToStr OBJECT-TYPE  
    SYNTAX  INTEGER (2..1024)
    MAX-ACCESS  read-only  
    STATUS  current  
    DESCRIPTION 
        "The string ID of Layer7 string table. The switch sends 
         HTTP Redirect back to client with this string when HTTP
         request matches the fltCurCfgHttpRedirMappingFromStr string"
    ::= { fltCurCfgHttpRedirMappingEntry 3 } 

fltNewCfgHttpRedirMappingTable OBJECT-TYPE
    SYNTAX  SEQUENCE OF FltNewCfgHttpRedirMappingEntry
    MAX-ACCESS  not-accessible
    STATUS  current
    DESCRIPTION
        "The table of HTTP redirection mapping table."
    ::= { filterCfg 11 }

fltNewCfgHttpRedirMappingEntry OBJECT-TYPE
    SYNTAX  FltNewCfgHttpRedirMappingEntry
    MAX-ACCESS  not-accessible
    STATUS  current
    DESCRIPTION
        "A row in the HTTP redirect mapping table."
    INDEX   { fltNewCfgHttpRedirMappingFilter, 
              fltNewCfgHttpRedirMappingFromStr }
    ::= { fltNewCfgHttpRedirMappingTable 1 }

FltNewCfgHttpRedirMappingEntry ::= SEQUENCE {
    fltNewCfgHttpRedirMappingFilter    Integer32,
    fltNewCfgHttpRedirMappingFromStr   INTEGER,
    fltNewCfgHttpRedirMappingToStr     INTEGER,
    fltNewCfgHttpRedirMappingDelete    INTEGER
    }

fltNewCfgHttpRedirMappingFilter OBJECT-TYPE
    SYNTAX  Integer32
    MAX-ACCESS  read-only
    STATUS  current
    DESCRIPTION
        "The filter number."
    ::= { fltNewCfgHttpRedirMappingEntry 1 }

fltNewCfgHttpRedirMappingFromStr OBJECT-TYPE  
    SYNTAX  INTEGER (1..1024)
    MAX-ACCESS  read-only  
    STATUS  current  
    DESCRIPTION 
        "The string ID of Layer7 string table. If HTTP request 
         matches this string then switch issues a HTTP REDIRECT 
         to client with the fltNewCfgHttpRedirMappingToStr string."  
    ::= { fltNewCfgHttpRedirMappingEntry 2 } 

fltNewCfgHttpRedirMappingToStr OBJECT-TYPE  
    SYNTAX  INTEGER (2..1024)
    MAX-ACCESS  read-create  
    STATUS  current  
    DESCRIPTION 
        "The string ID of Layer7 string table. The switch sends 
         HTTP Redirect back to client with this string when the
         HTTP request matches fltNewCfgHttpRedirMappingFromStr 
         string."
    ::= { fltNewCfgHttpRedirMappingEntry 4 } 

fltNewCfgHttpRedirMappingDelete OBJECT-TYPE
    SYNTAX  INTEGER {
        other(1),
        delete(2)
        }
    MAX-ACCESS  read-create
    STATUS  current
    DESCRIPTION
        "By setting the value to delete(2), the entire row is deleted."
    ::= { fltNewCfgHttpRedirMappingEntry 6 }

-- Global SLB General Configuration

gslbCurCfgGenState OBJECT-TYPE
    SYNTAX  INTEGER {
        on(1),
        off(2)
        }
     MAX-ACCESS  read-only
     STATUS  current
     DESCRIPTION
         "Turn on or off Distributed Server Load Balance."
    ::= { gslbGeneralCfg 1 }

gslbNewCfgGenState OBJECT-TYPE
    SYNTAX  INTEGER {
        on(1),
        off(2)
        }
    MAX-ACCESS  read-write
    STATUS  current
    DESCRIPTION
        "Turn on or off Distributed Server Load Balance."
    ::= { gslbGeneralCfg 2 }


gslbCurCfgGenHttpRedirect OBJECT-TYPE
    SYNTAX  INTEGER {
        enabled(1),
        disabled(2)
        }
    MAX-ACCESS  read-only
    STATUS  current
    DESCRIPTION
        "Enable/Disable HTTP redirect based GSLB in
         the current_configuration block."
    ::= { gslbGeneralCfg 7 }

gslbNewCfgGenHttpRedirect OBJECT-TYPE
    SYNTAX  INTEGER {
        enabled(1),
        disabled(2)
        }
    MAX-ACCESS  read-write
    STATUS  current
    DESCRIPTION
        "Enable/Disable HTTP redirect based GSLB in
         the new_configuration block."
    ::= { gslbGeneralCfg 8 }


gslbCurCfgGenMinco OBJECT-TYPE
    SYNTAX  INTEGER (0..65535)
    MAX-ACCESS  read-only
    STATUS  current
    DESCRIPTION
        "Minmum number of site connections in the current_configuration block."
    ::= { gslbGeneralCfg 13 }

gslbNewCfgGenMinco OBJECT-TYPE
    SYNTAX  INTEGER (0..65535)
    MAX-ACCESS  read-write
    STATUS  current
    DESCRIPTION
        "Minmum number of site connections in the new_configuration block."
    ::= { gslbGeneralCfg 14 }


gslbCurCfgGenUsern OBJECT-TYPE
    SYNTAX  INTEGER {
        enabled(1),
        disabled(2)
        }
    MAX-ACCESS  read-only
    STATUS  current
    DESCRIPTION
        "Enable/Disable HTTP redirect to real server name."
    ::= { gslbGeneralCfg 17 }

gslbNewCfgGenUsern OBJECT-TYPE
    SYNTAX  INTEGER {
        enabled(1),
        disabled(2)
        }
    MAX-ACCESS  read-write
    STATUS  current
    DESCRIPTION
        "Enable/Disable HTTP redirect to real server name."
    ::= { gslbGeneralCfg 18 }


gslbCurCfgGenNoremote OBJECT-TYPE
    SYNTAX INTEGER {
        enabled(1),
        disabled(2)
        }
    MAX-ACCESS read-only
    STATUS current
    DESCRIPTION
        "Enable/Disable no remote real SLB. Enabling will prevent the 
         switch from load balancing incoming traffic to remote reals in
         the event that all local reals are down."
    ::= { gslbGeneralCfg 25 }

gslbNewCfgGenNoremote OBJECT-TYPE
    SYNTAX INTEGER {
        enabled(1),
        disabled(2)
        }
    MAX-ACCESS read-write
    STATUS current
    DESCRIPTION
        "Enable/Disable no remote real SLB. Enabling will prevent the 
         switch from load balancing incoming traffic to remote reals in 
         the event that all local reals are down."
    ::= { gslbGeneralCfg 26 }

gslbCurCfgGenEncrypt OBJECT-TYPE
    SYNTAX INTEGER {
        enabled(1),
        disabled(2)
        }
    MAX-ACCESS read-only
    STATUS current
    DESCRIPTION
        "Enable/Disable encrypting remote site update."
    ::= { gslbGeneralCfg 27 }

gslbNewCfgGenEncrypt OBJECT-TYPE
    SYNTAX INTEGER {
        enabled(1),
        disabled(2)
        }
    MAX-ACCESS read-write
    STATUS current
    DESCRIPTION
        "Enable/Disable encrypting remote site update."
    ::= { gslbGeneralCfg 28 }

gslbCurCfgGenRemSiteUpdatePort OBJECT-TYPE
    SYNTAX  INTEGER (1..65535)
    MAX-ACCESS  read-only
    STATUS  current
    DESCRIPTION
        "TCP port number for remote site updates in
         the current configuration block."
    ::= { gslbGeneralCfg 29 }

gslbNewCfgGenRemSiteUpdatePort OBJECT-TYPE
    SYNTAX  INTEGER (1..65535)
    MAX-ACCESS  read-write
    STATUS  current
    DESCRIPTION
        "TCP port number for remote site updates in
         the new configuration block."
    ::= { gslbGeneralCfg 30 }

gslbCurCfgGenSessUtilCap OBJECT-TYPE
    SYNTAX  INTEGER (1..100)
    MAX-ACCESS  read-only
    STATUS  current
    DESCRIPTION
        "Session utilization capacity threshold in
         the current configuration block."
    ::= { gslbGeneralCfg 31 }

gslbNewCfgGenSessUtilCap OBJECT-TYPE
    SYNTAX  INTEGER (1..100)
    MAX-ACCESS  read-write
    STATUS  current
    DESCRIPTION
        "Session utilization capacity threshold in
         the new configuration block."
    ::= { gslbGeneralCfg 32 }

gslbCurCfgGenCpuUtilCap OBJECT-TYPE
    SYNTAX  INTEGER (1..100)
    MAX-ACCESS  read-only
    STATUS  current
    DESCRIPTION
        "CPU utilization capacity threshold in
         the current configuration block."
    ::= { gslbGeneralCfg 33 }

gslbNewCfgGenCpuUtilCap OBJECT-TYPE
    SYNTAX  INTEGER (1..100)
    MAX-ACCESS  read-write
    STATUS  current
    DESCRIPTION
        "CPU utilization capacity threshold in
         the new configuration block."
    ::= { gslbGeneralCfg 34 }

gslbCurCfgGenSourceIpNetmask OBJECT-TYPE
    SYNTAX IpAddress
    MAX-ACCESS  read-only
    STATUS  current
    DESCRIPTION
        "Source IP netmask for DNS persistence cache in
         the current configuration block."
    ::= { gslbGeneralCfg 35 }

gslbNewCfgGenSourceIpNetmask OBJECT-TYPE
    SYNTAX IpAddress
    MAX-ACCESS  read-write
    STATUS  current
    DESCRIPTION
        "Source IP netmask for DNS persistence cache in
         the new configuration block."
    ::= { gslbGeneralCfg 36 }

gslbCurCfgGenTimeout OBJECT-TYPE
    SYNTAX  INTEGER (1..1440)
    MAX-ACCESS  read-only
    STATUS  current
    DESCRIPTION
        "Timeout in minutes for DNS persistence cache in
         the current configuration block."
    ::= { gslbGeneralCfg 37 }

gslbNewCfgGenTimeout OBJECT-TYPE
    SYNTAX  INTEGER (1..1440)
    MAX-ACCESS  read-write
    STATUS  current
    DESCRIPTION
        "Timeout in minutes for DNS persistence cache in
         the new configuration block."
    ::= { gslbGeneralCfg 38 }

gslbCurCfgGenDnsDirect OBJECT-TYPE
    SYNTAX  INTEGER {
        enabled(1),
        disabled(2)
        }
    MAX-ACCESS  read-only
    STATUS  current
    DESCRIPTION
        "Enable/Disable authoritative DNS direct based Global SLB in
        the current configuration block."
    ::= { gslbGeneralCfg 39 }

gslbNewCfgGenDnsDirect OBJECT-TYPE
    SYNTAX  INTEGER {
        enabled(1),
        disabled(2)
        }
    MAX-ACCESS  read-write
    STATUS  current
    DESCRIPTION
        "Enable/Disable authoritative DNS direct based Global SLB in
        the new configuration block."
    ::= { gslbGeneralCfg 40 }

gslbCurCfgGenRemSiteUpdateVersion OBJECT-TYPE
    SYNTAX  INTEGER (1..5)
    MAX-ACCESS  read-only
    STATUS  current
    DESCRIPTION
        "DSSP version 1,2,3,4 or 5 to send out remote site updates in
        the current configuration block."
    ::= { gslbGeneralCfg 41 }

gslbNewCfgGenRemSiteUpdateVersion OBJECT-TYPE
    SYNTAX  INTEGER (1..5)
    MAX-ACCESS  read-write
    STATUS  current
    DESCRIPTION
        "DSSP version 1,2,3,4 or 5 to send out remote site updates in
        the new configuration block."
    ::= { gslbGeneralCfg 42 }

gslbCurCfgGenHostname OBJECT-TYPE
    SYNTAX  INTEGER {
        enabled(1),
        disabled(2)
        }
    MAX-ACCESS  read-only
    STATUS  current
    DESCRIPTION
        "Enable/Disable virtual service hostname matching in
        the current configuration block."
    ::= { gslbGeneralCfg 43 }

gslbNewCfgGenHostname OBJECT-TYPE
    SYNTAX  INTEGER {
        enabled(1),
        disabled(2)
        }
    MAX-ACCESS  read-write
    STATUS  current
    DESCRIPTION
        "Enable/Disable virtual service hostname matching in
        the new configuration block."
    ::= { gslbGeneralCfg 44 }

gslbCurCfgGenRemSiteUpdateIntervalSeconds OBJECT-TYPE
    SYNTAX  INTEGER (10..7200)
    MAX-ACCESS  read-only
    STATUS  current
    DESCRIPTION
        "The time interval in seconds for updating remote site status
         in the current_configuration block."
    ::= { gslbGeneralCfg 45 }

gslbNewCfgGenRemSiteUpdateIntervalSeconds OBJECT-TYPE
    SYNTAX  INTEGER (10..7200)
    MAX-ACCESS  read-write
    STATUS  current
    DESCRIPTION
        "The time interval in seconds for updating remote site status
         in the new_configuration block."
    ::= { gslbGeneralCfg 46 }

gslbCurCfgGenNoResp OBJECT-TYPE
    SYNTAX  INTEGER (1..5)
    MAX-ACCESS  read-only
    STATUS  current
    DESCRIPTION
        "DNS response code when no server is returned for the current_configuration block."
    ::= { gslbGeneralCfg 47 }

gslbNewCfgGenNoResp OBJECT-TYPE
    SYNTAX  INTEGER (1..5)
    MAX-ACCESS  read-write
    STATUS  current
    DESCRIPTION
        "DNS response code when no server is returned for the new_configuration block."
    ::= { gslbGeneralCfg 48 }

gslbCurCfgProximityTime OBJECT-TYPE
    SYNTAX  INTEGER (1..24)
    MAX-ACCESS  read-only
    STATUS  current
    DESCRIPTION
        "Current_configuration block maximum time allowed for Client Proximity calculation."
    ::= { gslbGeneralCfg 49 }

gslbNewCfgProximityTime OBJECT-TYPE
    SYNTAX  INTEGER (1..24)
    MAX-ACCESS  read-write
    STATUS  current
    DESCRIPTION
        "New_configuration block maximum time allowed for Client Proximity calculation."
    ::= { gslbGeneralCfg 50 }

gslbCurCfgProximityMask OBJECT-TYPE
    SYNTAX  INTEGER (8..24)
    MAX-ACCESS  read-only
    STATUS  current
    DESCRIPTION
        "Client Proximity default netmask of the client cache for the current_configuration block."
    ::= { gslbGeneralCfg 51 }

gslbNewCfgProximityMask OBJECT-TYPE
    SYNTAX  INTEGER (8..24)
    MAX-ACCESS  read-write
    STATUS  current
    DESCRIPTION
        "Client Proximity default netmask of the client cache for the new_configuration block."
    ::= { gslbGeneralCfg 52 }

gslbCurCfgProximityAge OBJECT-TYPE
    SYNTAX  INTEGER (0..10080)
    MAX-ACCESS  read-only
    STATUS  current
    DESCRIPTION
        "Client Proximity Age timeout of each client network entries for the current_configuration block."
    ::= { gslbGeneralCfg 53 }

gslbNewCfgProximityAge OBJECT-TYPE
    SYNTAX  INTEGER (0..10080)
    MAX-ACCESS  read-write
    STATUS  current
    DESCRIPTION
        "Client Proximity Age timeout of each client network entries for the new_configuration block."
    ::= { gslbGeneralCfg 54 }

gslbCurCfgGenSourceIpv6Prefix OBJECT-TYPE
    SYNTAX INTEGER (0..128)
    MAX-ACCESS  read-only
    STATUS  current
    DESCRIPTION
        "Source IPv6 prefix for DNS persistence cache in
         the current configuration block."
    ::= { gslbGeneralCfg 55 }

gslbNewCfgGenSourceIpv6Prefix OBJECT-TYPE
    SYNTAX INTEGER (0..128)
    MAX-ACCESS  read-write
    STATUS  current
    DESCRIPTION
        "Source IPv6 prefix for DNS persistence cache in
         the new configuration block."
    ::= { gslbGeneralCfg 56 }


-- Global SLB Remote Site Configuration

gslbRemSiteTableMaxSize OBJECT-TYPE
    SYNTAX  Integer32
    MAX-ACCESS  read-only
    STATUS  current
    DESCRIPTION
        "The maximum number of GSLB remote sites."
    ::= { gslbSitesCfg 1 }

gslbCurCfgRemSiteTable OBJECT-TYPE
    SYNTAX  SEQUENCE OF GslbCurCfgRemSiteTableEntry
    MAX-ACCESS  not-accessible
    STATUS  current
    DESCRIPTION
        "The GSLB remote site table in the current configuration block."
    ::= { gslbSitesCfg 2 }

gslbCurCfgRemSiteTableEntry OBJECT-TYPE
    SYNTAX  GslbCurCfgRemSiteTableEntry
    MAX-ACCESS  not-accessible
    STATUS  current
    DESCRIPTION
        "A row in the GSLB remote site table."
    INDEX   { gslbCurCfgRemSiteIndx }
    ::= { gslbCurCfgRemSiteTable 1 }

GslbCurCfgRemSiteTableEntry ::= SEQUENCE {
    gslbCurCfgRemSiteIndx        Integer32,
    gslbCurCfgRemSitePrimaryIp   IpAddress,
    gslbCurCfgRemSiteSecondaryIp IpAddress,
    gslbCurCfgRemSiteState       INTEGER,
    gslbCurCfgRemSiteUpdate      INTEGER,
    gslbCurCfgRemSiteName        DisplayString,
    gslbCurCfgRemSitePrimaryIPVer  INTEGER,
    gslbCurCfgRemSitePrimaryIp6  DisplayString,
    gslbCurCfgRemSiteSecondaryIPVer  INTEGER,
    gslbCurCfgRemSiteSecondaryIp6 DisplayString
    }

gslbCurCfgRemSiteIndx OBJECT-TYPE
    SYNTAX  Integer32
    MAX-ACCESS  read-only
    STATUS  current
    DESCRIPTION
        "The GSLB remote site table index."
    ::= { gslbCurCfgRemSiteTableEntry 1 }

gslbCurCfgRemSitePrimaryIp OBJECT-TYPE
    SYNTAX  IpAddress
    MAX-ACCESS  read-only
    STATUS  current
    DESCRIPTION
        "The primary IP address of the remote site in the 
         current_configuration block."
    ::= { gslbCurCfgRemSiteTableEntry 2 }

gslbCurCfgRemSiteSecondaryIp OBJECT-TYPE
    SYNTAX  IpAddress
    MAX-ACCESS  read-only
    STATUS  current
    DESCRIPTION
        "The secondary IP address of the remote site in the 
	 current_configuration block."
    ::= { gslbCurCfgRemSiteTableEntry 3 }

gslbCurCfgRemSiteState OBJECT-TYPE
    SYNTAX  INTEGER {
        enabled(1),
        disabled(2)
        }
    MAX-ACCESS  read-only
    STATUS  current
    DESCRIPTION
        "Enable/Disable GSLB for the remote site in the 
         current_configuration block."
    ::= { gslbCurCfgRemSiteTableEntry 4 }

gslbCurCfgRemSiteUpdate OBJECT-TYPE
    SYNTAX  INTEGER {
        enabled(1),
        disabled(2)
        }
    MAX-ACCESS  read-only
    STATUS  current
    DESCRIPTION
        "Enable/Disable GSLB for the remote site status update in the 
         current_configuration block."
    ::= { gslbCurCfgRemSiteTableEntry 5 }

gslbCurCfgRemSiteName OBJECT-TYPE
    SYNTAX DisplayString (SIZE(0..31))
    MAX-ACCESS read-only
    STATUS current
    DESCRIPTION
	"The name of the GSLB remote site."
    ::= { gslbCurCfgRemSiteTableEntry 6 }


gslbCurCfgRemSitePrimaryIPVer OBJECT-TYPE
    SYNTAX  INTEGER{
        ipv4(1),
        ipv6(2)
        }
    MAX-ACCESS  read-only
    STATUS  current
    DESCRIPTION
        "The primary IP address version of the remote site."
    ::= { gslbCurCfgRemSiteTableEntry 8 }

gslbCurCfgRemSitePrimaryIp6 OBJECT-TYPE
   SYNTAX DisplayString (SIZE(0..40))
    MAX-ACCESS  read-only
    STATUS  current
    DESCRIPTION
    "  Primary IPV6 address of the remote site
       Address should be 4-byte haxadecimal colon notation. Valid IPv6 address should be in
       any of the following forms xxxx:xxxx:xxxx:xxxx:xxxx:xxxx:xxxx:xxxx or xxxx::xxxx:xxxx:xxxx:xxxx or ::xxxx "
   ::= { gslbCurCfgRemSiteTableEntry 9 }

gslbCurCfgRemSiteSecondaryIPVer OBJECT-TYPE
    SYNTAX  INTEGER{
        ipv4(1),
        ipv6(2)
        }
    MAX-ACCESS  read-only
    STATUS  current
    DESCRIPTION
        "The secondary IP address version of the remote site."
    ::= { gslbCurCfgRemSiteTableEntry 10 }

gslbCurCfgRemSiteSecondaryIp6 OBJECT-TYPE
   SYNTAX DisplayString (SIZE(0..40))
    MAX-ACCESS  read-only
    STATUS  current
    DESCRIPTION
    "  Secondary IPV6 address of the remote site
       Address should be 4-byte haxadecimal colon notation. Valid IPv6 address should be in
       any of the following forms xxxx:xxxx:xxxx:xxxx:xxxx:xxxx:xxxx:xxxx or xxxx::xxxx:xxxx:xxxx:xxxx or ::xxxx "
   ::= { gslbCurCfgRemSiteTableEntry 11 }

gslbNewCfgRemSiteTable OBJECT-TYPE
    SYNTAX  SEQUENCE OF GslbNewCfgRemSiteTableEntry
    MAX-ACCESS  not-accessible
    STATUS  current
    DESCRIPTION
        "The GSLB remote site table in the current configuration block."
    ::= { gslbSitesCfg 3 }

gslbNewCfgRemSiteTableEntry OBJECT-TYPE
    SYNTAX  GslbNewCfgRemSiteTableEntry
    MAX-ACCESS  not-accessible
    STATUS  current
    DESCRIPTION
        "A row in the GSLB remote site table in the current configuration block."
    INDEX   { gslbNewCfgRemSiteIndx }
    ::= { gslbNewCfgRemSiteTable 1 }

GslbNewCfgRemSiteTableEntry ::= SEQUENCE {
    gslbNewCfgRemSiteIndx        Integer32,
    gslbNewCfgRemSitePrimaryIp   IpAddress,
    gslbNewCfgRemSiteSecondaryIp IpAddress,
    gslbNewCfgRemSiteState       INTEGER,
    gslbNewCfgRemSiteUpdate      INTEGER,
    gslbNewCfgRemSiteDelete      INTEGER,
    gslbNewCfgRemSiteName        DisplayString,
    gslbNewCfgRemSitePrimaryIPVer  INTEGER,
    gslbNewCfgRemSitePrimaryIp6  DisplayString,
    gslbNewCfgRemSiteSecondaryIPVer  INTEGER,
    gslbNewCfgRemSiteSecondaryIp6 DisplayString
    }

gslbNewCfgRemSiteIndx OBJECT-TYPE
    SYNTAX  Integer32
    MAX-ACCESS  read-only
    STATUS  current
    DESCRIPTION
        "The GSLB remote site table index."
    ::= { gslbNewCfgRemSiteTableEntry 1 }

gslbNewCfgRemSitePrimaryIp OBJECT-TYPE
    SYNTAX  IpAddress
    MAX-ACCESS  read-create
    STATUS  current
    DESCRIPTION
        "The primary IP address of the remote site in the new_configuration 
         block."
    ::= { gslbNewCfgRemSiteTableEntry 2 }

gslbNewCfgRemSiteSecondaryIp OBJECT-TYPE
    SYNTAX  IpAddress
    MAX-ACCESS  read-create
    STATUS  current
    DESCRIPTION
        "The secondary IP address of the remote site in the new_configuration 
         block."
    ::= { gslbNewCfgRemSiteTableEntry 3 }

gslbNewCfgRemSiteState OBJECT-TYPE
    SYNTAX  INTEGER {
        enabled(1),
        disabled(2)
        }
    MAX-ACCESS  read-create
    STATUS  current
    DESCRIPTION
        "Enable/Disable GSLB for the remote site in the new_configuration 
         block."
    ::= { gslbNewCfgRemSiteTableEntry 4 }

gslbNewCfgRemSiteUpdate OBJECT-TYPE
    SYNTAX  INTEGER {
        enabled(1),
        disabled(2)
        }
    MAX-ACCESS  read-create
    STATUS  current
    DESCRIPTION
        "Enable/Disable GSLB for the remote site status update in the 
         new_configuration block."
    ::= { gslbNewCfgRemSiteTableEntry 5 }

gslbNewCfgRemSiteDelete OBJECT-TYPE
    SYNTAX INTEGER {
        other(1),
        delete(2)
        }
    MAX-ACCESS read-create
    STATUS current
    DESCRIPTION
        "By setting the value to delete(2), the entire row is deleted."
    ::= { gslbNewCfgRemSiteTableEntry 6 }

gslbNewCfgRemSiteName OBJECT-TYPE
    SYNTAX DisplayString (SIZE(0..31))
    MAX-ACCESS read-create
    STATUS current
    DESCRIPTION
	"The name of the GSLB remote site."
    ::= { gslbNewCfgRemSiteTableEntry 7 }


gslbNewCfgRemSitePrimaryIPVer OBJECT-TYPE
    SYNTAX  INTEGER{
        ipv4(1),
        ipv6(2)
        }
    MAX-ACCESS  read-only
    STATUS  current
    DESCRIPTION
        "The primary IP address version of the remote site."
    ::= { gslbNewCfgRemSiteTableEntry 9 }

gslbNewCfgRemSitePrimaryIp6 OBJECT-TYPE
   SYNTAX DisplayString (SIZE(0..40))
    MAX-ACCESS  read-create
    STATUS  current
    DESCRIPTION
    "  Primary IPV6 address of the remote site
       Address should be 4-byte haxadecimal colon notation. Valid IPv6 address should be in
       any of the following forms xxxx:xxxx:xxxx:xxxx:xxxx:xxxx:xxxx:xxxx or xxxx::xxxx:xxxx:xxxx:xxxx or ::xxxx "
   ::= { gslbNewCfgRemSiteTableEntry 10 }

gslbNewCfgRemSiteSecondaryIPVer OBJECT-TYPE
    SYNTAX  INTEGER{
        ipv4(1),
        ipv6(2)
        }
    MAX-ACCESS  read-only
    STATUS  current
    DESCRIPTION
        "The secondary IP address version of the remote site."
    ::= { gslbNewCfgRemSiteTableEntry 11 }

gslbNewCfgRemSiteSecondaryIp6 OBJECT-TYPE
   SYNTAX DisplayString (SIZE(0..40))
    MAX-ACCESS  read-create
    STATUS  current
    DESCRIPTION
    "  Secondary IPV6 address of the remote site
       Address should be 4-byte haxadecimal colon notation. Valid IPv6 address should be in
       any of the following forms xxxx:xxxx:xxxx:xxxx:xxxx:xxxx:xxxx:xxxx or xxxx::xxxx:xxxx:xxxx:xxxx or ::xxxx "
   ::= { gslbNewCfgRemSiteTableEntry 12 }

-- Global SLB Enhanced Network Configuration

gslbEnhNetworkTableMaxSize OBJECT-TYPE
    SYNTAX  Integer32
    MAX-ACCESS  read-only
    STATUS  current
    DESCRIPTION
        "The maximum number of Global SLB networks."
    ::= { gslbEnhNetworkCfg 1 }

gslbCurCfgEnhNetworkTable OBJECT-TYPE
    SYNTAX SEQUENCE OF GslbCurCfgEnhNetworkTableEntry
    MAX-ACCESS not-accessible
    STATUS current
    DESCRIPTION
        "The table of network preference in the current_config."
    ::= { gslbEnhNetworkCfg 2 }

gslbCurCfgEnhNetworkTableEntry OBJECT-TYPE
    SYNTAX GslbCurCfgEnhNetworkTableEntry
    MAX-ACCESS not-accessible
    STATUS current
    DESCRIPTION
        "The table about a network preference entry configuration."
    INDEX { gslbCurCfgEnhNetworkIndx }
    ::= { gslbCurCfgEnhNetworkTable 1 }

GslbCurCfgEnhNetworkTableEntry ::= SEQUENCE {
    gslbCurCfgEnhNetworkIndx       Integer32,
    gslbCurCfgEnhNetworkState      INTEGER,
    gslbCurCfgEnhNetworkSourceIp   IpAddress,
    gslbCurCfgEnhNetworkNetMask    IpAddress,
    gslbCurCfgEnhNetworkVirtServer OCTET STRING,
    gslbCurCfgEnhNetworkRemRealServer OCTET STRING,
    gslbCurCfgEnhNetworkSourceIpV6  	     DisplayString,
    gslbCurCfgEnhNetworkVer      	     INTEGER,
    gslbCurCfgEnhNetworkSprefix      	     INTEGER

    }

gslbCurCfgEnhNetworkIndx  OBJECT-TYPE
    SYNTAX Integer32
    MAX-ACCESS read-only
    STATUS current
    DESCRIPTION
        "The current network preference table index."
    ::= { gslbCurCfgEnhNetworkTableEntry 1 }

gslbCurCfgEnhNetworkState OBJECT-TYPE
    SYNTAX  INTEGER {
        enabled(1),
        disabled(2)
        }
    MAX-ACCESS  read-only
    STATUS  current
    DESCRIPTION
        "Enable/Disable Global SLB for the network in the
         current_configuration block."
    ::= { gslbCurCfgEnhNetworkTableEntry 2 }

gslbCurCfgEnhNetworkSourceIp OBJECT-TYPE
    SYNTAX IpAddress
    MAX-ACCESS read-only
    STATUS current
    DESCRIPTION
        "The Source IP address of the network preference table."
    ::= { gslbCurCfgEnhNetworkTableEntry 3 }

gslbCurCfgEnhNetworkNetMask OBJECT-TYPE
    SYNTAX IpAddress
    MAX-ACCESS read-only
    STATUS current
    DESCRIPTION
        "The Net mask of the network preference table."
    ::= { gslbCurCfgEnhNetworkTableEntry 4 }

gslbCurCfgEnhNetworkVirtServer OBJECT-TYPE
    SYNTAX OCTET STRING
    MAX-ACCESS read-only
    STATUS current
    DESCRIPTION
        "The virtual servers in the network.
         The virtual servers are presented in bitmap format.

         in receiving order:

             OCTET 1  OCTET 2  .....
             xxxxxxxx xxxxxxxx .....
             |     || |_ server 9
             |     ||
             |     ||___ server 8
             |     |____ server 7
             |       .    .   .
             |__________ server 1

         where x : 1 - The represented virtual server belongs to the network
                   0 - The represented virtual server does not belong to the network"
    ::= { gslbCurCfgEnhNetworkTableEntry 5 }

gslbCurCfgEnhNetworkRemRealServer OBJECT-TYPE
    SYNTAX OCTET STRING
    MAX-ACCESS read-only
    STATUS current
    DESCRIPTION
        "The remote real servers in the network.
         The remote real servers are presented in bitmap format.

         in receiving order:

             OCTET 1  OCTET 2  .....
             xxxxxxxx xxxxxxxx .....
             |     || |_ server 9
             |     ||
             |     ||___ server 8
             |     |____ server 7
             |       .    .   .
             |__________ server 1

         where x : 1 - The represented remote real server belongs to the network
                   0 - The represented remote real server does not belong to the network"
    ::= { gslbCurCfgEnhNetworkTableEntry 6 }


gslbCurCfgEnhNetworkSourceIpV6 OBJECT-TYPE
   SYNTAX DisplayString (SIZE(0..40))
    MAX-ACCESS read-only
    STATUS  current
    DESCRIPTION
    "  The Source IPV6 address of the network table
       Address should be 4-byte haxadecimal colon notation. Valid IPv6 address should be in
       any of the following forms xxxx:xxxx:xxxx:xxxx:xxxx:xxxx:xxxx:xxxx or xxxx::xxxx:xxxx:xxxx:xxxx or ::xxxx "
   ::= { gslbCurCfgEnhNetworkTableEntry 7 }

gslbCurCfgEnhNetworkVer OBJECT-TYPE
    SYNTAX  INTEGER{
        ipv4(1),
        ipv6(2)
        }
    MAX-ACCESS  read-only
    STATUS  current
    DESCRIPTION
        "The secondary IP address version of the remote site."
    ::= { gslbCurCfgEnhNetworkTableEntry 8 }

gslbCurCfgEnhNetworkSprefix OBJECT-TYPE
    SYNTAX   INTEGER(0..128) 
    MAX-ACCESS read-only
    STATUS  current
    DESCRIPTION
        "The prefix length associated with the source IPV6 address of the network table."
    ::= { gslbCurCfgEnhNetworkTableEntry 9 }

gslbNewCfgEnhNetworkTable OBJECT-TYPE
    SYNTAX SEQUENCE OF GslbNewCfgEnhNetworkTableEntry
    MAX-ACCESS not-accessible
    STATUS current
    DESCRIPTION
        "The table of network preference in the new_config."
    ::= { gslbEnhNetworkCfg 3 }

gslbNewCfgEnhNetworkTableEntry OBJECT-TYPE
    SYNTAX GslbNewCfgEnhNetworkTableEntry
    MAX-ACCESS not-accessible
    STATUS current
    DESCRIPTION
        "The table about a network preference entry configuration."
    INDEX { gslbNewCfgEnhNetworkIndx }
    ::= { gslbNewCfgEnhNetworkTable 1 }

GslbNewCfgEnhNetworkTableEntry ::= SEQUENCE {
    gslbNewCfgEnhNetworkIndx       Integer32,
    gslbNewCfgEnhNetworkState      INTEGER,
    gslbNewCfgEnhNetworkSourceIp   IpAddress,
    gslbNewCfgEnhNetworkNetMask    IpAddress,
    gslbNewCfgEnhNetworkDelete     INTEGER,
    gslbNewCfgEnhNetworkVirtServer           OCTET STRING,
    gslbNewCfgEnhNetworkRemRealServer        OCTET STRING,
    gslbNewCfgEnhNetworkAddVirtServer        Integer32,
    gslbNewCfgEnhNetworkRemoveVirtServer     Integer32,
    gslbNewCfgEnhNetworkAddRemRealServer     Integer32,
    gslbNewCfgEnhNetworkRemoveRemRealServer  Integer32,
    gslbNewCfgEnhNetworkSourceIpV6  	     DisplayString,
    gslbNewCfgEnhNetworkVer      	     INTEGER,
    gslbNewCfgEnhNetworkSprefix      	     INTEGER
    }

gslbNewCfgEnhNetworkIndx  OBJECT-TYPE
    SYNTAX Integer32
    MAX-ACCESS read-only
    STATUS current
    DESCRIPTION
        "The new network preference table index."
    ::= { gslbNewCfgEnhNetworkTableEntry 1 }

gslbNewCfgEnhNetworkState OBJECT-TYPE
    SYNTAX  INTEGER {
        enabled(1),
        disabled(2)
        }
    MAX-ACCESS  read-create
    STATUS  current
    DESCRIPTION
        "Enable/Disable Global SLB for the network in
        the new_configuration block."
    ::= { gslbNewCfgEnhNetworkTableEntry 2 }

gslbNewCfgEnhNetworkSourceIp OBJECT-TYPE
    SYNTAX IpAddress
    MAX-ACCESS read-create
    STATUS current
    DESCRIPTION
        "The Source IP address of the network table."
    ::= { gslbNewCfgEnhNetworkTableEntry 3 }

gslbNewCfgEnhNetworkNetMask OBJECT-TYPE
    SYNTAX IpAddress
    MAX-ACCESS read-create
    STATUS current
    DESCRIPTION
        "The Net mask of the network preference table."
    ::= { gslbNewCfgEnhNetworkTableEntry 4 }

gslbNewCfgEnhNetworkDelete OBJECT-TYPE
    SYNTAX INTEGER {
        other(1),
        delete(2)
        }
    MAX-ACCESS read-create
    STATUS current
    DESCRIPTION
        "By setting the value to delete(2), the entire row is deleted."
    ::= { gslbNewCfgEnhNetworkTableEntry 5}

gslbNewCfgEnhNetworkVirtServer OBJECT-TYPE
    SYNTAX OCTET STRING
    MAX-ACCESS read-only
    STATUS current
    DESCRIPTION
        "The virtual servers in the network.
         The virtual servers are presented in bitmap format.

         in receiving order:

             OCTET 1  OCTET 2  .....
             xxxxxxxx xxxxxxxx .....
             |     || |_ server 9
             |     ||
             |     ||___ server 8
             |     |____ server 7
             |       .    .   .
             |__________ server 1

         where x : 1 - The represented virtual server belongs to the network
                   0 - The represented virtual server does not belong to the network"
    ::= { gslbNewCfgEnhNetworkTableEntry 6 }

gslbNewCfgEnhNetworkRemRealServer OBJECT-TYPE
    SYNTAX OCTET STRING
    MAX-ACCESS read-only
    STATUS current
    DESCRIPTION
        "The remote real servers in the network.
         The remote real servers are presented in bitmap format.

         in receiving order:

             OCTET 1  OCTET 2  .....
             xxxxxxxx xxxxxxxx .....
             |     || |_ server 9
             |     ||
             |     ||___ server 8
             |     |____ server 7
             |       .    .   .
             |__________ server 1

         where x : 1 - The represented remote real server belongs to the network
                   0 - The represented remote real server does not belong to the network"
    ::= { gslbNewCfgEnhNetworkTableEntry 7 }

gslbNewCfgEnhNetworkAddVirtServer OBJECT-TYPE
    SYNTAX  Integer32
    MAX-ACCESS  read-create
    STATUS  current
    DESCRIPTION
        "The virtual server to be added to the network. When read, 0 is returned."
    ::= { gslbNewCfgEnhNetworkTableEntry 8 }

gslbNewCfgEnhNetworkRemoveVirtServer OBJECT-TYPE
    SYNTAX  Integer32
    MAX-ACCESS  read-create
    STATUS  current
    DESCRIPTION
        "The virtual server to be removed from the network. When read, 0 is returned."
    ::= { gslbNewCfgEnhNetworkTableEntry 9 }

gslbNewCfgEnhNetworkAddRemRealServer OBJECT-TYPE
    SYNTAX  Integer32
    MAX-ACCESS  read-create
    STATUS  current
    DESCRIPTION
        "The remote real server to be added to the network. When read, 0 is returned."
    ::= { gslbNewCfgEnhNetworkTableEntry 10 }

gslbNewCfgEnhNetworkRemoveRemRealServer OBJECT-TYPE
    SYNTAX  Integer32
    MAX-ACCESS  read-create
    STATUS  current
    DESCRIPTION
        "The remote real server to be removed from the network. When read, 0 is returned."
    ::= { gslbNewCfgEnhNetworkTableEntry 11 }

gslbNewCfgEnhNetworkSourceIpV6 OBJECT-TYPE
   SYNTAX DisplayString (SIZE(0..40))
    MAX-ACCESS  read-create
    STATUS  current
    DESCRIPTION
    "  The Source IPV6 address of the network table
       Address should be 4-byte haxadecimal colon notation. Valid IPv6 address should be in
       any of the following forms xxxx:xxxx:xxxx:xxxx:xxxx:xxxx:xxxx:xxxx or xxxx::xxxx:xxxx:xxxx:xxxx or ::xxxx "
   ::= { gslbNewCfgEnhNetworkTableEntry 12 }

gslbNewCfgEnhNetworkVer OBJECT-TYPE
    SYNTAX  INTEGER{
        ipv4(1),
        ipv6(2)
        }
    MAX-ACCESS  read-only
    STATUS  current
    DESCRIPTION
        "The secondary IP address version of the remote site."
    ::= { gslbNewCfgEnhNetworkTableEntry 13 }

gslbNewCfgEnhNetworkSprefix OBJECT-TYPE
    SYNTAX   INTEGER(0..128) 
    MAX-ACCESS  read-create
    STATUS  current
    DESCRIPTION
        "The prefix length associated with the source IPV6 address of the network table."
    ::= { gslbNewCfgEnhNetworkTableEntry 14 }

-- Global SLB Rule Configuration

gslbRuleTableMaxSize OBJECT-TYPE
    SYNTAX  Integer32
    MAX-ACCESS  read-only
    STATUS  current
    DESCRIPTION
        "The maximum number of Global SLB rules."
    ::= { gslbRuleCfg 1 }

gslbCurCfgRuleTable OBJECT-TYPE
    SYNTAX SEQUENCE OF GslbCurCfgRuleTableEntry
    MAX-ACCESS not-accessible
    STATUS current
    DESCRIPTION
        "The rule table in the current configuration block."
    ::= { gslbRuleCfg 2 }

gslbCurCfgRuleTableEntry OBJECT-TYPE
    SYNTAX GslbCurCfgRuleTableEntry
    MAX-ACCESS not-accessible
    STATUS current
    DESCRIPTION
        "An entry in the rule table in the current configuration block."
    INDEX { gslbCurCfgRuleIndx }
    ::= { gslbCurCfgRuleTable 1 }

GslbCurCfgRuleTableEntry ::= SEQUENCE {
    gslbCurCfgRuleIndx         Integer32,
    gslbCurCfgRuleState        INTEGER,
    gslbCurCfgRuleStartHour    INTEGER,
    gslbCurCfgRuleStartMin     INTEGER,
    gslbCurCfgRuleEndHour      INTEGER,
    gslbCurCfgRuleEndMin       INTEGER,
    gslbCurCfgRuleTTL          INTEGER,
    gslbCurCfgRuleRR           INTEGER,
    gslbCurCfgRuleDname        DisplayString
    }

gslbCurCfgRuleIndx  OBJECT-TYPE
    SYNTAX Integer32
    MAX-ACCESS read-only
    STATUS current
    DESCRIPTION
        "The rule table index in the current configuration block."
    ::= { gslbCurCfgRuleTableEntry 1 }

gslbCurCfgRuleState OBJECT-TYPE
    SYNTAX  INTEGER {
        enabled(1),
        disabled(2)
        }
    MAX-ACCESS  read-only
    STATUS  current
    DESCRIPTION
        "Enable/Disable the rule in
         the current configuration block."
    ::= { gslbCurCfgRuleTableEntry 2 }

gslbCurCfgRuleStartHour OBJECT-TYPE
    SYNTAX  INTEGER (0..23)
    MAX-ACCESS  read-only
    STATUS  current
    DESCRIPTION
        "Start hour in 24-hour format for the rule in
         the current configuration block."
    ::= { gslbCurCfgRuleTableEntry 3 }

gslbCurCfgRuleStartMin OBJECT-TYPE
    SYNTAX  INTEGER (0..59)
    MAX-ACCESS  read-only
    STATUS  current
    DESCRIPTION
        "Start minutes for the rule in
         the current configuration block."
    ::= { gslbCurCfgRuleTableEntry 4 }

gslbCurCfgRuleEndHour OBJECT-TYPE
    SYNTAX  INTEGER (0..23)
    MAX-ACCESS  read-only
    STATUS  current
    DESCRIPTION
        "End hour in 24-hour format for the rule in
         the current configuration block."
    ::= { gslbCurCfgRuleTableEntry 5 }

gslbCurCfgRuleEndMin OBJECT-TYPE
    SYNTAX  INTEGER (0..59)
    MAX-ACCESS  read-only
    STATUS  current
    DESCRIPTION
        "End minutes for the rule in
         the current configuration block."
    ::= { gslbCurCfgRuleTableEntry 6 }

gslbCurCfgRuleTTL OBJECT-TYPE
    SYNTAX  INTEGER (0..65535)
    MAX-ACCESS  read-only
    STATUS  current
    DESCRIPTION
        "Time to live in seconds of DNS resource records for the rule in
         the current configuration block."
    ::= { gslbCurCfgRuleTableEntry 7 }

gslbCurCfgRuleRR OBJECT-TYPE
    SYNTAX  INTEGER (1..10)
    MAX-ACCESS  read-only
    STATUS  current
    DESCRIPTION
        "DNS resource records in DNS response for the rule in
         the current configuration block."
    ::= { gslbCurCfgRuleTableEntry 8 }

gslbCurCfgRuleDname OBJECT-TYPE
    SYNTAX DisplayString (SIZE(0..64))
    MAX-ACCESS read-only
    STATUS current
    DESCRIPTION
        "Network preference domain name for rule."
    ::= { gslbCurCfgRuleTableEntry 9 }

gslbNewCfgRuleTable OBJECT-TYPE
    SYNTAX SEQUENCE OF GslbNewCfgRuleTableEntry
    MAX-ACCESS not-accessible
    STATUS current
    DESCRIPTION
        "The rule table in the new configuration block."
    ::= { gslbRuleCfg 3 }

gslbNewCfgRuleTableEntry OBJECT-TYPE
    SYNTAX GslbNewCfgRuleTableEntry
    MAX-ACCESS not-accessible
    STATUS current
    DESCRIPTION
        "An entry in the rule table in the new configuration block."
    INDEX { gslbNewCfgRuleIndx }
    ::= { gslbNewCfgRuleTable 1 }

GslbNewCfgRuleTableEntry ::= SEQUENCE {
    gslbNewCfgRuleIndx         Integer32,
    gslbNewCfgRuleState        INTEGER,
    gslbNewCfgRuleStartHour    INTEGER,
    gslbNewCfgRuleStartMin     INTEGER,
    gslbNewCfgRuleEndHour      INTEGER,
    gslbNewCfgRuleEndMin       INTEGER,
    gslbNewCfgRuleTTL          INTEGER,
    gslbNewCfgRuleRR           INTEGER,
    gslbNewCfgRuleDname        DisplayString, 
    gslbNewCfgRuleDelete       INTEGER
    }

gslbNewCfgRuleIndx  OBJECT-TYPE
    SYNTAX Integer32
    MAX-ACCESS read-only
    STATUS current
    DESCRIPTION
        "The rule table index in the new configuration block."
    ::= { gslbNewCfgRuleTableEntry 1 }

gslbNewCfgRuleState OBJECT-TYPE
    SYNTAX  INTEGER {
        enabled(1),
        disabled(2)
        }
    MAX-ACCESS  read-create
    STATUS  current
    DESCRIPTION
        "Enable/Disable the rule in
         the new configuration block."
    ::= { gslbNewCfgRuleTableEntry 2 }

gslbNewCfgRuleStartHour OBJECT-TYPE
    SYNTAX  INTEGER (0..23)
    MAX-ACCESS  read-write
    STATUS  current
    DESCRIPTION
        "Start hour in 24-hour format for the rule in
         the new configuration block."
    ::= { gslbNewCfgRuleTableEntry 3 }

gslbNewCfgRuleStartMin OBJECT-TYPE
    SYNTAX  INTEGER (0..59)
    MAX-ACCESS  read-write
    STATUS  current
    DESCRIPTION
        "Start minutes for the rule in
         the new configuration block."
    ::= { gslbNewCfgRuleTableEntry 4 }

gslbNewCfgRuleEndHour OBJECT-TYPE
    SYNTAX  INTEGER (0..23)
    MAX-ACCESS  read-write
    STATUS  current
    DESCRIPTION
        "End hour in 24-hour format for the rule in
         the new configuration block."
    ::= { gslbNewCfgRuleTableEntry 5 }

gslbNewCfgRuleEndMin OBJECT-TYPE
    SYNTAX  INTEGER (0..59)
    MAX-ACCESS  read-write
    STATUS  current
    DESCRIPTION
        "End minutes for the rule in
         the new configuration block."
    ::= { gslbNewCfgRuleTableEntry 6 }

gslbNewCfgRuleTTL OBJECT-TYPE
    SYNTAX  INTEGER (0..65535)
    MAX-ACCESS  read-write
    STATUS  current
    DESCRIPTION
        "Time to live in seconds of DNS resource records for the rule in
         the new configuration block."
    ::= { gslbNewCfgRuleTableEntry 7 }

gslbNewCfgRuleRR OBJECT-TYPE
    SYNTAX  INTEGER (1..10)
    MAX-ACCESS  read-write
    STATUS  current
    DESCRIPTION
        "DNS resource records in DNS response for the rule in
         the new configuration block."
    ::= { gslbNewCfgRuleTableEntry 8 }

gslbNewCfgRuleDname OBJECT-TYPE
    SYNTAX DisplayString (SIZE(0..64))
    MAX-ACCESS read-create
    STATUS current
    DESCRIPTION
        "Network preference domain name for rule"
    ::= { gslbNewCfgRuleTableEntry 10 }

gslbNewCfgRuleDelete OBJECT-TYPE
    SYNTAX INTEGER {
        other(1),
        delete(2)
        }
    MAX-ACCESS read-create
    STATUS current
    DESCRIPTION
        "By setting the value to delete(2), the entire row is deleted."
    ::= { gslbNewCfgRuleTableEntry 9 }

-- Global SLB Metric Configuration

gslbMetricTableMaxSize OBJECT-TYPE
    SYNTAX Integer32
    MAX-ACCESS read-only
    STATUS current
    DESCRIPTION
        "The maximum number of Global SLB metrics for each Global SLB rule."
    ::= { gslbRuleCfg 4 }

gslbCurCfgMetricTable OBJECT-TYPE
    SYNTAX SEQUENCE OF GslbCurCfgMetricTableEntry
    MAX-ACCESS not-accessible
    STATUS current
    DESCRIPTION
        "The metric table in the current configuration block."
    ::= { gslbRuleCfg 5 }

gslbCurCfgMetricTableEntry OBJECT-TYPE
    SYNTAX GslbCurCfgMetricTableEntry
    MAX-ACCESS not-accessible
    STATUS current
    DESCRIPTION
        "An entry in the metric table in the current configuration block."
    INDEX { gslbCurCfgRuleMetricIndx, gslbCurCfgMetricIndx }
    ::= { gslbCurCfgMetricTable 1 }

GslbCurCfgMetricTableEntry ::= SEQUENCE {
    gslbCurCfgRuleMetricIndx        Integer32,
    gslbCurCfgMetricIndx            Integer32,
    gslbCurCfgMetricMetric          INTEGER,
    gslbCurCfgMetricNetworkBmap     OCTET STRING
    }

gslbCurCfgRuleMetricIndx  OBJECT-TYPE
    SYNTAX Integer32
    MAX-ACCESS read-only
    STATUS current
    DESCRIPTION
        "The rule table index in the current configuration block."
    ::= { gslbCurCfgMetricTableEntry 1 }

gslbCurCfgMetricIndx  OBJECT-TYPE
    SYNTAX Integer32
    MAX-ACCESS read-only
    STATUS current
    DESCRIPTION
        "The metric table index in the current configuration block."
    ::= { gslbCurCfgMetricTableEntry 2 }

gslbCurCfgMetricMetric OBJECT-TYPE
    SYNTAX INTEGER {
        leastconns(1),
        roundrobin(2),
        response(3),
        geographical(4),
        network(5),
        random(6),
        availability(7),
        qos(8),
        minmisses(9),
        hash(10),
        local(11),
        always(12),
        remote(13),
        none(14),
        persistence(15)
        }
    MAX-ACCESS read-only
    STATUS current
    DESCRIPTION
        "The metric to use to select next server in
         the current configuration block."
    ::= { gslbCurCfgMetricTableEntry 3 }

gslbCurCfgMetricNetworkBmap OBJECT-TYPE
    SYNTAX  OCTET STRING
    MAX-ACCESS  read-only
    STATUS  current
    DESCRIPTION
        "The networks added to the metric.  The networks added are
         presented in bitmap format.

         in receiving order:

             OCTET 1  OCTET 2  .....
             xxxxxxxx xxxxxxxx .....
             ||    || |_ network 9
             ||    ||
             ||    ||___ network 8
             ||    |____ network 7
             ||      .    .   .
             ||_________ network 2
             |__________ network 1

         where x : 1 - The represented network added to the metric
                   0 - The represented network added to the metric"
    ::= { gslbCurCfgMetricTableEntry 4 }

gslbNewCfgMetricTable OBJECT-TYPE
    SYNTAX SEQUENCE OF GslbNewCfgMetricTableEntry
    MAX-ACCESS not-accessible
    STATUS current
    DESCRIPTION
        "The metric table in the current configuration block."
    ::= { gslbRuleCfg 6 }

gslbNewCfgMetricTableEntry OBJECT-TYPE
    SYNTAX GslbNewCfgMetricTableEntry
    MAX-ACCESS not-accessible
    STATUS current
    DESCRIPTION
        "An entry in the metric table in the current configuration block."
    INDEX { gslbNewCfgRuleMetricIndx, gslbNewCfgMetricIndx }
    ::= { gslbNewCfgMetricTable 1 }

GslbNewCfgMetricTableEntry ::= SEQUENCE {
    gslbNewCfgRuleMetricIndx        Integer32,
    gslbNewCfgMetricIndx            Integer32,
    gslbNewCfgMetricMetric          INTEGER,
    gslbNewCfgMetricNetworkBmap     OCTET STRING,
    gslbNewCfgMetricAddNetwork      Integer32,
    gslbNewCfgMetricRemNetwork      Integer32
    }

gslbNewCfgRuleMetricIndx  OBJECT-TYPE
    SYNTAX Integer32
    MAX-ACCESS read-only
    STATUS current
    DESCRIPTION
        "The rule table index in the new configuration block."
    ::= { gslbNewCfgMetricTableEntry 1 }

gslbNewCfgMetricIndx  OBJECT-TYPE
    SYNTAX Integer32
    MAX-ACCESS read-only
    STATUS current
    DESCRIPTION
        "The metric table index in the new configuration block."
    ::= { gslbNewCfgMetricTableEntry 2 }

gslbNewCfgMetricMetric OBJECT-TYPE
    SYNTAX INTEGER {
        leastconns(1),
        roundrobin(2),
        response(3),
        geographical(4),
        network(5),
        random(6),
        availability(7),
        qos(8),
        minmisses(9),
        hash(10),
        local(11),
        always(12),
        remote(13),
        none(14),
        persistence(15)
        }
    MAX-ACCESS read-write
    STATUS current
    DESCRIPTION
        "The metric to use to select next server in
         the new configuration block."
    ::= { gslbNewCfgMetricTableEntry 3 }

gslbNewCfgMetricNetworkBmap OBJECT-TYPE
    SYNTAX  OCTET STRING
    MAX-ACCESS  read-only
    STATUS  current
    DESCRIPTION
        "The networks added to the metric.  The networks added are
         presented in bitmap format.

         in receiving order:

             OCTET 1  OCTET 2  .....
             xxxxxxxx xxxxxxxx .....
             ||    || |_ network 9
             ||    ||
             ||    ||___ network 8
             ||    |____ network 7
             ||      .    .   .
             ||_________ network 2
             |__________ network 1

         where x : 1 - The represented network added to the metric
                   0 - The represented network added to the metric"
    ::= { gslbNewCfgMetricTableEntry 4 }

gslbNewCfgMetricAddNetwork OBJECT-TYPE
    SYNTAX  Integer32
    MAX-ACCESS read-write
    STATUS  current
    DESCRIPTION
        "This is an action object to add network to a metric. The range of the
         valid index is between 1 and gslbEnhNetworkTableMaxSize. When read, the
         value '0' is returned always."
    ::= { gslbNewCfgMetricTableEntry 5 }

gslbNewCfgMetricRemNetwork OBJECT-TYPE
    SYNTAX  Integer32
    MAX-ACCESS read-write
    STATUS  current
    DESCRIPTION
        "This is an action object to remove network to a metric. The range of the
         valid index is between 1 and gslbEnhNetworkTableMaxSize. When read, the
         value '0' is returned always."
    ::= { gslbNewCfgMetricTableEntry 6 }


-- DNS SEC - Global

gslbCurCfgDnsSecGlobalEnabled OBJECT-TYPE
    SYNTAX INTEGER {
        enabled(1),
        disabled(2)
        }
    MAX-ACCESS read-only
    STATUS current
    DESCRIPTION
        "."
    ::= { gslbDnsSecGlobalCfg 1 }

gslbNewCfgDnsSecGlobalEnabled OBJECT-TYPE
    SYNTAX INTEGER {
        enabled(1),
        disabled(2)
        }
    MAX-ACCESS read-write
    STATUS current
    DESCRIPTION
        "."
    ::= { gslbDnsSecGlobalCfg 2 }

gslbCurCfgDnsSecGlobalRollTm OBJECT-TYPE
    SYNTAX INTEGER (1..168)
    MAX-ACCESS read-only
    STATUS current
    DESCRIPTION
        "Automatic Roll Over Timer - In Hours."
    ::= { gslbDnsSecGlobalCfg 3 }

gslbNewCfgDnsSecGlobalRollTm OBJECT-TYPE
    SYNTAX INTEGER (1..168)
    MAX-ACCESS read-write
    STATUS current
    DESCRIPTION
        "Automatic Roll Over Timer - In Hours."
    ::= { gslbDnsSecGlobalCfg 4 }

gslbCurCfgDnsSecGlobalType OBJECT-TYPE
    SYNTAX INTEGER {
        nsec(1),
        nsec3(2)
        }
    MAX-ACCESS read-only
    STATUS current
    DESCRIPTION
        "Automatic Roll Over Timer - In Hours."
    ::= { gslbDnsSecGlobalCfg 5 }

gslbNewCfgDnsSecGlobalType OBJECT-TYPE
    SYNTAX INTEGER {
        nsec(1),
        nsec3(2)
        }
    MAX-ACCESS read-write
    STATUS current
    DESCRIPTION
        "Automatic Roll Over Timer - In Hours."
    ::= { gslbDnsSecGlobalCfg 6 }

gslbCurCfgDnsSecGlobalKskRollTm OBJECT-TYPE
    SYNTAX INTEGER (1..168)
    MAX-ACCESS read-only
    STATUS current
    DESCRIPTION
        "Automatic KSK Roll Over Timer - In Hours."
    ::= { gslbDnsSecGlobalCfg 9 }

gslbNewCfgDnsSecGlobalKskRollTm OBJECT-TYPE
    SYNTAX INTEGER (1..168)
    MAX-ACCESS read-write
    STATUS current
    DESCRIPTION
        "Automatic KSK Roll Over Timer - In Hours."
    ::= { gslbDnsSecGlobalCfg 10 }


gslbCurCfgDnsSecGlobalNsec3SaltLen OBJECT-TYPE
    SYNTAX INTEGER (1..255)
    MAX-ACCESS read-only
    STATUS current
    DESCRIPTION
        "NSEC3 Salt Length in bytes."
    ::= { gslbDnsSecGlobalCfg 11 }

gslbNewCfgDnsSecGlobalNsec3SaltLen OBJECT-TYPE
    SYNTAX INTEGER (1..255)
    MAX-ACCESS read-write
    STATUS current
    DESCRIPTION
        "NSEC3 Salt Length in bytes."
    ::= { gslbDnsSecGlobalCfg 12 }

gslbCurCfgDnsSecGlobalNsec3SaltLifetime OBJECT-TYPE
    SYNTAX INTEGER (86400..2419200)
    MAX-ACCESS read-only
    STATUS current
    DESCRIPTION
        "NSEC3 Salt Lifetime in seconds."
    ::= { gslbDnsSecGlobalCfg 13 }

gslbNewCfgDnsSecGlobalNsec3SaltLifetime OBJECT-TYPE
    SYNTAX INTEGER (86400..2419200)
    MAX-ACCESS read-write
    STATUS current
    DESCRIPTION
        "NSEC3 Salt Lifetime in seconds."
    ::= { gslbDnsSecGlobalCfg 14 }

gslbCurCfgDnsSecGlobalNsec3HashIterations OBJECT-TYPE
    SYNTAX INTEGER (1..500)
    MAX-ACCESS read-only
    STATUS current
    DESCRIPTION
        "NSEC3 Salt Hash Iterations."
    ::= { gslbDnsSecGlobalCfg 15 }

gslbNewCfgDnsSecGlobalNsec3HashIterations OBJECT-TYPE
    SYNTAX INTEGER (1..500)
    MAX-ACCESS read-write
    STATUS current
    DESCRIPTION
        "NSEC3 Salt Hash Iterations."
    ::= { gslbDnsSecGlobalCfg 16 }

gslbCurCfgDnsSecGlobalSMPTServerUserName OBJECT-TYPE
    SYNTAX   DisplayString (SIZE(0..20))
    MAX-ACCESS  read-only
    STATUS  current
    DESCRIPTION
        "SMPT Server User Name."
    ::= { gslbDnsSecGlobalCfg  17 }

gslbNewCfgDnsSecGlobalSMPTServerUserName OBJECT-TYPE
    SYNTAX   DisplayString (SIZE(0..20))
    MAX-ACCESS  read-write
    STATUS  current
    DESCRIPTION
        "SMPT Server User Name."
    ::= { gslbDnsSecGlobalCfg  18 }

gslbCurDnsSecKeyTable OBJECT-TYPE
    SYNTAX  SEQUENCE OF GslbCurDnsSecKeyEntry
    MAX-ACCESS  not-accessible
    STATUS  current
    DESCRIPTION
        "."
    ::= { gslbDnsSecKeyCfg 1 }

gslbCurDnsSecKeyEntry OBJECT-TYPE
    SYNTAX  GslbCurDnsSecKeyEntry
    MAX-ACCESS  not-accessible
    STATUS  current
    DESCRIPTION
        "."
    INDEX   { gslbCurDnsSecKeyID }
    ::= { gslbCurDnsSecKeyTable 1 }

GslbCurDnsSecKeyEntry ::= SEQUENCE {
    gslbCurDnsSecKeyID                DisplayString,
    gslbCurDnsSecKeyUseCount          INTEGER,
    gslbCurDnsSecKeyType              INTEGER,
    gslbCurDnsSecKeyStatus            INTEGER,
    gslbCurDnsSecKeySize              INTEGER,
    gslbCurDnsSecKeyAlgo              INTEGER,
    gslbCurDnsSecKeyTTL               INTEGER,
    gslbCurDnsSecKeyExpPeriod         Unsigned32,
    gslbCurDnsSecKeyRollOverPeriod    Unsigned32,
    gslbCurDnsSecKeyValidityPeriod    Unsigned32,
    gslbCurDnsSecKeyPublicationPeriod Unsigned32
    }

gslbCurDnsSecKeyID OBJECT-TYPE
    SYNTAX   DisplayString (SIZE(0..32))
    MAX-ACCESS  read-only
    STATUS  current
    DESCRIPTION
        "DNS Sec Table Key."
    ::= { gslbCurDnsSecKeyEntry  1 }

gslbCurDnsSecKeyUseCount OBJECT-TYPE
    SYNTAX  INTEGER (0..65534)
    MAX-ACCESS  read-only
    STATUS  current
    DESCRIPTION
        "Usage count."
    ::= { gslbCurDnsSecKeyEntry 2 }

gslbCurDnsSecKeyType OBJECT-TYPE
    SYNTAX INTEGER {
        keyTypeKSK(1),
        keyTypeZSK(2),
        keyTypeInvalid(3)
        }
    MAX-ACCESS  read-only
    STATUS  current
    DESCRIPTION
        "KSK or ZSK."
    ::= { gslbCurDnsSecKeyEntry 3 }

gslbCurDnsSecKeyStatus OBJECT-TYPE
    SYNTAX INTEGER {
        enable(1),
        disable(2)
        }
    MAX-ACCESS  read-only
    STATUS  current
    DESCRIPTION
        "Key status."
    ::= { gslbCurDnsSecKeyEntry 4 }

gslbCurDnsSecKeySize OBJECT-TYPE
    SYNTAX INTEGER {
        keySize1024(1),
        keySize2048(2),
        keySize4096(3),
        keySizeInvalid(4)
        }
    MAX-ACCESS  read-only
    STATUS  current
    DESCRIPTION
        "Size of key (bits)."
    ::= { gslbCurDnsSecKeyEntry 5 }

gslbCurDnsSecKeyAlgo OBJECT-TYPE
    SYNTAX INTEGER {
        keyAlgoRsaSha1(1),
        keyAlgoRsaSha256(2),
        keyAlgoRsaSha512(3)
        }
    MAX-ACCESS  read-only
    STATUS  current
    DESCRIPTION
        "Signing algorithm."
    ::= { gslbCurDnsSecKeyEntry 6 }

gslbCurDnsSecKeyTTL OBJECT-TYPE
    SYNTAX  INTEGER (0..86400)
    MAX-ACCESS  read-only
    STATUS  current
    DESCRIPTION
        "DNSSEC - TTL in Seconds."
    ::= { gslbCurDnsSecKeyEntry 7 }

gslbCurDnsSecKeyExpPeriod OBJECT-TYPE
    SYNTAX      Unsigned32 (1..'ffffffff'h)
    MAX-ACCESS  read-only
    STATUS  current
    DESCRIPTION
        "Expiration period in Seconds."
    ::= { gslbCurDnsSecKeyEntry 8 }

gslbCurDnsSecKeyRollOverPeriod OBJECT-TYPE
    SYNTAX      Unsigned32 (1..'ffffffff'h)
    MAX-ACCESS  read-only
    STATUS  current
    DESCRIPTION
        "RollOver period in Seconds."
    ::= { gslbCurDnsSecKeyEntry 9 }

gslbCurDnsSecKeyValidityPeriod OBJECT-TYPE
    SYNTAX      Unsigned32 (1..'ffffffff'h)
    MAX-ACCESS  read-only
    STATUS  current
    DESCRIPTION
        "Signature validity period in Seconds."
    ::= { gslbCurDnsSecKeyEntry 10 }

gslbCurDnsSecKeyPublicationPeriod OBJECT-TYPE
    SYNTAX      Unsigned32 (1..'ffffffff'h)
    MAX-ACCESS  read-only
    STATUS  current
    DESCRIPTION
        "Signature publication period in Seconds."
    ::= { gslbCurDnsSecKeyEntry 11 }

gslbNewDnsSecKeyTable OBJECT-TYPE
    SYNTAX  SEQUENCE OF GslbNewDnsSecKeyEntry
    MAX-ACCESS  not-accessible
    STATUS  current
    DESCRIPTION
        "."
    ::= { gslbDnsSecKeyCfg 2 }

gslbNewDnsSecKeyEntry OBJECT-TYPE
    SYNTAX  GslbNewDnsSecKeyEntry
    MAX-ACCESS  not-accessible
    STATUS  current
    DESCRIPTION
        "."
    INDEX   { gslbNewDnsSecKeyID }
    ::= { gslbNewDnsSecKeyTable 1 }

GslbNewDnsSecKeyEntry ::= SEQUENCE {
    gslbNewDnsSecKeyID                DisplayString,
    gslbNewDnsSecKeyUseCount          INTEGER,
    gslbNewDnsSecKeyType              INTEGER,
    gslbNewDnsSecKeyStatus            INTEGER,
    gslbNewDnsSecKeySize              INTEGER,
    gslbNewDnsSecKeyAlgo              INTEGER,
    gslbNewDnsSecKeyTTL               INTEGER,
    gslbNewDnsSecKeyExpPeriod         Unsigned32,
    gslbNewDnsSecKeyRollOverPeriod    Unsigned32,
    gslbNewDnsSecKeyValidityPeriod    Unsigned32,
    gslbNewDnsSecKeyPublicationPeriod Unsigned32,
    gslbNewDnsSecKeyDelete            INTEGER,
    gslbNewDnsSecKeyGenerate          INTEGER,
    gslbNewDnsSecKeyGenerateStatus    INTEGER
    }

gslbNewDnsSecKeyID OBJECT-TYPE
    SYNTAX   DisplayString (SIZE(0..32))
    MAX-ACCESS  read-create
    STATUS  current
    DESCRIPTION
        "DNS Sec Table Key."
    ::= { gslbNewDnsSecKeyEntry  1 }

gslbNewDnsSecKeyUseCount OBJECT-TYPE
    SYNTAX  INTEGER (0..65534)
    MAX-ACCESS  read-only
    STATUS  current
    DESCRIPTION
        "Usage count."
    ::= { gslbNewDnsSecKeyEntry 2 }

gslbNewDnsSecKeyType OBJECT-TYPE
    SYNTAX INTEGER {
        keyTypeKSK(1),
        keyTypeZSK(2),
        keyTypeInvalid(3)
        }
    MAX-ACCESS  read-create
    STATUS  current
    DESCRIPTION
        "KSK or ZSK."
    ::= { gslbNewDnsSecKeyEntry 3 }

gslbNewDnsSecKeyStatus OBJECT-TYPE
    SYNTAX INTEGER {
        enable(1),
        disable(2)
        }
    MAX-ACCESS  read-write
    STATUS  current
    DESCRIPTION
        "Key state."
    ::= { gslbNewDnsSecKeyEntry 4 }

gslbNewDnsSecKeySize OBJECT-TYPE
    SYNTAX INTEGER {
        keySize1024(1),
        keySize2048(2),
        keySize4096(3),
        keySizeInvalid(4)
        }
    MAX-ACCESS  read-create
    STATUS  current
    DESCRIPTION
        "Size of key (bits)."
    ::= { gslbNewDnsSecKeyEntry 5 }

gslbNewDnsSecKeyAlgo OBJECT-TYPE
    SYNTAX INTEGER {
        keyAlgoRsaSha1(1),
        keyAlgoRsaSha256(2),
        keyAlgoRsaSha512(3)
        }
    MAX-ACCESS  read-create
    STATUS  current
    DESCRIPTION
        "Signing algorithm."
    ::= { gslbNewDnsSecKeyEntry 6 }

gslbNewDnsSecKeyTTL OBJECT-TYPE
    SYNTAX  INTEGER (0..86400)
    MAX-ACCESS  read-write
    STATUS  current
    DESCRIPTION
        "DNSSEC - TTL."
    ::= { gslbNewDnsSecKeyEntry 7 }

gslbNewDnsSecKeyExpPeriod OBJECT-TYPE
    SYNTAX      Unsigned32 (1..'ffffffff'h)
    MAX-ACCESS  read-write
    STATUS  current
    DESCRIPTION
        "Expiration period in Seconds."
    ::= { gslbNewDnsSecKeyEntry 8 }

gslbNewDnsSecKeyRollOverPeriod OBJECT-TYPE
    SYNTAX      Unsigned32 (1..'ffffffff'h)
    MAX-ACCESS  read-write
    STATUS  current
    DESCRIPTION
        "RollOver period in Seconds."
    ::= { gslbNewDnsSecKeyEntry 9 }

gslbNewDnsSecKeyValidityPeriod OBJECT-TYPE
    SYNTAX      Unsigned32 (1..'ffffffff'h)
    MAX-ACCESS  read-write
    STATUS  current
    DESCRIPTION
        "Signature validity period in Seconds."
    ::= { gslbNewDnsSecKeyEntry 10 }

gslbNewDnsSecKeyPublicationPeriod OBJECT-TYPE
    SYNTAX      Unsigned32 (1..'ffffffff'h)
    MAX-ACCESS  read-write
    STATUS  current
    DESCRIPTION
        "Signature publication period in Seconds."
    ::= { gslbNewDnsSecKeyEntry 11 }

gslbNewDnsSecKeyDelete OBJECT-TYPE
    SYNTAX  INTEGER {
        other(1),
        delete(2)
        }
    MAX-ACCESS  read-create
    STATUS  current
    DESCRIPTION
        "By setting the value to delete(2), the entire row is deleted."
    ::= { gslbNewDnsSecKeyEntry 13 }

gslbNewDnsSecKeyGenerate OBJECT-TYPE
    SYNTAX  INTEGER {
        other(1),
        generate(2)
        }
    MAX-ACCESS  read-create
    STATUS  current
    DESCRIPTION
        "By setting the value to generate(2), the key will be generated."
    ::= { gslbNewDnsSecKeyEntry 14 }

gslbNewDnsSecKeyGenerateStatus OBJECT-TYPE
    SYNTAX  INTEGER {
        notGenerated(1),
        generated(2),
        inProgress(3)
        }
    MAX-ACCESS  read-only
    STATUS  current
    DESCRIPTION
        "Returns the generate status."
    ::= { gslbNewDnsSecKeyEntry 15 }

gslbCurDnsSecZoneTable OBJECT-TYPE
    SYNTAX  SEQUENCE OF GslbCurDnsSecZoneEntry
    MAX-ACCESS  not-accessible
    STATUS  current
    DESCRIPTION
        "."
    ::= { gslbDnsSecZoneCfg 1 }

gslbCurDnsSecZoneEntry OBJECT-TYPE
    SYNTAX  GslbCurDnsSecZoneEntry
    MAX-ACCESS  not-accessible
    STATUS  current
    DESCRIPTION
        "."
    INDEX   { gslbCurDnsSecZoneID }
    ::= { gslbCurDnsSecZoneTable 1 }

GslbCurDnsSecZoneEntry ::= SEQUENCE {
    gslbCurDnsSecZoneID               DisplayString,
    gslbCurDnsSecZoneName             DisplayString,
    gslbCurDnsSecZoneKSK1             DisplayString,
    gslbCurDnsSecZoneKSK2             DisplayString,
    gslbCurDnsSecZoneKSK3             DisplayString,
    gslbCurDnsSecZoneZSK1             DisplayString,
    gslbCurDnsSecZoneZSK2             DisplayString,
    gslbCurDnsSecZoneZSK3             DisplayString,
    gslbCurDnsSecZoneStatus           INTEGER,
    gslbCurDnsSecZoneParentIPVer      INTEGER,
    gslbCurDnsSecZoneParentIPv4       IpAddress,
    gslbCurDnsSecZoneParentIPv6       DisplayString
    }

gslbCurDnsSecZoneID OBJECT-TYPE
    SYNTAX   DisplayString (SIZE(0..32))
    MAX-ACCESS  read-only
    STATUS  current
    DESCRIPTION
        "Zone ID."
    ::= { gslbCurDnsSecZoneEntry  1 }

gslbCurDnsSecZoneName OBJECT-TYPE
    SYNTAX   DisplayString (SIZE(0..65))
    MAX-ACCESS  read-only
    STATUS  current
    DESCRIPTION
        "Zone name (virt's dname)."
    ::= { gslbCurDnsSecZoneEntry  2 }

gslbCurDnsSecZoneKSK1 OBJECT-TYPE
    SYNTAX   DisplayString (SIZE(0..32))
    MAX-ACCESS  read-only
    STATUS  current
    DESCRIPTION
        "KSK 1 of the zone."
    ::= { gslbCurDnsSecZoneEntry  3 }

gslbCurDnsSecZoneKSK2 OBJECT-TYPE
    SYNTAX   DisplayString (SIZE(0..32))
    MAX-ACCESS  read-only
    STATUS  current
    DESCRIPTION
        "KSK 2 of the zone."
    ::= { gslbCurDnsSecZoneEntry  4 }

gslbCurDnsSecZoneKSK3 OBJECT-TYPE
    SYNTAX   DisplayString (SIZE(0..32))
    MAX-ACCESS  read-only
    STATUS  current
    DESCRIPTION
        "KSK 3 of the zone."
    ::= { gslbCurDnsSecZoneEntry  5 }

gslbCurDnsSecZoneZSK1 OBJECT-TYPE
    SYNTAX   DisplayString (SIZE(0..32))
    MAX-ACCESS  read-only
    STATUS  current
    DESCRIPTION
        "ZSK 1 of the zone."
    ::= { gslbCurDnsSecZoneEntry  6 }

gslbCurDnsSecZoneZSK2 OBJECT-TYPE
    SYNTAX   DisplayString (SIZE(0..32))
    MAX-ACCESS  read-only
    STATUS  current
    DESCRIPTION
        "ZSK 2 of the zone."
    ::= { gslbCurDnsSecZoneEntry  7 }

gslbCurDnsSecZoneZSK3 OBJECT-TYPE
    SYNTAX   DisplayString (SIZE(0..32))
    MAX-ACCESS  read-only
    STATUS  current
    DESCRIPTION
        "ZSK 1 of the zone."
    ::= { gslbCurDnsSecZoneEntry  8 }

gslbCurDnsSecZoneStatus OBJECT-TYPE
    SYNTAX INTEGER {
        enable(1),
        disable(2)
        }
    MAX-ACCESS  read-only
    STATUS  current
    DESCRIPTION
        "Zone status - Enabled/Disabled."
    ::= { gslbCurDnsSecZoneEntry 9 }

gslbCurDnsSecZoneParentIPVer OBJECT-TYPE
    SYNTAX  INTEGER{
        ipv4(1),
        ipv6(2)
        }
    MAX-ACCESS  read-only
    STATUS  current
    DESCRIPTION
        "The type of IP address."
    ::= { gslbCurDnsSecZoneEntry 10 }

gslbCurDnsSecZoneParentIPv4 OBJECT-TYPE
    SYNTAX IpAddress
    MAX-ACCESS  read-only
    STATUS  current
    DESCRIPTION
        "Parent IP."
    ::= { gslbCurDnsSecZoneEntry 11 }

gslbCurDnsSecZoneParentIPv6 OBJECT-TYPE
   SYNTAX DisplayString (SIZE(0..40))
    MAX-ACCESS  read-only
    STATUS  current
    DESCRIPTION
    "  IPV6 address of the Parent IP
       Address should be 4-byte haxadecimal colon notation. Valid IPv6 address should be in
       any of the following forms xxxx:xxxx:xxxx:xxxx:xxxx:xxxx:xxxx:xxxx or xxxx::xxxx:xxxx:xxxx:xxxx or ::xxxx "
   ::= { gslbCurDnsSecZoneEntry 12 }


gslbNewDnsSecZoneTable OBJECT-TYPE
    SYNTAX  SEQUENCE OF GslbNewDnsSecZoneEntry
    MAX-ACCESS  not-accessible
    STATUS  current
    DESCRIPTION
        "."
    ::= { gslbDnsSecZoneCfg 2 }

gslbNewDnsSecZoneEntry OBJECT-TYPE
    SYNTAX  GslbNewDnsSecZoneEntry
    MAX-ACCESS  not-accessible
    STATUS  current
    DESCRIPTION
        "."
    INDEX   { gslbNewDnsSecZoneID }
    ::= { gslbNewDnsSecZoneTable 1 }

GslbNewDnsSecZoneEntry ::= SEQUENCE {
    gslbNewDnsSecZoneID               DisplayString,
    gslbNewDnsSecZoneName             DisplayString,
    gslbNewDnsSecZoneKSK1             DisplayString,
    gslbNewDnsSecZoneKSK2             DisplayString,
    gslbNewDnsSecZoneKSK3             DisplayString,
    gslbNewDnsSecZoneZSK1             DisplayString,
    gslbNewDnsSecZoneZSK2             DisplayString,
    gslbNewDnsSecZoneZSK3             DisplayString,
    gslbNewDnsSecZoneStatus           INTEGER,
    gslbNewDnsSecZoneParentIPVer      INTEGER,
    gslbNewDnsSecZoneParentIPv4       IpAddress,
    gslbNewDnsSecZoneParentIPv6       DisplayString,
    gslbNewDnsSecZoneDelete           INTEGER
    }

gslbNewDnsSecZoneID OBJECT-TYPE
    SYNTAX   DisplayString (SIZE(0..32))
    MAX-ACCESS  read-create
    STATUS  current
    DESCRIPTION
        "Zone ID."
    ::= { gslbNewDnsSecZoneEntry  1 }

gslbNewDnsSecZoneName OBJECT-TYPE
    SYNTAX   DisplayString (SIZE(0..65))
    MAX-ACCESS  read-write
    STATUS  current
    DESCRIPTION
        "Zone name (virt's dname)."
    ::= { gslbNewDnsSecZoneEntry  2 }

gslbNewDnsSecZoneKSK1 OBJECT-TYPE
    SYNTAX   DisplayString (SIZE(0..32))
    MAX-ACCESS  read-write
    STATUS  current
    DESCRIPTION
        "KSK 1 of the zone."
    ::= { gslbNewDnsSecZoneEntry  3 }

gslbNewDnsSecZoneKSK2 OBJECT-TYPE
    SYNTAX   DisplayString (SIZE(0..32))
    MAX-ACCESS  read-write
    STATUS  current
    DESCRIPTION
        "KSK 2 of the zone."
    ::= { gslbNewDnsSecZoneEntry  4 }

gslbNewDnsSecZoneKSK3 OBJECT-TYPE
    SYNTAX   DisplayString (SIZE(0..32))
    MAX-ACCESS  read-write
    STATUS  current
    DESCRIPTION
        "KSK 3 of the zone."
    ::= { gslbNewDnsSecZoneEntry  5 }

gslbNewDnsSecZoneZSK1 OBJECT-TYPE
    SYNTAX   DisplayString (SIZE(0..32))
    MAX-ACCESS  read-write
    STATUS  current
    DESCRIPTION
        "ZSK 1 of the zone."
    ::= { gslbNewDnsSecZoneEntry  6 }

gslbNewDnsSecZoneZSK2 OBJECT-TYPE
    SYNTAX   DisplayString (SIZE(0..32))
    MAX-ACCESS  read-write
    STATUS  current
    DESCRIPTION
        "ZSK 2 of the zone."
    ::= { gslbNewDnsSecZoneEntry  7 }

gslbNewDnsSecZoneZSK3 OBJECT-TYPE
    SYNTAX   DisplayString (SIZE(0..32))
    MAX-ACCESS  read-write
    STATUS  current
    DESCRIPTION
        "ZSK 3 of the zone."
    ::= { gslbNewDnsSecZoneEntry  8 }

gslbNewDnsSecZoneStatus OBJECT-TYPE
    SYNTAX INTEGER {
        enable(1),
        disable(2)
        }
    MAX-ACCESS  read-write
    STATUS  current
    DESCRIPTION
        "Zone status - Enabled/Disabled."
    ::= { gslbNewDnsSecZoneEntry 9 }

gslbNewDnsSecZoneParentIPVer OBJECT-TYPE
    SYNTAX  INTEGER{
        ipv4(1),
        ipv6(2)
        }
    MAX-ACCESS  read-only
    STATUS  current
    DESCRIPTION
        "The type of IP address."
    ::= { gslbNewDnsSecZoneEntry 10 }

gslbNewDnsSecZoneParentIPv4 OBJECT-TYPE
    SYNTAX IpAddress
    MAX-ACCESS  read-write
    STATUS  current
    DESCRIPTION
        "IPV4 address of the Parent IP."
    ::= { gslbNewDnsSecZoneEntry 11 }

gslbNewDnsSecZoneParentIPv6 OBJECT-TYPE
   SYNTAX DisplayString (SIZE(0..40))
    MAX-ACCESS  read-write
    STATUS  current
    DESCRIPTION
    "  IPV6 address of the Parent IP
       Address should be 4-byte haxadecimal colon notation. Valid IPv6 address should be in
       any of the following forms xxxx:xxxx:xxxx:xxxx:xxxx:xxxx:xxxx:xxxx or xxxx::xxxx:xxxx:xxxx:xxxx or ::xxxx "
   ::= { gslbNewDnsSecZoneEntry 12 }

gslbNewDnsSecZoneDelete OBJECT-TYPE
    SYNTAX  INTEGER {
        other(1),
        delete(2)
        }
    MAX-ACCESS  read-write
    STATUS  current
    DESCRIPTION
        "By setting the value to delete(2), the entire row is deleted."
    ::= { gslbNewDnsSecZoneEntry 13 }


-- DNS SEC - Import/Export

gslbDnsSecImportExportSCPHostName OBJECT-TYPE
    SYNTAX   DisplayString (SIZE(0..128))
    MAX-ACCESS read-write
    STATUS current
    DESCRIPTION
        "SCP Server Host Name or Server IP Address."
    ::= { gslbDnsSecImportExport 1 }

gslbDnsSecImportExportSCPFileName OBJECT-TYPE
    SYNTAX   DisplayString (SIZE(0..128))
    MAX-ACCESS read-write
    STATUS current
    DESCRIPTION
        "SCP Server File name."
    ::= { gslbDnsSecImportExport 2 }

gslbDnsSecImportExportSCPUserName OBJECT-TYPE
    SYNTAX   DisplayString (SIZE(0..128))
    MAX-ACCESS read-write
    STATUS current
    DESCRIPTION
        "SCP Server User Name."
    ::= { gslbDnsSecImportExport 3 }

gslbDnsSecImportExportSCPPassword OBJECT-TYPE
    SYNTAX   DisplayString (SIZE(0..128))
    MAX-ACCESS read-write
    STATUS current
    DESCRIPTION
        "SCP Server Password."
    ::= { gslbDnsSecImportExport 4 }

gslbDnsSecImportExportKeyID OBJECT-TYPE
    SYNTAX   DisplayString (SIZE(0..32))
    MAX-ACCESS read-write
    STATUS current
    DESCRIPTION
        "DNSSEC Key ID."
    ::= { gslbDnsSecImportExport 5 }

gslbDnsSecImportExportZoneID OBJECT-TYPE
    SYNTAX   DisplayString (SIZE(0..32))
    MAX-ACCESS read-write
    STATUS current
    DESCRIPTION
        "DNSSEC Zone ID."
    ::= { gslbDnsSecImportExport 6 }

gslbDnsSecImportExportPassphrase OBJECT-TYPE
    SYNTAX   DisplayString (SIZE(0..40))
    MAX-ACCESS read-write
    STATUS current
    DESCRIPTION
        "Passphrase."
    ::= { gslbDnsSecImportExport 7 }

gslbDnsSecImportExportComponentType OBJECT-TYPE
    SYNTAX  INTEGER {
        none(0),
        key(1),
        dnskey(2),
        dsrecord(3)
        }
    MAX-ACCESS  read-write
    STATUS  current
    DESCRIPTION
        "Component type to import/export: key, dnskey or ds record.
         Currently only the key is Supported"
    ::= { gslbDnsSecImportExport 8 }

gslbDnsSecImportExportPortType OBJECT-TYPE
    SYNTAX  INTEGER {
        data(0),
        mgmt(1)
        }
    MAX-ACCESS  read-write
    STATUS  current
    DESCRIPTION
        "The port type: management or data."
    ::= { gslbDnsSecImportExport 9 }

gslbDnsSecImportExportImpKeyType OBJECT-TYPE
    SYNTAX INTEGER {
        keyTypeKSK(1),
        keyTypeZSK(2)
        }
    MAX-ACCESS  read-write
    STATUS  current
    DESCRIPTION
        "KSK or ZSK."
    ::= { gslbDnsSecImportExport 10 }

gslbDnsSecImportExportImpKeyStatus OBJECT-TYPE
    SYNTAX INTEGER {
        enable(1),
        disable(2)
        }
    MAX-ACCESS  read-write
    STATUS  current
    DESCRIPTION
        "Key status."
    ::= { gslbDnsSecImportExport 11 }

gslbDnsSecImportExportImpKeySize OBJECT-TYPE
    SYNTAX INTEGER {
        keySize1024(1),
        keySize2048(2),
        keySize4096(3)
        }
    MAX-ACCESS  read-only
    STATUS  current
    DESCRIPTION
        "Size of key (bits)."
    ::= { gslbDnsSecImportExport 12 }

gslbDnsSecImportExportImpKeyAlgo OBJECT-TYPE
    SYNTAX INTEGER {
        keyAlgoRsaSha1(1),
        keyAlgoRsaSha256(2),
        keyAlgoRsaSha512(3)
        }
    MAX-ACCESS  read-write
    STATUS  current
    DESCRIPTION
        "Signing algorithm."
    ::= { gslbDnsSecImportExport 13 }

gslbDnsSecImportExportImpKeyTTL OBJECT-TYPE
    SYNTAX  INTEGER (0..86400)
    MAX-ACCESS  read-write
    STATUS  current
    DESCRIPTION
        "DNSSEC - TTL in Seconds."
    ::= { gslbDnsSecImportExport 14 }

gslbDnsSecImportExportImpKeyExpPeriod OBJECT-TYPE
    SYNTAX      Unsigned32 (1..'ffffffff'h)
    MAX-ACCESS  read-write
    STATUS  current
    DESCRIPTION
        "Expiration period in Seconds."
    ::= { gslbDnsSecImportExport 15 }

gslbDnsSecImportExportImpKeyRollOverPeriod OBJECT-TYPE
    SYNTAX      Unsigned32 (1..'ffffffff'h)
    MAX-ACCESS  read-write
    STATUS  current
    DESCRIPTION
        "RollOver period in Seconds."
    ::= { gslbDnsSecImportExport 16 }

gslbDnsSecImportExportImpKeyValidityPeriod OBJECT-TYPE
    SYNTAX      Unsigned32 (1..'ffffffff'h)
    MAX-ACCESS  read-write
    STATUS  current
    DESCRIPTION
        "Signature validity period in Seconds."
    ::= { gslbDnsSecImportExport 17 }

gslbDnsSecImportExportImpKeyPublicationPeriod OBJECT-TYPE
    SYNTAX      Unsigned32 (1..'ffffffff'h)
    MAX-ACCESS  read-write
    STATUS  current
    DESCRIPTION
        "Signature publication period in Seconds."
    ::= { gslbDnsSecImportExport 18 }

gslbDnsSecImportExportAction OBJECT-TYPE
    SYNTAX  INTEGER {
        none(0),
        import(1),
        export(2)
        }
    MAX-ACCESS  read-write
    STATUS  current
    DESCRIPTION
        "Component type to import/export: key or dnskey."
    ::= { gslbDnsSecImportExport 19 }


-- DNS Responder VIP Configuration

gslbCurDnsResVipTable OBJECT-TYPE
    SYNTAX  SEQUENCE OF GslbCurDnsResVipEntry
    MAX-ACCESS  not-accessible
    STATUS  current
    DESCRIPTION
        "."
    ::= { gslbDnsResVipCfg 1 }

gslbCurDnsResVipEntry OBJECT-TYPE
    SYNTAX  GslbCurDnsResVipEntry
    MAX-ACCESS  not-accessible
    STATUS  current
    DESCRIPTION
        "."
    INDEX   { gslbCurDnsResVipIndex1, gslbCurDnsResVipIndex2 }
    ::= { gslbCurDnsResVipTable 1 }

GslbCurDnsResVipEntry ::= SEQUENCE {
    gslbCurDnsResVipIndex1       INTEGER,
    gslbCurDnsResVipIndex2       INTEGER,
    gslbCurDnsResVipName         DisplayString,
    gslbCurDnsResVipIPVer        INTEGER,
    gslbCurDnsResVipV4           IpAddress,
    gslbCurDnsResVipV6           DisplayString,
    gslbCurDnsResVipStatus       INTEGER
    }

gslbCurDnsResVipIndex1 OBJECT-TYPE
    SYNTAX INTEGER (1..1024)
    MAX-ACCESS  read-only
    STATUS  current
    DESCRIPTION
        "DNS Responder VIP Index 1."
    ::= { gslbCurDnsResVipEntry  1 }

gslbCurDnsResVipIndex2 OBJECT-TYPE
    SYNTAX INTEGER (1..1024)
    MAX-ACCESS  read-only
    STATUS  current
    DESCRIPTION
        "DNS Responder VIP Index 2."
    ::= { gslbCurDnsResVipEntry  2 }

gslbCurDnsResVipName OBJECT-TYPE
    SYNTAX   DisplayString (SIZE(0..32))
    MAX-ACCESS  read-only
    STATUS  current
    DESCRIPTION
        "DNS Responder VIP Name."
    ::= { gslbCurDnsResVipEntry  3 }

gslbCurDnsResVipIPVer OBJECT-TYPE
    SYNTAX  INTEGER{
        ipv4(1),
        ipv6(2)
        }
    MAX-ACCESS  read-only
    STATUS  current
    DESCRIPTION
        "The type of IP address of DNS Responder VIP."
    ::= { gslbCurDnsResVipEntry 4 }

gslbCurDnsResVipV4 OBJECT-TYPE
    SYNTAX IpAddress
    MAX-ACCESS  read-only
    STATUS  current
    DESCRIPTION
        "IPV4 address of the DNS Responder VIP."
    ::= { gslbCurDnsResVipEntry 5 }

gslbCurDnsResVipV6 OBJECT-TYPE
   SYNTAX DisplayString (SIZE(0..40))
    MAX-ACCESS  read-only
    STATUS  current
    DESCRIPTION
    "  IPV6 address of the DNS Responder VIP
       Address should be 4-byte haxadecimal colon notation. Valid IPv6 address should be in
       any of the following forms xxxx:xxxx:xxxx:xxxx:xxxx:xxxx:xxxx:xxxx or xxxx::xxxx:xxxx:xxxx:xxxx or ::xxxx "
   ::= { gslbCurDnsResVipEntry 6 }

gslbCurDnsResVipStatus OBJECT-TYPE
    SYNTAX INTEGER {
        enable(1),
        disable(2)
        }
    MAX-ACCESS  read-only
    STATUS  current
    DESCRIPTION
        "Zone status - Enabled/Disabled."
    ::= { gslbCurDnsResVipEntry 7 }


gslbNewDnsResVipTable OBJECT-TYPE
    SYNTAX  SEQUENCE OF GslbNewDnsResVipEntry
    MAX-ACCESS  not-accessible
    STATUS  current
    DESCRIPTION
        "."
    ::= { gslbDnsResVipCfg 2 }

gslbNewDnsResVipEntry OBJECT-TYPE
    SYNTAX  GslbNewDnsResVipEntry
    MAX-ACCESS  not-accessible
    STATUS  current
    DESCRIPTION
        "."
    INDEX   { gslbNewDnsResVipIndex1, gslbNewDnsResVipIndex2 }
    ::= { gslbNewDnsResVipTable 1 }

GslbNewDnsResVipEntry ::= SEQUENCE {
    gslbNewDnsResVipIndex1       INTEGER,
    gslbNewDnsResVipIndex2       INTEGER,
    gslbNewDnsResVipName         DisplayString,
    gslbNewDnsResVipIPVer        INTEGER,
    gslbNewDnsResVipV4           IpAddress,
    gslbNewDnsResVipV6           DisplayString,
    gslbNewDnsResVipStatus       INTEGER,
    gslbNewDnsResVipDelete       INTEGER
    }

gslbNewDnsResVipIndex1 OBJECT-TYPE
    SYNTAX INTEGER (1..1024)
    MAX-ACCESS  read-create
    STATUS  current
    DESCRIPTION
        "DNS Responder VIP Index 1."
    ::= { gslbNewDnsResVipEntry  1 }

gslbNewDnsResVipIndex2 OBJECT-TYPE
    SYNTAX INTEGER (1..1024)
    MAX-ACCESS  read-create
    STATUS  current
    DESCRIPTION
        "DNS Responder VIP Index 2."
    ::= { gslbNewDnsResVipEntry  2 }

gslbNewDnsResVipName OBJECT-TYPE
    SYNTAX   DisplayString (SIZE(0..32))
    MAX-ACCESS  read-write
    STATUS  current
    DESCRIPTION
        "DNS Responder VIP Name."
    ::= { gslbNewDnsResVipEntry  3 }

gslbNewDnsResVipIPVer OBJECT-TYPE
    SYNTAX  INTEGER{
        ipv4(1),
        ipv6(2)
        }
    MAX-ACCESS  read-write
    STATUS  current
    DESCRIPTION
        "The type of IP address of DNS Responder VIP."
    ::= { gslbNewDnsResVipEntry 4 }

gslbNewDnsResVipV4 OBJECT-TYPE
    SYNTAX IpAddress
    MAX-ACCESS  read-write
    STATUS  current
    DESCRIPTION
        "IPV4 address of the DNS Responder VIP."
    ::= { gslbNewDnsResVipEntry 5 }

gslbNewDnsResVipV6 OBJECT-TYPE
   SYNTAX DisplayString (SIZE(0..40))
    MAX-ACCESS  read-write
    STATUS  current
    DESCRIPTION
    "  IPV6 address of the DNS Responder VIP
       Address should be 4-byte haxadecimal colon notation. Valid IPv6 address should be in
       any of the following forms xxxx:xxxx:xxxx:xxxx:xxxx:xxxx:xxxx:xxxx or xxxx::xxxx:xxxx:xxxx:xxxx or ::xxxx "
   ::= { gslbNewDnsResVipEntry 6 }

gslbNewDnsResVipStatus OBJECT-TYPE
    SYNTAX INTEGER {
        enable(1),
        disable(2)
        }
    MAX-ACCESS  read-write
    STATUS  current
    DESCRIPTION
        "Zone status - Enabled/Disabled."
    ::= { gslbNewDnsResVipEntry 7 }

gslbNewDnsResVipDelete OBJECT-TYPE
    SYNTAX  INTEGER {
        other(1),
        delete(2)
        }
    MAX-ACCESS  read-write
    STATUS  current
    DESCRIPTION
        "By setting the value to delete(2), the entire row is deleted."
    ::= { gslbNewDnsResVipEntry 8 }


gslbDnsResVipEmptyIndexesTable OBJECT-TYPE
    SYNTAX  SEQUENCE OF GslbDnsResVipEmptyIndexesEntry
    MAX-ACCESS  not-accessible
    STATUS  current
    DESCRIPTION
        "."
    ::= { gslbDnsResVipCfg 3 }

gslbDnsResVipEmptyIndexesEntry OBJECT-TYPE
    SYNTAX  GslbDnsResVipEmptyIndexesEntry
    MAX-ACCESS  not-accessible
    STATUS  current
    DESCRIPTION
        "."
    INDEX   { gslbDnsResVipEmptyIndexesIndex }
    ::= { gslbDnsResVipEmptyIndexesTable 1 }

GslbDnsResVipEmptyIndexesEntry ::= SEQUENCE {
    gslbDnsResVipEmptyIndexesIndex       INTEGER
    }

gslbDnsResVipEmptyIndexesIndex OBJECT-TYPE
    SYNTAX INTEGER (1..1024)
    MAX-ACCESS  read-only
    STATUS  current
    DESCRIPTION
        "DNS Responder VIP Index."
    ::= { gslbDnsResVipEmptyIndexesEntry  1 }


-- Health Script Configuration
 
hcsTableMaxSize OBJECT-TYPE
    SYNTAX  Integer32
    MAX-ACCESS  read-only
    STATUS  current
    DESCRIPTION
        "The maximum number of scriptable health check entries."
    ::= { hcsCfg 1 }

hcsCurCfgTable OBJECT-TYPE
    SYNTAX  SEQUENCE OF HcsCurCfgTableEntry
    MAX-ACCESS  not-accessible
    STATUS  current
    DESCRIPTION
        "The scriptable health check table in the current configuration block."
    ::= { hcsCfg 2 }

hcsCurCfgTableEntry OBJECT-TYPE
    SYNTAX  HcsCurCfgTableEntry
    MAX-ACCESS  not-accessible
    STATUS  current
    DESCRIPTION
        "A row in the scriptable health check table."
    INDEX   { hcsCurCfgScriptIndex }
    ::= { hcsCurCfgTable 1 }

HcsCurCfgTableEntry ::= SEQUENCE {
    hcsCurCfgScriptIndex     Integer32,
    hcsCurCfgScriptString    OCTET STRING
    }

hcsCurCfgScriptIndex OBJECT-TYPE
    SYNTAX Integer32
    MAX-ACCESS read-only
    STATUS current
    DESCRIPTION
        "The index in the scriptable health check table."
    ::= { hcsCurCfgTableEntry 1 }

hcsCurCfgScriptString OBJECT-TYPE
    SYNTAX OCTET STRING 
    MAX-ACCESS read-only
    STATUS current
    DESCRIPTION
        "The scriptable health check string."
    ::= { hcsCurCfgTableEntry 2 }

hcsNewCfgTable OBJECT-TYPE
    SYNTAX  SEQUENCE OF HcsNewCfgTableEntry
    MAX-ACCESS  not-accessible
    STATUS  current
    DESCRIPTION
        "The scriptable health check table in the new configuration block."
    ::= { hcsCfg 3 }

hcsNewCfgTableEntry OBJECT-TYPE
    SYNTAX  HcsNewCfgTableEntry
    MAX-ACCESS  not-accessible
    STATUS  current
    DESCRIPTION
        "A row in the scriptable health check table."
    INDEX   { hcsNewCfgScriptIndex }
    ::= { hcsNewCfgTable 1 }

HcsNewCfgTableEntry ::= SEQUENCE {
    hcsNewCfgScriptIndex       Integer32,
    hcsNewCfgScriptString      OCTET STRING,
    hcsNewCfgAddSendCmd        DisplayString,     -- obsolete
    hcsNewCfgAddExpectCmd      DisplayString,     -- obsolete
    hcsNewCfgAddCloseCmd       INTEGER,
    hcsNewCfgRemLastCmd        INTEGER,
    hcsNewCfgAddWaitCmd        INTEGER,
    hcsNewCfgAddOffsetCmd      INTEGER,
    hcsNewCfgAddOpenProtCmd    DisplayString,
    hcsNewCfgAddDepthCmd       INTEGER,
    hcsNewCfgAddLongNsendCmd   OCTET STRING,
    hcsNewCfgAddLongNexpectCmd OCTET STRING,
    hcsNewCfgAddNsendCmd       DisplayString,     -- obsolete
    hcsNewCfgAddNexpectCmd     DisplayString,     -- obsolete
    hcsNewCfgAddLongBsendCmd   OCTET STRING,
    hcsNewCfgAddLongBexpectCmd OCTET STRING,
    hcsNewCfgAddLongSendCmd    OCTET STRING,
    hcsNewCfgAddLongExpectCmd  OCTET STRING,
    hcsNewCfgDeleteScript      INTEGER
    }

hcsNewCfgScriptIndex OBJECT-TYPE
    SYNTAX Integer32
    MAX-ACCESS read-only
    STATUS current
    DESCRIPTION
        "The index the scriptable health check."
    ::= { hcsNewCfgTableEntry 1 }

hcsNewCfgScriptString OBJECT-TYPE
    SYNTAX OCTET STRING
    MAX-ACCESS read-only
    STATUS current
    DESCRIPTION
        "The scriptable health check string."
    ::= { hcsNewCfgTableEntry 2 }


hcsNewCfgAddSendCmd OBJECT-TYPE
    SYNTAX DisplayString (SIZE(0..255))
    MAX-ACCESS read-create
    STATUS obsolete
    DESCRIPTION
        "Append an 'send' command to the script. The set value of this object
         should be the exact characters to be sent on the port opened with the
         'open' command. The 'send ' characters will be automatically appended.
         Also a 'null terminator' (\0) will be automatically appended. The null
         terminator and the 'send ' characters will be counted as characters in
         the script."
    ::= { hcsNewCfgTableEntry 4 }

hcsNewCfgAddExpectCmd OBJECT-TYPE
    SYNTAX DisplayString (SIZE(0..255))
    MAX-ACCESS read-create
    STATUS obsolete
    DESCRIPTION
        "Append an 'expect' command to the script. The set value of this 
	 object should be the exact characters expected to be received on
         the port opened with the 'open' command.  The value could also be
         a single wildcard character '*' which means any received content
	 will be accepted.  The 'expect ' characters will be automatically 
	 appended.  Also a 'null terminator'(\0) will be automatically  
         appended.  The null terminator and the 'expect ' characters will
         be counted as characters in the script."
    ::= { hcsNewCfgTableEntry 5 }

hcsNewCfgAddCloseCmd OBJECT-TYPE
    SYNTAX INTEGER {
        other(1),
        close(2)
        }
    MAX-ACCESS read-create
    STATUS current
    DESCRIPTION
        "Add close command to end of the script. When set to the value of 2
         (add), 'close' will be appended to the script. Also, a 
         'null terminator'(\0) will be automatically appended. The null 
         terminator and the 'close' characters will be counted as characters 
         in the script.  This command is only valid for TCP."
    ::= { hcsNewCfgTableEntry 6 }

hcsNewCfgRemLastCmd OBJECT-TYPE
    SYNTAX INTEGER {
        other(1),
        remove(2)
        }
    MAX-ACCESS read-create
    STATUS current
    DESCRIPTION
        "Remove the last command from the script. When set to the value of 2
         (remove), last command will be removed from the script. When read,
         other(1) is returned."
    ::= { hcsNewCfgTableEntry 7 }

hcsNewCfgDeleteScript OBJECT-TYPE
    SYNTAX INTEGER {
        other(1),
        delete(2)
        }
    MAX-ACCESS read-create
    STATUS current
    DESCRIPTION
        "When set to the value of 2 (delete), the entire row is deleted.
         When read, other(1) is returned. Setting the value to anything
         other than 2(delete) has no effect on the state of the row."
    ::= { hcsNewCfgTableEntry 8 }

hcsNewCfgAddOffsetCmd OBJECT-TYPE
    SYNTAX INTEGER (1..1464)
    MAX-ACCESS read-create
    STATUS current
    DESCRIPTION
        "Append an 'offset' command to the script. The set value of this
	 object should be the offset from the beginning of the data area
	 of the TCP/UDP packet to start matching the string configured
	 in the last bexpect command. The 'offset ' characters will be
         automatically appended. Also a 'null terminator'(\0) will be 
         automatically appended. The null terminator and the 'offset '
         characters will be counted as characters in the script.  When 
	 read, the return value has no significant meaning, but a 1 is
	 always returned."
    ::= { hcsNewCfgTableEntry 9 }

hcsNewCfgAddWaitCmd OBJECT-TYPE
    SYNTAX INTEGER (1..65535)
    MAX-ACCESS read-create
    STATUS current
    DESCRIPTION
        "Append a 'wait' command to the script. The set value of this
	 object should be the maximum waiting time for the packet
	 containing the content configured in the last expect command.
	 Wait time is in units of milliseconds, and the maximum
	 supported is 65535 ms.  The 'wait ' characters will be 
	 automatically appended. Also a 'null terminator'(\0) will be
         automatically appended. The null terminator and the 'wait ' 
         characters will be counted as characters in the script. When 
	 read, the return value has no significant meaning, but a 1 is
	 always returned. "
    ::= { hcsNewCfgTableEntry 10 }

hcsNewCfgAddOpenProtCmd OBJECT-TYPE
    SYNTAX DisplayString (SIZE(0..31))
    MAX-ACCESS read-create
    STATUS current
    DESCRIPTION
        "Append an 'open' command to the script. The value of this object
         should be real server port number or name, followed by a comma,
	 and then the protocol (either tcp or udp), e.g. '80,tcp'.  Only
	 the port number or name, and tcp or udp should be set. The 'open ' 
	 characters will be automatically appended. Also a 'null terminator'
         (\0) will be automatically appended. The null terminator and the
         'open ' characters will be counted as characters in the script."
    ::= { hcsNewCfgTableEntry 11 }

hcsNewCfgAddNsendCmd OBJECT-TYPE
    SYNTAX DisplayString (SIZE(0..255))
    MAX-ACCESS read-create
    STATUS obsolete
    DESCRIPTION
        "Append an 'nsend' command to the script. The 'nsend' command is
	 used to append additional content to the packet generated by the
    	 'bsend' command when the desired 'bsend' content is more than 255
	 characters.  The set value of this object should be the exact
	 characters to be appended.  The 'nsend ' characters will be
         automatically appended.  Also a 'null terminator' (\0) will be
         automatically appended. The null terminator and the 'nsend '
         characters will be counted as characters in the script."
    ::= { hcsNewCfgTableEntry 12 }

hcsNewCfgAddNexpectCmd OBJECT-TYPE
    SYNTAX DisplayString (SIZE(0..255))
    MAX-ACCESS read-create
    STATUS obsolete
    DESCRIPTION
        "Append an 'nexpect' command to the script.  The 'nexpect' command
	 is used to append additional characters to the 'bexpect' string
	 when the desired 'bexpect' string is more than 255 characters.  The
	 set value of this object should be the exact characters to be
	 appended.  The 'nexpect ' characters will be automatically appended. 
         Also a 'null terminator'(\0) will be automatically appended. 
         The null terminator and the 'nexpect ' characters will be counted 
	 as characters in the script."
    ::= { hcsNewCfgTableEntry 13 }

hcsNewCfgAddDepthCmd OBJECT-TYPE
    SYNTAX INTEGER (1..1464)
    MAX-ACCESS read-create
    STATUS current
    DESCRIPTION
        "Append a 'depth' command to the script. The set value of this
	 object should be the depth (search window) within the data
	 area of the TCP/UDP packet for matching the string configured
	 in the last bexpect command. The 'depth ' characters will be
         automatically appended. Also a 'null terminator'(\0) will be 
         automatically appended. The null terminator and the 'depth '
         characters will be counted as characters in the script. When 
	 read, the return value has no significant meaning, but a 1 is
	 always returned."
    ::= { hcsNewCfgTableEntry 14 }

hcsNewCfgAddLongBsendCmd OBJECT-TYPE
    SYNTAX OCTET STRING (SIZE(0..506))
    MAX-ACCESS read-create
    STATUS current
    DESCRIPTION
        "Append a 'bsend' command to the script. The set value of this
	 object should be the exact binary data in hex format to be sent 
         on the port opened with the 'open' command. The 'bsend ' characters 
         will be automatically appended. Also a 'null terminator' (\0)
	 will be automatically appended. The null terminator and the 'bsend '
	 characters will be counted as characters in the script."
    ::= { hcsNewCfgTableEntry 15 }

hcsNewCfgAddLongBexpectCmd OBJECT-TYPE
    SYNTAX OCTET STRING (SIZE(0..504))
    MAX-ACCESS read-create
    STATUS current
    DESCRIPTION
        "Append a 'bexpect' command to the script. The set value of this 
	 object should be the exact binary data in hex format expected to
	 be received on the port opened with the 'open' command. The value 
         could also be a single wildcard character '*' which means any 
         received content will be accepted.  The 'bexpect ' characters 
	 will be automatically appended.  Also a 'null terminator'(\0)
	 will be automatically appended.  The null terminator and the 
	 'bexpect ' characters will be counted as characters in the script."
    ::= { hcsNewCfgTableEntry 16 }

hcsNewCfgAddLongSendCmd OBJECT-TYPE
    SYNTAX OCTET STRING (SIZE(0..507))
    MAX-ACCESS read-create
    STATUS current
    DESCRIPTION
        "Append an 'send' command to the script. The set value of this object
         should be the exact characters to be sent on the port opened with the
         'open' command. The 'send ' characters will be automatically appended.
         Also a 'null terminator' (\0) will be automatically appended. The null
         terminator and the 'send ' characters will be counted as characters in
         the script."
    ::= { hcsNewCfgTableEntry 17 }

hcsNewCfgAddLongExpectCmd OBJECT-TYPE
    SYNTAX OCTET STRING (SIZE(0..505))
    MAX-ACCESS read-create
    STATUS current
    DESCRIPTION
        "Append an 'expect' command to the script. The set value of this 
	 object should be the exact characters expected to be received on
         the port opened with the 'open' command.  The value could also be
         a single wildcard character '*' which means any received content
	 will be accepted.  The 'expect ' characters will be automatically 
	 appended.  Also a 'null terminator'(\0) will be automatically  
         appended.  The null terminator and the 'expect ' characters will
         be counted as characters in the script."
    ::= { hcsNewCfgTableEntry 18 }

hcsNewCfgAddLongNsendCmd OBJECT-TYPE
    SYNTAX OCTET STRING (SIZE(0..506))
    MAX-ACCESS read-create
    STATUS current
    DESCRIPTION
        "Append an 'nsend' command to the script. The 'nsend' command is
	 used to append additional content to the packet generated by the
    	 'bsend' command when the desired 'bsend' content is more than 255
	 characters.  The set value of this object should be the exact
	 characters to be appended.  The 'nsend ' characters will be
         automatically appended.  Also a 'null terminator' (\0) will be
         automatically appended. The null terminator and the 'nsend '
         characters will be counted as characters in the script."
    ::= { hcsNewCfgTableEntry 19 }

hcsNewCfgAddLongNexpectCmd OBJECT-TYPE
    SYNTAX OCTET STRING (SIZE(0..504))
    MAX-ACCESS read-create
    STATUS current
    DESCRIPTION
        "Append an 'nexpect' command to the script.  The 'nexpect' command
	 is used to append additional characters to the 'bexpect' string
	 when the desired 'bexpect' string is more than 255 characters.  The
	 set value of this object should be the exact characters to be
	 appended.  The 'nexpect ' characters will be automatically appended. 
         Also a 'null terminator'(\0) will be automatically appended. 
         The null terminator and the 'nexpect ' characters will be counted 
	 as characters in the script."
    ::= { hcsNewCfgTableEntry 20 }

-- SNMP health check configuration 
 
snmphcTableMaxSize OBJECT-TYPE
    SYNTAX  Integer32
    MAX-ACCESS  read-only
    STATUS  current
    DESCRIPTION
        "The maximum number of SNMP health check entries."
    ::= { snmphcCfg 1 }

snmphcCurCfgTable OBJECT-TYPE
    SYNTAX  SEQUENCE OF SnmphcCurCfgTableEntry
    MAX-ACCESS  not-accessible
    STATUS  current
    DESCRIPTION
        "The SNMP health check table in the current configuration block."
    ::= { snmphcCfg 2 }

snmphcCurCfgTableEntry OBJECT-TYPE
    SYNTAX  SnmphcCurCfgTableEntry
    MAX-ACCESS  not-accessible
    STATUS  current
    DESCRIPTION
        "A row in the SNMP health check table."
    INDEX   { snmphcCurCfgIndex }
    ::= { snmphcCurCfgTable 1 }

SnmphcCurCfgTableEntry ::= SEQUENCE {
    snmphcCurCfgIndex          Integer32,
    snmphcCurCfgOid            DisplayString,
    snmphcCurCfgCommString     DisplayString,
    snmphcCurCfgRcvContent     DisplayString,
    snmphcCurCfgInvert         INTEGER,
    snmphcCurCfgUseWeight      INTEGER
    }

snmphcCurCfgIndex OBJECT-TYPE
    SYNTAX Integer32
    MAX-ACCESS read-only
    STATUS current
    DESCRIPTION
        "The index of the SNMP health check."
    ::= { snmphcCurCfgTableEntry 1 }

snmphcCurCfgOid OBJECT-TYPE
    SYNTAX DisplayString (SIZE(0..128))
    MAX-ACCESS read-only
    STATUS current
    DESCRIPTION
        "The OID to be sent in the SNMP get request packet."
    ::= { snmphcCurCfgTableEntry 2 }

snmphcCurCfgCommString OBJECT-TYPE
    SYNTAX DisplayString (SIZE(0..32))
    MAX-ACCESS read-only
    STATUS current
    DESCRIPTION
        "The community string to be used in the SNMP get request packet."
    ::= { snmphcCurCfgTableEntry 3 }

snmphcCurCfgRcvContent OBJECT-TYPE
    SYNTAX DisplayString (SIZE(0..64))
    MAX-ACCESS read-only
    STATUS current
    DESCRIPTION
        "The content expected in the SNMP response packet. The content  
        specified can be either a string or an integer value."
    ::= { snmphcCurCfgTableEntry 4 }

snmphcCurCfgInvert OBJECT-TYPE
    SYNTAX INTEGER {
        enabled(1),
        disabled(2)
        }
    MAX-ACCESS read-only
    STATUS current
    DESCRIPTION
        "When the invert option is enabled the health check will fail if
         the response packet contains the value specified in the 
         receive content field."
    ::= { snmphcCurCfgTableEntry 5 }

snmphcCurCfgUseWeight OBJECT-TYPE
    SYNTAX INTEGER {
        enabled(1),
        disabled(2)
        }
    MAX-ACCESS read-only
    STATUS current
    DESCRIPTION
        "When the weight option is enabled the real server weights are 
         adjusted dynamically based on the SNMP health check response."
    ::= { snmphcCurCfgTableEntry 6 }

snmphcNewCfgTable OBJECT-TYPE
    SYNTAX  SEQUENCE OF SnmphcNewCfgTableEntry
    MAX-ACCESS  not-accessible
    STATUS  current
    DESCRIPTION
        "The SNMP health check table in the new configuration block."
    ::= { snmphcCfg 3 }

snmphcNewCfgTableEntry OBJECT-TYPE
    SYNTAX  SnmphcNewCfgTableEntry
    MAX-ACCESS  not-accessible
    STATUS  current
    DESCRIPTION
        "A row in the SNMP health check table."
    INDEX   { snmphcNewCfgIndex }
    ::= { snmphcNewCfgTable 1 }

SnmphcNewCfgTableEntry ::= SEQUENCE {
    snmphcNewCfgIndex          Integer32,
    snmphcNewCfgOid            DisplayString,
    snmphcNewCfgCommString     DisplayString,
    snmphcNewCfgRcvContent     DisplayString,
    snmphcNewCfgInvert         INTEGER,
    snmphcNewCfgDeleteHc       INTEGER,
    snmphcNewCfgUseWeight      INTEGER
    }

snmphcNewCfgIndex OBJECT-TYPE
    SYNTAX Integer32
    MAX-ACCESS read-only
    STATUS current
    DESCRIPTION
        "The index of the SNMP health check."
    ::= { snmphcNewCfgTableEntry 1 }

snmphcNewCfgOid OBJECT-TYPE
    SYNTAX DisplayString (SIZE(0..128))
    MAX-ACCESS read-create
    STATUS current
    DESCRIPTION
        "The OID to be sent in the SNMP get request packet."
    ::= { snmphcNewCfgTableEntry 2 }

snmphcNewCfgCommString OBJECT-TYPE
    SYNTAX DisplayString (SIZE(0..32))
    MAX-ACCESS read-create
    STATUS current
    DESCRIPTION
        "The community string to be used in the SNMP get request packet."
    ::= { snmphcNewCfgTableEntry 3 }

snmphcNewCfgRcvContent OBJECT-TYPE
    SYNTAX DisplayString (SIZE(0..64))
    MAX-ACCESS read-create
    STATUS current
    DESCRIPTION
        "The content expected in the SNMP response packet. The content  
        specified can be either a string or an integer value."
    ::= { snmphcNewCfgTableEntry 4 }

snmphcNewCfgInvert OBJECT-TYPE
    SYNTAX INTEGER {
        enabled(1),
        disabled(2)
        }
    MAX-ACCESS read-create
    STATUS current
    DESCRIPTION
        "When the invert option is enabled the health check will fail if
         the response packet contains the value specified in the 
         receive content field."
    ::= { snmphcNewCfgTableEntry 5 }

snmphcNewCfgDeleteHc OBJECT-TYPE
    SYNTAX INTEGER {
        other(1),
        delete(2)
        }
    MAX-ACCESS read-create
    STATUS current
    DESCRIPTION
        "When set to the value of 2 (delete), the entire row is deleted.
         When read, other(1) is returned. Setting the value to anything
         other than 2(delete) has no effect on the state of the row."
    ::= { snmphcNewCfgTableEntry 6 }

snmphcNewCfgUseWeight OBJECT-TYPE
    SYNTAX INTEGER {
        enabled(1),
        disabled(2)
        }
    MAX-ACCESS read-create
    STATUS current
    DESCRIPTION
        "When the weight option is enabled the real server weights are 
         adjusted dynamically based on the SNMP health check response."
    ::= { snmphcNewCfgTableEntry 7 }

-- Table sizes in current/new configuration of various tables

curCfgFilterTableSize OBJECT-TYPE
    SYNTAX Integer32 
    MAX-ACCESS read-only 
    STATUS current 
    DESCRIPTION 
        "Indicates the number of entries in the filter table current 
         configuration." 
    ::= { layer4TableSize 1 }

newCfgFilterTableSize OBJECT-TYPE
    SYNTAX Integer32 
    MAX-ACCESS read-only 
    STATUS current 
    DESCRIPTION 
        "Indicates the number of entries in the filter table new 
         configuration." 
    ::= { layer4TableSize 2 }

curCfgRealServerTableSize OBJECT-TYPE
    SYNTAX Integer32 
    MAX-ACCESS read-only 
    STATUS current 
    DESCRIPTION 
        "Indicates the number of entries in the SLB real server table 
         current configuration." 
    ::= { layer4TableSize 3 }

newCfgRealServerTableSize OBJECT-TYPE
    SYNTAX Integer32 
    MAX-ACCESS read-only 
    STATUS current 
    DESCRIPTION 
        "Indicates the number of entries in the SLB real server table 
         new configuration." 
    ::= { layer4TableSize 4 }

curCfgRealServerGroupTableSize OBJECT-TYPE
    SYNTAX Integer32 
    MAX-ACCESS read-only 
    STATUS current 
    DESCRIPTION 
        "Indicates the number of entries in the SLB real server group table 
         current configuration." 
    ::= { layer4TableSize 5 }

newCfgRealServerGroupTableSize OBJECT-TYPE
    SYNTAX Integer32 
    MAX-ACCESS read-only 
    STATUS current 
    DESCRIPTION 
        "Indicates the number of entries in the SLB real server group table 
         new configuration." 
    ::= { layer4TableSize 6 }

curCfgVirtServerTableSize OBJECT-TYPE
    SYNTAX Integer32 
    MAX-ACCESS read-only 
    STATUS current 
    DESCRIPTION 
        "Indicates the number of entries in the SLB virtual server table 
         current configuration." 
    ::= { layer4TableSize 7 }

newCfgVirtServerTableSize OBJECT-TYPE
    SYNTAX Integer32 
    MAX-ACCESS read-only 
    STATUS current 
    DESCRIPTION 
        "Indicates the number of entries in the SLB virtual server table 
         new configuration." 
    ::= { layer4TableSize 8 }

-- PIP Table configuration 
 
pipTableMaxSize OBJECT-TYPE
    SYNTAX  Integer32
    MAX-ACCESS  read-only
    STATUS  current
    DESCRIPTION
        "The maximum number of PIP entries."
    ::= { pipTblCfg 1 }
    
pipCurCfgBaseType OBJECT-TYPE
    SYNTAX INTEGER {
        port(1),
        vlan(2)
        }
    MAX-ACCESS  read-only
    STATUS  current
    DESCRIPTION
        "The PIP base. 1 = port based, 2 = VLAN based"
    ::= { pipTblCfg 2 }
    
pipCurCfgTable OBJECT-TYPE
    SYNTAX  SEQUENCE OF PipCurCfgTableEntry
    MAX-ACCESS  not-accessible
    STATUS  current
    DESCRIPTION
        "The PIP table in the current configuration block."
    ::= { pipTblCfg 3 }

pipCurCfgTableEntry OBJECT-TYPE
    SYNTAX  PipCurCfgTableEntry
    MAX-ACCESS  not-accessible
    STATUS  current
    DESCRIPTION
        "A row in the PIP table."
    INDEX   { pipCurCfgPip }
    ::= { pipCurCfgTable 1 }

PipCurCfgTableEntry ::= SEQUENCE {
    pipCurCfgPip            IpAddress,
    pipCurCfgPortMap	    OCTET STRING,
    pipCurCfgVlanMap        OCTET STRING
    }

pipCurCfgPip OBJECT-TYPE
    SYNTAX  IpAddress
    MAX-ACCESS  read-only
    STATUS  current
    DESCRIPTION
        "Proxy IP address by the instance of the pipCurCfgIndex." 
    ::= { pipCurCfgTableEntry 1 }
    
pipCurCfgPortMap    OBJECT-TYPE
    SYNTAX  OCTET STRING (SIZE(0..8))
    MAX-ACCESS  read-only
    STATUS  current
    DESCRIPTION
        "This is a bit map of port. 
         in receiving order:

             OCTET 1  OCTET 2  .....
             xxxxxxxx xxxxxxxx ..... 
             ||    || |_ port 8
             ||    ||  
             ||    ||___ port 7
             ||    |____ port 6
             ||_________ port 1
             |__________ unused
 
         where x : 1 - PIP is used for this port.
               x : 0 - PIP Not used for this port."
         
    ::= { pipCurCfgTableEntry 2 }
    
pipCurCfgVlanMap    OBJECT-TYPE
    SYNTAX  OCTET STRING (SIZE(0..512))
    MAX-ACCESS  read-only
    STATUS  current
    DESCRIPTION
        "This is a bit map of VLAN. 

         in receiving order:

             OCTET 1  OCTET 2  .....
             xxxxxxxx xxxxxxxx ..... 
             ||    || |_ VLAN 8
             ||    ||  
             ||    ||___ VLAN 7
             ||    |____ VLAN 6
             ||_________ VLAN 1
             |__________ unused
 
         where x : 1 - PIP is used for this VLAN.
               x : 0 - PIP Not used for this VLAN."
         
    ::= { pipCurCfgTableEntry 3 }
    
pipNewCfgBaseType OBJECT-TYPE
    SYNTAX INTEGER {
        port(1),
        vlan(2)
        }
    MAX-ACCESS  read-write
    STATUS  current
    DESCRIPTION
        "The PIP base. 1 = port based, 2 = VLAN based"
    ::= { pipTblCfg 4 }
    
pipNewCfgTable OBJECT-TYPE
    SYNTAX  SEQUENCE OF PipNewCfgTableEntry
    MAX-ACCESS  not-accessible
    STATUS  current
    DESCRIPTION
        "The PIP table in the New configuration block."
    ::= { pipTblCfg 5 }

pipNewCfgTableEntry OBJECT-TYPE
    SYNTAX  PipNewCfgTableEntry
    MAX-ACCESS  not-accessible
    STATUS  current
    DESCRIPTION
        "A row in the PIP table."
    INDEX   { pipNewCfgPip }
    ::= { pipNewCfgTable 1 }

PipNewCfgTableEntry ::= SEQUENCE {
    pipNewCfgPip                IpAddress,
    pipNewCfgPortMap            OCTET STRING,
    pipNewCfgVlanMap            OCTET STRING,
    pipNewCfgDelete             INTEGER,
    pipNewCfgAddPortVlan        Integer32,
    pipNewCfgRemovePortVlan     Integer32,
    pipNewCfgAddPort            Integer32,
    pipNewCfgAddVlan            Integer32,
    pipNewCfgRemovePort         Integer32,
    pipNewCfgRemoveVlan         Integer32
    }

pipNewCfgPip OBJECT-TYPE
    SYNTAX  IpAddress
    MAX-ACCESS  read-only
    STATUS  current
    DESCRIPTION
        "PIP address by the instance of the pipCurCfgIndex." 
    ::= { pipNewCfgTableEntry 1 }
    
pipNewCfgPortMap    OBJECT-TYPE
    SYNTAX  OCTET STRING (SIZE(0..8))
    MAX-ACCESS  read-only
    STATUS  current
    DESCRIPTION
        "The bit map of port for PIP.
         in receiving order:

             OCTET 1  OCTET 2  .....
             xxxxxxxx xxxxxxxx ..... 
             ||    || |_ port 8
             ||    ||  
             ||    ||___ port 7
             ||    |____ port 6
             ||_________ port 1
             |__________ unused
 
         where x : 1 - PIP is used for this port.
               x : 0 - PIP Not used for this port."
 
    ::= { pipNewCfgTableEntry 2 }
    
pipNewCfgVlanMap    OBJECT-TYPE
    SYNTAX  OCTET STRING (SIZE(0..512))
    MAX-ACCESS  read-only
    STATUS  current
    DESCRIPTION
        "The bit map of VLAN for PIP.
         in receiving order:

             OCTET 1  OCTET 2  .....
             xxxxxxxx xxxxxxxx ..... 
             ||    || |_ VLAN 8
             ||    ||  
             ||    ||___ VLAN 7
             ||    |____ VLAN 6
             ||_________ VLAN 1
             |__________ unused
 
         where x : 1 - PIP is used for this VLAN.
               x : 0 - PIP Not used for this VLAN."
 
    ::= { pipNewCfgTableEntry 3 }

pipNewCfgDelete OBJECT-TYPE
    SYNTAX  INTEGER {
        other(1),
        delete(2)
        }
    MAX-ACCESS  read-create
    STATUS  current
    DESCRIPTION
        "By setting the value to delete(2), the entire row is deleted."
    ::= { pipNewCfgTableEntry 4 }

pipNewCfgAddPortVlan OBJECT-TYPE
    SYNTAX  Integer32
    MAX-ACCESS  read-create
    STATUS  current
    DESCRIPTION
        "The Port or VLAN to be associated with the PIP. When read, 0 is returned."
    ::= { pipNewCfgTableEntry 5 }

pipNewCfgRemovePortVlan OBJECT-TYPE 
    SYNTAX  Integer32 
    MAX-ACCESS  read-create 
    STATUS  current
    DESCRIPTION
        "The Port or VLAN to be disassociated from the PIP. When read, 
         0 is returned."
    ::= { pipNewCfgTableEntry 6 }

pipNewCfgAddPort OBJECT-TYPE
    SYNTAX  Integer32
    MAX-ACCESS  read-create
    STATUS  current
    DESCRIPTION
        "The Port to be associated with the PIP. When read, 0 is returned."
    ::= { pipNewCfgTableEntry 7 }

pipNewCfgAddVlan OBJECT-TYPE
    SYNTAX  Integer32
    MAX-ACCESS  read-create
    STATUS  current
    DESCRIPTION
        "The VLAN to be associated with the PIP. When read, 0 is returned."
    ::= { pipNewCfgTableEntry 8 }

pipNewCfgRemovePort OBJECT-TYPE 
    SYNTAX  Integer32 
    MAX-ACCESS  read-create 
    STATUS  current
    DESCRIPTION
        "The Port to be disassociated from the PIP. When read, 
         0 is returned."
    ::= { pipNewCfgTableEntry 9 }

pipNewCfgRemoveVlan OBJECT-TYPE 
    SYNTAX  Integer32 
    MAX-ACCESS  read-create 
    STATUS  current
    DESCRIPTION
        "The VLAN to be disassociated from the PIP. When read, 
         0 is returned."
    ::= { pipNewCfgTableEntry 10 }

-- IPv6 Proxy IP Configuration

pip6CurCfgTable OBJECT-TYPE
    SYNTAX  SEQUENCE OF Pip6CurCfgTableEntry
    MAX-ACCESS  not-accessible
    STATUS  current
    DESCRIPTION
        "The IPv6 PIP table in the current configuration block."
    ::= { pipTblCfg 6 }

pip6CurCfgTableEntry OBJECT-TYPE
    SYNTAX  Pip6CurCfgTableEntry
    MAX-ACCESS  not-accessible
    STATUS  current
    DESCRIPTION
        "A row in the IPv6 PIP table."
    INDEX   { pip6CurCfgPip }
    ::= { pip6CurCfgTable 1 }

Pip6CurCfgTableEntry ::= SEQUENCE {
    pip6CurCfgPip           DisplayString,
    pip6CurCfgPortMap	    OCTET STRING,
    pip6CurCfgVlanMap       OCTET STRING
    }

pip6CurCfgPip OBJECT-TYPE
    SYNTAX  DisplayString (SIZE(0..40))
    MAX-ACCESS  read-only
    STATUS  current
    DESCRIPTION
        "IPv6 Proxy IP address by the instance of the pip6CurCfgIndex." 
    ::= { pip6CurCfgTableEntry 1 }
    
pip6CurCfgPortMap    OBJECT-TYPE
    SYNTAX  OCTET STRING (SIZE(0..8))
    MAX-ACCESS  read-only
    STATUS  current
    DESCRIPTION
        "This is a bit map of port. 
         in receiving order:

             OCTET 1  OCTET 2  .....
             xxxxxxxx xxxxxxxx ..... 
             ||    || |_ port 8
             ||    ||  
             ||    ||___ port 7
             ||    |____ port 6
             ||_________ port 1
             |__________ unused
 
         where x : 1 - PIP is used for this port.
               x : 0 - PIP Not used for this port."
         
    ::= { pip6CurCfgTableEntry 2 }
    
pip6CurCfgVlanMap    OBJECT-TYPE
    SYNTAX  OCTET STRING (SIZE(0..512))
    MAX-ACCESS  read-only
    STATUS  current
    DESCRIPTION
        "This is a bit map of VLAN. 

         in receiving order:

             OCTET 1  OCTET 2  .....
             xxxxxxxx xxxxxxxx ..... 
             ||    || |_ VLAN 8
             ||    ||  
             ||    ||___ VLAN 7
             ||    |____ VLAN 6
             ||_________ VLAN 1
             |__________ unused
 
         where x : 1 - PIP is used for this VLAN.
               x : 0 - PIP Not used for this VLAN."
         
    ::= { pip6CurCfgTableEntry 3 }
    
pip6NewCfgTable OBJECT-TYPE
    SYNTAX  SEQUENCE OF Pip6NewCfgTableEntry
    MAX-ACCESS  not-accessible
    STATUS  current
    DESCRIPTION
        "The IPv6 PIP table in the New configuration block."
    ::= { pipTblCfg 7 }

pip6NewCfgTableEntry OBJECT-TYPE
    SYNTAX  Pip6NewCfgTableEntry
    MAX-ACCESS  not-accessible
    STATUS  current
    DESCRIPTION
        "A row in the IPv6 PIP table."
    INDEX   { pip6NewCfgPip }
    ::= { pip6NewCfgTable 1 }

Pip6NewCfgTableEntry ::= SEQUENCE {
    pip6NewCfgPip               DisplayString,
    pip6NewCfgPortMap           OCTET STRING,
    pip6NewCfgVlanMap           OCTET STRING,
    pip6NewCfgDelete            INTEGER,
    pip6NewCfgAddPortVlan       Integer32,
    pip6NewCfgRemovePortVlan    Integer32,
    pip6NewCfgAddPort           Integer32,
    pip6NewCfgAddVlan           Integer32,
    pip6NewCfgRemovePort        Integer32,
    pip6NewCfgRemoveVlan        Integer32
    }

pip6NewCfgPip OBJECT-TYPE
    SYNTAX DisplayString (SIZE(0..50)) 
    MAX-ACCESS  read-only
    STATUS  current
    DESCRIPTION
        "IPv6 PIP address by the instance of the pip6CurCfgIndex." 
    ::= { pip6NewCfgTableEntry 1 }
    
pip6NewCfgPortMap    OBJECT-TYPE
    SYNTAX  OCTET STRING (SIZE(0..8))
    MAX-ACCESS  read-only
    STATUS  current
    DESCRIPTION
        "The bit map of port for PIP.
         in receiving order:

             OCTET 1  OCTET 2  .....
             xxxxxxxx xxxxxxxx ..... 
             ||    || |_ port 8
             ||    ||  
             ||    ||___ port 7
             ||    |____ port 6
             ||_________ port 1
             |__________ unused
 
         where x : 1 - PIP is used for this port.
               x : 0 - PIP Not used for this port."
 
    ::= { pip6NewCfgTableEntry 2 }
    
pip6NewCfgVlanMap    OBJECT-TYPE
    SYNTAX  OCTET STRING (SIZE(0..512))
    MAX-ACCESS  read-only
    STATUS  current
    DESCRIPTION
        "The bit map of VLAN for PIP.
         in receiving order:

             OCTET 1  OCTET 2  .....
             xxxxxxxx xxxxxxxx ..... 
             ||    || |_ VLAN 8
             ||    ||  
             ||    ||___ VLAN 7
             ||    |____ VLAN 6
             ||_________ VLAN 1
             |__________ unused
 
         where x : 1 - PIP is used for this VLAN.
               x : 0 - PIP Not used for this VLAN."
 
    ::= { pip6NewCfgTableEntry 3 }

pip6NewCfgDelete OBJECT-TYPE
    SYNTAX  INTEGER {
        other(1),
        delete(2)
        }
    MAX-ACCESS  read-create
    STATUS  current
    DESCRIPTION
        "By setting the value to delete(2), the entire row is deleted."
    ::= { pip6NewCfgTableEntry 4 }

pip6NewCfgAddPortVlan OBJECT-TYPE
    SYNTAX  Integer32
    MAX-ACCESS  read-create
    STATUS  current
    DESCRIPTION
        "The Port or VLAN to be associated with the PIP. When read, 0 is returned."
    ::= { pip6NewCfgTableEntry 5 }

pip6NewCfgRemovePortVlan OBJECT-TYPE 
    SYNTAX  Integer32 
    MAX-ACCESS  read-create 
    STATUS  current
    DESCRIPTION
        "The Port or VLAN to be disassociated from the PIP. When read, 
         0 is returned."
    ::= { pip6NewCfgTableEntry 6 }

pip6NewCfgAddPort OBJECT-TYPE
    SYNTAX  Integer32
    MAX-ACCESS  read-create
    STATUS  current
    DESCRIPTION
        "The Port to be associated with the PIP. When read, 0 is returned."
    ::= { pip6NewCfgTableEntry 7 }

pip6NewCfgAddVlan OBJECT-TYPE
    SYNTAX  Integer32
    MAX-ACCESS  read-create
    STATUS  current
    DESCRIPTION
        "The VLAN to be associated with the PIP. When read, 0 is returned."
    ::= { pip6NewCfgTableEntry 8 }

pip6NewCfgRemovePort OBJECT-TYPE 
    SYNTAX  Integer32 
    MAX-ACCESS  read-create 
    STATUS  current
    DESCRIPTION
        "The Port to be disassociated from the PIP. When read, 
         0 is returned."
    ::= { pip6NewCfgTableEntry 9 }

pip6NewCfgRemoveVlan OBJECT-TYPE 
    SYNTAX  Integer32 
    MAX-ACCESS  read-create 
    STATUS  current
    DESCRIPTION
        "The VLAN to be disassociated from the PIP. When read, 
         0 is returned."
    ::= { pip6NewCfgTableEntry 10 }


-- SLB Statistics Group

-- SLB SP Real Servers Statistics Table

slbStatSpRealServerTable OBJECT-TYPE
    SYNTAX  SEQUENCE OF SlbStatSpRealServerEntry
    MAX-ACCESS  not-accessible
    STATUS  current
    DESCRIPTION
        "The sp-server statistics table.  This table shows the statistics 
         of real servers for a particular SP."
    ::= { slbSpStats 1 }

slbStatSpRealServerEntry OBJECT-TYPE
    SYNTAX  SlbStatSpRealServerEntry
    MAX-ACCESS  not-accessible
    STATUS  current
    DESCRIPTION
        "A row in the sp-server statistics table."
    INDEX  { slbStatSpRealServerSpIndex, slbStatSpRealServerServerIndex }
    ::= { slbStatSpRealServerTable 1 }

SlbStatSpRealServerEntry ::= SEQUENCE {
    slbStatSpRealServerSpIndex               Integer32,
    slbStatSpRealServerServerIndex           Integer32,
    slbStatSpRealServerCurrSessions          Gauge32,
    slbStatSpRealServerTotalSessions         Counter32,
    slbStatSpRealServerHCOctetsLow32         Counter32,
    slbStatSpRealServerHCOctetsHigh32        Counter32,
    slbStatSpRealServerHCOctets              Counter64
    }

slbStatSpRealServerSpIndex OBJECT-TYPE
    SYNTAX  Integer32
    MAX-ACCESS  read-only
    STATUS  current
    DESCRIPTION
        "The SP index."
    ::= { slbStatSpRealServerEntry 1 }

slbStatSpRealServerServerIndex OBJECT-TYPE 
    SYNTAX  Integer32 
    MAX-ACCESS  read-only
    STATUS  current 
    DESCRIPTION 
        "The real server number that identifies the server." 
    ::= { slbStatSpRealServerEntry 2 }

slbStatSpRealServerCurrSessions OBJECT-TYPE 
    SYNTAX  Gauge32
    MAX-ACCESS  read-only
    STATUS  current 
    DESCRIPTION 
        "The current sessions for the real server."
    ::= { slbStatSpRealServerEntry 3 }

slbStatSpRealServerTotalSessions OBJECT-TYPE 
    SYNTAX  Counter32 
    MAX-ACCESS  read-only
    STATUS  current 
    DESCRIPTION 
        "The total number of sessions for the real server."
    ::= { slbStatSpRealServerEntry 4 }

slbStatSpRealServerHCOctetsLow32 OBJECT-TYPE
    SYNTAX  Counter32
    MAX-ACCESS  read-only
    STATUS  current
    DESCRIPTION
        "The lower 32 bit value of the total octets received and transmitted 
         out of the real server on a particular SP."
    ::= { slbStatSpRealServerEntry 5 }

slbStatSpRealServerHCOctetsHigh32 OBJECT-TYPE
    SYNTAX  Counter32
    MAX-ACCESS  read-only
    STATUS  current
    DESCRIPTION
        "The higher 32 bit value of the total octets received and transmitted 
         out of the real server on a particular SP."
    ::= { slbStatSpRealServerEntry 6 }

slbStatSpRealServerHCOctets OBJECT-TYPE
    SYNTAX  Counter64
    MAX-ACCESS  read-only
    STATUS  current
    DESCRIPTION
        "The total octets received and transmitted by the real server on a 
         particular SP."
    ::= { slbStatSpRealServerEntry 7 }

slbStatSpFltTable OBJECT-TYPE
    SYNTAX  SEQUENCE OF SlbStatSpFltEntry
    MAX-ACCESS  not-accessible
    STATUS  current
    DESCRIPTION
        "The filter statistics table.  This table shows the statistics 
         of filters for a particular SP."
    ::= { slbSpStats 4 }

slbStatSpFltEntry OBJECT-TYPE
    SYNTAX  SlbStatSpFltEntry
    MAX-ACCESS  not-accessible
    STATUS  current
    DESCRIPTION
        "A row in the filter statistics table."
    INDEX  { slbStatSpFltSpIndex, slbStatSpFltIndex }
    ::= { slbStatSpFltTable 1 }

SlbStatSpFltEntry ::= SEQUENCE {
    slbStatSpFltSpIndex               Integer32,
    slbStatSpFltIndex                 Integer32,
    slbStatSpFltFirings               Counter32
    }

slbStatSpFltSpIndex OBJECT-TYPE
    SYNTAX  Integer32
    MAX-ACCESS  read-only
    STATUS  current
    DESCRIPTION
        "The SP index."
    ::= { slbStatSpFltEntry 1 }

slbStatSpFltIndex OBJECT-TYPE 
    SYNTAX  Integer32 
    MAX-ACCESS  read-only
    STATUS  current 
    DESCRIPTION 
        "The filter number." 
    ::= { slbStatSpFltEntry 2 }

slbStatSpFltFirings OBJECT-TYPE 
    SYNTAX  Counter32 
    MAX-ACCESS  read-only
    STATUS  current 
    DESCRIPTION 
        "The number of instances that the received packet matches the 
         filter rule on this SP."
    ::= { slbStatSpFltEntry 3 }

-- SLB Port Maintenance Statistics Table

slbStatSpMaintTable OBJECT-TYPE
    SYNTAX  SEQUENCE OF SlbStatSpMaintEntry
    MAX-ACCESS  not-accessible
    STATUS  current
    DESCRIPTION
        "The table of SLB SP maintenance statistics." 
    ::= { slbSpStats 5 }

slbStatSpMaintEntry OBJECT-TYPE
    SYNTAX  SlbStatSpMaintEntry
    MAX-ACCESS  not-accessible
    STATUS  current
    DESCRIPTION
        "A row in the SLB SP maintenance statistics table."
    INDEX   { slbStatSpMaintSpIndex }
    ::= { slbStatSpMaintTable 1 }
 
SlbStatSpMaintEntry ::= SEQUENCE {
    slbStatSpMaintSpIndex                   Integer32,
    slbStatSpMaintMaximumSessions           Integer32,
    slbStatSpMaintCurBindings               Gauge32,
    slbStatSpMaintCurBindings4Seconds       Gauge32,
    slbStatSpMaintCurBindings64Seconds      Gauge32,
    slbStatSpMaintTerminatedSessions        Counter32,
    slbStatSpMaintBindingFails              Counter32,
    slbStatSpMaintNonTcpFrames              Counter32,
    slbStatSpMaintTcpFragments              Counter32,
    slbStatSpMaintUdpDatagrams              Counter32,
    slbStatSpMaintIncorrectVIPs             Counter32,
    slbStatSpMaintIncorrectVports           Counter32,
    slbStatSpMaintRealServerNoAvails        Counter32,
    slbStatSpMaintFilteredDeniedFrames      Counter32,
    slbStatSpMaintLandAttacks		    Counter32,
    slbStatSpMaintIpFragTotalSessions	    Counter32,
    slbStatSpMaintIpFragCurSessions         Gauge32,
    slbStatSpMaintIpFragDiscards            Counter32,
    slbStatSpMaintIpFragTableFull           Counter32,
    slbStatSpMaintClear                     INTEGER,
    slbStatSpMaintOOSFinPktDrops            Counter32,
    slbStatSpMaintSymSessions		    Counter32,
    slbStatSpMaintSymValidSegments	    Counter32,
    slbStatSpMaintSymFragSessions	    Counter32,
    slbStatSpMaintSymSegAllocFails	    Counter32,
    slbStatSpMaintSymBufferAllocFails	    Counter32,	
    slbStatSpMaintSymConnAllocFails	    Counter32,
    slbStatSpMaintSymInvalidBuffers	    Counter32,
    slbStatSpMaintSymSegReallocFails	    Counter32,
    slbStatSpMaintSymPacketsIn		    Counter32,
    slbStatSpMaintSymPacketsWithNoData	    Counter32,
    slbStatSpMaintSymTcpPackets		    Counter32,
    slbStatSpMaintSymUdpPackets	            Counter32,
    slbStatSpMaintSymIcmpPackets	    Counter32,
    slbStatSpMaintSymOtherPackets	    Counter32,
    slbStatSpMaintSymMatchCount		    Counter32,
    slbStatSpMaintSymFetchErrors	    Counter32,
    slbStatSpMaintSymTruncPayloadToMp	    Counter32,
    slbStatSpMaintSymPacketsInFastPath	    Counter32
    }

slbStatSpMaintSpIndex OBJECT-TYPE
    SYNTAX  Integer32
    MAX-ACCESS  read-only
    STATUS  current
    DESCRIPTION
        "The SP number for which the statistics apply."
    ::= { slbStatSpMaintEntry 1 }

slbStatSpMaintMaximumSessions OBJECT-TYPE
    SYNTAX  Integer32
    MAX-ACCESS  read-only
    STATUS  current
    DESCRIPTION
        "The maximun number of entries per SP in the session table."
    ::= { slbStatSpMaintEntry 2 }

slbStatSpMaintCurBindings OBJECT-TYPE
    SYNTAX  Gauge32 
    MAX-ACCESS  read-only
    STATUS  current
    DESCRIPTION
        "The current number of sessions on the SP."
    ::= { slbStatSpMaintEntry 3 }

slbStatSpMaintCurBindings4Seconds OBJECT-TYPE
    SYNTAX  Gauge32 
    MAX-ACCESS  read-only
    STATUS  current
    DESCRIPTION
        "The 4 second average current number of sessions on the SP."
    ::= { slbStatSpMaintEntry 4 }

slbStatSpMaintCurBindings64Seconds OBJECT-TYPE
    SYNTAX  Gauge32 
    MAX-ACCESS  read-only
    STATUS  current
    DESCRIPTION
        "The 64 second average current number of sessions on the SP."
    ::= { slbStatSpMaintEntry 5 }

slbStatSpMaintTerminatedSessions OBJECT-TYPE
    SYNTAX  Counter32
    MAX-ACCESS  read-only
    STATUS  current
    DESCRIPTION
        "The count of the number of sessions closed because the server failed."
    ::= { slbStatSpMaintEntry 6 }

slbStatSpMaintBindingFails OBJECT-TYPE
    SYNTAX  Counter32
    MAX-ACCESS  read-only
    STATUS  current
    DESCRIPTION
        "The total number of binding failures on the SP. A binding failure 
         occurs when a SP runs out of session table entries."
    ::= { slbStatSpMaintEntry 7 }

slbStatSpMaintNonTcpFrames OBJECT-TYPE
    SYNTAX  Counter32
    MAX-ACCESS  read-only
    STATUS  current
    DESCRIPTION
        "The total number of non-TCP/IP frames dropped on the SP."
    ::= { slbStatSpMaintEntry 8 }

slbStatSpMaintTcpFragments OBJECT-TYPE
    SYNTAX  Counter32
    MAX-ACCESS  read-only
    STATUS  obsolete
    DESCRIPTION
        "The total number of TCP fragments dropped on the SP."
    ::= { slbStatSpMaintEntry 9 }

slbStatSpMaintUdpDatagrams OBJECT-TYPE
    SYNTAX  Counter32
    MAX-ACCESS  read-only
    STATUS  current
    DESCRIPTION
        "The total number of UDP datagrams dropped on the SP."
    ::= { slbStatSpMaintEntry 10 }

slbStatSpMaintIncorrectVIPs OBJECT-TYPE
    SYNTAX  Counter32
    MAX-ACCESS  read-only
    STATUS  current
    DESCRIPTION
        "The total number of frames with incorrect VIPs that are dropped on 
         the SP."
    ::= { slbStatSpMaintEntry 11 }

slbStatSpMaintIncorrectVports OBJECT-TYPE
    SYNTAX  Counter32
    MAX-ACCESS  read-only
    STATUS  current
    DESCRIPTION
        "The total number of frames with incorrect Virtual Port that are 
         dropped on the SP."
    ::= { slbStatSpMaintEntry 12 }

slbStatSpMaintRealServerNoAvails OBJECT-TYPE
    SYNTAX  Counter32
    MAX-ACCESS  read-only
    STATUS  current
    DESCRIPTION
        "The total number of frames that are dropped on the SP
	 because no real server is available."
    ::= { slbStatSpMaintEntry 13 }

slbStatSpMaintFilteredDeniedFrames OBJECT-TYPE
    SYNTAX  Counter32
    MAX-ACCESS  read-only
    STATUS  current
    DESCRIPTION
        "The total number of frames that are denied on the SP by the filter."
    ::= { slbStatSpMaintEntry 14 }

slbStatSpMaintLandAttacks OBJECT-TYPE
    SYNTAX  Counter32
    MAX-ACCESS  read-only
    STATUS  current
    DESCRIPTION
        "The total number of attacks that frames contain the same source
	 and destination IP addresses."
    ::= { slbStatSpMaintEntry 15 }

slbStatSpMaintIpFragTotalSessions OBJECT-TYPE
    SYNTAX  Counter32
    MAX-ACCESS  read-only
    STATUS  current
    DESCRIPTION
        "The total number of fragment sessions processed on the SP."
    ::= { slbStatSpMaintEntry 16 }

slbStatSpMaintIpFragCurSessions OBJECT-TYPE
    SYNTAX  Gauge32
    MAX-ACCESS  read-only
    STATUS  current
    DESCRIPTION
        "The number of sessions in the IP fragment binding table on the SP."
    ::= { slbStatSpMaintEntry 17 }

slbStatSpMaintIpFragDiscards OBJECT-TYPE
    SYNTAX  Counter32
    MAX-ACCESS  read-only
    STATUS  current
    DESCRIPTION
        "The total number of fragments discarded on the SP because there
         is no entry in the IP fragment binding table. "
    ::= { slbStatSpMaintEntry 18 }

slbStatSpMaintIpFragTableFull OBJECT-TYPE
    SYNTAX  Counter32
    MAX-ACCESS  read-only
    STATUS  current
    DESCRIPTION
        "The total number of times IP fragment binding table is full on the 
         SP."
    ::= { slbStatSpMaintEntry 19 }

slbStatSpMaintClear OBJECT-TYPE
    SYNTAX INTEGER {
	ok(1),
	clear(2)
	}
    MAX-ACCESS read-write
    STATUS current
    DESCRIPTION
        "This is an action object to clear the non-operational SLB statistics
         on the particular SP. 
         ok(1) is returned when read."
    ::= { slbStatSpMaintEntry 20 }

slbStatSpMaintOOSFinPktDrops OBJECT-TYPE
    SYNTAX  Counter32
    MAX-ACCESS  read-only
    STATUS  current
    DESCRIPTION
        "The total number of Out of state FIN Packets received on the SP."
    ::= { slbStatSpMaintEntry 21 }

-- START of Symantec SLB SP Maintenance Stats 
slbStatSpMaintSymSessions OBJECT-TYPE
    SYNTAX  Counter32
    MAX-ACCESS  read-only
    STATUS  current
    DESCRIPTION
        "Number of Symantec sessions."
    ::= { slbStatSpMaintEntry 22 }

slbStatSpMaintSymValidSegments OBJECT-TYPE
    SYNTAX  Counter32
    MAX-ACCESS  read-only
    STATUS  current
    DESCRIPTION
        "Number of Symantec valid segments."
    ::= { slbStatSpMaintEntry 23 }

slbStatSpMaintSymFragSessions OBJECT-TYPE
    SYNTAX  Counter32
    MAX-ACCESS  read-only
    STATUS  current
    DESCRIPTION
        "Number of Symantec fragment sessions."
    ::= { slbStatSpMaintEntry 24 }

slbStatSpMaintSymSegAllocFails OBJECT-TYPE
    SYNTAX  Counter32
    MAX-ACCESS  read-only
    STATUS  current
    DESCRIPTION
        "Number of Symantec segment allocation fails."
    ::= { slbStatSpMaintEntry 25 }

slbStatSpMaintSymBufferAllocFails OBJECT-TYPE
    SYNTAX  Counter32
    MAX-ACCESS  read-only
    STATUS  current
    DESCRIPTION
        "Number of Symantec buffers allocation fails."
    ::= { slbStatSpMaintEntry 26 }

slbStatSpMaintSymConnAllocFails OBJECT-TYPE
    SYNTAX  Counter32
    MAX-ACCESS  read-only
    STATUS  current
    DESCRIPTION
        "Number of Symantec Connection allocation fails."
    ::= { slbStatSpMaintEntry 27 }

slbStatSpMaintSymInvalidBuffers OBJECT-TYPE
    SYNTAX  Counter32
    MAX-ACCESS  read-only
    STATUS  current
    DESCRIPTION
        "Number of Symantec Invalid buffers."
    ::= { slbStatSpMaintEntry 28 }

slbStatSpMaintSymSegReallocFails OBJECT-TYPE
    SYNTAX  Counter32
    MAX-ACCESS  read-only
    STATUS  current
    DESCRIPTION
        "Number of Symantec Segment reallocation fails."
    ::= { slbStatSpMaintEntry 29 }

slbStatSpMaintSymPacketsIn OBJECT-TYPE
    SYNTAX  Counter32
    MAX-ACCESS  read-only
    STATUS  current
    DESCRIPTION
        "Symantec Deuce Inspection Stats - No. of packets in."
    ::= { slbStatSpMaintEntry 30 }

slbStatSpMaintSymPacketsWithNoData OBJECT-TYPE
    SYNTAX  Counter32
    MAX-ACCESS  read-only
    STATUS  current
    DESCRIPTION
        "Symantec Deuce Inspection Stats - No. of packets with no data."
    ::= { slbStatSpMaintEntry 31 }

slbStatSpMaintSymTcpPackets OBJECT-TYPE
    SYNTAX  Counter32
    MAX-ACCESS  read-only
    STATUS  current
    DESCRIPTION
        "Symantec Deuce Inspection Stats - No. of TCP packets"
    ::= { slbStatSpMaintEntry 32 }

slbStatSpMaintSymUdpPackets OBJECT-TYPE
    SYNTAX  Counter32
    MAX-ACCESS  read-only
    STATUS  current
    DESCRIPTION
        "Symantec Deuce Inspection Stats - No. of  UDP Packets"
    ::= { slbStatSpMaintEntry 33 }

slbStatSpMaintSymIcmpPackets OBJECT-TYPE
    SYNTAX  Counter32
    MAX-ACCESS  read-only
    STATUS  current
    DESCRIPTION
        "Symantec Deuce Inspection Stats - No. of  ICMP Packets"
    ::= { slbStatSpMaintEntry 34 }

slbStatSpMaintSymOtherPackets OBJECT-TYPE
    SYNTAX  Counter32
    MAX-ACCESS  read-only
    STATUS  current
    DESCRIPTION
        "Symantec Deuce Inspection Stats - No. of  Packets other than 
	 TCP UDP or ICMP"
    ::= { slbStatSpMaintEntry 35 }

slbStatSpMaintSymMatchCount OBJECT-TYPE
    SYNTAX  Counter32
    MAX-ACCESS  read-only
    STATUS  current
    DESCRIPTION
        "Symantec Deuce Inspection Stats - Match Count"
    ::= { slbStatSpMaintEntry 36 }

slbStatSpMaintSymFetchErrors OBJECT-TYPE
    SYNTAX  Counter32
    MAX-ACCESS  read-only
    STATUS  current
    DESCRIPTION
        "Symantec Deuce Inspection Stats - No. of Fetch Errors"
    ::= { slbStatSpMaintEntry 37 }

slbStatSpMaintSymTruncPayloadToMp OBJECT-TYPE
    SYNTAX  Counter32
    MAX-ACCESS  read-only
    STATUS  current
    DESCRIPTION
        "Symantec Deuce Inspection Stats - No. of Truncated payload to MP"
    ::= { slbStatSpMaintEntry 38 }

slbStatSpMaintSymPacketsInFastPath OBJECT-TYPE
    SYNTAX  Counter32
    MAX-ACCESS  read-only
    STATUS  current
    DESCRIPTION
        "Symantec Deuce Inspection Stats - No. of Packets in fast path"
    ::= { slbStatSpMaintEntry 39 }

-- END of Symantec SLB SP Maintenance Stats 

slbStatSpAuxSessTable OBJECT-TYPE
    SYNTAX  SEQUENCE OF SlbStatSpAuxSessEntry
    MAX-ACCESS  not-accessible
    STATUS  current
    DESCRIPTION
        "The auxiliary session table statistics for a particular SP."
    ::= { slbSpStats 6 }

slbStatSpAuxSessEntry OBJECT-TYPE
    SYNTAX  SlbStatSpAuxSessEntry
    MAX-ACCESS  not-accessible
    STATUS  current
    DESCRIPTION
        "The statistics of a particular auxiliary session table entry."
    INDEX   { slbStatSpAuxSessSpIndex, slbStatSpAuxSessIndex }
    ::= { slbStatSpAuxSessTable 1 }

SlbStatSpAuxSessEntry ::= SEQUENCE {
    slbStatSpAuxSessSpIndex             Integer32,
    slbStatSpAuxSessIndex               Integer32,
    slbStatSpAuxSessCurConn             Gauge32,
    slbStatSpAuxSessMaxConn             Integer32,
    slbStatSpAuxSessAllocFails          Counter32
    }

slbStatSpAuxSessSpIndex OBJECT-TYPE
    SYNTAX  Integer32
    MAX-ACCESS  read-only
    STATUS  current
    DESCRIPTION
        "The SP number." 
    ::= { slbStatSpAuxSessEntry 1 }

slbStatSpAuxSessIndex OBJECT-TYPE
    SYNTAX  Integer32
    MAX-ACCESS  read-only
    STATUS  current
    DESCRIPTION
        "The auxiliary session table number." 
    ::= { slbStatSpAuxSessEntry 2 }

slbStatSpAuxSessCurConn OBJECT-TYPE 
    SYNTAX  Gauge32
    MAX-ACCESS  read-only
    STATUS  current 
    DESCRIPTION 
        "The number of connections in this auxiliary sessions table."
    ::= { slbStatSpAuxSessEntry 3 }

slbStatSpAuxSessMaxConn OBJECT-TYPE 
    SYNTAX  Integer32 
    MAX-ACCESS  read-only
    STATUS  current 
    DESCRIPTION 
        "The maximum number of connections handled by this auxiliary session 
         table."
    ::= { slbStatSpAuxSessEntry 4 }

slbStatSpAuxSessAllocFails OBJECT-TYPE 
    SYNTAX  Counter32 
    MAX-ACCESS  read-only
    STATUS  current 
    DESCRIPTION 
        "The total number of allocation failures for this auxiliary session 
         table."
    ::= { slbStatSpAuxSessEntry 5 }

-- SLB Real Servers Statistics Table

slbStatRServerTable OBJECT-TYPE
    SYNTAX  SEQUENCE OF SlbStatRServerEntry
    MAX-ACCESS  not-accessible
    STATUS  current
    DESCRIPTION
        "The real server statistics table."
    ::= { layer4Stats 2 }

slbStatRServerEntry OBJECT-TYPE
    SYNTAX  SlbStatRServerEntry
    MAX-ACCESS  not-accessible
    STATUS  current
    DESCRIPTION
        "The statistics of a particular real server."
    INDEX   { slbStatRServerIndex }
    ::= { slbStatRServerTable 1 }

SlbStatRServerEntry ::= SEQUENCE {
    slbStatRServerIndex               Integer32,
    slbStatRServerCurrSessions        Gauge32,
    slbStatRServerTotalSessions       Counter32,
    slbStatRServerFailures            Counter32,
    slbStatRServerHighestSessions     Counter32,
    slbStatRServerHCOctetsLow32       Counter32,
    slbStatRServerHCOctetsHigh32      Counter32,
    slbStatRServerHCOctets            Counter64
    }

slbStatRServerIndex OBJECT-TYPE
    SYNTAX  Integer32
    MAX-ACCESS  read-only
    STATUS  current
    DESCRIPTION
        "The real server number that identifies the server." 
    ::= { slbStatRServerEntry 1 }

slbStatRServerCurrSessions OBJECT-TYPE 
    SYNTAX  Gauge32
    MAX-ACCESS  read-only
    STATUS  current 
    DESCRIPTION 
        "The number of sessions that are currently handled by the real server."
    ::= { slbStatRServerEntry 2 }

slbStatRServerTotalSessions OBJECT-TYPE 
    SYNTAX  Counter32 
    MAX-ACCESS  read-only
    STATUS  current 
    DESCRIPTION 
        "The total number of sessions that are handled by the real server."
    ::= { slbStatRServerEntry 3 }

slbStatRServerFailures OBJECT-TYPE 
    SYNTAX  Counter32 
    MAX-ACCESS  read-only
    STATUS  current 
    DESCRIPTION 
        "The total number of times that the real server is claimed down."
    ::= { slbStatRServerEntry 4 }

slbStatRServerHighestSessions OBJECT-TYPE 
    SYNTAX  Counter32 
    MAX-ACCESS  read-only
    STATUS  current 
    DESCRIPTION 
        "The highest sessions that have been handled by the real server."
    ::= { slbStatRServerEntry 5 }

slbStatRServerHCOctetsLow32 OBJECT-TYPE
    SYNTAX  Counter32
    MAX-ACCESS  read-only
    STATUS  current
    DESCRIPTION
        "The lower 32 bit value of octets received and transmitted out of the 
         real server."
    ::= { slbStatRServerEntry 6 }

slbStatRServerHCOctetsHigh32 OBJECT-TYPE
    SYNTAX  Counter32
    MAX-ACCESS  read-only
    STATUS  current
    DESCRIPTION
        "The higher 32 bit value of octets received and transmitted out
         of the real server."
    ::= { slbStatRServerEntry 7 }

slbStatRServerHCOctets OBJECT-TYPE
    SYNTAX  Counter64
    MAX-ACCESS  read-only
    STATUS  current
    DESCRIPTION
        "The total number of octets received and transmitted by the real 
         server."
    ::= { slbStatRServerEntry 8 }

-- SLB Real Server Groups Statistics Table

slbStatGroupTable OBJECT-TYPE
    SYNTAX  SEQUENCE OF SlbStatGroupEntry
    MAX-ACCESS  not-accessible
    STATUS  current
    DESCRIPTION
        "The real server group statistics table."
    ::= { layer4Stats 3 }

slbStatGroupEntry OBJECT-TYPE
    SYNTAX  SlbStatGroupEntry
    MAX-ACCESS  not-accessible
    STATUS  current
    DESCRIPTION
        "The statistics of a particular real server group."
    INDEX   { slbStatGroupIndex }
    ::= { slbStatGroupTable 1 }

SlbStatGroupEntry ::= SEQUENCE {
    slbStatGroupIndex               Integer32,
    slbStatGroupCurrSessions        Gauge32,
    slbStatGroupTotalSessions       Counter32,
    slbStatGroupHighestSessions     Counter32,
    slbStatGroupHCOctetsLow32       Counter32,
    slbStatGroupHCOctetsHigh32      Counter32,
    slbStatGroupWlmUpdates          Counter32, 
    slbStatGroupHCOctets            Counter64
    }

slbStatGroupIndex OBJECT-TYPE
    SYNTAX  Integer32
    MAX-ACCESS  read-only
    STATUS  current
    DESCRIPTION
        "The real server group number that identifies the group." 
    ::= { slbStatGroupEntry 1 }

slbStatGroupCurrSessions OBJECT-TYPE 
    SYNTAX  Gauge32
    MAX-ACCESS  read-only
    STATUS  current 
    DESCRIPTION 
        "The number of sessions that are currently handled by the real server 
         group."
    ::= { slbStatGroupEntry 2 }

slbStatGroupTotalSessions OBJECT-TYPE 
    SYNTAX  Counter32 
    MAX-ACCESS  read-only
    STATUS  current 
    DESCRIPTION 
        "The total number of sessions that are handled by the real 
         server group."
    ::= { slbStatGroupEntry 3 }

slbStatGroupHighestSessions OBJECT-TYPE 
    SYNTAX  Counter32 
    MAX-ACCESS  read-only
    STATUS  current 
    DESCRIPTION 
        "The highest sessions that have been handled by the real server group."
    ::= { slbStatGroupEntry 4 }

slbStatGroupHCOctetsLow32 OBJECT-TYPE
    SYNTAX  Counter32
    MAX-ACCESS  read-only
    STATUS  current
    DESCRIPTION
        "The lower 32 bit value of octets received and transmitted out of the 
         real server group."
    ::= { slbStatGroupEntry 5 }

slbStatGroupHCOctetsHigh32 OBJECT-TYPE
    SYNTAX  Counter32
    MAX-ACCESS  read-only
    STATUS  current
    DESCRIPTION
        "The higher 32 bit value of octets received and transmitted out
         of the real server group."
    ::= { slbStatGroupEntry 6 }

slbStatGroupHCOctets OBJECT-TYPE
    SYNTAX  Counter64
    MAX-ACCESS  read-only
    STATUS  current
    DESCRIPTION
        "The total octets received and transmitted by the real server group."
    ::= { slbStatGroupEntry 7 }

slbStatGroupWlmUpdates OBJECT-TYPE
    SYNTAX  Counter32
    MAX-ACCESS  read-only
    STATUS  current
    DESCRIPTION
        "Total weight updates from work load manager."
    ::= { slbStatGroupEntry 8 } 

-- SLB Virtual Server Statistics Table

slbStatVServerTable OBJECT-TYPE
    SYNTAX  SEQUENCE OF SlbStatVServerEntry
    MAX-ACCESS  not-accessible
    STATUS  current
    DESCRIPTION
        "The virtual server statistics table."
    ::= { layer4Stats 4 }

slbStatVServerEntry OBJECT-TYPE
    SYNTAX  SlbStatVServerEntry
    MAX-ACCESS  not-accessible
    STATUS  current
    DESCRIPTION
        "The statistics of a particular virtual server group."
    INDEX   { slbStatVServerIndex }
    ::= { slbStatVServerTable 1 }

SlbStatVServerEntry ::= SEQUENCE {
    slbStatVServerIndex                   Integer32,
    slbStatVServerCurrSessions            Gauge32,
    slbStatVServerTotalSessions           Counter32,
    slbStatVServerHighestSessions         Counter32,
    slbStatVServerHCOctetsLow32           Counter32,
    slbStatVServerHCOctetsHigh32          Counter32,
    slbStatVServerHeaderHits              Counter32,
    slbStatVServerHeaderMisses            Counter32,
    slbStatVServerHeaderTotalSessions     Counter32,
    slbStatVServerCookieRewrites          Counter32,
    slbStatVServerCookieInserts           Counter32,
    slbStatVServerHCOctets                Counter64,
    slbStatVServerIpAddress               DisplayString 
    }

slbStatVServerIndex OBJECT-TYPE
    SYNTAX  Integer32
    MAX-ACCESS  read-only
    STATUS  current
    DESCRIPTION
        "The virtual server number that identifies the server." 
    ::= { slbStatVServerEntry 1 }

slbStatVServerCurrSessions OBJECT-TYPE 
    SYNTAX  Gauge32
    MAX-ACCESS  read-only
    STATUS  current 
    DESCRIPTION 
        "The number of sessions that are currently handled by the 
         virtual server."
    ::= { slbStatVServerEntry 2 }

slbStatVServerTotalSessions OBJECT-TYPE 
    SYNTAX  Counter32 
    MAX-ACCESS  read-only
    STATUS  current 
    DESCRIPTION 
        "The total number of sessions that are handled by the virtual server."
    ::= { slbStatVServerEntry 3 }

slbStatVServerHighestSessions OBJECT-TYPE 
    SYNTAX  Counter32 
    MAX-ACCESS  read-only
    STATUS  current 
    DESCRIPTION 
        "The highest sessions that have been handled by the virtual server."
    ::= { slbStatVServerEntry 4 }

slbStatVServerHCOctetsLow32 OBJECT-TYPE
    SYNTAX  Counter32
    MAX-ACCESS  read-only
    STATUS  current
    DESCRIPTION
        "The lower 32 bit value of octets received and transmitted out
         of the virtual server."
    ::= { slbStatVServerEntry 5 }

slbStatVServerHCOctetsHigh32 OBJECT-TYPE
    SYNTAX  Counter32
    MAX-ACCESS  read-only
    STATUS  current
    DESCRIPTION
        "The higher 32 bit value of octets received and transmitted out
         of the virtual server."
    ::= { slbStatVServerEntry 6 }


--  HTTP Header LB stats 
slbStatVServerHeaderHits OBJECT-TYPE 
    SYNTAX  Counter32 
    MAX-ACCESS  read-only
    STATUS  current 
    DESCRIPTION 
        "The current HTTP header hits." 
    ::= { slbStatVServerEntry 8 }

slbStatVServerHeaderMisses OBJECT-TYPE 
    SYNTAX  Counter32 
    MAX-ACCESS  read-only
    STATUS  current 
    DESCRIPTION 
        "The current HTTP header misses."  
    ::= { slbStatVServerEntry 9 }

slbStatVServerHeaderTotalSessions OBJECT-TYPE 
    SYNTAX  Counter32 
    MAX-ACCESS  read-only
    STATUS  current 
    DESCRIPTION 
        "The total HTTP header sessions."
    ::= { slbStatVServerEntry 10 }

-- Cookie Statistics 
slbStatVServerCookieRewrites OBJECT-TYPE 
    SYNTAX  Counter32 
    MAX-ACCESS  read-only
    STATUS  current 
    DESCRIPTION 
        "The total Cookie Rewrites."
    ::= { slbStatVServerEntry 11 }

slbStatVServerCookieInserts OBJECT-TYPE 
    SYNTAX  Counter32 
    MAX-ACCESS  read-only
    STATUS  current 
    DESCRIPTION 
        "The total Cookie Inserts."
    ::= { slbStatVServerEntry 12 }

slbStatVServerHCOctets OBJECT-TYPE
    SYNTAX  Counter64
    MAX-ACCESS  read-only
    STATUS  current
    DESCRIPTION
        "The total octets received and transmitted by the virtual server."
    ::= { slbStatVServerEntry 13 }

slbStatVServerIpAddress   OBJECT-TYPE
    SYNTAX  DisplayString 
    MAX-ACCESS  read-only 
    STATUS  current
    DESCRIPTION
        "IP address of the virtual server." 
    ::= { slbStatVServerEntry  14 }

-- SLB Maintenance Statistics 

slbStatMaintMaximumSessions OBJECT-TYPE
    SYNTAX  Integer32
    MAX-ACCESS  read-only
    STATUS  current
    DESCRIPTION
        "The maximun number entries in the session table."
    ::= { slbMaintStats 1 }

slbStatMaintCurBindings OBJECT-TYPE
    SYNTAX  Gauge32 
    MAX-ACCESS  read-only
    STATUS  current
    DESCRIPTION
        "The current number of bindings on the port."
    ::= { slbMaintStats 2 }

slbStatMaintCurBindings4Seconds OBJECT-TYPE
    SYNTAX  Gauge32 
    MAX-ACCESS  read-only
    STATUS  current
    DESCRIPTION
        "The 4 second average current number of bindings on the port."
    ::= { slbMaintStats 3 }

slbStatMaintCurBindings64Seconds OBJECT-TYPE
    SYNTAX  Gauge32 
    MAX-ACCESS  read-only
    STATUS  current
    DESCRIPTION
        "The 64 second average current number of bindings on the port."
    ::= { slbMaintStats 4 }

slbStatMaintTerminatedSessions OBJECT-TYPE
    SYNTAX  Counter32
    MAX-ACCESS  read-only
    STATUS  current
    DESCRIPTION
        "The count of the number of sessions closed because the server failed."
    ::= { slbMaintStats 5 }

slbStatMaintAllocFailures OBJECT-TYPE
    SYNTAX  Counter32
    MAX-ACCESS  read-only
    STATUS  current
    DESCRIPTION
        "The total number of Binding failures on the port. A Binding Failure 
         occurs when a port runs out of binding table entries."
    ::= { slbMaintStats 6 }

slbStatMaintNonTcpFrames OBJECT-TYPE
    SYNTAX  Counter32
    MAX-ACCESS  read-only
    STATUS  current
    DESCRIPTION
        "The total number of non-TCP/IP frames dropped on the port."
    ::= { slbMaintStats 7 }

slbStatMaintTcpFragments OBJECT-TYPE
    SYNTAX  Counter32
    MAX-ACCESS  read-only
    STATUS  current
    DESCRIPTION
        "The total number of TCP fragments dropped on the port."
    ::= { slbMaintStats 8 }

slbStatMaintUdpDatagrams OBJECT-TYPE
    SYNTAX  Counter32
    MAX-ACCESS  read-only
    STATUS  current
    DESCRIPTION
        "The total number of UDP datagrams dropped on the port."
    ::= { slbMaintStats 9 }

slbIncorrectVirtServs OBJECT-TYPE 
    SYNTAX  Counter32 
    MAX-ACCESS  read-only
    STATUS  current 
    DESCRIPTION 
        "Incorrect Virtual Servers specified for Server Load Balancing."
    ::= { slbMaintStats  10}

slbIncorrectVports OBJECT-TYPE 
    SYNTAX  Counter32  
    MAX-ACCESS  read-only
    STATUS  current 
    DESCRIPTION 
        "Incorrect Virtual ports specified for Server Load Balancing."
    ::= { slbMaintStats 11 }

slbNoRealServs OBJECT-TYPE 
    SYNTAX  Counter32  
    MAX-ACCESS  read-only
    STATUS  current 
    DESCRIPTION 
        "No Real Servers available for Server Load Balancing."
    ::= { slbMaintStats 12 }

slbStatMaintBackupServActs OBJECT-TYPE
    SYNTAX  Counter32
    MAX-ACCESS  read-only
    STATUS  current
    DESCRIPTION
        "The total number of times that backup servers become active due 
         to failure of primary servers."
    ::= { slbMaintStats 13 }

slbStatMaintOverflowServActs OBJECT-TYPE
    SYNTAX  Counter32
    MAX-ACCESS  read-only
    STATUS  current
    DESCRIPTION
        "The total number of times that backup servers become
	 active due to primary servers reach overflow situation."
    ::= { slbMaintStats 14 }

slbStatMaintFilteredDeniedFrames OBJECT-TYPE
    SYNTAX  Counter32
    MAX-ACCESS  read-only
    STATUS  current
    DESCRIPTION
        "The total number of frames that are denied on the port by the filter."
    ::= { slbMaintStats 15 }

slbStatMaintLandAttacks OBJECT-TYPE
    SYNTAX  Counter32
    MAX-ACCESS  read-only
    STATUS  current
    DESCRIPTION
        "The total number of attacks that frames contain the same source
	 and destination IP addresses."
    ::= { slbMaintStats 16 }

slbStatMaintIpFragTotalSessions OBJECT-TYPE
    SYNTAX  Counter32
    MAX-ACCESS  read-only
    STATUS  current
    DESCRIPTION
        "The total number of fragment sessions processed."
    ::= { slbMaintStats 17 }

slbStatMaintIpFragCurSessions OBJECT-TYPE
    SYNTAX  Gauge32
    MAX-ACCESS  read-only
    STATUS  current
    DESCRIPTION
        "The number of sessions in the IP fragment binding table."
    ::= { slbMaintStats 18 }

slbStatMaintIpFragDiscards OBJECT-TYPE
    SYNTAX  Counter32
    MAX-ACCESS  read-only
    STATUS  current
    DESCRIPTION
        "The total number of fragmemts discarded on the SP because there
         is no entry in the IP fragment binding table. "
    ::= { slbMaintStats 19 }

slbStatMaintIpFragTableFull OBJECT-TYPE
    SYNTAX  Counter32
    MAX-ACCESS  read-only
    STATUS  current
    DESCRIPTION
        "The total number times IP fragment binding table is full on the SP."
    ::= { slbMaintStats 20 }

slbStatMaintIp6CurrSessions OBJECT-TYPE
    SYNTAX  Counter32
    MAX-ACCESS  read-only
    STATUS  current
    DESCRIPTION
        "The number of sessions  for ipv6."
    ::= { slbMaintStats 21 }

slbIncorrectIp6Vip  OBJECT-TYPE 
    SYNTAX  Counter32 
    MAX-ACCESS  read-only
    STATUS  current 
    DESCRIPTION 
        "Incorrect Ip6 VIPs specified for server load balancing."
    ::= { slbMaintStats  22}

slbIncorrectIp6Vports OBJECT-TYPE 
    SYNTAX  Counter32  
    MAX-ACCESS  read-only
    STATUS  current 
    DESCRIPTION 
        "Incorrect Ip6 virtual ports specified for server load balancing."
    ::= { slbMaintStats 23 }

slbStatMaintIp6PktDropped OBJECT-TYPE
    SYNTAX  Counter32
    MAX-ACCESS  read-only
    STATUS  current
    DESCRIPTION
        "The total number of Ip6 pacekets dropped."
    ::= { slbMaintStats 24 }


slbStatMaintOOSFinPktDrops OBJECT-TYPE
    SYNTAX  Counter32
    MAX-ACCESS  read-only
    STATUS  current
    DESCRIPTION
        "The total number Out of state FIN Packet drops."
    ::= { slbMaintStats 25 }

-- START of Symantec SLB Maintenance Stats
slbStatMaintSymSessions OBJECT-TYPE
    SYNTAX  Counter32
    MAX-ACCESS  read-only
    STATUS  current
    DESCRIPTION
        "Total number of Symantec sessions."
    ::= { slbMaintStats 26 }

slbStatMaintSymValidSegments OBJECT-TYPE
    SYNTAX  Counter32
    MAX-ACCESS  read-only
    STATUS  current
    DESCRIPTION
        "Total number of Symantec valid segments."
    ::= { slbMaintStats 27 }

slbStatMaintSymFragSessions OBJECT-TYPE
    SYNTAX  Counter32
    MAX-ACCESS  read-only
    STATUS  current
    DESCRIPTION
        "Total number of Symantec fragment sessions."
    ::= { slbMaintStats 28 }

slbStatMaintSymSegAllocFails OBJECT-TYPE
    SYNTAX  Counter32
    MAX-ACCESS  read-only
    STATUS  current
    DESCRIPTION
        "Total number of Symantec segment allocation fails."
    ::= { slbMaintStats 29 }

slbStatMaintSymBufferAllocFails OBJECT-TYPE
    SYNTAX  Counter32
    MAX-ACCESS  read-only
    STATUS  current
    DESCRIPTION
        "Total number of Symantec buffers allocation fails."
    ::= { slbMaintStats 30 }

slbStatMaintSymConnAllocFails OBJECT-TYPE
    SYNTAX  Counter32
    MAX-ACCESS  read-only
    STATUS  current
    DESCRIPTION
        "Total number of Symantec Connection allocation fails."
    ::= { slbMaintStats 31 }

slbStatMaintSymInvalidBuffers OBJECT-TYPE
    SYNTAX  Counter32
    MAX-ACCESS  read-only
    STATUS  current
    DESCRIPTION
        "Total number of Symantec Invalid buffers."
    ::= { slbMaintStats 32 }

slbStatMaintSymSegReallocFails OBJECT-TYPE
    SYNTAX  Counter32
    MAX-ACCESS  read-only
    STATUS  current
    DESCRIPTION
        "Total number of Symantec Segment reallocation fails."
    ::= { slbMaintStats 33 }

slbStatMaintSymPacketsIn OBJECT-TYPE
    SYNTAX  Counter32
    MAX-ACCESS  read-only
    STATUS  current
    DESCRIPTION
        "Symantec Deuce Inspection Stats - Total no. of Packets in."
    ::= { slbMaintStats 34 }

slbStatMaintSymPacketsWithNoData OBJECT-TYPE
    SYNTAX  Counter32
    MAX-ACCESS  read-only
    STATUS  current
    DESCRIPTION
        "Symantec Deuce Inspection Stats - Total no. of Packets with no data."
    ::= { slbMaintStats 35 }

slbStatMaintSymTcpPackets OBJECT-TYPE
    SYNTAX  Counter32
    MAX-ACCESS  read-only
    STATUS  current
    DESCRIPTION
        "Symantec Deuce Inspection Stats - Total no. of TCP packets"
    ::= { slbMaintStats 36 }

slbStatMaintSymUdpPackets OBJECT-TYPE
    SYNTAX  Counter32
    MAX-ACCESS  read-only
    STATUS  current
    DESCRIPTION
        "Symantec Deuce Inspection Stats - Total no. of UDP Packets"
    ::= { slbMaintStats 37 }

slbStatMaintSymIcmpPackets OBJECT-TYPE
    SYNTAX  Counter32
    MAX-ACCESS  read-only
    STATUS  current
    DESCRIPTION
        "Symantec Deuce Inspection Stats - Total no. of ICMP Packets"
    ::= { slbMaintStats 38 }

slbStatMaintSymOtherPackets OBJECT-TYPE
    SYNTAX  Counter32
    MAX-ACCESS  read-only
    STATUS  current
    DESCRIPTION
        "Symantec Deuce Inspection Stats - Total no. of Packets 
	 other than TCP UDP or ICMP"
    ::= { slbMaintStats 39 }

slbStatMaintSymMatchCount OBJECT-TYPE
    SYNTAX  Counter32
    MAX-ACCESS  read-only
    STATUS  current
    DESCRIPTION
        "Symantec Deuce Inspection Stats - Total Match Count"
    ::= { slbMaintStats 40 }

slbStatMaintSymFetchErrors OBJECT-TYPE
    SYNTAX  Counter32
    MAX-ACCESS  read-only
    STATUS  current
    DESCRIPTION
        "Symantec Deuce Inspection Stats - Total no. of Fetch Errors"
    ::= { slbMaintStats 41 }

slbStatMaintSymTruncPayloadToMp OBJECT-TYPE
    SYNTAX  Counter32
    MAX-ACCESS  read-only
    STATUS  current
    DESCRIPTION
        "Symantec Deuce Inspection Stats - Total no. of Truncated 
	 payload to MP"
    ::= { slbMaintStats 42 }

slbStatMaintSymPacketsInFastPath OBJECT-TYPE
    SYNTAX  Counter32
    MAX-ACCESS  read-only
    STATUS  current
    DESCRIPTION
        "Symantec Deuce Inspection Stats - Total no. of Packets in 
	 fast path"
    ::= { slbMaintStats 43 }

-- END of Symantec SLB Maintenance Stats 

-- Filter Statistics

fltStatTable OBJECT-TYPE
    SYNTAX  SEQUENCE OF FltStatTableEntry
    MAX-ACCESS  not-accessible
    STATUS  current
    DESCRIPTION
        "The filter statistics table."
    ::= { filterStats 1 }

fltStatTableEntry OBJECT-TYPE
    SYNTAX  FltStatTableEntry
    MAX-ACCESS  not-accessible
    STATUS  current
    DESCRIPTION
        "A row in filter statistics table."
    INDEX   { fltStatFltIndex }
    ::= { fltStatTable 1 }

FltStatTableEntry ::= SEQUENCE {
    fltStatFltIndex     Integer32,
    fltStatFltFirings	Counter32
    }

fltStatFltIndex OBJECT-TYPE 
    SYNTAX  Integer32 
    MAX-ACCESS  read-only
    STATUS  current 
    DESCRIPTION 
        "The number that identifies the filter." 
    ::= { fltStatTableEntry 1 }

fltStatFltFirings OBJECT-TYPE 
    SYNTAX  Counter32 
    MAX-ACCESS  read-only
    STATUS  current 
    DESCRIPTION 
        "The number of instances that the received packet matches the 
         filter rule."
    ::= { fltStatTableEntry 2 }

-- Global SLB Statitistics

-- Global SLB Remote Real Server Statistics

gslbStatRemRealServerTable OBJECT-TYPE
    SYNTAX  SEQUENCE OF GslbStatRemRealServerEntry
    MAX-ACCESS  not-accessible
    STATUS  current
    DESCRIPTION
        "The GSLB remote real server statistics table."
    ::= { gslbStats 1 }

gslbStatRemRealServerEntry OBJECT-TYPE
    SYNTAX  GslbStatRemRealServerEntry
    MAX-ACCESS  not-accessible
    STATUS  current
    DESCRIPTION
        "A row in the remote real server statistics table."
    INDEX   { gslbStatRemRealServerIndex }
    ::= { gslbStatRemRealServerTable 1 }

GslbStatRemRealServerEntry ::=	SEQUENCE {
    gslbStatRemRealServerIndex          Integer32,
    gslbStatRemRealServerDnsHandoffs    Counter32,
    gslbStatRemRealServerHttpRedirs     Counter32
    }

gslbStatRemRealServerIndex OBJECT-TYPE 
    SYNTAX  Integer32 
    MAX-ACCESS  read-only
    STATUS  current 
    DESCRIPTION 
        "The server number that identifies the remote real server." 
    ::= { gslbStatRemRealServerEntry 1 }

gslbStatRemRealServerDnsHandoffs OBJECT-TYPE 
    SYNTAX  Counter32 
    MAX-ACCESS  read-only
    STATUS  current 
    DESCRIPTION 
        "The number of DNS handoffs by the remote real server."
    ::= { gslbStatRemRealServerEntry 2 }

gslbStatRemRealServerHttpRedirs OBJECT-TYPE 
    SYNTAX  Counter32 
    MAX-ACCESS  read-only
    STATUS  current 
    DESCRIPTION 
        "The number of HTTP redirections by the remote real server."
    ::= { gslbStatRemRealServerEntry 3 }

-- The Global SLB Maintenance Statistics

gslbMaintStats OBJECT IDENTIFIER ::= { gslbStats 2 }

gslbStatMaintInGoodSiteUpdates OBJECT-TYPE 
    SYNTAX  Counter32 
    MAX-ACCESS  read-only
    STATUS  current 
    DESCRIPTION 
        "The number of good DSSPv1 remote site updates received."
    ::= { gslbMaintStats 1 }

gslbStatMaintInBadSiteUpdates OBJECT-TYPE 
    SYNTAX  Counter32 
    MAX-ACCESS  read-only
    STATUS  current 
    DESCRIPTION 
        "The number of bad remote site packets received."
    ::= { gslbMaintStats 2 }

gslbStatMaintOutSiteUpdates OBJECT-TYPE
    SYNTAX  Counter32
    MAX-ACCESS  read-only
    STATUS  current
    DESCRIPTION
        "The number of DSSPv1 remote site updates sent."
    ::= { gslbMaintStats 3 }

gslbStatMaintInGoodSiteUpdates2 OBJECT-TYPE
    SYNTAX  Counter32
    MAX-ACCESS  read-only
    STATUS  current
    DESCRIPTION
        "The number of good DSSPv2 remote site updates received."
    ::= { gslbMaintStats 4 }

gslbStatMaintOutSiteUpdates2 OBJECT-TYPE
    SYNTAX  Counter32
    MAX-ACCESS  read-only
    STATUS  current
    DESCRIPTION
        "The number of DSSPv2 remote site updates sent."
    ::= { gslbMaintStats 5 }


gslbStatMaintLocalSitePers OBJECT-TYPE
    SYNTAX  Counter32
    MAX-ACCESS  read-only
    STATUS  current
    DESCRIPTION
        "The number of local site DNS persistence cache entries added."
    ::= { gslbMaintStats 8 }


gslbStatMaintInDns OBJECT-TYPE
    SYNTAX  Counter32
    MAX-ACCESS  read-only
    STATUS  current
    DESCRIPTION
        "The number of DNS queries received."
    ::= { gslbMaintStats 10 }

gslbStatMaintInBadDns OBJECT-TYPE
    SYNTAX  Counter32
    MAX-ACCESS  read-only
    STATUS  current
    DESCRIPTION
        "The number of bad DNS queries received."
    ::= { gslbMaintStats 11 }

gslbStatMaintOutDns OBJECT-TYPE
    SYNTAX  Counter32
    MAX-ACCESS  read-only
    STATUS  current
    DESCRIPTION
        "The number of DNS responses sent."
    ::= { gslbMaintStats 12 }

gslbStatMaintInHttp OBJECT-TYPE
    SYNTAX  Counter32
    MAX-ACCESS  read-only
    STATUS  current
    DESCRIPTION
        "The number of HTTP requests received."
    ::= { gslbMaintStats 13 }

gslbStatMaintInBadHttp OBJECT-TYPE
    SYNTAX  Counter32
    MAX-ACCESS  read-only
    STATUS  current
    DESCRIPTION
        "The number of bad HTTP requests received."
    ::= { gslbMaintStats 14 }

gslbStatMaintOutHttp OBJECT-TYPE
    SYNTAX  Counter32
    MAX-ACCESS  read-only
    STATUS  current
    DESCRIPTION
        "The number of HTTP responses sent."
    ::= { gslbMaintStats 15 }

gslbStatMaintNoServer OBJECT-TYPE
    SYNTAX  Counter32
    MAX-ACCESS  read-only
    STATUS  current
    DESCRIPTION
        "The number of times no server returned."
    ::= { gslbMaintStats 16 }

gslbStatMaintNoDomain OBJECT-TYPE
    SYNTAX  Counter32
    MAX-ACCESS  read-only
    STATUS  current
    DESCRIPTION
        "The number of times no matching domain."
    ::= { gslbMaintStats 17 }

gslbStatMaintHostHits OBJECT-TYPE
    SYNTAX  Counter32
    MAX-ACCESS  read-only
    STATUS  current
    DESCRIPTION
        "The number of hostname domain hits."
    ::= { gslbMaintStats 18 }

gslbStatMaintRuleHits OBJECT-TYPE
    SYNTAX  Counter32
    MAX-ACCESS  read-only
    STATUS  current
    DESCRIPTION
        "The number of network domain hits."
    ::= { gslbMaintStats 19 }

gslbStatMaintVirtHits OBJECT-TYPE
    SYNTAX  Counter32
    MAX-ACCESS  read-only
    STATUS  current
    DESCRIPTION
        "The number of basic domain hits."
    ::= { gslbMaintStats 20 }

gslbStatMaintNoServerHost OBJECT-TYPE
    SYNTAX  Counter32
    MAX-ACCESS  read-only
    STATUS  current
    DESCRIPTION
        "The number of times no server returned for hostname domain."
    ::= { gslbMaintStats 21 }

gslbStatMaintNoServerRule OBJECT-TYPE
    SYNTAX  Counter32
    MAX-ACCESS  read-only
    STATUS  current
    DESCRIPTION
        "The number of times no server returned for network domain."
    ::= { gslbMaintStats 22 }

gslbStatMaintNoServerVirt OBJECT-TYPE
    SYNTAX  Counter32
    MAX-ACCESS  read-only
    STATUS  current
    DESCRIPTION
        "The number of times no server returned for basic domain."
    ::= { gslbMaintStats 23 }

gslbStatMaintLastNoResultDomain OBJECT-TYPE
    SYNTAX DisplayString (SIZE(0..255))
    MAX-ACCESS  read-only
    STATUS  current
    DESCRIPTION
        "The last no result domain."
    ::= { gslbMaintStats 24 }

gslbStatMaintLastSrcIp OBJECT-TYPE
    SYNTAX  IpAddress
    MAX-ACCESS  read-only
    STATUS  current
    DESCRIPTION
        "The last source IP address."
    ::= { gslbMaintStats 25 }

gslbStatMaintThresholdHits OBJECT-TYPE
    SYNTAX  Counter32
    MAX-ACCESS  read-only
    STATUS  current
    DESCRIPTION
        "The number of times any servers not returned due to threshold exceeded for the corresponding server."
    ::= { gslbMaintStats 26 }

gslbStatMaintLastSrcIpV6 OBJECT-TYPE
   SYNTAX DisplayString (SIZE(0..40))
    MAX-ACCESS  read-only
    STATUS  current
    DESCRIPTION
        "The last source IPV6 address."
   ::= { gslbMaintStats 27 }


-- Global SLB Group Statistics

gslbStatGroupTable OBJECT-TYPE
    SYNTAX  SEQUENCE OF GslbStatGroupEntry
    MAX-ACCESS  not-accessible
    STATUS  current
    DESCRIPTION
        "The GSLB group statistics table."
    ::= { gslbStats 3 }

gslbStatGroupEntry OBJECT-TYPE
    SYNTAX  GslbStatGroupEntry
    MAX-ACCESS  not-accessible
    STATUS  current
    DESCRIPTION
        "A row in the GSLB group statistics table."
    INDEX   { gslbStatGroupIndex }
    ::= { gslbStatGroupTable 1 }

GslbStatGroupEntry ::=	SEQUENCE {
    gslbStatGroupIndex          Integer32,
    gslbStatGroupDnsHandoffs    Counter32,
    gslbStatGroupHttpRedirs     Counter32
    }

gslbStatGroupIndex OBJECT-TYPE 
    SYNTAX  Integer32 
    MAX-ACCESS  read-only
    STATUS  current 
    DESCRIPTION 
        "The group number that identifies the real server group." 
    ::= { gslbStatGroupEntry 1 }

gslbStatGroupDnsHandoffs OBJECT-TYPE 
    SYNTAX  Counter32 
    MAX-ACCESS  read-only
    STATUS  current 
    DESCRIPTION 
        "The total number of DNS hand-offs sent to the remote real servers in 
         the group."
    ::= { gslbStatGroupEntry 2 }

gslbStatGroupHttpRedirs OBJECT-TYPE 
    SYNTAX  Counter32 
    MAX-ACCESS  read-only
    STATUS  current 
    DESCRIPTION 
        "The total number of HTTP redirects sent to the remote real servers in 
         the group."
    ::= { gslbStatGroupEntry 3 }

-- Global SLB Virtual Server Statistics

gslbStatVirtServerTable OBJECT-TYPE
    SYNTAX  SEQUENCE OF GslbStatVirtServerEntry
    MAX-ACCESS  not-accessible
    STATUS  current
    DESCRIPTION
        "The Global SLB virtual server statistics table."
    ::= { gslbStats 4 }

gslbStatVirtServerEntry OBJECT-TYPE
    SYNTAX  GslbStatVirtServerEntry
    MAX-ACCESS  not-accessible
    STATUS  current
    DESCRIPTION
        "A row in the Global SLB virtual server statistics table."
    INDEX   { gslbStatVirtServerIdx, gslbStatVirtServerServiceIdx, 
              gslbStatVirtServerRserverIdx }
    ::= { gslbStatVirtServerTable 1 }

GslbStatVirtServerEntry ::=	SEQUENCE {
    gslbStatVirtServerIdx            Integer32,
    gslbStatVirtServerServiceIdx     Integer32,
    gslbStatVirtServerRserverIdx     Integer32,
    gslbStatVirtServerVirtPort       Integer32,
    gslbStatVirtServerIpAddress      IpAddress,
    gslbStatVirtServerResponseTime   Integer32,
    gslbStatVirtServerMinSessAvail   Gauge32,
    gslbStatVirtServerDname          DisplayString,
    gslbStatVirtServerRemSite        Integer32,
    gslbStatVirtDnsDirect            Counter32
    }
  
gslbStatVirtServerIdx OBJECT-TYPE 
    SYNTAX  Integer32 
    MAX-ACCESS  read-only
    STATUS  current 
    DESCRIPTION 
        "The virtual server number that identifies the virtual server." 
    ::= { gslbStatVirtServerEntry 1 }

gslbStatVirtServerServiceIdx OBJECT-TYPE 
    SYNTAX  Integer32 
    MAX-ACCESS  read-only
    STATUS  current 
    DESCRIPTION 
        "The virtual server service number that identifies the virtual 
         service." 
    ::= { gslbStatVirtServerEntry 2 }

gslbStatVirtServerRserverIdx OBJECT-TYPE 
    SYNTAX  Integer32 
    MAX-ACCESS  read-only
    STATUS  current 
    DESCRIPTION 
        "The real server number that identifies a remote site. A index of 
         0 indicates a local virtual server number." 
    ::= { gslbStatVirtServerEntry 3 }

gslbStatVirtServerVirtPort OBJECT-TYPE 
    SYNTAX  Integer32
    MAX-ACCESS  read-only
    STATUS  current 
    DESCRIPTION 
        "The virtual server service port."
    ::= { gslbStatVirtServerEntry 4 }

gslbStatVirtServerIpAddress OBJECT-TYPE 
    SYNTAX  IpAddress
    MAX-ACCESS  read-only
    STATUS  current 
    DESCRIPTION 
        "The IP address of the virtual server or remote real server."
    ::= { gslbStatVirtServerEntry 5 }

gslbStatVirtServerResponseTime OBJECT-TYPE 
    SYNTAX  Integer32
    MAX-ACCESS  read-only
    STATUS  current 
    DESCRIPTION 
        "The average time (current weight) that each service takes to respond
         to information exchanges with its peers The time is specified in 
         ticks of 65 milliseconds."
    ::= { gslbStatVirtServerEntry 6 }

gslbStatVirtServerMinSessAvail OBJECT-TYPE 
    SYNTAX  Gauge32
    MAX-ACCESS  read-only
    STATUS  current 
    DESCRIPTION 
        "The current number of sessions available for serving client requests.
         This number will change as client traffic loads change, or as real 
         servers under the virtual server or remote sites go in or out of 
         service."
    ::= { gslbStatVirtServerEntry 7 }

gslbStatVirtServerDname OBJECT-TYPE
    SYNTAX DisplayString (SIZE(0..64))
    MAX-ACCESS read-only
    STATUS current
    DESCRIPTION
        "The domain name of the virtual server and remote real server."
    ::= { gslbStatVirtServerEntry 8 }

gslbStatVirtServerRemSite OBJECT-TYPE
    SYNTAX Integer32
    MAX-ACCESS read-only
    STATUS current
    DESCRIPTION
        "The remote site of the remote real server. For virtual server, the remote site is 0."
    ::= { gslbStatVirtServerEntry 9 }

gslbStatVirtDnsDirect OBJECT-TYPE
    SYNTAX Counter32
    MAX-ACCESS read-only
    STATUS current
    DESCRIPTION
        "The total number of DNS directs sent to the virtual server or remote real server."
    ::= { gslbStatVirtServerEntry 10 }

-- Global SLB Remote Site Statistics

gslbStatRemSiteTable OBJECT-TYPE
    SYNTAX SEQUENCE OF GslbStatRemSiteTableEntry
    MAX-ACCESS not-accessible
    STATUS current
    DESCRIPTION
        "The Global SLB remote site statistics table."
    ::= { gslbStats 5 }

gslbStatRemSiteTableEntry OBJECT-TYPE
    SYNTAX GslbStatRemSiteTableEntry
    MAX-ACCESS not-accessible
    STATUS current
    DESCRIPTION
        "A row in the Global SLB remote site statistics table."
    INDEX { gslbStatRemSiteIdx }
    ::= { gslbStatRemSiteTable 1 }

GslbStatRemSiteTableEntry ::=     SEQUENCE {
    gslbStatRemSiteIdx            Integer32,
    gslbStatRemSiteOutUpdates     Counter32,
    gslbStatRemSiteInUpdates      Counter32,
    gslbStatRemSiteOutUpdates2    Counter32,
    gslbStatRemSiteInUpdates2     Counter32,
    gslbStatRemSiteInBadUpdates   Counter32
    }

gslbStatRemSiteIdx OBJECT-TYPE
    SYNTAX Integer32
    MAX-ACCESS read-only
    STATUS current
    DESCRIPTION
        "The remote site number that identifies the remote site."
    ::= { gslbStatRemSiteTableEntry 1 }

gslbStatRemSiteOutUpdates OBJECT-TYPE
    SYNTAX Counter32
    MAX-ACCESS read-only
    STATUS current
    DESCRIPTION
        "The number of DSSPv1 remote site updates sent."
    ::= { gslbStatRemSiteTableEntry 2 }

gslbStatRemSiteInUpdates OBJECT-TYPE
    SYNTAX Counter32
    MAX-ACCESS read-only
    STATUS current
    DESCRIPTION
        "The number of good DSSPv1 remote site updates received."
    ::= { gslbStatRemSiteTableEntry 3 }

gslbStatRemSiteOutUpdates2 OBJECT-TYPE
    SYNTAX Counter32
    MAX-ACCESS read-only
    STATUS current
    DESCRIPTION
        "The number of DSSPv2 remote site updates sent."
    ::= { gslbStatRemSiteTableEntry 4 }

gslbStatRemSiteInUpdates2 OBJECT-TYPE
    SYNTAX Counter32
    MAX-ACCESS read-only
    STATUS current
    DESCRIPTION
        "The number of good DSSPv2 remote site updates received."
    ::= { gslbStatRemSiteTableEntry 5 }

gslbStatRemSiteInBadUpdates OBJECT-TYPE
    SYNTAX Counter32
    MAX-ACCESS read-only
    STATUS current
    DESCRIPTION
        "The number of bad remote site updates received."
    ::= { gslbStatRemSiteTableEntry 6 }


-- Global SLB Enhanced Network Statistics

gslbStatEnhNetworkTable OBJECT-TYPE
    SYNTAX SEQUENCE OF GslbStatEnhNetworkTableEntry
    MAX-ACCESS not-accessible
    STATUS current
    DESCRIPTION
        "The Global SLB network statistics table."
    ::= { gslbStats 6 }

gslbStatEnhNetworkTableEntry OBJECT-TYPE
    SYNTAX GslbStatEnhNetworkTableEntry
    MAX-ACCESS not-accessible
    STATUS current
    DESCRIPTION
        "A row in the Global SLB network statistics table."
    INDEX { gslbStatEnhNetworkIdx }
    ::= { gslbStatEnhNetworkTable 1 }

GslbStatEnhNetworkTableEntry ::=     SEQUENCE {
    gslbStatEnhNetworkIdx             Integer32,
    gslbStatEnhNetworkHit             Counter32
    }

gslbStatEnhNetworkIdx OBJECT-TYPE
    SYNTAX Integer32
    MAX-ACCESS read-only
    STATUS current
    DESCRIPTION
        "The network number that identifies the network."
    ::= { gslbStatEnhNetworkTableEntry 1 }

gslbStatEnhNetworkHit OBJECT-TYPE
    SYNTAX Counter32
    MAX-ACCESS read-only
    STATUS current
    DESCRIPTION
        "The number of times network is selected."
    ::= { gslbStatEnhNetworkTableEntry 2 }

-- Global SLB Rule Statistics

gslbStatRuleTable OBJECT-TYPE
    SYNTAX SEQUENCE OF GslbStatRuleTableEntry
    MAX-ACCESS not-accessible
    STATUS current
    DESCRIPTION
        "The Global SLB rule statistics table."
    ::= { gslbStats 7 }

gslbStatRuleTableEntry OBJECT-TYPE
    SYNTAX GslbStatRuleTableEntry
    MAX-ACCESS not-accessible
    STATUS current
    DESCRIPTION
        "A row in the Global SLB rule statistics table."
    INDEX { gslbStatRuleIdx }
    ::= { gslbStatRuleTable 1 }

GslbStatRuleTableEntry ::=     SEQUENCE {
    gslbStatRuleIdx               Integer32,
    gslbStatRuleLeastconns        Counter32,
    gslbStatRuleRoundrobin        Counter32,
    gslbStatRuleMinmisses         Counter32,
    gslbStatRuleHash              Counter32,
    gslbStatRuleResponse          Counter32,
    gslbStatRuleGeographical      Counter32,
    gslbStatRuleNetwork           Counter32,
    gslbStatRuleRandom            Counter32,
    gslbStatRuleAvailability      Counter32,
    gslbStatRuleQos               Counter32,
    gslbStatRulePersistence       Counter32,
    gslbStatRuleLocal             Counter32,
    gslbStatRuleAlways            Counter32,
    gslbStatRuleRemote            Counter32,
    gslbStatRuleTotal             Counter32
    }

gslbStatRuleIdx OBJECT-TYPE
    SYNTAX Integer32
    MAX-ACCESS read-only
    STATUS current
    DESCRIPTION
        "The rule number that identifies the rule."
    ::= { gslbStatRuleTableEntry 1 }

gslbStatRuleLeastconns OBJECT-TYPE
    SYNTAX Counter32
    MAX-ACCESS read-only
    STATUS current
    DESCRIPTION
        "The number of times leastconns is used."
    ::= { gslbStatRuleTableEntry 2 }

gslbStatRuleRoundrobin OBJECT-TYPE
    SYNTAX Counter32
    MAX-ACCESS read-only
    STATUS current
    DESCRIPTION
        "The number of times roundrobin is used."
    ::= { gslbStatRuleTableEntry 3 }

gslbStatRuleMinmisses OBJECT-TYPE
    SYNTAX Counter32
    MAX-ACCESS read-only
    STATUS current
    DESCRIPTION
        "The number of times minmisses is used."
    ::= { gslbStatRuleTableEntry 4 }

gslbStatRuleHash OBJECT-TYPE
    SYNTAX Counter32
    MAX-ACCESS read-only
    STATUS current
    DESCRIPTION
        "The number of times hash is used."
    ::= { gslbStatRuleTableEntry 5 }

gslbStatRuleResponse OBJECT-TYPE
    SYNTAX Counter32
    MAX-ACCESS read-only
    STATUS current
    DESCRIPTION
        "The number of times response is used."
    ::= { gslbStatRuleTableEntry 6 }

gslbStatRuleGeographical OBJECT-TYPE
    SYNTAX Counter32
    MAX-ACCESS read-only
    STATUS current
    DESCRIPTION
        "The number of times geographical is used."
    ::= { gslbStatRuleTableEntry 7 }

gslbStatRuleNetwork OBJECT-TYPE
    SYNTAX Counter32
    MAX-ACCESS read-only
    STATUS current
    DESCRIPTION
        "The number of times network is used."
    ::= { gslbStatRuleTableEntry 8 }

gslbStatRuleRandom OBJECT-TYPE
    SYNTAX Counter32
    MAX-ACCESS read-only
    STATUS current
    DESCRIPTION
        "The number of times random is used."
    ::= { gslbStatRuleTableEntry 9 }

gslbStatRuleAvailability OBJECT-TYPE
    SYNTAX Counter32
    MAX-ACCESS read-only
    STATUS current
    DESCRIPTION
        "The number of times availability is used."
    ::= { gslbStatRuleTableEntry 10 }

gslbStatRuleQos OBJECT-TYPE
    SYNTAX Counter32
    MAX-ACCESS read-only
    STATUS current
    DESCRIPTION
        "The number of times qos is used."
    ::= { gslbStatRuleTableEntry 11 }

gslbStatRulePersistence OBJECT-TYPE
    SYNTAX Counter32
    MAX-ACCESS read-only
    STATUS current
    DESCRIPTION
        "The number of times persistence is used."
    ::= { gslbStatRuleTableEntry 12 }

gslbStatRuleLocal OBJECT-TYPE
    SYNTAX Counter32
    MAX-ACCESS read-only
    STATUS current
    DESCRIPTION
        "The number of times local is used."
    ::= { gslbStatRuleTableEntry 13 }

gslbStatRuleAlways OBJECT-TYPE
    SYNTAX Counter32
    MAX-ACCESS read-only
    STATUS current
    DESCRIPTION
        "The number of times always is used."
    ::= { gslbStatRuleTableEntry 14 }

gslbStatRuleRemote OBJECT-TYPE
    SYNTAX Counter32
    MAX-ACCESS read-only
    STATUS current
    DESCRIPTION
        "The number of times remote is used."
    ::= { gslbStatRuleTableEntry 15 }

gslbStatRuleTotal OBJECT-TYPE
    SYNTAX Counter32
    MAX-ACCESS read-only
    STATUS current
    DESCRIPTION
        "The number of times all the metrics are used."
    ::= { gslbStatRuleTableEntry 16 }

-- Global SLB Geographical Statistics

gslbStatGeo OBJECT IDENTIFIER ::= { gslbStats 8 }

gslbStatGeoNA OBJECT-TYPE
    SYNTAX Counter32
    MAX-ACCESS read-only
    STATUS current
    DESCRIPTION
        "The number of times North America is selected."
    ::= { gslbStatGeo 1 }

gslbStatGeoSA OBJECT-TYPE
    SYNTAX Counter32
    MAX-ACCESS read-only
    STATUS current
    DESCRIPTION
        "The number of times South America is selected."
    ::= { gslbStatGeo 2 }

gslbStatGeoEU OBJECT-TYPE
    SYNTAX Counter32
    MAX-ACCESS read-only
    STATUS current
    DESCRIPTION
        "The number of times Europe is selected."
    ::= { gslbStatGeo 3 }

gslbStatGeoCA OBJECT-TYPE
    SYNTAX Counter32
    MAX-ACCESS read-only
    STATUS current
    DESCRIPTION
        "The number of times Caribbean is selected."
    ::= { gslbStatGeo 4 }

gslbStatGeoPR OBJECT-TYPE
    SYNTAX Counter32
    MAX-ACCESS read-only
    STATUS current
    DESCRIPTION
        "The number of times Pacific Rim is selected."
    ::= { gslbStatGeo 5 }

gslbStatGeoSS OBJECT-TYPE
    SYNTAX Counter32
    MAX-ACCESS read-only
    STATUS current
    DESCRIPTION
        "The number of times Sub-Sahara is selected."
    ::= { gslbStatGeo 6 }

gslbStatGeoJP OBJECT-TYPE
    SYNTAX Counter32
    MAX-ACCESS read-only
    STATUS current
    DESCRIPTION
        "The number of times Japan is selected."
    ::= { gslbStatGeo 7 }

gslbStatGeoTotal OBJECT-TYPE
    SYNTAX Counter32
    MAX-ACCESS read-only
    STATUS current
    DESCRIPTION
        "The number of times any of the regions are selected."
    ::= { gslbStatGeo 8 }

gslbStatGeoAF OBJECT-TYPE
    SYNTAX Counter32
    MAX-ACCESS read-only
    STATUS current
    DESCRIPTION
        "The number of times Africa is selected."
    ::= { gslbStatGeo 9 }

-- Global SLB DNS Persistence Cache Statistics

gslbStatPers OBJECT IDENTIFIER ::= { gslbStats 9 }

gslbStatPersCurrent OBJECT-TYPE
    SYNTAX Counter32
    MAX-ACCESS read-only
    STATUS current
    DESCRIPTION
        "The current number of entries in the DNS persistence cache."
    ::= { gslbStatPers 1 }

gslbStatPersHiwat OBJECT-TYPE
    SYNTAX Counter32
    MAX-ACCESS read-only
    STATUS current
    DESCRIPTION
        "The highest number of entries recorded in the DNS persistence cache."
    ::= { gslbStatPers 2 }

gslbStatPersMax OBJECT-TYPE
    SYNTAX Counter32
    MAX-ACCESS read-only
    STATUS current
    DESCRIPTION
        "The maximum number of entries supported in the DNS persistence cache."
    ::= { gslbStatPers 3 }

-- FTP Passive SLB/NAT Statistics

ftpSlbStatTotal  OBJECT-TYPE
    SYNTAX  Counter32
    MAX-ACCESS  read-only
    STATUS  current
    DESCRIPTION
        "The number of times the switch receives both active and passive
         FTP connections."
    ::= { ftpStats 1 }

ftpNatStatTotal  OBJECT-TYPE
    SYNTAX  Counter32
    MAX-ACCESS  read-only
    STATUS  current
    DESCRIPTION
	"The number of times the switch receives the 'port' command from 
         the client."
    ::= { ftpStats 2 } 

ftpStatActiveNatIndex  OBJECT-TYPE
    SYNTAX  Counter32
    MAX-ACCESS  read-only
    STATUS  current
    DESCRIPTION
	"The number of times the switch creates a new index due to 'port'
         command from the client."
    ::= { ftpStats 3 } 

ftpStatNatAckSeqDiff  OBJECT-TYPE
    SYNTAX  Counter32
    MAX-ACCESS  read-only
    STATUS  current
    DESCRIPTION
 	"The difference in the numbers of ACK and SEQ that the switch needs 
         for packet adjustment." 
    ::= { ftpStats 4 } 

ftpStatSlbParseIndex  OBJECT-TYPE
    SYNTAX  Counter32
    MAX-ACCESS  read-only
    STATUS  current
    DESCRIPTION
	"The number of times the switch creates a new index in response to the
         'pasv' command from the client."
    ::= { ftpStats 5 } 

ftpStatSlbParseAckSeqDiff  OBJECT-TYPE
    SYNTAX  Counter32
    MAX-ACCESS  read-only
    STATUS  current
    DESCRIPTION
 	"The difference in the numbers of ACK and SEQ that the switch needs 
         for FTP SLB parsing." 
    ::= { ftpStats 6 } 

ftpStatModeSwitchError OBJECT-TYPE
    SYNTAX  Counter32
    MAX-ACCESS  read-only
    STATUS  current
    DESCRIPTION
	"The number of times the switch is not able to switch modes from
         active to passive and vice versa." 
    ::= { ftpStats 7 } 

radiusAcctReqsStats     OBJECT IDENTIFIER ::= { wapStats 1 }
tpcpAddSessReqsStats    OBJECT IDENTIFIER ::= { wapStats 2 }
tpcpDeleteSessReqsStats OBJECT IDENTIFIER ::= { wapStats 3 }

radiusAcctReqs OBJECT-TYPE 
    SYNTAX  Counter32 
    MAX-ACCESS  read-only
    STATUS  current 
    DESCRIPTION 
        "Radius Account Request."
    ::= { radiusAcctReqsStats 1 }

radiusAcctWrapReqs OBJECT-TYPE 
    SYNTAX  Counter32 
    MAX-ACCESS  read-only
    STATUS  current 
    DESCRIPTION 
        "Radius Account Wrap Request."
    ::= { radiusAcctReqsStats 2 }

radiusAcctStartReqs OBJECT-TYPE 
    SYNTAX  Counter32 
    MAX-ACCESS  read-only
    STATUS  current 
    DESCRIPTION 
        "Radius Account Start Request."
    ::= { radiusAcctReqsStats 3 }

radiusAcctUpdateReqs OBJECT-TYPE 
    SYNTAX  Counter32 
    MAX-ACCESS  read-only
    STATUS  current 
    DESCRIPTION 
        "Radius Account Update Request."
    ::= { radiusAcctReqsStats 4 }

radiusAcctStopReqs OBJECT-TYPE 
    SYNTAX  Counter32 
    MAX-ACCESS  read-only
    STATUS  current 
    DESCRIPTION 
        "Radius Account stop Request."
    ::= { radiusAcctReqsStats 5 }

radiusAcctBadReqs OBJECT-TYPE 
    SYNTAX  Counter32 
    MAX-ACCESS  read-only
    STATUS  current 
    DESCRIPTION 
        "Radius Account Bad Request."
    ::= { radiusAcctReqsStats 6 }

radiusAcctAddSessionReqs OBJECT-TYPE 
    SYNTAX  Counter32 
    MAX-ACCESS  read-only
    STATUS  current 
    DESCRIPTION 
        "Radius Account add session Request."
    ::= { radiusAcctReqsStats 7 }

radiusAcctDeleteSessionReqs OBJECT-TYPE 
    SYNTAX  Counter32 
    MAX-ACCESS  read-only
    STATUS  current 
    DESCRIPTION 
        "Radius Account delete session Request."
    ::= { radiusAcctReqsStats 8 }

radiusAcctReqFailsSPDead OBJECT-TYPE 
    SYNTAX  Counter32 
    MAX-ACCESS  read-only
    STATUS  current 
    DESCRIPTION 
        "Radius Account request fails SP Dead."
    ::= { radiusAcctReqsStats 10 }

radiusAcctReqFailsDMAFails OBJECT-TYPE 
    SYNTAX  Counter32 
    MAX-ACCESS  read-only
    STATUS  current 
    DESCRIPTION 
        "Radius Account request fails DMA fails."
    ::= { radiusAcctReqsStats 11 }

radiusAcctReqWithFramedIp OBJECT-TYPE 
    SYNTAX  Counter32 
    MAX-ACCESS  read-only
    STATUS  current 
    DESCRIPTION 
        "Radius Account request containing the FRAMED_IP field."
    ::= { radiusAcctReqsStats 12 }

radiusAcctReqWithoutFramedIp OBJECT-TYPE 
    SYNTAX  Counter32 
    MAX-ACCESS  read-only
    STATUS  current 
    DESCRIPTION 
        "Radius Account request not containing the FRAMED_IP field."
    ::= { radiusAcctReqsStats 13 }

tpcpAddSessReqs OBJECT-TYPE 
    SYNTAX  Counter32 
    MAX-ACCESS  read-only
    STATUS  current 
    DESCRIPTION 
        "WAP add Session requests." 
    ::= { tpcpAddSessReqsStats 1 }

tpcpAddSessReqsFailsSPDead OBJECT-TYPE 
    SYNTAX  Counter32 
    MAX-ACCESS  read-only
    STATUS  current 
    DESCRIPTION 
        "WAP add Session Fails as the SP is dead."
    ::= { tpcpAddSessReqsStats 3 }

tpcpDeleteSessReqs OBJECT-TYPE 
    SYNTAX  Counter32 
    MAX-ACCESS  read-only
    STATUS  current 
    DESCRIPTION 
        "TPCP Delete Session Requests." 
    ::= { tpcpDeleteSessReqsStats 1 }

tpcpDeleteSessReqsFailsSPDead OBJECT-TYPE 
    SYNTAX  Counter32 
    MAX-ACCESS  read-only
    STATUS current 
    DESCRIPTION 
        "TPCP Delete Session Fails as the SP is dead."
    ::= { tpcpDeleteSessReqsStats 3 }

wapRequestToWrongSP OBJECT-TYPE 
    SYNTAX  Counter32 
    MAX-ACCESS  read-only
    STATUS  current 
    DESCRIPTION 
        "The  WAP delete Session Entries sent to wrong SP."
    ::= { wapStats 4 }

-- RTSP Statistics

rtspStatControlConns OBJECT-TYPE 
    SYNTAX  Counter32
    MAX-ACCESS  read-only
    STATUS  current 
    DESCRIPTION 
        "Total number of active RTSP control connections."
    ::= { rtspStats 1 }

rtspStatUDPStreams OBJECT-TYPE 
    SYNTAX  Counter32
    MAX-ACCESS  read-only
    STATUS  current 
    DESCRIPTION 
        "Total number of active UDP streams."
    ::= { rtspStats 2 }

rtspStatRedirects OBJECT-TYPE 
    SYNTAX  Counter32
    MAX-ACCESS  read-only
    STATUS  current 
    DESCRIPTION 
        "Total number of switch redirects."
    ::= { rtspStats 3 }

rtspStatConnDenied OBJECT-TYPE 
    SYNTAX  Counter32
    MAX-ACCESS  read-only
    STATUS  current 
    DESCRIPTION 
        "Total connections denied due to RTSP connection limit."
    ::= { rtspStats 4 }

rtspStatAllocFails OBJECT-TYPE 
    SYNTAX  Counter32
    MAX-ACCESS  read-only
    STATUS  current 
    DESCRIPTION 
        "Total cases of heap memory allocation failures."
    ::= { rtspStats 5 }

rtspStatBufferAllocs OBJECT-TYPE 
    SYNTAX  Gauge32
    MAX-ACCESS  read-only
    STATUS  current 
    DESCRIPTION 
        "The total number of buffer allocations used."
    ::= { rtspStats 6 }

-- TCP Rate Limiting Statistics
tcpLimitStatHoldDowns OBJECT-TYPE 
    SYNTAX  Counter32
    MAX-ACCESS  read-only
    STATUS  current 
    DESCRIPTION 
        "Total number of client hold downs triggered."
    ::= { tcpLimitStats 1 }

tcpLimitStatClientEntries OBJECT-TYPE 
    SYNTAX  Gauge32
    MAX-ACCESS  read-only
    STATUS  current 
    DESCRIPTION 
        "Current number of TCP rate limiting per-client state entries."
    ::= { tcpLimitStats 2 }
    
udpLimitStatHoldDowns OBJECT-TYPE 
    SYNTAX  Counter32
    MAX-ACCESS  read-only
    STATUS  current 
    DESCRIPTION 
        "Total number of UDP client hold downs triggered."
    ::= { tcpLimitStats 3 }
    
icmpLimitStatHoldDowns OBJECT-TYPE 
    SYNTAX  Counter32
    MAX-ACCESS  read-only
    STATUS  current 
    DESCRIPTION 
        "Total number of ICMP client hold downs triggered."
    ::= { tcpLimitStats 4 }

udpLimitStatClientEntries OBJECT-TYPE 
    SYNTAX  Counter32
    MAX-ACCESS  read-only
    STATUS  current 
    DESCRIPTION 
        "Current number of UDP rate limiting per-client state entries."
    ::= { tcpLimitStats 5 }
    
icmpLimitStatClientEntries OBJECT-TYPE 
    SYNTAX  Counter32
    MAX-ACCESS  read-only
    STATUS  current 
    DESCRIPTION 
        "Current number of ICMP rate limiting per-client state entries."
    ::= { tcpLimitStats 6 }    
    
-- DNS SLB Statistics

dnsSlbStatTCPQueries OBJECT-TYPE 
    SYNTAX  Counter32
    MAX-ACCESS  read-only
    STATUS  current 
    DESCRIPTION 
        "Total number of TCP DNS queries."
    ::= { dnsSlbStats 1 }

dnsSlbStatUDPQueries OBJECT-TYPE 
    SYNTAX  Counter32
    MAX-ACCESS  read-only
    STATUS  current 
    DESCRIPTION 
        "Total number of UDP DNS queries."
    ::= { dnsSlbStats 2 }

dnsSlbStatInvalidQueries OBJECT-TYPE 
    SYNTAX  Counter32
    MAX-ACCESS  read-only
    STATUS  current 
    DESCRIPTION 
        "Total number of invalid DNS queries."
    ::= { dnsSlbStats 3 }

dnsSlbStatMultipleQueries OBJECT-TYPE 
    SYNTAX  Counter32
    MAX-ACCESS  read-only
    STATUS  current 
    DESCRIPTION 
        "Total number of multiple DNS queries."
    ::= { dnsSlbStats 4 }

dnsSlbStatDnameParseErrors OBJECT-TYPE 
    SYNTAX  Counter32
    MAX-ACCESS  read-only
    STATUS  current 
    DESCRIPTION 
        "Total number of domain name parse errors."
    ::= { dnsSlbStats 5 }

dnsSlbStatFailedMatches OBJECT-TYPE 
    SYNTAX  Counter32
    MAX-ACCESS  read-only
    STATUS  current 
    DESCRIPTION 
        "Total number of failed real server name matches."
    ::= { dnsSlbStats 6 }

dnsSlbStatInternalErrors OBJECT-TYPE 
    SYNTAX  Counter32
    MAX-ACCESS  read-only
    STATUS  current 
    DESCRIPTION 
        "Total number of DNS parsing internal errors."
    ::= { dnsSlbStats 7 }

slbStatsClear OBJECT-TYPE
    SYNTAX INTEGER {
	ok(1),
	clear(2)
	}
    MAX-ACCESS read-write
    STATUS current
    DESCRIPTION
        "This is an action object to clear the non-operational SLB statistics. 
         ok(1) is returned when read."
    ::= { layer4Stats 15 }

slbStatAuxSessTable OBJECT-TYPE
    SYNTAX  SEQUENCE OF SlbStatAuxSessEntry
    MAX-ACCESS  not-accessible
    STATUS  current
    DESCRIPTION
        "The auxiliary session table statistics."
    ::= { layer4Stats 17 }

slbStatAuxSessEntry OBJECT-TYPE
    SYNTAX  SlbStatAuxSessEntry
    MAX-ACCESS  not-accessible
    STATUS  current
    DESCRIPTION
        "The statistics of a particular auxiliary session table entry."
    INDEX   { slbStatAuxSessIndex }
    ::= { slbStatAuxSessTable 1 }

SlbStatAuxSessEntry ::= SEQUENCE {
    slbStatAuxSessIndex               Integer32,
    slbStatAuxSessCurConn             Gauge32,
    slbStatAuxSessMaxConn             Integer32,
    slbStatAuxSessAllocFails          Counter32
    }

slbStatAuxSessIndex OBJECT-TYPE
    SYNTAX  Integer32
    MAX-ACCESS  read-only
    STATUS  current
    DESCRIPTION
        "The auxiliary session table number." 
    ::= { slbStatAuxSessEntry 1 }

slbStatAuxSessCurConn OBJECT-TYPE 
    SYNTAX  Gauge32
    MAX-ACCESS  read-only
    STATUS  current 
    DESCRIPTION 
        "The number of connections in this auxiliary sessions table."
    ::= { slbStatAuxSessEntry 2 }

slbStatAuxSessMaxConn OBJECT-TYPE 
    SYNTAX  Integer32 
    MAX-ACCESS  read-only
    STATUS  current 
    DESCRIPTION 
        "The maximum number of connections handled by this auxiliary session 
         table."
    ::= { slbStatAuxSessEntry 3 }

slbStatAuxSessAllocFails OBJECT-TYPE 
    SYNTAX  Counter32 
    MAX-ACCESS  read-only
    STATUS  current 
    DESCRIPTION 
        "The total number of allocation failures for this auxiliary session 
         table."
    ::= { slbStatAuxSessEntry 4 }

-- SSL SLB Statistics

sslSlbStatSessIdAllocFails OBJECT-TYPE 
    SYNTAX  Counter32
    MAX-ACCESS  read-only
    STATUS  current 
    DESCRIPTION 
        "The number of times allocation of a session table entry failed when
         attempting to store a SessionId in the table."
    ::= { sslSlbStats 1 }

sslSlbStatCurSessions OBJECT-TYPE 
    SYNTAX  Gauge32
    MAX-ACCESS  read-only
    STATUS  current 
    DESCRIPTION 
        "The current number of different TCP sessions using SSL service."
    ::= { sslSlbStats 2 }

sslSlbStatTotalSessions OBJECT-TYPE 
    SYNTAX  Counter32
    MAX-ACCESS  read-only
    STATUS  current 
    DESCRIPTION 
        "The total number of different TCP sessions using SSL service."
    ::= { sslSlbStats 3 }

sslSlbStatHighestSessions OBJECT-TYPE 
    SYNTAX  Counter32
    MAX-ACCESS  read-only
    STATUS  current 
    DESCRIPTION 
        "The high water mark of current sessions of different TCP sessions 
         using SSL service."
    ::= { sslSlbStats 4 }

sslSlbStatUniqCurSessions OBJECT-TYPE 
    SYNTAX  Gauge32
    MAX-ACCESS  read-only
    STATUS  current 
    DESCRIPTION 
        "The current number of unique SSL sessions seen on the switch."
    ::= { sslSlbStats 5 }

sslSlbStatUniqTotalSessions OBJECT-TYPE 
    SYNTAX  Counter32
    MAX-ACCESS  read-only
    STATUS  current 
    DESCRIPTION 
        "The total number of unique SSL sessions seen on the switch."
    ::= { sslSlbStats 6 }

sslSlbStatUniqHighestSessions OBJECT-TYPE 
    SYNTAX  Counter32
    MAX-ACCESS  read-only
    STATUS  current 
    DESCRIPTION 
        "The high water mark of unique SSL sessions seen on the switch."
    ::= { sslSlbStats 7 }

sslSlbStatPersistPortCurSessions OBJECT-TYPE 
    SYNTAX  Gauge32
    MAX-ACCESS  read-only
    STATUS  current 
    DESCRIPTION 
        "The current number of SessionIds maintained on SP 4, to allow for 
         persistence across different client ports."
    ::= { sslSlbStats 8 }

sslSlbStatPersistPortTotalSessions OBJECT-TYPE 
    SYNTAX  Counter32
    MAX-ACCESS  read-only
    STATUS  current 
    DESCRIPTION 
        "The total number of SessionIds maintained on SP 4, to allow for 
         persistence across different client ports."
    ::= { sslSlbStats 9 }

sslSlbStatPersistPortHighestSessions OBJECT-TYPE 
    SYNTAX  Counter32
    MAX-ACCESS  read-only
    STATUS  current 
    DESCRIPTION 
        "The high water mask of SessionIds maintained on SP 4, to allow for 
         persistence across different client ports."
    ::= { sslSlbStats 10 }


-- SLB Virtual Service Statistics Table

slbStatVirtServiceTable OBJECT-TYPE
    SYNTAX  SEQUENCE OF SlbStatVirtServiceEntry
    MAX-ACCESS  not-accessible
    STATUS  current
    DESCRIPTION
        "The virtual service statistics table."
    ::= { layer4Stats 18 }

slbStatVirtServiceEntry OBJECT-TYPE
    SYNTAX  SlbStatVirtServiceEntry
    MAX-ACCESS  not-accessible
    STATUS  current
    DESCRIPTION
        "The statistics of a particular virtual service."
    INDEX   { slbStatVirtServerIndex, slbStatVirtServiceIndex, slbStatRealServerIndex }
    ::= { slbStatVirtServiceTable 1 }

SlbStatVirtServiceEntry ::= SEQUENCE {
    slbStatVirtServerIndex                 Integer32,
    slbStatVirtServiceIndex                Integer32,
    slbStatRealServerIndex                 Integer32,
    slbStatVirtServiceCurrSessions         Gauge32,
    slbStatVirtServiceTotalSessions        Counter32,
    slbStatVirtServiceHighestSessions      Counter32,
    slbStatVirtServiceHCOctetsLow32        Counter32,
    slbStatVirtServiceHCOctetsHigh32       Counter32,
    slbStatVirtServiceHCOctets             Counter64
    }
    
slbStatVirtServerIndex OBJECT-TYPE
    SYNTAX  Integer32
    MAX-ACCESS  read-only
    STATUS  current
    DESCRIPTION
        "The virtual server number that identifies the service." 
    ::= { slbStatVirtServiceEntry 1 }
    
slbStatVirtServiceIndex OBJECT-TYPE
    SYNTAX  Integer32
    MAX-ACCESS  read-only
    STATUS  current
    DESCRIPTION
        "The virtual service number that identifies the service." 
    ::= { slbStatVirtServiceEntry 2 }
    
slbStatRealServerIndex OBJECT-TYPE
    SYNTAX  Integer32
    MAX-ACCESS  read-only
    STATUS  current
    DESCRIPTION
        "The real server index." 
    ::= { slbStatVirtServiceEntry 3 }
    
slbStatVirtServiceCurrSessions OBJECT-TYPE 
    SYNTAX  Gauge32
    MAX-ACCESS  read-only
    STATUS  current 
    DESCRIPTION 
        "The number of sessions that are currently handled by the 
         virtual service."
    ::= { slbStatVirtServiceEntry 4 }
    
slbStatVirtServiceTotalSessions OBJECT-TYPE 
    SYNTAX  Counter32 
    MAX-ACCESS  read-only
    STATUS  current 
    DESCRIPTION 
        "The total number of sessions that are handled by the virtual service."
    ::= { slbStatVirtServiceEntry 5}

slbStatVirtServiceHighestSessions OBJECT-TYPE 
    SYNTAX  Counter32 
    MAX-ACCESS  read-only
    STATUS  current 
    DESCRIPTION 
        "The highest sessions that have been handled by the virtual service."
    ::= { slbStatVirtServiceEntry 6}

slbStatVirtServiceHCOctetsLow32 OBJECT-TYPE
    SYNTAX  Counter32
    MAX-ACCESS  read-only
    STATUS  current
    DESCRIPTION
        "The lower 32 bit value of octets received and transmitted out
         of the virtual service."
    ::= { slbStatVirtServiceEntry 7}

slbStatVirtServiceHCOctetsHigh32 OBJECT-TYPE
    SYNTAX  Counter32
    MAX-ACCESS  read-only
    STATUS  current
    DESCRIPTION
        "The higher 32 bit value of octets received and transmitted out
         of the virtual service."
    ::= { slbStatVirtServiceEntry 8}

slbStatVirtServiceHCOctets OBJECT-TYPE
    SYNTAX  Counter64
    MAX-ACCESS  read-only
    STATUS  current
    DESCRIPTION
        "The total octets received and transmitted by the virtual service."
    ::= { slbStatVirtServiceEntry 9}



-- SIP statistics
sipTotalClientParseErrors OBJECT-TYPE 
    SYNTAX  Counter32 
    MAX-ACCESS  read-only
    STATUS  current 
    DESCRIPTION 
        "Total number of SIP Client parse Errors."
    ::= { sipStats 1 }

sipTotalServerParseErrors OBJECT-TYPE 
    SYNTAX  Counter32 
    MAX-ACCESS  read-only
    STATUS  current 
    DESCRIPTION 
        "Total number of SIP Server parse Errors."
    ::= { sipStats 2 }

sipTotalUnknownMethodReq OBJECT-TYPE 
    SYNTAX  Counter32 
    MAX-ACCESS  read-only
    STATUS  current 
    DESCRIPTION 
        "Total number of SIP unknown method requests."
    ::= { sipStats 3 }

sipTotalIncompleteMsgs OBJECT-TYPE 
    SYNTAX  Counter32 
    MAX-ACCESS  read-only
    STATUS  current 
    DESCRIPTION 
        "Total number of SIP Incomplete messages."
    ::= { sipStats 4 }

sipTotalSdpNatPackets OBJECT-TYPE
    SYNTAX  Counter32
    MAX-ACCESS  read-only
    STATUS  current
    DESCRIPTION
        "Total number of SDP NAT packets."
    ::= { sipStats 5 }


-- SLB WLM Statistics Table


wlmStats          OBJECT IDENTIFIER ::= { layer4Stats  21 }

slbStatWlmTable OBJECT-TYPE
    SYNTAX  SEQUENCE OF SlbStatWlmEntry
    MAX-ACCESS  not-accessible
    STATUS  current
    DESCRIPTION
        "The WLM statistics table."
    ::= { wlmStats 1 }

slbStatWlmEntry OBJECT-TYPE
    SYNTAX  SlbStatWlmEntry
    MAX-ACCESS  not-accessible
    STATUS  current
    DESCRIPTION
        "The statistics of a particular work load manager."
    INDEX   { slbStatWlmIndex }
    ::= { slbStatWlmTable 1 }

SlbStatWlmEntry ::= SEQUENCE {
    slbStatWlmIndex                   Integer32, 
    slbStatWlmRegReq                  Counter32,
    slbStatWlmRegRep                  Counter32,
    slbStatWlmRegRepErr               Counter32,
    slbStatWlmDeregReq                Counter32,
    slbStatWlmDeregRep                Counter32,
    slbStatWlmDeregRepErr             Counter32,
    slbStatWlmLbStateReq              Counter32,
    slbStatWlmLbStateRep              Counter32,
    slbStatWlmLbStateRepErr           Counter32,
    slbStatWlmMembStateReq            Counter32,
    slbStatWlmMembStateRep            Counter32,
    slbStatWlmMembStateRepErr         Counter32,
    slbStatWlmWtMsgRecv               Counter32,
    slbStatWlmWtMsgParErr             Counter32,
    slbStatWlmTotInvalidLb            Counter32,
    slbStatWlmTotInvalidGrp           Counter32,
    slbStatWlmTotInvalidRealSer       Counter32,
    slbStatWlmMsgInvalidSASPHeader    Counter32,
    slbStatWlmMsgParseErr             Counter32,
    slbStatWlmMsgUnsupMsgType         Counter32
    }

slbStatWlmIndex OBJECT-TYPE
    SYNTAX Integer32
    MAX-ACCESS  read-only
    STATUS  current
    DESCRIPTION
       "The work load manager number." 
    ::= { slbStatWlmEntry 1 }

slbStatWlmRegReq OBJECT-TYPE
    SYNTAX  Counter32
    MAX-ACCESS  read-only
    STATUS  current
    DESCRIPTION
        "Total number of registration request messages sent by the switch."
    ::= { slbStatWlmEntry 2 }

slbStatWlmRegRep OBJECT-TYPE
    SYNTAX  Counter32
    MAX-ACCESS  read-only
    STATUS  current
    DESCRIPTION
        "Total number of registration replies received from the GWM."
    ::= { slbStatWlmEntry 3 }

slbStatWlmRegRepErr OBJECT-TYPE
    SYNTAX  Counter32
    MAX-ACCESS  read-only
    STATUS  current
    DESCRIPTION
        "Total number of registration replies received where the return 
         code indicates an error."
    ::= { slbStatWlmEntry 4 }
slbStatWlmDeregReq OBJECT-TYPE
    SYNTAX  Counter32
    MAX-ACCESS  read-only
    STATUS  current
    DESCRIPTION
        "Total number of deregistration request messages sent by the switch."
    ::= { slbStatWlmEntry 5 }

slbStatWlmDeregRep OBJECT-TYPE
    SYNTAX  Counter32
    MAX-ACCESS  read-only
    STATUS  current
    DESCRIPTION
        "Total number of deregistration replies received from the GWM."
    ::= { slbStatWlmEntry 6 }

slbStatWlmDeregRepErr OBJECT-TYPE
    SYNTAX  Counter32
    MAX-ACCESS  read-only
    STATUS  current
    DESCRIPTION
        "Total number of deregistration replies received where the return code flag
         set indicating an error in processing of the deregistration request."
    ::= { slbStatWlmEntry 7 }

slbStatWlmLbStateReq OBJECT-TYPE
    SYNTAX  Counter32
    MAX-ACCESS  read-only
    STATUS  current
    DESCRIPTION
        "Total number of set LB state  request messages sent by the switch."
    ::= { slbStatWlmEntry 8 }

slbStatWlmLbStateRep OBJECT-TYPE
    SYNTAX  Counter32
    MAX-ACCESS  read-only
    STATUS  current
    DESCRIPTION
        "Total number of set LB state replies received from the GWM."
    ::= { slbStatWlmEntry 9 }

slbStatWlmLbStateRepErr OBJECT-TYPE
    SYNTAX  Counter32
    MAX-ACCESS  read-only
    STATUS  current
    DESCRIPTION
        "Total number of set LB state replies received where the return code code 
         flag set indicating an error in processing of the set LB state request."
    ::= { slbStatWlmEntry 10 }

slbStatWlmMembStateReq OBJECT-TYPE
    SYNTAX  Counter32
    MAX-ACCESS  read-only
    STATUS  current
    DESCRIPTION
        "Total number of set member state  request messages sent by the switch."
    ::= { slbStatWlmEntry 11 }

slbStatWlmMembStateRep OBJECT-TYPE
    SYNTAX  Counter32
    MAX-ACCESS  read-only
    STATUS  current
    DESCRIPTION
        "Total number of set member state  replies received from the GWM."
    ::= { slbStatWlmEntry 12 }

slbStatWlmMembStateRepErr OBJECT-TYPE
    SYNTAX  Counter32
    MAX-ACCESS  read-only
    STATUS  current
    DESCRIPTION
        "Total number of set member state replies received where the return 
         code code flag set indicating an error in processing of the set
	 member state request."
    ::= { slbStatWlmEntry 13 }

slbStatWlmWtMsgRecv OBJECT-TYPE
    SYNTAX  Counter32
    MAX-ACCESS  read-only
    STATUS  current
    DESCRIPTION
        "Total number of weight updates received from the GWM."
    ::= { slbStatWlmEntry 14 }

slbStatWlmWtMsgParErr OBJECT-TYPE
    SYNTAX  Counter32
    MAX-ACCESS  read-only
    STATUS  current
    DESCRIPTION
        "Total number of errorsencountered during parsing of the send weights message."
    ::= { slbStatWlmEntry 15 }

slbStatWlmTotInvalidLb  OBJECT-TYPE
    SYNTAX  Counter32
    MAX-ACCESS  read-only
    STATUS  current
    DESCRIPTION
        "This counter is incremented when the LB name in send weights message 
         does not match the switch LB name."
    ::= { slbStatWlmEntry 16 }

slbStatWlmTotInvalidGrp  OBJECT-TYPE
    SYNTAX  Counter32
    MAX-ACCESS  read-only
    STATUS  current
    DESCRIPTION
        "This counter is incremented when the group name in send weights message 
         does not match with any of the groups configured on the switch."
    ::= { slbStatWlmEntry 17 }

slbStatWlmTotInvalidRealSer  OBJECT-TYPE
    SYNTAX  Counter32
    MAX-ACCESS  read-only
    STATUS  current
    DESCRIPTION
        "This counter is incremented when the real server name in send weights message
         does not match with any of the reals configured on the switch."
    ::= { slbStatWlmEntry 18 }

slbStatWlmMsgInvalidSASPHeader  OBJECT-TYPE
    SYNTAX  Counter32
    MAX-ACCESS  read-only
    STATUS  current
    DESCRIPTION
        "Total number of messages received from the GWM with invalid headers."
    ::= { slbStatWlmEntry 19 }

slbStatWlmMsgParseErr  OBJECT-TYPE
    SYNTAX  Counter32
    MAX-ACCESS  read-only
    STATUS  current
    DESCRIPTION
        "Total number of parse errors."
    ::= { slbStatWlmEntry 20 }

slbStatWlmMsgUnsupMsgType  OBJECT-TYPE
    SYNTAX  Counter32
    MAX-ACCESS  read-only
    STATUS  current
    DESCRIPTION
        "Total messages received where the message type is not supported by the switch."
    ::= { slbStatWlmEntry 21 }



sessMirrorTotalCreateSessionMsgRx OBJECT-TYPE
    SYNTAX  Counter32
    MAX-ACCESS  read-only
    STATUS  current
    DESCRIPTION
        "Total number of create session messages received."
    ::= { sessMirrorStats 1 }

sessMirrorTotalCreateSessionMsgTx OBJECT-TYPE
    SYNTAX  Counter32
    MAX-ACCESS  read-only
    STATUS  current
    DESCRIPTION
        "Total number of create session messages transmitted ."
    ::= { sessMirrorStats 2 }

sessMirrorTotalCreateDataSessionMsgRx OBJECT-TYPE
    SYNTAX  Counter32
    MAX-ACCESS  read-only
    STATUS  current
    DESCRIPTION
        "Total number of create data session messages received."
    ::= { sessMirrorStats 3 }

sessMirrorTotalCreateDataSessionMsgTx OBJECT-TYPE
    SYNTAX  Counter32
    MAX-ACCESS  read-only
    STATUS  current
    DESCRIPTION
        "Total number of create data session messages transmitted."
    ::= { sessMirrorStats 4 }

sessMirrorTotalUpdateSessionMsgRx OBJECT-TYPE
    SYNTAX  Counter32
    MAX-ACCESS  read-only
    STATUS  current
    DESCRIPTION
        "Total number of update session messages received."
    ::= { sessMirrorStats 5 }

sessMirrorTotalUpdateSessionMsgTx OBJECT-TYPE
    SYNTAX  Counter32
    MAX-ACCESS  read-only
    STATUS  current
    DESCRIPTION
        "Total number of update session messages transmitted."
    ::= { sessMirrorStats 6 }

sessMirrorTotalUpdateDataSessionMsgRx OBJECT-TYPE
    SYNTAX  Counter32
    MAX-ACCESS  read-only
    STATUS  current
    DESCRIPTION
        "Total number of update data session messages received."
    ::= { sessMirrorStats 7 }

sessMirrorTotalUpdateDataSessionMsgTx OBJECT-TYPE
    SYNTAX  Counter32
    MAX-ACCESS  read-only
    STATUS  current
    DESCRIPTION
        "Total number of update data session messages transmitted."
    ::= { sessMirrorStats 8 }

sessMirrorTotalDeleteSessionMsgRx OBJECT-TYPE
    SYNTAX  Counter32
    MAX-ACCESS  read-only
    STATUS  current
    DESCRIPTION
        "Total number of delete session messages received."
    ::= { sessMirrorStats 9 }

sessMirrorTotalDeleteSessionMsgTx OBJECT-TYPE
    SYNTAX  Counter32
    MAX-ACCESS  read-only
    STATUS  current
    DESCRIPTION
        "Total number of delete session messages transmitted."
    ::= { sessMirrorStats 10 }

sessMirrorTotalDeleteDataSessionMsgRx OBJECT-TYPE
    SYNTAX  Counter32
    MAX-ACCESS  read-only
    STATUS  current
    DESCRIPTION
        "Total number of delete data session messages received."
    ::= { sessMirrorStats 11 }

sessMirrorTotalDeleteDataSessionMsgTx OBJECT-TYPE
    SYNTAX  Counter32
    MAX-ACCESS  read-only
    STATUS  current
    DESCRIPTION
        "Total number of delete data session messages transmitted."
    ::= { sessMirrorStats 12 }

sessMirrorTotalSessionsCreated OBJECT-TYPE
    SYNTAX  Counter32
    MAX-ACCESS  read-only
    STATUS  current
    DESCRIPTION
        "Total number of sessions created."
    ::= { sessMirrorStats 13 }

sessMirrorTotalDataSessionsCreated OBJECT-TYPE
    SYNTAX  Counter32
    MAX-ACCESS  read-only
    STATUS  current
    DESCRIPTION
        "Total number of data sessions created."
    ::= { sessMirrorStats 14 }

sessMirrorTotalSessionsUpdated OBJECT-TYPE
    SYNTAX  Counter32
    MAX-ACCESS  read-only
    STATUS  current
    DESCRIPTION
        "Total number of sessions updated."
    ::= { sessMirrorStats 15 }

sessMirrorTotalDataSessionsUpdated OBJECT-TYPE
    SYNTAX  Counter32
    MAX-ACCESS  read-only
    STATUS  current
    DESCRIPTION
        "Total number of data sessions updated."
    ::= { sessMirrorStats 16 }

sessMirrorTotalSessionsDeleted OBJECT-TYPE
    SYNTAX  Counter32
    MAX-ACCESS  read-only
    STATUS  current
    DESCRIPTION
        "Total number of sessions deleted."
    ::= { sessMirrorStats 17 }

sessMirrorTotalDataSessionsDeleted OBJECT-TYPE
    SYNTAX  Counter32
    MAX-ACCESS  read-only
    STATUS  current
    DESCRIPTION
        "Total number of data sessions deleted."
    ::= { sessMirrorStats 18 }

sessMirrorSessionTableFullErr OBJECT-TYPE
    SYNTAX  Counter32
    MAX-ACCESS  read-only
    STATUS  current
    DESCRIPTION
        "Error indicates session table full."
    ::= { sessMirrorStats 19 }

sessMirrorNoPortErr OBJECT-TYPE
    SYNTAX  Counter32
    MAX-ACCESS  read-only
    STATUS  current
    DESCRIPTION
        "Error indicates unavailable port."
    ::= { sessMirrorStats 20 }

sessMirrorSessionPresentErr OBJECT-TYPE
    SYNTAX  Counter32
    MAX-ACCESS  read-only
    STATUS  current
    DESCRIPTION
        "Error indicates session already present."
    ::= { sessMirrorStats 21 }

sessMirrorSessionNotFoundErr OBJECT-TYPE
    SYNTAX  Counter32
    MAX-ACCESS  read-only
    STATUS  current
    DESCRIPTION
        "Error indicates session not found."
    ::= { sessMirrorStats 22 }

sessMirrorCtrlSessionNotFoundErr OBJECT-TYPE
    SYNTAX  Counter32
    MAX-ACCESS  read-only
    STATUS  current
    DESCRIPTION
        "Error indicates control session not found."
    ::= { sessMirrorStats 23 }


-- Real Server Information Table

slbRealServerInfoTable OBJECT-TYPE
    SYNTAX  SEQUENCE OF SlbRealServerInfoEntry
    MAX-ACCESS  not-accessible
    STATUS  current
    DESCRIPTION
        "The table of real server run-time information."
    ::= { layer4Info 1 }

slbRealServerInfoEntry OBJECT-TYPE
    SYNTAX  SlbRealServerInfoEntry
    MAX-ACCESS  not-accessible
    STATUS  current
    DESCRIPTION
        "A row in the real server information table."
    INDEX   { slbRealServerInfoIndex }
    ::= { slbRealServerInfoTable 1 }
 
SlbRealServerInfoEntry ::= SEQUENCE {
    slbRealServerInfoIndex           Integer32,
    slbRealServerInfoIpAddr          IpAddress,
    slbRealServerMacAddr             PhysAddress,
    slbRealServerInfoSwitchPort      Integer32,
    slbRealServerInfoHealthLayer     INTEGER,
    slbRealServerInfoOverflow        INTEGER,
    slbRealServerInfoState           INTEGER,
    slbRealServerInfoVlan            Integer32
    }

slbRealServerInfoIndex OBJECT-TYPE
    SYNTAX  Integer32
    MAX-ACCESS  read-only
    STATUS  current
    DESCRIPTION
        "The real server index" 
    ::= { slbRealServerInfoEntry 1 }

slbRealServerInfoIpAddr OBJECT-TYPE
    SYNTAX  IpAddress
    MAX-ACCESS  read-only
    STATUS  current
    DESCRIPTION
        "IP address of the real server." 
    ::= { slbRealServerInfoEntry 2 }

slbRealServerMacAddr OBJECT-TYPE
    SYNTAX  PhysAddress
    MAX-ACCESS  read-only
    STATUS  current
    DESCRIPTION
        "The MAC address of the real server." 
    ::= { slbRealServerInfoEntry 3 }

slbRealServerInfoSwitchPort OBJECT-TYPE
    SYNTAX  Integer32
    MAX-ACCESS  read-only
    STATUS  current
    DESCRIPTION
        "The switch port that the real server is connected to." 
    ::= { slbRealServerInfoEntry 4 }

slbRealServerInfoHealthLayer  OBJECT-TYPE
    SYNTAX  INTEGER { 
        layer1(1), 
        layer3(3),
        layer4(4)
        } 
    MAX-ACCESS  read-only
    STATUS  current
    DESCRIPTION
        "The OSI layer at which the real server functionality is verified."
    ::= { slbRealServerInfoEntry 5 }

slbRealServerInfoOverflow OBJECT-TYPE
    SYNTAX  INTEGER {
	overflow(1),
        no-overflow(2) 
        } 
    MAX-ACCESS  read-only
    STATUS  current
    DESCRIPTION
        "The overflow state of the real server." 
    ::= { slbRealServerInfoEntry 6 }

slbRealServerInfoState OBJECT-TYPE
    SYNTAX  INTEGER {
        running(2),
        failed(3),
        disabled(4)
        } 
    MAX-ACCESS  read-only
    STATUS  current
    DESCRIPTION
        "The state of the real server."
    ::= { slbRealServerInfoEntry 7 }

slbRealServerInfoVlan OBJECT-TYPE
    SYNTAX  Integer32
    MAX-ACCESS  read-only
    STATUS  current
    DESCRIPTION
        "The VLAN that the real server belongs to." 
    ::= { slbRealServerInfoEntry 8 }

-- Real Server Rport Table
slbRealServerRportInfoTable OBJECT-TYPE
    SYNTAX  SEQUENCE OF SlbRealServerRportInfoEntry
    MAX-ACCESS  not-accessible
    STATUS  current
    DESCRIPTION
        "The table of real server rport run-time information."
    ::= { layer4Info 3 }

slbRealServerRportInfoEntry OBJECT-TYPE
    SYNTAX  SlbRealServerRportInfoEntry
    MAX-ACCESS  not-accessible
    STATUS  current
    DESCRIPTION
        "A row in the real server rport information table."
    INDEX   { slbRealServerRportRealIndex, slbRealServerRportServIndex  }
    ::= { slbRealServerRportInfoTable 1 }
 
SlbRealServerRportInfoEntry ::= SEQUENCE {
    slbRealServerRportRealIndex           Integer32,
    slbRealServerRportServIndex           Integer32,
    slbRealServerRportInfoRport           Integer32,
    slbRealServerRportInfoState           INTEGER,
    slbRealServerRportInfoGroup           INTEGER
    }

slbRealServerRportRealIndex OBJECT-TYPE
    SYNTAX  Integer32
    MAX-ACCESS  read-only
    STATUS  current
    DESCRIPTION
        "The real server index" 
    ::= { slbRealServerRportInfoEntry 1 }

slbRealServerRportServIndex OBJECT-TYPE
    SYNTAX  Integer32
    MAX-ACCESS  read-only
    STATUS  current
    DESCRIPTION
        "The real server service index" 
    ::= { slbRealServerRportInfoEntry 2 }

slbRealServerRportInfoRport OBJECT-TYPE
    SYNTAX  Integer32
    MAX-ACCESS  read-only
    STATUS  current
    DESCRIPTION
        "The real server real port number" 
    ::= { slbRealServerRportInfoEntry 3 }

slbRealServerRportInfoState OBJECT-TYPE
    SYNTAX  INTEGER {
        up(1),
        down(2)
        ,slowstart(3)
        } 
    MAX-ACCESS  read-only
    STATUS  current
    DESCRIPTION
        "The state of the real server port."
    ::= { slbRealServerRportInfoEntry 4 }

slbRealServerRportInfoGroup OBJECT-TYPE
    SYNTAX  INTEGER
    MAX-ACCESS  read-only
    STATUS  current 
    DESCRIPTION
        "The real server group number."
    ::= { slbRealServerRportInfoEntry 5 }

-- Virtual Server Service Information Table

slbVirtServicesInfoTable OBJECT-TYPE
    SYNTAX  SEQUENCE OF SlbVirtServicesInfoEntry
    MAX-ACCESS  not-accessible
    STATUS  current
    DESCRIPTION
        "The table of virtual server services run-time information."
    ::= { layer4Info 4 }

slbVirtServicesInfoEntry OBJECT-TYPE
    SYNTAX  SlbVirtServicesInfoEntry
    MAX-ACCESS  not-accessible
    STATUS  current
    DESCRIPTION
        "A row in the virtual service information table."
    INDEX   { slbVirtServicesInfoVirtServIndex, slbVirtServicesInfoSvcIndex, 
              slbVirtServicesInfoRealServIndex }
    ::= { slbVirtServicesInfoTable 1 }
 
SlbVirtServicesInfoEntry ::= SEQUENCE {
    slbVirtServicesInfoVirtServIndex   Integer32,
    slbVirtServicesInfoSvcIndex        Integer32,
    slbVirtServicesInfoRealServIndex   Integer32,
    slbVirtServicesInfoVport           Integer32,
    slbVirtServicesInfoRport           Integer32,
    slbVirtServicesInfoState           INTEGER,
    slbVirtServicesInfoResponseTime    Integer32,
    slbVirtServicesInfoWeight          Integer32
    }

slbVirtServicesInfoVirtServIndex OBJECT-TYPE
    SYNTAX  Integer32
    MAX-ACCESS  read-only
    STATUS  current
    DESCRIPTION
        "The virtual server index." 
    ::= { slbVirtServicesInfoEntry 1 }

slbVirtServicesInfoSvcIndex OBJECT-TYPE
    SYNTAX  Integer32
    MAX-ACCESS  read-only
    STATUS  current
    DESCRIPTION
        "The virtual service index." 
    ::= { slbVirtServicesInfoEntry 2 }

slbVirtServicesInfoRealServIndex OBJECT-TYPE
    SYNTAX  Integer32
    MAX-ACCESS  read-only
    STATUS  current
    DESCRIPTION
        "The real server index." 
    ::= { slbVirtServicesInfoEntry 3 }

slbVirtServicesInfoVport OBJECT-TYPE
    SYNTAX  Integer32
    MAX-ACCESS  read-only
    STATUS  current
    DESCRIPTION
        "The layer 4 virtual port number for the service." 
    ::= { slbVirtServicesInfoEntry 4 }

slbVirtServicesInfoRport OBJECT-TYPE
    SYNTAX  Integer32
    MAX-ACCESS  read-only
    STATUS  current
    DESCRIPTION
        "The layer 4 real port number for the service." 
    ::= { slbVirtServicesInfoEntry 5 }

slbVirtServicesInfoState OBJECT-TYPE
    SYNTAX  INTEGER {
        blocked(1),
        running(2),
        failed(3),
        disabled(4)
        ,slowstart(5)
	}
    MAX-ACCESS  read-only
    STATUS  current
    DESCRIPTION
        "The state of the real server for this virtual service." 
    ::= { slbVirtServicesInfoEntry 6 }

slbVirtServicesInfoResponseTime OBJECT-TYPE
    SYNTAX  Integer32
    MAX-ACCESS  read-only
    STATUS  current
    DESCRIPTION
        "The health check response time for the real server for this 
         virtual service." 
    ::= { slbVirtServicesInfoEntry 7 }

slbVirtServicesInfoWeight OBJECT-TYPE
    SYNTAX  Integer32
    MAX-ACCESS  read-only
    STATUS  current
    DESCRIPTION
        "The real server weight." 
    ::= { slbVirtServicesInfoEntry 8 }


-- slb session table info
slbSessionInfo        OBJECT IDENTIFIER ::= { layer4Info 5 }

slbSessionInfoState OBJECT-TYPE
    SYNTAX  INTEGER {
	start(1), 
        idle(2),
        inprogress(3),
	complete(4)
	}
    MAX-ACCESS  read-write
    STATUS  current
    DESCRIPTION
 	"When this object is read the current state is returned.
         idle(2) indicates that there is no session binding table request
         in progress.
	 When a read on this object returns inprogress(3) indicates that
	 a session binding table retrieval request is in progress.
         Setting the value to start(1), will start a new session table 
         retrieval operation based on the filtering criteria.
         complete(4) indicates that the session table has been retrieved.
         Once the slbSessionInfoTable is read the state should be set back to 
         'idle' which frees the session table buffer and others can issue a 
         request command via SNMP."
	
    ::= { slbSessionInfo 1 }

slbSessionInfoType OBJECT-TYPE
    SYNTAX  INTEGER {
	all(1),
	cip(2),
	cport(3),
	dip(4),
	dport(5),
	pip(6),
	pport(7),
	filter(8),
	flag(9),
	port(10),
	real(11)
	}
    MAX-ACCESS  read-write
    STATUS  current
    DESCRIPTION
        "This identifies the filtering criteria for the 
         session binding table request. 
	 all(1)   : Show all session entries
	 cip(2)   : Show all session entries with source IP address
         cport(3) : Show all session entries with source port
         dip(4)   : Show all session entries with destination IP address
         dport(5) : Show all session entries with destination port
         pip(6)   : Show all session entries with proxy IP address
         pport(7) : Show all session entries with proxy port
         filter(8): Show all session entries with matching filter
         flag(9)  : Show all session entries with matching flag
         port(10) : Show all session entries with ingress port
         real(11) : Show all session entries with real IP address."
    ::= { slbSessionInfo 2 }

slbSessionInfoIpAddr OBJECT-TYPE
    SYNTAX  IpAddress
    MAX-ACCESS  read-write
    STATUS  current
    DESCRIPTION
        "IP address of the requested filtering criteria 
	 0.0.0.0 if the filtering criteria is not  to match
         session entries with the same IP address."
    ::= { slbSessionInfo 3 }

slbSessionInfoFilterId OBJECT-TYPE
    SYNTAX  Integer32
    MAX-ACCESS  read-write
    STATUS  current
    DESCRIPTION
         "This field indicates that the session is created by filtering
          code as a result of the IP header keys matching the filtering
          criteria. 0 if slbSessionInfoFilterID is not the matching criteria."
    ::= { slbSessionInfo 4 }

slbSessionInfoPortId OBJECT-TYPE
    SYNTAX  Integer32
    MAX-ACCESS  read-write
    STATUS  current
    DESCRIPTION
        "The <port number> if the filtering criteria is (port) to
         match all session entries with the matching ingress port 
         or this represents the <real port> if the requested filtering
         criteria is to match session entries with (pport) proxy port, 
         (cport) source port, (dport) destination port,  
         This entry is 0 if the filtering criteria is not to match
         session entries with the same port."
    ::= { slbSessionInfo 5 }

slbSessionInfoFlag OBJECT-TYPE
    SYNTAX  INTEGER {
	eFlag(1),
	lFlag(2),
	nFlag(3),
	pFlag(4),
	sFlag(5),
	tFlag(6),
	uFlag(7),
	wFlag(8),
	ruFlag(9),
	riFlag(10),
	viFlag(11),
	vrFlag(12),
	vsFlag(13),
        vmFlag(14),
	vdFlag(15),
	none(20)
	}
    MAX-ACCESS  read-write
    STATUS  current
    DESCRIPTION
        "If the filtering criteria is flag select one of e|l|n|p|s|t|u|w(Flag)
         none(20) is selected if flag is not the fitering criteria.

         eFlag: Indicates the session is in use and will be aged out if no
                traffic is received within session timeout value.

         lFlag: Indicates the session is a link load balance session.

         nFlag: Indicates the session only translates the destination
                MAC when forwarding client traffic to the real server.

         pFlag: Indicates the session is a persistent session and is not to
                be aged out. Fields (6), (7) and (8) are not shown for
                persistent session.

         sFlag: Indicates the session is a persistent session and the
                application is SSL or Cookie Pbind.

         tFlag: Indicates the session is TCP rate limiting per-client entry.

         uFlag: Indicates the session is L7 delay binding and switch is
                trying to open TCP connection to real server.

         wFlag: Indicates the session only translates the destination
                MAC when forwarding layer 7 WCR traffic to the real server.

         ruFlag: Indicates the session is a UDP rate limiting per-client entry.

         riFlag: Indicates the session is a ICMP rate limiting per-client 
                 entry.

         viFlag: Indicates the session is a SIP INVITE session.

         vrFlag: Indicates the session is a SIP REGISTER session.

         vsFlag: Indicates the session is a SIP SUBSCRIBE session.

         vmFlag: Indicates the session is a SIP MESSAGE session.

         vdFlag: Indicates the session is a SIP NAT data session."

    ::= { slbSessionInfo 6 }

slbSessionInfoStringFormatFlag OBJECT-TYPE
    SYNTAX  INTEGER {
	formatted(1),
	none(2)
	}
    MAX-ACCESS  read-write
    STATUS  current
    DESCRIPTION
        "The flag which determines if the session table entries
         have to be formatted or (none) indicates no formatting to be done." 
    ::= { slbSessionInfo 7 }

slbSessionInfoMaxSessDump OBJECT-TYPE
    SYNTAX  Integer32 
    MAX-ACCESS  read-only
    STATUS  current
    DESCRIPTION
    "The maximum number of sessions that can exist at any given time."
    ::= { slbSessionInfo 9 }

slbSessionInfoTable OBJECT-TYPE
    SYNTAX SEQUENCE OF SlbSessionInfoEntry
    MAX-ACCESS not-accessible
    STATUS current
    DESCRIPTION
        "The table of SLB session entries."
    ::= { slbSessionInfo 8 }

slbSessionInfoEntry OBJECT-TYPE
    SYNTAX SlbSessionInfoEntry
    MAX-ACCESS not-accessible
    STATUS current
    DESCRIPTION
        "Information about SLB sessions."
    INDEX { slbSessionInfoSpIndex, slbSessionInfoIndex }
    ::= { slbSessionInfoTable 1 }
 
SlbSessionInfoEntry ::= SEQUENCE {
    slbSessionInfoSpIndex                    Integer32,
    slbSessionInfoIndex                      Integer32,
    slbSessionInfoString            	     OCTET STRING
    }

slbSessionInfoSpIndex OBJECT-TYPE
    SYNTAX  Integer32
    MAX-ACCESS  read-only
    STATUS  current
    DESCRIPTION
        "The SP which created the session." 
    ::= { slbSessionInfoEntry 1 }

slbSessionInfoIndex OBJECT-TYPE
    SYNTAX  Integer32
    MAX-ACCESS  read-only
    STATUS  current
    DESCRIPTION
        "The index to the slbSessionInfoTable." 
    ::= { slbSessionInfoEntry 2 }

slbSessionInfoString OBJECT-TYPE
    SYNTAX OCTET STRING
    MAX-ACCESS read-only
    STATUS current
    DESCRIPTION
        "The string representing the SLB session entries in the formatted case:
	 The fields, (1)-(13), associated with a session, as identified in the
	 example below are described in the following.

3, 01: 1.1.1.1 4586, 2.2.2.1 http -> 3567 3.3.3.1 http age 6 f:10 ELNPSRtUW c:#
(1) (2) (3)     (4)  (5)      (6)     (7)   (8)    (9)  (10)  (11)  (12) (13)

3, 01: 1.1.1.1 4586, 2.2.2.1 http ->
(1) (2) (3)     (4)  (5)      (6)
       1.1.1.2 3567 3.3.3.1 http age 6 f:10 ELNPSRtUW c:#
        (7a)     (7)   (8)    (9) (10)  (11)  (12) (13)

------------------------------------------------------------------
(1) SP number:
    This field indicates which SP created the session.

(2) Ingress port:
    This field shows the physical port# of the client traffic that
    entered to the switch.

(3) Source IP address:
    This field contains the source IP address from client IP packet.

(4) Source port:                          
    This field identifies the TCP/UDP source port from client packet.

(5) Destination IP address:
    This is the destination IP address from client TCP/UDP packet.

    For load balancing, this address is the virtual IP address.
    For filtering redirect, this address is the destination server's address.

(6) Destination port:
    This field identifies the TCP/UDP destination port from client packet.

(7a)Proxy IP address:                     
    This field contains the proxy IP address substituted by the switch.

(7) Proxy port:                           
    This field identifies the TCP/UDP source port substituted by the switch.

    The switch does this substitution when Direct Access Mode is enabled or
    Proxy is enabled.

(8) Real server IP address:               
    For load balancing, this field contains the IP address of the real
    server that the switch selects to forward client packet to.
    If the switch does not find live server, this field is the
    same as destination IP address(5).

    e.g. 3,01: 1.1.1.1 1040, 2.2.2.1 http -> 3.3.3.1 http age 10
         3,01: 1.1.1.1 1040, 2.2.2.1 http -> 2.2.2.1 http age 10

    For filtering, this field also shows the real server IP address. No
    address is shown if the filter action is Allow, Deny or NAT.
    It will show ALLOW, DENY or NAT instead.

    e.g. 3,01: 1.1.1.1 1040, 2.2.2.1 http -> 3.3.3.1 http age 10 f:11
         3,01: 1.1.1.1 1040, 2.2.2.1 http ALLOW age 10 f:22

(9) Server port:                          
    For load balancing, this field is the same as destination port(6)
    except for the RTSP UDP session. For RTSP UDP session, this server
    port is obtained from client-server negotiation.

    e.g. 3,01: 1.1.1.1 1040, 2.2.2.1 http -> 3.3.3.1 http age 10
         3,01: 1.1.1.1 6970, 2.2.2.1 rtsp -> 3.3.3.1 21220 age 10 P

    For filtering, this field is the filtering application port.
    It is for internal use only. This field can be urlwcr, wcr,
    idslb, linkslb or nonat.
    e.g. 3,01: 1.1.1.1 1040, 2.2.2.1 http -> 3.3.3.1 urlwcr age 4 f:123
         2,07: 1.1.1.1 1706, 2.2.2.1 http -> 192.168.4.10 linklb age 8 f:10 E

(10) Age:
    This is the session timeout value. If no packet is received within
    the value specified, the session is freed.
    e.g. age 10    - The session is aged out in 10 minutes.
         age < 160 - The session is aged out in 160 minutes. This <
                     indicates that slowage is used(user configures
                     /cfg/slb/adv/slowage)

(11) Filter number:                       
     This field indicates that the session is created by filtering
     code as a result of the IP header keys matching the filtering
     criteria.

(12) Flag:
     E: Indicates the session is in use and will be aged out if no
        traffic is received within session timeout value.

     L: Indicates the session is a link load balance session.

     N: Indicates the session only translates the destination
        MAC when forwarding client traffic to the real server.

     P: Indicates the session is a persistent session and is not to
        be aged out. Fields (6), (7) and (8) are not shown for
        persistent session.

     S: Indicates the session is a persistent session and the
        application is SSL or Cookie Pbind.

     Rt: Indicates the session is TCP rate limiting per-client entry.

     Ru: Indicates the session is UDP rate limiting per-client entry.

     Ri: Indicates the session is ICMP rate limiting per-client entry.

     U: Indicates the session is L7 delay binding and switch is
        trying to open TCP connection to real server.

     W: Indicates the session only translates the destination
        MAC when forwarding layer 7 WCR traffic to the real server.

(13) Persistent session user count:
     This counter indicates the number of client sessions created
     associated with this persistent session."
    ::= { slbSessionInfoEntry 3 }

-- Global SLB Information

gslbInfo         OBJECT IDENTIFIER ::= { layer4Info 6 }

-- Global SLB Remote Real Server Information

gslbInfoRemRealServerTable OBJECT-TYPE
    SYNTAX SEQUENCE OF GslbInfoRemRealServerEntry
    MAX-ACCESS not-accessible
    STATUS current
    DESCRIPTION
        "The Global SLB virtual server information table."
    ::= { gslbInfo 1 }

gslbInfoRemRealServerEntry OBJECT-TYPE
    SYNTAX GslbInfoRemRealServerEntry
    MAX-ACCESS not-accessible
    STATUS current
    DESCRIPTION
        "A row in the Global SLB remote real server information table."
    INDEX { gslbInfoRemRealServerIdx }
    ::= { gslbInfoRemRealServerTable 1 }

GslbInfoRemRealServerEntry ::=     SEQUENCE {
    gslbInfoRemRealServerIdx            Integer32,
    gslbInfoRemRealServerIpAddr         IpAddress,
    gslbInfoRemRealServerName           DisplayString,
    gslbInfoRemRealServerState          INTEGER
    }

gslbInfoRemRealServerIdx OBJECT-TYPE
    SYNTAX Integer32
    MAX-ACCESS read-only
    STATUS current
    DESCRIPTION
        "The remote real server number that identifies the remote real server."
    ::= { gslbInfoRemRealServerEntry 1 }

gslbInfoRemRealServerIpAddr OBJECT-TYPE
    SYNTAX IpAddress
    MAX-ACCESS read-only
    STATUS current
    DESCRIPTION
        "IP address of the remote real server."
    ::= { gslbInfoRemRealServerEntry 2 }

gslbInfoRemRealServerName OBJECT-TYPE
    SYNTAX DisplayString (SIZE(0..31))
    MAX-ACCESS read-only
    STATUS current
    DESCRIPTION
        "The name of the remote real server."
    ::= { gslbInfoRemRealServerEntry 3 }

gslbInfoRemRealServerState OBJECT-TYPE
    SYNTAX INTEGER {
        running(2),
        failed(3),
        disabled(4)
        }
    MAX-ACCESS read-only
    STATUS current
    DESCRIPTION
        "The state of the remote real server."
    ::= { gslbInfoRemRealServerEntry 4 }

-- Global SLB Virtual Server Information

gslbInfoVirtServerTable OBJECT-TYPE
    SYNTAX SEQUENCE OF GslbInfoVirtServerEntry
    MAX-ACCESS not-accessible
    STATUS current
    DESCRIPTION
        "The Global SLB virtual server information table."
    ::= { gslbInfo 2 }

gslbInfoVirtServerEntry OBJECT-TYPE
    SYNTAX GslbInfoVirtServerEntry
    MAX-ACCESS not-accessible
    STATUS current
    DESCRIPTION
        "A row in the Global SLB virtual server information table."
    INDEX { gslbInfoVirtServerIdx, gslbInfoVirtServerServiceIdx,
            gslbInfoVirtServerRserverIdx }
    ::= { gslbInfoVirtServerTable 1 }

GslbInfoVirtServerEntry ::=     SEQUENCE {
    gslbInfoVirtServerIdx            Integer32,
    gslbInfoVirtServerServiceIdx     Integer32,
    gslbInfoVirtServerRserverIdx     Integer32,
    gslbInfoVirtServerDname          DisplayString,
    gslbInfoVirtServerVirtPort       Integer32,
    gslbInfoVirtServerIpAddress      IpAddress,
    gslbInfoVirtServerResponse       Integer32,
    gslbInfoVirtServerSessAvail      Integer32,
    gslbInfoVirtServerSessCur        Integer32,
    gslbInfoVirtServerSessMax        Integer32,
    gslbInfoVirtServerSessUtil       INTEGER,
    gslbInfoVirtServerCpuUtil        INTEGER,
    gslbInfoVirtServerRemSite        Integer32,
    gslbInfoVirtServerWeight         INTEGER,
    gslbInfoVirtServerAvail          INTEGER,
    gslbInfoVirtServerRegion         INTEGER
    }

gslbInfoVirtServerIdx OBJECT-TYPE
    SYNTAX Integer32
    MAX-ACCESS read-only
    STATUS current
    DESCRIPTION
        "The virtual server number that identifies the virtual server."
    ::= { gslbInfoVirtServerEntry 1 }

gslbInfoVirtServerServiceIdx OBJECT-TYPE
    SYNTAX Integer32
    MAX-ACCESS read-only
    STATUS current
    DESCRIPTION
        "The virtual server service number that identifies the virtual service."
    ::= { gslbInfoVirtServerEntry 2 }

gslbInfoVirtServerRserverIdx OBJECT-TYPE
    SYNTAX Integer32
    MAX-ACCESS read-only
    STATUS current
    DESCRIPTION
        "The real server number that identifies a remote real server.
         An index of 0 indicates virtual server."
    ::= { gslbInfoVirtServerEntry 3 }

gslbInfoVirtServerDname OBJECT-TYPE
    SYNTAX DisplayString (SIZE(0..64))
    MAX-ACCESS read-only
    STATUS current
    DESCRIPTION
        "The domain name of the virtual server and remote real server."
    ::= { gslbInfoVirtServerEntry 4 }

gslbInfoVirtServerVirtPort OBJECT-TYPE
    SYNTAX Integer32
    MAX-ACCESS read-only
    STATUS current
    DESCRIPTION
        "The service port of the virtual server and remote real server."
    ::= { gslbInfoVirtServerEntry 5 }

gslbInfoVirtServerIpAddress OBJECT-TYPE
    SYNTAX IpAddress
    MAX-ACCESS read-only
    STATUS current
    DESCRIPTION
        "The IP address of the virtual server or remote real server."
    ::= { gslbInfoVirtServerEntry 6 }

gslbInfoVirtServerResponse OBJECT-TYPE
    SYNTAX Integer32
    MAX-ACCESS read-only
    STATUS current
    DESCRIPTION
        "The health check response time of the virtual server or remote real server."
    ::= { gslbInfoVirtServerEntry 7 }

gslbInfoVirtServerSessAvail OBJECT-TYPE
    SYNTAX Integer32
    MAX-ACCESS read-only
    STATUS current
    DESCRIPTION
        "The available sessions of the virtual server or remote real server."
    ::= { gslbInfoVirtServerEntry 8 }

gslbInfoVirtServerSessCur OBJECT-TYPE
    SYNTAX Integer32
    MAX-ACCESS read-only
    STATUS current
    DESCRIPTION
        "The current sessions of the virtual server or remote real server."
    ::= { gslbInfoVirtServerEntry 9 }

gslbInfoVirtServerSessMax OBJECT-TYPE
    SYNTAX Integer32
    MAX-ACCESS read-only
    STATUS current
    DESCRIPTION
        "The maximum sessions supported by the virtual server or remote real server."
    ::= { gslbInfoVirtServerEntry 10 }

gslbInfoVirtServerSessUtil OBJECT-TYPE
    SYNTAX INTEGER(1..100)
    MAX-ACCESS read-only
    STATUS current
    DESCRIPTION
        "The sessions utilization (current/max) of the virtual server or remote real server."
    ::= { gslbInfoVirtServerEntry 11 }

gslbInfoVirtServerCpuUtil OBJECT-TYPE
    SYNTAX INTEGER(1..100)
    MAX-ACCESS read-only
    STATUS current
    DESCRIPTION
        "The CPU utilization of the virtual server or remote real server."
    ::= { gslbInfoVirtServerEntry 12 }

gslbInfoVirtServerRemSite OBJECT-TYPE
    SYNTAX Integer32
    MAX-ACCESS read-only
    STATUS current
    DESCRIPTION
        "The remote site of the remote real server. For virtual server, the remote site is 0."
    ::= { gslbInfoVirtServerEntry 13 }

gslbInfoVirtServerWeight OBJECT-TYPE
    SYNTAX INTEGER(1..48)
    MAX-ACCESS read-only
    STATUS current
    DESCRIPTION
        "The weight of the virtual server or remote real server."
    ::= { gslbInfoVirtServerEntry 14 }

gslbInfoVirtServerAvail OBJECT-TYPE
    SYNTAX INTEGER(1..48)
    MAX-ACCESS read-only
    STATUS current
    DESCRIPTION
        "The availability of the virtual server or remote real server."
    ::= { gslbInfoVirtServerEntry 15 }

gslbInfoVirtServerRegion OBJECT-TYPE
    SYNTAX INTEGER {
        unknown(0),
        northamerica(1),
        southamerica(2),
        europe(3),
        caribbean(4),
        pacificrim(5),
        subsahara(6),
        japan(7),
        caribbeansubsahara(8),
	africa(9)
        }
    MAX-ACCESS read-only
    STATUS current
    DESCRIPTION
        "The region of the virtual server or remote real server."
    ::= { gslbInfoVirtServerEntry 16 }

-- Global SLB Remote Site Information

gslbInfoRemSiteTable OBJECT-TYPE
    SYNTAX SEQUENCE OF GslbInfoRemSiteEntry
    MAX-ACCESS not-accessible
    STATUS current
    DESCRIPTION
        "The Global SLB remote site information table."
    ::= { gslbInfo 3 }

gslbInfoRemSiteEntry OBJECT-TYPE
    SYNTAX GslbInfoRemSiteEntry
    MAX-ACCESS not-accessible
    STATUS current
    DESCRIPTION
        "A row in the Global SLB remote site information table."
    INDEX { gslbInfoRemSiteIdx }
    ::= { gslbInfoRemSiteTable 1 }

GslbInfoRemSiteEntry ::=     SEQUENCE {
    gslbInfoRemSiteIdx            Integer32,
    gslbInfoRemSitePrimaryIp      IpAddress,
    gslbInfoRemSiteSecondaryIp    IpAddress,
    gslbInfoRemSiteName           DisplayString,
    gslbInfoRemSiteState          INTEGER
    }

gslbInfoRemSiteIdx OBJECT-TYPE
    SYNTAX Integer32
    MAX-ACCESS read-only
    STATUS current
    DESCRIPTION
        "The remote site number that identifies the remote site."
    ::= { gslbInfoRemSiteEntry 1 }

gslbInfoRemSitePrimaryIp OBJECT-TYPE
    SYNTAX IpAddress
    MAX-ACCESS read-only
    STATUS current
    DESCRIPTION
        "The primary IP address of the remote site."
    ::= { gslbInfoRemSiteEntry 2 }

gslbInfoRemSiteSecondaryIp OBJECT-TYPE
    SYNTAX IpAddress
    MAX-ACCESS read-only
    STATUS current
    DESCRIPTION
        "The secondary IP address of the remote site."
    ::= { gslbInfoRemSiteEntry 3 }

gslbInfoRemSiteName OBJECT-TYPE
    SYNTAX DisplayString (SIZE(0..31))
    MAX-ACCESS read-only
    STATUS current
    DESCRIPTION
        "The name of the remote site."
    ::= { gslbInfoRemSiteEntry 4 }

gslbInfoRemSiteState OBJECT-TYPE
    SYNTAX INTEGER {
        running(2),
        failed(3),
        disabled(4)
        }
    MAX-ACCESS read-only
    STATUS current
    DESCRIPTION
        "The state of the remote site."
    ::= { gslbInfoRemSiteEntry 5 }

gslbInfoDnsSec        OBJECT IDENTIFIER ::= { gslbInfo 4 }

gslbInfoDnsSecKey     OBJECT IDENTIFIER ::= { gslbInfoDnsSec 2 }

gslbInfoDnsSecKeyTable OBJECT-TYPE
    SYNTAX  SEQUENCE OF GslbInfoDnsSecKeyEntry
    MAX-ACCESS  not-accessible
    STATUS  current
    DESCRIPTION
        "."
    ::= { gslbInfoDnsSecKey 1 }

gslbInfoDnsSecKeyEntry OBJECT-TYPE
    SYNTAX  GslbInfoDnsSecKeyEntry
    MAX-ACCESS  not-accessible
    STATUS  current
    DESCRIPTION
        "."
    INDEX   { gslbInfoDnsSecKeyID }
    ::= { gslbInfoDnsSecKeyTable 1 }

GslbInfoDnsSecKeyEntry ::= SEQUENCE {
    gslbInfoDnsSecKeyID                DisplayString,
    gslbInfoDnsSecKeyStatus            INTEGER
    }

gslbInfoDnsSecKeyID OBJECT-TYPE
    SYNTAX   DisplayString (SIZE(0..32))
    MAX-ACCESS  read-only
    STATUS  current
    DESCRIPTION
        "DNS Sec Table Key."
    ::= { gslbInfoDnsSecKeyEntry  1 }

gslbInfoDnsSecKeyStatus OBJECT-TYPE
    SYNTAX INTEGER {
    initRollProess(1), 
    newKeyCreated(2),
	newZskKeyDeployed(3),
	oldKeyRemoval(4),
	retrDsFromParent(5),
	newKskKeyDeployed(6),
	waitDsChangeOnParent(7),
	rolloverNotRunning(8),
	invalid(9),
	expired(10)
        }
    MAX-ACCESS  read-only
    STATUS  current
    DESCRIPTION
        "Key status."
    ::= { gslbInfoDnsSecKeyEntry 4 }



-- wlm Information

wlmInfo         OBJECT IDENTIFIER ::= { layer4Info 7 }

slbWlmInfoTable OBJECT-TYPE
    SYNTAX SEQUENCE OF SlbWlmInfoEntry
    MAX-ACCESS not-accessible
    STATUS current
    DESCRIPTION
        "The table of workload manager run-time information."
    ::= { wlmInfo 1 }

slbWlmInfoEntry OBJECT-TYPE
    SYNTAX SlbWlmInfoEntry
    MAX-ACCESS not-accessible
    STATUS current
    DESCRIPTION
        "A row in the workload manager information table."
    INDEX { slbWlmInfoIndex }
    ::= { slbWlmInfoTable 1 }

SlbWlmInfoEntry ::= SEQUENCE {
    slbWlmInfoIndex           Integer32,
    slbWlmInfoIpAddr          IpAddress,
    slbWlmInfoPort            INTEGER,
    slbWlmInfoState           INTEGER 
     }

slbWlmInfoIndex OBJECT-TYPE
    SYNTAX  Integer32
    MAX-ACCESS  read-only
    STATUS  current
    DESCRIPTION
        "The workload manager index."
    ::= { slbWlmInfoEntry 1 }

slbWlmInfoIpAddr OBJECT-TYPE
    SYNTAX  IpAddress
    MAX-ACCESS  read-only
    STATUS  current
    DESCRIPTION
        "IP address of the workload manager."
    ::= { slbWlmInfoEntry 2 }

slbWlmInfoPort OBJECT-TYPE
    SYNTAX  INTEGER (0..65534)
    MAX-ACCESS  read-only
    STATUS  current
    DESCRIPTION
        "The port number of the workload manager."
    ::= { slbWlmInfoEntry 3 }

slbWlmInfoState OBJECT-TYPE
    SYNTAX  INTEGER  { connected(1), notconnected(2)}
    MAX-ACCESS  read-only
    STATUS  current
    DESCRIPTION
        "The state of the workload manager."
    ::= { slbWlmInfoEntry 4 }


slbPortInfo         OBJECT IDENTIFIER ::= { layer4Info 8 }

slbPortInfoTable OBJECT-TYPE
    SYNTAX SEQUENCE OF SlbPortInfoEntry
    MAX-ACCESS not-accessible
    STATUS current
    DESCRIPTION
        "The table of port information."
    ::= { slbPortInfo 1 }

slbPortInfoEntry OBJECT-TYPE
    SYNTAX SlbPortInfoEntry
    MAX-ACCESS not-accessible
    STATUS current
    DESCRIPTION
        "A row in the port information table."
    INDEX { slbPortInfoIndex }
    ::= { slbPortInfoTable 1 }

SlbPortInfoEntry ::= SEQUENCE {
    slbPortInfoIndex           Integer32,
    slbPortClientState         INTEGER,
    slbPortSerState            INTEGER,
    slbPortFltState            INTEGER,
    slbPortRTSState            INTEGER,
    slbPortHotStandbyState     INTEGER,
    slbPortInterSWState        INTEGER,
    slbPortProxyState          INTEGER,
    slbPortIdSlbState          INTEGER,
    slbPortSymantecState       INTEGER,
    slbPortFitersAdded         OCTET STRING 
    }

slbPortInfoIndex OBJECT-TYPE
    SYNTAX Integer32
    MAX-ACCESS read-only
    STATUS current
    DESCRIPTION
        "Index of slb port."
    ::= { slbPortInfoEntry 1 }

slbPortClientState OBJECT-TYPE
    SYNTAX INTEGER {
        enabled(1),
        disabled(2)
        }
    MAX-ACCESS read-only
    STATUS current
    DESCRIPTION
        "Client state on the slb port."
    ::= { slbPortInfoEntry 2 }

slbPortSerState OBJECT-TYPE
    SYNTAX INTEGER {
        enabled(1),
        disabled(2)
        }
    MAX-ACCESS read-only
    STATUS current
    DESCRIPTION
        "Server state on the slb port."
    ::= { slbPortInfoEntry 3 }

slbPortFltState OBJECT-TYPE
    SYNTAX  INTEGER {
        enabled(1),
        disabled(2)
        } 
    MAX-ACCESS read-only
    STATUS current
    DESCRIPTION
        " Filter state on the slb port ."
    ::= { slbPortInfoEntry 4 }

slbPortRTSState OBJECT-TYPE
    SYNTAX INTEGER {
        enabled(1),
        disabled(2)
        }
    MAX-ACCESS read-only
    STATUS current
    DESCRIPTION
        "RTS processing state on the slb port."
    ::= { slbPortInfoEntry 5 }

slbPortHotStandbyState  OBJECT-TYPE
    SYNTAX INTEGER {
        enabled(1),
        disabled(2)
        }
    MAX-ACCESS read-only
    STATUS current
    DESCRIPTION
        "Hot standby state on the slb port."
    ::= { slbPortInfoEntry 6 }

slbPortInterSWState OBJECT-TYPE
    SYNTAX INTEGER {
        enabled(1),
        disabled(2)
        }
    MAX-ACCESS read-only
    STATUS current
    DESCRIPTION
        "Inter-switch processing state on the slb port."
    ::= { slbPortInfoEntry 7 }            

slbPortProxyState  OBJECT-TYPE
    SYNTAX INTEGER {
        enabled(1),
        disabled(2)
        }
    MAX-ACCESS read-only
    STATUS current
    DESCRIPTION
        "Proxy state on the slb port."
    ::= { slbPortInfoEntry 8 }

slbPortIdSlbState  OBJECT-TYPE
    SYNTAX INTEGER {
        enabled(1),
        disabled(2)
        }
    MAX-ACCESS read-only
    STATUS current
    DESCRIPTION
        "Intrusion detection server load balancing state on the slb port."
    ::= { slbPortInfoEntry 9 }

slbPortSymantecState  OBJECT-TYPE
    SYNTAX INTEGER {
        enabled(1),
        disabled(2)
        }
    MAX-ACCESS read-only
    STATUS current
    DESCRIPTION
        " Symantec Processing state on the slb port."
    ::= { slbPortInfoEntry 10 }

slbPortFitersAdded   OBJECT-TYPE
    SYNTAX  OCTET STRING (SIZE(0..256))
    MAX-ACCESS read-only
    STATUS current
    DESCRIPTION
        "The filtering rules applied to the port.  The filtering rules are
         presented in bitmap format.

         in receiving order:

             OCTET 1  OCTET 2  .....
             xxxxxxxx xxxxxxxx .....
             ||    || |_ filter 9
             ||    ||
             ||    ||___ filter 8
             ||    |____ filter 7
             ||      .    .   .
             ||_________ filter 2
             |__________ filter 1 

         where x : 1 - The represented filter rule applied to the port
                   0 - The represented filter rule not applied to the port."
    ::= { slbPortInfoEntry 11 }


synAttackInfo         OBJECT IDENTIFIER ::= { layer4Info 9 }

synAtkState OBJECT-TYPE
    SYNTAX INTEGER { on(1), off(2) }
    MAX-ACCESS read-only
    STATUS current
    DESCRIPTION
        "State of the Syn Attack, represents whether it is running or not."
    ::= { synAttackInfo 1}

synAtkInterval OBJECT-TYPE
    SYNTAX Integer32
    MAX-ACCESS read-only
    STATUS current
    DESCRIPTION
        "Specifies interval period of syn attack inspection in seconds,
         it returns 0 if synAtk is OFF."
    ::= { synAttackInfo 2}

synAtkThreshhold OBJECT-TYPE
    SYNTAX Integer32
    MAX-ACCESS read-only
    STATUS current
    DESCRIPTION
        "Specifies threshold of syn attack alram, it returns 0
         if synAtk is OFF ."
    ::= { synAttackInfo 3}

synAtkWarningFired OBJECT-TYPE
    SYNTAX Integer32
    MAX-ACCESS read-only
    STATUS current
    DESCRIPTION
        "Specifies number of times syn attack warnings fired."
    ::= { synAttackInfo 4}

synAtkResponseInterval OBJECT-TYPE
    SYNTAX Integer32
    MAX-ACCESS read-only
    STATUS current
    DESCRIPTION
        "Specifies interval period of syn cookie generation in milliseconds,
         it returns 0 if synAtk is OFF."
    ::= { synAttackInfo 5}

synAtkOnOff OBJECT-TYPE
    SYNTAX INTEGER { on(1), off(2) }
    MAX-ACCESS read-only
    STATUS current
    DESCRIPTION
        "Globaly set SYN Protection ON/FF."
    ::= { synAttackInfo 6}


slbFreeVirtualServerIndexInfo OBJECT-TYPE
    SYNTAX  INTEGER
    MAX-ACCESS  read-only
    STATUS  current
    DESCRIPTION
        "Retrieve the next virtual server index"
    ::= { layer4Info 10 }

slbFreeRealGroupIndexInfo OBJECT-TYPE
    SYNTAX  INTEGER
    MAX-ACCESS  read-only
    STATUS  current
    DESCRIPTION
        "Retrieve the next server group index"
    ::= { layer4Info 11 }

slbFreeRealServerIndexInfo OBJECT-TYPE
    SYNTAX  INTEGER
    MAX-ACCESS  read-only
    STATUS  current
    DESCRIPTION
        "Retrieve the next real server index"
    ::= { layer4Info 12 }

-- Operation Commands

slbOperRealServerTable OBJECT-TYPE
    SYNTAX  SEQUENCE OF SlbOperRealServerEntry
    MAX-ACCESS  not-accessible
    STATUS  current
    DESCRIPTION
        "The table of real servers."
    ::= { layer4Oper 1 }

slbOperRealServerEntry OBJECT-TYPE
    SYNTAX  SlbOperRealServerEntry
    MAX-ACCESS  not-accessible
    STATUS  current
    DESCRIPTION
        "A row in the slbOperRealServerTable "
    INDEX   { slbOperRealServerIndex }
    ::= { slbOperRealServerTable 1 }

SlbOperRealServerEntry ::= SEQUENCE {
    slbOperRealServerIndex              Integer32,
    slbOperRealServerStatus             INTEGER
    }

slbOperRealServerIndex OBJECT-TYPE
    SYNTAX  Integer32
    MAX-ACCESS  read-only
    STATUS  current
    DESCRIPTION
        "The index for the  real server." 
    ::= { slbOperRealServerEntry 1 }

slbOperRealServerStatus OBJECT-TYPE
    SYNTAX  INTEGER {
	enable(1),
	disable(2),
	cookiepersistent(3),
	fastage(4),
	cookiepersistentfastage(5)
	}
    MAX-ACCESS  read-write
    STATUS  current
    DESCRIPTION
        "This an action object which is used to temporarily enable/disable a
         real server. The real server will be returned to its configured
         operational mode when the switch is reset. Setting the value to 
         'cookiepersistant' allows cookie persistent HTTP 1.0 sessions
         when the real server is offline.'fastage' option is for removing the
         existing sessions. And 'cookiepersistentfastage' allows cookie
         persistent sessions and remove the existing sessions when real server is offline."
    ::= { slbOperRealServerEntry 2 }

slbOperClearSessionTable OBJECT-TYPE
    SYNTAX  INTEGER {
	ok(1),
	clear(2)
	}
    MAX-ACCESS  read-write
    STATUS  current
    DESCRIPTION
        "This is an action object to clear session binding table.
         ok(1) is returned when read."
    ::= { layer4Oper 2 }

slbOperConfigSync OBJECT-TYPE
    SYNTAX  INTEGER {
	ok(1),
	sync(2)
	}
    MAX-ACCESS  read-write
    STATUS  current
    DESCRIPTION
        "When set to a value of 'sync(2)' it synchronizes the SLB, filter
         and VRRP configuration on a peer switch. To take effect, peers must
         be configured on the switches and the administrator password on the
         switches must be identical. 
         'ok(1)' is returned when the object os read."
    ::= { layer4Oper 3 }

-- Global SLB Operations

gslbOper         OBJECT IDENTIFIER ::= { layer4Oper 4 }

gslbOperQuery    OBJECT IDENTIFIER ::= { gslbOper 1 }
gslbOperAdd      OBJECT IDENTIFIER ::= { gslbOper 2 }
gslbOperRemove OBJECT-TYPE
    SYNTAX  INTEGER {
        ok(1),
        remove(2)
        }
    MAX-ACCESS  read-write
    STATUS  current
    DESCRIPTION
        "This is an action object to Remove all entries
         from Global SLB DNS persistence cache.
         ok(1) is returned when read."
    ::= { gslbOper 3 }

gslbOperAvPersis OBJECT IDENTIFIER ::= { gslbOper 4 }

gslbOperClear OBJECT-TYPE
    SYNTAX  INTEGER {
        ok(1),
        clear(2)
        }
    MAX-ACCESS  read-write
    STATUS  current
    DESCRIPTION
        "This is an action object when we set to a value of(2)
         it clear the client cache of dynamic entries.
         ok(1) is returned when read."
    ::= { gslbOper 5 }

gslbOperDnsSec OBJECT IDENTIFIER ::= { gslbOper 6 }

gslbOperDnsSecTable OBJECT-TYPE
    SYNTAX  SEQUENCE OF GslbOperDnsSecEntry
    MAX-ACCESS  not-accessible
    STATUS  current
    DESCRIPTION
        "."
    ::= { gslbOperDnsSec 1 }

gslbOperDnsSecEntry OBJECT-TYPE
    SYNTAX  GslbOperDnsSecEntry
    MAX-ACCESS  not-accessible
    STATUS  current
    DESCRIPTION
        "."
    INDEX   { gslbOperDnsSecKeyID }
    ::= { gslbOperDnsSecTable 1 }

GslbOperDnsSecEntry ::= SEQUENCE {
    gslbOperDnsSecKeyID                 DisplayString,
    gslbOperDnsSecEmergencyRollover     INTEGER,
    gslbOperDnsSecImmediateRollover     INTEGER
    }

gslbOperDnsSecKeyID OBJECT-TYPE
    SYNTAX   DisplayString (SIZE(0..32))
    MAX-ACCESS  read-only
    STATUS  current
    DESCRIPTION
        "DNS Sec Table Key."
    ::= { gslbOperDnsSecEntry  1 }

gslbOperDnsSecEmergencyRollover OBJECT-TYPE
    SYNTAX  INTEGER {
        other(1),
        rollover(2)
        }
    MAX-ACCESS  read-write
    STATUS  current
    DESCRIPTION
        "By setting the value to rollover(2), DNSSEC emergency rollover procedure of a key will be Performed."
    ::= { gslbOperDnsSecEntry 2 }

gslbOperDnsSecImmediateRollover OBJECT-TYPE
    SYNTAX  INTEGER {
        other(1),
        rollover(2)
        }
    MAX-ACCESS  read-write
    STATUS  current
    DESCRIPTION
        "By setting the value to rollover(2), DNSSEC immediate rollover procedure of a key will be Performed."
    ::= { gslbOperDnsSecEntry 3 }


gslbOperQueryDomain OBJECT-TYPE
    SYNTAX  DisplayString
    MAX-ACCESS  read-write
    STATUS  current
    DESCRIPTION
        "Domain to query Global SLB selection."
    ::= { gslbOperQuery 1 }

gslbOperQuerySrcIp OBJECT-TYPE
    SYNTAX IpAddress
    MAX-ACCESS  read-write
    STATUS  current
    DESCRIPTION
        "Source Ip Address to query Global SLB selection."
    ::= { gslbOperQuery 2 }

gslbOperSendQuery OBJECT-TYPE
    SYNTAX  INTEGER {
    ok(1),
    query(2)
    }
    MAX-ACCESS  read-write
    STATUS  current
    DESCRIPTION
        "Query Global SLB selection.When set to a value of Query(2)
         it sends Global SLB selection query.Ok(1) is returned when
         this object is read."
    ::= { gslbOperQuery 3 }

gslbOperQuerySrcIpV6 OBJECT-TYPE
   SYNTAX DisplayString (SIZE(0..40))
    MAX-ACCESS  read-write
    STATUS  current
    DESCRIPTION
    "  Source Ip V6 Address to query Global SLB selection.
       Address should be 4-byte haxadecimal colon notation. Valid IPv6 address should be in
       any of the following forms xxxx:xxxx:xxxx:xxxx:xxxx:xxxx:xxxx:xxxx or xxxx::xxxx:xxxx:xxxx:xxxx or ::xxxx "
   ::= { gslbOperQuery 4 }

gslbOperQuerySrcIpVer OBJECT-TYPE
    SYNTAX  INTEGER{
        ipv4(1),
        ipv6(2)
        }
    MAX-ACCESS  read-only
    STATUS  current
    DESCRIPTION
        "Source Ip Version to query Global SLB selection."
    ::= { gslbOperQuery 5 }

gslbOperQueryType OBJECT-TYPE
    SYNTAX  INTEGER{
        a(1),
        aaaa(2)
        }
    MAX-ACCESS  read-write
    STATUS  current
    DESCRIPTION
        "Global SLB selection Query Type."
    ::= { gslbOperQuery 6 }

gslbOperAddDomain OBJECT-TYPE
    SYNTAX  DisplayString
    MAX-ACCESS  read-write
    STATUS  current
    DESCRIPTION
        "Domain to be added into Global SLB DNS Presistence cache."
    ::= { gslbOperAdd 1 }

gslbOperAddSrcIp OBJECT-TYPE
    SYNTAX IpAddress
    MAX-ACCESS  read-write
    STATUS  current
    DESCRIPTION
        "Source Ip Address to be added into Global SLB DNS
         Persistence cache."
    ::= { gslbOperAdd 2 }

gslbOperAddServerIp OBJECT-TYPE
    SYNTAX  IpAddress
    MAX-ACCESS  read-write
    STATUS  current
    DESCRIPTION
        "Server Ip Address to be added into Global SLB DNS
         Persistence cache."
    ::= { gslbOperAdd 3 }

gslbOperAddEntry OBJECT-TYPE
    SYNTAX  INTEGER {
        ok(1),
        add(2)
        }
    MAX-ACCESS  read-write
    STATUS  current
    DESCRIPTION
        "Add entry to Global SLB DNS persistence cache.
         When set to a value of add(2) Entry will be added into
         Global SLB DNS persistence cache.
         Ok(1) is returned when object is read."
    ::= { gslbOperAdd 4 }

gslbOperAddSrcIp6 OBJECT-TYPE
    SYNTAX   DisplayString (SIZE(0..40))
    MAX-ACCESS  read-write
    STATUS  current
    DESCRIPTION
        "Source Ip Address to be added into Global SLB DNS
         Persistence cache.
	 Address should be 4-byte haxadecimal colon notation.
         Valid IPv6 address should be in any of the following forms
           xxxx:xxxx:xxxx:xxxx:xxxx:xxxx:xxxx:xxxx or
           xxxx::xxxx:xxxx:xxxx:xxxx or ::xxxx"
    ::= { gslbOperAdd 5 }

gslbOperAddServerIp6 OBJECT-TYPE
    SYNTAX   DisplayString (SIZE(0..40))
    MAX-ACCESS  read-write
    STATUS  current
    DESCRIPTION
        "Server IPV6 Address to be added into Global SLB DNS
         Persistence cache.
	 Address should be 4-byte haxadecimal colon notation.
         Valid IPv6 address should be in any of the following forms
           xxxx:xxxx:xxxx:xxxx:xxxx:xxxx:xxxx:xxxx or
           xxxx::xxxx:xxxx:xxxx:xxxx or ::xxxx"
    ::= { gslbOperAdd 6 }

gslbOperAvPersisVirtNum OBJECT-TYPE
    SYNTAX  INTEGER (1..1024)
    MAX-ACCESS read-write
    STATUS  current
    DESCRIPTION
      "Enter Virtual Server Number for which GSLB
       availability persistence should be enabled/disabled."
    ::= { gslbOperAvPersis 1 }

gslbOperAvPersisState OBJECT-TYPE
    SYNTAX  INTEGER {
    enabled(1),
    disabled(2)
    }
    MAX-ACCESS  read-write
    STATUS  current
    DESCRIPTION
      "Enable or Disable GSLB availability persistence."
    ::= { gslbOperAvPersis 2 }

gslbOperAvpersistence OBJECT-TYPE
    SYNTAX  INTEGER {
    ok(1),
    config(2)
    }
    MAX-ACCESS  read-write
    STATUS  current
    DESCRIPTION
      "When we set to a value of 2(config),it enable/disable 
       GSLB availability persistence for configures virtual server.
       Ok(1) is returned when this object is read."
    ::= { gslbOperAvPersis 3 }


slbOperGroupRealServerTable OBJECT-TYPE
    SYNTAX  SEQUENCE OF SlbOperGroupRealServerEntry
    MAX-ACCESS  not-accessible
    STATUS  current
    DESCRIPTION
        "The table of real server per group."
    ::= { layer4Oper 5 }

slbOperGroupRealServerEntry OBJECT-TYPE
    SYNTAX  SlbOperGroupRealServerEntry
    MAX-ACCESS  not-accessible
    STATUS  current
    DESCRIPTION
        "A row in the Real server group table."
    INDEX   { slbOperRealServGroupIndex, slbOperGroupRealServIndex}
    ::= { slbOperGroupRealServerTable 1 }

SlbOperGroupRealServerEntry ::= SEQUENCE {
    slbOperRealServGroupIndex        Integer32,
    slbOperGroupRealServIndex        Integer32,
    slbOperGroupRealServerState      INTEGER
    }

slbOperRealServGroupIndex OBJECT-TYPE
    SYNTAX  Integer32
    MAX-ACCESS  read-only
    STATUS  current
    DESCRIPTION
        "The real server group index." 
    ::= { slbOperGroupRealServerEntry 1 }

slbOperGroupRealServIndex OBJECT-TYPE
    SYNTAX  Integer32
    MAX-ACCESS  read-only
    STATUS  current
    DESCRIPTION
        "The real server index." 
    ::= { slbOperGroupRealServerEntry 2 }

slbOperGroupRealServerState OBJECT-TYPE
    SYNTAX  INTEGER {
	enable(1),
	disable(2)
	}
    MAX-ACCESS  read-write
    STATUS  current
    DESCRIPTION
        "This an action object which is used to temporarily enable/disable a
         real server in group. The real server will be returned to its configured
         operational mode when the switch is reset."
    ::= { slbOperGroupRealServerEntry 3 }

slbOperSessionDel OBJECT IDENTIFIER ::= { layer4Oper 6 }

slbOperSessionDelSrcIp OBJECT-TYPE
    SYNTAX  IpAddress
    MAX-ACCESS  read-write
    STATUS  current
    DESCRIPTION
            "Session Source IP Address to be deleted"
    ::= { slbOperSessionDel 1}

slbOperSessionDelSrcPort OBJECT-TYPE
    SYNTAX  INTEGER (0..65534)
    MAX-ACCESS  read-write
    STATUS  current
    DESCRIPTION
            "Session Source Port to be deleted"
    ::= { slbOperSessionDel 2}

slbOperSessionDelDestIp OBJECT-TYPE
    SYNTAX  IpAddress
    MAX-ACCESS  read-write
    STATUS  current
    DESCRIPTION
            "Session Destination IP Address to be deleted"
    ::= { slbOperSessionDel 3 }
slbOperSessionDelDestPort OBJECT-TYPE
    SYNTAX  INTEGER (0..65534)
    MAX-ACCESS  read-write
    STATUS  current
    DESCRIPTION
            "Session Destination Port to be deleted"
    ::= { slbOperSessionDel 4 }

slbOperSessionDelTransType OBJECT-TYPE
    SYNTAX  INTEGER {
        tcp(1),
        udp(2)
        }
    MAX-ACCESS  read-write
    STATUS  current
    DESCRIPTION
             "Set a flag indicating whether Transport Type
              is TCP or UDP"
    ::= { slbOperSessionDel 5 }

slbOperSessionDelete OBJECT-TYPE
    SYNTAX  INTEGER {
        ok(1),
        delete(2)
        }
    MAX-ACCESS  read-write
    STATUS  current
    DESCRIPTION
        "This is an action object to delete session table entry.
         when set to a value of delete(2) it deletes session 
         table entry. Ok(1) is returned when object is read."
    ::= { slbOperSessionDel 6 }


slbOperHttpCachePurgeTable OBJECT-TYPE
    SYNTAX  SEQUENCE OF SlbOperHttpCachePurgeEntry
    MAX-ACCESS  not-accessible
    STATUS  current
    DESCRIPTION
        "The table of services per server."
    ::= {layer4Oper 7 }

slbOperHttpCachePurgeEntry OBJECT-TYPE
    SYNTAX SlbOperHttpCachePurgeEntry
    MAX-ACCESS  not-accessible
    STATUS  current
    DESCRIPTION
        "A row in the http cache purge service table."
    INDEX   { slbOperHttpCachePurgeServerIndex, slbOperHttpCachePurgeServiceIndex}
    ::= { slbOperHttpCachePurgeTable 1 }

SlbOperHttpCachePurgeEntry ::= SEQUENCE {
    slbOperHttpCachePurgeServerIndex   Integer32,
    slbOperHttpCachePurgeServiceIndex  Integer32,
    slbOperHttpCachePurgeURL           DisplayString 
    }

slbOperHttpCachePurgeServerIndex OBJECT-TYPE
    SYNTAX  Integer32 (1..1024)
    MAX-ACCESS  read-create
    STATUS  current
    DESCRIPTION
        "The Http Cache purge server index."
    ::= { slbOperHttpCachePurgeEntry 1 }

slbOperHttpCachePurgeServiceIndex OBJECT-TYPE
    SYNTAX  Integer32 (10..65534)
    MAX-ACCESS  read-create
    STATUS  current
    DESCRIPTION
        "The Http Cache purge service index."
    ::= { slbOperHttpCachePurgeEntry 2 }

slbOperHttpCachePurgeURL OBJECT-TYPE
    SYNTAX DisplayString 
    MAX-ACCESS  read-create
    STATUS  current
    DESCRIPTION
        "Set object URL or all."
    ::= { slbOperHttpCachePurgeEntry 3 }

ocspCachePurge OBJECT IDENTIFIER ::= { layer4Oper 8 }

slbOperOcspCachePurge OBJECT-TYPE
    SYNTAX DisplayString
    MAX-ACCESS  read-write
    STATUS  current
    DESCRIPTION
        "Client authentication policy id or All."
    ::= { ocspCachePurge 1 }

-- Server load balancing - Inbound Link Load Balancing Table

slbCurCfgLinklbState OBJECT-TYPE
    SYNTAX INTEGER {
        enabled(1),
        disabled(2)
        }
    MAX-ACCESS  read-only
    STATUS  current
    DESCRIPTION
        "Enable or disable Inbound Link load balancing. "
    ::= { linklbCfg 1 }

slbNewCfgLinklbState OBJECT-TYPE
    SYNTAX INTEGER {
        enabled(1),
        disabled(2)
        }
    MAX-ACCESS  read-write
    STATUS  current
    DESCRIPTION
        "Enable or disable Inbound Link load balancing. "
    ::= { linklbCfg 2 }

slbCurCfgLinklbRealGroup OBJECT-TYPE
    SYNTAX  Integer32  
    MAX-ACCESS  read-only
    STATUS  current
    DESCRIPTION
        "The real server group number for Link load balancing."
    ::= { linklbCfg 3 }

slbNewCfgLinklbRealGroup OBJECT-TYPE
    SYNTAX  Integer32  
    MAX-ACCESS  read-write
    STATUS  current
    DESCRIPTION
        "The real server group number for Link load balancing."
    ::= { linklbCfg 4 }

slbCurCfgLinklbTTL OBJECT-TYPE
    SYNTAX  INTEGER (0..65535) 
    MAX-ACCESS  read-only
    STATUS  current
    DESCRIPTION
        "Set Time to Live for DNS resource records."
    ::= { linklbCfg 6 }

slbNewCfgLinklbTTL OBJECT-TYPE
    SYNTAX  INTEGER (0..65535) 
    MAX-ACCESS  read-write
    STATUS  current
    DESCRIPTION
        "Set Time to Live for DNS resource records."
    ::= { linklbCfg 7 }

slbLinklbDrecord   OBJECT IDENTIFIER ::= { linklbCfg 5 }

slbDrecordTableMaxSize OBJECT-TYPE
    SYNTAX  Integer32 
    MAX-ACCESS  read-only 
    STATUS  current 
    DESCRIPTION 
        "The maximum number of entries in Drecord table."
    ::= { slbLinklbDrecord 1 }

slbCurCfgDrecordTable OBJECT-TYPE
    SYNTAX  SEQUENCE OF SlbCurCfgDrecordEntry
    MAX-ACCESS  not-accessible
    STATUS  current
    DESCRIPTION
        "The table of Domain records for Inbound link load balancing
         in the current configuration block."
    ::= { slbLinklbDrecord 2 }

slbCurCfgDrecordEntry OBJECT-TYPE
    SYNTAX  SlbCurCfgDrecordEntry
    MAX-ACCESS  not-accessible
    STATUS  current
    DESCRIPTION
        "A row in the Domain record table for Inbound Link Load
         balancing."
    INDEX   { slbCurCfgDrecordIndex }
    ::= { slbCurCfgDrecordTable 1 }

SlbCurCfgDrecordEntry ::= SEQUENCE {
    slbCurCfgDrecordIndex            INTEGER,
    slbCurCfgDomainRecordState       INTEGER,
    slbCurCfgDomainRecordName        DisplayString
    }

slbCurCfgDrecordIndex OBJECT-TYPE
    SYNTAX  INTEGER (1..64)
    MAX-ACCESS  read-only
    STATUS  current
    DESCRIPTION
        "The index of the Domain record table." 
    ::= { slbCurCfgDrecordEntry 1 }

slbCurCfgDomainRecordState OBJECT-TYPE
    SYNTAX  INTEGER {
	enabled(1),
	disabled(2)
	}
    MAX-ACCESS  read-only
    STATUS  current
    DESCRIPTION
        "Enable/disable a  domain record."
    ::= { slbCurCfgDrecordEntry 2 }

slbCurCfgDomainRecordName OBJECT-TYPE 
    SYNTAX  DisplayString (SIZE(0..34))
    MAX-ACCESS  read-only
    STATUS  current 
    DESCRIPTION 
        "The name of the domain record."  
    ::= { slbCurCfgDrecordEntry 3 }

slbNewCfgDrecordTable OBJECT-TYPE
    SYNTAX  SEQUENCE OF SlbNewCfgDrecordEntry
    MAX-ACCESS  not-accessible
    STATUS  current
    DESCRIPTION
        "The table of Domain records for Inbound link load balancing
         in the new configuration block."
    ::= { slbLinklbDrecord 3 }

slbNewCfgDrecordEntry OBJECT-TYPE
    SYNTAX  SlbNewCfgDrecordEntry
    MAX-ACCESS  not-accessible
    STATUS  current
    DESCRIPTION
        "A row in the Domain record table for Inbound Link Load
         balancing."
    INDEX   { slbNewCfgDrecordIndex }
    ::= { slbNewCfgDrecordTable 1 }

SlbNewCfgDrecordEntry ::= SEQUENCE {
    slbNewCfgDrecordIndex            INTEGER,
    slbNewCfgDomainRecordState       INTEGER,
    slbNewCfgDomainRecordName        DisplayString,
    slbNewCfgDrecordDelete           INTEGER 
    }

slbNewCfgDrecordIndex OBJECT-TYPE
    SYNTAX  INTEGER (1..64)
    MAX-ACCESS  read-only
    STATUS  current
    DESCRIPTION
        "The index of the Domain record table." 
    ::= { slbNewCfgDrecordEntry 1 }

slbNewCfgDomainRecordState OBJECT-TYPE
    SYNTAX  INTEGER {
	enabled(1),
	disabled(2)
	}
    MAX-ACCESS  read-create
    STATUS  current
    DESCRIPTION
        "Enable/disable a  domain record."
    ::= { slbNewCfgDrecordEntry 2 }

slbNewCfgDomainRecordName OBJECT-TYPE 
    SYNTAX  DisplayString (SIZE(0..34))
    MAX-ACCESS  read-create 
    STATUS  current 
    DESCRIPTION 
        "The name of the domain record."  
    ::= { slbNewCfgDrecordEntry 3 }

slbNewCfgDrecordDelete OBJECT-TYPE
    SYNTAX  INTEGER {
        other(1),
        delete(2)
        }
    MAX-ACCESS  read-create
    STATUS  current
    DESCRIPTION
        "By setting the value to delete(2), the entire row is deleted."
    ::= { slbNewCfgDrecordEntry 4 }

slbDrecordVirtRealMappingTableMaxSize OBJECT-TYPE
    SYNTAX  Integer32 
    MAX-ACCESS  read-only 
    STATUS  current 
    DESCRIPTION 
        "The maximum number of entries in Drecord Virtual Real server
         mapping Table." 
    ::= { slbLinklbDrecord 4 }

slbCurCfgDrecordVirtRealMappingTable OBJECT-TYPE
    SYNTAX  SEQUENCE OF SlbCurCfgDrecordVirtRealMappingEntry
    MAX-ACCESS  not-accessible
    STATUS  current
    DESCRIPTION
        "The table of Domain records and virtual server and real
         server mappings."
    ::= { slbLinklbDrecord 5 }

slbCurCfgDrecordVirtRealMappingEntry OBJECT-TYPE
    SYNTAX  SlbCurCfgDrecordVirtRealMappingEntry
    MAX-ACCESS  not-accessible
    STATUS  current
    DESCRIPTION
        "A row in the Domain record and virtual/real server mapping table
         for Inbound Link Load balancing."
    INDEX   { slbCurCfgDomainRecordIndex, slbCurCfgEntryIndex}
    ::= { slbCurCfgDrecordVirtRealMappingTable 1 }

SlbCurCfgDrecordVirtRealMappingEntry ::= SEQUENCE {
    slbCurCfgDomainRecordIndex            INTEGER,
    slbCurCfgEntryIndex                   INTEGER,
    slbCurCfgDrecordVirtServer            Integer32,
    slbCurCfgDrecordRealServer            Integer32,
    slbCurCfgDrecordEntryState            INTEGER
    }

slbCurCfgDomainRecordIndex OBJECT-TYPE
    SYNTAX  INTEGER (1..64)
    MAX-ACCESS  read-only
    STATUS  current
    DESCRIPTION
        "The number of the domain record." 
    ::= { slbCurCfgDrecordVirtRealMappingEntry 1 }

slbCurCfgEntryIndex OBJECT-TYPE
    SYNTAX  INTEGER (1..8)
    MAX-ACCESS  read-only
    STATUS  current
    DESCRIPTION
        "The number of the entry virtual real server mapping." 
    ::= { slbCurCfgDrecordVirtRealMappingEntry 2 }

slbCurCfgDrecordVirtServer OBJECT-TYPE
    SYNTAX  Integer32 
    MAX-ACCESS  read-only
    STATUS  current
    DESCRIPTION
        "The virtual server number."
    ::= { slbCurCfgDrecordVirtRealMappingEntry 3 }

slbCurCfgDrecordRealServer OBJECT-TYPE
    SYNTAX  Integer32 
    MAX-ACCESS  read-only
    STATUS  current
    DESCRIPTION
        "The Real server number."
    ::= { slbCurCfgDrecordVirtRealMappingEntry 4 }


slbCurCfgDrecordEntryState OBJECT-TYPE
    SYNTAX  INTEGER {
	enabled(1),
	disabled(2)
	}
    MAX-ACCESS  read-only
    STATUS  current
    DESCRIPTION
        "Enable/disable a mapping in this table."
    ::= { slbCurCfgDrecordVirtRealMappingEntry 5 }

slbNewCfgDrecordVirtRealMappingTable OBJECT-TYPE
    SYNTAX  SEQUENCE OF SlbNewCfgDrecordVirtRealMappingEntry
    MAX-ACCESS  not-accessible
    STATUS  current
    DESCRIPTION
        "The table of Domain records and virtual server and real
         server mappings."
    ::= { slbLinklbDrecord 6 }

slbNewCfgDrecordVirtRealMappingEntry OBJECT-TYPE
    SYNTAX  SlbNewCfgDrecordVirtRealMappingEntry
    MAX-ACCESS  not-accessible
    STATUS  current
    DESCRIPTION
        "A row in the Domain record and virtual/real server mapping table
         for Inbound Link Load balancing."
    INDEX   { slbNewCfgDomainRecordIndex, slbNewCfgEntryIndex }
    ::= { slbNewCfgDrecordVirtRealMappingTable 1 }

SlbNewCfgDrecordVirtRealMappingEntry ::= SEQUENCE {
    slbNewCfgDomainRecordIndex            INTEGER,
    slbNewCfgEntryIndex                   INTEGER,
    slbNewCfgDrecordVirtServer            Integer32,
    slbNewCfgDrecordRealServer            Integer32,
    slbNewCfgDrecordEntryState            INTEGER,
    slbNewCfgDrecordEntryDelete           INTEGER
    }

slbNewCfgDomainRecordIndex OBJECT-TYPE
    SYNTAX  INTEGER (1..64)
    MAX-ACCESS  read-only
    STATUS  current
    DESCRIPTION
        "The number of the domain record." 
    ::= { slbNewCfgDrecordVirtRealMappingEntry 1 }

slbNewCfgEntryIndex OBJECT-TYPE
    SYNTAX  INTEGER (1..8)
    MAX-ACCESS  read-only
    STATUS  current
    DESCRIPTION
        "The number of the virtual real server mapping." 
    ::= { slbNewCfgDrecordVirtRealMappingEntry 2 }

slbNewCfgDrecordVirtServer OBJECT-TYPE
    SYNTAX  Integer32 
    MAX-ACCESS  read-create
    STATUS  current
    DESCRIPTION
        "The virtual server number."
    ::= { slbNewCfgDrecordVirtRealMappingEntry 3 }

slbNewCfgDrecordRealServer OBJECT-TYPE
    SYNTAX  Integer32 
    MAX-ACCESS  read-create
    STATUS  current
    DESCRIPTION
        "The Real server number."
    ::= { slbNewCfgDrecordVirtRealMappingEntry 4 }

slbNewCfgDrecordEntryState OBJECT-TYPE
    SYNTAX  INTEGER {
	enabled(1),
	disabled(2)
	}
    MAX-ACCESS  read-create
    STATUS  current
    DESCRIPTION
        "Enable/disable a mapping in this table."
    ::= { slbNewCfgDrecordVirtRealMappingEntry 5 }

slbNewCfgDrecordEntryDelete OBJECT-TYPE
    SYNTAX  INTEGER {
        other(1),
        delete(2)
        }
    MAX-ACCESS  read-create
    STATUS  current
    DESCRIPTION
        "By setting the value to delete(2), the entire row is deleted."
    ::= { slbNewCfgDrecordVirtRealMappingEntry 6 }

slbCurSslCfgSSLAdminStatus OBJECT-TYPE
    SYNTAX  INTEGER {
        enabled(1),
        disabled(2)
        }
    MAX-ACCESS  read-only
    STATUS  current
    DESCRIPTION
        "Status (enable/disable) of SSL policy."
    ::= { sslCfg 1 }


slbCurSslCfgSSLPolTable OBJECT-TYPE
    SYNTAX  SEQUENCE OF SlbCurSslCfgSSLPolEntry
    MAX-ACCESS  not-accessible
    STATUS  current
    DESCRIPTION
        "The table for configuring ssl  policy."
    ::= { sslPol 5 }

slbCurSslCfgSSLPolEntry OBJECT-TYPE
    SYNTAX  SlbCurSslCfgSSLPolEntry
    MAX-ACCESS  not-accessible
    STATUS  current
    DESCRIPTION
        "A row in the ssl policy table."
    INDEX   { slbCurSslCfgSSLPolNameIdIndex }
    ::= { slbCurSslCfgSSLPolTable 1 }

SlbCurSslCfgSSLPolEntry ::= SEQUENCE {
    slbCurSslCfgSSLPolNameIdIndex             DisplayString,
    slbCurSslCfgSSLPolName                    DisplayString,
    slbCurSslCfgSSLPolPassInfoCipherName      DisplayString,
    slbCurSslCfgSSLPolPassInfoCipherFlag      INTEGER,
    slbCurSslCfgSSLPolPassInfoVersionName     DisplayString,
    slbCurSslCfgSSLPolPassInfoVersionFlag     INTEGER,
    slbCurSslCfgSSLPolPassInfoHeadBitsName    DisplayString,
    slbCurSslCfgSSLPolPassInfoHeadBitsFlag    INTEGER,
    slbCurSslCfgSSLPolPassInfoFrontend        INTEGER,
    slbCurSslCfgSSLPolCipherName              INTEGER,
    slbCurSslCfgSSLPolCipherUserdef           DisplayString,
    slbCurSslCfgSSLPolIntermcaChainName       DisplayString,
    slbCurSslCfgSSLPolIntermcaChainType       DisplayString,
    slbCurSslCfgSSLPolBecipher                INTEGER,
    slbCurSslCfgSSLPolAuthpol                 DisplayString,
    slbCurSslCfgSSLPolConvuri                 DisplayString,
    slbCurSslCfgSSLPolBessl                   INTEGER,
    slbCurSslCfgSSLPolConvert                 INTEGER,
    slbCurSslCfgSSLPolAdminStatus             INTEGER
    }
slbCurSslCfgSSLPolNameIdIndex OBJECT-TYPE
    SYNTAX   DisplayString
    MAX-ACCESS  read-only
    STATUS  current
    DESCRIPTION
        "The SSL policy name(key id) as an index."
    ::= {slbCurSslCfgSSLPolEntry  1 }

slbCurSslCfgSSLPolName  OBJECT-TYPE
    SYNTAX   DisplayString
    MAX-ACCESS  read-only
    STATUS  current
    DESCRIPTION
        "SSL policy name."
    ::= {slbCurSslCfgSSLPolEntry  2 }

slbCurSslCfgSSLPolPassInfoCipherName OBJECT-TYPE
    SYNTAX DisplayString 
    MAX-ACCESS  read-only
    STATUS  current
    DESCRIPTION
        "The SSL cipher-suite header name."
    ::= {slbCurSslCfgSSLPolEntry  3 }

slbCurSslCfgSSLPolPassInfoCipherFlag OBJECT-TYPE
    SYNTAX  INTEGER 
    MAX-ACCESS  read-only
    STATUS  current
    DESCRIPTION
        "SSL cipher-suite information to backend servers enabled."
    ::= {slbCurSslCfgSSLPolEntry  4 }

slbCurSslCfgSSLPolPassInfoVersionName OBJECT-TYPE
    SYNTAX  DisplayString
    MAX-ACCESS  read-only
    STATUS  current
    DESCRIPTION
        "SSL version header name."
    ::= {slbCurSslCfgSSLPolEntry  5 }

slbCurSslCfgSSLPolPassInfoVersionFlag OBJECT-TYPE
    SYNTAX   INTEGER
    MAX-ACCESS  read-only
    STATUS  current
    DESCRIPTION
        "SSL version information to backend servers enabled."
    ::= {slbCurSslCfgSSLPolEntry  6 }

slbCurSslCfgSSLPolPassInfoHeadBitsName OBJECT-TYPE
    SYNTAX   DisplayString
    MAX-ACCESS  read-only
    STATUS  current
    DESCRIPTION
        "The passive cipher bits information to backend server."
    ::= {slbCurSslCfgSSLPolEntry  7 }


slbCurSslCfgSSLPolPassInfoHeadBitsFlag OBJECT-TYPE
    SYNTAX   INTEGER
    MAX-ACCESS  read-only
    STATUS  current
    DESCRIPTION
        "Cipher bits information to backend servers enabled."
    ::= {slbCurSslCfgSSLPolEntry  8 }


slbCurSslCfgSSLPolPassInfoFrontend OBJECT-TYPE
    SYNTAX   INTEGER
    MAX-ACCESS  read-only
    STATUS  current
    DESCRIPTION
        "Enable/Disable add Front-End-Https: on header."
    ::= {slbCurSslCfgSSLPolEntry  9 }

slbCurSslCfgSSLPolCipherName  OBJECT-TYPE
    SYNTAX  INTEGER 
    MAX-ACCESS  read-only
    STATUS  current
    DESCRIPTION
        "Cipher name for SSL."
    ::= {slbCurSslCfgSSLPolEntry  10 }

slbCurSslCfgSSLPolCipherUserdef  OBJECT-TYPE
    SYNTAX  DisplayString
    MAX-ACCESS  read-only
    STATUS  current
    DESCRIPTION
        "Cipher-suite allowed for SSL."
    ::= {slbCurSslCfgSSLPolEntry  11 }


slbCurSslCfgSSLPolIntermcaChainName  OBJECT-TYPE
    SYNTAX   DisplayString
    MAX-ACCESS  read-only
    STATUS  current
    DESCRIPTION
        "Intermediate CA certificate chain name."
    ::= {slbCurSslCfgSSLPolEntry  12 }

slbCurSslCfgSSLPolIntermcaChainType  OBJECT-TYPE
    SYNTAX   DisplayString
    MAX-ACCESS  read-only
    STATUS  current
    DESCRIPTION
        "Intermediate CA certificate chain type certificate=cert,Group=group,None=<empty string>."
    ::= {slbCurSslCfgSSLPolEntry  13 }

slbCurSslCfgSSLPolBecipher  OBJECT-TYPE
    SYNTAX  INTEGER{
        low(0),
        medium(1),
        high(2)
        }
    MAX-ACCESS  read-only
    STATUS  current
    DESCRIPTION
        "Allowed cipher-suites in backend SSL [0-low, 1-midium, 2-high] ."
    ::= {slbCurSslCfgSSLPolEntry  14 }

slbCurSslCfgSSLPolAuthpol  OBJECT-TYPE
    SYNTAX   DisplayString
    MAX-ACCESS  read-only
    STATUS  current
    DESCRIPTION
        "Client authentication policy."
    ::= {slbCurSslCfgSSLPolEntry  15 }

slbCurSslCfgSSLPolConvuri  OBJECT-TYPE
    SYNTAX   DisplayString
    MAX-ACCESS  read-only
    STATUS  current
    DESCRIPTION
        "Host regex for HTTP redirection conversion."
    ::= {slbCurSslCfgSSLPolEntry  16 }

slbCurSslCfgSSLPolBessl  OBJECT-TYPE
    SYNTAX  INTEGER{
        enabled(1),
        disabled(2)
        }
    MAX-ACCESS  read-only
    STATUS  current
    DESCRIPTION
        "Enable/Disable backend SSL encryption."
    ::= {slbCurSslCfgSSLPolEntry  17 }

slbCurSslCfgSSLPolConvert  OBJECT-TYPE
    SYNTAX  INTEGER {
        enabled(1),
        disabled(2)
        }
    MAX-ACCESS  read-only
    STATUS  current
    DESCRIPTION
        "Enable/Disable HTTP redirection conversion."
    ::= {slbCurSslCfgSSLPolEntry  18 }

slbCurSslCfgSSLPolAdminStatus OBJECT-TYPE
    SYNTAX  INTEGER {
        enabled(1),
        disabled(2)
        }
    MAX-ACCESS  read-only
    STATUS  current
    DESCRIPTION
        "Enable or disable ssl policy."
    ::= {slbCurSslCfgSSLPolEntry 19 }



slbNewSslCfgSSLAdminStatus OBJECT-TYPE
    SYNTAX  INTEGER {
        enabled(1),
        disabled(2)
        }
    MAX-ACCESS  read-create
    STATUS  current
    DESCRIPTION
        "Status (enable/disable) of SSL policy."
    ::= { sslCfg 2 }


slbNewSslCfgSSLPolTable OBJECT-TYPE
    SYNTAX  SEQUENCE OF SlbNewSslCfgSSLPolEntry
    MAX-ACCESS  not-accessible
    STATUS  current
    DESCRIPTION
        "The table for configuring ssl  policy."
    ::= { sslPol 7 }

slbNewSslCfgSSLPolEntry OBJECT-TYPE
    SYNTAX  SlbNewSslCfgSSLPolEntry
    MAX-ACCESS  not-accessible
    STATUS  current
    DESCRIPTION
        "A row in the ssl policy table."
    INDEX   { slbNewSslCfgSSLPolNameIdIndex }
    ::= { slbNewSslCfgSSLPolTable 1 }

SlbNewSslCfgSSLPolEntry ::= SEQUENCE {
    slbNewSslCfgSSLPolNameIdIndex             DisplayString,
    slbNewSslCfgSSLPolName                    DisplayString,
    slbNewSslCfgSSLPolPassInfoCipherName      DisplayString,
    slbNewSslCfgSSLPolPassInfoCipherFlag      INTEGER,
    slbNewSslCfgSSLPolPassInfoVersionName     DisplayString,
    slbNewSslCfgSSLPolPassInfoVersionFlag     INTEGER,
    slbNewSslCfgSSLPolPassInfoHeadBitsName    DisplayString,
    slbNewSslCfgSSLPolPassInfoHeadBitsFlag    INTEGER,
    slbNewSslCfgSSLPolPassInfoFrontend        INTEGER,
    slbNewSslCfgSSLPolCipherName              INTEGER,
    slbNewSslCfgSSLPolCipherUserdef           DisplayString,
    slbNewSslCfgSSLPolIntermcaChainName       DisplayString,
    slbNewSslCfgSSLPolIntermcaChainType       DisplayString,
    slbNewSslCfgSSLPolBecipher                INTEGER,
    slbNewSslCfgSSLPolAuthpol                 DisplayString,
    slbNewSslCfgSSLPolConvuri                 DisplayString,
    slbNewSslCfgSSLPolBessl                   INTEGER,
    slbNewSslCfgSSLPolConvert                 INTEGER,
    slbNewSslCfgSSLPolAdminStatus             INTEGER,
    slbNewSslCfgSSLPolDel                     INTEGER
    }

slbNewSslCfgSSLPolNameIdIndex OBJECT-TYPE
    SYNTAX   DisplayString
    MAX-ACCESS  read-create
    STATUS  current
    DESCRIPTION
        "The SSL policy name(key id) as an index."
    ::= {slbNewSslCfgSSLPolEntry  1 }

slbNewSslCfgSSLPolName  OBJECT-TYPE
    SYNTAX   DisplayString
    MAX-ACCESS  read-create
    STATUS  current
    DESCRIPTION
        "SSL policy name,length of the string should be 32 charecters."
    ::= {slbNewSslCfgSSLPolEntry  2 }


slbNewSslCfgSSLPolPassInfoCipherName OBJECT-TYPE
    SYNTAX  DisplayString 
    MAX-ACCESS  read-create
    STATUS  current
    DESCRIPTION
        "The SSL cipher-suite header name."
    ::= {slbNewSslCfgSSLPolEntry  3 }

slbNewSslCfgSSLPolPassInfoCipherFlag OBJECT-TYPE
    SYNTAX  INTEGER {
        enabled(1),
        disabled(2)
        }
    MAX-ACCESS  read-create
    STATUS  current
    DESCRIPTION
        "Enable/Disable cipher-suite information to backend servers."
    ::= {slbNewSslCfgSSLPolEntry  4 }

slbNewSslCfgSSLPolPassInfoVersionName OBJECT-TYPE
    SYNTAX  DisplayString
    MAX-ACCESS  read-create
    STATUS  current
    DESCRIPTION
        "SSL version header name."
    ::= {slbNewSslCfgSSLPolEntry  5 }

slbNewSslCfgSSLPolPassInfoVersionFlag OBJECT-TYPE
    SYNTAX  INTEGER {
        enabled(1),
        disabled(2)
        }
    MAX-ACCESS  read-create
    STATUS  current
    DESCRIPTION
        "Enable/Disable  SSL version information to backend servers."
    ::= {slbNewSslCfgSSLPolEntry  6 }


slbNewSslCfgSSLPolPassInfoHeadBitsName OBJECT-TYPE
    SYNTAX  DisplayString 
    MAX-ACCESS  read-create
    STATUS  current
    DESCRIPTION
        "The passive cipher bits information to backend server."
    ::= {slbNewSslCfgSSLPolEntry  7 }


slbNewSslCfgSSLPolPassInfoHeadBitsFlag OBJECT-TYPE
    SYNTAX  INTEGER {
        enabled(1),
        disabled(2)
        }
    MAX-ACCESS  read-create
    STATUS  current
    DESCRIPTION
        "Enable/Disable Cipher bits information to backend servers."
    ::= {slbNewSslCfgSSLPolEntry  8 }


slbNewSslCfgSSLPolPassInfoFrontend OBJECT-TYPE
    SYNTAX  INTEGER {
        enabled(1),
        disabled(2)
        }
    MAX-ACCESS  read-create
    STATUS  current
    DESCRIPTION
        "Enable/Disable add Front-End-Https: on header."
    ::= {slbNewSslCfgSSLPolEntry 9 }


slbNewSslCfgSSLPolCipherName  OBJECT-TYPE
    SYNTAX  INTEGER 
    MAX-ACCESS  read-create
    STATUS  current
    DESCRIPTION
        "Cipher name for SSL."
    ::= {slbNewSslCfgSSLPolEntry  10 }

slbNewSslCfgSSLPolCipherUserdef  OBJECT-TYPE
    SYNTAX  DisplayString
    MAX-ACCESS  read-create
    STATUS  current
    DESCRIPTION
        "Cipher-suite allowed for SSL."
    ::= {slbNewSslCfgSSLPolEntry  11 }


slbNewSslCfgSSLPolIntermcaChainName  OBJECT-TYPE
    SYNTAX   DisplayString
    MAX-ACCESS  read-create
    STATUS  current
    DESCRIPTION
        "Intermediate CA certificate chain name."
    ::= {slbNewSslCfgSSLPolEntry  12 }

slbNewSslCfgSSLPolIntermcaChainType  OBJECT-TYPE
    SYNTAX   DisplayString
    MAX-ACCESS  read-create
    STATUS  current
    DESCRIPTION
        "Intermediate CA certificate chain type certificate=cert,Group=group,None=<empty string>."
    ::= {slbNewSslCfgSSLPolEntry  13 }


slbNewSslCfgSSLPolBecipher  OBJECT-TYPE
    SYNTAX INTEGER{
        low(0),
        medium(1),
        high(2)
        }
    MAX-ACCESS  read-create
    STATUS  current
    DESCRIPTION
        "Allowed cipher-suites in backend SSL [0-low, 1-midium, 2-high]."
    ::= {slbNewSslCfgSSLPolEntry  14 }

slbNewSslCfgSSLPolAuthpol  OBJECT-TYPE
    SYNTAX   DisplayString
    MAX-ACCESS  read-create
    STATUS  current
    DESCRIPTION
        "Client authentication policy."
    ::= {slbNewSslCfgSSLPolEntry  15 }

slbNewSslCfgSSLPolConvuri  OBJECT-TYPE
    SYNTAX   DisplayString
    MAX-ACCESS  read-create
    STATUS  current
    DESCRIPTION
        "Host regex for HTTP redirection conversion."
    ::= {slbNewSslCfgSSLPolEntry  16 }

slbNewSslCfgSSLPolBessl  OBJECT-TYPE
    SYNTAX  INTEGER{
        enabled(1),
        disabled(2)
        }
    MAX-ACCESS  read-create
    STATUS  current
    DESCRIPTION
        "Enable/Disable backend SSL encryption."
    ::= {slbNewSslCfgSSLPolEntry  17 }

slbNewSslCfgSSLPolConvert  OBJECT-TYPE
    SYNTAX  INTEGER{
        enabled(1),
        disabled(2)
        }
    MAX-ACCESS  read-create
    STATUS  current
    DESCRIPTION
        "Enable/Disable HTTP redirection conversion."
    ::= {slbNewSslCfgSSLPolEntry  18 }

slbNewSslCfgSSLPolAdminStatus OBJECT-TYPE
    SYNTAX  INTEGER {
        enabled(1),
        disabled(2)
        }
    MAX-ACCESS  read-create
    STATUS  current
    DESCRIPTION
        "Enable or disable ssl policy."
    ::= {slbNewSslCfgSSLPolEntry 19 }

slbNewSslCfgSSLPolDel  OBJECT-TYPE
    SYNTAX  INTEGER {
        other(1),
        delete(2)
    }
    MAX-ACCESS  read-create
    STATUS  current
    DESCRIPTION
        "Delete SSL policy."
    ::= {slbNewSslCfgSSLPolEntry  20 }




slbCurSslCfgAuthPolTable OBJECT-TYPE
    SYNTAX  SEQUENCE OF SlbCurSslCfgAuthPolEntry
    MAX-ACCESS  not-accessible
    STATUS  current
    DESCRIPTION
        "The table for configuring Client Authentication  policy."
    ::= { authPol 1 }

slbCurSslCfgAuthPolEntry OBJECT-TYPE
    SYNTAX  SlbCurSslCfgAuthPolEntry
    MAX-ACCESS  not-accessible
    STATUS  current
    DESCRIPTION
        "A row in the Client Authentication policy table."
    INDEX   { slbCurSslCfgAuthPolNameIdIndex }
    ::= { slbCurSslCfgAuthPolTable 1 }

SlbCurSslCfgAuthPolEntry ::= SEQUENCE {
    slbCurSslCfgAuthPolNameIdIndex           DisplayString,
    slbCurSslCfgAuthPolName                  DisplayString,
    slbCurSslCfgAuthPolValidityMethod        INTEGER,
    slbCurSslCfgAuthPolValidityStaturi       DisplayString,
    slbCurSslCfgAuthPolValidityUriprior      INTEGER,
    slbCurSslCfgAuthPolValidityCachtime      INTEGER,
    slbCurSslCfgAuthPolValidityTimedev       INTEGER,
    slbCurSslCfgAuthPolValidityAlgorthmName  DisplayString,
    slbCurSslCfgAuthPolValidityVchain        INTEGER,
    slbCurSslCfgAuthPolValiditySecure        INTEGER,
    slbCurSslCfgAuthPolPassinfoVersionName   DisplayString,
    slbCurSslCfgAuthPolPassinfoVersionFlag   INTEGER,
    slbCurSslCfgAuthPolPassinfoSerialName    DisplayString,
    slbCurSslCfgAuthPolPassinfoSerialFlag    INTEGER,
    slbCurSslCfgAuthPolPassinfoAlgoName      DisplayString,
    slbCurSslCfgAuthPolPassinfoAlgoFlag      INTEGER,
    slbCurSslCfgAuthPolPassinfoIssuerName    DisplayString,
    slbCurSslCfgAuthPolPassinfoIssuerFlag    INTEGER,
    slbCurSslCfgAuthPolPassinfoNbeforeName   DisplayString,
    slbCurSslCfgAuthPolPassinfoNbeforeFlag   INTEGER,
    slbCurSslCfgAuthPolPassinfoNafterName    DisplayString,
    slbCurSslCfgAuthPolPassinfoNafterFlag    INTEGER,
    slbCurSslCfgAuthPolPassinfoSubjectName   DisplayString,
    slbCurSslCfgAuthPolPassinfoSubjectFlag   INTEGER,
    slbCurSslCfgAuthPolPassinfoKeytypeName   DisplayString,
    slbCurSslCfgAuthPolPassinfoKeytypeFlag   INTEGER,
    slbCurSslCfgAuthPolPassinfoMd5Name       DisplayString,
    slbCurSslCfgAuthPolPassinfoMd5Flag       INTEGER,
    slbCurSslCfgAuthPolPassinfoCertName      DisplayString,
    slbCurSslCfgAuthPolPassinfoCertFormat    INTEGER,
    slbCurSslCfgAuthPolPassinfoCertFlag      INTEGER,
    slbCurSslCfgAuthPolPassinfoCharset       INTEGER,
    slbCurSslCfgAuthPolTrustcaChainName      DisplayString,
    slbCurSslCfgAuthPolTrustcaChainType      DisplayString,
    slbCurSslCfgAuthPolCadepth               INTEGER,
    slbCurSslCfgAuthPolCaverify              INTEGER,
    slbCurSslCfgAuthPolFailurl               DisplayString,
    slbCurSslCfgAuthPolAdminStatus           INTEGER,
    slbCurSslCfgAuthPolPassinfoComp2424      INTEGER
    }

slbCurSslCfgAuthPolNameIdIndex  OBJECT-TYPE
    SYNTAX   DisplayString
    MAX-ACCESS  read-only
    STATUS  current
    DESCRIPTION
        "The Auth policy name(key id) as an index."
    ::= {slbCurSslCfgAuthPolEntry  1 }


slbCurSslCfgAuthPolName  OBJECT-TYPE
    SYNTAX   DisplayString
    MAX-ACCESS  read-only
    STATUS  current
    DESCRIPTION
        "Auth policy name."
    ::= {slbCurSslCfgAuthPolEntry  2 }

slbCurSslCfgAuthPolValidityMethod OBJECT-TYPE
    SYNTAX  INTEGER 
    MAX-ACCESS  read-only
    STATUS  current
    DESCRIPTION
        "Certificate validation check method."
    ::= {slbCurSslCfgAuthPolEntry  3 }

slbCurSslCfgAuthPolValidityStaturi OBJECT-TYPE
    SYNTAX   DisplayString
    MAX-ACCESS  read-only
    STATUS  current
    DESCRIPTION
        "Static URI for OCSP validation requests."
    ::= {slbCurSslCfgAuthPolEntry  4 }

slbCurSslCfgAuthPolValidityUriprior OBJECT-TYPE
    SYNTAX  INTEGER {
        clientcert(1),
        staticuri(2)
        }
    MAX-ACCESS  read-only
    STATUS  current
    DESCRIPTION
        "OCSP URI priority."
    ::= {slbCurSslCfgAuthPolEntry  5 }

slbCurSslCfgAuthPolValidityCachtime OBJECT-TYPE
    SYNTAX  INTEGER
    MAX-ACCESS  read-only
    STATUS  current
    DESCRIPTION
        "OCSP response cache time."
    ::= {slbCurSslCfgAuthPolEntry  6 }

slbCurSslCfgAuthPolValidityTimedev OBJECT-TYPE
    SYNTAX INTEGER
    MAX-ACCESS  read-only
    STATUS  current
    DESCRIPTION
        "OCSP response time deviation."
    ::= {slbCurSslCfgAuthPolEntry  7 }

slbCurSslCfgAuthPolValidityAlgorthmName OBJECT-TYPE
    SYNTAX   DisplayString
    MAX-ACCESS  read-only
    STATUS  current
    DESCRIPTION
        "Allowed signing algorithm for the OCSP response[all, md5, sha1, sha256, sha384, sha512]."
    ::= {slbCurSslCfgAuthPolEntry  8 }


slbCurSslCfgAuthPolValidityVchain OBJECT-TYPE
    SYNTAX  INTEGER {
        enabled(1),
        disabled(2)
        }
    MAX-ACCESS  read-only
    STATUS  current
    DESCRIPTION
        "Enable/Disable validating every CA certificate in the CA chain u."
    ::= {slbCurSslCfgAuthPolEntry  9 }

slbCurSslCfgAuthPolValiditySecure OBJECT-TYPE
    SYNTAX  INTEGER {
        enabled(1),
        disabled(2)
        }
    MAX-ACCESS  read-only
    STATUS  current
    DESCRIPTION
        "Enable/Disable secure OCSP response by sending random nonce with."
    ::= {slbCurSslCfgAuthPolEntry  10 }

slbCurSslCfgAuthPolPassinfoVersionName OBJECT-TYPE
    SYNTAX   DisplayString
    MAX-ACCESS  read-only
    STATUS  current
    DESCRIPTION
        "Certificate version header."
    ::= {slbCurSslCfgAuthPolEntry  11 }

slbCurSslCfgAuthPolPassinfoVersionFlag OBJECT-TYPE
    SYNTAX  INTEGER
    MAX-ACCESS  read-only
    STATUS  current
    DESCRIPTION
        "Pass certificate version information to backend server?."
    ::= {slbCurSslCfgAuthPolEntry  12 }

slbCurSslCfgAuthPolPassinfoSerialName OBJECT-TYPE
    SYNTAX   DisplayString
    MAX-ACCESS  read-only
    STATUS  current
    DESCRIPTION
        "Certificate serial-number header ."
    ::= {slbCurSslCfgAuthPolEntry  13 }

slbCurSslCfgAuthPolPassinfoSerialFlag OBJECT-TYPE
    SYNTAX  INTEGER 
    MAX-ACCESS  read-only
    STATUS  current
    DESCRIPTION
        "Pass certificate serial-number to backend server?."
    ::= {slbCurSslCfgAuthPolEntry  14 }

slbCurSslCfgAuthPolPassinfoAlgoName OBJECT-TYPE
    SYNTAX   DisplayString
    MAX-ACCESS  read-only
    STATUS  current
    DESCRIPTION
        "Certificate signature algorithm header name."
    ::= {slbCurSslCfgAuthPolEntry  15 }

slbCurSslCfgAuthPolPassinfoAlgoFlag OBJECT-TYPE
    SYNTAX  INTEGER 
    MAX-ACCESS  read-only
    STATUS  current
    DESCRIPTION
        "Pass certificate Signature Algorithm to backend server?"
    ::= {slbCurSslCfgAuthPolEntry  16 }

slbCurSslCfgAuthPolPassinfoIssuerName OBJECT-TYPE
    SYNTAX   DisplayString
    MAX-ACCESS  read-only
    STATUS  current
    DESCRIPTION
        "Certificate issuer header."
    ::= {slbCurSslCfgAuthPolEntry  17 }

slbCurSslCfgAuthPolPassinfoIssuerFlag OBJECT-TYPE
    SYNTAX  INTEGER 
    MAX-ACCESS  read-only
    STATUS  current
    DESCRIPTION
        "Pass certificate issuer information to backend server?"
    ::= {slbCurSslCfgAuthPolEntry  18 }

slbCurSslCfgAuthPolPassinfoNbeforeName OBJECT-TYPE
    SYNTAX   DisplayString
    MAX-ACCESS  read-only
    STATUS  current
    DESCRIPTION
        "Certificate 'Not Before Validity Dates' header."
    ::= {slbCurSslCfgAuthPolEntry  19 }

slbCurSslCfgAuthPolPassinfoNbeforeFlag OBJECT-TYPE
    SYNTAX  INTEGER 
    MAX-ACCESS  read-only
    STATUS  current
    DESCRIPTION
        "Pass certificate 'Not Before' Validity Date to backend serverr?"
    ::= {slbCurSslCfgAuthPolEntry  20 }

slbCurSslCfgAuthPolPassinfoNafterName OBJECT-TYPE
    SYNTAX DisplayString
    MAX-ACCESS  read-only
    STATUS  current
    DESCRIPTION
        "Certificate 'Not After Validity Dates' header."
    ::= {slbCurSslCfgAuthPolEntry  21 }

slbCurSslCfgAuthPolPassinfoNafterFlag OBJECT-TYPE
    SYNTAX  INTEGER 
    MAX-ACCESS  read-only
    STATUS  current
    DESCRIPTION
        "Pass certificate 'Not After' Validity Date to backend server?"
    ::= {slbCurSslCfgAuthPolEntry  22 }

slbCurSslCfgAuthPolPassinfoSubjectName OBJECT-TYPE
    SYNTAX   DisplayString
    MAX-ACCESS  read-only
    STATUS  current
    DESCRIPTION
        "Certificate subject header name."
    ::= {slbCurSslCfgAuthPolEntry  23 }

slbCurSslCfgAuthPolPassinfoSubjectFlag OBJECT-TYPE
    SYNTAX  INTEGER
    MAX-ACCESS  read-only
    STATUS  current
    DESCRIPTION
        "Pass certificate subject to backend server?"
    ::= {slbCurSslCfgAuthPolEntry  24 }

slbCurSslCfgAuthPolPassinfoKeytypeName OBJECT-TYPE
    SYNTAX   DisplayString
    MAX-ACCESS  read-only
    STATUS  current
    DESCRIPTION
        "Certificate Public Key Type header."
    ::= {slbCurSslCfgAuthPolEntry  25 }

slbCurSslCfgAuthPolPassinfoKeytypeFlag OBJECT-TYPE
    SYNTAX  INTEGER 
    MAX-ACCESS  read-only
    STATUS  current
    DESCRIPTION
        "Pass certificate Public Key Type information to backend servers?"
    ::= {slbCurSslCfgAuthPolEntry  26 }

slbCurSslCfgAuthPolPassinfoMd5Name OBJECT-TYPE
    SYNTAX   DisplayString
    MAX-ACCESS  read-only
    STATUS  current
    DESCRIPTION
        "Certificate MD5 Hash header."
    ::= {slbCurSslCfgAuthPolEntry  27 }

slbCurSslCfgAuthPolPassinfoMd5Flag OBJECT-TYPE
    SYNTAX  INTEGER 
    MAX-ACCESS  read-only
    STATUS  current
    DESCRIPTION
        "Pass certificate MD5 Hash information to backend servers?"
    ::= {slbCurSslCfgAuthPolEntry  28 }

slbCurSslCfgAuthPolPassinfoCertName OBJECT-TYPE
    SYNTAX   DisplayString
    MAX-ACCESS  read-only
    STATUS  current
    DESCRIPTION
        "Certificate header."
    ::= {slbCurSslCfgAuthPolEntry  29 }

slbCurSslCfgAuthPolPassinfoCertFormat OBJECT-TYPE
    SYNTAX  INTEGER 
    MAX-ACCESS  read-only
    STATUS  current
    DESCRIPTION
        "Certificate Header Lines Format."
    ::= {slbCurSslCfgAuthPolEntry  30 }

slbCurSslCfgAuthPolPassinfoCertFlag OBJECT-TYPE
    SYNTAX  INTEGER
    MAX-ACCESS  read-only
    STATUS  current
    DESCRIPTION
        "Pass certificate information to backend servers?"
    ::= {slbCurSslCfgAuthPolEntry  31 }

slbCurSslCfgAuthPolPassinfoCharset OBJECT-TYPE
    SYNTAX  INTEGER  
    MAX-ACCESS  read-only
    STATUS  current
    DESCRIPTION
        "Set the character set to be used for information."
    ::= {slbCurSslCfgAuthPolEntry  32 }

slbCurSslCfgAuthPolTrustcaChainName OBJECT-TYPE
    SYNTAX   DisplayString
    MAX-ACCESS  read-only
    STATUS  current
    DESCRIPTION
        "Trusted client's CA certificate."
    ::= {slbCurSslCfgAuthPolEntry  33 }

slbCurSslCfgAuthPolTrustcaChainType OBJECT-TYPE
    SYNTAX   DisplayString
    MAX-ACCESS  read-only
    STATUS  current
    DESCRIPTION
        "Tusted client's CA certificate type certificate=cert,Group=group,None=<empty string>."
    ::= {slbCurSslCfgAuthPolEntry  34 }

slbCurSslCfgAuthPolCadepth OBJECT-TYPE
    SYNTAX  INTEGER
    MAX-ACCESS  read-only
    STATUS  current
    DESCRIPTION
        "Maximum depth to search the trusted CA in the CA certificate."
    ::= {slbCurSslCfgAuthPolEntry  35 }

slbCurSslCfgAuthPolCaverify OBJECT-TYPE
    SYNTAX  INTEGER
    MAX-ACCESS  read-only
    STATUS  current
    DESCRIPTION
        "Certificate's CA verification level."
    ::= {slbCurSslCfgAuthPolEntry  36 }

slbCurSslCfgAuthPolFailurl OBJECT-TYPE
    SYNTAX   DisplayString
    MAX-ACCESS  read-only
    STATUS  current
    DESCRIPTION
        "URL for redirection when client authentication fails"
    ::= {slbCurSslCfgAuthPolEntry  37 }

slbCurSslCfgAuthPolAdminStatus  OBJECT-TYPE
    SYNTAX  INTEGER {
        enabled(1),
        disabled(2)
        }
    MAX-ACCESS  read-only
    STATUS  current
    DESCRIPTION
        "Enable or disable Auth policy."
    ::= {slbCurSslCfgAuthPolEntry  38}

slbCurSslCfgAuthPolPassinfoComp2424 OBJECT-TYPE
    SYNTAX  INTEGER{
        enabled(1),
        disabled(2)
        }
    MAX-ACCESS  read-only
    STATUS  current
    DESCRIPTION
        "Enable/Disable the 2424SSL Headers Compliance Mode."
    ::= {slbCurSslCfgAuthPolEntry  39 }

slbNewSslCfgAuthPolTable OBJECT-TYPE
    SYNTAX  SEQUENCE OF SlbNewSslCfgAuthPolEntry
    MAX-ACCESS  not-accessible
    STATUS  current
    DESCRIPTION
        "The table for configuring Client Authentication  policy."
    ::= { authPol 3 }

slbNewSslCfgAuthPolEntry OBJECT-TYPE
    SYNTAX  SlbNewSslCfgAuthPolEntry 
    MAX-ACCESS  not-accessible
    STATUS  current
    DESCRIPTION
        "A row in the Client Authentication policy table."
    INDEX   { slbNewSslCfgAuthPolNameIdIndex }
    ::= { slbNewSslCfgAuthPolTable 1 }

SlbNewSslCfgAuthPolEntry ::= SEQUENCE {
    slbNewSslCfgAuthPolNameIdIndex           DisplayString,
    slbNewSslCfgAuthPolName                  DisplayString,
    slbNewSslCfgAuthPolValidityMethod        INTEGER,
    slbNewSslCfgAuthPolValidityStaturi       DisplayString,
    slbNewSslCfgAuthPolValidityUriprior      INTEGER,
    slbNewSslCfgAuthPolValidityCachtime      INTEGER,
    slbNewSslCfgAuthPolValidityTimedev       INTEGER,
    slbNewSslCfgAuthPolValidityAlgorthmName  DisplayString,
    slbNewSslCfgAuthPolValidityVchain        INTEGER,
    slbNewSslCfgAuthPolValiditySecure        INTEGER,
    slbNewSslCfgAuthPolPassinfoVersionName   DisplayString,
    slbNewSslCfgAuthPolPassinfoVersionFlag   INTEGER,
    slbNewSslCfgAuthPolPassinfoSerialName    DisplayString,
    slbNewSslCfgAuthPolPassinfoSerialFlag    INTEGER,
    slbNewSslCfgAuthPolPassinfoAlgoName      DisplayString,
    slbNewSslCfgAuthPolPassinfoAlgoFlag      INTEGER,
    slbNewSslCfgAuthPolPassinfoIssuerName    DisplayString,
    slbNewSslCfgAuthPolPassinfoIssuerFlag    INTEGER,
    slbNewSslCfgAuthPolPassinfoNbeforeName   DisplayString,
    slbNewSslCfgAuthPolPassinfoNbeforeFlag   INTEGER,
    slbNewSslCfgAuthPolPassinfoNafterName    DisplayString,
    slbNewSslCfgAuthPolPassinfoNafterFlag    INTEGER,
    slbNewSslCfgAuthPolPassinfoSubjectName   DisplayString,
    slbNewSslCfgAuthPolPassinfoSubjectFlag   INTEGER,
    slbNewSslCfgAuthPolPassinfoKeytypeName   DisplayString,
    slbNewSslCfgAuthPolPassinfoKeytypeFlag   INTEGER,
    slbNewSslCfgAuthPolPassinfoMd5Name       DisplayString,
    slbNewSslCfgAuthPolPassinfoMd5Flag       INTEGER,
    slbNewSslCfgAuthPolPassinfoCertName      DisplayString,
    slbNewSslCfgAuthPolPassinfoCertFormat    INTEGER,
    slbNewSslCfgAuthPolPassinfoCertFlag      INTEGER,
    slbNewSslCfgAuthPolPassinfoCharset       INTEGER,
    slbNewSslCfgAuthPolTrustcaChainName      DisplayString,
    slbNewSslCfgAuthPolTrustcaChainType      DisplayString,
    slbNewSslCfgAuthPolCadepth               INTEGER,
    slbNewSslCfgAuthPolCaverify              INTEGER,
    slbNewSslCfgAuthPolFailurl               DisplayString,
    slbNewSslCfgAuthPolAdminStatus           INTEGER,
    slbNewSslCfgAuthPolDelete                INTEGER, 
    slbNewSslCfgAuthPolPassinfoComp2424      INTEGER
    }

slbNewSslCfgAuthPolNameIdIndex  OBJECT-TYPE
    SYNTAX   DisplayString
    MAX-ACCESS  read-only
    STATUS  current
    DESCRIPTION
        "The Auth policy name(key id) as an index."
    ::= {slbNewSslCfgAuthPolEntry  1 }

slbNewSslCfgAuthPolName  OBJECT-TYPE
    SYNTAX   DisplayString
    MAX-ACCESS  read-create
    STATUS  current
    DESCRIPTION
        "Auth policy name."
    ::= {slbNewSslCfgAuthPolEntry  2 }

slbNewSslCfgAuthPolValidityMethod OBJECT-TYPE
    SYNTAX INTEGER 
    MAX-ACCESS  read-create
    STATUS  current
    DESCRIPTION
        "Certificate validation check method."
    ::= {slbNewSslCfgAuthPolEntry  3 }

slbNewSslCfgAuthPolValidityStaturi OBJECT-TYPE
    SYNTAX   DisplayString
    MAX-ACCESS  read-create
    STATUS  current
    DESCRIPTION
        "Static URI for OCSP validation requests."
    ::= {slbNewSslCfgAuthPolEntry  4 }

slbNewSslCfgAuthPolValidityUriprior OBJECT-TYPE
    SYNTAX  INTEGER {
        clientcert(1),
        staticuri(2)
        }
    MAX-ACCESS  read-create
    STATUS  current
    DESCRIPTION
        "OCSP URI priority."
    ::= {slbNewSslCfgAuthPolEntry  5 }

slbNewSslCfgAuthPolValidityCachtime OBJECT-TYPE
    SYNTAX  INTEGER 
    MAX-ACCESS  read-create
    STATUS  current
    DESCRIPTION
        "OCSP response cache time."
    ::= {slbNewSslCfgAuthPolEntry  6 }

slbNewSslCfgAuthPolValidityTimedev OBJECT-TYPE
    SYNTAX  INTEGER
    MAX-ACCESS  read-create
    STATUS  current
    DESCRIPTION
        "OCSP response time deviation."
    ::= {slbNewSslCfgAuthPolEntry  7 }

slbNewSslCfgAuthPolValidityAlgorthmName OBJECT-TYPE
    SYNTAX   DisplayString
    MAX-ACCESS  read-create
    STATUS  current
    DESCRIPTION
        "Allowed signing algorithm for the OCSP response [all, md5, sha1, sha256, sha384, sha512]."
    ::= {slbNewSslCfgAuthPolEntry  8 }

slbNewSslCfgAuthPolValidityVchain OBJECT-TYPE
    SYNTAX  INTEGER {
        enabled(1),
        disabled(2)
        }
    MAX-ACCESS  read-create
    STATUS  current
    DESCRIPTION
        "Enable/Disable validating every CA certificate in the CA chain u."
    ::= {slbNewSslCfgAuthPolEntry  9 }

slbNewSslCfgAuthPolValiditySecure OBJECT-TYPE
    SYNTAX  INTEGER {
        enabled(1),
        disabled(2)
        }
    MAX-ACCESS  read-create
    STATUS  current
    DESCRIPTION
        "Enable/Disable secure OCSP response by sending random nonce with."
    ::= {slbNewSslCfgAuthPolEntry  10 }

slbNewSslCfgAuthPolPassinfoVersionName OBJECT-TYPE
    SYNTAX   DisplayString
    MAX-ACCESS  read-create
    STATUS  current
    DESCRIPTION
        "Certificate version header."
    ::= {slbNewSslCfgAuthPolEntry  11 }

slbNewSslCfgAuthPolPassinfoVersionFlag OBJECT-TYPE
    SYNTAX  INTEGER {
        enabled(1),
        disabled(2)
        }
    MAX-ACCESS  read-create
    STATUS  current
    DESCRIPTION
         "Pass certificate version information to backend server?."
    ::= {slbNewSslCfgAuthPolEntry  12 }


slbNewSslCfgAuthPolPassinfoSerialName OBJECT-TYPE
    SYNTAX   DisplayString
    MAX-ACCESS  read-create
    STATUS  current
    DESCRIPTION
        "Certificate serial-number header."
    ::= {slbNewSslCfgAuthPolEntry  13 }

slbNewSslCfgAuthPolPassinfoSerialFlag OBJECT-TYPE
    SYNTAX  INTEGER {
        enabled(1),
        disabled(2)
        }
    MAX-ACCESS  read-create
    STATUS  current
    DESCRIPTION
        "Pass certificate serial-number to backend server?"
    ::= {slbNewSslCfgAuthPolEntry  14 }

slbNewSslCfgAuthPolPassinfoAlgoName OBJECT-TYPE
    SYNTAX   DisplayString
    MAX-ACCESS  read-create
    STATUS  current
    DESCRIPTION
        "Certificate signature algorithm header name."
    ::= {slbNewSslCfgAuthPolEntry  15 }

slbNewSslCfgAuthPolPassinfoAlgoFlag OBJECT-TYPE
    SYNTAX  INTEGER {
        enabled(1),
        disabled(2)
        }
    MAX-ACCESS  read-create
    STATUS  current
    DESCRIPTION
        "Pass certificate Signature Algorithm to backend server?"
    ::= {slbNewSslCfgAuthPolEntry  16 }

slbNewSslCfgAuthPolPassinfoIssuerName OBJECT-TYPE
    SYNTAX   DisplayString
    MAX-ACCESS  read-create
    STATUS  current
    DESCRIPTION
        "Certificate issuer header."
    ::= {slbNewSslCfgAuthPolEntry  17 }

slbNewSslCfgAuthPolPassinfoIssuerFlag OBJECT-TYPE
    SYNTAX  INTEGER {
        enabled(1),
        disabled(2)
        }
    MAX-ACCESS  read-create
    STATUS  current
    DESCRIPTION
        "Pass certificate issuer information to backend server?"
    ::= {slbNewSslCfgAuthPolEntry  18 }

slbNewSslCfgAuthPolPassinfoNbeforeName OBJECT-TYPE
    SYNTAX   DisplayString
    MAX-ACCESS  read-create
    STATUS  current
    DESCRIPTION
        "Certificate 'Not Before Validity Dates' header."
    ::= {slbNewSslCfgAuthPolEntry  19 }

slbNewSslCfgAuthPolPassinfoNbeforeFlag OBJECT-TYPE
    SYNTAX  INTEGER {
        enabled(1),
        disabled(2)
        }
    MAX-ACCESS  read-create
    STATUS  current
    DESCRIPTION
        "Pass certificate 'Not Before' Validity Date to backend serverr?"
    ::= {slbNewSslCfgAuthPolEntry  20 }

slbNewSslCfgAuthPolPassinfoNafterName OBJECT-TYPE
    SYNTAX   DisplayString
    MAX-ACCESS  read-create
    STATUS  current
    DESCRIPTION
        "Certificate 'Not After Validity Dates' header."
    ::= {slbNewSslCfgAuthPolEntry  21 }

slbNewSslCfgAuthPolPassinfoNafterFlag OBJECT-TYPE
    SYNTAX  INTEGER {
        enabled(1),
        disabled(2)
        }
    MAX-ACCESS  read-create
    STATUS  current
    DESCRIPTION
        "Pass certificate 'Not After' Validity Date to backend server?"
    ::= {slbNewSslCfgAuthPolEntry  22 }

slbNewSslCfgAuthPolPassinfoSubjectName OBJECT-TYPE
    SYNTAX   DisplayString
    MAX-ACCESS  read-create
    STATUS  current
    DESCRIPTION
        "Certificate subject header name."
    ::= {slbNewSslCfgAuthPolEntry  23 }

slbNewSslCfgAuthPolPassinfoSubjectFlag OBJECT-TYPE
    SYNTAX  INTEGER {
        enabled(1),
        disabled(2)
        }
    MAX-ACCESS  read-create
    STATUS  current
    DESCRIPTION
        "Pass certificate subject to backend server?"
    ::= {slbNewSslCfgAuthPolEntry  24 }


slbNewSslCfgAuthPolPassinfoKeytypeName OBJECT-TYPE
    SYNTAX   DisplayString
    MAX-ACCESS  read-create
    STATUS  current
    DESCRIPTION
        "Certificate Public Key Type header."
    ::= {slbNewSslCfgAuthPolEntry  25 }

slbNewSslCfgAuthPolPassinfoKeytypeFlag OBJECT-TYPE
    SYNTAX  INTEGER {
        enabled(1),
        disabled(2)
        }
    MAX-ACCESS  read-create
    STATUS  current
    DESCRIPTION
        "Pass certificate Public Key Type information to backend servers?"
    ::= {slbNewSslCfgAuthPolEntry  26 }

slbNewSslCfgAuthPolPassinfoMd5Name OBJECT-TYPE
    SYNTAX   DisplayString
    MAX-ACCESS  read-create
    STATUS  current
    DESCRIPTION
        "Certificate MD5 Hash header."
    ::= {slbNewSslCfgAuthPolEntry  27 }

slbNewSslCfgAuthPolPassinfoMd5Flag OBJECT-TYPE
    SYNTAX  INTEGER {
        enabled(1),
        disabled(2)
        }
    MAX-ACCESS  read-create
    STATUS  current
    DESCRIPTION
        "Pass certificate MD5 Hash information to backend servers?"
    ::= {slbNewSslCfgAuthPolEntry  28 }

slbNewSslCfgAuthPolPassinfoCertName OBJECT-TYPE
    SYNTAX   DisplayString
    MAX-ACCESS  read-create
    STATUS  current
    DESCRIPTION
        "Certificate header."
    ::= {slbNewSslCfgAuthPolEntry  29 }

slbNewSslCfgAuthPolPassinfoCertFormat OBJECT-TYPE
    SYNTAX INTEGER 
    MAX-ACCESS  read-create
    STATUS  current
    DESCRIPTION
        "Certificate Header Lines Format."
    ::= {slbNewSslCfgAuthPolEntry  30 }

slbNewSslCfgAuthPolPassinfoCertFlag OBJECT-TYPE
    SYNTAX  INTEGER {
        enabled(1),
        disabled(2)
        }
    MAX-ACCESS  read-create
    STATUS  current
    DESCRIPTION
        "Pass certificate information to backend servers?"
    ::= {slbNewSslCfgAuthPolEntry  31 }

slbNewSslCfgAuthPolPassinfoCharset OBJECT-TYPE
    SYNTAX  INTEGER
    MAX-ACCESS  read-create
    STATUS  current
    DESCRIPTION
        "Set the character set to be used for information."
    ::= {slbNewSslCfgAuthPolEntry  32 }

slbNewSslCfgAuthPolTrustcaChainName OBJECT-TYPE
    SYNTAX  DisplayString 
    MAX-ACCESS  read-create
    STATUS  current
    DESCRIPTION
        "Trusted client's CA certificate name."
    ::= {slbNewSslCfgAuthPolEntry  33 }

slbNewSslCfgAuthPolTrustcaChainType OBJECT-TYPE
    SYNTAX  DisplayString
    MAX-ACCESS  read-create
    STATUS  current
    DESCRIPTION
        "Trusted client's CA certificate type certificate=cert,Group=group,None=<empty string>."
    ::= {slbNewSslCfgAuthPolEntry  34 }

slbNewSslCfgAuthPolCadepth OBJECT-TYPE
    SYNTAX  INTEGER
    MAX-ACCESS  read-create
    STATUS  current
    DESCRIPTION
        "Maximum depth to search the trusted CA in the CA certificate."
    ::= {slbNewSslCfgAuthPolEntry  35 }

slbNewSslCfgAuthPolCaverify OBJECT-TYPE
    SYNTAX  INTEGER 
    MAX-ACCESS  read-create
    STATUS  current
    DESCRIPTION
        "Certificate's CA verification level."
    ::= {slbNewSslCfgAuthPolEntry  36 }

slbNewSslCfgAuthPolFailurl OBJECT-TYPE
    SYNTAX   DisplayString
    MAX-ACCESS  read-create
    STATUS  current
    DESCRIPTION
        "URL for redirection when client authentication fails"
    ::= {slbNewSslCfgAuthPolEntry  37 }

slbNewSslCfgAuthPolAdminStatus  OBJECT-TYPE
    SYNTAX  INTEGER {
        enabled(1),
        disabled(2)
        }
    MAX-ACCESS  read-create
    STATUS  current
    DESCRIPTION
        "Enable or disable Auth policy."
    ::= {slbNewSslCfgAuthPolEntry  38}

slbNewSslCfgAuthPolDelete OBJECT-TYPE
    SYNTAX  INTEGER {
        other(1),
        delete(2)
    }
    MAX-ACCESS  read-create
    STATUS  current
    DESCRIPTION
        "Delete Client Authentication Policy."
    ::= {slbNewSslCfgAuthPolEntry  39 }


slbNewSslCfgAuthPolPassinfoComp2424 OBJECT-TYPE
    SYNTAX  INTEGER{
        enabled(1),
        disabled(2)
        }
    MAX-ACCESS  read-create
    STATUS  current
    DESCRIPTION
        "Enable/Disable the 2424SSL Headers Compliance Mode."
    ::= {slbNewSslCfgAuthPolEntry  40 }


-- Certificate Repository
slbCurSslCfgCertsTable OBJECT-TYPE
    SYNTAX  SEQUENCE OF SlbCurSslCfgCertsEntry
    MAX-ACCESS  not-accessible
    STATUS  current
    DESCRIPTION
        "."
    ::= { certs 1 }

slbCurSslCfgCertsEntry OBJECT-TYPE
    SYNTAX  SlbCurSslCfgCertsEntry 
    MAX-ACCESS  not-accessible
    STATUS  current
    DESCRIPTION
        "."
    INDEX   { slbCurSslCfgCertsID, slbCurSslCfgCertsType }
    ::= { slbCurSslCfgCertsTable 1 }

SlbCurSslCfgCertsEntry ::= SEQUENCE {
    slbCurSslCfgCertsID                    DisplayString,
    slbCurSslCfgCertsType                  INTEGER,
    slbCurSslCfgCertsName                  DisplayString,
    slbCurSslCfgCertsKeySize               INTEGER,
    slbCurSslCfgCertsExpirty               DisplayString,
    slbCurSslCfgCertsCommonName            DisplayString,
    slbCurSslCfgCertsHashAlgo              INTEGER,
    slbCurSslCfgCertsCountryName           DisplayString,
    slbCurSslCfgCertsPrpvinceName          DisplayString,
    slbCurSslCfgCertsLocalityName          DisplayString,
    slbCurSslCfgCertsOrganizationName      DisplayString,
    slbCurSslCfgCertsOrganizationUnitName  DisplayString,
    slbCurSslCfgCertsEMail                 DisplayString,
    slbCurSslCfgCertsValidityPeriod        INTEGER,
    slbCurSslCfgCertsStatus                INTEGER
    }

slbCurSslCfgCertsID OBJECT-TYPE
    SYNTAX   DisplayString (SIZE(0..32))
    MAX-ACCESS  read-only
    STATUS  current
    DESCRIPTION
        "."
    ::= { slbCurSslCfgCertsEntry  1 }

slbCurSslCfgCertsType  OBJECT-TYPE
    SYNTAX  INTEGER {
                     key(1),
                     certificateRequest(2),
                     serverCertificate(3),
                     trustedCertificate(4),
                     intermediateCertificate(5)
                    }
    MAX-ACCESS  read-only
    STATUS  current
    DESCRIPTION
        "."
    ::= { slbCurSslCfgCertsEntry  2 }

slbCurSslCfgCertsName  OBJECT-TYPE
    SYNTAX  DisplayString (SIZE(0..32))
    MAX-ACCESS  read-only
    STATUS  current
    DESCRIPTION
        "."
    ::= { slbCurSslCfgCertsEntry  3 }

slbCurSslCfgCertsKeySize  OBJECT-TYPE
    SYNTAX  INTEGER {
                     ks512(1),
                     ks1024(2),
                     ks2048(3),
                     ks4096(4),
                     unknown(6)
                    }
    MAX-ACCESS  read-only
    STATUS  current
    DESCRIPTION
        "."
    ::= { slbCurSslCfgCertsEntry  4 }

slbCurSslCfgCertsExpirty  OBJECT-TYPE
    SYNTAX  DisplayString
    MAX-ACCESS  read-only
    STATUS  current
    DESCRIPTION
        "."
    ::= { slbCurSslCfgCertsEntry  5 }

slbCurSslCfgCertsCommonName  OBJECT-TYPE
    SYNTAX  DisplayString (SIZE(0..85))
    MAX-ACCESS  read-only
    STATUS  current
    DESCRIPTION
        "."
    ::= { slbCurSslCfgCertsEntry  6 }

slbCurSslCfgCertsHashAlgo  OBJECT-TYPE
    SYNTAX  INTEGER {
                     md5(1),
                     sha1(2),
                     sha256(3),
                     sha384(4),
                     sha512(5),
                     unknown(6)
                    }
    MAX-ACCESS  read-only
    STATUS  current
    DESCRIPTION
        "."
    ::= { slbCurSslCfgCertsEntry  7 }

slbCurSslCfgCertsCountryName  OBJECT-TYPE
    SYNTAX  DisplayString (SIZE(0..85))
    MAX-ACCESS  read-only
    STATUS  current
    DESCRIPTION
        "."
    ::= { slbCurSslCfgCertsEntry  8 }

slbCurSslCfgCertsPrpvinceName  OBJECT-TYPE
    SYNTAX  DisplayString (SIZE(0..149))
    MAX-ACCESS  read-only
    STATUS  current
    DESCRIPTION
        "."
    ::= { slbCurSslCfgCertsEntry  9 }

slbCurSslCfgCertsLocalityName  OBJECT-TYPE
    SYNTAX  DisplayString (SIZE(0..149))
    MAX-ACCESS  read-only
    STATUS  current
    DESCRIPTION
        "."
    ::= { slbCurSslCfgCertsEntry  10 }

slbCurSslCfgCertsOrganizationName  OBJECT-TYPE
    SYNTAX  DisplayString (SIZE(0..85))
    MAX-ACCESS  read-only
    STATUS  current
    DESCRIPTION
        "."
    ::= { slbCurSslCfgCertsEntry  11 }

slbCurSslCfgCertsOrganizationUnitName  OBJECT-TYPE
    SYNTAX  DisplayString (SIZE(0..85))
    MAX-ACCESS  read-only
    STATUS  current
    DESCRIPTION
        "."
    ::= { slbCurSslCfgCertsEntry  12 }

slbCurSslCfgCertsEMail  OBJECT-TYPE
    SYNTAX  DisplayString (SIZE(0..149))
    MAX-ACCESS  read-only
    STATUS  current
    DESCRIPTION
        "."
    ::= { slbCurSslCfgCertsEntry  13 }

slbCurSslCfgCertsValidityPeriod  OBJECT-TYPE
    SYNTAX  INTEGER  (1..3650)
    MAX-ACCESS  read-only
    STATUS  current
    DESCRIPTION
        "."
    ::= { slbCurSslCfgCertsEntry  14 }

slbCurSslCfgCertsStatus OBJECT-TYPE
    SYNTAX  INTEGER {
        generated(1),
        notGenerated(2)
        }
    MAX-ACCESS  read-only
    STATUS  current
    DESCRIPTION
        "Shows if the current certificate is generated."
    ::= { slbCurSslCfgCertsEntry 15 }

slbNewSslCfgCertsTable OBJECT-TYPE
    SYNTAX  SEQUENCE OF SlbNewSslCfgCertsEntry
    MAX-ACCESS  not-accessible
    STATUS  current
    DESCRIPTION
        "."
    ::= { certs 2 }

slbNewSslCfgCertsEntry OBJECT-TYPE
    SYNTAX  SlbNewSslCfgCertsEntry 
    MAX-ACCESS  not-accessible
    STATUS  current
    DESCRIPTION
        "."
    INDEX   { slbNewSslCfgCertsID, slbNewSslCfgCertsType }
    ::= { slbNewSslCfgCertsTable 1 }

SlbNewSslCfgCertsEntry ::= SEQUENCE {
    slbNewSslCfgCertsID                    DisplayString,
    slbNewSslCfgCertsType                  INTEGER,
    slbNewSslCfgCertsName                  DisplayString,
    slbNewSslCfgCertsKeySize               INTEGER,
    slbNewSslCfgCertsExpirty               DisplayString,
    slbNewSslCfgCertsCommonName            DisplayString,
    slbNewSslCfgCertsHashAlgo              INTEGER,
    slbNewSslCfgCertsCountryName           DisplayString,
    slbNewSslCfgCertsPrpvinceName          DisplayString,
    slbNewSslCfgCertsLocalityName          DisplayString,
    slbNewSslCfgCertsOrganizationName      DisplayString,
    slbNewSslCfgCertsOrganizationUnitName  DisplayString,
    slbNewSslCfgCertsEMail                 DisplayString,
    slbNewSslCfgCertsValidityPeriod        INTEGER,
    slbNewSslCfgCertsDelete                INTEGER,
    slbNewSslCfgCertsGenerate              INTEGER,
    slbNewSslCfgCertsStatus                INTEGER
    }

slbNewSslCfgCertsID OBJECT-TYPE
    SYNTAX   DisplayString (SIZE(0..32))
    MAX-ACCESS  read-only
    STATUS  current
    DESCRIPTION
        "."
    ::= { slbNewSslCfgCertsEntry  1 }

slbNewSslCfgCertsType  OBJECT-TYPE
    SYNTAX  INTEGER {
                     key(1),
                     certificateRequest(2),
                     serverCertificate(3),
                     trustedCertificate(4),
                     intermediateCertificate(5)
                    }
    MAX-ACCESS  read-only
    STATUS  current
    DESCRIPTION
        "."
    ::= { slbNewSslCfgCertsEntry  2 }

slbNewSslCfgCertsName  OBJECT-TYPE
    SYNTAX  DisplayString (SIZE(0..32))
    MAX-ACCESS  read-write
      STATUS  current
      DESCRIPTION
          "."
      ::= { slbNewSslCfgCertsEntry  3 }

slbNewSslCfgCertsKeySize  OBJECT-TYPE
    SYNTAX  INTEGER {
                     ks512(1),
                     ks1024(2),
                     ks2048(3),
                     ks4096(4),
                     unknown(6)
                    }
    MAX-ACCESS  read-create
      STATUS  current
      DESCRIPTION
          "."
      ::= { slbNewSslCfgCertsEntry  4 }

slbNewSslCfgCertsExpirty  OBJECT-TYPE
    SYNTAX  DisplayString
    MAX-ACCESS  read-only
      STATUS  current
      DESCRIPTION
          "."
      ::= { slbNewSslCfgCertsEntry  5 }

slbNewSslCfgCertsCommonName  OBJECT-TYPE
    SYNTAX  DisplayString (SIZE(0..85))
      MAX-ACCESS  read-create
      STATUS  current
      DESCRIPTION
          "."
      ::= { slbNewSslCfgCertsEntry  6 }

slbNewSslCfgCertsHashAlgo  OBJECT-TYPE
    SYNTAX  INTEGER {
                     md5(1),
                     sha1(2),
                     sha256(3),
                     sha384(4),
                     sha512(5),
                     unknown(6)
                    }
    MAX-ACCESS  read-create
    STATUS  current
    DESCRIPTION
        "."
    ::= { slbNewSslCfgCertsEntry  7 }

slbNewSslCfgCertsCountryName  OBJECT-TYPE
    SYNTAX  DisplayString (SIZE(0..85))
    MAX-ACCESS  read-create
    STATUS  current
    DESCRIPTION
        "."
    ::= { slbNewSslCfgCertsEntry  8 }

slbNewSslCfgCertsPrpvinceName  OBJECT-TYPE
    SYNTAX  DisplayString (SIZE(0..149))
    MAX-ACCESS  read-create
    STATUS  current
    DESCRIPTION
        "."
    ::= { slbNewSslCfgCertsEntry  9 }

slbNewSslCfgCertsLocalityName  OBJECT-TYPE
    SYNTAX  DisplayString (SIZE(0..149))
    MAX-ACCESS  read-create
    STATUS  current
    DESCRIPTION
        "."
    ::= { slbNewSslCfgCertsEntry  10 }

slbNewSslCfgCertsOrganizationName  OBJECT-TYPE
    SYNTAX  DisplayString (SIZE(0..85))
    MAX-ACCESS  read-create
    STATUS  current
    DESCRIPTION
        "."
    ::= { slbNewSslCfgCertsEntry  11 }

slbNewSslCfgCertsOrganizationUnitName  OBJECT-TYPE
    SYNTAX  DisplayString (SIZE(0..85))
    MAX-ACCESS  read-create
    STATUS  current
    DESCRIPTION
        "."
    ::= { slbNewSslCfgCertsEntry  12 }

slbNewSslCfgCertsEMail  OBJECT-TYPE
    SYNTAX  DisplayString (SIZE(0..149))
    MAX-ACCESS  read-create
    STATUS  current
    DESCRIPTION
        "."
    ::= { slbNewSslCfgCertsEntry  13 }

slbNewSslCfgCertsValidityPeriod  OBJECT-TYPE
    SYNTAX  INTEGER  (1..3650)
    MAX-ACCESS  read-create
    STATUS  current
    DESCRIPTION
        "."
    ::= { slbNewSslCfgCertsEntry  14 }

slbNewSslCfgCertsDelete OBJECT-TYPE
    SYNTAX  INTEGER {
        other(1),
        delete(2)
        }
    MAX-ACCESS  read-write
    STATUS  current
    DESCRIPTION
        "Delete certificate."
    ::= { slbNewSslCfgCertsEntry 15 }

slbNewSslCfgCertsGenerate OBJECT-TYPE
    SYNTAX  INTEGER {
        other(1),
        generate(2)
        }
    MAX-ACCESS  read-write
    STATUS  current
    DESCRIPTION
        "By setting the value to generate(2), the Certicicate will be generated."
    ::= { slbNewSslCfgCertsEntry 16 }

slbNewSslCfgCertsStatus OBJECT-TYPE
    SYNTAX  INTEGER {
        generated(1),
        notGenerated(2),
	inProgress(3)
        }
    MAX-ACCESS  read-only
    STATUS  current
    DESCRIPTION
        "Shows if the current certificate is generated."
    ::= { slbNewSslCfgCertsEntry 17 }

slbSslCfgCertsDefaults  OBJECT IDENTIFIER ::= { certs 3 }

slbCurSslCfgCertsDefaultsCountryName OBJECT-TYPE
    SYNTAX  DisplayString (SIZE (2))
    MAX-ACCESS  read-only
    STATUS  current
    DESCRIPTION
        "SSL certificate Country Name in 2 letter code."
    ::= { slbSslCfgCertsDefaults 1 }

slbNewSslCfgCertsDefaultsCountryName OBJECT-TYPE
    SYNTAX  DisplayString (SIZE (2))
    MAX-ACCESS  read-write
    STATUS  current
    DESCRIPTION
        "SSL certificate Country Name in 2 letter code."
    ::= { slbSslCfgCertsDefaults 2 }

slbCurSslCfgCertsDefaultsProvinceName OBJECT-TYPE
    SYNTAX  DisplayString (SIZE(0..149))
    MAX-ACCESS  read-only
    STATUS  current
    DESCRIPTION
        "SSL Certificate State or Province Name."
    ::= { slbSslCfgCertsDefaults 3 }

slbNewSslCfgCertsDefaultsProvinceName OBJECT-TYPE
    SYNTAX  DisplayString (SIZE(0..149))
    MAX-ACCESS  read-write
    STATUS  current
    DESCRIPTION
        "SSL Certificate State or Province Name."
    ::= { slbSslCfgCertsDefaults 4 }

slbCurSslCfgCertsDefaultsLocallyName OBJECT-TYPE
    SYNTAX  DisplayString (SIZE(0..149))
    MAX-ACCESS  read-only
    STATUS  current
    DESCRIPTION
        "SSL certificate locality name (e.g. city)."
    ::= { slbSslCfgCertsDefaults 5 }

slbNewSslCfgCertsDefaultsLocallyName OBJECT-TYPE
    SYNTAX  DisplayString (SIZE(0..149))
    MAX-ACCESS  read-write
    STATUS  current
    DESCRIPTION
        "SSL certificate locality name (e.g. city)."
    ::= { slbSslCfgCertsDefaults 6 }

slbCurSslCfgCertsDefaultsOrganizationName OBJECT-TYPE
    SYNTAX  DisplayString (SIZE(0..85))
    MAX-ACCESS  read-only
    STATUS  current
    DESCRIPTION
        "SSL certificate Organization Name (e.g. company)."
    ::= { slbSslCfgCertsDefaults 7 }

slbNewSslCfgCertsDefaultsOrganizationName OBJECT-TYPE
    SYNTAX  DisplayString (SIZE(0..85))
    MAX-ACCESS  read-write
    STATUS  current
    DESCRIPTION
        "SSL certificate Organization Name (e.g. company)."
    ::= { slbSslCfgCertsDefaults 8 }

slbCurSslCfgCertsDefaultsOrganizationUnitName OBJECT-TYPE
    SYNTAX  DisplayString (SIZE(0..85))
    MAX-ACCESS  read-only
    STATUS  current
    DESCRIPTION
        "SSL certificate Organizational Unit Name (e.g. accounting)."
    ::= { slbSslCfgCertsDefaults 9 }

slbNewSslCfgCertsDefaultsOrganizationUnitName OBJECT-TYPE
    SYNTAX  DisplayString (SIZE(0..85))
    MAX-ACCESS  read-write
    STATUS  current
    DESCRIPTION
        "SSL certificate Organizational Unit Name (e.g. accounting)."
    ::= { slbSslCfgCertsDefaults 10 }

slbCurSslCfgCertsDefaultsEMail OBJECT-TYPE
    SYNTAX  DisplayString (SIZE(0..149))
    MAX-ACCESS  read-only
    STATUS  current
    DESCRIPTION
        "SSL certificate Email (e.g. admin@company.com)."
    ::= { slbSslCfgCertsDefaults 11 }

slbNewSslCfgCertsDefaultsEMail OBJECT-TYPE
    SYNTAX  DisplayString (SIZE(0..149))
    MAX-ACCESS  read-write
    STATUS  current
    DESCRIPTION
        "SSL certificate Email (e.g. admin@company.com)."
    ::= { slbSslCfgCertsDefaults 12 }

slbCurSslCfgGroupsTable OBJECT-TYPE
    SYNTAX  SEQUENCE OF SlbCurSslCfgGroupsEntry
    MAX-ACCESS  not-accessible
    STATUS  current
    DESCRIPTION
        "."
    ::= { certs 4 }

slbCurSslCfgGroupsEntry OBJECT-TYPE
    SYNTAX  SlbCurSslCfgGroupsEntry 
    MAX-ACCESS  not-accessible
    STATUS  current
    DESCRIPTION
        "."
    INDEX   { slbCurSslCfgGroupsID }
    ::= { slbCurSslCfgGroupsTable 1 }

SlbCurSslCfgGroupsEntry ::= SEQUENCE {
    slbCurSslCfgGroupsID          DisplayString,
    slbCurSslCfgGroupsName        DisplayString,
    slbCurSslCfgGroupsType        INTEGER,
    slbCurSslCfgGroupsDefaultCert DisplayString,
    slbCurSslCfgGroupsCertBmap    OCTET STRING
    }

slbCurSslCfgGroupsID OBJECT-TYPE
    SYNTAX   DisplayString (SIZE(0..32))
    MAX-ACCESS  read-only
    STATUS  current
    DESCRIPTION
        "."
    ::= { slbCurSslCfgGroupsEntry  1 }

slbCurSslCfgGroupsName  OBJECT-TYPE
    SYNTAX  DisplayString (SIZE(0..32))
    MAX-ACCESS  read-only
      STATUS  current
      DESCRIPTION
          "."
      ::= { slbCurSslCfgGroupsEntry  2 }

slbCurSslCfgGroupsType  OBJECT-TYPE
    SYNTAX  INTEGER {
                     serverCertificate(3),
                     trustedCertificate(4),
                     intermediateCertificate(5)
                    }
    MAX-ACCESS  read-only
    STATUS  current
    DESCRIPTION
        "."
    ::= { slbCurSslCfgGroupsEntry  3 }

slbCurSslCfgGroupsDefaultCert OBJECT-TYPE
    SYNTAX  DisplayString (SIZE(0..32))
    MAX-ACCESS  read-only
      STATUS  current
      DESCRIPTION
          "."
      ::= { slbCurSslCfgGroupsEntry  4 }

slbCurSslCfgGroupsCertBmap OBJECT-TYPE
    SYNTAX  OCTET STRING
    MAX-ACCESS  read-only
    STATUS  current
    DESCRIPTION
         "List of Certificates the group holds - Selected certificates 
         are presented in a bitmap format.
         Receiving order is as:

	 OCTET 1  OCTET 2  .....
	 xxxxxxxx xxxxxxxx .....
	 ||    || |_ Cert 9
	 ||    ||
	 ||    ||___ Cert 4
	 ||    |____ Cert 3
	 ||      .    .   .
	 ||_________ Cert 2
	 |__________ Cert 1

	 where x : 1 - The represented certficate is selected
	 0 - The represented certificate is not selected."
    ::= { slbCurSslCfgGroupsEntry  5 }	 

slbNewSslCfgGroupsTable OBJECT-TYPE
    SYNTAX  SEQUENCE OF SlbNewSslCfgGroupsEntry
    MAX-ACCESS  not-accessible
    STATUS  current
    DESCRIPTION
        "."
    ::= { certs 5 }

slbNewSslCfgGroupsEntry OBJECT-TYPE
    SYNTAX  SlbNewSslCfgGroupsEntry 
    MAX-ACCESS  not-accessible
    STATUS  current
    DESCRIPTION
        "."
    INDEX   { slbNewSslCfgGroupsID }
    ::= { slbNewSslCfgGroupsTable 1 }

SlbNewSslCfgGroupsEntry ::= SEQUENCE {
    slbNewSslCfgGroupsID          DisplayString,
    slbNewSslCfgGroupsName        DisplayString,
    slbNewSslCfgGroupsType        INTEGER,
    slbNewSslCfgGroupsDelete      INTEGER,
    slbNewSslCfgGroupsDefaultCert DisplayString,
    slbNewSslCfgGroupsAddCert     DisplayString,
    slbNewSslCfgGroupsRemCert     DisplayString,
    slbNewSslCfgGroupsCertBmap    OCTET STRING
    }

slbNewSslCfgGroupsID OBJECT-TYPE
    SYNTAX   DisplayString (SIZE(0..32))
    MAX-ACCESS  read-only
    STATUS  current
    DESCRIPTION
        "."
    ::= { slbNewSslCfgGroupsEntry  1 }

slbNewSslCfgGroupsName  OBJECT-TYPE
    SYNTAX  DisplayString (SIZE(0..32))
    MAX-ACCESS  read-write
      STATUS  current
      DESCRIPTION
          "."
      ::= { slbNewSslCfgGroupsEntry  2 }

slbNewSslCfgGroupsType  OBJECT-TYPE
    SYNTAX  INTEGER {
                     serverCertificate(3),
                     trustedCertificate(4),
                     intermediateCertificate(5)
                    }
    MAX-ACCESS  read-write
    STATUS  current
    DESCRIPTION
        "."
    ::= { slbNewSslCfgGroupsEntry  3 }

slbNewSslCfgGroupsDelete OBJECT-TYPE
    SYNTAX  INTEGER {
        other(1),
        delete(2)
        }
    MAX-ACCESS  read-write
    STATUS  current
    DESCRIPTION
        "Delete certificate group."
    ::= { slbNewSslCfgGroupsEntry 4 }

slbNewSslCfgGroupsDefaultCert OBJECT-TYPE
    SYNTAX  DisplayString (SIZE(0..32))
    MAX-ACCESS  read-write 
      STATUS  current
      DESCRIPTION
          "."
      ::= { slbNewSslCfgGroupsEntry  5 }

slbNewSslCfgGroupsAddCert  OBJECT-TYPE
    SYNTAX  DisplayString (SIZE(0..32))
    MAX-ACCESS  read-write
    STATUS  current
    DESCRIPTION
        "Add cerificate to the group"
    ::= { slbNewSslCfgGroupsEntry  6 }

slbNewSslCfgGroupsRemCert  OBJECT-TYPE
    SYNTAX  DisplayString (SIZE(0..32))
    MAX-ACCESS  read-write
    STATUS  current
    DESCRIPTION
        "Remove cerificate from the group"
    ::= { slbNewSslCfgGroupsEntry  7 }	

slbNewSslCfgGroupsCertBmap OBJECT-TYPE
    SYNTAX  OCTET STRING
    MAX-ACCESS  read-only
    STATUS  current
    DESCRIPTION
         "List of Certificates the group holds - Selected certificates 
         are presented in a bitmap format.
         Receiving order is as:

	 OCTET 1  OCTET 2  .....
	 xxxxxxxx xxxxxxxx .....
	 ||    || |_ Cert 9
	 ||    ||
	 ||    ||___ Cert 4
	 ||    |____ Cert 3
	 ||      .    .   .
	 ||_________ Cert 2
	 |__________ Cert 1

	 where x : 1 - The represented certficate is selected
	 0 - The represented certificate is not selected."
    ::= { slbNewSslCfgGroupsEntry  8 }

-- Service Mapping Real Port Table 

slbSmtportTableMaxSize OBJECT-TYPE
    SYNTAX  Integer32 
    MAX-ACCESS  read-only 
    STATUS  current 
    DESCRIPTION 
        "The maximum number of entries in service mapping real port table." 
    ::= { smtportCfg 1 }

slbCurCfgSmtportTable OBJECT-TYPE
    SYNTAX  SEQUENCE OF SlbCurCfgSmtportEntry 
    MAX-ACCESS  not-accessible
    STATUS  current
    DESCRIPTION
        "The service mapping real port table."
    ::= { smtportCfg 2 }

slbCurCfgSmtportEntry OBJECT-TYPE
    SYNTAX  SlbCurCfgSmtportEntry
    MAX-ACCESS  not-accessible
    STATUS  current
    DESCRIPTION
        "A row in the service mapping real port table."
    INDEX   { slbCurCfgSmtportIndex }
    ::= { slbCurCfgSmtportTable 1 }

SlbCurCfgSmtportEntry ::= SEQUENCE {
    slbCurCfgSmtportIndex          Integer32,
    slbCurCfgSmtportNum            INTEGER
    }

slbCurCfgSmtportIndex OBJECT-TYPE 
    SYNTAX  Integer32 
    MAX-ACCESS  read-only 
    STATUS  current 
    DESCRIPTION 
        "The service mapping real port index." 
    ::= { slbCurCfgSmtportEntry 1 }

slbCurCfgSmtportNum OBJECT-TYPE  
    SYNTAX  INTEGER (2..65534)
    MAX-ACCESS  read-only  
    STATUS  current  
    DESCRIPTION 
        "The service mapping real port number."  
    ::= { slbCurCfgSmtportEntry 2 } 

slbNewCfgSmtportTable OBJECT-TYPE
    SYNTAX  SEQUENCE OF SlbNewCfgSmtportEntry 
    MAX-ACCESS  not-accessible
    STATUS  current
    DESCRIPTION
        "The table of real server service ports."
    ::= { smtportCfg 3 }

slbNewCfgSmtportEntry OBJECT-TYPE
    SYNTAX  SlbNewCfgSmtportEntry
    MAX-ACCESS  not-accessible
    STATUS  current
    DESCRIPTION
        "A row in the service mapping real port table."
    INDEX   { slbNewCfgSmtportIndex }
    ::= { slbNewCfgSmtportTable 1 }

SlbNewCfgSmtportEntry ::= SEQUENCE {
    slbNewCfgSmtportIndex          Integer32,
    slbNewCfgSmtportNum            INTEGER,
    slbNewCfgSmtportDelete         INTEGER
    }

slbNewCfgSmtportIndex OBJECT-TYPE 
    SYNTAX  Integer32 
    MAX-ACCESS  read-only 
    STATUS  current 
    DESCRIPTION 
        "The service mapping real port index" 
    ::= { slbNewCfgSmtportEntry 1 }

slbNewCfgSmtportNum OBJECT-TYPE  
    SYNTAX  INTEGER (2..65534)
    MAX-ACCESS  read-create  
    STATUS  current  
    DESCRIPTION 
        "The service mapping real port number."  
    ::= { slbNewCfgSmtportEntry 2 } 

slbNewCfgSmtportDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { slbNewCfgSmtportEntry 3 }

slbSmtportTableAvaibleIndex OBJECT-TYPE
    SYNTAX  Integer32
    MAX-ACCESS  read-only
    STATUS  current
    DESCRIPTION
        "The first free real port index of the Service Mapping Table. Value 0 will be returned
         when all 16 real ports are configured."
    ::= { smtportCfg 4 }


slbWlmTableMaxSize OBJECT-TYPE
    SYNTAX Integer32 
    MAX-ACCESS read-only 
    STATUS current 
    DESCRIPTION 
        "The maximum number of entries in Workload Manager table." 
    ::= { wlmCfg 1 }

slbCurCfgWlmTable OBJECT-TYPE
    SYNTAX SEQUENCE OF SlbCurCfgWlmEntry
    MAX-ACCESS not-accessible
    STATUS current
    DESCRIPTION
        "The table of Workload Managers configuration."
    ::= { wlmCfg 2 }

slbCurCfgWlmEntry OBJECT-TYPE
    SYNTAX SlbCurCfgWlmEntry
    MAX-ACCESS not-accessible
    STATUS current
    DESCRIPTION
        "Information about a particular Workload Manager configuration."
    INDEX { slbCurCfgWlmIndex }
    ::= { slbCurCfgWlmTable 1 }
 
SlbCurCfgWlmEntry ::= SEQUENCE {
    slbCurCfgWlmIndex           Integer32,
    slbCurCfgWlmIpAddr          IpAddress,
    slbCurCfgWlmPort            INTEGER,
    slbCurCfgWlmGroups          DisplayString,
    slbCurCfgWlmState           INTEGER
    }

slbCurCfgWlmIndex OBJECT-TYPE
    SYNTAX  Integer32
    MAX-ACCESS  read-only
    STATUS  current
    DESCRIPTION
        "The Workload Manager number" 
    ::= { slbCurCfgWlmEntry 1 }

slbCurCfgWlmIpAddr OBJECT-TYPE
    SYNTAX  IpAddress
    MAX-ACCESS  read-only
    STATUS  current
    DESCRIPTION
        "IP address of the Workload Manager."
    ::= { slbCurCfgWlmEntry 2 }

slbCurCfgWlmPort OBJECT-TYPE
    SYNTAX  INTEGER (0..65534)
    MAX-ACCESS  read-only
    STATUS  current
    DESCRIPTION
        "The port number for the Workload Manager." 
    ::= { slbCurCfgWlmEntry 3 }

slbCurCfgWlmGroups OBJECT-TYPE
    SYNTAX DisplayString  ( SIZE ( 0 .. 255  ) ) 
    MAX-ACCESS read-only
    STATUS current
    DESCRIPTION 
        "The group number for the Workload Manager."
    ::= { slbCurCfgWlmEntry 4 }

slbCurCfgWlmState OBJECT-TYPE
    SYNTAX INTEGER {
        enabled(1),
        disabled(2)
    }
    MAX-ACCESS read-only
    STATUS current
    DESCRIPTION
        "Connection state of the Workload Manager."
    ::= { slbCurCfgWlmEntry 5 }

slbNewCfgWlmTable OBJECT-TYPE
    SYNTAX SEQUENCE OF SlbNewCfgWlmEntry
    MAX-ACCESS not-accessible
    STATUS current
    DESCRIPTION
        "The table of Workload Managers configuration."
    ::= { wlmCfg 3 }

slbNewCfgWlmEntry OBJECT-TYPE
    SYNTAX SlbNewCfgWlmEntry
    MAX-ACCESS not-accessible
    STATUS current
    DESCRIPTION
        "Information about a particular Workload Manager configuration."
    INDEX { slbNewCfgWlmIndex }
    ::= { slbNewCfgWlmTable 1 }
 
SlbNewCfgWlmEntry ::= SEQUENCE {
    slbNewCfgWlmIndex           Integer32,
    slbNewCfgWlmIpAddr          IpAddress,
    slbNewCfgWlmPort            INTEGER,
    slbNewCfgWlmDelete          INTEGER,
    slbNewCfgWlmGroups          DisplayString,
    slbNewCfgWlmState           INTEGER
    }

slbNewCfgWlmIndex OBJECT-TYPE
    SYNTAX  Integer32
    MAX-ACCESS  read-only
    STATUS  current
    DESCRIPTION
        "The Workload Manager number" 
    ::= { slbNewCfgWlmEntry 1 }

slbNewCfgWlmIpAddr OBJECT-TYPE
    SYNTAX  IpAddress
    MAX-ACCESS  read-create
    STATUS  current
    DESCRIPTION
        "IP address of the Workload Manager."
    ::= { slbNewCfgWlmEntry 2 }

slbNewCfgWlmPort OBJECT-TYPE
    SYNTAX  INTEGER (0..65534)
    MAX-ACCESS  read-create
    STATUS  current
    DESCRIPTION
        "The port number for the Workload Manager." 
    ::= { slbNewCfgWlmEntry 3 }

slbNewCfgWlmDelete OBJECT-TYPE
    SYNTAX  INTEGER {
        other(1),
        delete(2)
        }
    MAX-ACCESS  read-create
    STATUS  current
    DESCRIPTION
        "By setting the value to delete(2), the entire row is deleted."
    ::= { slbNewCfgWlmEntry 4 }

slbNewCfgWlmGroups OBJECT-TYPE
    SYNTAX DisplayString  ( SIZE ( 0 .. 255  ) )
    MAX-ACCESS read-only
    STATUS current
    DESCRIPTION
        "The group number for the Workload Manager."
    ::= { slbNewCfgWlmEntry 5 }

slbNewCfgWlmState OBJECT-TYPE
    SYNTAX INTEGER {
        enabled(1),
            disabled(2)
    }
    MAX-ACCESS read-only
    STATUS current
    DESCRIPTION
        "Connection state of the Workload Manager."
    ::= { slbNewCfgWlmEntry 6 }


slbCurAcclCfgCachememcache OBJECT-TYPE
   SYNTAX  INTEGER (1..50)
   MAX-ACCESS  read-only
   STATUS  current
   DESCRIPTION
       "Maximum percentage of Alteon RAM to be allocate for caching."
   ::= { caching 1}

slbNewAcclCfgCachememcache OBJECT-TYPE
   SYNTAX  INTEGER (1..50)
   MAX-ACCESS  read-write
   STATUS  current
   DESCRIPTION
       "Defines the maximum percentage of Alteon RAM to be allocate for caching."
   ::= { caching 2}

slbCurAcclCfgCacheOnOff OBJECT-TYPE
   SYNTAX  INTEGER {
       on(1),
       off(2)
       }
   MAX-ACCESS  read-only
   STATUS  current
   DESCRIPTION
       "Globally ON or OFF of caching."
   ::= { caching 3}

slbNewAcclCfgCacheOnOff OBJECT-TYPE
   SYNTAX  INTEGER {
       on(1),
       off(2)
       }
   MAX-ACCESS  read-write
   STATUS  current
   DESCRIPTION
       "Globally ON or OFF of caching."
   ::= { caching 4}

slbCurAcclCfgCachePolTable OBJECT-TYPE
    SYNTAX  SEQUENCE OF SlbCurAcclCfgCachePolEntry
    MAX-ACCESS  not-accessible
    STATUS  current
    DESCRIPTION
        "The table for configuring caching policy."
    ::= { caching 5 }

slbCurAcclCfgCachePolEntry OBJECT-TYPE
    SYNTAX  SlbCurAcclCfgCachePolEntry
    MAX-ACCESS  not-accessible
    STATUS  current
    DESCRIPTION
        "A row in the caching policy table."
    INDEX   { slbCurAcclCfgCachePolNameIdIndex }
    ::= { slbCurAcclCfgCachePolTable 1 }

SlbCurAcclCfgCachePolEntry ::= SEQUENCE {
    slbCurAcclCfgCachePolNameIdIndex          DisplayString,
    slbCurAcclCfgCachePolName                 DisplayString,
    slbCurAcclCfgCachePolExpireTime           INTEGER,
    slbCurAcclCfgCachePolMinSize              INTEGER,
    slbCurAcclCfgCachePolMaxSize              INTEGER,
    slbCurAcclCfgCachePolURLList              DisplayString,
    slbCurAcclCfgCachePolStore                INTEGER,
    slbCurAcclCfgCachePolServe                INTEGER,
    slbCurAcclCfgCachePolQuery                INTEGER,
    slbCurAcclCfgCachePolBrowser              INTEGER,
    slbCurAcclCfgCachePolAdminStatus          INTEGER
    }

slbCurAcclCfgCachePolNameIdIndex OBJECT-TYPE
    SYNTAX   DisplayString (SIZE (0..31))
    MAX-ACCESS  read-only
    STATUS  current
    DESCRIPTION
        "The caching policy ID(key id) as an index."
    ::= { slbCurAcclCfgCachePolEntry 1 }

slbCurAcclCfgCachePolName OBJECT-TYPE
    SYNTAX   DisplayString (SIZE (0..31))
    MAX-ACCESS  read-only
    STATUS  current
    DESCRIPTION
        "Cache policy name."
    ::= { slbCurAcclCfgCachePolEntry 2 }

slbCurAcclCfgCachePolExpireTime OBJECT-TYPE
    SYNTAX  INTEGER 
    MAX-ACCESS  read-only
    STATUS  current
    DESCRIPTION
        "Maximum expiration time in seconds."
    ::= { slbCurAcclCfgCachePolEntry 3 }

slbCurAcclCfgCachePolMinSize OBJECT-TYPE
    SYNTAX  INTEGER 
    MAX-ACCESS  read-only
    STATUS  current
    DESCRIPTION
        "Minimum Object size to be stored in bytes."
    ::= { slbCurAcclCfgCachePolEntry 4 }

slbCurAcclCfgCachePolMaxSize OBJECT-TYPE
    SYNTAX  INTEGER
    MAX-ACCESS  read-only
    STATUS  current
    DESCRIPTION
        "Maximum Object size to be stored in bytes." 
    ::= { slbCurAcclCfgCachePolEntry 5 }

slbCurAcclCfgCachePolURLList OBJECT-TYPE
    SYNTAX   DisplayString (SIZE (0..31))
    MAX-ACCESS  read-only
    STATUS  current
    DESCRIPTION
        "URL list which is associated with this policy."
    ::= { slbCurAcclCfgCachePolEntry 6 }

slbCurAcclCfgCachePolStore OBJECT-TYPE
    SYNTAX  INTEGER {
        srvrhdr(1),
        cacheall(2)
        }
    MAX-ACCESS  read-only
    STATUS  current
    DESCRIPTION
        "Caching behavior for storing new objects in cache."
    ::= { slbCurAcclCfgCachePolEntry 7 }

slbCurAcclCfgCachePolServe OBJECT-TYPE
    SYNTAX  INTEGER {
        clnthdr(1),
        refresh(2),
        cache(3)
        }
    MAX-ACCESS  read-only
    STATUS  current
    DESCRIPTION
        "Cache behavior when serving clients with objects."
    ::= { slbCurAcclCfgCachePolEntry 8 }

slbCurAcclCfgCachePolQuery OBJECT-TYPE
    SYNTAX  INTEGER {
        consider(1),
        ignore(2)
        }
    MAX-ACCESS  read-only
    STATUS  current
    DESCRIPTION
        "Specifies whether query parameters added to object URL should be considered when storing/serving object from cache."
    ::= { slbCurAcclCfgCachePolEntry 9 }

slbCurAcclCfgCachePolBrowser OBJECT-TYPE
    SYNTAX  INTEGER {
        enabled(1),
        disabled(2)
        }
    MAX-ACCESS  read-only
    STATUS  current
    DESCRIPTION
        "Optimize browser cache."
    ::= { slbCurAcclCfgCachePolEntry 10 }

slbCurAcclCfgCachePolAdminStatus OBJECT-TYPE
    SYNTAX  INTEGER {
        enabled(1),
        disabled(2)
        }
    MAX-ACCESS  read-only
    STATUS  current
    DESCRIPTION
        "Status (enable/disable) of caching policy."
    ::= { slbCurAcclCfgCachePolEntry 11 }

slbNewAcclCfgCachePolTable OBJECT-TYPE
    SYNTAX  SEQUENCE OF SlbNewAcclCfgCachePolEntry
    MAX-ACCESS  not-accessible
    STATUS  current
    DESCRIPTION
        "The table for configuring caching policy."
    ::= { caching 6 }

slbNewAcclCfgCachePolEntry OBJECT-TYPE
    SYNTAX  SlbNewAcclCfgCachePolEntry
    MAX-ACCESS  not-accessible
    STATUS  current
    DESCRIPTION
        "A row in the caching policy table."
    INDEX   { slbNewAcclCfgCachePolNameIdIndex }
    ::= { slbNewAcclCfgCachePolTable 1 }

SlbNewAcclCfgCachePolEntry ::= SEQUENCE {
    slbNewAcclCfgCachePolNameIdIndex          DisplayString,
    slbNewAcclCfgCachePolName                 DisplayString,
    slbNewAcclCfgCachePolExpireTime           INTEGER,
    slbNewAcclCfgCachePolMinSize              INTEGER,
    slbNewAcclCfgCachePolMaxSize              INTEGER,
    slbNewAcclCfgCachePolURLList              DisplayString,
    slbNewAcclCfgCachePolStore                INTEGER,
    slbNewAcclCfgCachePolServe                INTEGER,
    slbNewAcclCfgCachePolQuery                INTEGER,
    slbNewAcclCfgCachePolBrowser              INTEGER,
    slbNewAcclCfgCachePolAdminStatus          INTEGER,
    slbNewAcclCfgCachePolDelete               INTEGER
    }

slbNewAcclCfgCachePolNameIdIndex OBJECT-TYPE
    SYNTAX   DisplayString (SIZE (0..31))
    MAX-ACCESS  read-only
    STATUS  current
    DESCRIPTION
        "The caching policy ID(key id) as an index, length of the string should be 32 charecters."
    ::= { slbNewAcclCfgCachePolEntry 1 }

slbNewAcclCfgCachePolName OBJECT-TYPE
    SYNTAX   DisplayString (SIZE (0..31))
    MAX-ACCESS  read-create
    STATUS  current
    DESCRIPTION
        "Cache policy name, length of the string should be 32 charecters."
    ::= { slbNewAcclCfgCachePolEntry 2 }

slbNewAcclCfgCachePolExpireTime OBJECT-TYPE
    SYNTAX  INTEGER
    MAX-ACCESS  read-create
    STATUS  current
    DESCRIPTION
        "Set maximum expiration time, Range is 60- 43,200,000 seconds (~500 days)."
    ::= { slbNewAcclCfgCachePolEntry 3 }

slbNewAcclCfgCachePolMinSize OBJECT-TYPE
    SYNTAX  INTEGER
    MAX-ACCESS  read-create
    STATUS  current
    DESCRIPTION
        "Minimum Object size to be stored [Bytes], Values: 1-65536."
    ::= { slbNewAcclCfgCachePolEntry 4 }

slbNewAcclCfgCachePolMaxSize OBJECT-TYPE
    SYNTAX  INTEGER
    MAX-ACCESS  read-create
    STATUS  current
    DESCRIPTION
        "Maximum Object size to be stored [Bytes], Values: 1-512000000."
    ::= { slbNewAcclCfgCachePolEntry 5 }

slbNewAcclCfgCachePolURLList OBJECT-TYPE
    SYNTAX   DisplayString (SIZE (0..31))
    MAX-ACCESS  read-create
    STATUS  current
    DESCRIPTION
        "URL list to be associated with this policy, Values: 1-32 character string."
    ::= { slbNewAcclCfgCachePolEntry 6 }

slbNewAcclCfgCachePolStore OBJECT-TYPE
    SYNTAX  INTEGER {
        srvrhdr(1),
        cacheall(2)
        }
    MAX-ACCESS  read-create
    STATUS  current
    DESCRIPTION
        "Define caching behavior for storing New objects in cache."
    ::= { slbNewAcclCfgCachePolEntry 7 }

slbNewAcclCfgCachePolServe OBJECT-TYPE
    SYNTAX  INTEGER {
        clnthdr(1),
        refresh(2),
        cache(3)
        }
    MAX-ACCESS  read-create
    STATUS  current
    DESCRIPTION
        "Define cache behavior when serving clients with objects."
    ::= { slbNewAcclCfgCachePolEntry 8 }

slbNewAcclCfgCachePolQuery OBJECT-TYPE
    SYNTAX  INTEGER {
        consider(1),
        ignore(2)
        }
    MAX-ACCESS  read-create
    STATUS  current
    DESCRIPTION
        "Specifies whether query parameters added to object URL should be considered when storing/serving object from cache."
    ::= { slbNewAcclCfgCachePolEntry 9 }

slbNewAcclCfgCachePolBrowser OBJECT-TYPE
    SYNTAX  INTEGER {
        enabled(1),
        disabled(2)
        }
    MAX-ACCESS  read-create
    STATUS  current
    DESCRIPTION
        "Optimize browser cache."
    ::= { slbNewAcclCfgCachePolEntry 10 }

slbNewAcclCfgCachePolAdminStatus OBJECT-TYPE
    SYNTAX  INTEGER {
        enabled(1),
        disabled(2)
        }
    MAX-ACCESS  read-create
    STATUS  current
    DESCRIPTION
        "Enable or disable caching policy."
    ::= { slbNewAcclCfgCachePolEntry 11 }

slbNewAcclCfgCachePolDelete OBJECT-TYPE
    SYNTAX  INTEGER {
        other(1),
        delete(2)
        }
    MAX-ACCESS  read-create
    STATUS  current
    DESCRIPTION
        "Delete Caching policy."
    ::= { slbNewAcclCfgCachePolEntry 12 }

slbCurAcclCfgCacheUrlListTable OBJECT-TYPE
    SYNTAX  SEQUENCE OF SlbCurAcclCfgCacheUrlListEntry
    MAX-ACCESS  not-accessible
    STATUS  current
    DESCRIPTION
        "The table for configuring caching URL LIST."
    ::= { caching 7 }

slbCurAcclCfgCacheUrlListEntry OBJECT-TYPE
    SYNTAX  SlbCurAcclCfgCacheUrlListEntry
    MAX-ACCESS  not-accessible
    STATUS  current
    DESCRIPTION
        "A row in the caching URL LIST table."
    INDEX   { slbCurAcclCfgCacheUrlListIdIndex }
    ::= { slbCurAcclCfgCacheUrlListTable 1 }

SlbCurAcclCfgCacheUrlListEntry ::= SEQUENCE {
    slbCurAcclCfgCacheUrlListIdIndex          DisplayString,
    slbCurAcclCfgCacheUrlListName             DisplayString,
    slbCurAcclCfgCacheUrlListAdminStatus          INTEGER
    }

slbCurAcclCfgCacheUrlListIdIndex OBJECT-TYPE
    SYNTAX   DisplayString (SIZE (0..31))
    MAX-ACCESS  read-only
    STATUS  current
    DESCRIPTION
        "The caching policy URL LIST (key id) as an index."
    ::= { slbCurAcclCfgCacheUrlListEntry 1 }

slbCurAcclCfgCacheUrlListName OBJECT-TYPE
    SYNTAX   DisplayString (SIZE (0..31))
    MAX-ACCESS  read-only
    STATUS  current
    DESCRIPTION
        "Cache URL LIST name."
    ::= { slbCurAcclCfgCacheUrlListEntry 2 }

slbCurAcclCfgCacheUrlListAdminStatus OBJECT-TYPE
    SYNTAX  INTEGER {
        enabled(1),
        disabled(2)
        }
    MAX-ACCESS  read-only
    STATUS  current
    DESCRIPTION
        "Status (enable/disable) of caching URL LIST."
    ::= { slbCurAcclCfgCacheUrlListEntry 3 }

slbNewAcclCfgCacheUrlListTable OBJECT-TYPE
    SYNTAX  SEQUENCE OF SlbNewAcclCfgCacheUrlListEntry
    MAX-ACCESS  not-accessible
    STATUS  current
    DESCRIPTION
        "The table for configuring caching URL LIST."
    ::= { caching 8 }

slbNewAcclCfgCacheUrlListEntry OBJECT-TYPE
    SYNTAX  SlbNewAcclCfgCacheUrlListEntry
    MAX-ACCESS  not-accessible
    STATUS  current
    DESCRIPTION
        "A row in the caching URL LIST table."
    INDEX   { slbNewAcclCfgCacheUrlListIdIndex }
    ::= { slbNewAcclCfgCacheUrlListTable 1 }

SlbNewAcclCfgCacheUrlListEntry ::= SEQUENCE {
    slbNewAcclCfgCacheUrlListIdIndex          DisplayString,
    slbNewAcclCfgCacheUrlListName             DisplayString,
    slbNewAcclCfgCacheUrlListAdminStatus      INTEGER,
    slbNewAcclCfgCacheUrlListDel              INTEGER,
    slbNewAcclCfgCacheUrlListCopy             DisplayString
    }

slbNewAcclCfgCacheUrlListIdIndex OBJECT-TYPE
    SYNTAX   DisplayString (SIZE (0..31))
    MAX-ACCESS  read-only
    STATUS  current
    DESCRIPTION
        "The caching policy URL LIST (key id) as an index."
    ::= { slbNewAcclCfgCacheUrlListEntry 1 }

slbNewAcclCfgCacheUrlListName OBJECT-TYPE
    SYNTAX   DisplayString (SIZE (0..31))
    MAX-ACCESS  read-create
    STATUS  current
    DESCRIPTION
        "Cache URL LIST name."
    ::= { slbNewAcclCfgCacheUrlListEntry 2 }

slbNewAcclCfgCacheUrlListAdminStatus OBJECT-TYPE
    SYNTAX  INTEGER {
        enabled(1),
        disabled(2)
        }
    MAX-ACCESS  read-create
    STATUS  current
    DESCRIPTION
        "Status (enable/disable) of caching URL LIST."
    ::= { slbNewAcclCfgCacheUrlListEntry 3 }

slbNewAcclCfgCacheUrlListDel OBJECT-TYPE
    SYNTAX  INTEGER {
        other(1),
        delete(2)
        }
    MAX-ACCESS  read-create
    STATUS  current
    DESCRIPTION
        "Delete Caching URL list."
    ::= { slbNewAcclCfgCacheUrlListEntry 5 }

slbNewAcclCfgCacheUrlListCopy OBJECT-TYPE
    SYNTAX   DisplayString
    MAX-ACCESS  read-create
    STATUS  current
    DESCRIPTION
        "Duplicating an entire Rule-List by defining the destination Rule-list id."
    ::= { slbNewAcclCfgCacheUrlListEntry 6 }

slbCurAcclCfgCacheUrlRuleTable OBJECT-TYPE
    SYNTAX  SEQUENCE OF SlbCurAcclCfgCacheUrlRuleEntry
    MAX-ACCESS  not-accessible
    STATUS  current
    DESCRIPTION
        "The table for configuring caching URL Rules."
    ::= { caching 9 }

slbCurAcclCfgCacheUrlRuleEntry OBJECT-TYPE
    SYNTAX  SlbCurAcclCfgCacheUrlRuleEntry
    MAX-ACCESS  not-accessible
    STATUS  current
    DESCRIPTION
        "A row in the caching URL Rule table."
    INDEX   { slbCurAcclCfgCacheUrlRuleListIdIndex, slbCurAcclCfgCacheUrlRuleIndex }
    ::= { slbCurAcclCfgCacheUrlRuleTable 1 }

SlbCurAcclCfgCacheUrlRuleEntry ::= SEQUENCE {
    slbCurAcclCfgCacheUrlRuleListIdIndex          DisplayString,
    slbCurAcclCfgCacheUrlRuleIndex                INTEGER,
    slbCurAcclCfgCacheUrlRuleName                 DisplayString,
    slbCurAcclCfgCacheUrlRuleDomainM              INTEGER,
    slbCurAcclCfgCacheUrlRuleDomain               DisplayString,
    slbCurAcclCfgCacheUrlRuleURLm                 INTEGER,
    slbCurAcclCfgCacheUrlRuleURL                  DisplayString,
    slbCurAcclCfgCacheUrlRuleExpire               INTEGER,
    slbCurAcclCfgCacheUrlRuleCache                INTEGER,
    slbCurAcclCfgCacheUrlRuleAdminStatus          INTEGER
    }

slbCurAcclCfgCacheUrlRuleListIdIndex OBJECT-TYPE
    SYNTAX   DisplayString (SIZE (0..31))
    MAX-ACCESS  read-only
    STATUS  current
    DESCRIPTION
        "The caching policy URL LIST (key id) as an index."
    ::= { slbCurAcclCfgCacheUrlRuleEntry 1 }

slbCurAcclCfgCacheUrlRuleIndex OBJECT-TYPE
    SYNTAX   INTEGER
    MAX-ACCESS  read-only
    STATUS  current
    DESCRIPTION
        "The caching URL Rule number as an index."
    ::= { slbCurAcclCfgCacheUrlRuleEntry 2 }

slbCurAcclCfgCacheUrlRuleName OBJECT-TYPE
    SYNTAX   DisplayString (SIZE (0..31))
    MAX-ACCESS  read-only
    STATUS  current
    DESCRIPTION
        "The caching URL Rule name."
    ::= { slbCurAcclCfgCacheUrlRuleEntry 3 }

slbCurAcclCfgCacheUrlRuleDomainM OBJECT-TYPE
    SYNTAX  INTEGER {
        any(1),
        text(2),
        regex(3)
        }
    MAX-ACCESS  read-only
    STATUS  current
    DESCRIPTION
        "Defines whether Domain matching should be evaluated as String, Regex or match, any (default any)."
    ::= { slbCurAcclCfgCacheUrlRuleEntry 4 }

slbCurAcclCfgCacheUrlRuleDomain OBJECT-TYPE
    SYNTAX   DisplayString (SIZE (0..255))
    MAX-ACCESS  read-only
    STATUS  current
    DESCRIPTION
        "Defines the Virtual Host for which this rule applies."
    ::= { slbCurAcclCfgCacheUrlRuleEntry 5 }

slbCurAcclCfgCacheUrlRuleURLm OBJECT-TYPE
    SYNTAX  INTEGER {
        any(1),
        text(2),
        regex(3)
        }
    MAX-ACCESS  read-only
    STATUS  current
    DESCRIPTION
        "Defines whether URL matching should be evaluated as String, Regex or match, any (default any)."
    ::= { slbCurAcclCfgCacheUrlRuleEntry 6 }

slbCurAcclCfgCacheUrlRuleURL OBJECT-TYPE
    SYNTAX   DisplayString 
    MAX-ACCESS  read-only
    STATUS  current
    DESCRIPTION
        "Defines URL of specific object (file/folder) to be matched by this rule."
    ::= { slbCurAcclCfgCacheUrlRuleEntry 7 }

slbCurAcclCfgCacheUrlRuleExpire OBJECT-TYPE
    SYNTAX   INTEGER
    MAX-ACCESS  read-only
    STATUS  current
    DESCRIPTION
        "The Maximum time for the cache object to served from cache (in seconds)."
    ::= { slbCurAcclCfgCacheUrlRuleEntry 8 }

slbCurAcclCfgCacheUrlRuleCache OBJECT-TYPE
    SYNTAX  INTEGER {
        enabled(1),
        disabled(2)
        }
    MAX-ACCESS  read-only
    STATUS  current
    DESCRIPTION
        "Defines if the matched response should be cached or not."
    ::= { slbCurAcclCfgCacheUrlRuleEntry 9 }

slbCurAcclCfgCacheUrlRuleAdminStatus OBJECT-TYPE
    SYNTAX  INTEGER {
        enabled(1),
        disabled(2)
        }
    MAX-ACCESS  read-only
    STATUS  current
    DESCRIPTION
        "Status (enable/disable) of caching URL Rule."
    ::= { slbCurAcclCfgCacheUrlRuleEntry 10 }

slbNewAcclCfgCacheUrlRuleTable OBJECT-TYPE
    SYNTAX  SEQUENCE OF SlbNewAcclCfgCacheUrlRuleEntry
    MAX-ACCESS  not-accessible
    STATUS  current
    DESCRIPTION
        "The table for configuring caching URL Rules."
    ::= { caching 10 }

slbNewAcclCfgCacheUrlRuleEntry OBJECT-TYPE
    SYNTAX  SlbNewAcclCfgCacheUrlRuleEntry
    MAX-ACCESS  not-accessible
    STATUS  current
    DESCRIPTION
        "A row in the caching URL Rule table."
    INDEX   { slbNewAcclCfgCacheUrlRuleListIdIndex, slbNewAcclCfgCacheUrlRuleIndex }
    ::= { slbNewAcclCfgCacheUrlRuleTable 1 }

SlbNewAcclCfgCacheUrlRuleEntry ::= SEQUENCE {
    slbNewAcclCfgCacheUrlRuleListIdIndex          DisplayString,
    slbNewAcclCfgCacheUrlRuleIndex                INTEGER,
    slbNewAcclCfgCacheUrlRuleName                 DisplayString,
    slbNewAcclCfgCacheUrlRuleDomainM              INTEGER,
    slbNewAcclCfgCacheUrlRuleDomain               DisplayString,
    slbNewAcclCfgCacheUrlRuleURLm                 INTEGER,
    slbNewAcclCfgCacheUrlRuleURL                  DisplayString,
    slbNewAcclCfgCacheUrlRuleExpire               INTEGER,
    slbNewAcclCfgCacheUrlRuleCache                INTEGER,
    slbNewAcclCfgCacheUrlRuleAdminStatus          INTEGER,
    slbNewAcclCfgCacheUrlRuleDelete               INTEGER,
    slbNewAcclCfgCacheUrlRuleCopy                 INTEGER 
    }

slbNewAcclCfgCacheUrlRuleListIdIndex OBJECT-TYPE
    SYNTAX   DisplayString (SIZE (0..31))
    MAX-ACCESS  read-only
    STATUS  current
    DESCRIPTION
        "The caching policy URL LIST (key id) as an index."
    ::= { slbNewAcclCfgCacheUrlRuleEntry 1 }

slbNewAcclCfgCacheUrlRuleIndex OBJECT-TYPE
    SYNTAX   INTEGER
    MAX-ACCESS  read-only
    STATUS  current
    DESCRIPTION
        "The caching URL Rule number as an index."
    ::= { slbNewAcclCfgCacheUrlRuleEntry 2 }

slbNewAcclCfgCacheUrlRuleName OBJECT-TYPE
    SYNTAX   DisplayString (SIZE (0..31))
    MAX-ACCESS  read-create
    STATUS  current
    DESCRIPTION
        "The caching URL Rule name."
    ::= { slbNewAcclCfgCacheUrlRuleEntry 3 }

slbNewAcclCfgCacheUrlRuleDomainM OBJECT-TYPE
    SYNTAX  INTEGER {
        any(1),
        text(2),
        regex(3)
        }
    MAX-ACCESS  read-create
    STATUS  current
    DESCRIPTION
        "Defines whether Domain matching should be evaluated as String, Regex or match, any (default any)."
    ::= { slbNewAcclCfgCacheUrlRuleEntry 4 }

slbNewAcclCfgCacheUrlRuleDomain OBJECT-TYPE
    SYNTAX   DisplayString (SIZE (0..255))
    MAX-ACCESS  read-create
    STATUS  current
    DESCRIPTION
        "Defines the Virtual Host for which this rule applies."
    ::= { slbNewAcclCfgCacheUrlRuleEntry 5 }

slbNewAcclCfgCacheUrlRuleURLm OBJECT-TYPE
    SYNTAX  INTEGER {
        any(1),
        text(2),
        regex(3)
        }
    MAX-ACCESS  read-create
    STATUS  current
    DESCRIPTION
        "Defines whether URL matching should be evaluated as String, Regex or match, any (default any)."
    ::= { slbNewAcclCfgCacheUrlRuleEntry 6 }

slbNewAcclCfgCacheUrlRuleURL OBJECT-TYPE
    SYNTAX   DisplayString  
    MAX-ACCESS  read-create
    STATUS  current
    DESCRIPTION
        "Defines URL of specific object (file/folder) to be matched by this rule."
    ::= { slbNewAcclCfgCacheUrlRuleEntry 7 }

slbNewAcclCfgCacheUrlRuleExpire OBJECT-TYPE
    SYNTAX   INTEGER
    MAX-ACCESS  read-create
    STATUS  current
    DESCRIPTION
        "The Maximum time for the cache object to served from cache (in seconds)."
    ::= { slbNewAcclCfgCacheUrlRuleEntry 8 }

slbNewAcclCfgCacheUrlRuleCache OBJECT-TYPE
    SYNTAX  INTEGER {
        enabled(1),
        disabled(2)
        }
    MAX-ACCESS  read-create
    STATUS  current
    DESCRIPTION
        "Defines if the matched response should be cached or not."
    ::= { slbNewAcclCfgCacheUrlRuleEntry 9 }

slbNewAcclCfgCacheUrlRuleAdminStatus OBJECT-TYPE
    SYNTAX  INTEGER {
        enabled(1),
        disabled(2)
        }
    MAX-ACCESS  read-create
    STATUS  current
    DESCRIPTION
        "Status (enable/disable) of caching URL Rule."
    ::= { slbNewAcclCfgCacheUrlRuleEntry 10 }

slbNewAcclCfgCacheUrlRuleDelete OBJECT-TYPE
    SYNTAX  INTEGER {
        other(1),
        delete(2)
        }
    MAX-ACCESS  read-create
    STATUS  current
    DESCRIPTION
        "By setting the value to delete(2), the entire row is deleted."
    ::= { slbNewAcclCfgCacheUrlRuleEntry 11 }

slbNewAcclCfgCacheUrlRuleCopy OBJECT-TYPE
    SYNTAX   INTEGER 
    MAX-ACCESS  read-create
    STATUS  current
    DESCRIPTION
        "Copy rule to another index in the same rule-list. When read,
         zero is returned."
    ::= { slbNewAcclCfgCacheUrlRuleEntry 12 }

slbCurAcclCfgCompOnOff OBJECT-TYPE
   SYNTAX  INTEGER {
       on(1),
       off(2)
       }
   MAX-ACCESS  read-only
   STATUS  current
   DESCRIPTION
       "Globally ON or OFF of compression."
   ::= { compression 1}

slbNewAcclCfgCompOnOff OBJECT-TYPE
   SYNTAX  INTEGER {
       on(1),
       off(2)
       }
   MAX-ACCESS  read-write
   STATUS  current
   DESCRIPTION
       "Globally ON or OFF of compression."
   ::= { compression 2}

slbCurAcclCfgCompPolTable OBJECT-TYPE
    SYNTAX  SEQUENCE OF SlbCurAcclCfgCompPolEntry
    MAX-ACCESS  not-accessible
    STATUS  current
    DESCRIPTION
        "The table for configuring compression policy."
    ::= { compression 3 }

slbCurAcclCfgCompPolEntry OBJECT-TYPE
    SYNTAX  SlbCurAcclCfgCompPolEntry
    MAX-ACCESS  not-accessible
    STATUS  current
    DESCRIPTION
        "A row in the compression policy table."
    INDEX   { slbCurAcclCfgCompPolNameIdIndex }
    ::= { slbCurAcclCfgCompPolTable 1 }

SlbCurAcclCfgCompPolEntry ::= SEQUENCE {
    slbCurAcclCfgCompPolNameIdIndex          DisplayString,
    slbCurAcclCfgCompPolName                 DisplayString,
    slbCurAcclCfgCompPolAlgrthm              INTEGER,
    slbCurAcclCfgCompPolComplv1              INTEGER,
    slbCurAcclCfgCompPolMinSize              INTEGER,
    slbCurAcclCfgCompPolMaxSize              INTEGER,
    slbCurAcclCfgCompPolURLList              DisplayString,
    slbCurAcclCfgCompPolBrwsList             DisplayString,
    slbCurAcclCfgCompPolPreDefBrwsRuleList   INTEGER,
    slbCurAcclCfgCompPolCompsrv              INTEGER,
    slbCurAcclCfgCompPolAdminStatus          INTEGER
    }

slbCurAcclCfgCompPolNameIdIndex OBJECT-TYPE
    SYNTAX   DisplayString (SIZE (0..31))
    MAX-ACCESS  read-only
    STATUS  current
    DESCRIPTION
        "The compression policy ID(key id) as an index."
    ::= { slbCurAcclCfgCompPolEntry 1 }

slbCurAcclCfgCompPolName OBJECT-TYPE
    SYNTAX   DisplayString (SIZE (0..31))
    MAX-ACCESS  read-only
    STATUS  current
    DESCRIPTION
        "Compression policy name."
    ::= { slbCurAcclCfgCompPolEntry 2 }

slbCurAcclCfgCompPolAlgrthm OBJECT-TYPE
    SYNTAX  INTEGER {
        gzip(1),
        deflate(2)
        }
    MAX-ACCESS  read-only
    STATUS  current
    DESCRIPTION
        "Preferred compression algorithm."
    ::= { slbCurAcclCfgCompPolEntry 3 }

slbCurAcclCfgCompPolComplv1 OBJECT-TYPE
    SYNTAX  INTEGER (1..9)
    MAX-ACCESS  read-only
    STATUS  current
    DESCRIPTION
        "Compression level."
    ::= { slbCurAcclCfgCompPolEntry 4 }

slbCurAcclCfgCompPolMinSize OBJECT-TYPE
    SYNTAX  INTEGER (1..65535)
    MAX-ACCESS  read-only
    STATUS  current
    DESCRIPTION
        "Minimum file size to be compressed [Byte]."
    ::= { slbCurAcclCfgCompPolEntry 5 }

slbCurAcclCfgCompPolMaxSize OBJECT-TYPE
    SYNTAX  INTEGER
    MAX-ACCESS  read-only
    STATUS  current
    DESCRIPTION
        "Maximum file size to be compressed [Byte]."
    ::= { slbCurAcclCfgCompPolEntry 6 }

slbCurAcclCfgCompPolURLList OBJECT-TYPE
    SYNTAX   DisplayString (SIZE (0..31))
    MAX-ACCESS  read-only
    STATUS  current
    DESCRIPTION
        "URL list which is associated with this policy."
    ::= { slbCurAcclCfgCompPolEntry 7 }

slbCurAcclCfgCompPolBrwsList OBJECT-TYPE
    SYNTAX   DisplayString (SIZE (0..31))
    MAX-ACCESS  read-only
    STATUS  current
    DESCRIPTION
        "Browser list which is associated with this policy."
    ::= { slbCurAcclCfgCompPolEntry 8 }

slbCurAcclCfgCompPolPreDefBrwsRuleList OBJECT-TYPE
    SYNTAX  INTEGER {
        enabled(1),
        disabled(2)
        }
    MAX-ACCESS  read-only
    STATUS  current
    DESCRIPTION
        "Enable/Disable predefined browser exceptions rule-list."
    ::= { slbCurAcclCfgCompPolEntry 9 }

slbCurAcclCfgCompPolCompsrv OBJECT-TYPE
    SYNTAX  INTEGER {
        enabled(1),
        disabled(2)
        }
    MAX-ACCESS  read-only
    STATUS  current
    DESCRIPTION
        "Enable/Disable compression by real server."
    ::= { slbCurAcclCfgCompPolEntry 10 }

slbCurAcclCfgCompPolAdminStatus OBJECT-TYPE
    SYNTAX  INTEGER {
        enabled(1),
        disabled(2)
        }
    MAX-ACCESS  read-only
    STATUS  current
    DESCRIPTION
        "Status (enable/disable) of compression policy."
    ::= { slbCurAcclCfgCompPolEntry 11 }

slbNewAcclCfgCompPolTable OBJECT-TYPE
    SYNTAX  SEQUENCE OF SlbNewAcclCfgCompPolEntry
    MAX-ACCESS  not-accessible
    STATUS  current
    DESCRIPTION
        "The table for configuring compression policy."
    ::= { compression 4 }

slbNewAcclCfgCompPolEntry OBJECT-TYPE
    SYNTAX  SlbNewAcclCfgCompPolEntry
    MAX-ACCESS  not-accessible
    STATUS  current
    DESCRIPTION
        "A row in the compression policy table."
    INDEX   { slbNewAcclCfgCompPolNameIdIndex }
    ::= { slbNewAcclCfgCompPolTable 1 }

SlbNewAcclCfgCompPolEntry ::= SEQUENCE {
    slbNewAcclCfgCompPolNameIdIndex          DisplayString,
    slbNewAcclCfgCompPolName                 DisplayString,
    slbNewAcclCfgCompPolAlgrthm              INTEGER,
    slbNewAcclCfgCompPolComplv1              INTEGER,
    slbNewAcclCfgCompPolMinSize              INTEGER,
    slbNewAcclCfgCompPolMaxSize              INTEGER,
    slbNewAcclCfgCompPolURLList              DisplayString,
    slbNewAcclCfgCompPolBrwsList             DisplayString,
    slbNewAcclCfgCompPolPreDefBrwsRuleList   INTEGER,
    slbNewAcclCfgCompPolCompsrv              INTEGER,
    slbNewAcclCfgCompPolAdminStatus          INTEGER,
    slbNewAcclCfgCompPolDelete               INTEGER
    }

slbNewAcclCfgCompPolNameIdIndex OBJECT-TYPE
    SYNTAX   DisplayString (SIZE (0..31))
    MAX-ACCESS  read-only
    STATUS  current
    DESCRIPTION
        "The compression policy ID(key id) as an index."
    ::= { slbNewAcclCfgCompPolEntry 1 }

slbNewAcclCfgCompPolName OBJECT-TYPE
    SYNTAX   DisplayString (SIZE (0..31))
    MAX-ACCESS  read-create
    STATUS  current
    DESCRIPTION
        "Compression policy name."
    ::= { slbNewAcclCfgCompPolEntry 2 }

slbNewAcclCfgCompPolAlgrthm OBJECT-TYPE
    SYNTAX  INTEGER {
        gzip(1),
        deflate(2)
        }
    MAX-ACCESS  read-create
    STATUS  current
    DESCRIPTION
        "Preferred compression algorithm."
    ::= { slbNewAcclCfgCompPolEntry 3 }

slbNewAcclCfgCompPolComplv1 OBJECT-TYPE
    SYNTAX  INTEGER (1..9)
    MAX-ACCESS  read-create
    STATUS  current
    DESCRIPTION
        "Compression level."
    ::= { slbNewAcclCfgCompPolEntry 4 }

slbNewAcclCfgCompPolMinSize OBJECT-TYPE
    SYNTAX  INTEGER (1..65535)
    MAX-ACCESS  read-create
    STATUS  current
    DESCRIPTION
        "Minimum file size to be compressed [Byte]."
    ::= { slbNewAcclCfgCompPolEntry 5 }

slbNewAcclCfgCompPolMaxSize OBJECT-TYPE
    SYNTAX  INTEGER
    MAX-ACCESS  read-create
    STATUS  current
    DESCRIPTION
        "Maximum file size to be compressed [Byte], Values: 1-2000000000, 0-Unlimited "
    ::= { slbNewAcclCfgCompPolEntry 6 }

slbNewAcclCfgCompPolURLList OBJECT-TYPE
    SYNTAX   DisplayString (SIZE (0..31))
    MAX-ACCESS  read-create
    STATUS  current
    DESCRIPTION
        "URL list which is associated with this policy."
    ::= { slbNewAcclCfgCompPolEntry 7 }

slbNewAcclCfgCompPolBrwsList OBJECT-TYPE
    SYNTAX   DisplayString (SIZE (0..31))
    MAX-ACCESS  read-create
    STATUS  current
    DESCRIPTION
        "Browser list which is associated with this policy."
    ::= { slbNewAcclCfgCompPolEntry 8 }

slbNewAcclCfgCompPolPreDefBrwsRuleList OBJECT-TYPE
    SYNTAX  INTEGER {
        enabled(1),
        disabled(2)
        }
    MAX-ACCESS  read-create
    STATUS  current
    DESCRIPTION
        "Enable/Disable predefined browser exceptions rule-list."
    ::= { slbNewAcclCfgCompPolEntry 9 }

slbNewAcclCfgCompPolCompsrv OBJECT-TYPE
    SYNTAX  INTEGER {
        enabled(1),
        disabled(2)
        }
    MAX-ACCESS  read-create
    STATUS  current
    DESCRIPTION
        "Enable/Disable compression by real server."
    ::= { slbNewAcclCfgCompPolEntry 10 }

slbNewAcclCfgCompPolAdminStatus OBJECT-TYPE
    SYNTAX  INTEGER {
        enabled(1),
        disabled(2)
        }
    MAX-ACCESS  read-create
    STATUS  current
    DESCRIPTION
        "Status (enable/disable) of compression policy."
    ::= { slbNewAcclCfgCompPolEntry 11 }

slbNewAcclCfgCompPolDelete OBJECT-TYPE
    SYNTAX  INTEGER {
        other(1),
        delete(2)
        }
    MAX-ACCESS  read-create
    STATUS  current
    DESCRIPTION
        "Delete compression policy."
    ::= { slbNewAcclCfgCompPolEntry 12 }

slbCurAcclCfgCompUrlListTable OBJECT-TYPE
    SYNTAX  SEQUENCE OF SlbCurAcclCfgCompUrlListEntry
    MAX-ACCESS  not-accessible
    STATUS  current
    DESCRIPTION
        "The table for configuring compression URL LIST."
    ::= { compression 5 }

slbCurAcclCfgCompUrlListEntry OBJECT-TYPE
    SYNTAX  SlbCurAcclCfgCompUrlListEntry
    MAX-ACCESS  not-accessible
    STATUS  current
    DESCRIPTION
        "A row in the compression URL LIST table."
    INDEX   { slbCurAcclCfgCompUrlListIdIndex }
    ::= { slbCurAcclCfgCompUrlListTable 1 }

SlbCurAcclCfgCompUrlListEntry ::= SEQUENCE {
    slbCurAcclCfgCompUrlListIdIndex          DisplayString,
    slbCurAcclCfgCompUrlListName             DisplayString,
    slbCurAcclCfgCompUrlListAdminStatus      INTEGER
    }

slbCurAcclCfgCompUrlListIdIndex OBJECT-TYPE
    SYNTAX   DisplayString (SIZE (0..31))
    MAX-ACCESS  read-only
    STATUS  current
    DESCRIPTION
        "The compression policy URL LIST (key id) as an index."
    ::= { slbCurAcclCfgCompUrlListEntry 1 }

slbCurAcclCfgCompUrlListName OBJECT-TYPE
    SYNTAX   DisplayString (SIZE (0..31))
    MAX-ACCESS  read-only
    STATUS  current
    DESCRIPTION
        "Compression URL LIST name."
    ::= { slbCurAcclCfgCompUrlListEntry 2 }

slbCurAcclCfgCompUrlListAdminStatus OBJECT-TYPE
    SYNTAX  INTEGER {
        enabled(1),
        disabled(2)
        }
    MAX-ACCESS  read-only
    STATUS  current
    DESCRIPTION
        "Status (enable/disable) of compression URL LIST."
    ::= { slbCurAcclCfgCompUrlListEntry 3 }


slbNewAcclCfgCompUrlListTable OBJECT-TYPE
    SYNTAX  SEQUENCE OF SlbNewAcclCfgCompUrlListEntry
    MAX-ACCESS  not-accessible
    STATUS  current
    DESCRIPTION
        "The table for configuring compression URL LIST."
    ::= { compression 6 }

slbNewAcclCfgCompUrlListEntry OBJECT-TYPE
    SYNTAX  SlbNewAcclCfgCompUrlListEntry
    MAX-ACCESS  not-accessible
    STATUS  current
    DESCRIPTION
        "A row in the compression URL LIST table."
    INDEX   { slbNewAcclCfgCompUrlListIdIndex }
    ::= { slbNewAcclCfgCompUrlListTable 1 }

SlbNewAcclCfgCompUrlListEntry ::= SEQUENCE {
    slbNewAcclCfgCompUrlListIdIndex          DisplayString,
    slbNewAcclCfgCompUrlListName             DisplayString,
    slbNewAcclCfgCompUrlListAdminStatus      INTEGER,
    slbNewAcclCfgCompUrlListDel              INTEGER,
    slbNewAcclCfgCompUrlListCopy             DisplayString
    }

slbNewAcclCfgCompUrlListIdIndex OBJECT-TYPE
    SYNTAX   DisplayString (SIZE (0..31))
    MAX-ACCESS  read-only
    STATUS  current
    DESCRIPTION
        "The compression policy URL LIST (key id) as an index."
    ::= { slbNewAcclCfgCompUrlListEntry 1 }

slbNewAcclCfgCompUrlListName OBJECT-TYPE
    SYNTAX   DisplayString (SIZE (0..31))
    MAX-ACCESS  read-create
    STATUS  current
    DESCRIPTION
        "Compression URL LIST name."
    ::= { slbNewAcclCfgCompUrlListEntry 2 }

slbNewAcclCfgCompUrlListAdminStatus OBJECT-TYPE
    SYNTAX  INTEGER {
        enabled(1),
        disabled(2)
        }
    MAX-ACCESS  read-create
    STATUS  current
    DESCRIPTION
        "Status (enable/disable) of compression URL LIST."
    ::= { slbNewAcclCfgCompUrlListEntry 3 }

slbNewAcclCfgCompUrlListDel OBJECT-TYPE
    SYNTAX  INTEGER {
        other(1),
        delete(2)
        }
    MAX-ACCESS  read-create
    STATUS  current
    DESCRIPTION
        "Delete Compression URL list."
    ::= { slbNewAcclCfgCompUrlListEntry 4 }

slbNewAcclCfgCompUrlListCopy OBJECT-TYPE
    SYNTAX   DisplayString
    MAX-ACCESS  read-create
    STATUS  current
    DESCRIPTION
        "Duplicating an entire Rule-List by defining the destination Rule-list id."
    ::= { slbNewAcclCfgCompUrlListEntry 5 }

slbCurAcclCfgCompUrlRuleTable OBJECT-TYPE
    SYNTAX  SEQUENCE OF SlbCurAcclCfgCompUrlRuleEntry
    MAX-ACCESS  not-accessible
    STATUS  current
    DESCRIPTION
        "The table for configuring compression URL Rules."
    ::= { compression 7 }

slbCurAcclCfgCompUrlRuleEntry OBJECT-TYPE
    SYNTAX  SlbCurAcclCfgCompUrlRuleEntry
    MAX-ACCESS  not-accessible
    STATUS  current
    DESCRIPTION
        "A row in the compression URL Rule table."
    INDEX   { slbCurAcclCfgCompUrlRuleListIdIndex, slbCurAcclCfgCompUrlRuleIndex }
    ::= { slbCurAcclCfgCompUrlRuleTable 1 }

SlbCurAcclCfgCompUrlRuleEntry ::= SEQUENCE {
    slbCurAcclCfgCompUrlRuleListIdIndex          DisplayString,
    slbCurAcclCfgCompUrlRuleIndex                INTEGER,
    slbCurAcclCfgCompUrlRuleName                 DisplayString,
    slbCurAcclCfgCompUrlRuleDomainM              INTEGER,
    slbCurAcclCfgCompUrlRuleDomain               DisplayString,
    slbCurAcclCfgCompUrlRuleURLm                 INTEGER,
    slbCurAcclCfgCompUrlRuleURL                  DisplayString,
    slbCurAcclCfgCompUrlRuleCompress             INTEGER,
    slbCurAcclCfgCompUrlRuleAdminStatus          INTEGER
    }

slbCurAcclCfgCompUrlRuleListIdIndex OBJECT-TYPE
    SYNTAX   DisplayString (SIZE (0..31))
    MAX-ACCESS  read-only
    STATUS  current
    DESCRIPTION
        "The compression URL LIST (key id) as an index."
    ::= { slbCurAcclCfgCompUrlRuleEntry 1 }

slbCurAcclCfgCompUrlRuleIndex OBJECT-TYPE
    SYNTAX   INTEGER
    MAX-ACCESS  read-only
    STATUS  current
    DESCRIPTION
        "The compression URL Rule number as an index."
    ::= { slbCurAcclCfgCompUrlRuleEntry 2 }

slbCurAcclCfgCompUrlRuleName OBJECT-TYPE
    SYNTAX   DisplayString (SIZE (0..31))
    MAX-ACCESS  read-only
    STATUS  current
    DESCRIPTION
        "The compression URL Rule name."
    ::= { slbCurAcclCfgCompUrlRuleEntry 3 }

slbCurAcclCfgCompUrlRuleDomainM OBJECT-TYPE
    SYNTAX  INTEGER {
        any(1),
        text(2),
        regex(3)
        }
    MAX-ACCESS  read-only
    STATUS  current
    DESCRIPTION
        "Defines whether Domain matching should be evaluated as String, Regex or match, any (default any)."
    ::= { slbCurAcclCfgCompUrlRuleEntry 4 }

slbCurAcclCfgCompUrlRuleDomain OBJECT-TYPE
    SYNTAX   DisplayString (SIZE (0..255))
    MAX-ACCESS  read-only
    STATUS  current
    DESCRIPTION
        "Defines the Virtual Host for which this rule applies."
    ::= { slbCurAcclCfgCompUrlRuleEntry 5 }

slbCurAcclCfgCompUrlRuleURLm OBJECT-TYPE
    SYNTAX  INTEGER {
        any(1),
        text(2),
        regex(3)
        }
    MAX-ACCESS  read-only
    STATUS  current
    DESCRIPTION
        "Defines whether URL matching should be evaluated as String, Regex or match, any (default any)."
    ::= { slbCurAcclCfgCompUrlRuleEntry 6 }

slbCurAcclCfgCompUrlRuleURL OBJECT-TYPE
    SYNTAX   DisplayString
    MAX-ACCESS  read-only
    STATUS  current
    DESCRIPTION
        "Defines URL of specific object (file/folder) to be matched by this rule."
    ::= { slbCurAcclCfgCompUrlRuleEntry 7 }

slbCurAcclCfgCompUrlRuleCompress OBJECT-TYPE
    SYNTAX  INTEGER {
        enabled(1),
        disabled(2)
        }
    MAX-ACCESS  read-only
    STATUS  current
    DESCRIPTION
        "Enable/Disable the compression."
    ::= { slbCurAcclCfgCompUrlRuleEntry 8 }

slbCurAcclCfgCompUrlRuleAdminStatus OBJECT-TYPE
    SYNTAX  INTEGER {
        enabled(1),
        disabled(2)
        }
    MAX-ACCESS  read-only
    STATUS  current
    DESCRIPTION
        "Status (enable/disable) of compression URL Rule."
    ::= { slbCurAcclCfgCompUrlRuleEntry 9 }

slbNewAcclCfgCompUrlRuleTable OBJECT-TYPE
    SYNTAX  SEQUENCE OF SlbNewAcclCfgCompUrlRuleEntry
    MAX-ACCESS  not-accessible
    STATUS  current
    DESCRIPTION
        "The table for configuring compression URL Rules."
    ::= { compression 8 }

slbNewAcclCfgCompUrlRuleEntry OBJECT-TYPE
    SYNTAX  SlbNewAcclCfgCompUrlRuleEntry
    MAX-ACCESS  not-accessible
    STATUS  current
    DESCRIPTION
        "A row in the compression URL Rule table."
    INDEX   { slbNewAcclCfgCompUrlRuleListIdIndex, slbNewAcclCfgCompUrlRuleIndex }
    ::= { slbNewAcclCfgCompUrlRuleTable 1 }

SlbNewAcclCfgCompUrlRuleEntry ::= SEQUENCE {
    slbNewAcclCfgCompUrlRuleListIdIndex          DisplayString,
    slbNewAcclCfgCompUrlRuleIndex                INTEGER,
    slbNewAcclCfgCompUrlRuleName                 DisplayString,
    slbNewAcclCfgCompUrlRuleDomainM              INTEGER,
    slbNewAcclCfgCompUrlRuleDomain               DisplayString,
    slbNewAcclCfgCompUrlRuleURLm                 INTEGER,
    slbNewAcclCfgCompUrlRuleURL                  DisplayString,
    slbNewAcclCfgCompUrlRuleCompress             INTEGER,
    slbNewAcclCfgCompUrlRuleAdminStatus          INTEGER,
    slbNewAcclCfgCompUrlRuleDelete               INTEGER,
    slbNewAcclCfgCompUrlRuleCopy                 DisplayString
    }

slbNewAcclCfgCompUrlRuleListIdIndex OBJECT-TYPE
    SYNTAX   DisplayString (SIZE (0..31))
    MAX-ACCESS  read-only
    STATUS  current
    DESCRIPTION
        "The compression URL LIST (key id) as an index."
    ::= { slbNewAcclCfgCompUrlRuleEntry 1 }

slbNewAcclCfgCompUrlRuleIndex OBJECT-TYPE
    SYNTAX   INTEGER
    MAX-ACCESS  read-only
    STATUS  current
    DESCRIPTION
        "The compression URL Rule number as an index."
    ::= { slbNewAcclCfgCompUrlRuleEntry 2 }

slbNewAcclCfgCompUrlRuleName OBJECT-TYPE
    SYNTAX   DisplayString (SIZE (0..31))
    MAX-ACCESS  read-create
    STATUS  current
    DESCRIPTION
        "The compression URL Rule name."
    ::= { slbNewAcclCfgCompUrlRuleEntry 3 }

slbNewAcclCfgCompUrlRuleDomainM OBJECT-TYPE
    SYNTAX  INTEGER {
        any(1),
        text(2),
        regex(3)
        }
    MAX-ACCESS  read-create
    STATUS  current
    DESCRIPTION
        "Defines whether Domain matching should be evaluated as String, Regex or match, any (default any)."
    ::= { slbNewAcclCfgCompUrlRuleEntry 4 }

slbNewAcclCfgCompUrlRuleDomain OBJECT-TYPE
    SYNTAX   DisplayString (SIZE (0..255))
    MAX-ACCESS  read-create
    STATUS  current
    DESCRIPTION
        "Defines the Virtual Host for which this rule applies."
    ::= { slbNewAcclCfgCompUrlRuleEntry 5 }

slbNewAcclCfgCompUrlRuleURLm OBJECT-TYPE
    SYNTAX  INTEGER {
        any(1),
        text(2),
        regex(3)
        }
    MAX-ACCESS  read-create
    STATUS  current
    DESCRIPTION
        "Defines whether URL matching should be evaluated as String, Regex or match, any (default any)."
    ::= { slbNewAcclCfgCompUrlRuleEntry 6 }

slbNewAcclCfgCompUrlRuleURL OBJECT-TYPE
    SYNTAX   DisplayString
    MAX-ACCESS  read-create
    STATUS  current
    DESCRIPTION
        "Defines URL of specific object (file/folder) to be matched by this rule."
    ::= { slbNewAcclCfgCompUrlRuleEntry 7 }

slbNewAcclCfgCompUrlRuleCompress OBJECT-TYPE
    SYNTAX  INTEGER {
        enabled(1),
        disabled(2)
        }
    MAX-ACCESS  read-create
    STATUS  current
    DESCRIPTION
        "Enable/Disable the compression."
    ::= { slbNewAcclCfgCompUrlRuleEntry 8 }

slbNewAcclCfgCompUrlRuleAdminStatus OBJECT-TYPE
    SYNTAX  INTEGER {
        enabled(1),
        disabled(2)
        }
    MAX-ACCESS  read-create
    STATUS  current
    DESCRIPTION
        "Status (enable/disable) of compression URL Rule."
    ::= { slbNewAcclCfgCompUrlRuleEntry 9 }

slbNewAcclCfgCompUrlRuleDelete OBJECT-TYPE
    SYNTAX  INTEGER {
        other(1),
        delete(2)
        }
    MAX-ACCESS  read-create
    STATUS  current
    DESCRIPTION
        "By setting the value to delete(2), the entire row is deleted."
    ::= { slbNewAcclCfgCompUrlRuleEntry 10 }

slbNewAcclCfgCompUrlRuleCopy OBJECT-TYPE
    SYNTAX   DisplayString
    MAX-ACCESS  read-create
    STATUS  current
    DESCRIPTION
        "Copy rule to another index in the same rule-list."
    ::= { slbNewAcclCfgCompUrlRuleEntry 11 }

slbCurAcclCfgCompBrwsListTable OBJECT-TYPE
    SYNTAX  SEQUENCE OF SlbCurAcclCfgCompBrwsListEntry
    MAX-ACCESS  not-accessible
    STATUS  current
    DESCRIPTION
        "The table for configuring compression browser LIST."
    ::= { compression 9 }

slbCurAcclCfgCompBrwsListEntry OBJECT-TYPE
    SYNTAX  SlbCurAcclCfgCompBrwsListEntry
    MAX-ACCESS  not-accessible
    STATUS  current
    DESCRIPTION
        "A row in the compression browser LIST table."
    INDEX   { slbCurAcclCfgCompBrwsListIdIndex }
    ::= { slbCurAcclCfgCompBrwsListTable 1 }

SlbCurAcclCfgCompBrwsListEntry ::= SEQUENCE {
    slbCurAcclCfgCompBrwsListIdIndex          DisplayString,
    slbCurAcclCfgCompBrwsListName             DisplayString,
    slbCurAcclCfgCompBrwsListAdminStatus      INTEGER
    }

slbCurAcclCfgCompBrwsListIdIndex OBJECT-TYPE
    SYNTAX   DisplayString (SIZE (0..31))
    MAX-ACCESS  read-only
    STATUS  current
    DESCRIPTION
        "The compression policy browser LIST (key id) as an index."
    ::= { slbCurAcclCfgCompBrwsListEntry 1 }

slbCurAcclCfgCompBrwsListName OBJECT-TYPE
    SYNTAX   DisplayString (SIZE (0..31))
    MAX-ACCESS  read-only
    STATUS  current
    DESCRIPTION
        "Compression browser list name."
    ::= { slbCurAcclCfgCompBrwsListEntry 2 }

slbCurAcclCfgCompBrwsListAdminStatus OBJECT-TYPE
    SYNTAX  INTEGER {
        enabled(1),
        disabled(2)
        }
    MAX-ACCESS  read-only
    STATUS  current
    DESCRIPTION
        "Status (enable/disable) of compression browser list."
    ::= { slbCurAcclCfgCompBrwsListEntry 3 }


slbNewAcclCfgCompBrwsListTable OBJECT-TYPE
    SYNTAX  SEQUENCE OF SlbNewAcclCfgCompBrwsListEntry
    MAX-ACCESS  not-accessible
    STATUS  current
    DESCRIPTION
        "The table for configuring compression browser list."
    ::= { compression 10 }

slbNewAcclCfgCompBrwsListEntry OBJECT-TYPE
    SYNTAX  SlbNewAcclCfgCompBrwsListEntry
    MAX-ACCESS  not-accessible
    STATUS  current
    DESCRIPTION
        "A row in the compression browser list table."
    INDEX   { slbNewAcclCfgCompBrwsListIdIndex }
    ::= { slbNewAcclCfgCompBrwsListTable 1 }

SlbNewAcclCfgCompBrwsListEntry ::= SEQUENCE {
    slbNewAcclCfgCompBrwsListIdIndex          DisplayString,
    slbNewAcclCfgCompBrwsListName             DisplayString,
    slbNewAcclCfgCompBrwsListAdminStatus      INTEGER,
    slbNewAcclCfgCompBrwsListDel              INTEGER,
    slbNewAcclCfgCompBrwsListCopy             DisplayString
    }

slbNewAcclCfgCompBrwsListIdIndex OBJECT-TYPE
    SYNTAX   DisplayString (SIZE (0..31))
    MAX-ACCESS  read-only
    STATUS  current
    DESCRIPTION
        "The compression policy browser list (key id) as an index."
    ::= { slbNewAcclCfgCompBrwsListEntry 1 }

slbNewAcclCfgCompBrwsListName OBJECT-TYPE
    SYNTAX   DisplayString (SIZE (0..31))
    MAX-ACCESS  read-create
    STATUS  current
    DESCRIPTION
        "Compression browser list name."
    ::= { slbNewAcclCfgCompBrwsListEntry 2 }

slbNewAcclCfgCompBrwsListAdminStatus OBJECT-TYPE
    SYNTAX  INTEGER {
        enabled(1),
        disabled(2)
        }
    MAX-ACCESS  read-create
    STATUS  current
    DESCRIPTION
        "Status (enable/disable) of compression browser list."
    ::= { slbNewAcclCfgCompBrwsListEntry 3 }

slbNewAcclCfgCompBrwsListDel OBJECT-TYPE
    SYNTAX  INTEGER {
        other(1),
        delete(2)
        }
    MAX-ACCESS  read-create
    STATUS  current
    DESCRIPTION
        "Delete Compression Browser list."
    ::= { slbNewAcclCfgCompBrwsListEntry 4 }

slbNewAcclCfgCompBrwsListCopy OBJECT-TYPE
    SYNTAX   DisplayString
    MAX-ACCESS  read-create
    STATUS  current
    DESCRIPTION
        "Duplicating an entire browser list by defining the destination browser list id."
    ::= { slbNewAcclCfgCompBrwsListEntry 5 }

slbCurAcclCfgCompBrwsRuleTable OBJECT-TYPE
    SYNTAX  SEQUENCE OF SlbCurAcclCfgCompBrwsRuleEntry
    MAX-ACCESS  not-accessible
    STATUS  current
    DESCRIPTION
        "The table for configuring compression browser Rules."
    ::= { compression 11 }

slbCurAcclCfgCompBrwsRuleEntry OBJECT-TYPE
    SYNTAX  SlbCurAcclCfgCompBrwsRuleEntry
    MAX-ACCESS  not-accessible
    STATUS  current
    DESCRIPTION
        "A row in the compression browser Rule table."
    INDEX   { slbCurAcclCfgCompBrwsRuleListIdIndex, slbCurAcclCfgCompBrwsRuleIndex }
    ::= { slbCurAcclCfgCompBrwsRuleTable 1 }

SlbCurAcclCfgCompBrwsRuleEntry ::= SEQUENCE {
    slbCurAcclCfgCompBrwsRuleListIdIndex          DisplayString,
    slbCurAcclCfgCompBrwsRuleIndex                INTEGER,
    slbCurAcclCfgCompBrwsRuleName                 DisplayString,
    slbCurAcclCfgCompBrwsRuleAgentM               INTEGER,
    slbCurAcclCfgCompBrwsRuleAgent                DisplayString,
    slbCurAcclCfgCompBrwsRuleContentM             INTEGER,
    slbCurAcclCfgCompBrwsRuleContent              DisplayString,
    slbCurAcclCfgCompBrwsRuleCompress             INTEGER,
    slbCurAcclCfgCompBrwsRuleAdminStatus          INTEGER
    }

slbCurAcclCfgCompBrwsRuleListIdIndex OBJECT-TYPE
    SYNTAX   DisplayString (SIZE (0..31))
    MAX-ACCESS  read-only
    STATUS  current
    DESCRIPTION
        "The compression browser list (key id) as an index."
    ::= { slbCurAcclCfgCompBrwsRuleEntry 1 }

slbCurAcclCfgCompBrwsRuleIndex OBJECT-TYPE
    SYNTAX   INTEGER
    MAX-ACCESS  read-only
    STATUS  current
    DESCRIPTION
        "The compression browser Rule number as an index."
    ::= { slbCurAcclCfgCompBrwsRuleEntry 2 }

slbCurAcclCfgCompBrwsRuleName OBJECT-TYPE
    SYNTAX   DisplayString (SIZE (0..31))
    MAX-ACCESS  read-only
    STATUS  current
    DESCRIPTION
        "The compression browser Rule name."
    ::= { slbCurAcclCfgCompBrwsRuleEntry 3 }

slbCurAcclCfgCompBrwsRuleAgentM OBJECT-TYPE
    SYNTAX  INTEGER {
        any(1),
        text(2),
        regex(3)
        }
    MAX-ACCESS  read-only
    STATUS  current
    DESCRIPTION
        "Defines whether user agent field should be evaluated as String, Regex or match, any (default any)."
    ::= { slbCurAcclCfgCompBrwsRuleEntry 4 }

slbCurAcclCfgCompBrwsRuleAgent OBJECT-TYPE
    SYNTAX   DisplayString (SIZE (0..255))
    MAX-ACCESS  read-only
    STATUS  current
    DESCRIPTION
        "Defines the User-Agent string for which this rule applies."
    ::= { slbCurAcclCfgCompBrwsRuleEntry 5 }

slbCurAcclCfgCompBrwsRuleContentM OBJECT-TYPE
    SYNTAX  INTEGER {
        any(1),
        text(2),
        regex(3)
        }
    MAX-ACCESS  read-only
    STATUS  current
    DESCRIPTION
        "Defines whether content type should be evaluated as String, Regex or match, any (default any)."
    ::= { slbCurAcclCfgCompBrwsRuleEntry 6 }

slbCurAcclCfgCompBrwsRuleContent OBJECT-TYPE
    SYNTAX   DisplayString
    MAX-ACCESS  read-only
    STATUS  current
    DESCRIPTION
        "Defines the Content-type string for which this rule applies."
    ::= { slbCurAcclCfgCompBrwsRuleEntry 7 }

slbCurAcclCfgCompBrwsRuleCompress OBJECT-TYPE
    SYNTAX  INTEGER {
        enabled(1),
        disabled(2)
        }
    MAX-ACCESS  read-only
    STATUS  current
    DESCRIPTION
        "Enable/Disable the compression. Defines if the matched response should be compressed or not"
    ::= { slbCurAcclCfgCompBrwsRuleEntry 8 }

slbCurAcclCfgCompBrwsRuleAdminStatus OBJECT-TYPE
    SYNTAX  INTEGER {
        enabled(1),
        disabled(2)
        }
    MAX-ACCESS  read-only
    STATUS  current
    DESCRIPTION
        "Status (enable/disable) of compression browser Rule."
    ::= { slbCurAcclCfgCompBrwsRuleEntry 9 }

slbNewAcclCfgCompBrwsRuleTable OBJECT-TYPE
    SYNTAX  SEQUENCE OF SlbNewAcclCfgCompBrwsRuleEntry
    MAX-ACCESS  not-accessible
    STATUS  current
    DESCRIPTION
        "The table for configuring compression browser Rules."
    ::= { compression 12 }

slbNewAcclCfgCompBrwsRuleEntry OBJECT-TYPE
    SYNTAX  SlbNewAcclCfgCompBrwsRuleEntry
    MAX-ACCESS  not-accessible
    STATUS  current
    DESCRIPTION
        "A row in the compression browser Rule table."
    INDEX   { slbNewAcclCfgCompBrwsRuleListIdIndex, slbNewAcclCfgCompBrwsRuleIndex }
    ::= { slbNewAcclCfgCompBrwsRuleTable 1 }

SlbNewAcclCfgCompBrwsRuleEntry ::= SEQUENCE {
    slbNewAcclCfgCompBrwsRuleListIdIndex          DisplayString,
    slbNewAcclCfgCompBrwsRuleIndex                INTEGER,
    slbNewAcclCfgCompBrwsRuleName                 DisplayString,
    slbNewAcclCfgCompBrwsRuleAgentM               INTEGER,
    slbNewAcclCfgCompBrwsRuleAgent                DisplayString,
    slbNewAcclCfgCompBrwsRuleContentM             INTEGER,
    slbNewAcclCfgCompBrwsRuleContent              DisplayString,
    slbNewAcclCfgCompBrwsRuleCompress             INTEGER,
    slbNewAcclCfgCompBrwsRuleAdminStatus          INTEGER,
    slbNewAcclCfgCompBrwsRuleDelete               INTEGER,
    slbNewAcclCfgCompBrwsRuleCopy                 INTEGER
    }

slbNewAcclCfgCompBrwsRuleListIdIndex OBJECT-TYPE
    SYNTAX   DisplayString (SIZE (0..31))
    MAX-ACCESS  read-only
    STATUS  current
    DESCRIPTION
        "The compression browser list (key id) as an index."
    ::= { slbNewAcclCfgCompBrwsRuleEntry 1 }

slbNewAcclCfgCompBrwsRuleIndex OBJECT-TYPE
    SYNTAX   INTEGER
    MAX-ACCESS  read-only
    STATUS  current
    DESCRIPTION
        "The compression browser Rule number as an index."
    ::= { slbNewAcclCfgCompBrwsRuleEntry 2 }

slbNewAcclCfgCompBrwsRuleName OBJECT-TYPE
    SYNTAX   DisplayString (SIZE (0..31))
    MAX-ACCESS  read-create
    STATUS  current
    DESCRIPTION
        "The compression browser Rule name."
    ::= { slbNewAcclCfgCompBrwsRuleEntry 3 }

slbNewAcclCfgCompBrwsRuleAgentM OBJECT-TYPE
    SYNTAX  INTEGER {
        any(1),
        text(2),
        regex(3)
        }
    MAX-ACCESS  read-create
    STATUS  current
    DESCRIPTION
        "Defines whether user agent field should be evaluated as String, Regex or match, any (default any)."
    ::= { slbNewAcclCfgCompBrwsRuleEntry 4 }

slbNewAcclCfgCompBrwsRuleAgent OBJECT-TYPE
    SYNTAX   DisplayString (SIZE (0..255))
    MAX-ACCESS  read-create
    STATUS  current
    DESCRIPTION
        "Defines the User-Agent string for which this rule applies."
    ::= { slbNewAcclCfgCompBrwsRuleEntry 5 }

slbNewAcclCfgCompBrwsRuleContentM OBJECT-TYPE
    SYNTAX  INTEGER {
        any(1),
        text(2),
        regex(3)
        }
    MAX-ACCESS  read-create
    STATUS  current
    DESCRIPTION
        "Defines whether content type should be evaluated as String, Regex or match, any (default any)."
    ::= { slbNewAcclCfgCompBrwsRuleEntry 6 }

slbNewAcclCfgCompBrwsRuleContent OBJECT-TYPE
    SYNTAX   DisplayString
    MAX-ACCESS  read-create
    STATUS  current
    DESCRIPTION
        "Defines the Content-type string for which this rule applies."
    ::= { slbNewAcclCfgCompBrwsRuleEntry 7 }

slbNewAcclCfgCompBrwsRuleCompress OBJECT-TYPE
    SYNTAX  INTEGER {
        enabled(1),
        disabled(2)
        }
    MAX-ACCESS  read-create
    STATUS  current
    DESCRIPTION
        "Enable/Disable the compression. Defines if the matched response should be compressed or not"
    ::= { slbNewAcclCfgCompBrwsRuleEntry 8 }

slbNewAcclCfgCompBrwsRuleAdminStatus OBJECT-TYPE
    SYNTAX  INTEGER {
        enabled(1),
        disabled(2)
        }
    MAX-ACCESS  read-create
    STATUS  current
    DESCRIPTION
        "Status (enable/disable) of compression browser Rule."
    ::= { slbNewAcclCfgCompBrwsRuleEntry 9 }

slbNewAcclCfgCompBrwsRuleDelete OBJECT-TYPE
    SYNTAX  INTEGER {
        other(1),
        delete(2)
        }
    MAX-ACCESS  read-create
    STATUS  current
    DESCRIPTION
        "By setting the value to delete(2), the entire row is deleted."
    ::= { slbNewAcclCfgCompBrwsRuleEntry 10 }

slbNewAcclCfgCompBrwsRuleCopy OBJECT-TYPE
    SYNTAX   INTEGER
    MAX-ACCESS  read-create
    STATUS  current
    DESCRIPTION
        "Copy rule to another index in the same rule-list."
    ::= { slbNewAcclCfgCompBrwsRuleEntry 11 }


 -- NWCLSS

 -- Network classes
slbCurNwclssCfgNetworkClassesTable OBJECT-TYPE
    SYNTAX  SEQUENCE OF SlbCurNwclssCfgNetworkClassesEntry
    MAX-ACCESS  not-accessible
    STATUS  current
    DESCRIPTION
        "Current network classes table."
    ::= { nwclssCfg 1 }

slbCurNwclssCfgNetworkClassesEntry OBJECT-TYPE
    SYNTAX  SlbCurNwclssCfgNetworkClassesEntry
    MAX-ACCESS  not-accessible
    STATUS  current
    DESCRIPTION
        "A row in the network classes table."
    INDEX   { slbCurNwclssCfgNetworkClassesId }
    ::= { slbCurNwclssCfgNetworkClassesTable 1 }

SlbCurNwclssCfgNetworkClassesEntry ::= SEQUENCE {
    slbCurNwclssCfgNetworkClassesId          DisplayString,
    slbCurNwclssCfgNetworkClassesName        DisplayString,
    slbCurNwclssCfgNetworkClassesIpVer       INTEGER
    }

slbCurNwclssCfgNetworkClassesId OBJECT-TYPE
    SYNTAX   DisplayString (SIZE (0..32))
    MAX-ACCESS  read-only
    STATUS  current
    DESCRIPTION
        "Network class id."
    ::= { slbCurNwclssCfgNetworkClassesEntry 1 }

slbCurNwclssCfgNetworkClassesName OBJECT-TYPE
    SYNTAX   DisplayString (SIZE (0..32))
    MAX-ACCESS  read-only
    STATUS  current
    DESCRIPTION
        "Network class name."
    ::= { slbCurNwclssCfgNetworkClassesEntry 2 }

slbCurNwclssCfgNetworkClassesIpVer OBJECT-TYPE
    SYNTAX  INTEGER{
        ipv4(1),
        ipv6(2)
        }
    MAX-ACCESS  read-only
    STATUS  current
    DESCRIPTION
        "The type of IP address."
   ::= { slbCurNwclssCfgNetworkClassesEntry 3 }

slbNewNwclssCfgNetworkClassesTable OBJECT-TYPE
    SYNTAX  SEQUENCE OF SlbNewNwclssCfgNetworkClassesEntry
    MAX-ACCESS  not-accessible
    STATUS  current
    DESCRIPTION
        "New network classes table."
    ::= { nwclssCfg 2 }

slbNewNwclssCfgNetworkClassesEntry OBJECT-TYPE
    SYNTAX  SlbNewNwclssCfgNetworkClassesEntry
    MAX-ACCESS  not-accessible
    STATUS  current
    DESCRIPTION
        "A row in the new network classes table."
    INDEX   { slbNewNwclssCfgNetworkClassesId }
    ::= { slbNewNwclssCfgNetworkClassesTable 1 }

SlbNewNwclssCfgNetworkClassesEntry ::= SEQUENCE {
    slbNewNwclssCfgNetworkClassesId       	DisplayString,
    slbNewNwclssCfgNetworkClassesName     	DisplayString,
    slbNewNwclssCfgNetworkClassesIpVer      INTEGER,
    slbNewNwclssCfgNetworkClassesDel	INTEGER,
    slbNewNwclssCfgNetworkClassesCopy       DisplayString
    }

slbNewNwclssCfgNetworkClassesId OBJECT-TYPE
    SYNTAX   DisplayString (SIZE (0..32))
    MAX-ACCESS  read-only
    STATUS  current
    DESCRIPTION
        "Network class id."
    ::= { slbNewNwclssCfgNetworkClassesEntry 1 }

slbNewNwclssCfgNetworkClassesName OBJECT-TYPE
    SYNTAX   DisplayString (SIZE (0..32))
    MAX-ACCESS  read-create
    STATUS  current
    DESCRIPTION
        "Network class name."
    ::= { slbNewNwclssCfgNetworkClassesEntry 2 }

slbNewNwclssCfgNetworkClassesIpVer OBJECT-TYPE
    SYNTAX  INTEGER {
        ipv4(1),
        ipv6(2)
        }
    MAX-ACCESS  read-create
    STATUS  current
    DESCRIPTION
        "The type of IP address."
    ::= { slbNewNwclssCfgNetworkClassesEntry 3 }

slbNewNwclssCfgNetworkClassesDel OBJECT-TYPE
    SYNTAX  INTEGER {
        other(1),
        delete(2)
        }
    MAX-ACCESS  read-create
    STATUS  current
    DESCRIPTION
        "By setting the value to delete(2), the entire row is deleted."
    ::= { slbNewNwclssCfgNetworkClassesEntry 4 }

slbNewNwclssCfgNetworkClassesCopy OBJECT-TYPE
    SYNTAX   DisplayString (SIZE (0..32))
    MAX-ACCESS  read-create
    STATUS  current
    DESCRIPTION
        "Duplicating an entire Network class by defining the destination Network class id."
    ::= { slbNewNwclssCfgNetworkClassesEntry 5 }

 -- Network elements
slbCurNwclssCfgNetworkElementsTable OBJECT-TYPE
    SYNTAX  SEQUENCE OF SlbCurNwclssCfgNetworkElementsEntry
    MAX-ACCESS  not-accessible
    STATUS  current
    DESCRIPTION
        "Current network elements table."
    ::= { nwclssCfg 3 }

slbCurNwclssCfgNetworkElementsEntry OBJECT-TYPE
    SYNTAX  SlbCurNwclssCfgNetworkElementsEntry
    MAX-ACCESS  not-accessible
    STATUS  current
    DESCRIPTION
        "A row in the network elements table."
    INDEX   { slbCurNwclssCfgNetworkElementsNcId, slbCurNwclssCfgNetworkElementsId }
    ::= { slbCurNwclssCfgNetworkElementsTable 1 }

SlbCurNwclssCfgNetworkElementsEntry ::= SEQUENCE {
    slbCurNwclssCfgNetworkElementsNcId          DisplayString,
    slbCurNwclssCfgNetworkElementsId		DisplayString,
    slbCurNwclssCfgNetworkElementsNetType    	INTEGER,
    slbCurNwclssCfgNetworkElementsIp      	IpAddress,
    slbCurNwclssCfgNetworkElementsMask    	IpAddress,
    slbCurNwclssCfgNetworkElementsFromIp      	IpAddress,
    slbCurNwclssCfgNetworkElementsToIp      	IpAddress,
    slbCurNwclssCfgNetworkElementsIpv6Addr      DisplayString,
    slbCurNwclssCfgNetworkElementsPrefixLen    	INTEGER,
    slbCurNwclssCfgNetworkElementsFromIpv6Addr  DisplayString,
    slbCurNwclssCfgNetworkElementsToIpv6Addr    DisplayString,
    slbCurNwclssCfgNetworkElementsMatchType     INTEGER
    }
 
slbCurNwclssCfgNetworkElementsNcId OBJECT-TYPE
    SYNTAX   DisplayString (SIZE (0..32))
    MAX-ACCESS  read-only
    STATUS  current
    DESCRIPTION
        "Id of network class which owns network element."
    ::= { slbCurNwclssCfgNetworkElementsEntry 1 }

slbCurNwclssCfgNetworkElementsId OBJECT-TYPE
    SYNTAX   DisplayString (SIZE (0..32))
    MAX-ACCESS  read-only
    STATUS  current
    DESCRIPTION
        "Network element id."
    ::= { slbCurNwclssCfgNetworkElementsEntry 2 }

slbCurNwclssCfgNetworkElementsNetType OBJECT-TYPE
    SYNTAX  INTEGER{
        subnet(1),
        range(2)
        }
    MAX-ACCESS  read-only
    STATUS  current
    DESCRIPTION
        "The type of network."
   ::= { slbCurNwclssCfgNetworkElementsEntry 3 }

slbCurNwclssCfgNetworkElementsIp OBJECT-TYPE
    SYNTAX  IpAddress
    MAX-ACCESS  read-only
    STATUS  current
    DESCRIPTION
        "IPv4 address of network element."
    ::= { slbCurNwclssCfgNetworkElementsEntry 4 }

slbCurNwclssCfgNetworkElementsMask OBJECT-TYPE
    SYNTAX  IpAddress
    MAX-ACCESS  read-only
    STATUS  current  
    DESCRIPTION
        "Subnet mask of network element."
    ::= { slbCurNwclssCfgNetworkElementsEntry 5 }

slbCurNwclssCfgNetworkElementsFromIp OBJECT-TYPE
    SYNTAX  IpAddress
    MAX-ACCESS  read-only
    STATUS  current
    DESCRIPTION
        "From IP address of network element."
    ::= { slbCurNwclssCfgNetworkElementsEntry 6 }

slbCurNwclssCfgNetworkElementsToIp OBJECT-TYPE
    SYNTAX  IpAddress
    MAX-ACCESS  read-only
    STATUS  current
    DESCRIPTION
        "To IP address of network element."
    ::= { slbCurNwclssCfgNetworkElementsEntry 7 }

slbCurNwclssCfgNetworkElementsIpv6Addr OBJECT-TYPE
    SYNTAX   DisplayString (SIZE(0..40))
    MAX-ACCESS  read-only
    STATUS  current
    DESCRIPTION
        "The IPv6 address of network element.
	 Address should be 4-byte haxadecimal colon notation.
         Valid IPv6 address should be in any of the following forms
           xxxx:xxxx:xxxx:xxxx:xxxx:xxxx:xxxx:xxxx or
           xxxx::xxxx:xxxx:xxxx:xxxx or ::xxxx"
    ::= { slbCurNwclssCfgNetworkElementsEntry 8 }

slbCurNwclssCfgNetworkElementsPrefixLen OBJECT-TYPE
    SYNTAX  INTEGER(1..128) 
    MAX-ACCESS  read-only
    STATUS  current
    DESCRIPTION
        "The prefix length associated with the network IP address ."
    ::= { slbCurNwclssCfgNetworkElementsEntry 9 }

slbCurNwclssCfgNetworkElementsFromIpv6Addr OBJECT-TYPE
    SYNTAX   DisplayString (SIZE(0..40))
    MAX-ACCESS  read-only
    STATUS  current
    DESCRIPTION
        "The from IPv6 address of network element.
	 Address should be 4-byte haxadecimal colon notation.
         Valid IPv6 address should be in any of the following forms
           xxxx:xxxx:xxxx:xxxx:xxxx:xxxx:xxxx:xxxx or
           xxxx::xxxx:xxxx:xxxx:xxxx or ::xxxx"
    ::= { slbCurNwclssCfgNetworkElementsEntry 10 }

slbCurNwclssCfgNetworkElementsToIpv6Addr OBJECT-TYPE
    SYNTAX   DisplayString (SIZE(0..40))
    MAX-ACCESS  read-only
    STATUS  current
    DESCRIPTION
        "The to IPv6 address of network element.
	 Address should be 4-byte haxadecimal colon notation.
         Valid IPv6 address should be in any of the following forms
           xxxx:xxxx:xxxx:xxxx:xxxx:xxxx:xxxx:xxxx or
           xxxx::xxxx:xxxx:xxxx:xxxx or ::xxxx"
    ::= { slbCurNwclssCfgNetworkElementsEntry 11 }
 
slbCurNwclssCfgNetworkElementsMatchType OBJECT-TYPE
    SYNTAX  INTEGER{
        include(1),
        exclude(2)
        }
    MAX-ACCESS  read-only
    STATUS  current
    DESCRIPTION
        "The match type of network element."
   ::= { slbCurNwclssCfgNetworkElementsEntry 12 }

slbNewNwclssCfgNetworkElementsTable  OBJECT-TYPE
    SYNTAX  SEQUENCE OF SlbNewNwclssCfgNetworkElementsEntry
    MAX-ACCESS  not-accessible
    STATUS  current
    DESCRIPTION
        "New network elements table."
    ::= { nwclssCfg 4 }

slbNewNwclssCfgNetworkElementsEntry OBJECT-TYPE
    SYNTAX  SlbNewNwclssCfgNetworkElementsEntry
    MAX-ACCESS  not-accessible
    STATUS  current
    DESCRIPTION
        "A row in the new network elements table."
    INDEX   { slbNewNwclssCfgNetworkElementsNcId, slbNewNwclssCfgNetworkElementsId }
    ::= { slbNewNwclssCfgNetworkElementsTable 1 }
 
SlbNewNwclssCfgNetworkElementsEntry ::= SEQUENCE {
    slbNewNwclssCfgNetworkElementsNcId          DisplayString,
    slbNewNwclssCfgNetworkElementsId		DisplayString,
    slbNewNwclssCfgNetworkElementsNetType    	INTEGER,
    slbNewNwclssCfgNetworkElementsIp      	IpAddress,
    slbNewNwclssCfgNetworkElementsMask    	IpAddress,
    slbNewNwclssCfgNetworkElementsFromIp      	IpAddress,
    slbNewNwclssCfgNetworkElementsToIp      	IpAddress,
    slbNewNwclssCfgNetworkElementsIpv6Addr      DisplayString,
    slbNewNwclssCfgNetworkElementsPrefixLen    	INTEGER,
    slbNewNwclssCfgNetworkElementsFromIpv6Addr  DisplayString,
    slbNewNwclssCfgNetworkElementsToIpv6Addr    DisplayString,
    slbNewNwclssCfgNetworkElementsMatchType     INTEGER,
    slbNewNwclssCfgNetworkElementsDel		INTEGER
    }

slbNewNwclssCfgNetworkElementsNcId OBJECT-TYPE
    SYNTAX   DisplayString (SIZE (0..32))
    MAX-ACCESS  read-only
    STATUS  current
    DESCRIPTION
        "ID of network class which owns network element."
    ::= { slbNewNwclssCfgNetworkElementsEntry 1 }

slbNewNwclssCfgNetworkElementsId OBJECT-TYPE
    SYNTAX   DisplayString (SIZE (0..32))
    MAX-ACCESS  read-only
    STATUS  current
    DESCRIPTION
        "Network class ID."
    ::= { slbNewNwclssCfgNetworkElementsEntry 2 }

slbNewNwclssCfgNetworkElementsNetType OBJECT-TYPE
    SYNTAX  INTEGER {
        subnet(1),
        range(2)
        }
    MAX-ACCESS  read-create
    STATUS  current
    DESCRIPTION
        "The type of network."
    ::= { slbNewNwclssCfgNetworkElementsEntry 3 }

slbNewNwclssCfgNetworkElementsIp OBJECT-TYPE
    SYNTAX  IpAddress
    MAX-ACCESS  read-create
    STATUS  current
    DESCRIPTION
        "IP address of network element."
    ::= { slbNewNwclssCfgNetworkElementsEntry 4 }

slbNewNwclssCfgNetworkElementsMask OBJECT-TYPE
    SYNTAX  IpAddress
    MAX-ACCESS  read-create
    STATUS  current  
    DESCRIPTION
        "Subnet mask of network element."
    ::= { slbNewNwclssCfgNetworkElementsEntry 5 }

slbNewNwclssCfgNetworkElementsFromIp OBJECT-TYPE
    SYNTAX  IpAddress
    MAX-ACCESS  read-create
    STATUS  current
    DESCRIPTION
        "From IP address of network element."
    ::= { slbNewNwclssCfgNetworkElementsEntry 6 }

slbNewNwclssCfgNetworkElementsToIp OBJECT-TYPE
    SYNTAX  IpAddress
    MAX-ACCESS  read-create
    STATUS  current
    DESCRIPTION
        "To IP address of network element."
    ::= { slbNewNwclssCfgNetworkElementsEntry 7 }

slbNewNwclssCfgNetworkElementsIpv6Addr OBJECT-TYPE
    SYNTAX   DisplayString (SIZE(0..40))
    MAX-ACCESS  read-create
    STATUS  current
    DESCRIPTION
        "The IPv6 address of network element.
	 Address should be 4-byte haxadecimal colon notation.
         Valid IPv6 address should be in any of the following forms
           xxxx:xxxx:xxxx:xxxx:xxxx:xxxx:xxxx:xxxx or
           xxxx::xxxx:xxxx:xxxx:xxxx or ::xxxx"
    ::= { slbNewNwclssCfgNetworkElementsEntry 8 }

slbNewNwclssCfgNetworkElementsPrefixLen OBJECT-TYPE
    SYNTAX  INTEGER(1..128) 
    MAX-ACCESS  read-create
    STATUS  current
    DESCRIPTION
        "The prefix length associated with the network IP address ."
    ::= { slbNewNwclssCfgNetworkElementsEntry 9 }

slbNewNwclssCfgNetworkElementsFromIpv6Addr OBJECT-TYPE
    SYNTAX   DisplayString (SIZE(0..40))
    MAX-ACCESS  read-create
    STATUS  current
    DESCRIPTION
        "The from IPv6 address of network element.
	 Address should be 4-byte haxadecimal colon notation.
         Valid IPv6 address should be in any of the following forms
           xxxx:xxxx:xxxx:xxxx:xxxx:xxxx:xxxx:xxxx or
           xxxx::xxxx:xxxx:xxxx:xxxx or ::xxxx"
    ::= { slbNewNwclssCfgNetworkElementsEntry 10 }

slbNewNwclssCfgNetworkElementsToIpv6Addr OBJECT-TYPE
    SYNTAX   DisplayString (SIZE(0..40))
    MAX-ACCESS  read-create
    STATUS  current
    DESCRIPTION
        "The to IPv6 address of network element.
	 Address should be 4-byte haxadecimal colon notation.
         Valid IPv6 address should be in any of the following forms
           xxxx:xxxx:xxxx:xxxx:xxxx:xxxx:xxxx:xxxx or
           xxxx::xxxx:xxxx:xxxx:xxxx or ::xxxx"
    ::= { slbNewNwclssCfgNetworkElementsEntry 11 }

slbNewNwclssCfgNetworkElementsMatchType OBJECT-TYPE
    SYNTAX  INTEGER{
        include(1),
        exclude(2)
        }
    MAX-ACCESS  read-create
    STATUS  current
    DESCRIPTION
        "The match type of network element."
   ::= { slbNewNwclssCfgNetworkElementsEntry 12 }

slbNewNwclssCfgNetworkElementsDel OBJECT-TYPE
    SYNTAX  INTEGER {
        other(1),
        delete(2)
        }
    MAX-ACCESS  read-create
    STATUS  current
    DESCRIPTION
        "By setting the value to delete(2), the entire row is deleted."
    ::= { slbNewNwclssCfgNetworkElementsEntry 13 }

	-- NWCLSS END

cachStatSummTotObj OBJECT-TYPE
   SYNTAX  Integer32
   MAX-ACCESS  read-only
   STATUS  current 
   DESCRIPTION
       "Number of Objects served by cache within the measuring period."
   ::= {cachStats 1}

cachStatSummHitPerc OBJECT-TYPE
   SYNTAX  Integer32
   MAX-ACCESS  read-only
   STATUS  current 
   DESCRIPTION
       "Percent of HTTP requests served by objects from cache."
   ::= {cachStats 2}

cachStatSummServRate OBJECT-TYPE
   SYNTAX  Integer32
   MAX-ACCESS  read-only
   STATUS  current 
   DESCRIPTION
       "Rate of requests served by cache every second."
   ::= {cachStats 3}

cachStatSummNewCachedObj OBJECT-TYPE
   SYNTAX  Integer32
   MAX-ACCESS  read-only
   STATUS  current  
   DESCRIPTION
       "Amount of new objects cached during the measuring period."
   ::= {cachStats 4}

cachStatSummRateNewCachedObj OBJECT-TYPE
   SYNTAX  Integer32
   MAX-ACCESS  read-only
   STATUS  current 
   DESCRIPTION
       "Average number of new objects cached every second."
   ::= {cachStats 5}

cachStatSummNewCachedBytes OBJECT-TYPE
   SYNTAX  Integer32
   MAX-ACCESS  read-only
   STATUS  current 
   DESCRIPTION
       "Amount of new bytes cached during the measuring period."
   ::= {cachStats 6}

cachStatSummRateNewCachedBytes OBJECT-TYPE
   SYNTAX  Integer32
   MAX-ACCESS  read-only
   STATUS  current 
   DESCRIPTION
       "Average number of new bytes cached every second."
   ::= {cachStats 7}

cachStatSummObjSmaller10K OBJECT-TYPE
   SYNTAX  Integer32
   MAX-ACCESS  read-only
   STATUS  current 
   DESCRIPTION
       "Amount of objects cached during last measuring period of size smaller than 10KB."
   ::= {cachStats 8}

cachStatSummObj11KTO50K OBJECT-TYPE
   SYNTAX  Integer32
   MAX-ACCESS  read-only
   STATUS  current 
   DESCRIPTION
       "Amount of objects cached during last measuring period of size between 11KB and 50KB."
   ::= {cachStats 9}

cachStatSummObj51KTO100K OBJECT-TYPE
   SYNTAX  Integer32
   MAX-ACCESS  read-only
   STATUS  current 
   DESCRIPTION
       "Amount of objects cached during last measuring period of size between 51KB and 100KB."
   ::= {cachStats 10}

cachStatSummObj101KTO1M OBJECT-TYPE
   SYNTAX  Integer32
   MAX-ACCESS  read-only
   STATUS  current 
   DESCRIPTION
       "Amount of objects cached during last measuring period of size between 101KB and 1MB."
   ::= {cachStats 11}

cachStatSummObjLarger1M OBJECT-TYPE
   SYNTAX  Integer32
   MAX-ACCESS  read-only
   STATUS  current 
   DESCRIPTION
       "Amount of objects cached during last measuring period of size larger than 1MB."
   ::= {cachStats 12}

cachPerServStatTable OBJECT-TYPE
   SYNTAX SEQUENCE OF CachPerServStatEntry
   MAX-ACCESS not-accessible
   STATUS current 
   DESCRIPTION
       "A table for cache statistics per virtual service."
   ::= {cachStats 13}

cachPerServStatEntry OBJECT-TYPE
   SYNTAX CachPerServStatEntry 
   MAX-ACCESS not-accessible
   STATUS  current 
   DESCRIPTION
       " The row definition for cache statistics per virtual service table."
   INDEX  { cachStatPerServVirtServIndex, cachStatPerServVirtServiceIndex}
   ::= {cachPerServStatTable 1}

CachPerServStatEntry  ::= SEQUENCE {
        cachStatPerServVirtServIndex                    Integer32,
        cachStatPerServVirtServiceIndex                 Integer32,
        cachStatPerServVirtServPort                     Integer32,	
	cachStatPerServCachePolId                       DisplayString,
        cachStatPerServTotObj                           Integer32,
        cachStatPerServHitPerc                          Integer32,
        cachStatPerServServRate                         Integer32,
        cachStatPerServNewCachedObj                     Integer32,
        cachStatPerServRateNewCachedObj                 Integer32,
        cachStatPerServNewCachedBytes                   Integer32,
        cachStatPerServRateNewCachedBytes               Integer32,
        cachStatPerServObjSmaller10K                    Integer32,
        cachStatPerServObj11KTO50K                      Integer32,
        cachStatPerServObj51KTO100K                     Integer32,
	cachStatPerServObj101KTO1M                      Integer32,
        cachStatPerServObjLarger1M                      Integer32
        }
cachStatPerServVirtServIndex  OBJECT-TYPE
   SYNTAX  Integer32 
   MAX-ACCESS  read-write
   STATUS  current
   DESCRIPTION
       "Virtual server index."
   ::= {cachPerServStatEntry 1}

cachStatPerServVirtServiceIndex  OBJECT-TYPE
   SYNTAX  Integer32 
   MAX-ACCESS  read-write
   STATUS  current
   DESCRIPTION
       "Virtual server service index."
   ::= {cachPerServStatEntry 2}

cachStatPerServVirtServPort  OBJECT-TYPE
   SYNTAX  Integer32 
   MAX-ACCESS  read-write
   STATUS  current
   DESCRIPTION
       "Virtual server service port number."
   ::= {cachPerServStatEntry 3}

cachStatPerServCachePolId  OBJECT-TYPE
   SYNTAX  DisplayString 
   MAX-ACCESS  read-only
   STATUS  current
   DESCRIPTION
       "Cache policy identifier associated with the virtual service."
   ::= {cachPerServStatEntry 4}

cachStatPerServTotObj  OBJECT-TYPE
   SYNTAX  Integer32
   MAX-ACCESS  read-only
   STATUS  current
   DESCRIPTION
       "Number of objects served by cache during the measuring period for virtual service."
   ::= {cachPerServStatEntry 5}

cachStatPerServHitPerc  OBJECT-TYPE
   SYNTAX  Integer32
   MAX-ACCESS  read-only
   STATUS  current
   DESCRIPTION
       "Percent of HTTP requests served by objects from cache for virtual service."
   ::= {cachPerServStatEntry 6}

cachStatPerServServRate  OBJECT-TYPE
   SYNTAX  Integer32
   MAX-ACCESS  read-only
   STATUS  current
   DESCRIPTION
       "Rate of requests served by cache every second for virtual service."
   ::= {cachPerServStatEntry 7}

cachStatPerServNewCachedObj  OBJECT-TYPE
   SYNTAX  Integer32
   MAX-ACCESS  read-only
   STATUS  current
   DESCRIPTION
       "Amount of new objects cached during the measuring period for virtual service."
   ::= {cachPerServStatEntry 8}

cachStatPerServRateNewCachedObj  OBJECT-TYPE
   SYNTAX  Integer32
   MAX-ACCESS  read-only
   STATUS  current
   DESCRIPTION
       "Average number of new objects cached every second for virtual service."
   ::= {cachPerServStatEntry 9}

cachStatPerServNewCachedBytes  OBJECT-TYPE
   SYNTAX  Integer32
   MAX-ACCESS  read-only
   STATUS  current
   DESCRIPTION
       "Amount of new bytes cached during the measuring period for virtual service."
   ::= {cachPerServStatEntry 10}

cachStatPerServRateNewCachedBytes  OBJECT-TYPE
   SYNTAX  Integer32
   MAX-ACCESS  read-only
   STATUS  current
   DESCRIPTION
       "Average number of new bytes cached every second for virtual service."
   ::= {cachPerServStatEntry 11}

cachStatPerServObjSmaller10K  OBJECT-TYPE
   SYNTAX  Integer32
   MAX-ACCESS  read-only
   STATUS  current
   DESCRIPTION
       "Amount of objects cached during last measuring period of size smaller than 10KB for virtual service."
   ::= {cachPerServStatEntry 12}

cachStatPerServObj11KTO50K  OBJECT-TYPE
   SYNTAX  Integer32
   MAX-ACCESS  read-only
   STATUS  current
   DESCRIPTION
       "Amount of objects cached during last measuring period of size between 11KB and 50KB for virtual service."
   ::= {cachPerServStatEntry 13}

cachStatPerServObj51KTO100K  OBJECT-TYPE
   SYNTAX  Integer32
   MAX-ACCESS  read-only
   STATUS  current
   DESCRIPTION
       "Amount of objects cached during last measuring period of size between 51KB and 100KB for virtual service."
   ::= {cachPerServStatEntry 14}

cachStatPerServObj101KTO1M  OBJECT-TYPE
   SYNTAX  Integer32
   MAX-ACCESS  read-only
   STATUS  current
   DESCRIPTION
       "Amount of objects cached during last measuring period of size between 101KB and 1MB for virtual service."
   ::= {cachPerServStatEntry 15}

cachStatPerServObjLarger1M  OBJECT-TYPE
   SYNTAX  Integer32
   MAX-ACCESS  read-only
   STATUS  current
   DESCRIPTION
       "Amount of objects cached during last measuring period of size larger than 1MB for virtual service."
   ::= {cachPerServStatEntry 16}

cachPerRuleListStatsTable OBJECT-TYPE
   SYNTAX SEQUENCE OF CachPerRuleListStatsEntry
   MAX-ACCESS not-accessible
   STATUS current 
   DESCRIPTION
       "A table for cache statistics per rule list."
   ::= {cachStats 14}

cachPerRuleListStatsEntry OBJECT-TYPE
   SYNTAX CachPerRuleListStatsEntry 
   MAX-ACCESS not-accessible
   STATUS  current 
   DESCRIPTION
       " The row definition for cache statistics per rule list table."
   INDEX  { cachRuleListId }
   ::= {cachPerRuleListStatsTable 1}

CachPerRuleListStatsEntry  ::= SEQUENCE {
        cachRuleListIndex                   Integer32,
        cachRuleListId                      DisplayString,
        cachRuleListNumOfObjCac             Integer32,
        cachRuleListNumOfBytesCac           Integer32
        }

cachRuleListIndex  OBJECT-TYPE
   SYNTAX  Integer32
   MAX-ACCESS  read-only
   STATUS  current
   DESCRIPTION
       "Cache rule list index."
   ::= {cachPerRuleListStatsEntry 1}

cachRuleListId  OBJECT-TYPE
   SYNTAX  DisplayString
   MAX-ACCESS  read-only
   STATUS  current
   DESCRIPTION
       "Cache rule list identifier."
   ::= {cachPerRuleListStatsEntry 2}

cachRuleListNumOfObjCac OBJECT-TYPE
   SYNTAX  Integer32
   MAX-ACCESS  read-only
   STATUS  current
   DESCRIPTION
       "Number of objects cached by this rule list."
   ::= {cachPerRuleListStatsEntry 3}

cachRuleListNumOfBytesCac  OBJECT-TYPE
   SYNTAX  Integer32
   MAX-ACCESS  read-only
   STATUS  current
   DESCRIPTION
       "Number of bytes cached by this rule list."
   ::= {cachPerRuleListStatsEntry 4}

cachPerRuleStatsTable OBJECT-TYPE
   SYNTAX SEQUENCE OF CachPerRuleStatsEntry
   MAX-ACCESS not-accessible
   STATUS current 
   DESCRIPTION
       "A table for cache statistics per rule."
   ::= {cachStats 15}

cachPerRuleStatsEntry OBJECT-TYPE
   SYNTAX CachPerRuleStatsEntry 
   MAX-ACCESS not-accessible
   STATUS  current 
   DESCRIPTION
       " The row definition for cache statistics per rule table."
   INDEX  { cachRuleRuleListIndex, cachRuleIndex }
   ::= {cachPerRuleStatsTable 1}

CachPerRuleStatsEntry  ::= SEQUENCE {
        cachRuleRuleListIndex               Integer32,
        cachRuleIndex                       Integer32,
        cachRuleRuleListId                  DisplayString,
        cachRuleNumOfObjCac                 Integer32,
        cachRuleNumOfBytesCac               Integer32
        }

cachRuleRuleListIndex  OBJECT-TYPE
   SYNTAX  Integer32 
   MAX-ACCESS  read-only
   STATUS  current
   DESCRIPTION
       "Cache rule rule-list index."
   ::= {cachPerRuleStatsEntry 1}

cachRuleIndex  OBJECT-TYPE
   SYNTAX  Integer32 
   MAX-ACCESS  read-only
   STATUS  current
   DESCRIPTION
       "Cache rule number."
   ::= {cachPerRuleStatsEntry 2}

cachRuleRuleListId  OBJECT-TYPE
   SYNTAX  DisplayString
   MAX-ACCESS  read-only
   STATUS  current
   DESCRIPTION
       "Cache rule rule-list identifier."
   ::= {cachPerRuleStatsEntry 3}

cachRuleNumOfObjCac  OBJECT-TYPE
   SYNTAX  Integer32 
   MAX-ACCESS  read-only
   STATUS  current
   DESCRIPTION
       "Number of objects cached by the rule."
   ::= {cachPerRuleStatsEntry 4}

cachRuleNumOfBytesCac  OBJECT-TYPE
   SYNTAX  Integer32 
   MAX-ACCESS  read-only
   STATUS  current
   DESCRIPTION
       "Number of bytes cached by the rule."
   ::= {cachPerRuleStatsEntry 5}

compUnCompressedThrputKB OBJECT-TYPE
   SYNTAX  Integer32
   MAX-ACCESS  read-only
   STATUS  current
   DESCRIPTION
       "Total throughput of compressible object before compression counted during measuring period."
   ::= {compStats 1}

compAvgSizeBefCompKB  OBJECT-TYPE
   SYNTAX  Integer32
   MAX-ACCESS  read-only
   STATUS  current
   DESCRIPTION
       "Average object size before compression."
   ::= {compStats 2}

compCompressedThrputKB OBJECT-TYPE
   SYNTAX  Integer32
   MAX-ACCESS  read-only
   STATUS  current
   DESCRIPTION
       "Total throughput of compressible objects after compression counted during measuring period."
   ::= {compStats 3}

compAvgSizeAftCompKB OBJECT-TYPE
   SYNTAX  Integer32
   MAX-ACCESS  read-only
   STATUS  current
   DESCRIPTION
       "Average object size after compression."
   ::= {compStats 4}

compAvgCompRatio OBJECT-TYPE
   SYNTAX  Integer32
   MAX-ACCESS  read-only
   STATUS  current
   DESCRIPTION
       "Average compression ratio during measuring period."
   ::= {compStats 5}

compThrputCompRatio OBJECT-TYPE
   SYNTAX  Integer32
   MAX-ACCESS  read-only
   STATUS  current
   DESCRIPTION
       "Effective compression ratio out of total traffic."
   ::= {compStats 6}

compStatPerServTable OBJECT-TYPE
   SYNTAX SEQUENCE OF CompStatPerServEntry
   MAX-ACCESS not-accessible
   STATUS current
   DESCRIPTION
       "A table for compression statistics per virtual service."
   ::= {compStats 7}

compStatPerServEntry OBJECT-TYPE
   SYNTAX CompStatPerServEntry 
   MAX-ACCESS not-accessible
   STATUS  current
   DESCRIPTION
       " The row definition for compression statistics per virtual service table."
   INDEX  { compStatPerServVirtServIndex, compStatPerServVirtServiceIndex}
   ::= {compStatPerServTable 1}

CompStatPerServEntry  ::= SEQUENCE {
        compStatPerServVirtServIndex      Integer32,
        compStatPerServVirtServiceIndex   Integer32,
	compStatPerServVirtServPort       Integer32,
	compStatPerServCompPolId          DisplayString,
        compStatPerServUnComprTputKb      Integer32,
        compStatPerServComprTputKb        Integer32,
        compStatPerServAvgSizeBefComp     Integer32,
        compStatPerServAvgSizeAftComp     Integer32,
        compStatPerServAvgCompRatio       Integer32,
	compStatPerServThrputCompRatio     Integer32
        }

compStatPerServVirtServIndex  OBJECT-TYPE
   SYNTAX  Integer32 
   MAX-ACCESS  read-write
   STATUS  current
   DESCRIPTION
       "Virtual server number."
   ::= {compStatPerServEntry 1}

compStatPerServVirtServiceIndex  OBJECT-TYPE
   SYNTAX  Integer32 
   MAX-ACCESS  read-write
   STATUS  current
   DESCRIPTION
       "Virtual server service index."
   ::= {compStatPerServEntry 2}

compStatPerServVirtServPort  OBJECT-TYPE
   SYNTAX  Integer32 
   MAX-ACCESS  read-write
   STATUS  current
   DESCRIPTION
       "Virtual server service port number."
   ::= {compStatPerServEntry 3}

compStatPerServCompPolId  OBJECT-TYPE
   SYNTAX  DisplayString 
   MAX-ACCESS  read-only
   STATUS  current
   DESCRIPTION
       "Compression policy identifier associated with the virtual service."
   ::= {compStatPerServEntry 4}

compStatPerServUnComprTputKb  OBJECT-TYPE
   SYNTAX  Integer32
   MAX-ACCESS  read-only
   STATUS  current
   DESCRIPTION
       "Total throughput of compressible object before compression counted during measuring period for virtual service."
   ::= {compStatPerServEntry 5}

compStatPerServComprTputKb  OBJECT-TYPE
   SYNTAX  Integer32
   MAX-ACCESS  read-only
   STATUS  current
   DESCRIPTION
       "Total throughput of compressible objects after compression counted during measuring period for virtual service."
   ::= {compStatPerServEntry 6}

compStatPerServAvgSizeBefComp  OBJECT-TYPE
   SYNTAX  Integer32
   MAX-ACCESS  read-only
   STATUS  current
   DESCRIPTION
       "Average object size before compression for virtual service."
   ::= {compStatPerServEntry 7}

compStatPerServAvgSizeAftComp  OBJECT-TYPE
   SYNTAX  Integer32
   MAX-ACCESS  read-only
   STATUS  current
   DESCRIPTION
       "Average object size after compression for virtual service."
   ::= {compStatPerServEntry 8}

compStatPerServAvgCompRatio  OBJECT-TYPE
   SYNTAX  Integer32
   MAX-ACCESS  read-only
   STATUS  current
   DESCRIPTION
       "Average compression ratio during measuring period for virtual service."
   ::= {compStatPerServEntry 9}

compStatPerServThrputCompRatio  OBJECT-TYPE
   SYNTAX  Integer32
   MAX-ACCESS  read-only
   STATUS  current
   DESCRIPTION
       "Effective compression ratio out of total traffic for virtual service."
   ::= {compStatPerServEntry 10}

compPerBrowRuleListStatsTable OBJECT-TYPE
   SYNTAX SEQUENCE OF CompPerBrowRuleListStatsEntry
   MAX-ACCESS not-accessible
   STATUS current
   DESCRIPTION
       "A table for compression statistics per rule list."
   ::= {compStats 8}

compPerBrowRuleListStatsEntry OBJECT-TYPE
   SYNTAX CompPerBrowRuleListStatsEntry 
   MAX-ACCESS not-accessible
   STATUS  current
   DESCRIPTION
       " The row definition for compression statistics per rule list table."
   INDEX  { compBrowRuleListIndex }
   ::= {compPerBrowRuleListStatsTable 1}

CompPerBrowRuleListStatsEntry  ::= SEQUENCE {
        compBrowRuleListIndex                          Integer32,
        compBrowRuleListId                             DisplayString,
        compBrowRuleListNumOfObj                       Integer32,
        compBrowRuleListSizeBefComp                    Integer32,
        compBrowRuleListSizeAftComp                    Integer32,
        compBrowRuleListCompRatio                      Integer32
        }

compBrowRuleListIndex  OBJECT-TYPE
   SYNTAX  Integer32
   MAX-ACCESS  read-only
   STATUS  current
   DESCRIPTION
       "Compression browsing rule list index."
   ::= {compPerBrowRuleListStatsEntry 1}

compBrowRuleListId  OBJECT-TYPE
   SYNTAX  DisplayString
   MAX-ACCESS  read-only
   STATUS  current
   DESCRIPTION
       "Compression browsing rule list identifier."
   ::= {compPerBrowRuleListStatsEntry 2}

compBrowRuleListNumOfObj  OBJECT-TYPE
   SYNTAX  Integer32
   MAX-ACCESS  read-only
   STATUS  current
   DESCRIPTION
       "Number of objects matched by this rule-list during measuring period."
   ::= {compPerBrowRuleListStatsEntry 3}

compBrowRuleListSizeBefComp  OBJECT-TYPE
   SYNTAX  Integer32
   MAX-ACCESS  read-only
   STATUS  current
   DESCRIPTION
       "Total size of all matched objects by this browser rule-list before compression."
   ::= {compPerBrowRuleListStatsEntry 4}

compBrowRuleListSizeAftComp  OBJECT-TYPE
   SYNTAX  Integer32
   MAX-ACCESS  read-only
   STATUS  current
   DESCRIPTION
       "Total size of all matched objects by this browser rule-list after compression."
   ::= {compPerBrowRuleListStatsEntry 5}

compBrowRuleListCompRatio  OBJECT-TYPE
   SYNTAX  Integer32
   MAX-ACCESS  read-only
   STATUS  current
   DESCRIPTION
       "Compression ratio per rule list."
   ::= {compPerBrowRuleListStatsEntry 6}

compPerBrowRuleStatsTable OBJECT-TYPE
   SYNTAX SEQUENCE OF CompPerBrowRuleStatsEntry
   MAX-ACCESS not-accessible
   STATUS current
   DESCRIPTION
       "A table for compression statistics per browser rule."
   ::= {compStats 9}

compPerBrowRuleStatsEntry OBJECT-TYPE
   SYNTAX CompPerBrowRuleStatsEntry 
   MAX-ACCESS not-accessible
   STATUS  current
   DESCRIPTION
       " The row definition for compression statistics per browser rule."
   INDEX  { compBrowRuleRuleListIndex, compBrowRuleIndex }
   ::= {compPerBrowRuleStatsTable 1}

CompPerBrowRuleStatsEntry  ::= SEQUENCE {
        compBrowRuleRuleListIndex               Integer32,
        compBrowRuleIndex                       Integer32,
        compBrowRuleRuleListId                  DisplayString,
        compBrowRuleNumOfObj                    Integer32,
        compBrowRuleSizeBefComp                 Integer32,
        compBrowRuleSizeAftComp                 Integer32,
        compBrowRuleCompRatio                   Integer32
        }

compBrowRuleRuleListIndex  OBJECT-TYPE
   SYNTAX  Integer32
   MAX-ACCESS  read-only
   STATUS  current
   DESCRIPTION
       "Compression browser rule rule-list index."
   ::= {compPerBrowRuleStatsEntry 1}

compBrowRuleIndex  OBJECT-TYPE
   SYNTAX  Integer32
   MAX-ACCESS  read-only
   STATUS  current
   DESCRIPTION
       "Compression browser rule index."
   ::= {compPerBrowRuleStatsEntry 2}

compBrowRuleRuleListId  OBJECT-TYPE
   SYNTAX  DisplayString
   MAX-ACCESS  read-only
   STATUS  current
   DESCRIPTION
       "Compression browser rule rule-list identifier."
   ::= {compPerBrowRuleStatsEntry 3}

compBrowRuleNumOfObj  OBJECT-TYPE
   SYNTAX  Integer32
   MAX-ACCESS  read-only
   STATUS  current
   DESCRIPTION
       "Number of objects matched by this browser rule during measuring period."
   ::= {compPerBrowRuleStatsEntry 4}

compBrowRuleSizeBefComp  OBJECT-TYPE
   SYNTAX  Integer32
   MAX-ACCESS  read-only
   STATUS  current
   DESCRIPTION
       "Total size of all matched objects for this browser rule before compression."
   ::= {compPerBrowRuleStatsEntry 5}

compBrowRuleSizeAftComp  OBJECT-TYPE
   SYNTAX  Integer32
   MAX-ACCESS  read-only
   STATUS  current
   DESCRIPTION
       "Total size of all matched objects for this browser rule after compression."
   ::= {compPerBrowRuleStatsEntry 6}

compBrowRuleCompRatio  OBJECT-TYPE
   SYNTAX  Integer32
   MAX-ACCESS  read-only
   STATUS  current
   DESCRIPTION
       "Compression ratio per browser rule."
   ::= {compPerBrowRuleStatsEntry 7}

compPerUrlRuleListStatsTable OBJECT-TYPE
   SYNTAX SEQUENCE OF CompPerUrlRuleListStatsEntry 
   MAX-ACCESS not-accessible
   STATUS current
   DESCRIPTION
       "A table for compression statistics per URL Rule list."
   ::= {compStats 10}

compPerUrlRuleListStatsEntry OBJECT-TYPE
   SYNTAX CompPerUrlRuleListStatsEntry
   MAX-ACCESS not-accessible
   STATUS  current
   DESCRIPTION
       " The row definition for this table."
   INDEX  { compUrlRuleListIndex }
   ::= {compPerUrlRuleListStatsTable 1}

CompPerUrlRuleListStatsEntry  ::= SEQUENCE {
        compUrlRuleListIndex                        Integer32,
        compUrlRuleListId                           DisplayString,
        compUrlRuleListNumOfObj                     Integer32,
        compUrlRuleListSizeBefComp                  Integer32,
        compUrlRuleListSizeAftComp                  Integer32,
        compUrlRuleListCompRatio                    Integer32
        }

compUrlRuleListIndex  OBJECT-TYPE
   SYNTAX  Integer32
   MAX-ACCESS  read-only
   STATUS  current
   DESCRIPTION
       "Compression url rule list index."
   ::= {compPerUrlRuleListStatsEntry 1}

compUrlRuleListId  OBJECT-TYPE
   SYNTAX  DisplayString
   MAX-ACCESS  read-only
   STATUS  current
   DESCRIPTION
       "Compression url rule list identifier."
   ::= {compPerUrlRuleListStatsEntry 2}

compUrlRuleListNumOfObj OBJECT-TYPE
   SYNTAX  Integer32
   MAX-ACCESS  read-only
   STATUS  current
   DESCRIPTION
       "Number of objects matched by this url rule list during measuring period."
   ::= {compPerUrlRuleListStatsEntry 3}

compUrlRuleListSizeBefComp  OBJECT-TYPE
   SYNTAX  Integer32
   MAX-ACCESS  read-only
   STATUS  current
   DESCRIPTION
       "Total size of all matched objects for this url rule list before compression."
   ::= {compPerUrlRuleListStatsEntry 4}

compUrlRuleListSizeAftComp  OBJECT-TYPE
   SYNTAX  Integer32
   MAX-ACCESS  read-only
   STATUS  current
   DESCRIPTION
       "Total size of all matched objects this url rule list after compression."
   ::= {compPerUrlRuleListStatsEntry 5}

compUrlRuleListCompRatio  OBJECT-TYPE
   SYNTAX  Integer32
   MAX-ACCESS  read-only
   STATUS  current
   DESCRIPTION
       "Compression ratio for this url rule list."
   ::= {compPerUrlRuleListStatsEntry 6}

compPerUrlRuleStatsTable OBJECT-TYPE
   SYNTAX SEQUENCE OF CompPerUrlRuleStatsEntry 
   MAX-ACCESS not-accessible
   STATUS current
   DESCRIPTION
       "A table for compression statistics per URL Rule."
   ::= {compStats 11}

compPerUrlRuleStatsEntry OBJECT-TYPE
   SYNTAX CompPerUrlRuleStatsEntry
   MAX-ACCESS not-accessible
   STATUS  current
   DESCRIPTION
       " The row definition for this table."
   INDEX  { compUrlRuleRuleListIndex, compUrlRuleIndex }
   ::= {compPerUrlRuleStatsTable 1}

CompPerUrlRuleStatsEntry  ::= SEQUENCE {
        compUrlRuleRuleListIndex               Integer32,
        compUrlRuleIndex                       Integer32,
        compUrlRuleRuleListId                  DisplayString,
        compUrlRuleNumOfObj                    Integer32,
        compUrlRuleSizeBefComp                 Integer32,
        compUrlRuleSizeAftComp                 Integer32,
        compUrlRuleCompRatio                   Integer32
        }

compUrlRuleRuleListIndex  OBJECT-TYPE
   SYNTAX  Integer32
   MAX-ACCESS  read-only
   STATUS  current
   DESCRIPTION
       "Compression url rule rule-list index."
   ::= {compPerUrlRuleStatsEntry 1}

compUrlRuleIndex  OBJECT-TYPE
   SYNTAX  Integer32
   MAX-ACCESS  read-only
   STATUS  current
   DESCRIPTION
       "Compression url rule index."
   ::= {compPerUrlRuleStatsEntry 2}

compUrlRuleRuleListId  OBJECT-TYPE
   SYNTAX  DisplayString
   MAX-ACCESS  read-only
   STATUS  current
   DESCRIPTION
       "Compression url rule rule-list identifier."
   ::= {compPerUrlRuleStatsEntry 3}

compUrlRuleNumOfObj OBJECT-TYPE
   SYNTAX  Integer32
   MAX-ACCESS  read-only
   STATUS  current
   DESCRIPTION
       "Number of objects matched by this url rule during measuring period."
   ::= {compPerUrlRuleStatsEntry 4}

compUrlRuleSizeBefComp  OBJECT-TYPE
   SYNTAX  Integer32
   MAX-ACCESS  read-only
   STATUS  current
   DESCRIPTION
       "Total size of all matched objects for this url rule before compression."
   ::= {compPerUrlRuleStatsEntry 5}

compUrlRuleSizeAftComp  OBJECT-TYPE
   SYNTAX  Integer32
   MAX-ACCESS  read-only
   STATUS  current
   DESCRIPTION
       "Total size of all matched objects for this url rule after compression."
   ::= {compPerUrlRuleStatsEntry 6}

compUrlRuleCompRatio  OBJECT-TYPE
   SYNTAX  Integer32
   MAX-ACCESS  read-only
   STATUS  current
   DESCRIPTION
       "Compression ratio for this url rule."
   ::= {compPerUrlRuleStatsEntry 7}

sslOffNewHandShake OBJECT-TYPE
   SYNTAX  Integer32 
   MAX-ACCESS  read-only
   STATUS  current
   DESCRIPTION
       "Number of new SSL handshakes between clients and AAS per second."
   ::= {sslSlbStats 11}

sslOffReusedHandShake OBJECT-TYPE
   SYNTAX  Integer32 
   MAX-ACCESS  read-only
   STATUS  current
   DESCRIPTION
       "Number of existing SSL handshakes reused by clients to communicate with AAS per second."
   ::= {sslSlbStats 12}

sslOffPerReusedHandShake OBJECT-TYPE
   SYNTAX  Integer32 
   MAX-ACCESS  read-only
   STATUS  current
   DESCRIPTION
       "Percentage of SSL session re-using keys."
   ::= {sslSlbStats 13}

sslOffPercSessUsingSSLv2 OBJECT-TYPE
   SYNTAX  Integer32 
   MAX-ACCESS  read-only
   STATUS  current
   DESCRIPTION
       "Percentage of session using SSLv2 out of all session during measuring period."
   ::= {sslSlbStats 14}

sslOffPercSessUsingSSLv3 OBJECT-TYPE
   SYNTAX  INTEGER
   MAX-ACCESS  read-only
   STATUS  current
   DESCRIPTION
       "Percentage of session using SSLv3 out of all session during measuring period."
   ::= {sslSlbStats 15}

sslOffPercSessUsingTLS OBJECT-TYPE
   SYNTAX  INTEGER
   MAX-ACCESS  read-only
   STATUS  current
   DESCRIPTION
       "Percentage of session using TLS1.0 out of all session during measuring period."
   ::= {sslSlbStats 16}

sslOffPerServStatsTable OBJECT-TYPE
   SYNTAX SEQUENCE OF SslOffPerServStatsEntry
   MAX-ACCESS not-accessible
   STATUS current
   DESCRIPTION
       "A table for SSL statistics per virtual service."
   ::= {sslSlbStats 17}

sslOffPerServStatsEntry OBJECT-TYPE
   SYNTAX SslOffPerServStatsEntry
   MAX-ACCESS not-accessible
   STATUS  current
   DESCRIPTION
       " The row definition for SSL statistics per virtual service table."
   INDEX  { sslOffPerServVirtServIndex, sslOffPerServVirtServiceIndex}
   ::= {sslOffPerServStatsTable 1}

SslOffPerServStatsEntry  ::= SEQUENCE {
        sslOffPerServVirtServIndex           Integer32,
        sslOffPerServVirtServiceIndex        Integer32,
	sslOffPerServVirtServPort            Integer32,
	sslOffPerServSslPolId                DisplayString,
        sslOffPerServNewhandShake            Integer32,
        sslOffPerServReusedhandShake         Integer32,
        sslOffPerServPercReusedhandShake     Integer32,
        sslOffPerServSessUsingSSLv2          Integer32,
        sslOffPerServSessUsingSSLv3          Integer32,
        sslOffPerServSessUsingTLS            Integer32,
        sslOffPerServSessUsingTLS11          Integer32
        }

sslOffPerServVirtServIndex  OBJECT-TYPE
   SYNTAX  Integer32 
   MAX-ACCESS  read-only
   STATUS  current
   DESCRIPTION
       "Virtual server number."
   ::= {sslOffPerServStatsEntry 1}

sslOffPerServVirtServiceIndex  OBJECT-TYPE
   SYNTAX  Integer32 
   MAX-ACCESS  read-only
   STATUS  current
   DESCRIPTION
       "Virtual server service index."
   ::= {sslOffPerServStatsEntry 2}

sslOffPerServVirtServPort  OBJECT-TYPE
   SYNTAX  Integer32 
   MAX-ACCESS  read-only
   STATUS  current
   DESCRIPTION
       "Virtual server service port number."
   ::= {sslOffPerServStatsEntry 3}

sslOffPerServSslPolId  OBJECT-TYPE
   SYNTAX  DisplayString 
   MAX-ACCESS  read-only
   STATUS  current
   DESCRIPTION
       "SSL policy identifier associated with the virtual service."
   ::= {sslOffPerServStatsEntry 4}

sslOffPerServNewhandShake  OBJECT-TYPE
   SYNTAX  Integer32
   MAX-ACCESS  read-only
   STATUS  current
   DESCRIPTION
       "Number of New SSL handshakes between Clients and AAS per second for this virtual service."
   ::= {sslOffPerServStatsEntry 5}

sslOffPerServReusedhandShake OBJECT-TYPE
   SYNTAX  Integer32
   MAX-ACCESS  read-only
   STATUS  current
   DESCRIPTION
       "Number of existing SSL handshakes re-used by clients to communicate with AAS per second for virtual service."
   ::= {sslOffPerServStatsEntry 6}

sslOffPerServPercReusedhandShake OBJECT-TYPE
   SYNTAX  Integer32
   MAX-ACCESS  read-only
   STATUS  current
   DESCRIPTION
       "Percentage of SSL session re-using keys for virtual service."
   ::= {sslOffPerServStatsEntry 7}

sslOffPerServSessUsingSSLv2  OBJECT-TYPE
   SYNTAX  Integer32
   MAX-ACCESS  read-only
   STATUS  current
   DESCRIPTION
       "Percentage of session using SSLv2 out of all session during measuring period for virtual service."
   ::= {sslOffPerServStatsEntry 8}

sslOffPerServSessUsingSSLv3 OBJECT-TYPE
   SYNTAX  Integer32
   MAX-ACCESS  read-only
   STATUS  current
   DESCRIPTION
       "Percentage of session using SSLv3 out of all session during measuring period for virtual service."
   ::= {sslOffPerServStatsEntry 9}

sslOffPerServSessUsingTLS OBJECT-TYPE
   SYNTAX  Integer32
   MAX-ACCESS  read-only
   STATUS  current
   DESCRIPTION
       "Percentage of session using TLS1.0 out of all session during measuring period for virtual service."
   ::= {sslOffPerServStatsEntry 10}

sslOffPerServSessUsingTLS11 OBJECT-TYPE
   SYNTAX  Integer32
   MAX-ACCESS  read-only
   STATUS  current
   DESCRIPTION
       "Percentage of session using TLS1.1 out of all session during measuring period for virtual service."
   ::= {sslOffPerServStatsEntry 11}

sslOffPercSessUsingTLS11 OBJECT-TYPE
   SYNTAX  INTEGER
   MAX-ACCESS  read-only
   STATUS  current
   DESCRIPTION
       "Percentage of session using TLS1.1 out of all session during measuring period."
   ::= {sslSlbStats 18}

httpStatSummCliusingKeepAliv  OBJECT-TYPE
   SYNTAX  Integer32
   MAX-ACCESS  read-only
   STATUS  current
   DESCRIPTION
       "Number of clients sending connection: keep-alive."
   ::= {httpStats 1}

httpStatSummHTTP10Per OBJECT-TYPE
   SYNTAX  Integer32
   MAX-ACCESS  read-only
   STATUS  current
   DESCRIPTION
       "Percent of requests done using HTTP 1.0 during the measuring period."
   ::= {httpStats 2}

httpStatSummHTTP11Per  OBJECT-TYPE
   SYNTAX  Integer32
   MAX-ACCESS  read-only
   STATUS  current
   DESCRIPTION
       "Percent of requests done using HTTP 1.1 during measuring period."
   ::= {httpStats 3}

httpStatSummHttpToHttpsRedir  OBJECT-TYPE
   SYNTAX  Integer32
   MAX-ACCESS  read-only
   STATUS  current
   DESCRIPTION
       "Number of HTTP redirect location headers updated from HTTP to HTTPS by AAS."
   ::= {httpStats 4}

httpStatSummAvgNumReqPerConn OBJECT-TYPE
   SYNTAX  Integer32
   MAX-ACCESS  read-only
   STATUS  current
   DESCRIPTION
       "The average number of requests done over each client connection."
   ::= {httpStats 5}

httpStatSummResSmall1Kb  OBJECT-TYPE
   SYNTAX  Integer32
   MAX-ACCESS  read-only
   STATUS  current
   DESCRIPTION
       "Number of responses for which content size reported smaller than 1KB."
   ::= {httpStats 6}

httpStatSummRes1KbTo10Kb  OBJECT-TYPE
   SYNTAX  Integer32
   MAX-ACCESS  read-only
   STATUS  current
   DESCRIPTION
       "Number of responses for which content size reported  between 1KB and 10KB."
   ::= {httpStats 7}

httpStatSummRes11KbTo50Kb  OBJECT-TYPE
   SYNTAX  Integer32
   MAX-ACCESS  read-only
   STATUS  current
   DESCRIPTION
       "Number of responses for which content size reported between 11KB and 50KB."
   ::= {httpStats 8}

httpStatSummRes51KbTo100Kb  OBJECT-TYPE
   SYNTAX  Integer32
   MAX-ACCESS  read-only
   STATUS  current
   DESCRIPTION
       "Number of responses for which content size reported between 51KB and 100KB."
   ::= {httpStats 9}

httpStatSummResLarger100Kb  OBJECT-TYPE
   SYNTAX  Integer32
   MAX-ACCESS  read-only
   STATUS  current
   DESCRIPTION
       "Number of responses for which content size reported larger than 100KB."
   ::= {httpStats 10}

httpTransSummReqCliToAas  OBJECT-TYPE
   SYNTAX  Integer32
   MAX-ACCESS  read-only
   STATUS  current
   DESCRIPTION
       "Number of clients requests from AAS done in the measuring period ."
   ::= {httpStats 11}

httpTransSummReqAasToSer  OBJECT-TYPE
   SYNTAX  Integer32
   MAX-ACCESS  read-only
   STATUS  current
   DESCRIPTION
       "Number of AAS requests from servers done in the measuring period."
   ::= {httpStats 12}

httpTransSummResSerToAas  OBJECT-TYPE
   SYNTAX  Integer32
   MAX-ACCESS  read-only
   STATUS  current
   DESCRIPTION
       "Number of servers responses to AAS in the measuring period."
   ::= {httpStats 13}

httpTransSummResAasToCli  OBJECT-TYPE
   SYNTAX  Integer32
   MAX-ACCESS  read-only
   STATUS  current
   DESCRIPTION
       "Number of AAS responses to clients in the measuring period."
   ::= {httpStats 14}

httpTransSummTransRate  OBJECT-TYPE
   SYNTAX  Integer32
   MAX-ACCESS  read-only
   STATUS  current
   DESCRIPTION
       "HTTP transactions per second."
   ::= {httpStats 15}

httpPerServStatsTable OBJECT-TYPE
   SYNTAX SEQUENCE OF HttpPerServStatsEntry
   MAX-ACCESS not-accessible
   STATUS current
   DESCRIPTION
       "A table for HTTP statistics per virtual service."
   ::= {httpStats 16}

httpPerServStatsEntry OBJECT-TYPE
   SYNTAX HttpPerServStatsEntry 
   MAX-ACCESS not-accessible
   STATUS  current
   DESCRIPTION
       " The row definition for HTTP statistics per virtual service table."
   INDEX  { httpPerServStatsVirtServIndex, httpPerServStatsVirtServiceIndex}
   ::= {httpPerServStatsTable 1}

HttpPerServStatsEntry  ::= SEQUENCE {
        httpPerServStatsVirtServIndex       Integer32,
        httpPerServStatsVirtServiceIndex    Integer32,
	httpPerServStatsVirtServPort        Integer32,
        httpPerServStatsCliUseKeepAlive     Integer32,
	httpPerServStatsHttp10VsHttp11Ratio Integer32,
	httpPerServStatsHttpToHTTPSRedir    Integer32,
	httpPerServStatsAvgNumReqPerConn    Integer32,
	httpPerServStatsRespSmall1Kb        Integer32,
	httpPerServStatsResp1KbTo10Kb       Integer32,
        httpPerServStatsResp11KbTo50Kb      Integer32,
	httpPerServStatsResp51KbTo100Kb     Integer32,
	httpPerServStatsRespLarger100Kb     Integer32,
        httpPerServStatsReqCliToAas         Integer32,
        httpPerServStatsReqAasToSer         Integer32,
        httpPerServStatsRespSerToAas        Integer32,
	httpPerServStatsRespAasToCli        Integer32,
	httpPerServStatsTransRate           Integer32
        }

httpPerServStatsVirtServIndex  OBJECT-TYPE
   SYNTAX  Integer32 
   MAX-ACCESS  read-write
   STATUS  current
   DESCRIPTION
       "Virtual server number."
   ::= {httpPerServStatsEntry 1}

httpPerServStatsVirtServiceIndex  OBJECT-TYPE
   SYNTAX  Integer32 
   MAX-ACCESS  read-write
   STATUS  current
   DESCRIPTION
       "Virtual server service index."
   ::= {httpPerServStatsEntry 2}

httpPerServStatsVirtServPort  OBJECT-TYPE
   SYNTAX  Integer32 
   MAX-ACCESS  read-write
   STATUS  current
   DESCRIPTION
       "Virtual server service port number."
   ::= {httpPerServStatsEntry 3}

httpPerServStatsCliUseKeepAlive  OBJECT-TYPE
   SYNTAX  Integer32
   MAX-ACCESS  read-only
   STATUS  current
   DESCRIPTION
       "Number of clients sending Connection: Keep-Alive for virtual service."
   ::= {httpPerServStatsEntry 4}

httpPerServStatsHttp10VsHttp11Ratio  OBJECT-TYPE
   SYNTAX  Integer32
   MAX-ACCESS  read-only
   STATUS  current
   DESCRIPTION
       "Ratio of requests done using HTTP 1.0 and HTTP 1.1 during measuring period for virtual service."
   ::= {httpPerServStatsEntry 5}

httpPerServStatsHttpToHTTPSRedir  OBJECT-TYPE
   SYNTAX  Integer32
   MAX-ACCESS  read-only
   STATUS  current
   DESCRIPTION
       "Number of HTTP redirect location headers updated from HTTP to HTTPS by AAS for virtual service."
   ::= {httpPerServStatsEntry 6}

httpPerServStatsAvgNumReqPerConn OBJECT-TYPE
   SYNTAX  Integer32
   MAX-ACCESS  read-only
   STATUS  current
   DESCRIPTION
       "The average number of requests done over each client connection for virtual service."
   ::= {httpPerServStatsEntry 7}

httpPerServStatsRespSmall1Kb  OBJECT-TYPE
   SYNTAX  Integer32
   MAX-ACCESS  read-only
   STATUS  current
   DESCRIPTION
       "Number of responses for which content size reported smaller than 1KB for virtual service."
   ::= {httpPerServStatsEntry 8}

httpPerServStatsResp1KbTo10Kb  OBJECT-TYPE
   SYNTAX  Integer32
   MAX-ACCESS  read-only
   STATUS  current
   DESCRIPTION
       "Number of responses for which content size reported  between 1KB and 10KB for virtual service."
   ::= {httpPerServStatsEntry 9}

httpPerServStatsResp11KbTo50Kb  OBJECT-TYPE
   SYNTAX  Integer32
   MAX-ACCESS  read-only
   STATUS  current
   DESCRIPTION
       "Number of responses for which content size reported between 11KB and 50KB for virtual service."
   ::= {httpPerServStatsEntry 10}

httpPerServStatsResp51KbTo100Kb  OBJECT-TYPE
   SYNTAX  Integer32
   MAX-ACCESS  read-only
   STATUS  current
   DESCRIPTION
       "Number of responses for which content size reported between 51KB and 100KB for virtual service."
   ::= {httpPerServStatsEntry 11}

httpPerServStatsRespLarger100Kb  OBJECT-TYPE
   SYNTAX  Integer32
   MAX-ACCESS  read-only
   STATUS  current
   DESCRIPTION
       "Number of responses for which content size reported larger than 100KB for virtual service."
   ::= {httpPerServStatsEntry 12}

httpPerServStatsReqCliToAas  OBJECT-TYPE
   SYNTAX  Integer32
   MAX-ACCESS  read-only
   STATUS  current
   DESCRIPTION
       "Number of clients requests from AAS done in the measuring period for virtual service."
   ::= {httpPerServStatsEntry 13}

httpPerServStatsReqAasToSer  OBJECT-TYPE
   SYNTAX  Integer32
   MAX-ACCESS  read-only
   STATUS  current
   DESCRIPTION
       "Number of AAS requests from servers done in the measuring period for virtual service."
   ::= {httpPerServStatsEntry 14}

httpPerServStatsRespSerToAas  OBJECT-TYPE
   SYNTAX  Integer32
   MAX-ACCESS  read-only
   STATUS  current
   DESCRIPTION
       "Number of servers responses to AAS in the measuring period for virtual service."
   ::= {httpPerServStatsEntry 15}

httpPerServStatsRespAasToCli  OBJECT-TYPE
   SYNTAX  Integer32
   MAX-ACCESS  read-only
   STATUS  current
   DESCRIPTION
       "Number of AAS responses to clients in the measuring period for virtual service."
   ::= {httpPerServStatsEntry 16}

httpPerServStatsTransRate  OBJECT-TYPE
   SYNTAX  Integer32
   MAX-ACCESS  read-only
   STATUS  current
   DESCRIPTION
       "Transactions rate for virtual service."
   ::= {httpPerServStatsEntry 17}

connmngStatSummServConn  OBJECT-TYPE
   SYNTAX  Integer32
   MAX-ACCESS  read-only
   STATUS  current
   DESCRIPTION
       "Number of concurrent backend server connections."
   ::= {connmngStats 1}

connmngStatSummCliReq OBJECT-TYPE
   SYNTAX  Integer32
   MAX-ACCESS  read-only
   STATUS  current
   DESCRIPTION
       "Number of client requests passed to AX."
   ::= {connmngStats 2}

connmngStatSummMulRatio OBJECT-TYPE
   SYNTAX  Integer32
   MAX-ACCESS  read-only
   STATUS  current
   DESCRIPTION
       "Connection multiplexing ratio."
   ::= {connmngStats 3}

connmngPerServStatsTable OBJECT-TYPE
   SYNTAX SEQUENCE OF ConnmngPerServStatsEntry
   MAX-ACCESS not-accessible
   STATUS current
   DESCRIPTION
       "A table for connection management statistics per virtual service."
   ::= {connmngStats 4}

connmngPerServStatsEntry OBJECT-TYPE
   SYNTAX ConnmngPerServStatsEntry 
   MAX-ACCESS not-accessible
   STATUS  current
   DESCRIPTION
       " The row definition for connection management statistics per virtual service table."
   INDEX  { connmngPerServStatsVirtServIndex, connmngPerServStatsVirtServiceIndex}
   ::= {connmngPerServStatsTable 1}

ConnmngPerServStatsEntry  ::= SEQUENCE {
        connmngPerServStatsVirtServIndex       Integer32,
        connmngPerServStatsVirtServiceIndex    Integer32,
        connmngPerServStatsVirtServPort        Integer32,          
        connmngPerServStatsServConn            Integer32,
        connmngPerServStatsCliReq              Integer32,
        connmngPerServStatsMulRatio            Integer32
        }

connmngPerServStatsVirtServIndex  OBJECT-TYPE
   SYNTAX  Integer32 
   MAX-ACCESS  read-write
   STATUS  current
   DESCRIPTION
       "Virtual server number."
   ::= {connmngPerServStatsEntry 1}

connmngPerServStatsVirtServiceIndex  OBJECT-TYPE
   SYNTAX  Integer32 
   MAX-ACCESS  read-write
   STATUS  current
   DESCRIPTION
       "Virtual server service index."
   ::= {connmngPerServStatsEntry 2}

connmngPerServStatsVirtServPort  OBJECT-TYPE
   SYNTAX  Integer32 
   MAX-ACCESS  read-write
   STATUS  current
   DESCRIPTION
       "Virtual server service port number."
   ::= {connmngPerServStatsEntry 3}

connmngPerServStatsServConn  OBJECT-TYPE
   SYNTAX  Integer32
   MAX-ACCESS  read-only
   STATUS  current
   DESCRIPTION
       "Number of concurrent backend server connections for virtual service."
   ::= {connmngPerServStatsEntry 4}

connmngPerServStatsCliReq  OBJECT-TYPE
   SYNTAX  Integer32
   MAX-ACCESS  read-only
   STATUS  current
   DESCRIPTION
       "Number of client requests passed to AX for virtual service."
   ::= {connmngPerServStatsEntry 5}

connmngPerServStatsMulRatio  OBJECT-TYPE
   SYNTAX  Integer32
   MAX-ACCESS  read-only
   STATUS  current
   DESCRIPTION
       "Connection multiplexing ratio for virtual service."
   ::= {connmngPerServStatsEntry 6}



slbSapAslrTableMaxSize OBJECT-TYPE
    SYNTAX  Integer32 
    MAX-ACCESS  read-only 
    STATUS  current 
    DESCRIPTION 
        "The maximum number of entries in SAP ASLR connection management table." 
    ::= { sapCfg 1 }

slbCurCfgSapAslrTable OBJECT-TYPE
    SYNTAX  SEQUENCE OF SlbCurCfgSapAslrEntry 
    MAX-ACCESS  not-accessible
    STATUS  current
    DESCRIPTION
        "The SAP ASLR connection management  table."
    ::= { sapCfg 2 }

slbCurCfgSapAslrEntry OBJECT-TYPE
    SYNTAX  SlbCurCfgSapAslrEntry
    MAX-ACCESS  not-accessible
    STATUS  current
    DESCRIPTION
        "A row in the SAP ASLR connection management table."
    INDEX   { slbCurCfgSapAslrIndex }
    ::= { slbCurCfgSapAslrTable 1 }

SlbCurCfgSapAslrEntry ::= SEQUENCE {
    slbCurCfgSapAslrIndex           Integer32,
    slbCurCfgSapAslrIpAddr          IpAddress,
    slbCurCfgSapAslrIpv6Addr     DisplayString,
    slbCurCfgSapAslrIpVer            INTEGER,
    slbCurCfgSapAslrPortNum      INTEGER,
    slbCurCfgSapAslrVipAddr       IpAddress,
    slbCurCfgSapAslrVipv6Addr   DisplayString,
    slbCurCfgSapAslrVipIpVer      INTEGER,
    slbCurCfgSapAslrInterval        INTEGER,
    slbCurCfgSapAslrState            INTEGER,
    slbCurCfgSapAslrName           DisplayString,
    slbCurCfgSapAslrLastAct        DisplayString,
    slbCurCfgSapAslrAutoConfig  INTEGER,
    slbCurCfgSapAslrSessionInfo INTEGER,
    slbCurCfgSapAslrDelete          INTEGER,
    slbCurCfgSapAslrSignature    DisplayString,
    slbCurCfgSapAslrServCert      DisplayString
    }

slbCurCfgSapAslrIndex OBJECT-TYPE
    SYNTAX  Integer32
    MAX-ACCESS  read-only
    STATUS  current
    DESCRIPTION
        "The Sap Aslr number" 
    ::= { slbCurCfgSapAslrEntry 1 }

slbCurCfgSapAslrIpAddr OBJECT-TYPE
    SYNTAX  IpAddress
    MAX-ACCESS  read-only
    STATUS  current
    DESCRIPTION
        "IP address of the Sap Aslr identified by the instance of the 
         slbCurCfgSapAslrIndex." 
    ::= { slbCurCfgSapAslrEntry 2 }

slbCurCfgSapAslrIpv6Addr OBJECT-TYPE
   SYNTAX DisplayString (SIZE(0..40))
    MAX-ACCESS  read-only
    STATUS  current
    DESCRIPTION
    "  IPV6 address of the Sap Aslr manager identified by the instance of the slbCurCfgSapAslrIndex
       Address should be 4-byte haxadecimal colon notation. Valid IPv6 address should be in
       any of the following forms xxxx:xxxx:xxxx:xxxx:xxxx:xxxx:xxxx:xxxx or xxxx::xxxx:xxxx:xxxx:xxxx or ::xxxx "
   ::= { slbCurCfgSapAslrEntry 3 }


slbCurCfgSapAslrIpVer OBJECT-TYPE
    SYNTAX  INTEGER{
        ipv4(1),
        ipv6(2)
        }
    MAX-ACCESS  read-only
    STATUS  current
    DESCRIPTION
        "The type of IP address."
    ::= { slbCurCfgSapAslrEntry 4  }


slbCurCfgSapAslrPortNum OBJECT-TYPE  
    SYNTAX  INTEGER (2..65534)
    MAX-ACCESS  read-only  
    STATUS  current  
    DESCRIPTION 
        "The Sap Aslr service port number."  
    ::= { slbCurCfgSapAslrEntry 5 } 


slbCurCfgSapAslrVipAddr OBJECT-TYPE
    SYNTAX  IpAddress
    MAX-ACCESS  read-only
    STATUS  current
    DESCRIPTION
        "IP address of the VIP identified by the instance of the 
         slbNewCfgSapAslrIndex." 
    ::= { slbCurCfgSapAslrEntry 6 }

slbCurCfgSapAslrVipv6Addr OBJECT-TYPE
   SYNTAX DisplayString (SIZE(0..40))
    MAX-ACCESS  read-only
    STATUS  current
    DESCRIPTION
    "  IPV6 address of the VIP identified by the instance of the slbNewCfgSapAslrIndex
       Address should be 4-byte haxadecimal colon notation. Valid IPv6 address should be in
       any of the following forms xxxx:xxxx:xxxx:xxxx:xxxx:xxxx:xxxx:xxxx or xxxx::xxxx:xxxx:xxxx:xxxx or ::xxxx "
   ::= { slbCurCfgSapAslrEntry 7 }

slbCurCfgSapAslrVipIpVer OBJECT-TYPE
    SYNTAX  INTEGER{
        ipv4(1),
        ipv6(2)
        }
    MAX-ACCESS  read-only
    STATUS  current
    DESCRIPTION
        "The type of VIP IP address."
    ::= { slbCurCfgSapAslrEntry 8  }

slbCurCfgSapAslrInterval OBJECT-TYPE
    SYNTAX  INTEGER (1..60)
    MAX-ACCESS  read-only
    STATUS  current
    DESCRIPTION
        "Set the Sap Aslr server inspection interval." 
    ::= { slbCurCfgSapAslrEntry 9 }


slbCurCfgSapAslrState OBJECT-TYPE
    SYNTAX  INTEGER {
	enabled(1),
	disabled(2)
	}
    MAX-ACCESS  read-only
    STATUS  current
    DESCRIPTION
        "Enable or disable the Sap Aslr server sampling." 
    ::= { slbCurCfgSapAslrEntry 10 }

slbCurCfgSapAslrName OBJECT-TYPE 
    SYNTAX  DisplayString (SIZE(0..31))
    MAX-ACCESS  read-only 
    STATUS  current 
    DESCRIPTION 
        "The name of the Sap Aslr connection."  
    ::= { slbCurCfgSapAslrEntry 11 }

slbCurCfgSapAslrLastAct OBJECT-TYPE 
    SYNTAX  DisplayString (SIZE(0..31))
    MAX-ACCESS  read-only 
    STATUS  current 
    DESCRIPTION 
        "The Sap Aslr connection last activity time stamp."  
    ::= { slbCurCfgSapAslrEntry 12 }

slbCurCfgSapAslrAutoConfig OBJECT-TYPE
    SYNTAX  INTEGER {
        basic(1),
        full(2)
        }
    MAX-ACCESS  read-create
    STATUS  current
    DESCRIPTION
        "Defines the configuration update process.  
         When set the value to basic (1), the configuration is limited,
	 comparing to full (2)"
    ::= { slbCurCfgSapAslrEntry 13 }

slbCurCfgSapAslrSessionInfo  OBJECT-TYPE
 SYNTAX  INTEGER 
    MAX-ACCESS  read-only
    STATUS  current
    DESCRIPTION
        "Set the Sap Aslr session information.
	When read, zero is returned." 
    ::= { slbCurCfgSapAslrEntry 14 }


slbCurCfgSapAslrDelete OBJECT-TYPE
    SYNTAX  INTEGER {
        other(1),
        delete(2)
        }
    MAX-ACCESS  read-only
    STATUS  current
    DESCRIPTION
        "When set to the value of 2 (delete), the entire row is deleted. 
         When read, other(1) is returned. Setting the value to anything 
         other than 2(delete) has no effect on the state of the row."
    ::= { slbCurCfgSapAslrEntry 15 }



slbCurCfgSapAslrSignature OBJECT-TYPE 
    SYNTAX  DisplayString (SIZE(0..40))
    MAX-ACCESS  read-only 
    STATUS  current 
    DESCRIPTION 
        "The Sap Aslr connection signature."  
    ::= { slbCurCfgSapAslrEntry 16 }

slbCurCfgSapAslrServCert OBJECT-TYPE
    SYNTAX  DisplayString  (SIZE(0..32))
    MAX-ACCESS  read-create
    STATUS  current
    DESCRIPTION
        "Server Certificate name associated with this virtual service."
    ::= { slbCurCfgSapAslrEntry 17 }

slbNewCfgSapAslrTable OBJECT-TYPE
    SYNTAX  SEQUENCE OF SlbNewCfgSapAslrEntry 
    MAX-ACCESS  not-accessible
    STATUS  current
    DESCRIPTION
        "The SAP ASLR connection management  table."
    ::= { sapCfg 3 }

slbNewCfgSapAslrEntry OBJECT-TYPE
    SYNTAX  SlbNewCfgSapAslrEntry
    MAX-ACCESS  not-accessible
    STATUS  current
    DESCRIPTION
        "A row in the SAP ASLR connection management table."
    INDEX   { slbNewCfgSapAslrIndex }
    ::= { slbNewCfgSapAslrTable 1 }

SlbNewCfgSapAslrEntry ::= SEQUENCE {
    slbNewCfgSapAslrIndex           Integer32,
    slbNewCfgSapAslrIpAddr          IpAddress,
    slbNewCfgSapAslrIpv6Addr     DisplayString,
    slbNewCfgSapAslrIpVer            INTEGER,
    slbNewCfgSapAslrPortNum      INTEGER,
    slbNewCfgSapAslrVipAddr       IpAddress,
    slbNewCfgSapAslrVipv6Addr   DisplayString,
    slbNewCfgSapAslrVipIpVer      INTEGER,
    slbNewCfgSapAslrInterval        INTEGER,
    slbNewCfgSapAslrState            INTEGER,
    slbNewCfgSapAslrName           DisplayString,
    slbNewCfgSapAslrLastAct        DisplayString,
    slbNewCfgSapAslrAutoConfig INTEGER,
    slbNewCfgSapAslrSessionInfo  INTEGER,
    slbNewCfgSapAslrDelete           INTEGER,
    slbNewCfgSapAslrSignature     DisplayString,
    slbNewCfgSapAslrServCert       DisplayString
    }

slbNewCfgSapAslrIndex OBJECT-TYPE
    SYNTAX  Integer32
    MAX-ACCESS  read-create
    STATUS  current
    DESCRIPTION
        "The Sap Aslr number" 
    ::= { slbNewCfgSapAslrEntry 1 }

slbNewCfgSapAslrIpAddr OBJECT-TYPE
    SYNTAX  IpAddress
    MAX-ACCESS  read-create
    STATUS  current
    DESCRIPTION
        "IP address of the Sap Aslr identified by the instance of the 
         slbNewCfgSapAslrIndex." 
    ::= { slbNewCfgSapAslrEntry 2 }

slbNewCfgSapAslrIpv6Addr OBJECT-TYPE
   SYNTAX DisplayString (SIZE(0..40))
    MAX-ACCESS  read-create
    STATUS  current
    DESCRIPTION
    "  IPV6 address of the Sap Aslr manager identified by the instance of the slbNewCfgSapAslrIndex
       Address should be 4-byte haxadecimal colon notation. Valid IPv6 address should be in
       any of the following forms xxxx:xxxx:xxxx:xxxx:xxxx:xxxx:xxxx:xxxx or xxxx::xxxx:xxxx:xxxx:xxxx or ::xxxx "
   ::= { slbNewCfgSapAslrEntry 3 }

slbNewCfgSapAslrIpVer OBJECT-TYPE
    SYNTAX  INTEGER{
        ipv4(1),
        ipv6(2)
        }
    MAX-ACCESS  read-create
    STATUS  current
    DESCRIPTION
        "The type of IP address."
    ::= { slbNewCfgSapAslrEntry 4  }

slbNewCfgSapAslrPortNum OBJECT-TYPE  
    SYNTAX  INTEGER (2..65534)
    MAX-ACCESS  read-create 
    STATUS  current  
    DESCRIPTION 
        "The Sap Aslr service port number."  
    ::= { slbNewCfgSapAslrEntry 5 } 

slbNewCfgSapAslrVipAddr OBJECT-TYPE
    SYNTAX  IpAddress
    MAX-ACCESS  read-create
    STATUS  current
    DESCRIPTION
        "IP address of the VIP identified by the instance of the 
         slbNewCfgSapAslrIndex." 
    ::= { slbNewCfgSapAslrEntry 6 }

slbNewCfgSapAslrVipv6Addr OBJECT-TYPE
   SYNTAX DisplayString (SIZE(0..40))
    MAX-ACCESS  read-create
    STATUS  current
    DESCRIPTION
    "  IPV6 address of the VIP identified by the instance of the slbNewCfgSapAslrIndex
       Address should be 4-byte haxadecimal colon notation. Valid IPv6 address should be in
       any of the following forms xxxx:xxxx:xxxx:xxxx:xxxx:xxxx:xxxx:xxxx or xxxx::xxxx:xxxx:xxxx:xxxx or ::xxxx "
   ::= { slbNewCfgSapAslrEntry 7 }


slbNewCfgSapAslrVipIpVer OBJECT-TYPE
    SYNTAX  INTEGER{
        ipv4(1),
        ipv6(2)
        }
    MAX-ACCESS  read-create
    STATUS  current
    DESCRIPTION
        "The type of VIP IP address."
    ::= { slbNewCfgSapAslrEntry 8  }

slbNewCfgSapAslrInterval OBJECT-TYPE
    SYNTAX  INTEGER (4..60)
    MAX-ACCESS  read-create
    STATUS  current
    DESCRIPTION
        "Set the Sap Aslr server inspection interval." 
    ::= { slbNewCfgSapAslrEntry 9 }

slbNewCfgSapAslrState OBJECT-TYPE
    SYNTAX  INTEGER {
	enabled(1),
	disabled(2)
	}
    MAX-ACCESS  read-create
    STATUS  current
    DESCRIPTION
        "Enable or disable the Sap Aslr server sampling." 
    ::= { slbNewCfgSapAslrEntry 10 }

slbNewCfgSapAslrName OBJECT-TYPE 
    SYNTAX  DisplayString (SIZE(0..31))
    MAX-ACCESS  read-create 
    STATUS  current 
    DESCRIPTION 
        "The name of the Sap Aslr connection."  
    ::= { slbNewCfgSapAslrEntry 11 }

slbNewCfgSapAslrLastAct OBJECT-TYPE 
    SYNTAX  DisplayString (SIZE(0..31))
    MAX-ACCESS  read-create 
    STATUS  current 
    DESCRIPTION 
        "The Sap Aslr last activity time stamp."  
    ::= { slbNewCfgSapAslrEntry 12 }

slbNewCfgSapAslrAutoConfig OBJECT-TYPE
    SYNTAX  INTEGER {
        basic(1),
        full(2)
        }
    MAX-ACCESS  read-create
    STATUS  current
    DESCRIPTION
        "Defines the configuration update process.  
         When set the value to basic (1), the configuration is limited,
	 comparing to full (2)"
    ::= { slbNewCfgSapAslrEntry 13 }

slbNewCfgSapAslrSessionInfo  OBJECT-TYPE
 SYNTAX  INTEGER 
    MAX-ACCESS  read-create
    STATUS  current
    DESCRIPTION
        "Set the Sap Aslr session information.
	When read, zero is returned." 
    ::= { slbNewCfgSapAslrEntry 14 }

slbNewCfgSapAslrDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { slbNewCfgSapAslrEntry 15 }

slbNewCfgSapAslrSignature OBJECT-TYPE 
    SYNTAX  DisplayString (SIZE(0..40))
    MAX-ACCESS  read-create 
    STATUS  current 
    DESCRIPTION 
        "The Sap Aslr connection signature."  
    ::= { slbNewCfgSapAslrEntry 16 }

slbNewCfgSapAslrServCert OBJECT-TYPE
    SYNTAX  DisplayString  (SIZE(0..32))
    MAX-ACCESS  read-create
    STATUS  current
    DESCRIPTION
        "Server Certificate name associated with this virtual service."
    ::= { slbNewCfgSapAslrEntry 17 }


slbStatSapAslrTable OBJECT-TYPE
    SYNTAX  SEQUENCE OF SlbStatSapAslrEntry
    MAX-ACCESS  not-accessible
    STATUS  current
    DESCRIPTION
        "The sap aslrr statistics table.  This table shows the statistics 
         of sap aslr for a particular vip."
    ::= { sapStats 1 }

slbStatSapAslrEntry OBJECT-TYPE
    SYNTAX  SlbStatSapAslrEntry
    MAX-ACCESS  not-accessible
    STATUS  current
    DESCRIPTION
        "A row in the sap aslr statistics table."
    INDEX  { slbStatSapAslrIndex }
    ::= { slbStatSapAslrTable 1 }
              
SlbStatSapAslrEntry ::= SEQUENCE {
   slbStatSapAslrIndex                    Integer32,
   slbStatSapAslrSampling             Counter32,
   slbStatSapAslrFailure                 Counter32,
   slbStatSapAslrDeviceUpdates  Counter32,
   slbStatSapAslrDeviceFailure     Counter32,
   slbStatSapAslrLastAct                DisplayString
    }

slbStatSapAslrIndex OBJECT-TYPE
    SYNTAX  Integer32
    MAX-ACCESS  read-only
    STATUS  current
    DESCRIPTION
        "The Sap Aslr table index."
    ::= { slbStatSapAslrEntry 1 }

slbStatSapAslrSampling OBJECT-TYPE 
    SYNTAX  Counter32 
    MAX-ACCESS  read-only
    STATUS  current 
    DESCRIPTION 
        "The number of Sap Aslr server lookups." 
    ::= { slbStatSapAslrEntry 2 }

slbStatSapAslrFailure OBJECT-TYPE 
    SYNTAX  Counter32
    MAX-ACCESS  read-only
    STATUS  current 
    DESCRIPTION 
        "The number of Sap Aslr server lookup failures."
    ::= { slbStatSapAslrEntry 3 }

slbStatSapAslrDeviceUpdates OBJECT-TYPE 
    SYNTAX  Counter32 
    MAX-ACCESS  read-only
    STATUS  current 
    DESCRIPTION 
        "The number of Alteon automated configuration updates."
    ::= { slbStatSapAslrEntry 4 }

slbStatSapAslrDeviceFailure OBJECT-TYPE
    SYNTAX  Counter32
    MAX-ACCESS  read-only
    STATUS  current
    DESCRIPTION
        "The number of Alteon automated configuration failure."
    ::= { slbStatSapAslrEntry 5 }

slbStatSapAslrLastAct OBJECT-TYPE
    SYNTAX  DisplayString (SIZE(0..31))
    MAX-ACCESS  read-only
    STATUS  current
    DESCRIPTION
        "The Sap Aslr last activity time stamp."
    ::= { slbStatSapAslrEntry 6 }

END
