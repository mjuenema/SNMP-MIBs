-- file automatically created


TELDAT-TRAP-IPX-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ipxTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IPX event subsystem."
    REVISION "201401200930Z"
    DESCRIPTION "Initial implementation"
        ::= { telEventTraps 165 }


ipxEventsGroup	OBJECT IDENTIFIER	::= { ipxTrapsMIB 1 }

ipxNotifications	OBJECT IDENTIFIER	::= { ipxTrapsMIB 2 }
ipxNotificationsPrefix	OBJECT IDENTIFIER	::= { ipxNotifications 0 }

ipxEventObjects1 OBJECT-IDENTITY
    STATUS current
    DESCRIPTION
        "Event IPX.1
        An IPX packet arrived on a network and the IPX forwarder is
        not installed."
    ::= { ipxEventsGroup 1 }

ipx1_source_net OBJECT-TYPE
    SYNTAX Integer32
    MAX-ACCESS accessible-for-notify
    STATUS current
    DESCRIPTION
        "Parameter 'source_net' in event IPX.1"
    ::= { ipxEventObjects1 1 }

ipx1_source_node OBJECT-TYPE
    SYNTAX DisplayString
    MAX-ACCESS accessible-for-notify
    STATUS current
    DESCRIPTION
        "Parameter 'source_node' in event IPX.1"
    ::= { ipxEventObjects1 2 }

ipx1_dest_net OBJECT-TYPE
    SYNTAX Integer32
    MAX-ACCESS accessible-for-notify
    STATUS current
    DESCRIPTION
        "Parameter 'dest_net' in event IPX.1"
    ::= { ipxEventObjects1 3 }

ipx1_dest_node OBJECT-TYPE
    SYNTAX DisplayString
    MAX-ACCESS accessible-for-notify
    STATUS current
    DESCRIPTION
        "Parameter 'dest_node' in event IPX.1"
    ::= { ipxEventObjects1 4 }

ipxEventObjects2 OBJECT-IDENTITY
    STATUS current
    DESCRIPTION
        "Event IPX.2
        IPX forwarder input queue has overflowed."
    ::= { ipxEventsGroup 2 }

ipx2_source_net OBJECT-TYPE
    SYNTAX Integer32
    MAX-ACCESS accessible-for-notify
    STATUS current
    DESCRIPTION
        "Parameter 'source_net' in event IPX.2"
    ::= { ipxEventObjects2 1 }

ipx2_source_node OBJECT-TYPE
    SYNTAX DisplayString
    MAX-ACCESS accessible-for-notify
    STATUS current
    DESCRIPTION
        "Parameter 'source_node' in event IPX.2"
    ::= { ipxEventObjects2 2 }

ipx2_dest_net OBJECT-TYPE
    SYNTAX Integer32
    MAX-ACCESS accessible-for-notify
    STATUS current
    DESCRIPTION
        "Parameter 'dest_net' in event IPX.2"
    ::= { ipxEventObjects2 3 }

ipx2_dest_node OBJECT-TYPE
    SYNTAX DisplayString
    MAX-ACCESS accessible-for-notify
    STATUS current
    DESCRIPTION
        "Parameter 'dest_node' in event IPX.2"
    ::= { ipxEventObjects2 4 }

ipx2_interface OBJECT-TYPE
    SYNTAX DisplayString
    MAX-ACCESS accessible-for-notify
    STATUS current
    DESCRIPTION
        "Parameter 'interface' in event IPX.2"
    ::= { ipxEventObjects2 5 }

ipxEventObjects3 OBJECT-IDENTITY
    STATUS current
    DESCRIPTION
        "Event IPX.3
        This message is generated when a packet arrives for this host with
        an incorrect checksum."
    ::= { ipxEventsGroup 3 }

ipx3_source_net OBJECT-TYPE
    SYNTAX Integer32
    MAX-ACCESS accessible-for-notify
    STATUS current
    DESCRIPTION
        "Parameter 'source_net' in event IPX.3"
    ::= { ipxEventObjects3 1 }

ipx3_source_node OBJECT-TYPE
    SYNTAX DisplayString
    MAX-ACCESS accessible-for-notify
    STATUS current
    DESCRIPTION
        "Parameter 'source_node' in event IPX.3"
    ::= { ipxEventObjects3 2 }

ipxEventObjects4 OBJECT-IDENTITY
    STATUS current
    DESCRIPTION
        "Event IPX.4
        This message is generated when an error packet is received."
    ::= { ipxEventsGroup 4 }

ipx4_error_type OBJECT-TYPE
    SYNTAX Integer32
    MAX-ACCESS accessible-for-notify
    STATUS current
    DESCRIPTION
        "Parameter 'error_type' in event IPX.4"
    ::= { ipxEventObjects4 1 }

ipx4_source_net OBJECT-TYPE
    SYNTAX Integer32
    MAX-ACCESS accessible-for-notify
    STATUS current
    DESCRIPTION
        "Parameter 'source_net' in event IPX.4"
    ::= { ipxEventObjects4 2 }

ipx4_source_node OBJECT-TYPE
    SYNTAX DisplayString
    MAX-ACCESS accessible-for-notify
    STATUS current
    DESCRIPTION
        "Parameter 'source_node' in event IPX.4"
    ::= { ipxEventObjects4 3 }

ipxEventObjects5 OBJECT-IDENTITY
    STATUS current
    DESCRIPTION
        "Event IPX.5
        A packet arrived for an unknown or unsupported socket or type.
        The packet was a broadcast packet."
    ::= { ipxEventsGroup 5 }

ipx5_destination_socket OBJECT-TYPE
    SYNTAX Integer32
    MAX-ACCESS accessible-for-notify
    STATUS current
    DESCRIPTION
        "Parameter 'destination_socket' in event IPX.5"
    ::= { ipxEventObjects5 1 }

ipx5_packet_type OBJECT-TYPE
    SYNTAX Integer32
    MAX-ACCESS accessible-for-notify
    STATUS current
    DESCRIPTION
        "Parameter 'packet_type' in event IPX.5"
    ::= { ipxEventObjects5 2 }

ipx5_source_net OBJECT-TYPE
    SYNTAX Integer32
    MAX-ACCESS accessible-for-notify
    STATUS current
    DESCRIPTION
        "Parameter 'source_net' in event IPX.5"
    ::= { ipxEventObjects5 3 }

ipx5_source_node OBJECT-TYPE
    SYNTAX DisplayString
    MAX-ACCESS accessible-for-notify
    STATUS current
    DESCRIPTION
        "Parameter 'source_node' in event IPX.5"
    ::= { ipxEventObjects5 4 }

ipxEventObjects6 OBJECT-IDENTITY
    STATUS current
    DESCRIPTION
        "Event IPX.6
        A packet arrived for an unknown or unsupported socket or type.
        The packet was addressed to the router."
    ::= { ipxEventsGroup 6 }

ipx6_destination_socket OBJECT-TYPE
    SYNTAX Integer32
    MAX-ACCESS accessible-for-notify
    STATUS current
    DESCRIPTION
        "Parameter 'destination_socket' in event IPX.6"
    ::= { ipxEventObjects6 1 }

ipx6_packet_type OBJECT-TYPE
    SYNTAX Integer32
    MAX-ACCESS accessible-for-notify
    STATUS current
    DESCRIPTION
        "Parameter 'packet_type' in event IPX.6"
    ::= { ipxEventObjects6 2 }

ipx6_source_net OBJECT-TYPE
    SYNTAX Integer32
    MAX-ACCESS accessible-for-notify
    STATUS current
    DESCRIPTION
        "Parameter 'source_net' in event IPX.6"
    ::= { ipxEventObjects6 3 }

ipx6_source_node OBJECT-TYPE
    SYNTAX DisplayString
    MAX-ACCESS accessible-for-notify
    STATUS current
    DESCRIPTION
        "Parameter 'source_node' in event IPX.6"
    ::= { ipxEventObjects6 4 }

ipxEventObjects7 OBJECT-IDENTITY
    STATUS current
    DESCRIPTION
        "Event IPX.7
        The forwarder was bringing up IPX on the specified serial line
        interface, but no host address was set so the interface was not enabled."
    ::= { ipxEventsGroup 7 }

ipx7_interface OBJECT-TYPE
    SYNTAX DisplayString
    MAX-ACCESS accessible-for-notify
    STATUS current
    DESCRIPTION
        "Parameter 'interface' in event IPX.7"
    ::= { ipxEventObjects7 1 }

ipxEventObjects8 OBJECT-IDENTITY
    STATUS current
    DESCRIPTION
        "Event IPX.8
        This message is generated when a packet is received with a bad SAP type."
    ::= { ipxEventsGroup 8 }

ipx8_packet_type OBJECT-TYPE
    SYNTAX Integer32
    MAX-ACCESS accessible-for-notify
    STATUS current
    DESCRIPTION
        "Parameter 'packet_type' in event IPX.8"
    ::= { ipxEventObjects8 1 }

ipx8_source_net OBJECT-TYPE
    SYNTAX Integer32
    MAX-ACCESS accessible-for-notify
    STATUS current
    DESCRIPTION
        "Parameter 'source_net' in event IPX.8"
    ::= { ipxEventObjects8 2 }

ipx8_source_node OBJECT-TYPE
    SYNTAX DisplayString
    MAX-ACCESS accessible-for-notify
    STATUS current
    DESCRIPTION
        "Parameter 'source_node' in event IPX.8"
    ::= { ipxEventObjects8 3 }

ipxEventObjects9 OBJECT-IDENTITY
    STATUS current
    DESCRIPTION
        "Event IPX.9
        SAP has received a General Reply packet from the specified host.
        The data in the packet will be used to update the SAP database."
    ::= { ipxEventsGroup 9 }

ipx9_source_net OBJECT-TYPE
    SYNTAX Integer32
    MAX-ACCESS accessible-for-notify
    STATUS current
    DESCRIPTION
        "Parameter 'source_net' in event IPX.9"
    ::= { ipxEventObjects9 1 }

ipx9_source_node OBJECT-TYPE
    SYNTAX DisplayString
    MAX-ACCESS accessible-for-notify
    STATUS current
    DESCRIPTION
        "Parameter 'source_node' in event IPX.9"
    ::= { ipxEventObjects9 2 }

ipxEventObjects10 OBJECT-IDENTITY
    STATUS current
    DESCRIPTION
        "Event IPX.10
        A new entry cannot be added to the SAP table because it is full.
        The new entry is discarded."
    ::= { ipxEventsGroup 10 }

ipx10_service_type OBJECT-TYPE
    SYNTAX Integer32
    MAX-ACCESS accessible-for-notify
    STATUS current
    DESCRIPTION
        "Parameter 'service_type' in event IPX.10"
    ::= { ipxEventObjects10 1 }

ipx10_service_name OBJECT-TYPE
    SYNTAX DisplayString
    MAX-ACCESS accessible-for-notify
    STATUS current
    DESCRIPTION
        "Parameter 'service_name' in event IPX.10"
    ::= { ipxEventObjects10 2 }

ipxEventObjects11 OBJECT-IDENTITY
    STATUS current
    DESCRIPTION
        "Event IPX.11
        A SAP General Reply was received with a different network/address pair
        than is presently in the SAP database."
    ::= { ipxEventsGroup 11 }

ipx11_service_type OBJECT-TYPE
    SYNTAX Integer32
    MAX-ACCESS accessible-for-notify
    STATUS current
    DESCRIPTION
        "Parameter 'service_type' in event IPX.11"
    ::= { ipxEventObjects11 1 }

ipx11_service_name OBJECT-TYPE
    SYNTAX DisplayString
    MAX-ACCESS accessible-for-notify
    STATUS current
    DESCRIPTION
        "Parameter 'service_name' in event IPX.11"
    ::= { ipxEventObjects11 2 }

ipx11_new_net OBJECT-TYPE
    SYNTAX Integer32
    MAX-ACCESS accessible-for-notify
    STATUS current
    DESCRIPTION
        "Parameter 'new_net' in event IPX.11"
    ::= { ipxEventObjects11 3 }

ipx11_new_node OBJECT-TYPE
    SYNTAX DisplayString
    MAX-ACCESS accessible-for-notify
    STATUS current
    DESCRIPTION
        "Parameter 'new_node' in event IPX.11"
    ::= { ipxEventObjects11 4 }

ipxEventObjects12 OBJECT-IDENTITY
    STATUS current
    DESCRIPTION
        "Event IPX.12
        A SAP table entry has been declared dead. It will be advertised as
        unreachable for another 60 seconds, and then removed from the SAP table."
    ::= { ipxEventsGroup 12 }

ipx12_service_type OBJECT-TYPE
    SYNTAX Integer32
    MAX-ACCESS accessible-for-notify
    STATUS current
    DESCRIPTION
        "Parameter 'service_type' in event IPX.12"
    ::= { ipxEventObjects12 1 }

ipx12_service_name OBJECT-TYPE
    SYNTAX DisplayString
    MAX-ACCESS accessible-for-notify
    STATUS current
    DESCRIPTION
        "Parameter 'service_name' in event IPX.12"
    ::= { ipxEventObjects12 2 }

ipxEventObjects13 OBJECT-IDENTITY
    STATUS current
    DESCRIPTION
        "Event IPX.13
        A SAP Nearest Service Query was received with an illegal length."
    ::= { ipxEventsGroup 13 }

ipx13_source_net OBJECT-TYPE
    SYNTAX Integer32
    MAX-ACCESS accessible-for-notify
    STATUS current
    DESCRIPTION
        "Parameter 'source_net' in event IPX.13"
    ::= { ipxEventObjects13 1 }

ipx13_source_node OBJECT-TYPE
    SYNTAX DisplayString
    MAX-ACCESS accessible-for-notify
    STATUS current
    DESCRIPTION
        "Parameter 'source_node' in event IPX.13"
    ::= { ipxEventObjects13 2 }

ipx13_length OBJECT-TYPE
    SYNTAX Integer32
    MAX-ACCESS accessible-for-notify
    STATUS current
    DESCRIPTION
        "Parameter 'length' in event IPX.13"
    ::= { ipxEventObjects13 3 }

ipxEventObjects14 OBJECT-IDENTITY
    STATUS current
    DESCRIPTION
        "Event IPX.14
        A SAP Nearest Service Query was received from the specified node.
        It will be answered as appropriate."
    ::= { ipxEventsGroup 14 }

ipx14_source_net OBJECT-TYPE
    SYNTAX Integer32
    MAX-ACCESS accessible-for-notify
    STATUS current
    DESCRIPTION
        "Parameter 'source_net' in event IPX.14"
    ::= { ipxEventObjects14 1 }

ipx14_source_node OBJECT-TYPE
    SYNTAX DisplayString
    MAX-ACCESS accessible-for-notify
    STATUS current
    DESCRIPTION
        "Parameter 'source_node' in event IPX.14"
    ::= { ipxEventObjects14 2 }

ipxEventObjects15 OBJECT-IDENTITY
    STATUS current
    DESCRIPTION
        "Event IPX.15
        A SAP General Service Query was received from the specified node.
        It will be answered as appropriate."
    ::= { ipxEventsGroup 15 }

ipx15_source_net OBJECT-TYPE
    SYNTAX Integer32
    MAX-ACCESS accessible-for-notify
    STATUS current
    DESCRIPTION
        "Parameter 'source_net' in event IPX.15"
    ::= { ipxEventObjects15 1 }

ipx15_source_node OBJECT-TYPE
    SYNTAX DisplayString
    MAX-ACCESS accessible-for-notify
    STATUS current
    DESCRIPTION
        "Parameter 'source_node' in event IPX.15"
    ::= { ipxEventObjects15 2 }

ipxEventObjects16 OBJECT-IDENTITY
    STATUS current
    DESCRIPTION
        "Event IPX.16
        A SAP General Service Query was sent on the specified network.
        One is sent on a network when it comes up."
    ::= { ipxEventsGroup 16 }

ipx16_interface OBJECT-TYPE
    SYNTAX DisplayString
    MAX-ACCESS accessible-for-notify
    STATUS current
    DESCRIPTION
        "Parameter 'interface' in event IPX.16"
    ::= { ipxEventObjects16 1 }

ipxEventObjects17 OBJECT-IDENTITY
    STATUS current
    DESCRIPTION
        "Event IPX.17
        No buffer is available to send a SAP General Service Query or Reply
        packet. Since a General Service Reply can require multiple packets,
        the message notes how many packets the router sent on this network
        before they ran out."
    ::= { ipxEventsGroup 17 }

ipx17_interface OBJECT-TYPE
    SYNTAX DisplayString
    MAX-ACCESS accessible-for-notify
    STATUS current
    DESCRIPTION
        "Parameter 'interface' in event IPX.17"
    ::= { ipxEventObjects17 1 }

ipx17_count OBJECT-TYPE
    SYNTAX Integer32
    MAX-ACCESS accessible-for-notify
    STATUS current
    DESCRIPTION
        "Parameter 'count' in event IPX.17"
    ::= { ipxEventObjects17 2 }

ipxEventObjects18 OBJECT-IDENTITY
    STATUS current
    DESCRIPTION
        "Event IPX.18
        The specified network just sent a SAP General Service Reply. It took
        the specified number of packets to send the complete SAP database."
    ::= { ipxEventsGroup 18 }

ipx18_interface OBJECT-TYPE
    SYNTAX DisplayString
    MAX-ACCESS accessible-for-notify
    STATUS current
    DESCRIPTION
        "Parameter 'interface' in event IPX.18"
    ::= { ipxEventObjects18 1 }

ipx18_count OBJECT-TYPE
    SYNTAX Integer32
    MAX-ACCESS accessible-for-notify
    STATUS current
    DESCRIPTION
        "Parameter 'count' in event IPX.18"
    ::= { ipxEventObjects18 2 }

ipxEventObjects19 OBJECT-IDENTITY
    STATUS current
    DESCRIPTION
        "Event IPX.19
        The router received a NETBIOS emulation multinetwork broadcast packet
        for forwarding to other IPX networks. The IPX hop count indicates
        how many routers it has been through."
    ::= { ipxEventsGroup 19 }

ipx19_source_net OBJECT-TYPE
    SYNTAX Integer32
    MAX-ACCESS accessible-for-notify
    STATUS current
    DESCRIPTION
        "Parameter 'source_net' in event IPX.19"
    ::= { ipxEventObjects19 1 }

ipx19_source_node OBJECT-TYPE
    SYNTAX DisplayString
    MAX-ACCESS accessible-for-notify
    STATUS current
    DESCRIPTION
        "Parameter 'source_node' in event IPX.19"
    ::= { ipxEventObjects19 2 }

ipx19_dest_net OBJECT-TYPE
    SYNTAX Integer32
    MAX-ACCESS accessible-for-notify
    STATUS current
    DESCRIPTION
        "Parameter 'dest_net' in event IPX.19"
    ::= { ipxEventObjects19 3 }

ipx19_dest_node OBJECT-TYPE
    SYNTAX DisplayString
    MAX-ACCESS accessible-for-notify
    STATUS current
    DESCRIPTION
        "Parameter 'dest_node' in event IPX.19"
    ::= { ipxEventObjects19 4 }

ipx19_interface OBJECT-TYPE
    SYNTAX DisplayString
    MAX-ACCESS accessible-for-notify
    STATUS current
    DESCRIPTION
        "Parameter 'interface' in event IPX.19"
    ::= { ipxEventObjects19 5 }

ipx19_hop_count OBJECT-TYPE
    SYNTAX Integer32
    MAX-ACCESS accessible-for-notify
    STATUS current
    DESCRIPTION
        "Parameter 'hop_count' in event IPX.19"
    ::= { ipxEventObjects19 6 }

ipxEventObjects20 OBJECT-IDENTITY
    STATUS current
    DESCRIPTION
        "Event IPX.20
        A NETBIOS emulation broadcast packet has been through more than
        8 routers. It will be dropped."
    ::= { ipxEventsGroup 20 }

ipx20_source_net OBJECT-TYPE
    SYNTAX Integer32
    MAX-ACCESS accessible-for-notify
    STATUS current
    DESCRIPTION
        "Parameter 'source_net' in event IPX.20"
    ::= { ipxEventObjects20 1 }

ipx20_source_node OBJECT-TYPE
    SYNTAX DisplayString
    MAX-ACCESS accessible-for-notify
    STATUS current
    DESCRIPTION
        "Parameter 'source_node' in event IPX.20"
    ::= { ipxEventObjects20 2 }

ipx20_interface OBJECT-TYPE
    SYNTAX DisplayString
    MAX-ACCESS accessible-for-notify
    STATUS current
    DESCRIPTION
        "Parameter 'interface' in event IPX.20"
    ::= { ipxEventObjects20 3 }

ipxEventObjects21 OBJECT-IDENTITY
    STATUS current
    DESCRIPTION
        "Event IPX.21
        This IPX NETBIOS emulation broadcast packet has already been on
        one of the directly attached networks. The router will not forward it
        since that would generate a duplicate."
    ::= { ipxEventsGroup 21 }

ipx21_source_net OBJECT-TYPE
    SYNTAX Integer32
    MAX-ACCESS accessible-for-notify
    STATUS current
    DESCRIPTION
        "Parameter 'source_net' in event IPX.21"
    ::= { ipxEventObjects21 1 }

ipx21_source_node OBJECT-TYPE
    SYNTAX DisplayString
    MAX-ACCESS accessible-for-notify
    STATUS current
    DESCRIPTION
        "Parameter 'source_node' in event IPX.21"
    ::= { ipxEventObjects21 2 }

ipx21_interface OBJECT-TYPE
    SYNTAX DisplayString
    MAX-ACCESS accessible-for-notify
    STATUS current
    DESCRIPTION
        "Parameter 'interface' in event IPX.21"
    ::= { ipxEventObjects21 3 }

ipx21_connected_network OBJECT-TYPE
    SYNTAX Integer32
    MAX-ACCESS accessible-for-notify
    STATUS current
    DESCRIPTION
        "Parameter 'connected_network' in event IPX.21"
    ::= { ipxEventObjects21 4 }

ipxEventObjects22 OBJECT-IDENTITY
    STATUS current
    DESCRIPTION
        "Event IPX.22
        No memory available to make working copy of this NETBIOS emulation
        packet to send it out multiple interfaces."
    ::= { ipxEventsGroup 22 }

ipx22_source_net OBJECT-TYPE
    SYNTAX Integer32
    MAX-ACCESS accessible-for-notify
    STATUS current
    DESCRIPTION
        "Parameter 'source_net' in event IPX.22"
    ::= { ipxEventObjects22 1 }

ipx22_source_node OBJECT-TYPE
    SYNTAX DisplayString
    MAX-ACCESS accessible-for-notify
    STATUS current
    DESCRIPTION
        "Parameter 'source_node' in event IPX.22"
    ::= { ipxEventObjects22 2 }

ipxEventObjects23 OBJECT-IDENTITY
    STATUS current
    DESCRIPTION
        "Event IPX.23
        Attempting to send NETBIOS emulation packet on network that does not
        support broadcast. The packet will not be sent on that network."
    ::= { ipxEventsGroup 23 }

ipx23_source_net OBJECT-TYPE
    SYNTAX Integer32
    MAX-ACCESS accessible-for-notify
    STATUS current
    DESCRIPTION
        "Parameter 'source_net' in event IPX.23"
    ::= { ipxEventObjects23 1 }

ipx23_source_node OBJECT-TYPE
    SYNTAX DisplayString
    MAX-ACCESS accessible-for-notify
    STATUS current
    DESCRIPTION
        "Parameter 'source_node' in event IPX.23"
    ::= { ipxEventObjects23 2 }

ipx23_interface OBJECT-TYPE
    SYNTAX DisplayString
    MAX-ACCESS accessible-for-notify
    STATUS current
    DESCRIPTION
        "Parameter 'interface' in event IPX.23"
    ::= { ipxEventObjects23 3 }

ipxEventObjects24 OBJECT-IDENTITY
    STATUS current
    DESCRIPTION
        "Event IPX.24
        Attempting to send NETBIOS emulation packet on a network with
        no network number. The packet will not be sent on that network."
    ::= { ipxEventsGroup 24 }

ipx24_source_net OBJECT-TYPE
    SYNTAX Integer32
    MAX-ACCESS accessible-for-notify
    STATUS current
    DESCRIPTION
        "Parameter 'source_net' in event IPX.24"
    ::= { ipxEventObjects24 1 }

ipx24_source_node OBJECT-TYPE
    SYNTAX DisplayString
    MAX-ACCESS accessible-for-notify
    STATUS current
    DESCRIPTION
        "Parameter 'source_node' in event IPX.24"
    ::= { ipxEventObjects24 2 }

ipx24_interface OBJECT-TYPE
    SYNTAX DisplayString
    MAX-ACCESS accessible-for-notify
    STATUS current
    DESCRIPTION
        "Parameter 'interface' in event IPX.24"
    ::= { ipxEventObjects24 3 }

ipxEventObjects25 OBJECT-IDENTITY
    STATUS current
    DESCRIPTION
        "Event IPX.25
        No packet buffer available to copy this NETBIOS emulation broadcast
        packet into in order to send it on a network."
    ::= { ipxEventsGroup 25 }

ipx25_source_net OBJECT-TYPE
    SYNTAX Integer32
    MAX-ACCESS accessible-for-notify
    STATUS current
    DESCRIPTION
        "Parameter 'source_net' in event IPX.25"
    ::= { ipxEventObjects25 1 }

ipx25_source_node OBJECT-TYPE
    SYNTAX DisplayString
    MAX-ACCESS accessible-for-notify
    STATUS current
    DESCRIPTION
        "Parameter 'source_node' in event IPX.25"
    ::= { ipxEventObjects25 2 }

ipxEventObjects26 OBJECT-IDENTITY
    STATUS current
    DESCRIPTION
        "Event IPX.26
        The router did not successfully transmit an outgoing NETBIOS emulation
        broadcast packet for the reason the error code indicates."
    ::= { ipxEventsGroup 26 }

ipx26_interface OBJECT-TYPE
    SYNTAX DisplayString
    MAX-ACCESS accessible-for-notify
    STATUS current
    DESCRIPTION
        "Parameter 'interface' in event IPX.26"
    ::= { ipxEventObjects26 1 }

ipx26_reason_code OBJECT-TYPE
    SYNTAX Integer32
    MAX-ACCESS accessible-for-notify
    STATUS current
    DESCRIPTION
        "Parameter 'reason_code' in event IPX.26"
    ::= { ipxEventObjects26 2 }

ipxEventObjects27 OBJECT-IDENTITY
    STATUS current
    DESCRIPTION
        "Event IPX.27
        RIP packet received which was not a request or response."
    ::= { ipxEventsGroup 27 }

ipx27_RIP_opcode OBJECT-TYPE
    SYNTAX Integer32
    MAX-ACCESS accessible-for-notify
    STATUS current
    DESCRIPTION
        "Parameter 'RIP_opcode' in event IPX.27"
    ::= { ipxEventObjects27 1 }

ipx27_source_net OBJECT-TYPE
    SYNTAX Integer32
    MAX-ACCESS accessible-for-notify
    STATUS current
    DESCRIPTION
        "Parameter 'source_net' in event IPX.27"
    ::= { ipxEventObjects27 2 }

ipx27_source_node OBJECT-TYPE
    SYNTAX DisplayString
    MAX-ACCESS accessible-for-notify
    STATUS current
    DESCRIPTION
        "Parameter 'source_node' in event IPX.27"
    ::= { ipxEventObjects27 3 }

ipxEventObjects28 OBJECT-IDENTITY
    STATUS current
    DESCRIPTION
        "Event IPX.28
        This message is generated when a RIP response packet is received.
        It will be parsed, and the data incorporated into the routing table."
    ::= { ipxEventsGroup 28 }

ipx28_source_net OBJECT-TYPE
    SYNTAX Integer32
    MAX-ACCESS accessible-for-notify
    STATUS current
    DESCRIPTION
        "Parameter 'source_net' in event IPX.28"
    ::= { ipxEventObjects28 1 }

ipx28_source_node OBJECT-TYPE
    SYNTAX DisplayString
    MAX-ACCESS accessible-for-notify
    STATUS current
    DESCRIPTION
        "Parameter 'source_node' in event IPX.28"
    ::= { ipxEventObjects28 2 }

ipxEventObjects29 OBJECT-IDENTITY
    STATUS current
    DESCRIPTION
        "Event IPX.29
        A RIP response was received with an entry having a network number
        of 00000000 or FFFFFFFF. That entry will be ignored."
    ::= { ipxEventsGroup 29 }

ipx29_network OBJECT-TYPE
    SYNTAX Integer32
    MAX-ACCESS accessible-for-notify
    STATUS current
    DESCRIPTION
        "Parameter 'network' in event IPX.29"
    ::= { ipxEventObjects29 1 }

ipx29_source_net OBJECT-TYPE
    SYNTAX Integer32
    MAX-ACCESS accessible-for-notify
    STATUS current
    DESCRIPTION
        "Parameter 'source_net' in event IPX.29"
    ::= { ipxEventObjects29 2 }

ipx29_source_node OBJECT-TYPE
    SYNTAX DisplayString
    MAX-ACCESS accessible-for-notify
    STATUS current
    DESCRIPTION
        "Parameter 'source_node' in event IPX.29"
    ::= { ipxEventObjects29 3 }

ipxEventObjects30 OBJECT-IDENTITY
    STATUS current
    DESCRIPTION
        "Event IPX.30
        This message is generated when a new network cannot be added to the
        routing table because it is full. The entry is discarded."
    ::= { ipxEventsGroup 30 }

ipx30_network OBJECT-TYPE
    SYNTAX Integer32
    MAX-ACCESS accessible-for-notify
    STATUS current
    DESCRIPTION
        "Parameter 'network' in event IPX.30"
    ::= { ipxEventObjects30 1 }

ipxEventObjects31 OBJECT-IDENTITY
    STATUS current
    DESCRIPTION
        "Event IPX.31
        This message is generated when the route to a network changes.
        The specified router_net/router_node is now the best route to
        this network, with the noted number of hops."
    ::= { ipxEventsGroup 31 }

ipx31_network OBJECT-TYPE
    SYNTAX Integer32
    MAX-ACCESS accessible-for-notify
    STATUS current
    DESCRIPTION
        "Parameter 'network' in event IPX.31"
    ::= { ipxEventObjects31 1 }

ipx31_router_net OBJECT-TYPE
    SYNTAX Integer32
    MAX-ACCESS accessible-for-notify
    STATUS current
    DESCRIPTION
        "Parameter 'router_net' in event IPX.31"
    ::= { ipxEventObjects31 2 }

ipx31_router_node OBJECT-TYPE
    SYNTAX DisplayString
    MAX-ACCESS accessible-for-notify
    STATUS current
    DESCRIPTION
        "Parameter 'router_node' in event IPX.31"
    ::= { ipxEventObjects31 3 }

ipx31_hop_count OBJECT-TYPE
    SYNTAX Integer32
    MAX-ACCESS accessible-for-notify
    STATUS current
    DESCRIPTION
        "Parameter 'hop_count' in event IPX.31"
    ::= { ipxEventObjects31 4 }

ipxEventObjects32 OBJECT-IDENTITY
    STATUS current
    DESCRIPTION
        "Event IPX.32
        This message is generated when a network is declared unreachable
        because no routing updates have been heard for it in 240 seconds.
        It will be advertised as unreachable for another 60 seconds, and then
        deleted from the routing table."
    ::= { ipxEventsGroup 32 }

ipx32_network OBJECT-TYPE
    SYNTAX Integer32
    MAX-ACCESS accessible-for-notify
    STATUS current
    DESCRIPTION
        "Parameter 'network' in event IPX.32"
    ::= { ipxEventObjects32 1 }

ipxEventObjects33 OBJECT-IDENTITY
    STATUS current
    DESCRIPTION
        "Event IPX.33
        This message is generated when a RIP Request packet is being parsed
        for a Reply."
    ::= { ipxEventsGroup 33 }

ipx33_source_net OBJECT-TYPE
    SYNTAX Integer32
    MAX-ACCESS accessible-for-notify
    STATUS current
    DESCRIPTION
        "Parameter 'source_net' in event IPX.33"
    ::= { ipxEventObjects33 1 }

ipx33_source_node OBJECT-TYPE
    SYNTAX DisplayString
    MAX-ACCESS accessible-for-notify
    STATUS current
    DESCRIPTION
        "Parameter 'source_node' in event IPX.33"
    ::= { ipxEventObjects33 2 }

ipxEventObjects34 OBJECT-IDENTITY
    STATUS current
    DESCRIPTION
        "Event IPX.34
        A RIP request packet was received which is too short to contain one
        RIP entry. It will be discarded."
    ::= { ipxEventsGroup 34 }

ipx34_source_net OBJECT-TYPE
    SYNTAX Integer32
    MAX-ACCESS accessible-for-notify
    STATUS current
    DESCRIPTION
        "Parameter 'source_net' in event IPX.34"
    ::= { ipxEventObjects34 1 }

ipx34_source_node OBJECT-TYPE
    SYNTAX DisplayString
    MAX-ACCESS accessible-for-notify
    STATUS current
    DESCRIPTION
        "Parameter 'source_node' in event IPX.34"
    ::= { ipxEventObjects34 2 }

ipx34_packet_length OBJECT-TYPE
    SYNTAX Integer32
    MAX-ACCESS accessible-for-notify
    STATUS current
    DESCRIPTION
        "Parameter 'packet_length' in event IPX.34"
    ::= { ipxEventObjects34 3 }

ipxEventObjects35 OBJECT-IDENTITY
    STATUS current
    DESCRIPTION
        "Event IPX.35
        A RIP Query has been sent on the specified interface. A Query is sent
        on each interface when it comes up."
    ::= { ipxEventsGroup 35 }

ipx35_interface OBJECT-TYPE
    SYNTAX DisplayString
    MAX-ACCESS accessible-for-notify
    STATUS current
    DESCRIPTION
        "Parameter 'interface' in event IPX.35"
    ::= { ipxEventObjects35 1 }

ipxEventObjects36 OBJECT-IDENTITY
    STATUS current
    DESCRIPTION
        "Event IPX.36
        No buffer is available to send a RIP Query or Response packet."
    ::= { ipxEventsGroup 36 }

ipx36_interface OBJECT-TYPE
    SYNTAX DisplayString
    MAX-ACCESS accessible-for-notify
    STATUS current
    DESCRIPTION
        "Parameter 'interface' in event IPX.36"
    ::= { ipxEventObjects36 1 }

ipx36_packet_count OBJECT-TYPE
    SYNTAX Integer32
    MAX-ACCESS accessible-for-notify
    STATUS current
    DESCRIPTION
        "Parameter 'packet_count' in event IPX.36"
    ::= { ipxEventObjects36 2 }

ipxEventObjects37 OBJECT-IDENTITY
    STATUS current
    DESCRIPTION
        "Event IPX.37
        The router sent a RIP Response. The router sent the response in
        the specified number of packets."
    ::= { ipxEventsGroup 37 }

ipx37_interface OBJECT-TYPE
    SYNTAX DisplayString
    MAX-ACCESS accessible-for-notify
    STATUS current
    DESCRIPTION
        "Parameter 'interface' in event IPX.37"
    ::= { ipxEventObjects37 1 }

ipx37_packet_count OBJECT-TYPE
    SYNTAX Integer32
    MAX-ACCESS accessible-for-notify
    STATUS current
    DESCRIPTION
        "Parameter 'packet_count' in event IPX.37"
    ::= { ipxEventObjects37 2 }

ipxEventObjects38 OBJECT-IDENTITY
    STATUS current
    DESCRIPTION
        "Event IPX.38
        This message is generated when an IPX packet arrives on a network and
        the IPX forwarder is not active on that network."
    ::= { ipxEventsGroup 38 }

ipx38_source_net OBJECT-TYPE
    SYNTAX Integer32
    MAX-ACCESS accessible-for-notify
    STATUS current
    DESCRIPTION
        "Parameter 'source_net' in event IPX.38"
    ::= { ipxEventObjects38 1 }

ipx38_source_node OBJECT-TYPE
    SYNTAX DisplayString
    MAX-ACCESS accessible-for-notify
    STATUS current
    DESCRIPTION
        "Parameter 'source_node' in event IPX.38"
    ::= { ipxEventObjects38 2 }

ipx38_dest_net OBJECT-TYPE
    SYNTAX Integer32
    MAX-ACCESS accessible-for-notify
    STATUS current
    DESCRIPTION
        "Parameter 'dest_net' in event IPX.38"
    ::= { ipxEventObjects38 3 }

ipx38_dest_node OBJECT-TYPE
    SYNTAX DisplayString
    MAX-ACCESS accessible-for-notify
    STATUS current
    DESCRIPTION
        "Parameter 'dest_node' in event IPX.38"
    ::= { ipxEventObjects38 4 }

ipxEventObjects39 OBJECT-IDENTITY
    STATUS current
    DESCRIPTION
        "Event IPX.39
        The router sent a RIP delta Response. This response includes only
        those networks whose data changed in the last update period. The router
        sent the response in the specified number of packets."
    ::= { ipxEventsGroup 39 }

ipx39_interface OBJECT-TYPE
    SYNTAX DisplayString
    MAX-ACCESS accessible-for-notify
    STATUS current
    DESCRIPTION
        "Parameter 'interface' in event IPX.39"
    ::= { ipxEventObjects39 1 }

ipx39_packet_count OBJECT-TYPE
    SYNTAX Integer32
    MAX-ACCESS accessible-for-notify
    STATUS current
    DESCRIPTION
        "Parameter 'packet_count' in event IPX.39"
    ::= { ipxEventObjects39 2 }

ipxEventObjects40 OBJECT-IDENTITY
    STATUS current
    DESCRIPTION
        "Event IPX.40
        The router did not successfully transmit an outgoing RIP response
        packet for the reason the error code indicates."
    ::= { ipxEventsGroup 40 }

ipx40_interface OBJECT-TYPE
    SYNTAX DisplayString
    MAX-ACCESS accessible-for-notify
    STATUS current
    DESCRIPTION
        "Parameter 'interface' in event IPX.40"
    ::= { ipxEventObjects40 1 }

ipx40_reason_code OBJECT-TYPE
    SYNTAX Integer32
    MAX-ACCESS accessible-for-notify
    STATUS current
    DESCRIPTION
        "Parameter 'reason_code' in event IPX.40"
    ::= { ipxEventObjects40 2 }

ipxEventObjects41 OBJECT-IDENTITY
    STATUS current
    DESCRIPTION
        "Event IPX.41
        The router did not successfully transmit an outgoing RIP query packet
        for the reason the error code indicates."
    ::= { ipxEventsGroup 41 }

ipx41_interface OBJECT-TYPE
    SYNTAX DisplayString
    MAX-ACCESS accessible-for-notify
    STATUS current
    DESCRIPTION
        "Parameter 'interface' in event IPX.41"
    ::= { ipxEventObjects41 1 }

ipx41_reason_code OBJECT-TYPE
    SYNTAX Integer32
    MAX-ACCESS accessible-for-notify
    STATUS current
    DESCRIPTION
        "Parameter 'reason_code' in event IPX.41"
    ::= { ipxEventObjects41 2 }

ipxEventObjects42 OBJECT-IDENTITY
    STATUS current
    DESCRIPTION
        "Event IPX.42
        A SAP Nearest Service Reply will be sent to the specified node.
        The service_type is the type of service, and the service_name is
        the name of the service."
    ::= { ipxEventsGroup 42 }

ipx42_service_type OBJECT-TYPE
    SYNTAX Integer32
    MAX-ACCESS accessible-for-notify
    STATUS current
    DESCRIPTION
        "Parameter 'service_type' in event IPX.42"
    ::= { ipxEventObjects42 1 }

ipx42_service_name OBJECT-TYPE
    SYNTAX DisplayString
    MAX-ACCESS accessible-for-notify
    STATUS current
    DESCRIPTION
        "Parameter 'service_name' in event IPX.42"
    ::= { ipxEventObjects42 2 }

ipx42_source_net OBJECT-TYPE
    SYNTAX Integer32
    MAX-ACCESS accessible-for-notify
    STATUS current
    DESCRIPTION
        "Parameter 'source_net' in event IPX.42"
    ::= { ipxEventObjects42 3 }

ipx42_source_node OBJECT-TYPE
    SYNTAX DisplayString
    MAX-ACCESS accessible-for-notify
    STATUS current
    DESCRIPTION
        "Parameter 'source_node' in event IPX.42"
    ::= { ipxEventObjects42 4 }

ipx42_interface OBJECT-TYPE
    SYNTAX DisplayString
    MAX-ACCESS accessible-for-notify
    STATUS current
    DESCRIPTION
        "Parameter 'interface' in event IPX.42"
    ::= { ipxEventObjects42 5 }

ipxEventObjects43 OBJECT-IDENTITY
    STATUS current
    DESCRIPTION
        "Event IPX.43
        A SAP Nearest Service Query was received from the specified node via
        the specified interface. If this router is the best route to
        the closest server of the specified service_type, this router
        will answer."
    ::= { ipxEventsGroup 43 }

ipx43_service_type OBJECT-TYPE
    SYNTAX Integer32
    MAX-ACCESS accessible-for-notify
    STATUS current
    DESCRIPTION
        "Parameter 'service_type' in event IPX.43"
    ::= { ipxEventObjects43 1 }

ipx43_source_net OBJECT-TYPE
    SYNTAX Integer32
    MAX-ACCESS accessible-for-notify
    STATUS current
    DESCRIPTION
        "Parameter 'source_net' in event IPX.43"
    ::= { ipxEventObjects43 2 }

ipx43_source_node OBJECT-TYPE
    SYNTAX DisplayString
    MAX-ACCESS accessible-for-notify
    STATUS current
    DESCRIPTION
        "Parameter 'source_node' in event IPX.43"
    ::= { ipxEventObjects43 3 }

ipx43_interface OBJECT-TYPE
    SYNTAX DisplayString
    MAX-ACCESS accessible-for-notify
    STATUS current
    DESCRIPTION
        "Parameter 'interface' in event IPX.43"
    ::= { ipxEventObjects43 4 }

ipxEventObjects44 OBJECT-IDENTITY
    STATUS current
    DESCRIPTION
        "Event IPX.44
        The router sent a SAP delta General Service Reply on the specified
        network. This Reply only includes those services whose data changed in
        the last update period. It took the specified number of packets to send
        the changes in SAP database."
    ::= { ipxEventsGroup 44 }

ipx44_interface OBJECT-TYPE
    SYNTAX DisplayString
    MAX-ACCESS accessible-for-notify
    STATUS current
    DESCRIPTION
        "Parameter 'interface' in event IPX.44"
    ::= { ipxEventObjects44 1 }

ipx44_count OBJECT-TYPE
    SYNTAX Integer32
    MAX-ACCESS accessible-for-notify
    STATUS current
    DESCRIPTION
        "Parameter 'count' in event IPX.44"
    ::= { ipxEventObjects44 2 }

ipxEventObjects45 OBJECT-IDENTITY
    STATUS current
    DESCRIPTION
        "Event IPX.45
        This message is generated when a new service is added to the SAP table.
        The specified via_net/via_node is the route to this service, with
        the noted number of hops."
    ::= { ipxEventsGroup 45 }

ipx45_service_type OBJECT-TYPE
    SYNTAX Integer32
    MAX-ACCESS accessible-for-notify
    STATUS current
    DESCRIPTION
        "Parameter 'service_type' in event IPX.45"
    ::= { ipxEventObjects45 1 }

ipx45_service_name OBJECT-TYPE
    SYNTAX DisplayString
    MAX-ACCESS accessible-for-notify
    STATUS current
    DESCRIPTION
        "Parameter 'service_name' in event IPX.45"
    ::= { ipxEventObjects45 2 }

ipx45_via_net OBJECT-TYPE
    SYNTAX Integer32
    MAX-ACCESS accessible-for-notify
    STATUS current
    DESCRIPTION
        "Parameter 'via_net' in event IPX.45"
    ::= { ipxEventObjects45 3 }

ipx45_via_node OBJECT-TYPE
    SYNTAX DisplayString
    MAX-ACCESS accessible-for-notify
    STATUS current
    DESCRIPTION
        "Parameter 'via_node' in event IPX.45"
    ::= { ipxEventObjects45 4 }

ipx45_hop_count OBJECT-TYPE
    SYNTAX Integer32
    MAX-ACCESS accessible-for-notify
    STATUS current
    DESCRIPTION
        "Parameter 'hop_count' in event IPX.45"
    ::= { ipxEventObjects45 5 }

ipx45_interface OBJECT-TYPE
    SYNTAX DisplayString
    MAX-ACCESS accessible-for-notify
    STATUS current
    DESCRIPTION
        "Parameter 'interface' in event IPX.45"
    ::= { ipxEventObjects45 6 }

ipxEventObjects46 OBJECT-IDENTITY
    STATUS current
    DESCRIPTION
        "Event IPX.46
        A SAP Nearest Service Query was received from the specified node via
        the specified interface, but processing of these packets has been
        administratively disabled on this interface. The query will be ignored."
    ::= { ipxEventsGroup 46 }

ipx46_source_net OBJECT-TYPE
    SYNTAX Integer32
    MAX-ACCESS accessible-for-notify
    STATUS current
    DESCRIPTION
        "Parameter 'source_net' in event IPX.46"
    ::= { ipxEventObjects46 1 }

ipx46_source_node OBJECT-TYPE
    SYNTAX DisplayString
    MAX-ACCESS accessible-for-notify
    STATUS current
    DESCRIPTION
        "Parameter 'source_node' in event IPX.46"
    ::= { ipxEventObjects46 2 }

ipx46_interface OBJECT-TYPE
    SYNTAX DisplayString
    MAX-ACCESS accessible-for-notify
    STATUS current
    DESCRIPTION
        "Parameter 'interface' in event IPX.46"
    ::= { ipxEventObjects46 3 }

ipxEventObjects47 OBJECT-IDENTITY
    STATUS current
    DESCRIPTION
        "Event IPX.47
        The router did not successfully transmit an outgoing SAP query packet
        for the reason the error code indicates."
    ::= { ipxEventsGroup 47 }

ipx47_interface OBJECT-TYPE
    SYNTAX DisplayString
    MAX-ACCESS accessible-for-notify
    STATUS current
    DESCRIPTION
        "Parameter 'interface' in event IPX.47"
    ::= { ipxEventObjects47 1 }

ipx47_reason_code OBJECT-TYPE
    SYNTAX Integer32
    MAX-ACCESS accessible-for-notify
    STATUS current
    DESCRIPTION
        "Parameter 'reason_code' in event IPX.47"
    ::= { ipxEventObjects47 2 }

ipxEventObjects48 OBJECT-IDENTITY
    STATUS current
    DESCRIPTION
        "Event IPX.48
        The router did not successfully transmit an outgoing RIP query packet
        for the reason the error code indicates."
    ::= { ipxEventsGroup 48 }

ipx48_interface OBJECT-TYPE
    SYNTAX DisplayString
    MAX-ACCESS accessible-for-notify
    STATUS current
    DESCRIPTION
        "Parameter 'interface' in event IPX.48"
    ::= { ipxEventObjects48 1 }

ipx48_reason_code OBJECT-TYPE
    SYNTAX Integer32
    MAX-ACCESS accessible-for-notify
    STATUS current
    DESCRIPTION
        "Parameter 'reason_code' in event IPX.48"
    ::= { ipxEventObjects48 2 }

ipxEventObjects49 OBJECT-IDENTITY
    STATUS current
    DESCRIPTION
        "Event IPX.49
        A SAP Nearest Service Query was received from source_net/source_node,
        but the SAP database has no service registered of
        the desired service_type. No response will be sent."
    ::= { ipxEventsGroup 49 }

ipx49_service_type OBJECT-TYPE
    SYNTAX Integer32
    MAX-ACCESS accessible-for-notify
    STATUS current
    DESCRIPTION
        "Parameter 'service_type' in event IPX.49"
    ::= { ipxEventObjects49 1 }

ipx49_source_net OBJECT-TYPE
    SYNTAX Integer32
    MAX-ACCESS accessible-for-notify
    STATUS current
    DESCRIPTION
        "Parameter 'source_net' in event IPX.49"
    ::= { ipxEventObjects49 2 }

ipx49_source_node OBJECT-TYPE
    SYNTAX DisplayString
    MAX-ACCESS accessible-for-notify
    STATUS current
    DESCRIPTION
        "Parameter 'source_node' in event IPX.49"
    ::= { ipxEventObjects49 3 }

ipx49_interface OBJECT-TYPE
    SYNTAX DisplayString
    MAX-ACCESS accessible-for-notify
    STATUS current
    DESCRIPTION
        "Parameter 'interface' in event IPX.49"
    ::= { ipxEventObjects49 4 }

ipxEventObjects50 OBJECT-IDENTITY
    STATUS current
    DESCRIPTION
        "Event IPX.50
        This message is generated when a previously reachable service becomes
        unreachable, and is marked as Dead in the SAP table.
        The specified via_net/via_node is the server or router that announced
        the service as being unreachable."
    ::= { ipxEventsGroup 50 }

ipx50_service_type OBJECT-TYPE
    SYNTAX Integer32
    MAX-ACCESS accessible-for-notify
    STATUS current
    DESCRIPTION
        "Parameter 'service_type' in event IPX.50"
    ::= { ipxEventObjects50 1 }

ipx50_service_name OBJECT-TYPE
    SYNTAX DisplayString
    MAX-ACCESS accessible-for-notify
    STATUS current
    DESCRIPTION
        "Parameter 'service_name' in event IPX.50"
    ::= { ipxEventObjects50 2 }

ipx50_via_net OBJECT-TYPE
    SYNTAX Integer32
    MAX-ACCESS accessible-for-notify
    STATUS current
    DESCRIPTION
        "Parameter 'via_net' in event IPX.50"
    ::= { ipxEventObjects50 3 }

ipx50_via_node OBJECT-TYPE
    SYNTAX DisplayString
    MAX-ACCESS accessible-for-notify
    STATUS current
    DESCRIPTION
        "Parameter 'via_node' in event IPX.50"
    ::= { ipxEventObjects50 4 }

ipx50_interface OBJECT-TYPE
    SYNTAX DisplayString
    MAX-ACCESS accessible-for-notify
    STATUS current
    DESCRIPTION
        "Parameter 'interface' in event IPX.50"
    ::= { ipxEventObjects50 5 }

ipxEventObjects51 OBJECT-IDENTITY
    STATUS current
    DESCRIPTION
        "Event IPX.51
        This message is generated when a previously reachable network becomes
        unreachable, and is marked as Dead in the RIP table.
        The specified router_net/router_node is the router that announced
        the network as being unreachable."
    ::= { ipxEventsGroup 51 }

ipx51_network OBJECT-TYPE
    SYNTAX Integer32
    MAX-ACCESS accessible-for-notify
    STATUS current
    DESCRIPTION
        "Parameter 'network' in event IPX.51"
    ::= { ipxEventObjects51 1 }

ipx51_router_net OBJECT-TYPE
    SYNTAX Integer32
    MAX-ACCESS accessible-for-notify
    STATUS current
    DESCRIPTION
        "Parameter 'router_net' in event IPX.51"
    ::= { ipxEventObjects51 2 }

ipx51_router_node OBJECT-TYPE
    SYNTAX DisplayString
    MAX-ACCESS accessible-for-notify
    STATUS current
    DESCRIPTION
        "Parameter 'router_node' in event IPX.51"
    ::= { ipxEventObjects51 3 }

ipxEventObjects52 OBJECT-IDENTITY
    STATUS current
    DESCRIPTION
        "Event IPX.52
        This message is generated when a RIP response packet is received with
        a source network number that is not the same as the network number
        of this interface. The packet will be ignored."
    ::= { ipxEventsGroup 52 }

ipx52_source_net OBJECT-TYPE
    SYNTAX Integer32
    MAX-ACCESS accessible-for-notify
    STATUS current
    DESCRIPTION
        "Parameter 'source_net' in event IPX.52"
    ::= { ipxEventObjects52 1 }

ipx52_source_node OBJECT-TYPE
    SYNTAX DisplayString
    MAX-ACCESS accessible-for-notify
    STATUS current
    DESCRIPTION
        "Parameter 'source_node' in event IPX.52"
    ::= { ipxEventObjects52 2 }

ipx52_local_net OBJECT-TYPE
    SYNTAX Integer32
    MAX-ACCESS accessible-for-notify
    STATUS current
    DESCRIPTION
        "Parameter 'local_net' in event IPX.52"
    ::= { ipxEventObjects52 3 }

ipx52_interface OBJECT-TYPE
    SYNTAX DisplayString
    MAX-ACCESS accessible-for-notify
    STATUS current
    DESCRIPTION
        "Parameter 'interface' in event IPX.52"
    ::= { ipxEventObjects52 4 }

ipxEventObjects53 OBJECT-IDENTITY
    STATUS current
    DESCRIPTION
        "Event IPX.53
        This message is generated when a SAP response packet is received with
        a source network number that is not the same as the network number
        of this interface. The packet will be ignored."
    ::= { ipxEventsGroup 53 }

ipx53_source_net OBJECT-TYPE
    SYNTAX Integer32
    MAX-ACCESS accessible-for-notify
    STATUS current
    DESCRIPTION
        "Parameter 'source_net' in event IPX.53"
    ::= { ipxEventObjects53 1 }

ipx53_source_node OBJECT-TYPE
    SYNTAX DisplayString
    MAX-ACCESS accessible-for-notify
    STATUS current
    DESCRIPTION
        "Parameter 'source_node' in event IPX.53"
    ::= { ipxEventObjects53 2 }

ipx53_local_net OBJECT-TYPE
    SYNTAX Integer32
    MAX-ACCESS accessible-for-notify
    STATUS current
    DESCRIPTION
        "Parameter 'local_net' in event IPX.53"
    ::= { ipxEventObjects53 3 }

ipx53_interface OBJECT-TYPE
    SYNTAX DisplayString
    MAX-ACCESS accessible-for-notify
    STATUS current
    DESCRIPTION
        "Parameter 'interface' in event IPX.53"
    ::= { ipxEventObjects53 4 }

ipxEventObjects54 OBJECT-IDENTITY
    STATUS current
    DESCRIPTION
        "Event IPX.54
        This message is generated when the route to a service in the SAP table
        changes. The specified via_net/via_node is the new route to
        this service, with the noted number of hops."
    ::= { ipxEventsGroup 54 }

ipx54_service_type OBJECT-TYPE
    SYNTAX Integer32
    MAX-ACCESS accessible-for-notify
    STATUS current
    DESCRIPTION
        "Parameter 'service_type' in event IPX.54"
    ::= { ipxEventObjects54 1 }

ipx54_service_name OBJECT-TYPE
    SYNTAX DisplayString
    MAX-ACCESS accessible-for-notify
    STATUS current
    DESCRIPTION
        "Parameter 'service_name' in event IPX.54"
    ::= { ipxEventObjects54 2 }

ipx54_via_net OBJECT-TYPE
    SYNTAX Integer32
    MAX-ACCESS accessible-for-notify
    STATUS current
    DESCRIPTION
        "Parameter 'via_net' in event IPX.54"
    ::= { ipxEventObjects54 3 }

ipx54_via_node OBJECT-TYPE
    SYNTAX DisplayString
    MAX-ACCESS accessible-for-notify
    STATUS current
    DESCRIPTION
        "Parameter 'via_node' in event IPX.54"
    ::= { ipxEventObjects54 4 }

ipx54_hop_count OBJECT-TYPE
    SYNTAX Integer32
    MAX-ACCESS accessible-for-notify
    STATUS current
    DESCRIPTION
        "Parameter 'hop_count' in event IPX.54"
    ::= { ipxEventObjects54 5 }

ipx54_interface OBJECT-TYPE
    SYNTAX DisplayString
    MAX-ACCESS accessible-for-notify
    STATUS current
    DESCRIPTION
        "Parameter 'interface' in event IPX.54"
    ::= { ipxEventObjects54 6 }

ipxEventObjects55 OBJECT-IDENTITY
    STATUS current
    DESCRIPTION
        "Event IPX.55
        This message is generated when a new network is added to
        the RIP routing table. The new network was advertised by
        router_net/router_node, which is now the route to this network, with
        the noted number of hops."
    ::= { ipxEventsGroup 55 }

ipx55_network OBJECT-TYPE
    SYNTAX Integer32
    MAX-ACCESS accessible-for-notify
    STATUS current
    DESCRIPTION
        "Parameter 'network' in event IPX.55"
    ::= { ipxEventObjects55 1 }

ipx55_router_net OBJECT-TYPE
    SYNTAX Integer32
    MAX-ACCESS accessible-for-notify
    STATUS current
    DESCRIPTION
        "Parameter 'router_net' in event IPX.55"
    ::= { ipxEventObjects55 2 }

ipx55_router_node OBJECT-TYPE
    SYNTAX DisplayString
    MAX-ACCESS accessible-for-notify
    STATUS current
    DESCRIPTION
        "Parameter 'router_node' in event IPX.55"
    ::= { ipxEventObjects55 3 }

ipx55_hop_count OBJECT-TYPE
    SYNTAX Integer32
    MAX-ACCESS accessible-for-notify
    STATUS current
    DESCRIPTION
        "Parameter 'hop_count' in event IPX.55"
    ::= { ipxEventObjects55 4 }

ipxEventObjects56 OBJECT-IDENTITY
    STATUS current
    DESCRIPTION
        "Event IPX.56
        This message is generated when a network is removed from
        the RIP routing table because no routing updates have been heard for it
        in 300 seconds. This normally happens 60 seconds after
        an IPX.012 message on the same service."
    ::= { ipxEventsGroup 56 }

ipx56_network OBJECT-TYPE
    SYNTAX Integer32
    MAX-ACCESS accessible-for-notify
    STATUS current
    DESCRIPTION
        "Parameter 'network' in event IPX.56"
    ::= { ipxEventObjects56 1 }

ipxEventObjects57 OBJECT-IDENTITY
    STATUS current
    DESCRIPTION
        "Event IPX.57
        The specified network interface has gone down, and this SAP service
        having a first hop on that network will be placed in the dead state.
        It will be advertised as unreachable for another 60 seconds, and then
        removed from the SAP table. However, if there are alternate routes to
        the same service, they will be learned about within 60 seconds."
    ::= { ipxEventsGroup 57 }

ipx57_service_type OBJECT-TYPE
    SYNTAX Integer32
    MAX-ACCESS accessible-for-notify
    STATUS current
    DESCRIPTION
        "Parameter 'service_type' in event IPX.57"
    ::= { ipxEventObjects57 1 }

ipx57_service_name OBJECT-TYPE
    SYNTAX DisplayString
    MAX-ACCESS accessible-for-notify
    STATUS current
    DESCRIPTION
        "Parameter 'service_name' in event IPX.57"
    ::= { ipxEventObjects57 2 }

ipx57_interface OBJECT-TYPE
    SYNTAX DisplayString
    MAX-ACCESS accessible-for-notify
    STATUS current
    DESCRIPTION
        "Parameter 'interface' in event IPX.57"
    ::= { ipxEventObjects57 3 }

ipxEventObjects58 OBJECT-IDENTITY
    STATUS current
    DESCRIPTION
        "Event IPX.58
        This message is generated when a network is removed from
        the SAP routing table because no SAP responses have been heard for it
        in 300 seconds."
    ::= { ipxEventsGroup 58 }

ipx58_service_type OBJECT-TYPE
    SYNTAX Integer32
    MAX-ACCESS accessible-for-notify
    STATUS current
    DESCRIPTION
        "Parameter 'service_type' in event IPX.58"
    ::= { ipxEventObjects58 1 }

ipx58_service_name OBJECT-TYPE
    SYNTAX DisplayString
    MAX-ACCESS accessible-for-notify
    STATUS current
    DESCRIPTION
        "Parameter 'service_name' in event IPX.58"
    ::= { ipxEventObjects58 2 }

ipxEventObjects59 OBJECT-IDENTITY
    STATUS current
    DESCRIPTION
        "Event IPX.59
        This message is generated when an advertisement for a service is
        received, but that service is on an IPX network (service_net) that
        this router has no route to. This advertisement will be ignored."
    ::= { ipxEventsGroup 59 }

ipx59_service_type OBJECT-TYPE
    SYNTAX Integer32
    MAX-ACCESS accessible-for-notify
    STATUS current
    DESCRIPTION
        "Parameter 'service_type' in event IPX.59"
    ::= { ipxEventObjects59 1 }

ipx59_service_name OBJECT-TYPE
    SYNTAX DisplayString
    MAX-ACCESS accessible-for-notify
    STATUS current
    DESCRIPTION
        "Parameter 'service_name' in event IPX.59"
    ::= { ipxEventObjects59 2 }

ipx59_service_net OBJECT-TYPE
    SYNTAX Integer32
    MAX-ACCESS accessible-for-notify
    STATUS current
    DESCRIPTION
        "Parameter 'service_net' in event IPX.59"
    ::= { ipxEventObjects59 3 }

ipx59_service_node OBJECT-TYPE
    SYNTAX DisplayString
    MAX-ACCESS accessible-for-notify
    STATUS current
    DESCRIPTION
        "Parameter 'service_node' in event IPX.59"
    ::= { ipxEventObjects59 4 }

ipx59_via_net OBJECT-TYPE
    SYNTAX Integer32
    MAX-ACCESS accessible-for-notify
    STATUS current
    DESCRIPTION
        "Parameter 'via_net' in event IPX.59"
    ::= { ipxEventObjects59 5 }

ipx59_via_node OBJECT-TYPE
    SYNTAX DisplayString
    MAX-ACCESS accessible-for-notify
    STATUS current
    DESCRIPTION
        "Parameter 'via_node' in event IPX.59"
    ::= { ipxEventObjects59 6 }

ipx59_interface OBJECT-TYPE
    SYNTAX DisplayString
    MAX-ACCESS accessible-for-notify
    STATUS current
    DESCRIPTION
        "Parameter 'interface' in event IPX.59"
    ::= { ipxEventObjects59 7 }

ipxEventObjects61 OBJECT-IDENTITY
    STATUS current
    DESCRIPTION
        "Event IPX.61
        The SAP protocol has completed the transmission of the periodic
        SAP General Service Response packets on all IPX interfaces.
        In doing this, it attempted to send packet_count packets in total."
    ::= { ipxEventsGroup 61 }

ipx61_packet_count OBJECT-TYPE
    SYNTAX Integer32
    MAX-ACCESS accessible-for-notify
    STATUS current
    DESCRIPTION
        "Parameter 'packet_count' in event IPX.61"
    ::= { ipxEventObjects61 1 }

ipxEventObjects62 OBJECT-IDENTITY
    STATUS current
    DESCRIPTION
        "Event IPX.62
        There was no packet buffer available to send one packet of
        the periodic SAP General Service Response. The response will stall for
        half a second, waiting for a buffer to become available.
        The packet_number is the count of this packet within the complete
        response, starting at 0."
    ::= { ipxEventsGroup 62 }

ipx62_packet_number OBJECT-TYPE
    SYNTAX Integer32
    MAX-ACCESS accessible-for-notify
    STATUS current
    DESCRIPTION
        "Parameter 'packet_number' in event IPX.62"
    ::= { ipxEventObjects62 1 }

ipx62_interface OBJECT-TYPE
    SYNTAX DisplayString
    MAX-ACCESS accessible-for-notify
    STATUS current
    DESCRIPTION
        "Parameter 'interface' in event IPX.62"
    ::= { ipxEventObjects62 2 }

ipxEventObjects63 OBJECT-IDENTITY
    STATUS current
    DESCRIPTION
        "Event IPX.63
        The router did not successfully transmit an outgoing SAP periodic
        General Service Response for the reason the error code indicates."
    ::= { ipxEventsGroup 63 }

ipx63_interface OBJECT-TYPE
    SYNTAX DisplayString
    MAX-ACCESS accessible-for-notify
    STATUS current
    DESCRIPTION
        "Parameter 'interface' in event IPX.63"
    ::= { ipxEventObjects63 1 }

ipx63_reason_code OBJECT-TYPE
    SYNTAX Integer32
    MAX-ACCESS accessible-for-notify
    STATUS current
    DESCRIPTION
        "Parameter 'reason_code' in event IPX.63"
    ::= { ipxEventObjects63 2 }

ipxEventObjects64 OBJECT-IDENTITY
    STATUS current
    DESCRIPTION
        "Event IPX.64
        A SAP periodic General Service Reply packet has just been sent on the
        specified network. There were entry_count services in this packet."
    ::= { ipxEventsGroup 64 }

ipx64_entry_count OBJECT-TYPE
    SYNTAX Integer32
    MAX-ACCESS accessible-for-notify
    STATUS current
    DESCRIPTION
        "Parameter 'entry_count' in event IPX.64"
    ::= { ipxEventObjects64 1 }

ipx64_interface OBJECT-TYPE
    SYNTAX DisplayString
    MAX-ACCESS accessible-for-notify
    STATUS current
    DESCRIPTION
        "Parameter 'interface' in event IPX.64"
    ::= { ipxEventObjects64 2 }

ipxEventObjects67 OBJECT-IDENTITY
    STATUS current
    DESCRIPTION
        "Event IPX.67
        The IPX routing cache entry for the listed destination has been cleared."
    ::= { ipxEventsGroup 67 }

ipx67_dest_net OBJECT-TYPE
    SYNTAX Integer32
    MAX-ACCESS accessible-for-notify
    STATUS current
    DESCRIPTION
        "Parameter 'dest_net' in event IPX.67"
    ::= { ipxEventObjects67 1 }

ipx67_dest_node OBJECT-TYPE
    SYNTAX DisplayString
    MAX-ACCESS accessible-for-notify
    STATUS current
    DESCRIPTION
        "Parameter 'dest_node' in event IPX.67"
    ::= { ipxEventObjects67 2 }

ipxEventObjects69 OBJECT-IDENTITY
    STATUS current
    DESCRIPTION
        "Event IPX.69
        This message is generated when a new alternate entry cannot be made
        to routing table because alternate entry space is already full."
    ::= { ipxEventsGroup 69 }

ipx69_protocol OBJECT-TYPE
    SYNTAX DisplayString
    MAX-ACCESS accessible-for-notify
    STATUS current
    DESCRIPTION
        "Parameter 'protocol' in event IPX.69"
    ::= { ipxEventObjects69 1 }

ipx69_destination_net OBJECT-TYPE
    SYNTAX Integer32
    MAX-ACCESS accessible-for-notify
    STATUS current
    DESCRIPTION
        "Parameter 'destination_net' in event IPX.69"
    ::= { ipxEventObjects69 2 }

ipxEventObjects70 OBJECT-IDENTITY
    STATUS current
    DESCRIPTION
        "Event IPX.70
        This message is generated when a new alternate entry cannot be made
        to routing table because alternate entry space for a given route
        is already full."
    ::= { ipxEventsGroup 70 }

ipx70_destination_net OBJECT-TYPE
    SYNTAX Integer32
    MAX-ACCESS accessible-for-notify
    STATUS current
    DESCRIPTION
        "Parameter 'destination_net' in event IPX.70"
    ::= { ipxEventObjects70 1 }

ipxEventObjects71 OBJECT-IDENTITY
    STATUS current
    DESCRIPTION
        "Event IPX.71
        This message is generated when an IPX packet is received with
        an encapsulation other than that which has been selected
        for this interface."
    ::= { ipxEventsGroup 71 }

ipx71_encap_seen OBJECT-TYPE
    SYNTAX DisplayString
    MAX-ACCESS accessible-for-notify
    STATUS current
    DESCRIPTION
        "Parameter 'encap_seen' in event IPX.71"
    ::= { ipxEventObjects71 1 }

ipx71_encap_used OBJECT-TYPE
    SYNTAX DisplayString
    MAX-ACCESS accessible-for-notify
    STATUS current
    DESCRIPTION
        "Parameter 'encap_used' in event IPX.71"
    ::= { ipxEventObjects71 2 }

ipx71_interface OBJECT-TYPE
    SYNTAX DisplayString
    MAX-ACCESS accessible-for-notify
    STATUS current
    DESCRIPTION
        "Parameter 'interface' in event IPX.71"
    ::= { ipxEventObjects71 3 }

ipxEventObjects72 OBJECT-IDENTITY
    STATUS current
    DESCRIPTION
        "Event IPX.72
        An IPXWAN Response is built from a Request.
        An attempt has been made to build the response without a request."
    ::= { ipxEventsGroup 72 }

ipx72_iw_pkttype OBJECT-TYPE
    SYNTAX DisplayString
    MAX-ACCESS accessible-for-notify
    STATUS current
    DESCRIPTION
        "Parameter 'iw_pkttype' in event IPX.72"
    ::= { ipxEventObjects72 1 }

ipx72_interface OBJECT-TYPE
    SYNTAX DisplayString
    MAX-ACCESS accessible-for-notify
    STATUS current
    DESCRIPTION
        "Parameter 'interface' in event IPX.72"
    ::= { ipxEventObjects72 2 }

ipxEventObjects74 OBJECT-IDENTITY
    STATUS current
    DESCRIPTION
        "Event IPX.74
        IPXWAN has been configured to run on an unsupported interface type."
    ::= { ipxEventsGroup 74 }

ipx74_interface OBJECT-TYPE
    SYNTAX DisplayString
    MAX-ACCESS accessible-for-notify
    STATUS current
    DESCRIPTION
        "Parameter 'interface' in event IPX.74"
    ::= { ipxEventObjects74 1 }

ipxEventObjects75 OBJECT-IDENTITY
    STATUS current
    DESCRIPTION
        "Event IPX.75
        IPXWAN has been configured to run on the interface, but it has been
        disabled by the user."
    ::= { ipxEventsGroup 75 }

ipx75_interface OBJECT-TYPE
    SYNTAX DisplayString
    MAX-ACCESS accessible-for-notify
    STATUS current
    DESCRIPTION
        "Parameter 'interface' in event IPX.75"
    ::= { ipxEventObjects75 1 }

ipxEventObjects76 OBJECT-IDENTITY
    STATUS current
    DESCRIPTION
        "Event IPX.76
        An IPXWAN packet was dropped because it was received on an unsupported
        interface type."
    ::= { ipxEventsGroup 76 }

ipx76_iw_pkttype OBJECT-TYPE
    SYNTAX DisplayString
    MAX-ACCESS accessible-for-notify
    STATUS current
    DESCRIPTION
        "Parameter 'iw_pkttype' in event IPX.76"
    ::= { ipxEventObjects76 1 }

ipx76_interface OBJECT-TYPE
    SYNTAX DisplayString
    MAX-ACCESS accessible-for-notify
    STATUS current
    DESCRIPTION
        "Parameter 'interface' in event IPX.76"
    ::= { ipxEventObjects76 2 }

ipxEventObjects77 OBJECT-IDENTITY
    STATUS current
    DESCRIPTION
        "Event IPX.77
        An IPXWAN packet was dropped because it was received on an interface
        which is configured to be disabled for IPXWAN traffic."
    ::= { ipxEventsGroup 77 }

ipx77_iw_pkttype OBJECT-TYPE
    SYNTAX DisplayString
    MAX-ACCESS accessible-for-notify
    STATUS current
    DESCRIPTION
        "Parameter 'iw_pkttype' in event IPX.77"
    ::= { ipxEventObjects77 1 }

ipx77_interface OBJECT-TYPE
    SYNTAX DisplayString
    MAX-ACCESS accessible-for-notify
    STATUS current
    DESCRIPTION
        "Parameter 'interface' in event IPX.77"
    ::= { ipxEventObjects77 2 }

ipxEventObjects78 OBJECT-IDENTITY
    STATUS current
    DESCRIPTION
        "Event IPX.78
        An IPXWAN packet was rejected because the confidence ID check failed."
    ::= { ipxEventsGroup 78 }

ipx78_iw_pkttype OBJECT-TYPE
    SYNTAX DisplayString
    MAX-ACCESS accessible-for-notify
    STATUS current
    DESCRIPTION
        "Parameter 'iw_pkttype' in event IPX.78"
    ::= { ipxEventObjects78 1 }

ipx78_interface OBJECT-TYPE
    SYNTAX DisplayString
    MAX-ACCESS accessible-for-notify
    STATUS current
    DESCRIPTION
        "Parameter 'interface' in event IPX.78"
    ::= { ipxEventObjects78 2 }

ipxEventObjects79 OBJECT-IDENTITY
    STATUS current
    DESCRIPTION
        "Event IPX.79
        An IPXWAN packet was rejected because the node id reported in it
        was identical to the local node id."
    ::= { ipxEventsGroup 79 }

ipx79_iw_pkttype OBJECT-TYPE
    SYNTAX DisplayString
    MAX-ACCESS accessible-for-notify
    STATUS current
    DESCRIPTION
        "Parameter 'iw_pkttype' in event IPX.79"
    ::= { ipxEventObjects79 1 }

ipx79_interface OBJECT-TYPE
    SYNTAX DisplayString
    MAX-ACCESS accessible-for-notify
    STATUS current
    DESCRIPTION
        "Parameter 'interface' in event IPX.79"
    ::= { ipxEventObjects79 2 }

ipxEventObjects81 OBJECT-IDENTITY
    STATUS current
    DESCRIPTION
        "Event IPX.81
        An attempt to send an IPXWAN packet failed."
    ::= { ipxEventsGroup 81 }

ipx81_iw_pkttype OBJECT-TYPE
    SYNTAX DisplayString
    MAX-ACCESS accessible-for-notify
    STATUS current
    DESCRIPTION
        "Parameter 'iw_pkttype' in event IPX.81"
    ::= { ipxEventObjects81 1 }

ipx81_interface OBJECT-TYPE
    SYNTAX DisplayString
    MAX-ACCESS accessible-for-notify
    STATUS current
    DESCRIPTION
        "Parameter 'interface' in event IPX.81"
    ::= { ipxEventObjects81 2 }

ipxEventObjects82 OBJECT-IDENTITY
    STATUS current
    DESCRIPTION
        "Event IPX.82
        An IPXWAN packet was dropped due to a sequence number mismatch."
    ::= { ipxEventsGroup 82 }

ipx82_iw_pkttype OBJECT-TYPE
    SYNTAX DisplayString
    MAX-ACCESS accessible-for-notify
    STATUS current
    DESCRIPTION
        "Parameter 'iw_pkttype' in event IPX.82"
    ::= { ipxEventObjects82 1 }

ipx82_interface OBJECT-TYPE
    SYNTAX DisplayString
    MAX-ACCESS accessible-for-notify
    STATUS current
    DESCRIPTION
        "Parameter 'interface' in event IPX.82"
    ::= { ipxEventObjects82 2 }

ipxEventObjects83 OBJECT-IDENTITY
    STATUS current
    DESCRIPTION
        "Event IPX.83
        The router rejected an IPXWAN packet because the other side of the link
        did not accept an option."
    ::= { ipxEventsGroup 83 }

ipx83_iw_pkttype OBJECT-TYPE
    SYNTAX DisplayString
    MAX-ACCESS accessible-for-notify
    STATUS current
    DESCRIPTION
        "Parameter 'iw_pkttype' in event IPX.83"
    ::= { ipxEventObjects83 1 }

ipx83_interface OBJECT-TYPE
    SYNTAX DisplayString
    MAX-ACCESS accessible-for-notify
    STATUS current
    DESCRIPTION
        "Parameter 'interface' in event IPX.83"
    ::= { ipxEventObjects83 2 }

ipx83_opt_type OBJECT-TYPE
    SYNTAX DisplayString
    MAX-ACCESS accessible-for-notify
    STATUS current
    DESCRIPTION
        "Parameter 'opt_type' in event IPX.83"
    ::= { ipxEventObjects83 3 }

ipxEventObjects84 OBJECT-IDENTITY
    STATUS current
    DESCRIPTION
        "Event IPX.84
        A previously timed-out IPXWAN connection is to be retried."
    ::= { ipxEventsGroup 84 }

ipx84_interface OBJECT-TYPE
    SYNTAX DisplayString
    MAX-ACCESS accessible-for-notify
    STATUS current
    DESCRIPTION
        "Parameter 'interface' in event IPX.84"
    ::= { ipxEventObjects84 1 }

ipxEventObjects85 OBJECT-IDENTITY
    STATUS current
    DESCRIPTION
        "Event IPX.85
        An IPXWAN connection attempt timed-out."
    ::= { ipxEventsGroup 85 }

ipx85_interface OBJECT-TYPE
    SYNTAX DisplayString
    MAX-ACCESS accessible-for-notify
    STATUS current
    DESCRIPTION
        "Parameter 'interface' in event IPX.85"
    ::= { ipxEventObjects85 1 }

ipxEventObjects86 OBJECT-IDENTITY
    STATUS current
    DESCRIPTION
        "Event IPX.86
        An IPXWAN packet was successfully received, accepted, and processed."
    ::= { ipxEventsGroup 86 }

ipx86_iw_pkttype OBJECT-TYPE
    SYNTAX DisplayString
    MAX-ACCESS accessible-for-notify
    STATUS current
    DESCRIPTION
        "Parameter 'iw_pkttype' in event IPX.86"
    ::= { ipxEventObjects86 1 }

ipx86_interface OBJECT-TYPE
    SYNTAX DisplayString
    MAX-ACCESS accessible-for-notify
    STATUS current
    DESCRIPTION
        "Parameter 'interface' in event IPX.86"
    ::= { ipxEventObjects86 2 }

ipxEventObjects87 OBJECT-IDENTITY
    STATUS current
    DESCRIPTION
        "Event IPX.87
        An IPXWAN packet was successfully sent on the interface."
    ::= { ipxEventsGroup 87 }

ipx87_iw_pkttype OBJECT-TYPE
    SYNTAX DisplayString
    MAX-ACCESS accessible-for-notify
    STATUS current
    DESCRIPTION
        "Parameter 'iw_pkttype' in event IPX.87"
    ::= { ipxEventObjects87 1 }

ipx87_interface OBJECT-TYPE
    SYNTAX DisplayString
    MAX-ACCESS accessible-for-notify
    STATUS current
    DESCRIPTION
        "Parameter 'interface' in event IPX.87"
    ::= { ipxEventObjects87 2 }

ipxEventObjects88 OBJECT-IDENTITY
    STATUS current
    DESCRIPTION
        "Event IPX.88
        An IPXWAN connection is up on the given interface."
    ::= { ipxEventsGroup 88 }

ipx88_interface OBJECT-TYPE
    SYNTAX DisplayString
    MAX-ACCESS accessible-for-notify
    STATUS current
    DESCRIPTION
        "Parameter 'interface' in event IPX.88"
    ::= { ipxEventObjects88 1 }

ipxEventObjects89 OBJECT-IDENTITY
    STATUS current
    DESCRIPTION
        "Event IPX.89
        An IPXWAN connection has gone down on the given interface. This can
        happen if the link goes down, if the protocol goes down on the link
        (IPXCP goes down) or if a Timer Request packet is received."
    ::= { ipxEventsGroup 89 }

ipx89_interface OBJECT-TYPE
    SYNTAX DisplayString
    MAX-ACCESS accessible-for-notify
    STATUS current
    DESCRIPTION
        "Parameter 'interface' in event IPX.89"
    ::= { ipxEventObjects89 1 }

ipxEventObjects90 OBJECT-IDENTITY
    STATUS current
    DESCRIPTION
        "Event IPX.90
        The router received a SAP Nearest Service Query from
        source_net/source_node. The SAP database indicates that a server exists
        on the same network as the client. The server will be allowed
        to respond for itself."
    ::= { ipxEventsGroup 90 }

ipx90_service_type OBJECT-TYPE
    SYNTAX Integer32
    MAX-ACCESS accessible-for-notify
    STATUS current
    DESCRIPTION
        "Parameter 'service_type' in event IPX.90"
    ::= { ipxEventObjects90 1 }

ipx90_source_net OBJECT-TYPE
    SYNTAX Integer32
    MAX-ACCESS accessible-for-notify
    STATUS current
    DESCRIPTION
        "Parameter 'source_net' in event IPX.90"
    ::= { ipxEventObjects90 2 }

ipx90_source_node OBJECT-TYPE
    SYNTAX DisplayString
    MAX-ACCESS accessible-for-notify
    STATUS current
    DESCRIPTION
        "Parameter 'source_node' in event IPX.90"
    ::= { ipxEventObjects90 3 }

ipx90_interface OBJECT-TYPE
    SYNTAX DisplayString
    MAX-ACCESS accessible-for-notify
    STATUS current
    DESCRIPTION
        "Parameter 'interface' in event IPX.90"
    ::= { ipxEventObjects90 4 }

ipxEventObjects91 OBJECT-IDENTITY
    STATUS current
    DESCRIPTION
        "Event IPX.91
        A NetBIOS type 20 packet must be at least 62 bytes in length.
        The forwarder drops the packet."
    ::= { ipxEventsGroup 91 }

ipx91_source_net OBJECT-TYPE
    SYNTAX Integer32
    MAX-ACCESS accessible-for-notify
    STATUS current
    DESCRIPTION
        "Parameter 'source_net' in event IPX.91"
    ::= { ipxEventObjects91 1 }

ipx91_source_node OBJECT-TYPE
    SYNTAX DisplayString
    MAX-ACCESS accessible-for-notify
    STATUS current
    DESCRIPTION
        "Parameter 'source_node' in event IPX.91"
    ::= { ipxEventObjects91 2 }

ipx91_interface OBJECT-TYPE
    SYNTAX DisplayString
    MAX-ACCESS accessible-for-notify
    STATUS current
    DESCRIPTION
        "Parameter 'interface' in event IPX.91"
    ::= { ipxEventObjects91 3 }

ipxEventObjects92 OBJECT-IDENTITY
    STATUS current
    DESCRIPTION
        "Event IPX.92
        A new pair of stations have been added to the proxy keepalive table."
    ::= { ipxEventsGroup 92 }

ipx92_source_net OBJECT-TYPE
    SYNTAX Integer32
    MAX-ACCESS accessible-for-notify
    STATUS current
    DESCRIPTION
        "Parameter 'source_net' in event IPX.92"
    ::= { ipxEventObjects92 1 }

ipx92_source_node OBJECT-TYPE
    SYNTAX DisplayString
    MAX-ACCESS accessible-for-notify
    STATUS current
    DESCRIPTION
        "Parameter 'source_node' in event IPX.92"
    ::= { ipxEventObjects92 2 }

ipx92_source_socket OBJECT-TYPE
    SYNTAX Integer32
    MAX-ACCESS accessible-for-notify
    STATUS current
    DESCRIPTION
        "Parameter 'source_socket' in event IPX.92"
    ::= { ipxEventObjects92 3 }

ipx92_dest_net OBJECT-TYPE
    SYNTAX Integer32
    MAX-ACCESS accessible-for-notify
    STATUS current
    DESCRIPTION
        "Parameter 'dest_net' in event IPX.92"
    ::= { ipxEventObjects92 4 }

ipx92_dest_node OBJECT-TYPE
    SYNTAX DisplayString
    MAX-ACCESS accessible-for-notify
    STATUS current
    DESCRIPTION
        "Parameter 'dest_node' in event IPX.92"
    ::= { ipxEventObjects92 5 }

ipx92_dest_socket OBJECT-TYPE
    SYNTAX Integer32
    MAX-ACCESS accessible-for-notify
    STATUS current
    DESCRIPTION
        "Parameter 'dest_socket' in event IPX.92"
    ::= { ipxEventObjects92 6 }

ipxEventObjects93 OBJECT-IDENTITY
    STATUS current
    DESCRIPTION
        "Event IPX.93
        A pair of stations have been removed from the proxy keepalive table."
    ::= { ipxEventsGroup 93 }

ipx93_source_net OBJECT-TYPE
    SYNTAX Integer32
    MAX-ACCESS accessible-for-notify
    STATUS current
    DESCRIPTION
        "Parameter 'source_net' in event IPX.93"
    ::= { ipxEventObjects93 1 }

ipx93_source_node OBJECT-TYPE
    SYNTAX DisplayString
    MAX-ACCESS accessible-for-notify
    STATUS current
    DESCRIPTION
        "Parameter 'source_node' in event IPX.93"
    ::= { ipxEventObjects93 2 }

ipx93_source_socket OBJECT-TYPE
    SYNTAX Integer32
    MAX-ACCESS accessible-for-notify
    STATUS current
    DESCRIPTION
        "Parameter 'source_socket' in event IPX.93"
    ::= { ipxEventObjects93 3 }

ipx93_dest_net OBJECT-TYPE
    SYNTAX Integer32
    MAX-ACCESS accessible-for-notify
    STATUS current
    DESCRIPTION
        "Parameter 'dest_net' in event IPX.93"
    ::= { ipxEventObjects93 4 }

ipx93_dest_node OBJECT-TYPE
    SYNTAX DisplayString
    MAX-ACCESS accessible-for-notify
    STATUS current
    DESCRIPTION
        "Parameter 'dest_node' in event IPX.93"
    ::= { ipxEventObjects93 5 }

ipx93_dest_socket OBJECT-TYPE
    SYNTAX Integer32
    MAX-ACCESS accessible-for-notify
    STATUS current
    DESCRIPTION
        "Parameter 'dest_socket' in event IPX.93"
    ::= { ipxEventObjects93 6 }

ipxEventObjects95 OBJECT-IDENTITY
    STATUS current
    DESCRIPTION
        "Event IPX.95
        The router dropped a Serialization packet because the output network
        interface has IPX KeepAlive filtering enabled."
    ::= { ipxEventsGroup 95 }

ipx95_source_net OBJECT-TYPE
    SYNTAX Integer32
    MAX-ACCESS accessible-for-notify
    STATUS current
    DESCRIPTION
        "Parameter 'source_net' in event IPX.95"
    ::= { ipxEventObjects95 1 }

ipx95_source_node OBJECT-TYPE
    SYNTAX DisplayString
    MAX-ACCESS accessible-for-notify
    STATUS current
    DESCRIPTION
        "Parameter 'source_node' in event IPX.95"
    ::= { ipxEventObjects95 2 }

ipx95_dest_net OBJECT-TYPE
    SYNTAX Integer32
    MAX-ACCESS accessible-for-notify
    STATUS current
    DESCRIPTION
        "Parameter 'dest_net' in event IPX.95"
    ::= { ipxEventObjects95 3 }

ipx95_dest_node OBJECT-TYPE
    SYNTAX DisplayString
    MAX-ACCESS accessible-for-notify
    STATUS current
    DESCRIPTION
        "Parameter 'dest_node' in event IPX.95"
    ::= { ipxEventObjects95 4 }

ipx95_interface OBJECT-TYPE
    SYNTAX DisplayString
    MAX-ACCESS accessible-for-notify
    STATUS current
    DESCRIPTION
        "Parameter 'interface' in event IPX.95"
    ::= { ipxEventObjects95 5 }

ipxEventObjects97 OBJECT-IDENTITY
    STATUS current
    DESCRIPTION
        "Event IPX.97
        The router sent a proxy keepalive packet."
    ::= { ipxEventsGroup 97 }

ipx97_type OBJECT-TYPE
    SYNTAX DisplayString
    MAX-ACCESS accessible-for-notify
    STATUS current
    DESCRIPTION
        "Parameter 'type' in event IPX.97"
    ::= { ipxEventObjects97 1 }

ipx97_source_net OBJECT-TYPE
    SYNTAX Integer32
    MAX-ACCESS accessible-for-notify
    STATUS current
    DESCRIPTION
        "Parameter 'source_net' in event IPX.97"
    ::= { ipxEventObjects97 2 }

ipx97_source_node OBJECT-TYPE
    SYNTAX DisplayString
    MAX-ACCESS accessible-for-notify
    STATUS current
    DESCRIPTION
        "Parameter 'source_node' in event IPX.97"
    ::= { ipxEventObjects97 3 }

ipx97_source_socket OBJECT-TYPE
    SYNTAX Integer32
    MAX-ACCESS accessible-for-notify
    STATUS current
    DESCRIPTION
        "Parameter 'source_socket' in event IPX.97"
    ::= { ipxEventObjects97 4 }

ipx97_dest_net OBJECT-TYPE
    SYNTAX Integer32
    MAX-ACCESS accessible-for-notify
    STATUS current
    DESCRIPTION
        "Parameter 'dest_net' in event IPX.97"
    ::= { ipxEventObjects97 5 }

ipx97_dest_node OBJECT-TYPE
    SYNTAX DisplayString
    MAX-ACCESS accessible-for-notify
    STATUS current
    DESCRIPTION
        "Parameter 'dest_node' in event IPX.97"
    ::= { ipxEventObjects97 6 }

ipx97_dest_socket OBJECT-TYPE
    SYNTAX Integer32
    MAX-ACCESS accessible-for-notify
    STATUS current
    DESCRIPTION
        "Parameter 'dest_socket' in event IPX.97"
    ::= { ipxEventObjects97 7 }

ipxEventObjects98 OBJECT-IDENTITY
    STATUS current
    DESCRIPTION
        "Event IPX.98
        A RIP packet has successfully PASSED through the RIP Router filter
        on the given interface.
        The RIP Router filter is based upon the source_node in
        the IPX packet header, which is displayed by the message."
    ::= { ipxEventsGroup 98 }

ipx98_source_net OBJECT-TYPE
    SYNTAX Integer32
    MAX-ACCESS accessible-for-notify
    STATUS current
    DESCRIPTION
        "Parameter 'source_net' in event IPX.98"
    ::= { ipxEventObjects98 1 }

ipx98_source_node OBJECT-TYPE
    SYNTAX DisplayString
    MAX-ACCESS accessible-for-notify
    STATUS current
    DESCRIPTION
        "Parameter 'source_node' in event IPX.98"
    ::= { ipxEventObjects98 2 }

ipx98_interface OBJECT-TYPE
    SYNTAX DisplayString
    MAX-ACCESS accessible-for-notify
    STATUS current
    DESCRIPTION
        "Parameter 'interface' in event IPX.98"
    ::= { ipxEventObjects98 3 }

ipxEventObjects99 OBJECT-IDENTITY
    STATUS current
    DESCRIPTION
        "Event IPX.99
        A RIP packet has been DROPPED by the RIP Router filter on the
        given interface.
        The RIP Router filter is based upon the source_node in
        the IPX packet header, which is displayed by the message."
    ::= { ipxEventsGroup 99 }

ipx99_source_net OBJECT-TYPE
    SYNTAX Integer32
    MAX-ACCESS accessible-for-notify
    STATUS current
    DESCRIPTION
        "Parameter 'source_net' in event IPX.99"
    ::= { ipxEventObjects99 1 }

ipx99_source_node OBJECT-TYPE
    SYNTAX DisplayString
    MAX-ACCESS accessible-for-notify
    STATUS current
    DESCRIPTION
        "Parameter 'source_node' in event IPX.99"
    ::= { ipxEventObjects99 2 }

ipx99_interface OBJECT-TYPE
    SYNTAX DisplayString
    MAX-ACCESS accessible-for-notify
    STATUS current
    DESCRIPTION
        "Parameter 'interface' in event IPX.99"
    ::= { ipxEventObjects99 3 }

ipxEventObjects100 OBJECT-IDENTITY
    STATUS current
    DESCRIPTION
        "Event IPX.100
        A RIP routing information entry for the given IPX network number
        has successfully PASSED through the RIP filter on the given interface
        in the stated filtering direction, which is either inbound or outbound."
    ::= { ipxEventsGroup 100 }

ipx100_iodir OBJECT-TYPE
    SYNTAX DisplayString
    MAX-ACCESS accessible-for-notify
    STATUS current
    DESCRIPTION
        "Parameter 'iodir' in event IPX.100"
    ::= { ipxEventObjects100 1 }

ipx100_ipx_network OBJECT-TYPE
    SYNTAX Integer32
    MAX-ACCESS accessible-for-notify
    STATUS current
    DESCRIPTION
        "Parameter 'ipx_network' in event IPX.100"
    ::= { ipxEventObjects100 2 }

ipx100_interface OBJECT-TYPE
    SYNTAX DisplayString
    MAX-ACCESS accessible-for-notify
    STATUS current
    DESCRIPTION
        "Parameter 'interface' in event IPX.100"
    ::= { ipxEventObjects100 3 }

ipxEventObjects101 OBJECT-IDENTITY
    STATUS current
    DESCRIPTION
        "Event IPX.101
        A RIP routing information entry for the given IPX network number
        has been DROPPED by the RIP filter on the given interface in the stated
        filtering direction, which is either inbound or outbound."
    ::= { ipxEventsGroup 101 }

ipx101_iodir OBJECT-TYPE
    SYNTAX DisplayString
    MAX-ACCESS accessible-for-notify
    STATUS current
    DESCRIPTION
        "Parameter 'iodir' in event IPX.101"
    ::= { ipxEventObjects101 1 }

ipx101_ipx_network OBJECT-TYPE
    SYNTAX Integer32
    MAX-ACCESS accessible-for-notify
    STATUS current
    DESCRIPTION
        "Parameter 'ipx_network' in event IPX.101"
    ::= { ipxEventObjects101 2 }

ipx101_interface OBJECT-TYPE
    SYNTAX DisplayString
    MAX-ACCESS accessible-for-notify
    STATUS current
    DESCRIPTION
        "Parameter 'interface' in event IPX.101"
    ::= { ipxEventObjects101 3 }

ipxEventObjects102 OBJECT-IDENTITY
    STATUS current
    DESCRIPTION
        "Event IPX.102
        A SAP routing information entry has successfully PASSED through the
        SAP filter on the given interface in the stated filtering direction,
        which is either inbound or outbound."
    ::= { ipxEventsGroup 102 }

ipx102_iodir OBJECT-TYPE
    SYNTAX DisplayString
    MAX-ACCESS accessible-for-notify
    STATUS current
    DESCRIPTION
        "Parameter 'iodir' in event IPX.102"
    ::= { ipxEventObjects102 1 }

ipx102_service_type OBJECT-TYPE
    SYNTAX Integer32
    MAX-ACCESS accessible-for-notify
    STATUS current
    DESCRIPTION
        "Parameter 'service_type' in event IPX.102"
    ::= { ipxEventObjects102 2 }

ipx102_service_name OBJECT-TYPE
    SYNTAX DisplayString
    MAX-ACCESS accessible-for-notify
    STATUS current
    DESCRIPTION
        "Parameter 'service_name' in event IPX.102"
    ::= { ipxEventObjects102 3 }

ipx102_service_hops OBJECT-TYPE
    SYNTAX Integer32
    MAX-ACCESS accessible-for-notify
    STATUS current
    DESCRIPTION
        "Parameter 'service_hops' in event IPX.102"
    ::= { ipxEventObjects102 4 }

ipx102_interface OBJECT-TYPE
    SYNTAX DisplayString
    MAX-ACCESS accessible-for-notify
    STATUS current
    DESCRIPTION
        "Parameter 'interface' in event IPX.102"
    ::= { ipxEventObjects102 5 }

ipxEventObjects103 OBJECT-IDENTITY
    STATUS current
    DESCRIPTION
        "Event IPX.103
        A SAP routing information entry has been DROPPED by the SAP filter
        on the given interface in the stated filtering direction, which is
        either inbound or outbound."
    ::= { ipxEventsGroup 103 }

ipx103_iodir OBJECT-TYPE
    SYNTAX DisplayString
    MAX-ACCESS accessible-for-notify
    STATUS current
    DESCRIPTION
        "Parameter 'iodir' in event IPX.103"
    ::= { ipxEventObjects103 1 }

ipx103_service_type OBJECT-TYPE
    SYNTAX Integer32
    MAX-ACCESS accessible-for-notify
    STATUS current
    DESCRIPTION
        "Parameter 'service_type' in event IPX.103"
    ::= { ipxEventObjects103 2 }

ipx103_service_name OBJECT-TYPE
    SYNTAX DisplayString
    MAX-ACCESS accessible-for-notify
    STATUS current
    DESCRIPTION
        "Parameter 'service_name' in event IPX.103"
    ::= { ipxEventObjects103 3 }

ipx103_service_hops OBJECT-TYPE
    SYNTAX Integer32
    MAX-ACCESS accessible-for-notify
    STATUS current
    DESCRIPTION
        "Parameter 'service_hops' in event IPX.103"
    ::= { ipxEventObjects103 4 }

ipx103_interface OBJECT-TYPE
    SYNTAX DisplayString
    MAX-ACCESS accessible-for-notify
    STATUS current
    DESCRIPTION
        "Parameter 'interface' in event IPX.103"
    ::= { ipxEventObjects103 5 }

ipxEventObjects104 OBJECT-IDENTITY
    STATUS current
    DESCRIPTION
        "Event IPX.104
        An IPX packet has PASSED through the IPX filter on the given interface
        in the stated filtering direction, which is either inbound or outbound."
    ::= { ipxEventsGroup 104 }

ipx104_iodir OBJECT-TYPE
    SYNTAX DisplayString
    MAX-ACCESS accessible-for-notify
    STATUS current
    DESCRIPTION
        "Parameter 'iodir' in event IPX.104"
    ::= { ipxEventObjects104 1 }

ipx104_packet_type OBJECT-TYPE
    SYNTAX Integer32
    MAX-ACCESS accessible-for-notify
    STATUS current
    DESCRIPTION
        "Parameter 'packet_type' in event IPX.104"
    ::= { ipxEventObjects104 2 }

ipx104_source_net OBJECT-TYPE
    SYNTAX Integer32
    MAX-ACCESS accessible-for-notify
    STATUS current
    DESCRIPTION
        "Parameter 'source_net' in event IPX.104"
    ::= { ipxEventObjects104 3 }

ipx104_source_node OBJECT-TYPE
    SYNTAX DisplayString
    MAX-ACCESS accessible-for-notify
    STATUS current
    DESCRIPTION
        "Parameter 'source_node' in event IPX.104"
    ::= { ipxEventObjects104 4 }

ipx104_source_socket OBJECT-TYPE
    SYNTAX Integer32
    MAX-ACCESS accessible-for-notify
    STATUS current
    DESCRIPTION
        "Parameter 'source_socket' in event IPX.104"
    ::= { ipxEventObjects104 5 }

ipx104_dest_net OBJECT-TYPE
    SYNTAX Integer32
    MAX-ACCESS accessible-for-notify
    STATUS current
    DESCRIPTION
        "Parameter 'dest_net' in event IPX.104"
    ::= { ipxEventObjects104 6 }

ipx104_dest_node OBJECT-TYPE
    SYNTAX DisplayString
    MAX-ACCESS accessible-for-notify
    STATUS current
    DESCRIPTION
        "Parameter 'dest_node' in event IPX.104"
    ::= { ipxEventObjects104 7 }

ipx104_dest_socket OBJECT-TYPE
    SYNTAX Integer32
    MAX-ACCESS accessible-for-notify
    STATUS current
    DESCRIPTION
        "Parameter 'dest_socket' in event IPX.104"
    ::= { ipxEventObjects104 8 }

ipx104_service_hops OBJECT-TYPE
    SYNTAX Integer32
    MAX-ACCESS accessible-for-notify
    STATUS current
    DESCRIPTION
        "Parameter 'service_hops' in event IPX.104"
    ::= { ipxEventObjects104 9 }

ipx104_interface OBJECT-TYPE
    SYNTAX DisplayString
    MAX-ACCESS accessible-for-notify
    STATUS current
    DESCRIPTION
        "Parameter 'interface' in event IPX.104"
    ::= { ipxEventObjects104 10 }

ipxEventObjects105 OBJECT-IDENTITY
    STATUS current
    DESCRIPTION
        "Event IPX.105
        An IPX packet has been DROPPED by the IPX filter on the given interface
        in the stated filtering direction, which is either inbound or outbound."
    ::= { ipxEventsGroup 105 }

ipx105_iodir OBJECT-TYPE
    SYNTAX DisplayString
    MAX-ACCESS accessible-for-notify
    STATUS current
    DESCRIPTION
        "Parameter 'iodir' in event IPX.105"
    ::= { ipxEventObjects105 1 }

ipx105_packet_type OBJECT-TYPE
    SYNTAX Integer32
    MAX-ACCESS accessible-for-notify
    STATUS current
    DESCRIPTION
        "Parameter 'packet_type' in event IPX.105"
    ::= { ipxEventObjects105 2 }

ipx105_source_net OBJECT-TYPE
    SYNTAX Integer32
    MAX-ACCESS accessible-for-notify
    STATUS current
    DESCRIPTION
        "Parameter 'source_net' in event IPX.105"
    ::= { ipxEventObjects105 3 }

ipx105_source_node OBJECT-TYPE
    SYNTAX DisplayString
    MAX-ACCESS accessible-for-notify
    STATUS current
    DESCRIPTION
        "Parameter 'source_node' in event IPX.105"
    ::= { ipxEventObjects105 4 }

ipx105_source_socket OBJECT-TYPE
    SYNTAX Integer32
    MAX-ACCESS accessible-for-notify
    STATUS current
    DESCRIPTION
        "Parameter 'source_socket' in event IPX.105"
    ::= { ipxEventObjects105 5 }

ipx105_dest_net OBJECT-TYPE
    SYNTAX Integer32
    MAX-ACCESS accessible-for-notify
    STATUS current
    DESCRIPTION
        "Parameter 'dest_net' in event IPX.105"
    ::= { ipxEventObjects105 6 }

ipx105_dest_node OBJECT-TYPE
    SYNTAX DisplayString
    MAX-ACCESS accessible-for-notify
    STATUS current
    DESCRIPTION
        "Parameter 'dest_node' in event IPX.105"
    ::= { ipxEventObjects105 7 }

ipx105_dest_socket OBJECT-TYPE
    SYNTAX Integer32
    MAX-ACCESS accessible-for-notify
    STATUS current
    DESCRIPTION
        "Parameter 'dest_socket' in event IPX.105"
    ::= { ipxEventObjects105 8 }

ipx105_service_hops OBJECT-TYPE
    SYNTAX Integer32
    MAX-ACCESS accessible-for-notify
    STATUS current
    DESCRIPTION
        "Parameter 'service_hops' in event IPX.105"
    ::= { ipxEventObjects105 9 }

ipx105_interface OBJECT-TYPE
    SYNTAX DisplayString
    MAX-ACCESS accessible-for-notify
    STATUS current
    DESCRIPTION
        "Parameter 'interface' in event IPX.105"
    ::= { ipxEventObjects105 10 }


ipxNotification1 NOTIFICATION-TYPE
    OBJECTS { 
              ipx1_source_net, 
              ipx1_source_node,
              ipx1_dest_net,
              ipx1_dest_node 
            }
    STATUS current
    DESCRIPTION
        "Notification of Event IPX.1

        Message: 'Packet from $1/$2 for $3/$4 ignored'

        Parameters list:
              $1: ipx1_source_net
              $2: ipx1_source_node
              $3: ipx1_dest_net
              $4: ipx1_dest_node

        An IPX packet arrived on a network and the IPX forwarder is
        not installed."
    ::= { ipxNotificationsPrefix 1 }

ipxNotification2 NOTIFICATION-TYPE
    OBJECTS { 
              ipx2_source_net, 
              ipx2_source_node,
              ipx2_dest_net,
              ipx2_dest_node,
              ipx2_interface 
            }
    STATUS current
    DESCRIPTION
        "Notification of Event IPX.2

        Message: 'Queue overflow, $1/$2 -> $3/$4, interface $5'

        Parameters list:
              $1: ipx2_source_net
              $2: ipx2_source_node
              $3: ipx2_dest_net
              $4: ipx2_dest_node
              $5: ipx2_interface

        IPX forwarder input queue has overflowed."
    ::= { ipxNotificationsPrefix 2 }

ipxNotification3 NOTIFICATION-TYPE
    OBJECTS { 
              ipx3_source_net, 
              ipx3_source_node 
            }
    STATUS current
    DESCRIPTION
        "Notification of Event IPX.3

        Message: 'Bad host checksum from $1/$2'

        Parameters list:
              $1: ipx3_source_net
              $2: ipx3_source_node

        This message is generated when a packet arrives for this host with
        an incorrect checksum."
    ::= { ipxNotificationsPrefix 3 }

ipxNotification4 NOTIFICATION-TYPE
    OBJECTS { 
              ipx4_error_type, 
              ipx4_source_net,
              ipx4_source_node 
            }
    STATUS current
    DESCRIPTION
        "Notification of Event IPX.4

        Message: 'Error packet, errno $1, received from $2/$3'

        Parameters list:
              $1: ipx4_error_type
              $2: ipx4_source_net
              $3: ipx4_source_node

        This message is generated when an error packet is received."
    ::= { ipxNotificationsPrefix 4 }

ipxNotification5 NOTIFICATION-TYPE
    OBJECTS { 
              ipx5_destination_socket, 
              ipx5_packet_type,
              ipx5_source_net,
              ipx5_source_node 
            }
    STATUS current
    DESCRIPTION
        "Notification of Event IPX.5

        Message: 'No handler for socket $1 type $2 from $3/$4'

        Parameters list:
              $1: ipx5_destination_socket
              $2: ipx5_packet_type
              $3: ipx5_source_net
              $4: ipx5_source_node

        A packet arrived for an unknown or unsupported socket or type.
        The packet was a broadcast packet."
    ::= { ipxNotificationsPrefix 5 }

ipxNotification6 NOTIFICATION-TYPE
    OBJECTS { 
              ipx6_destination_socket, 
              ipx6_packet_type,
              ipx6_source_net,
              ipx6_source_node 
            }
    STATUS current
    DESCRIPTION
        "Notification of Event IPX.6

        Message: 'No handler for socket $1 type $2 from $3/$4'

        Parameters list:
              $1: ipx6_destination_socket
              $2: ipx6_packet_type
              $3: ipx6_source_net
              $4: ipx6_source_node

        A packet arrived for an unknown or unsupported socket or type.
        The packet was addressed to the router."
    ::= { ipxNotificationsPrefix 6 }

ipxNotification7 NOTIFICATION-TYPE
    OBJECTS { 
              ipx7_interface 
            }
    STATUS current
    DESCRIPTION
        "Notification of Event IPX.7

        Message: 'no host address set for interface $1, not enabled'

        Parameters list:
              $1: ipx7_interface

        The forwarder was bringing up IPX on the specified serial line
        interface, but no host address was set so the interface was not enabled."
    ::= { ipxNotificationsPrefix 7 }

ipxNotification8 NOTIFICATION-TYPE
    OBJECTS { 
              ipx8_packet_type, 
              ipx8_source_net,
              ipx8_source_node 
            }
    STATUS current
    DESCRIPTION
        "Notification of Event IPX.8

        Message: 'SAP bad type $1 from $2/$3'

        Parameters list:
              $1: ipx8_packet_type
              $2: ipx8_source_net
              $3: ipx8_source_node

        This message is generated when a packet is received with a bad SAP type."
    ::= { ipxNotificationsPrefix 8 }

ipxNotification9 NOTIFICATION-TYPE
    OBJECTS { 
              ipx9_source_net, 
              ipx9_source_node 
            }
    STATUS current
    DESCRIPTION
        "Notification of Event IPX.9

        Message: 'SAP general reply from $1/$2'

        Parameters list:
              $1: ipx9_source_net
              $2: ipx9_source_node

        SAP has received a General Reply packet from the specified host.
        The data in the packet will be used to update the SAP database."
    ::= { ipxNotificationsPrefix 9 }

ipxNotification10 NOTIFICATION-TYPE
    OBJECTS { 
              ipx10_service_type, 
              ipx10_service_name 
            }
    STATUS current
    DESCRIPTION
        "Notification of Event IPX.10

        Message: 'SAP table overflow, discarded type $1 name [$2]'

        Parameters list:
              $1: ipx10_service_type
              $2: ipx10_service_name

        A new entry cannot be added to the SAP table because it is full.
        The new entry is discarded."
    ::= { ipxNotificationsPrefix 10 }

ipxNotification11 NOTIFICATION-TYPE
    OBJECTS { 
              ipx11_service_type, 
              ipx11_service_name,
              ipx11_new_net,
              ipx11_new_node 
            }
    STATUS current
    DESCRIPTION
        "Notification of Event IPX.11

        Message: 'SAP service type $1 name [$2] moved to $3/$4'

        Parameters list:
              $1: ipx11_service_type
              $2: ipx11_service_name
              $3: ipx11_new_net
              $4: ipx11_new_node

        A SAP General Reply was received with a different network/address pair
        than is presently in the SAP database."
    ::= { ipxNotificationsPrefix 11 }

ipxNotification12 NOTIFICATION-TYPE
    OBJECTS { 
              ipx12_service_type, 
              ipx12_service_name 
            }
    STATUS current
    DESCRIPTION
        "Notification of Event IPX.12

        Message: 'SAP deleted type $1 name [$2]'

        Parameters list:
              $1: ipx12_service_type
              $2: ipx12_service_name

        A SAP table entry has been declared dead. It will be advertised as
        unreachable for another 60 seconds, and then removed from the SAP table."
    ::= { ipxNotificationsPrefix 12 }

ipxNotification13 NOTIFICATION-TYPE
    OBJECTS { 
              ipx13_source_net, 
              ipx13_source_node,
              ipx13_length 
            }
    STATUS current
    DESCRIPTION
        "Notification of Event IPX.13

        Message: 'SAP bad length Nearest Service Query from $1/$2, len $3'

        Parameters list:
              $1: ipx13_source_net
              $2: ipx13_source_node
              $3: ipx13_length

        A SAP Nearest Service Query was received with an illegal length."
    ::= { ipxNotificationsPrefix 13 }

ipxNotification14 NOTIFICATION-TYPE
    OBJECTS { 
              ipx14_source_net, 
              ipx14_source_node 
            }
    STATUS current
    DESCRIPTION
        "Notification of Event IPX.14

        Message: 'SAP nearest query from $1/$2'

        Parameters list:
              $1: ipx14_source_net
              $2: ipx14_source_node

        A SAP Nearest Service Query was received from the specified node.
        It will be answered as appropriate."
    ::= { ipxNotificationsPrefix 14 }

ipxNotification15 NOTIFICATION-TYPE
    OBJECTS { 
              ipx15_source_net, 
              ipx15_source_node 
            }
    STATUS current
    DESCRIPTION
        "Notification of Event IPX.15

        Message: 'SAP general query from $1/$2'

        Parameters list:
              $1: ipx15_source_net
              $2: ipx15_source_node

        A SAP General Service Query was received from the specified node.
        It will be answered as appropriate."
    ::= { ipxNotificationsPrefix 15 }

ipxNotification16 NOTIFICATION-TYPE
    OBJECTS { 
              ipx16_interface 
            }
    STATUS current
    DESCRIPTION
        "Notification of Event IPX.16

        Message: 'SAP General Service Query sent, interface $1'

        Parameters list:
              $1: ipx16_interface

        A SAP General Service Query was sent on the specified network.
        One is sent on a network when it comes up."
    ::= { ipxNotificationsPrefix 16 }

ipxNotification17 NOTIFICATION-TYPE
    OBJECTS { 
              ipx17_interface, 
              ipx17_count 
            }
    STATUS current
    DESCRIPTION
        "Notification of Event IPX.17

        Message: 'No memory for SAP General Service Query or Reply, interface $1, $2 packets sent'

        Parameters list:
              $1: ipx17_interface
              $2: ipx17_count

        No buffer is available to send a SAP General Service Query or Reply
        packet. Since a General Service Reply can require multiple packets,
        the message notes how many packets the router sent on this network
        before they ran out."
    ::= { ipxNotificationsPrefix 17 }

ipxNotification18 NOTIFICATION-TYPE
    OBJECTS { 
              ipx18_interface, 
              ipx18_count 
            }
    STATUS current
    DESCRIPTION
        "Notification of Event IPX.18

        Message: 'SAP General Service Reply sent, interface $1, $2 packets'

        Parameters list:
              $1: ipx18_interface
              $2: ipx18_count

        The specified network just sent a SAP General Service Reply. It took
        the specified number of packets to send the complete SAP database."
    ::= { ipxNotificationsPrefix 18 }

ipxNotification19 NOTIFICATION-TYPE
    OBJECTS { 
              ipx19_source_net, 
              ipx19_source_node,
              ipx19_dest_net,
              ipx19_dest_node,
              ipx19_interface,
              ipx19_hop_count 
            }
    STATUS current
    DESCRIPTION
        "Notification of Event IPX.19

        Message: 'NETBIOS broadcast $1/$2 -> $3/$4, interface $5, $6 hops'

        Parameters list:
              $1: ipx19_source_net
              $2: ipx19_source_node
              $3: ipx19_dest_net
              $4: ipx19_dest_node
              $5: ipx19_interface
              $6: ipx19_hop_count

        The router received a NETBIOS emulation multinetwork broadcast packet
        for forwarding to other IPX networks. The IPX hop count indicates
        how many routers it has been through."
    ::= { ipxNotificationsPrefix 19 }

ipxNotification20 NOTIFICATION-TYPE
    OBJECTS { 
              ipx20_source_net, 
              ipx20_source_node,
              ipx20_interface 
            }
    STATUS current
    DESCRIPTION
        "Notification of Event IPX.20

        Message: 'NETBIOS too many hops from $1/$2 interface $3, ignored'

        Parameters list:
              $1: ipx20_source_net
              $2: ipx20_source_node
              $3: ipx20_interface

        A NETBIOS emulation broadcast packet has been through more than
        8 routers. It will be dropped."
    ::= { ipxNotificationsPrefix 20 }

ipxNotification21 NOTIFICATION-TYPE
    OBJECTS { 
              ipx21_source_net, 
              ipx21_source_node,
              ipx21_interface,
              ipx21_connected_network 
            }
    STATUS current
    DESCRIPTION
        "Notification of Event IPX.21

        Message: 'NETBIOS from $1/$2 interface $3, already on $4, ignored'

        Parameters list:
              $1: ipx21_source_net
              $2: ipx21_source_node
              $3: ipx21_interface
              $4: ipx21_connected_network

        This IPX NETBIOS emulation broadcast packet has already been on
        one of the directly attached networks. The router will not forward it
        since that would generate a duplicate."
    ::= { ipxNotificationsPrefix 21 }

ipxNotification22 NOTIFICATION-TYPE
    OBJECTS { 
              ipx22_source_net, 
              ipx22_source_node 
            }
    STATUS current
    DESCRIPTION
        "Notification of Event IPX.22

        Message: 'NETBIOS from $1/$2, no memory to copy'

        Parameters list:
              $1: ipx22_source_net
              $2: ipx22_source_node

        No memory available to make working copy of this NETBIOS emulation
        packet to send it out multiple interfaces."
    ::= { ipxNotificationsPrefix 22 }

ipxNotification23 NOTIFICATION-TYPE
    OBJECTS { 
              ipx23_source_net, 
              ipx23_source_node,
              ipx23_interface 
            }
    STATUS current
    DESCRIPTION
        "Notification of Event IPX.23

        Message: 'NETBIOS from $1/$2, non-broadcast interface $3 unsupported'

        Parameters list:
              $1: ipx23_source_net
              $2: ipx23_source_node
              $3: ipx23_interface

        Attempting to send NETBIOS emulation packet on network that does not
        support broadcast. The packet will not be sent on that network."
    ::= { ipxNotificationsPrefix 23 }

ipxNotification24 NOTIFICATION-TYPE
    OBJECTS { 
              ipx24_source_net, 
              ipx24_source_node,
              ipx24_interface 
            }
    STATUS current
    DESCRIPTION
        "Notification of Event IPX.24

        Message: 'NETBIOS from $1/$2, un-numbered interface $3 unsupported'

        Parameters list:
              $1: ipx24_source_net
              $2: ipx24_source_node
              $3: ipx24_interface

        Attempting to send NETBIOS emulation packet on a network with
        no network number. The packet will not be sent on that network."
    ::= { ipxNotificationsPrefix 24 }

ipxNotification25 NOTIFICATION-TYPE
    OBJECTS { 
              ipx25_source_net, 
              ipx25_source_node 
            }
    STATUS current
    DESCRIPTION
        "Notification of Event IPX.25

        Message: 'NETBIOS from $1/$2, no buffer to copy'

        Parameters list:
              $1: ipx25_source_net
              $2: ipx25_source_node

        No packet buffer available to copy this NETBIOS emulation broadcast
        packet into in order to send it on a network."
    ::= { ipxNotificationsPrefix 25 }

ipxNotification26 NOTIFICATION-TYPE
    OBJECTS { 
              ipx26_interface, 
              ipx26_reason_code 
            }
    STATUS current
    DESCRIPTION
        "Notification of Event IPX.26

        Message: 'NETBIOS send discarded, interface $1, reason $2'

        Parameters list:
              $1: ipx26_interface
              $2: ipx26_reason_code

        The router did not successfully transmit an outgoing NETBIOS emulation
        broadcast packet for the reason the error code indicates."
    ::= { ipxNotificationsPrefix 26 }

ipxNotification27 NOTIFICATION-TYPE
    OBJECTS { 
              ipx27_RIP_opcode, 
              ipx27_source_net,
              ipx27_source_node 
            }
    STATUS current
    DESCRIPTION
        "Notification of Event IPX.27

        Message: 'Bad RIP type $1 from $2/$3'

        Parameters list:
              $1: ipx27_RIP_opcode
              $2: ipx27_source_net
              $3: ipx27_source_node

        RIP packet received which was not a request or response."
    ::= { ipxNotificationsPrefix 27 }

ipxNotification28 NOTIFICATION-TYPE
    OBJECTS { 
              ipx28_source_net, 
              ipx28_source_node 
            }
    STATUS current
    DESCRIPTION
        "Notification of Event IPX.28

        Message: 'RIP response from $1/$2'

        Parameters list:
              $1: ipx28_source_net
              $2: ipx28_source_node

        This message is generated when a RIP response packet is received.
        It will be parsed, and the data incorporated into the routing table."
    ::= { ipxNotificationsPrefix 28 }

ipxNotification29 NOTIFICATION-TYPE
    OBJECTS { 
              ipx29_network, 
              ipx29_source_net,
              ipx29_source_node 
            }
    STATUS current
    DESCRIPTION
        "Notification of Event IPX.29

        Message: 'Bad network $1 in RIP from $2/$3'

        Parameters list:
              $1: ipx29_network
              $2: ipx29_source_net
              $3: ipx29_source_node

        A RIP response was received with an entry having a network number
        of 00000000 or FFFFFFFF. That entry will be ignored."
    ::= { ipxNotificationsPrefix 29 }

ipxNotification30 NOTIFICATION-TYPE
    OBJECTS { 
              ipx30_network 
            }
    STATUS current
    DESCRIPTION
        "Notification of Event IPX.30

        Message: 'Network routing table overflow, discarding $1'

        Parameters list:
              $1: ipx30_network

        This message is generated when a new network cannot be added to the
        routing table because it is full. The entry is discarded."
    ::= { ipxNotificationsPrefix 30 }

ipxNotification31 NOTIFICATION-TYPE
    OBJECTS { 
              ipx31_network, 
              ipx31_router_net,
              ipx31_router_node,
              ipx31_hop_count 
            }
    STATUS current
    DESCRIPTION
        "Notification of Event IPX.31

        Message: 'RIP route to network $1 now via $2/$3, $4 hops'

        Parameters list:
              $1: ipx31_network
              $2: ipx31_router_net
              $3: ipx31_router_node
              $4: ipx31_hop_count

        This message is generated when the route to a network changes.
        The specified router_net/router_node is now the best route to
        this network, with the noted number of hops."
    ::= { ipxNotificationsPrefix 31 }

ipxNotification32 NOTIFICATION-TYPE
    OBJECTS { 
              ipx32_network 
            }
    STATUS current
    DESCRIPTION
        "Notification of Event IPX.32

        Message: 'RIP route to $1 aged away'

        Parameters list:
              $1: ipx32_network

        This message is generated when a network is declared unreachable
        because no routing updates have been heard for it in 240 seconds.
        It will be advertised as unreachable for another 60 seconds, and then
        deleted from the routing table."
    ::= { ipxNotificationsPrefix 32 }

ipxNotification33 NOTIFICATION-TYPE
    OBJECTS { 
              ipx33_source_net, 
              ipx33_source_node 
            }
    STATUS current
    DESCRIPTION
        "Notification of Event IPX.33

        Message: 'Responding to RIP Request from $1/$2'

        Parameters list:
              $1: ipx33_source_net
              $2: ipx33_source_node

        This message is generated when a RIP Request packet is being parsed
        for a Reply."
    ::= { ipxNotificationsPrefix 33 }

ipxNotification34 NOTIFICATION-TYPE
    OBJECTS { 
              ipx34_source_net, 
              ipx34_source_node,
              ipx34_packet_length 
            }
    STATUS current
    DESCRIPTION
        "Notification of Event IPX.34

        Message: 'RIP Request from $1/$2 too short, len $3'

        Parameters list:
              $1: ipx34_source_net
              $2: ipx34_source_node
              $3: ipx34_packet_length

        A RIP request packet was received which is too short to contain one
        RIP entry. It will be discarded."
    ::= { ipxNotificationsPrefix 34 }

ipxNotification35 NOTIFICATION-TYPE
    OBJECTS { 
              ipx35_interface 
            }
    STATUS current
    DESCRIPTION
        "Notification of Event IPX.35

        Message: 'RIP Query sent, interface $1'

        Parameters list:
              $1: ipx35_interface

        A RIP Query has been sent on the specified interface. A Query is sent
        on each interface when it comes up."
    ::= { ipxNotificationsPrefix 35 }

ipxNotification36 NOTIFICATION-TYPE
    OBJECTS { 
              ipx36_interface, 
              ipx36_packet_count 
            }
    STATUS current
    DESCRIPTION
        "Notification of Event IPX.36

        Message: 'No memory for RIP packet, interface $1, $2 packets sent'

        Parameters list:
              $1: ipx36_interface
              $2: ipx36_packet_count

        No buffer is available to send a RIP Query or Response packet."
    ::= { ipxNotificationsPrefix 36 }

ipxNotification37 NOTIFICATION-TYPE
    OBJECTS { 
              ipx37_interface, 
              ipx37_packet_count 
            }
    STATUS current
    DESCRIPTION
        "Notification of Event IPX.37

        Message: 'RIP Response sent interface $1, $2 packets'

        Parameters list:
              $1: ipx37_interface
              $2: ipx37_packet_count

        The router sent a RIP Response. The router sent the response in
        the specified number of packets."
    ::= { ipxNotificationsPrefix 37 }

ipxNotification38 NOTIFICATION-TYPE
    OBJECTS { 
              ipx38_source_net, 
              ipx38_source_node,
              ipx38_dest_net,
              ipx38_dest_node 
            }
    STATUS current
    DESCRIPTION
        "Notification of Event IPX.38

        Message: 'Packet from $1/$2 for $3/$4 ignored'

        Parameters list:
              $1: ipx38_source_net
              $2: ipx38_source_node
              $3: ipx38_dest_net
              $4: ipx38_dest_node

        This message is generated when an IPX packet arrives on a network and
        the IPX forwarder is not active on that network."
    ::= { ipxNotificationsPrefix 38 }

ipxNotification39 NOTIFICATION-TYPE
    OBJECTS { 
              ipx39_interface, 
              ipx39_packet_count 
            }
    STATUS current
    DESCRIPTION
        "Notification of Event IPX.39

        Message: 'RIP delta Response sent interface $1, $2 packets'

        Parameters list:
              $1: ipx39_interface
              $2: ipx39_packet_count

        The router sent a RIP delta Response. This response includes only
        those networks whose data changed in the last update period. The router
        sent the response in the specified number of packets."
    ::= { ipxNotificationsPrefix 39 }

ipxNotification40 NOTIFICATION-TYPE
    OBJECTS { 
              ipx40_interface, 
              ipx40_reason_code 
            }
    STATUS current
    DESCRIPTION
        "Notification of Event IPX.40

        Message: 'RIP Response send discarded, interface $1, reason $2'

        Parameters list:
              $1: ipx40_interface
              $2: ipx40_reason_code

        The router did not successfully transmit an outgoing RIP response
        packet for the reason the error code indicates."
    ::= { ipxNotificationsPrefix 40 }

ipxNotification41 NOTIFICATION-TYPE
    OBJECTS { 
              ipx41_interface, 
              ipx41_reason_code 
            }
    STATUS current
    DESCRIPTION
        "Notification of Event IPX.41

        Message: 'RIP Query send discarded, interface $1, reason $2'

        Parameters list:
              $1: ipx41_interface
              $2: ipx41_reason_code

        The router did not successfully transmit an outgoing RIP query packet
        for the reason the error code indicates."
    ::= { ipxNotificationsPrefix 41 }

ipxNotification42 NOTIFICATION-TYPE
    OBJECTS { 
              ipx42_service_type, 
              ipx42_service_name,
              ipx42_source_net,
              ipx42_source_node,
              ipx42_interface 
            }
    STATUS current
    DESCRIPTION
        "Notification of Event IPX.42

        Message: 'SAP giving Nearest Server Reply of type $1 name [$2] to $3/$4, interface $5'

        Parameters list:
              $1: ipx42_service_type
              $2: ipx42_service_name
              $3: ipx42_source_net
              $4: ipx42_source_node
              $5: ipx42_interface

        A SAP Nearest Service Reply will be sent to the specified node.
        The service_type is the type of service, and the service_name is
        the name of the service."
    ::= { ipxNotificationsPrefix 42 }

ipxNotification43 NOTIFICATION-TYPE
    OBJECTS { 
              ipx43_service_type, 
              ipx43_source_net,
              ipx43_source_node,
              ipx43_interface 
            }
    STATUS current
    DESCRIPTION
        "Notification of Event IPX.43

        Message: 'SAP Nearest Query for service type $1 from $2/$3, interface $4'

        Parameters list:
              $1: ipx43_service_type
              $2: ipx43_source_net
              $3: ipx43_source_node
              $4: ipx43_interface

        A SAP Nearest Service Query was received from the specified node via
        the specified interface. If this router is the best route to
        the closest server of the specified service_type, this router
        will answer."
    ::= { ipxNotificationsPrefix 43 }

ipxNotification44 NOTIFICATION-TYPE
    OBJECTS { 
              ipx44_interface, 
              ipx44_count 
            }
    STATUS current
    DESCRIPTION
        "Notification of Event IPX.44

        Message: 'SAP delta General Service Reply sent, interface $1, $2 packets'

        Parameters list:
              $1: ipx44_interface
              $2: ipx44_count

        The router sent a SAP delta General Service Reply on the specified
        network. This Reply only includes those services whose data changed in
        the last update period. It took the specified number of packets to send
        the changes in SAP database."
    ::= { ipxNotificationsPrefix 44 }

ipxNotification45 NOTIFICATION-TYPE
    OBJECTS { 
              ipx45_service_type, 
              ipx45_service_name,
              ipx45_via_net,
              ipx45_via_node,
              ipx45_hop_count,
              ipx45_interface 
            }
    STATUS current
    DESCRIPTION
        "Notification of Event IPX.45

        Message: 'SAP new service route to service type $1 name [$2] via $3/$4, $5 hops, interface $6'

        Parameters list:
              $1: ipx45_service_type
              $2: ipx45_service_name
              $3: ipx45_via_net
              $4: ipx45_via_node
              $5: ipx45_hop_count
              $6: ipx45_interface

        This message is generated when a new service is added to the SAP table.
        The specified via_net/via_node is the route to this service, with
        the noted number of hops."
    ::= { ipxNotificationsPrefix 45 }

ipxNotification46 NOTIFICATION-TYPE
    OBJECTS { 
              ipx46_source_net, 
              ipx46_source_node,
              ipx46_interface 
            }
    STATUS current
    DESCRIPTION
        "Notification of Event IPX.46

        Message: 'SAP Nearest Query from $1/$2 ignored, interface $3'

        Parameters list:
              $1: ipx46_source_net
              $2: ipx46_source_node
              $3: ipx46_interface

        A SAP Nearest Service Query was received from the specified node via
        the specified interface, but processing of these packets has been
        administratively disabled on this interface. The query will be ignored."
    ::= { ipxNotificationsPrefix 46 }

ipxNotification47 NOTIFICATION-TYPE
    OBJECTS { 
              ipx47_interface, 
              ipx47_reason_code 
            }
    STATUS current
    DESCRIPTION
        "Notification of Event IPX.47

        Message: 'SAP Query send discarded, interface $1, reason $2'

        Parameters list:
              $1: ipx47_interface
              $2: ipx47_reason_code

        The router did not successfully transmit an outgoing SAP query packet
        for the reason the error code indicates."
    ::= { ipxNotificationsPrefix 47 }

ipxNotification48 NOTIFICATION-TYPE
    OBJECTS { 
              ipx48_interface, 
              ipx48_reason_code 
            }
    STATUS current
    DESCRIPTION
        "Notification of Event IPX.48

        Message: 'SAP Response send discarded, interface $1, reason $2'

        Parameters list:
              $1: ipx48_interface
              $2: ipx48_reason_code

        The router did not successfully transmit an outgoing RIP query packet
        for the reason the error code indicates."
    ::= { ipxNotificationsPrefix 48 }

ipxNotification49 NOTIFICATION-TYPE
    OBJECTS { 
              ipx49_service_type, 
              ipx49_source_net,
              ipx49_source_node,
              ipx49_interface 
            }
    STATUS current
    DESCRIPTION
        "Notification of Event IPX.49

        Message: 'SAP no server of type $1 for Query from $2/$3, interface $4'

        Parameters list:
              $1: ipx49_service_type
              $2: ipx49_source_net
              $3: ipx49_source_node
              $4: ipx49_interface

        A SAP Nearest Service Query was received from source_net/source_node,
        but the SAP database has no service registered of
        the desired service_type. No response will be sent."
    ::= { ipxNotificationsPrefix 49 }

ipxNotification50 NOTIFICATION-TYPE
    OBJECTS { 
              ipx50_service_type, 
              ipx50_service_name,
              ipx50_via_net,
              ipx50_via_node,
              ipx50_interface 
            }
    STATUS current
    DESCRIPTION
        "Notification of Event IPX.50

        Message: 'SAP dead service route to service type $1 name [$2] reported by $3/$4 has become unreachable, interface $5'

        Parameters list:
              $1: ipx50_service_type
              $2: ipx50_service_name
              $3: ipx50_via_net
              $4: ipx50_via_node
              $5: ipx50_interface

        This message is generated when a previously reachable service becomes
        unreachable, and is marked as Dead in the SAP table.
        The specified via_net/via_node is the server or router that announced
        the service as being unreachable."
    ::= { ipxNotificationsPrefix 50 }

ipxNotification51 NOTIFICATION-TYPE
    OBJECTS { 
              ipx51_network, 
              ipx51_router_net,
              ipx51_router_node 
            }
    STATUS current
    DESCRIPTION
        "Notification of Event IPX.51

        Message: 'RIP route died to network $1 from router $2/$3'

        Parameters list:
              $1: ipx51_network
              $2: ipx51_router_net
              $3: ipx51_router_node

        This message is generated when a previously reachable network becomes
        unreachable, and is marked as Dead in the RIP table.
        The specified router_net/router_node is the router that announced
        the network as being unreachable."
    ::= { ipxNotificationsPrefix 51 }

ipxNotification52 NOTIFICATION-TYPE
    OBJECTS { 
              ipx52_source_net, 
              ipx52_source_node,
              ipx52_local_net,
              ipx52_interface 
            }
    STATUS current
    DESCRIPTION
        "Notification of Event IPX.52

        Message: 'RIP response from wrong network $1/$2 not local network $3, interface $4'

        Parameters list:
              $1: ipx52_source_net
              $2: ipx52_source_node
              $3: ipx52_local_net
              $4: ipx52_interface

        This message is generated when a RIP response packet is received with
        a source network number that is not the same as the network number
        of this interface. The packet will be ignored."
    ::= { ipxNotificationsPrefix 52 }

ipxNotification53 NOTIFICATION-TYPE
    OBJECTS { 
              ipx53_source_net, 
              ipx53_source_node,
              ipx53_local_net,
              ipx53_interface 
            }
    STATUS current
    DESCRIPTION
        "Notification of Event IPX.53

        Message: 'SAP response from wrong network $1/$2 not local network $3, interface $4'

        Parameters list:
              $1: ipx53_source_net
              $2: ipx53_source_node
              $3: ipx53_local_net
              $4: ipx53_interface

        This message is generated when a SAP response packet is received with
        a source network number that is not the same as the network number
        of this interface. The packet will be ignored."
    ::= { ipxNotificationsPrefix 53 }

ipxNotification54 NOTIFICATION-TYPE
    OBJECTS { 
              ipx54_service_type, 
              ipx54_service_name,
              ipx54_via_net,
              ipx54_via_node,
              ipx54_hop_count,
              ipx54_interface 
            }
    STATUS current
    DESCRIPTION
        "Notification of Event IPX.54

        Message: 'SAP service route to service type $1 name [$2] is now via $3/$4, $5 hops, interface $6'

        Parameters list:
              $1: ipx54_service_type
              $2: ipx54_service_name
              $3: ipx54_via_net
              $4: ipx54_via_node
              $5: ipx54_hop_count
              $6: ipx54_interface

        This message is generated when the route to a service in the SAP table
        changes. The specified via_net/via_node is the new route to
        this service, with the noted number of hops."
    ::= { ipxNotificationsPrefix 54 }

ipxNotification55 NOTIFICATION-TYPE
    OBJECTS { 
              ipx55_network, 
              ipx55_router_net,
              ipx55_router_node,
              ipx55_hop_count 
            }
    STATUS current
    DESCRIPTION
        "Notification of Event IPX.55

        Message: 'New RIP network number $1 via $2/$3, $4 hops'

        Parameters list:
              $1: ipx55_network
              $2: ipx55_router_net
              $3: ipx55_router_node
              $4: ipx55_hop_count

        This message is generated when a new network is added to
        the RIP routing table. The new network was advertised by
        router_net/router_node, which is now the route to this network, with
        the noted number of hops."
    ::= { ipxNotificationsPrefix 55 }

ipxNotification56 NOTIFICATION-TYPE
    OBJECTS { 
              ipx56_network 
            }
    STATUS current
    DESCRIPTION
        "Notification of Event IPX.56

        Message: 'RIP route to $1 garbage collected'

        Parameters list:
              $1: ipx56_network

        This message is generated when a network is removed from
        the RIP routing table because no routing updates have been heard for it
        in 300 seconds. This normally happens 60 seconds after
        an IPX.012 message on the same service."
    ::= { ipxNotificationsPrefix 56 }

ipxNotification57 NOTIFICATION-TYPE
    OBJECTS { 
              ipx57_service_type, 
              ipx57_service_name,
              ipx57_interface 
            }
    STATUS current
    DESCRIPTION
        "Notification of Event IPX.57

        Message: 'SAP deleted type $1 name [$2], interface $3 down'

        Parameters list:
              $1: ipx57_service_type
              $2: ipx57_service_name
              $3: ipx57_interface

        The specified network interface has gone down, and this SAP service
        having a first hop on that network will be placed in the dead state.
        It will be advertised as unreachable for another 60 seconds, and then
        removed from the SAP table. However, if there are alternate routes to
        the same service, they will be learned about within 60 seconds."
    ::= { ipxNotificationsPrefix 57 }

ipxNotification58 NOTIFICATION-TYPE
    OBJECTS { 
              ipx58_service_type, 
              ipx58_service_name 
            }
    STATUS current
    DESCRIPTION
        "Notification of Event IPX.58

        Message: 'SAP type $1 name [$2] garbage collected'

        Parameters list:
              $1: ipx58_service_type
              $2: ipx58_service_name

        This message is generated when a network is removed from
        the SAP routing table because no SAP responses have been heard for it
        in 300 seconds."
    ::= { ipxNotificationsPrefix 58 }

ipxNotification59 NOTIFICATION-TYPE
    OBJECTS { 
              ipx59_service_type, 
              ipx59_service_name,
              ipx59_service_net,
              ipx59_service_node,
              ipx59_via_net,
              ipx59_via_node,
              ipx59_interface 
            }
    STATUS current
    DESCRIPTION
        "Notification of Event IPX.59

        Message: 'SAP unreachable service type $1 name [$2] at $3/$4 from $5/$6, interface $7'

        Parameters list:
              $1: ipx59_service_type
              $2: ipx59_service_name
              $3: ipx59_service_net
              $4: ipx59_service_node
              $5: ipx59_via_net
              $6: ipx59_via_node
              $7: ipx59_interface

        This message is generated when an advertisement for a service is
        received, but that service is on an IPX network (service_net) that
        this router has no route to. This advertisement will be ignored."
    ::= { ipxNotificationsPrefix 59 }

ipxNotification60 NOTIFICATION-TYPE
    STATUS current
    DESCRIPTION
        "Notification of Event IPX.60

        Message: 'SAP periodic General Service Response starting'

        The SAP protocol is beginning the transmission of
        SAP General Service Response packets on all IPX interfaces. This happens
        approximately every 60 seconds. It will generally be followed
        by IPX.064 messages (if there are any services), followed by
        an IPX.061 message."
    ::= { ipxNotificationsPrefix 60 }

ipxNotification61 NOTIFICATION-TYPE
    OBJECTS { 
              ipx61_packet_count 
            }
    STATUS current
    DESCRIPTION
        "Notification of Event IPX.61

        Message: 'SAP periodic General Service Response completed, $1 packet'

        Parameters list:
              $1: ipx61_packet_count

        The SAP protocol has completed the transmission of the periodic
        SAP General Service Response packets on all IPX interfaces.
        In doing this, it attempted to send packet_count packets in total."
    ::= { ipxNotificationsPrefix 61 }

ipxNotification62 NOTIFICATION-TYPE
    OBJECTS { 
              ipx62_packet_number, 
              ipx62_interface 
            }
    STATUS current
    DESCRIPTION
        "Notification of Event IPX.62

        Message: 'No memory for SAP periodic General Service Response packet $1, delaying, interface $2'

        Parameters list:
              $1: ipx62_packet_number
              $2: ipx62_interface

        There was no packet buffer available to send one packet of
        the periodic SAP General Service Response. The response will stall for
        half a second, waiting for a buffer to become available.
        The packet_number is the count of this packet within the complete
        response, starting at 0."
    ::= { ipxNotificationsPrefix 62 }

ipxNotification63 NOTIFICATION-TYPE
    OBJECTS { 
              ipx63_interface, 
              ipx63_reason_code 
            }
    STATUS current
    DESCRIPTION
        "Notification of Event IPX.63

        Message: 'SAP periodic General Service Response send discarded, interface $1, reason $2'

        Parameters list:
              $1: ipx63_interface
              $2: ipx63_reason_code

        The router did not successfully transmit an outgoing SAP periodic
        General Service Response for the reason the error code indicates."
    ::= { ipxNotificationsPrefix 63 }

ipxNotification64 NOTIFICATION-TYPE
    OBJECTS { 
              ipx64_entry_count, 
              ipx64_interface 
            }
    STATUS current
    DESCRIPTION
        "Notification of Event IPX.64

        Message: 'SAP periodic General Service Reply sent, $1 entries, interface $2'

        Parameters list:
              $1: ipx64_entry_count
              $2: ipx64_interface

        A SAP periodic General Service Reply packet has just been sent on the
        specified network. There were entry_count services in this packet."
    ::= { ipxNotificationsPrefix 64 }

ipxNotification65 NOTIFICATION-TYPE
    STATUS current
    DESCRIPTION
        "Notification of Event IPX.65

        Message: 'routing cache cleared'

        The IPX routing cache has been cleared, probably as the result of
        a routing table change."
    ::= { ipxNotificationsPrefix 65 }

ipxNotification66 NOTIFICATION-TYPE
    STATUS current
    DESCRIPTION
        "Notification of Event IPX.66

        Message: 'routing cache garbage collecting...'

        The IPX routing cache is collecting nonsense data. This takes several
        passes, and is only done when the cache starts overflowing."
    ::= { ipxNotificationsPrefix 66 }

ipxNotification67 NOTIFICATION-TYPE
    OBJECTS { 
              ipx67_dest_net, 
              ipx67_dest_node 
            }
    STATUS current
    DESCRIPTION
        "Notification of Event IPX.67

        Message: 'routing cache entry for destination $1/$2 cleared'

        Parameters list:
              $1: ipx67_dest_net
              $2: ipx67_dest_node

        The IPX routing cache entry for the listed destination has been cleared."
    ::= { ipxNotificationsPrefix 67 }

ipxNotification68 NOTIFICATION-TYPE
    STATUS current
    DESCRIPTION
        "Notification of Event IPX.68

        Message: 'no memory left for IPX local network/node cache entries'

        The IPX routing local network/node cache needs memory before it can add
        a new local network and its table into the IPX cache."
    ::= { ipxNotificationsPrefix 68 }

ipxNotification69 NOTIFICATION-TYPE
    OBJECTS { 
              ipx69_protocol, 
              ipx69_destination_net 
            }
    STATUS current
    DESCRIPTION
        "Notification of Event IPX.69

        Message: '$1 Table overflow, destination $2'

        Parameters list:
              $1: ipx69_protocol
              $2: ipx69_destination_net

        This message is generated when a new alternate entry cannot be made
        to routing table because alternate entry space is already full."
    ::= { ipxNotificationsPrefix 69 }

ipxNotification70 NOTIFICATION-TYPE
    OBJECTS { 
              ipx70_destination_net 
            }
    STATUS current
    DESCRIPTION
        "Notification of Event IPX.70

        Message: 'route overflow, destination $1'

        Parameters list:
              $1: ipx70_destination_net

        This message is generated when a new alternate entry cannot be made
        to routing table because alternate entry space for a given route
        is already full."
    ::= { ipxNotificationsPrefix 70 }

ipxNotification71 NOTIFICATION-TYPE
    OBJECTS { 
              ipx71_encap_seen, 
              ipx71_encap_used,
              ipx71_interface 
            }
    STATUS current
    DESCRIPTION
        "Notification of Event IPX.71

        Message: 'dropped pkt with encaps $1 using $2 on interface $3'

        Parameters list:
              $1: ipx71_encap_seen
              $2: ipx71_encap_used
              $3: ipx71_interface

        This message is generated when an IPX packet is received with
        an encapsulation other than that which has been selected
        for this interface."
    ::= { ipxNotificationsPrefix 71 }

ipxNotification72 NOTIFICATION-TYPE
    OBJECTS { 
              ipx72_iw_pkttype, 
              ipx72_interface 
            }
    STATUS current
    DESCRIPTION
        "Notification of Event IPX.72

        Message: 'Error building IPXWAN $1 on interface $2'

        Parameters list:
              $1: ipx72_iw_pkttype
              $2: ipx72_interface

        An IPXWAN Response is built from a Request.
        An attempt has been made to build the response without a request."
    ::= { ipxNotificationsPrefix 72 }

ipxNotification73 NOTIFICATION-TYPE
    STATUS current
    DESCRIPTION
        "Notification of Event IPX.73

        Message: 'Router name and Node ID must be configured before IPXWAN can operate'

        The IPX configuration parameters Name and Node ID must be configured
        before IPXWAN can operate on any network."
    ::= { ipxNotificationsPrefix 73 }

ipxNotification74 NOTIFICATION-TYPE
    OBJECTS { 
              ipx74_interface 
            }
    STATUS current
    DESCRIPTION
        "Notification of Event IPX.74

        Message: 'IPXWAN can't operate on interface $1 because it's an unsupported type'

        Parameters list:
              $1: ipx74_interface

        IPXWAN has been configured to run on an unsupported interface type."
    ::= { ipxNotificationsPrefix 74 }

ipxNotification75 NOTIFICATION-TYPE
    OBJECTS { 
              ipx75_interface 
            }
    STATUS current
    DESCRIPTION
        "Notification of Event IPX.75

        Message: 'IPXWAN is configured but not enabled to run on interface $1'

        Parameters list:
              $1: ipx75_interface

        IPXWAN has been configured to run on the interface, but it has been
        disabled by the user."
    ::= { ipxNotificationsPrefix 75 }

ipxNotification76 NOTIFICATION-TYPE
    OBJECTS { 
              ipx76_iw_pkttype, 
              ipx76_interface 
            }
    STATUS current
    DESCRIPTION
        "Notification of Event IPX.76

        Message: 'IPXWAN $1 packet dropeed because it was received on an unsupported interface type, interface $2'

        Parameters list:
              $1: ipx76_iw_pkttype
              $2: ipx76_interface

        An IPXWAN packet was dropped because it was received on an unsupported
        interface type."
    ::= { ipxNotificationsPrefix 76 }

ipxNotification77 NOTIFICATION-TYPE
    OBJECTS { 
              ipx77_iw_pkttype, 
              ipx77_interface 
            }
    STATUS current
    DESCRIPTION
        "Notification of Event IPX.77

        Message: 'IPXWAN $1 packet dropped - it was received on interface $2 which is disabled for IPXWAN traffic'

        Parameters list:
              $1: ipx77_iw_pkttype
              $2: ipx77_interface

        An IPXWAN packet was dropped because it was received on an interface
        which is configured to be disabled for IPXWAN traffic."
    ::= { ipxNotificationsPrefix 77 }

ipxNotification78 NOTIFICATION-TYPE
    OBJECTS { 
              ipx78_iw_pkttype, 
              ipx78_interface 
            }
    STATUS current
    DESCRIPTION
        "Notification of Event IPX.78

        Message: 'IPXWAN $1 packet received on interface $2 was rejected due to the confidence ID check failing'

        Parameters list:
              $1: ipx78_iw_pkttype
              $2: ipx78_interface

        An IPXWAN packet was rejected because the confidence ID check failed."
    ::= { ipxNotificationsPrefix 78 }

ipxNotification79 NOTIFICATION-TYPE
    OBJECTS { 
              ipx79_iw_pkttype, 
              ipx79_interface 
            }
    STATUS current
    DESCRIPTION
        "Notification of Event IPX.79

        Message: 'IPXWAN $1 packet received on interface $2 was rejected because its node id is identical to the local node id'

        Parameters list:
              $1: ipx79_iw_pkttype
              $2: ipx79_interface

        An IPXWAN packet was rejected because the node id reported in it
        was identical to the local node id."
    ::= { ipxNotificationsPrefix 79 }

ipxNotification80 NOTIFICATION-TYPE
    STATUS current
    DESCRIPTION
        "Notification of Event IPX.80

        Message: 'Not able to get a buffer to build an IPXWAN packet'

        An attempt to get a buffer to build an IPXWAN packet failed."
    ::= { ipxNotificationsPrefix 80 }

ipxNotification81 NOTIFICATION-TYPE
    OBJECTS { 
              ipx81_iw_pkttype, 
              ipx81_interface 
            }
    STATUS current
    DESCRIPTION
        "Notification of Event IPX.81

        Message: 'An attempt to send an IPXWAN $1 packet on interface $2 failed'

        Parameters list:
              $1: ipx81_iw_pkttype
              $2: ipx81_interface

        An attempt to send an IPXWAN packet failed."
    ::= { ipxNotificationsPrefix 81 }

ipxNotification82 NOTIFICATION-TYPE
    OBJECTS { 
              ipx82_iw_pkttype, 
              ipx82_interface 
            }
    STATUS current
    DESCRIPTION
        "Notification of Event IPX.82

        Message: 'IPXWAN $1 packet received on interface $2 was rejected due to a sequence number mismatch'

        Parameters list:
              $1: ipx82_iw_pkttype
              $2: ipx82_interface

        An IPXWAN packet was dropped due to a sequence number mismatch."
    ::= { ipxNotificationsPrefix 82 }

ipxNotification83 NOTIFICATION-TYPE
    OBJECTS { 
              ipx83_iw_pkttype, 
              ipx83_interface,
              ipx83_opt_type 
            }
    STATUS current
    DESCRIPTION
        "Notification of Event IPX.83

        Message: 'IPXWNA $1 rejected on interface $2 - $3 option not accepted'

        Parameters list:
              $1: ipx83_iw_pkttype
              $2: ipx83_interface
              $3: ipx83_opt_type

        The router rejected an IPXWAN packet because the other side of the link
        did not accept an option."
    ::= { ipxNotificationsPrefix 83 }

ipxNotification84 NOTIFICATION-TYPE
    OBJECTS { 
              ipx84_interface 
            }
    STATUS current
    DESCRIPTION
        "Notification of Event IPX.84

        Message: 'IPXWAN connection to be retried on interface $1'

        Parameters list:
              $1: ipx84_interface

        A previously timed-out IPXWAN connection is to be retried."
    ::= { ipxNotificationsPrefix 84 }

ipxNotification85 NOTIFICATION-TYPE
    OBJECTS { 
              ipx85_interface 
            }
    STATUS current
    DESCRIPTION
        "Notification of Event IPX.85

        Message: 'IPXWAN connection on interface $1 timed-out'

        Parameters list:
              $1: ipx85_interface

        An IPXWAN connection attempt timed-out."
    ::= { ipxNotificationsPrefix 85 }

ipxNotification86 NOTIFICATION-TYPE
    OBJECTS { 
              ipx86_iw_pkttype, 
              ipx86_interface 
            }
    STATUS current
    DESCRIPTION
        "Notification of Event IPX.86

        Message: 'IPXWAN $1 packet received on interface $2'

        Parameters list:
              $1: ipx86_iw_pkttype
              $2: ipx86_interface

        An IPXWAN packet was successfully received, accepted, and processed."
    ::= { ipxNotificationsPrefix 86 }

ipxNotification87 NOTIFICATION-TYPE
    OBJECTS { 
              ipx87_iw_pkttype, 
              ipx87_interface 
            }
    STATUS current
    DESCRIPTION
        "Notification of Event IPX.87

        Message: 'IPXWAN $1 packet sent on interface $2'

        Parameters list:
              $1: ipx87_iw_pkttype
              $2: ipx87_interface

        An IPXWAN packet was successfully sent on the interface."
    ::= { ipxNotificationsPrefix 87 }

ipxNotification88 NOTIFICATION-TYPE
    OBJECTS { 
              ipx88_interface 
            }
    STATUS current
    DESCRIPTION
        "Notification of Event IPX.88

        Message: 'IPXWAN connection has come up on interface $1'

        Parameters list:
              $1: ipx88_interface

        An IPXWAN connection is up on the given interface."
    ::= { ipxNotificationsPrefix 88 }

ipxNotification89 NOTIFICATION-TYPE
    OBJECTS { 
              ipx89_interface 
            }
    STATUS current
    DESCRIPTION
        "Notification of Event IPX.89

        Message: 'IPXWAN connection has gone down on interface $1'

        Parameters list:
              $1: ipx89_interface

        An IPXWAN connection has gone down on the given interface. This can
        happen if the link goes down, if the protocol goes down on the link
        (IPXCP goes down) or if a Timer Request packet is received."
    ::= { ipxNotificationsPrefix 89 }

ipxNotification90 NOTIFICATION-TYPE
    OBJECTS { 
              ipx90_service_type, 
              ipx90_source_net,
              ipx90_source_node,
              ipx90_interface 
            }
    STATUS current
    DESCRIPTION
        "Notification of Event IPX.90

        Message: 'SAP no server reply required for type $1 for Query from $2/$3, interface $4'

        Parameters list:
              $1: ipx90_service_type
              $2: ipx90_source_net
              $3: ipx90_source_node
              $4: ipx90_interface

        The router received a SAP Nearest Service Query from
        source_net/source_node. The SAP database indicates that a server exists
        on the same network as the client. The server will be allowed
        to respond for itself."
    ::= { ipxNotificationsPrefix 90 }

ipxNotification91 NOTIFICATION-TYPE
    OBJECTS { 
              ipx91_source_net, 
              ipx91_source_node,
              ipx91_interface 
            }
    STATUS current
    DESCRIPTION
        "Notification of Event IPX.91

        Message: 'short NETBIOS frame from $1/$2 interface $3, ignored'

        Parameters list:
              $1: ipx91_source_net
              $2: ipx91_source_node
              $3: ipx91_interface

        A NetBIOS type 20 packet must be at least 62 bytes in length.
        The forwarder drops the packet."
    ::= { ipxNotificationsPrefix 91 }

ipxNotification92 NOTIFICATION-TYPE
    OBJECTS { 
              ipx92_source_net, 
              ipx92_source_node,
              ipx92_source_socket,
              ipx92_dest_net,
              ipx92_dest_node,
              ipx92_dest_socket 
            }
    STATUS current
    DESCRIPTION
        "Notification of Event IPX.92

        Message: 'Add KeepAlive proxy connection $1/$2.$3 <-> $4/$5.$6'

        Parameters list:
              $1: ipx92_source_net
              $2: ipx92_source_node
              $3: ipx92_source_socket
              $4: ipx92_dest_net
              $5: ipx92_dest_node
              $6: ipx92_dest_socket

        A new pair of stations have been added to the proxy keepalive table."
    ::= { ipxNotificationsPrefix 92 }

ipxNotification93 NOTIFICATION-TYPE
    OBJECTS { 
              ipx93_source_net, 
              ipx93_source_node,
              ipx93_source_socket,
              ipx93_dest_net,
              ipx93_dest_node,
              ipx93_dest_socket 
            }
    STATUS current
    DESCRIPTION
        "Notification of Event IPX.93

        Message: 'Delete KeepAlive proxy connection $1/$2.$3 <-> $4/$5.$6'

        Parameters list:
              $1: ipx93_source_net
              $2: ipx93_source_node
              $3: ipx93_source_socket
              $4: ipx93_dest_net
              $5: ipx93_dest_node
              $6: ipx93_dest_socket

        A pair of stations have been removed from the proxy keepalive table."
    ::= { ipxNotificationsPrefix 93 }

ipxNotification94 NOTIFICATION-TYPE
    STATUS current
    DESCRIPTION
        "Notification of Event IPX.94

        Message: 'no memory for IPX KeepAlive Proxy connection table'

        The IPX Keepalive Proxy initialization routine was unable to allocate
        memory for its connection table. (IPX KeepAlive Proxy feature will not
        be enabled)."
    ::= { ipxNotificationsPrefix 94 }

ipxNotification95 NOTIFICATION-TYPE
    OBJECTS { 
              ipx95_source_net, 
              ipx95_source_node,
              ipx95_dest_net,
              ipx95_dest_node,
              ipx95_interface 
            }
    STATUS current
    DESCRIPTION
        "Notification of Event IPX.95

        Message: 'Serial packet dropped $1/$2 -> $3/$4, filtered interface $5'

        Parameters list:
              $1: ipx95_source_net
              $2: ipx95_source_node
              $3: ipx95_dest_net
              $4: ipx95_dest_node
              $5: ipx95_interface

        The router dropped a Serialization packet because the output network
        interface has IPX KeepAlive filtering enabled."
    ::= { ipxNotificationsPrefix 95 }

ipxNotification96 NOTIFICATION-TYPE
    STATUS current
    DESCRIPTION
        "Notification of Event IPX.96

        Message: 'No memory for proxy keepalive request or response'

        No buffer is available to send an IPX keepalive message."
    ::= { ipxNotificationsPrefix 96 }

ipxNotification97 NOTIFICATION-TYPE
    OBJECTS { 
              ipx97_type, 
              ipx97_source_net,
              ipx97_source_node,
              ipx97_source_socket,
              ipx97_dest_net,
              ipx97_dest_node,
              ipx97_dest_socket 
            }
    STATUS current
    DESCRIPTION
        "Notification of Event IPX.97

        Message: 'Sent proxy keepalive $1 $2/$3.$4 -> $5/$6.$7'

        Parameters list:
              $1: ipx97_type
              $2: ipx97_source_net
              $3: ipx97_source_node
              $4: ipx97_source_socket
              $5: ipx97_dest_net
              $6: ipx97_dest_node
              $7: ipx97_dest_socket

        The router sent a proxy keepalive packet."
    ::= { ipxNotificationsPrefix 97 }

ipxNotification98 NOTIFICATION-TYPE
    OBJECTS { 
              ipx98_source_net, 
              ipx98_source_node,
              ipx98_interface 
            }
    STATUS current
    DESCRIPTION
        "Notification of Event IPX.98

        Message: 'RIP Router filter PASS packet from $1/$2, interface $3'

        Parameters list:
              $1: ipx98_source_net
              $2: ipx98_source_node
              $3: ipx98_interface

        A RIP packet has successfully PASSED through the RIP Router filter
        on the given interface.
        The RIP Router filter is based upon the source_node in
        the IPX packet header, which is displayed by the message."
    ::= { ipxNotificationsPrefix 98 }

ipxNotification99 NOTIFICATION-TYPE
    OBJECTS { 
              ipx99_source_net, 
              ipx99_source_node,
              ipx99_interface 
            }
    STATUS current
    DESCRIPTION
        "Notification of Event IPX.99

        Message: 'RIP Router filter DROP packet from $1/$2, interface $3'

        Parameters list:
              $1: ipx99_source_net
              $2: ipx99_source_node
              $3: ipx99_interface

        A RIP packet has been DROPPED by the RIP Router filter on the
        given interface.
        The RIP Router filter is based upon the source_node in
        the IPX packet header, which is displayed by the message."
    ::= { ipxNotificationsPrefix 99 }

ipxNotification100 NOTIFICATION-TYPE
    OBJECTS { 
              ipx100_iodir, 
              ipx100_ipx_network,
              ipx100_interface 
            }
    STATUS current
    DESCRIPTION
        "Notification of Event IPX.100

        Message: 'RIP $1 filter PASS IPX network number $2, interface $3'

        Parameters list:
              $1: ipx100_iodir
              $2: ipx100_ipx_network
              $3: ipx100_interface

        A RIP routing information entry for the given IPX network number
        has successfully PASSED through the RIP filter on the given interface
        in the stated filtering direction, which is either inbound or outbound."
    ::= { ipxNotificationsPrefix 100 }

ipxNotification101 NOTIFICATION-TYPE
    OBJECTS { 
              ipx101_iodir, 
              ipx101_ipx_network,
              ipx101_interface 
            }
    STATUS current
    DESCRIPTION
        "Notification of Event IPX.101

        Message: 'RIP $1 filter DROP network $2, interface $3'

        Parameters list:
              $1: ipx101_iodir
              $2: ipx101_ipx_network
              $3: ipx101_interface

        A RIP routing information entry for the given IPX network number
        has been DROPPED by the RIP filter on the given interface in the stated
        filtering direction, which is either inbound or outbound."
    ::= { ipxNotificationsPrefix 101 }

ipxNotification102 NOTIFICATION-TYPE
    OBJECTS { 
              ipx102_iodir, 
              ipx102_service_type,
              ipx102_service_name,
              ipx102_service_hops,
              ipx102_interface 
            }
    STATUS current
    DESCRIPTION
        "Notification of Event IPX.102

        Message: 'SAP $1 filter PASS type $2 name [$3], hops $4, interface $5'

        Parameters list:
              $1: ipx102_iodir
              $2: ipx102_service_type
              $3: ipx102_service_name
              $4: ipx102_service_hops
              $5: ipx102_interface

        A SAP routing information entry has successfully PASSED through the
        SAP filter on the given interface in the stated filtering direction,
        which is either inbound or outbound."
    ::= { ipxNotificationsPrefix 102 }

ipxNotification103 NOTIFICATION-TYPE
    OBJECTS { 
              ipx103_iodir, 
              ipx103_service_type,
              ipx103_service_name,
              ipx103_service_hops,
              ipx103_interface 
            }
    STATUS current
    DESCRIPTION
        "Notification of Event IPX.103

        Message: 'SAP $1 filter DROP type $2 name [$3], hops $4, interface $5'

        Parameters list:
              $1: ipx103_iodir
              $2: ipx103_service_type
              $3: ipx103_service_name
              $4: ipx103_service_hops
              $5: ipx103_interface

        A SAP routing information entry has been DROPPED by the SAP filter
        on the given interface in the stated filtering direction, which is
        either inbound or outbound."
    ::= { ipxNotificationsPrefix 103 }

ipxNotification104 NOTIFICATION-TYPE
    OBJECTS { 
              ipx104_iodir, 
              ipx104_packet_type,
              ipx104_source_net,
              ipx104_source_node,
              ipx104_source_socket,
              ipx104_dest_net,
              ipx104_dest_node,
              ipx104_dest_socket,
              ipx104_service_hops,
              ipx104_interface 
            }
    STATUS current
    DESCRIPTION
        "Notification of Event IPX.104

        Message: 'IPX $1 filter PASS type $2, $3/$4.$5 -> $6/$7.$8, hops $9, interface $10'

        Parameters list:
              $1: ipx104_iodir
              $2: ipx104_packet_type
              $3: ipx104_source_net
              $4: ipx104_source_node
              $5: ipx104_source_socket
              $6: ipx104_dest_net
              $7: ipx104_dest_node
              $8: ipx104_dest_socket
              $9: ipx104_service_hops
              $10: ipx104_interface

        An IPX packet has PASSED through the IPX filter on the given interface
        in the stated filtering direction, which is either inbound or outbound."
    ::= { ipxNotificationsPrefix 104 }

ipxNotification105 NOTIFICATION-TYPE
    OBJECTS { 
              ipx105_iodir, 
              ipx105_packet_type,
              ipx105_source_net,
              ipx105_source_node,
              ipx105_source_socket,
              ipx105_dest_net,
              ipx105_dest_node,
              ipx105_dest_socket,
              ipx105_service_hops,
              ipx105_interface 
            }
    STATUS current
    DESCRIPTION
        "Notification of Event IPX.105

        Message: 'IPX $1 filter DROP type $2, $3/$4.$5 -> $6/$7.$8, hops $9, interface $10'

        Parameters list:
              $1: ipx105_iodir
              $2: ipx105_packet_type
              $3: ipx105_source_net
              $4: ipx105_source_node
              $5: ipx105_source_socket
              $6: ipx105_dest_net
              $7: ipx105_dest_node
              $8: ipx105_dest_socket
              $9: ipx105_service_hops
              $10: ipx105_interface

        An IPX packet has been DROPPED by the IPX filter on the given interface
        in the stated filtering direction, which is either inbound or outbound."
    ::= { ipxNotificationsPrefix 105 }


END
