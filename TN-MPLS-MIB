TN-MPLS-MIB DEFINITIONS ::= BEGIN
                                                                        
IMPORTS
        MODULE-IDENTITY, OBJECT-TYPE,
        NOTIFICATION-TYPE, 
        Unsigned32, IpAddress, Counter64,
        Counter32, Integer32, Gauge32                   FROM SNMPv2-SMI
 
        MODULE-COMPLIANCE, OBJECT-GROUP, 
        NOTIFICATION-GROUP                              FROM SNMPv2-CONF

        RowStatus, RowPointer,
        TruthValue, TimeStamp,
        TimeInterval, TestAndIncr,
        TEXTUAL-CONVENTION                              FROM SNMPv2-TC

--        InterfaceIndexOrZero                            FROM IF-MIB

--        InetAddressIPv6                                 FROM INET-ADDRESS-MIB

        MplsLabel, MplsLSPID                            FROM MPLS-LSR-MIB
--        mplsXCLspId, mplsInSegmentEntry,
--        mplsOutSegmentEntry                             

        mplsTunnelIndex, mplsTunnelInstance,
        mplsTunnelIngressLSRId, mplsTunnelARHopEntry,
        MplsTunnelIndex                                 FROM MPLS-TE-MIB

        TmnxAdminState, TmnxOperState, 
        TNamedItem, TNamedItemOrEmpty, 
        TmnxActionType, TmnxVRtrMplsLspID,
        TmnxRsvpDSTEClassType, TLNamedItemOrEmpty,       
        TmnxEnabledDisabled, TmnxMplsTpGlobalID,
        TmnxMplsTpNodeID                                FROM TN-TC-MIB
             
        tnSRMIBModules, tnSRObjs                        FROM TROPIC-GLOBAL-REG 
        
        vRtrID, vRtrIfIndex                             FROM TN-VRTR-MIB

        InetAddressType, InetAddress                    FROM INET-ADDRESS-MIB

        tnSysSwitchId                                   FROM TROPIC-SYSTEM-MIB
        ;

tnMplsMIBModule MODULE-IDENTITY
        LAST-UPDATED "201505290000Z"
        ORGANIZATION "Nokia"
        CONTACT-INFO
            "Nokia SROS Support
             Web: http://support.nokia.com"
        DESCRIPTION
        "This document is the SNMP MIB module to manage and provision the 
        MPLS extensions for the Nokia SROS device.
         
        Copyright 2003-2013 Nokia. All rights reserved.
        Reproduction of this document is authorized on the condition that
        the foregoing copyright notice is included.

        This SNMP MIB module (Specification) embodies Nokia's
        proprietary intellectual property.  Nokia retains 
        all title and ownership in the Specification, including any 
        revisions.

        Nokia grants all interested parties a non-exclusive 
        license to use and distribute an unmodified copy of this 
        Specification in connection with management of Nokia 
        products, and without fee, provided this copyright notice and 
        license appear on all copies.

        This Specification is supplied 'as is', and Nokia 
        makes no warranty, either express or implied, as to the use, 
        operation, condition, or performance of the Specification."
--
--  Revision History
--
        REVISION        "201509290000Z"
        DESCRIPTION     "Added support for vRtrMplsLspNameTable."

        REVISION        "201505290000Z"
        DESCRIPTION     "Updated the DEFVAL of vRtrMplsLspAdminState MIB
                         to outOfService"

        REVISION        "201504300000Z"
        DESCRIPTION     "Added support for MIBs in TN-MPLS-MIB"

        REVISION        "1102010000Z"
        DESCRIPTION     "Rev 9.0                1 Feb 2011 00:00
                         9.0 release of the TIMETRA-MPLS-MIB."

        REVISION        "0902280000Z"
        DESCRIPTION     "Rev 7.0                28 Feb 2009 00:00
                         7.0 release of the TIMETRA-MPLS-MIB."

        REVISION        "0807010000Z"
        DESCRIPTION     "Rev 6.1                01 Jul 2008 00:00
                         6.1 release of the TIMETRA-MPLS-MIB."

        REVISION        "0801010000Z"
        DESCRIPTION     "Rev 6.0                01 Jan 2008 00:00
                         6.0 release of the TIMETRA-MPLS-MIB."

        REVISION        "0701010000Z"
        DESCRIPTION     "Rev 5.0                01 Jan 2007 00:00
                         5.0 release of the TIMETRA-MPLS-MIB."

        REVISION        "0603230000Z"   
        DESCRIPTION     "Rev 4.0                23 Mar 2006 00:00
                         4.0 release of the TIMETRA-MPLS-MIB."

        REVISION        "0508310000Z"   
        DESCRIPTION     "Rev 3.0                31 Aug 2005 00:00
                         3.0 release of the TIMETRA-MPLS-MIB."

        REVISION        "0501240000Z"   
        DESCRIPTION     "Rev 2.1                24 Jan 2005 00:00
                         2.1 release of the TIMETRA-MPLS-MIB."

        REVISION        "0401150000Z"
        DESCRIPTION     "Rev 2.0                15 Jan 2004 00:00
                         2.0 release of the TIMETRA-MPLS-MIB."

        REVISION        "0308150000Z"
        DESCRIPTION     "Rev 1.2                15 Aug 2003 00:00
                         1.2 release of the TIMETRA-MPLS-MIB."

        REVISION        "0009070000Z"
        DESCRIPTION     "Rev 1.0                20 Jan 2003 00:00
                         1.0 Release of the TIMETRA-MPLS-MIB."

        REVISION        "0008140000Z"
        DESCRIPTION     "Rev 0.1                14 Aug 2000 00:00
                         Initial version of the TIMETRA-MPLS-MIB."

        ::= { tnSRMIBModules 6 }
        
tnMplsObjs            OBJECT IDENTIFIER ::= { tnSRObjs 6 }
-- tnMplsConformance     OBJECT IDENTIFIER ::= { tnSRConfs 6 }
-- tnMplsNotifyPrefix   OBJECT IDENTIFIER ::= { tnSRNotifyPrefix 6 }
--    tnMplsNotifications   OBJECT IDENTIFIER ::= { tnMplsNotifyPrefix 0 }

--%%%%%%%%%%%%%%%%%%%%%%%%%%%%%%%%%%%%%%%%%%%%%%%%%%%%%%%%%%%%%%%%%%%%%%
--
--  MPLS extensions
--


--  Textual Conventions

TmnxMplsLspFailCode ::= TEXTUAL-CONVENTION
    STATUS    current
    DESCRIPTION
        "TmnxMplsLspFailCode is an enumerated integer that defines the  
         reason for LSP Path and LSP Crossconnect failure."
    SYNTAX    INTEGER {
                  noError (0),
                  admissionControlError (1),
                  noRouteToDestination (2),
                  trafficControlSystemError (3),
                  routingError (4), 
                  noResourcesAvailable (5),
                  badNode (6),
                  routingLoop (7),
                  labelAllocationError (8),
                  badL3PID (9),
                  tunnelLocallyRepaired (10),
                  unknownObjectClass (11),
                  unknownCType (12),
                  noEgressMplsInterface (13),
                  noEgressRsvpInterface (14),
                  looseHopsInFRRLsp (15),
                  unknown (16),
                  retryExceeded (17),
                  noCspfRouteOwner (18),
                  noCspfRouteToDestination (19),
                  hopLimitExceeded (20),
                  looseHopsInManualBypassLsp (21),
                  emptyPathInManualBypassLsp (22),
                  lspFlowControlled (23),
                  srlgSecondaryNotDisjoint (24),
                  srlgPrimaryCspfDisabled (25),
                  srlgPrimaryPathDown (26),
                  localLinkMaintenance (27),
                  unexpectedCtObject (28),
                  unsupportedCt (29),
                  invalidCt (30),
                  invCtAndSetupPri (31),
                  invCtAndHoldPri (32),
                  invCtAndSetupAndHoldPri (33),
                  localNodeMaintenance (34),
                  softPreemption (35),
                  p2mpNotSupported (36),
                  badXro (37),
                  localNodeInXro (38),
                  routeBlockedByXro (39),
                  xroTooComplex (40),
                  rsvpNotSupported (41)
                  }

TmnxMplsLabelOwner ::= TEXTUAL-CONVENTION
    STATUS    current
    DESCRIPTION
        "TmnxMplsLabelOwner is an enumerated integer that specifies
        the module that owns a particular MPLS label."
    SYNTAX    INTEGER {       
                  none (0),
                  rsvp (1),
                  tldp (2),
                  ildp (3),
                  svcmgr (4),
                  bgp (5),
                  mirror (6),
                  static (7),
                  vprn (8)
              }  

TmnxMplsOperDownReasonCode ::= TEXTUAL-CONVENTION
    STATUS    current
    DESCRIPTION
        "TmnxMplsOperDownReasonCode is an enumerated integer that specifies 
         the reason that the MPLS instance is operationally down."
    SYNTAX    INTEGER {
                  operUp (0),             -- Operationally up
                  adminDown (1),          -- Administratively down
                  noResources (2),        -- No resources available
                  systemIpDown (3),       -- System IP interface is 
                                          -- operationally down
                  iomFailure (4),         -- Iom failure
                  clearDown (5)           -- Clear command in progress  
              } 

TmnxMplsMBBType ::= TEXTUAL-CONVENTION
    STATUS    current
    DESCRIPTION
        "TmnxMplsMBBType is an enumerated integer that specifies 
         the type of make-before-break (MBB)."
    SYNTAX    INTEGER {
                  none (0), --no MBB in progress or no last MBB
                  configChange (1),
                  timerBasedResignal (2),             
                  manualResignal (3),
                  globalRevert (4),
                  delayedRetry (5),
                  gracefulShutdown (6),
                  softPreemption (7),
                  pathChange (8),
                  autoBandwidth (9)
                 }           
                 
TmnxMplsP2mpInstFailCode ::= TEXTUAL-CONVENTION
    STATUS    current
    DESCRIPTION
        "TmnxMplsP2mpInstFailCode is an enumerated integer that defines the  
         reason for P2MP instance going down."
    SYNTAX    INTEGER {
                  noError (0),
                  noS2LOperational (1)
                 }                        

TmnxMplsRouterId ::= TEXTUAL-CONVENTION 
    DISPLAY-HINT "d" 
    STATUS      current 
    DESCRIPTION 
        "The value of TmnxMplsRouterId provides a 32-bit, unsigned integer 
         uniquely identifying the router in the Autonomous System. To ensure 
         uniqueness, this may default to the value of one of the router's 
         IPv4 host addresses if IPv4 is configured on the router." 
    SYNTAX      Unsigned32 (0..'FFFFFFFF'h)         

TmnxMplsLspAutoBWLastAdjCause ::= TEXTUAL-CONVENTION
    STATUS    current
    DESCRIPTION
        "TmnxMplsLspAutoBWLastAdjCause is an enumerated integer that specifies 
         cause of auto-bandwidth last adjustment."
    SYNTAX    INTEGER {
                  none (0),
                  manual (1),
                  normal (2),
                  overflow (3),             
                  vllCAC (4)
                 }   
  
TmnxMplsLspBgpRSVPLSPTunState ::= TEXTUAL-CONVENTION
    STATUS  current
    DESCRIPTION
        "TmnxMplsLspBgpRSVPLSPTunState is an enumerated integer that specifies 
         whether an RSVP LSP is allowed or blocked in its usage as a transport 
         LSP for BGP tunnel routes. 

         In 'include(1)' mode, an RSVP LSPs is allowed to be used as transport 
         LSP for BGP tunnel routes.

         In 'exclude(2)' mode, an RSVP LSP is not allowed to be used as a
         transport LSP for BGP tunnel routes."
    SYNTAX INTEGER {
                include (1),
                exclude (2)
            }
        
TmnxMplsLspAddrType ::= TEXTUAL-CONVENTION
    STATUS    current
    DESCRIPTION
        "TmnxMplsLspAddrType is an enumerated integer that specifies
        the address type for an MPLS LSP."
    SYNTAX    INTEGER {       
                  ipv4   (1),
                  nodeId (2)
              }  

--
--  The Virtual Router MPLS Labeled Switch Path (LSP) Table
--
vRtrMplsLspTable    OBJECT-TYPE
    SYNTAX      SEQUENCE OF VRtrMplsLspEntry
    MAX-ACCESS  not-accessible
    STATUS      current
    DESCRIPTION
        "The vRtrMplsLspTable has an entry for each Labeled Switch
         Path (LSP) configured for a virtual router in the system."
    ::= { tnMplsObjs 1 }

vRtrMplsLspEntry    OBJECT-TYPE
    SYNTAX      VRtrMplsLspEntry
    MAX-ACCESS  not-accessible
    STATUS      current
    DESCRIPTION
        "Each row entry represents a Labeled Switch Path (LSP) configured
         for a virtual router in the system.  Entries can be created and
         deleted via SNMP SET operations.  Setting RowStatus to 'active'
         requires vRtrMplsLspName to have been assigned a valid value."
    INDEX { tnSysSwitchId, vRtrID, vRtrMplsLspIndex }
    ::= { vRtrMplsLspTable 1 }

VRtrMplsLspEntry ::= SEQUENCE {
    vRtrMplsLspIndex                    TmnxVRtrMplsLspID,
    vRtrMplsLspRowStatus                RowStatus,
    vRtrMplsLspLastChange               TimeStamp,
    vRtrMplsLspName                     TLNamedItemOrEmpty,
    vRtrMplsLspAdminState               TmnxAdminState,
    vRtrMplsLspOperState                TmnxOperState,
    vRtrMplsLspFromAddr                 IpAddress,
    vRtrMplsLspToAddr                   IpAddress,
    vRtrMplsLspType                     INTEGER,
    vRtrMplsLspOutSegIndx               Integer32,
    vRtrMplsLspRetryTimer               Unsigned32,
    vRtrMplsLspRetryLimit               Unsigned32,
    vRtrMplsLspMetric                   Unsigned32,
    vRtrMplsLspDecrementTtl             TruthValue,
    vRtrMplsLspCspf                     TruthValue,
    vRtrMplsLspFastReroute              TruthValue,
    vRtrMplsLspFRHopLimit               Unsigned32,
    vRtrMplsLspFRBandwidth              Unsigned32,
    vRtrMplsLspClassOfService           TNamedItemOrEmpty,
    vRtrMplsLspSetupPriority            Unsigned32,
    vRtrMplsLspHoldPriority             Unsigned32,
    vRtrMplsLspRecord                   TruthValue,
    vRtrMplsLspPreference               Unsigned32,
    vRtrMplsLspBandwidth                Integer32,
    vRtrMplsLspBwProtect                TruthValue,
    vRtrMplsLspHopLimit                 Unsigned32,                
    vRtrMplsLspNegotiatedMTU            Unsigned32,
    vRtrMplsLspRsvpResvStyle            INTEGER,
    vRtrMplsLspRsvpAdspec               TruthValue,
    vRtrMplsLspFRMethod                 INTEGER,
    vRtrMplsLspFRNodeProtect            TruthValue,
    vRtrMplsLspAdminGroupInclude        Unsigned32,
    vRtrMplsLspAdminGroupExclude        Unsigned32,
    vRtrMplsLspAdaptive                 TruthValue,
    vRtrMplsLspInheritance              Unsigned32,
    vRtrMplsLspOptimizeTimer            Unsigned32,
    vRtrMplsLspOperFastReroute          TruthValue,
    vRtrMplsLspFRObject                 TruthValue,
    vRtrMplsLspHoldTimer                Unsigned32,
    vRtrMplsLspCspfTeMetricEnabled      TruthValue,
    vRtrMplsLspP2mpId                   Unsigned32,
    vRtrMplsLspClassType                TmnxRsvpDSTEClassType,
    vRtrMplsLspOperMetric               Unsigned32,
    vRtrMplsLspLdpOverRsvpInclude       TruthValue,
    vRtrMplsLspLeastFill                TruthValue,
    vRtrMplsLspVprnAutoBindInclude      TruthValue,
    vRtrMplsLspMainCTRetryLimit         Unsigned32,
    vRtrMplsLspIgpShortcut              TruthValue,
    vRtrMplsLspOriginTemplate           TNamedItemOrEmpty, 
    vRtrMplsLspAutoBandwidth            TruthValue,
    vRtrMplsLspCspfToFirstLoose         TruthValue,
    vRtrMplsLspPropAdminGroup           TruthValue,
    vRtrMplsLspBgpShortcut              TruthValue,
    vRtrMplsLspBgpTransportTunnel       TmnxMplsLspBgpRSVPLSPTunState,
    vRtrMplsLspSwitchStbyPath           TmnxActionType,
    vRtrMplsLspSwitchStbyPathIndex      MplsTunnelIndex,
    vRtrMplsLspSwitchStbyPathForce      TruthValue,
    vRtrMplsLspExcludeNodeAddrType      InetAddressType,
    vRtrMplsLspExcludeNodeAddr          InetAddress,
    vRtrMplsLspIgpShortcutLfaType       INTEGER,
    vRtrMplsLspToAddrType               TmnxMplsLspAddrType,
    vRtrMplsLspFromAddrType             TmnxMplsLspAddrType, 
    vRtrMplsLspToNodeId                 TmnxMplsTpNodeID, 
    vRtrMplsLspFromNodeId               TmnxMplsTpNodeID, 
    vRtrMplsLspDestGlobalId             TmnxMplsTpGlobalID, 
    vRtrMplsLspDestTunnelNum            Unsigned32
}

vRtrMplsLspIndex OBJECT-TYPE
    SYNTAX      TmnxVRtrMplsLspID
    MAX-ACCESS  accessible-for-notify
    STATUS      current
    DESCRIPTION
        "The unique value which identifies this Labeled Switch
         Path (LSP) for this virtual router in the Nokia 
         SROS system.  It is a unique value among entries with the 
         same value of vRtrID."
    ::= { vRtrMplsLspEntry 1 }

vRtrMplsLspRowStatus   OBJECT-TYPE
    SYNTAX      RowStatus
    MAX-ACCESS  read-create
    STATUS      current
    DESCRIPTION
        "The row status used for creation, deletion, or control
         of vRtrMplsLspTable entries.  Before the row can be
         placed into the 'active' state vRtrMplsLspName must
         have been assigned a valid value."
    ::= { vRtrMplsLspEntry 2 }

vRtrMplsLspLastChange       OBJECT-TYPE
    SYNTAX      TimeStamp
    MAX-ACCESS  read-only
    STATUS      current
    DESCRIPTION
        "The sysUpTime when this row was last modified."
    ::= { vRtrMplsLspEntry 3 }

vRtrMplsLspName     OBJECT-TYPE
    SYNTAX      TLNamedItemOrEmpty
    MAX-ACCESS  read-create
    STATUS      current
    DESCRIPTION
        "Administrative name for this Labeled Switch Path.
         The vRtrMplsLspName must be unique within a virtual
         router instance.

         When the value of the object vRtrMplsLspType is 'p2mpAuto', LSPs 
         are auto-created dynamically by the system using LSP template values 
         configured in the associated row entry of  vRtrMplsLspTemplateTable.
         For auto-created LSPs, vRtrMplsLspName can have a maximum of
         64 characters which consists of vRtrMplsLspTemplateName, vRtrID
         and MTTM(Multicast Tunnel Table Manager)Identifier.

         If vRtrMplsLspType is not 'p2mpAuto', vRtrMplsLspName can have a maximum 
         of 32 characters. "
    ::= { vRtrMplsLspEntry 4 }

vRtrMplsLspAdminState       OBJECT-TYPE
    SYNTAX      TmnxAdminState
    MAX-ACCESS  read-create
    STATUS      current
    DESCRIPTION
        "The desired administrative state for this LSP."
    DEFVAL { outOfService }
    ::= { vRtrMplsLspEntry 5 }

vRtrMplsLspOperState        OBJECT-TYPE
    SYNTAX      TmnxOperState
    MAX-ACCESS  read-only
    STATUS      current
    DESCRIPTION
        "The current operational state of this LSP."
    ::= { vRtrMplsLspEntry 6 }

vRtrMplsLspFromAddr OBJECT-TYPE
    SYNTAX      IpAddress
    MAX-ACCESS  read-create
    STATUS      current
    DESCRIPTION
        "Source IP address of this LSP.  If vRtrMplsLspFromAddr has not
         been explicitly set, the system IP address will be used."
    ::= { vRtrMplsLspEntry 7 }

vRtrMplsLspToAddr OBJECT-TYPE
    SYNTAX      IpAddress
    MAX-ACCESS  read-create
    STATUS      current
    DESCRIPTION
        "Destination IP address of this LSP.  This LSP will not be
         signaled until vRtrMplsLspToAddr is explicitly set."
    ::= { vRtrMplsLspEntry 8 }
       
vRtrMplsLspType     OBJECT-TYPE
    SYNTAX      INTEGER {
                    unknown    (1),
                    dynamic    (2),
                    static     (3),
                    bypassOnly (4),
                    p2mpLsp    (5),
                    p2mpAuto   (6),
                    mplsTp     (7)
                }
    MAX-ACCESS  read-create
    STATUS      current
    DESCRIPTION
        "The vRtrMplsLspType object is an enumerated value that indicates
         whether the label value is statically or dynamically assigned or
         whether the LSP will be used exclusively for bypass protection.
         The value 'p2mpLsp' will be used to indicate point to multipoint LSPs 
         used for multicast traffic.

         When the value of the vRtrMplsLspType is 'p2mpAuto', it specifies that
         the LSP is auto-created dynamically by the system and the row entry
         is dynamically created by the system  using LSP Template values 
         configured in the associated row entry of vRtrMplsLspTemplateTable.

         The value 'mplsTp' specifies that the LSP is an MPLS-TP Static LSP.
              
         A 'wrongValue' error is returned if an attempt is made to set
         an object in the row entry where the value of vRtrMplsLspType is 
         'p2mpAuto'."
    DEFVAL { dynamic }
    ::= { vRtrMplsLspEntry 9 }

vRtrMplsLspOutSegIndx   OBJECT-TYPE
    SYNTAX      Integer32 (0..2147483647)
    MAX-ACCESS  read-create
    STATUS      current
    DESCRIPTION
        "The vRtrMplsLspOutSegIndx is the index value of the entry in 
         the mplsOutSegmentTable associated with this vRtrMplsLspEntry
         when vRtrMplsLspType is 'static'.  If vRtrMplsLspType is
         'dynamic', the value of this object will be zero (0)."
    DEFVAL { 0 }
    ::= { vRtrMplsLspEntry 10 }
        
vRtrMplsLspRetryTimer   OBJECT-TYPE
    SYNTAX      Unsigned32 (1..600)
    UNITS       "seconds"
    MAX-ACCESS  read-create
    STATUS      current
    DESCRIPTION
        "The value of vRtrMplsLspRetryTimer specifies the time in seconds
         the software will wait before attempting the establish the
         failed LSP."
    DEFVAL { 30 }
    ::= { vRtrMplsLspEntry 11 }
        
vRtrMplsLspRetryLimit      OBJECT-TYPE
    SYNTAX      Unsigned32 (0..10000)
    MAX-ACCESS  read-create
    STATUS      current
    DESCRIPTION
        "The value of vRtrMplsLspRetryLimit specifies the number of
         attempts the software should make to reestablish a failed LSP
         before the LSP is disabled.  A value of 0 indicates that an
         infinite number of retry attempts should be made."
    DEFVAL { 0 }
    ::= { vRtrMplsLspEntry 12 }

vRtrMplsLspMetric       OBJECT-TYPE
    SYNTAX      Unsigned32 (0..65535)
    MAX-ACCESS  read-create
    STATUS      current
    DESCRIPTION
        "The value of vRtrMplsLspMetric specifies the metric for this
         LSP which is used to select an LSP among a set of LSPs which are
         destined to the same egress 7x50 router.  The LSP with the lowest
         metric will be selected.

         In LDP-over-RSVP, LDP performs a lookup in the Routing Table 
         Manager (RTM) which provides the next hop to the destination PE 
         and the advertising router (ABR or destination PE itself).  If the
         advertising router matches the targeted LDP peer, LDP then 
         performs a second lookup for the advertising router in the Tunnel 
         Table Manager (TTM). This lookup returns the best RSVP LSP to use
         to forward packets for an LDP FEC learned through the targeted 
         LDP session.  The lookup returns the LSP with the lowest metric.
         If multiple LSPs have the same metric, then the result of the 
         lookup will be to select the first one available in the TTM."
    DEFVAL { 0 }
    ::= { vRtrMplsLspEntry 13 }
        
vRtrMplsLspDecrementTtl OBJECT-TYPE
    SYNTAX      TruthValue
    MAX-ACCESS  read-create
    STATUS      current
    DESCRIPTION
        "When the value of vRtrMplsLspDecrementTtl is 'true', the ingress 
         ESR writes the TTL of the IP packet into the label and each 
         transit ESR decrements the TTL in the label.  At the egress ESR 
         the TTL value from the label is written into the IP packet.
         
         When the value of vRtrMplsLspDecrementTtl is 'false', the ingress
         ESR ignores the IP packet TTL and writes the value of 255 into the
         label; and the egress ESR does not write the label's TTL into the
         IP packet."
    DEFVAL { true }
    ::= { vRtrMplsLspEntry 14 }

vRtrMplsLspCspf         OBJECT-TYPE
    SYNTAX      TruthValue
    MAX-ACCESS  read-create
    STATUS      current
    DESCRIPTION
        "When the value of vRtrMplsLspCspf is 'true', CSPF computation
         for constrained-path LSP is enabled.  When the value of
         vRtrMplsLspCspf is 'false' CSPF computation is disabled."
    DEFVAL { false }
    ::= { vRtrMplsLspEntry 15 }
        
vRtrMplsLspFastReroute  OBJECT-TYPE
    SYNTAX      TruthValue
    MAX-ACCESS  read-create
    STATUS      current
    DESCRIPTION
        "When the value of vRtrMplsLspFastReroute is 'true', fast reroute
         is enabled.  A pre-computed detour LSP is created from each node
         in the primary path of this LSP.  In case of a failure of a link 
         or LSP between two nodes, traffic is immediately rerouted on the
         pre-computed detour LSP thus avoiding packet loss.  Each node
         along the primary path of the LSP tries to establish a detour LSP 
         as follows:  Each upstream node will setup a detour LSP that
         avoids only the immediate downstream node and merges back onto
         the actual path of the LSP as soon as possible.  The detour LSP
         may take one or more hops (upto the value of vRtrMplsLspFRHopLimit)
         before merging back onto the main LSP path.
         
         When the upstream node detects a downstream link or node failure,
         it immediately send traffic for that LSP on the detour path and
         at the same time signals back to the ingress ESR about the
         failure.
         
         Fast reroute applies only to the primary path of this LSP.
         No configuration is required on the transit hops of the LSP.
         The ingress ESR will signal all intermediate ESRs using RSVP
         to setup their detours.
         
         When the value of vRtrMplsLspFastReroute is 'false', fast
         rerouting is disabled."
    DEFVAL { false }
    ::= { vRtrMplsLspEntry 16 }
        
vRtrMplsLspFRHopLimit   OBJECT-TYPE
    SYNTAX      Unsigned32 (0..255)
    MAX-ACCESS  read-create
    STATUS      current
    DESCRIPTION
        "The value of vRtrMplsLspFRHopLimit specifies the total number
         of hops a detour LSP can take before merging back onto the
         main LSP path."
    DEFVAL { 16 }
    ::= { vRtrMplsLspEntry 17 }
        
vRtrMplsLspFRBandwidth  OBJECT-TYPE
    SYNTAX      Unsigned32
    UNITS       "mega-bits per second"
    MAX-ACCESS  read-create
    STATUS      current
    DESCRIPTION
        "The value of vRtrMplsLspFRBandwidth specified the amount of
         bandwidth in mega-bits per second (Mbps) to be reserved for the
         detour LSP. A value of zero (0) indicates that no bandwidth
         is reserved."
    DEFVAL { 0 }
    ::= { vRtrMplsLspEntry 18 }
          
vRtrMplsLspClassOfService   OBJECT-TYPE
    SYNTAX      TNamedItemOrEmpty
    MAX-ACCESS  read-create
    STATUS      current
    DESCRIPTION
        "The name of the class of service value to be assigned to all
         packets on the LSP is specified with vRtrMplsLspClassOfService.
         The EXP bits in the MPLS header are set based on the global
         mapping table that specified the mapping between the forwarding
         class and the EXP bits.  When class of service is specified,
         all packets will be marked with the same EXP bits that match
         the vRtrMplsLspClassOfService name in the mapping table.
         
         An empty string, ''H, specifies no class of service.  Packets
         are assigned EXP bits based on the same mapping table, however
         each packet is marked with EXP bits based on the forwarding
         class from which it is serviced.
         
         When the value of vRtrMplsLspPathCosSource is set to 'inherit',
         the value of vRtrMplsLspClassOfService is applied to that
         specific LSP/path."
    DEFVAL { ''H }
    ::= { vRtrMplsLspEntry 19 }
        
vRtrMplsLspSetupPriority    OBJECT-TYPE
    SYNTAX      Unsigned32 (0..7)
    MAX-ACCESS  read-create
    STATUS      current
    DESCRIPTION
        "The value of vRtrMplsLspSetupPriority specifies the setup priority
         to use when insufficient bandwidth is available to setup a LSP.
         The setup priority is compared against the hold priority of
         existing LSPs.  If the setup priority is higher than the hold
         priority of the established LSPs, this LSP may preempt the other
         LSPs.  A value of zero (0) is the highest priority and a value
         of seven (7) is the lowest priority.
         
         When the value of vRtrMplsLspPathSetupPriority is set to '-1',
         the value of vRtrMplsLspSetupPriority is applied to that specific
         LSP/path."
    DEFVAL { 7 }
    ::= { vRtrMplsLspEntry 20 }
        
vRtrMplsLspHoldPriority     OBJECT-TYPE
    SYNTAX      Unsigned32 (0..7)
    MAX-ACCESS  read-create
    STATUS      current
    DESCRIPTION
        "The value of vRtrMplsLspHoldPriority specifies the hold priority
         to use when insufficient bandwidth is available to setup a LSP.
         The setup priority is compared against the hold priority of
         existing LSPs.  If the setup priority is higher than the hold
         priority of the established LSPs, this LSP may preempt the other
         LSPs.  A value of zero (0) is the highest priority and a value
         of seven (7) is the lowest priority.
         
         When the value of vRtrMplsLspPathHoldPriority is set to '-1',
         the value of vRtrMplsLspHoldPriority is applied to that specific
         LSP/path."
    DEFVAL { 0 }
    ::= { vRtrMplsLspEntry 21 }

vRtrMplsLspRecord       OBJECT-TYPE
    SYNTAX      TruthValue
    MAX-ACCESS  read-create
    STATUS      current
    DESCRIPTION
        "When the value of vRtrMplsLspRecord is 'true', recording of all
         the hops that a LSP traverses is enabled.
         
         When the value of vRtrMplsLspRecord is 'false, recording of all
         the hops that a LSP traverses is disabled."
    DEFVAL { true }
    ::= { vRtrMplsLspEntry 22 }       

vRtrMplsLspPreference   OBJECT-TYPE
    SYNTAX      Unsigned32 (1..255)
    MAX-ACCESS  read-create
    STATUS      current
    DESCRIPTION
        "The value of vRtrMplsLspPreference specifies the preference for
         the LSP.  This value is used for load balancing between multiple
         LSPs that exist between the same ingress and egress routers.
         By default, traffic is load balanced among the LSPs, since all
         LSPs have the same preference.  To prefer one LSP over another,
         change the preference value for that LSP.  The LSP with the
         lowest preference is used."
    DEFVAL { 255 }
    ::= { vRtrMplsLspEntry 23 }

vRtrMplsLspBandwidth    OBJECT-TYPE
    SYNTAX      Integer32
    UNITS       "mega-bits per second"
    MAX-ACCESS  read-create
    STATUS      current
    DESCRIPTION
        "The value of vRtrMplsLspBandwidth specifies the amount of
         bandwidth in mega-bits per second (Mbps) to be reserved for the LSP.
         A value of zero (0) indicates that no bandwidth is reserved.
         
         When vRtrMplsLspPathBandwidth is set to -1, the value of
         vRtrMplsLspBandwidth is applied to that specific LSP/path."
    DEFVAL { 0 }
    ::= { vRtrMplsLspEntry 24 }
        
vRtrMplsLspBwProtect    OBJECT-TYPE
    SYNTAX      TruthValue
    MAX-ACCESS  read-create
    STATUS      current
    DESCRIPTION
        "When vRtrMplsLspBwProtect has a value of 'true', bandwidth
         protection is enabled on a LSP.  LSPs that reserve bandwidth
         will be used for EF services where customers need guaranteed
         bandwidth.  It is expected that multiple EF services will be
         assigned to a single LSP.  When bandwidth protection is
         enabled on an LSP, each time this LSP is used for a certain
         service the bandwidth allocated on that service is deducted
         from the bandwidth reserved for the LSP.  Once the bandwidth is
         exhausted on the LSP, the ESR will provide feedback to the
         provider indicating that this LSP has exhausted its resources."
    DEFVAL { false }
    ::= { vRtrMplsLspEntry 25 }
        
vRtrMplsLspHopLimit     OBJECT-TYPE
    SYNTAX      Unsigned32 (2..255)
    MAX-ACCESS  read-create
    STATUS      current
    DESCRIPTION
        "The value of vRtrMplsLspHopLimit specifies the maximum number
         of hops that a LSP will traverse including the ingress and
         egress ESRs.  A LSP will not be setup if the hop limit is
         exceeded.
         
         When the value of vRtrMplsLspPathHopLimit is set to zero (0),
         the value of vRtrMplsLspHopLimit is applied to that specific
         LSP/path."
    DEFVAL { 255 }
    ::= { vRtrMplsLspEntry 26 }

vRtrMplsLspNegotiatedMTU     OBJECT-TYPE
    SYNTAX      Unsigned32
    MAX-ACCESS  read-only
    STATUS      current
    DESCRIPTION
        "The value of vRtrMplsLspNegotiatedMTU specifies the size 
         for the Maximum transmission unit (MTU) that is negotiated
         during LSP establishment."
    DEFVAL { 0 }
    ::= { vRtrMplsLspEntry 27 }

vRtrMplsLspRsvpResvStyle    OBJECT-TYPE
    SYNTAX      INTEGER {
                    se (1),
                    ff (2)
                }
    MAX-ACCESS  read-create
    STATUS      current
    DESCRIPTION
            "The value of vRtrMplsLspRsvpResvStyle specifies the reservation 
             style for RSVP. The reservation style can be set to 'Shared- 
             Explicit' (se) or 'Fixed-Filter' (ff)."
    DEFVAL { se }
    ::= { vRtrMplsLspEntry 28 }

vRtrMplsLspRsvpAdspec   OBJECT-TYPE
    SYNTAX      TruthValue
    MAX-ACCESS  read-create
    STATUS      current
    DESCRIPTION
        "When the value of vRtrMplsLspRsvpAdspec is 'true', the ADSPEC
         object will be included in RSVP messages. 
         When the value of vRtrMplsLspRsvpAdspec is 'false', the ADSPEC
         object will not be included in RSVP messages."
    DEFVAL { false }
    ::= { vRtrMplsLspEntry 29 }

vRtrMplsLspFRMethod    OBJECT-TYPE
    SYNTAX      INTEGER {
                    oneToOneBackup(1),
                    facilityBackup(2)
                }
    MAX-ACCESS  read-create
    STATUS      current
    DESCRIPTION
            "The value of vRtrMplsLspFRMethod specifies the fast reroute 
             method used. 
             
             In the 'One-to-one Backup' method, a backup LSP is established 
             which will intersect the original LSP somewhere downstream
             of the point of link or node failure. For each LSP that is 
             backed up, a separate backup LSP is established.
             
             In the 'Facility Backup' method, instead of creating a separate
             LSP for every LSP that is to be backed up, a single LSP is 
             created which serves as a backup for a set of LSPs. Such an LSP
             tunnel is called a 'bypass tunnel'."
    DEFVAL { oneToOneBackup }
    ::= { vRtrMplsLspEntry 30 }

vRtrMplsLspFRNodeProtect   OBJECT-TYPE
    SYNTAX      TruthValue
    MAX-ACCESS  read-create
    STATUS      current
    DESCRIPTION
        "Setting the value of vRtrMplsLspFRNodeProtect to 'true' enables
         node protection i.e. protection against the failure of a node on
         the LSP. 

         Setting the value to 'false' disables node protection."
    DEFVAL { true }
    ::= { vRtrMplsLspEntry 31 }

vRtrMplsLspAdminGroupInclude   OBJECT-TYPE
    SYNTAX      Unsigned32
    MAX-ACCESS  read-create
    STATUS      current
    DESCRIPTION
        "The value of vRtrMplsLspAdminGroupInclude is a bit-map that
         specifies a list of admin groups that should be included when
         this LSP is setup. If bit 'n' is set, then the admin group 
         with value 'n' is included for this LSP. This implies that 
         each link that this LSP goes through must be associated with  
         at least one of the admin groups in the include list.

         By default, all admin groups are in the include list."
    DEFVAL { '00000000'H }
    ::= { vRtrMplsLspEntry 32 }

vRtrMplsLspAdminGroupExclude   OBJECT-TYPE
    SYNTAX      Unsigned32
    MAX-ACCESS  read-create
    STATUS      current
    DESCRIPTION
        "The value of vRtrMplsLspAdminGroupExclude is a bit-map that
         specifies a list of admin groups that should be excluded when
         this LSP is setup. If bit 'n' is set, then the admin group 
         with value 'n' is excluded for this LSP. This implies that 
         each link that this LSP goes through must not be associated
         with any of the admin groups in the exclude list.

         By default, no admin groups are in the exclude list."
    DEFVAL { '00000000'H }
    ::= { vRtrMplsLspEntry 33 }

vRtrMplsLspAdaptive   OBJECT-TYPE
    SYNTAX      TruthValue
    MAX-ACCESS  read-create
    STATUS      current
    DESCRIPTION
        "Setting the value of vRtrMplsLspAdaptive to 'true' enables
         make-before-break functionality for the LSP. When the attributes
         of an already established LSP are changed, either through manual 
         configuration or due to a change in network topology, 
         make-before-break functionality ensures that the resources of 
         the existing LSP will not be released until a new path (with the
         same LSP Id) has been established and traffic flowing over the 
         existing path is seamlessly transferred to the new path.
         
         Setting the value to 'false' disables make-before-break 
         functionality."
    DEFVAL { true }
    ::= { vRtrMplsLspEntry 34 }

vRtrMplsLspInheritance   OBJECT-TYPE
    SYNTAX      Unsigned32
    MAX-ACCESS  read-create
    STATUS      current
    DESCRIPTION
        "For each writable object in this row that can be configured to
         inherit its value from the corresponding object in the 
         vRtrMplsGeneralTable, there is bit within vRtrMplsLspInheritance
         that controls whether to inherit the operational value of the
         object or use the administratively set value. 

         Non mask bits will always have value of zero.

         This object is a bit-mask, with the following positions:

         vRtrMplsLspOptimizeTimer                0x1
         vRtrMplsLspFRObject                     0x2
         vRtrMplsLspHoldTimer                    0x4
         vRtrMplsLspDestGlobalId                 0x8
         vRtrMplsLspDestTunnelNum                0x10
         vRtrMplsLspFromNodeId                   0x20

         When the bit for an object is set to one, then the object's 
         administrative and operational value are whatever the DEFVAL 
         or most recently SET value is.
         
         When the bit for an object is set to zero, then the object's 
         administrative and operational value are inherited from the 
         corresponding object in vRtrMplsGeneralTable."
    DEFVAL { 0 } -- by default inherit everything from vRtrMplsGeneralTable
    ::= { vRtrMplsLspEntry 35 }

vRtrMplsLspOptimizeTimer   OBJECT-TYPE
    SYNTAX      Unsigned32 (0..65535)
    UNITS       "seconds"
    MAX-ACCESS  read-create
    STATUS      current
    DESCRIPTION
        "The value of vRtrMplsLspOptimizeTimer specifies the time, in 
         seconds, the software will wait before attempting to re-optimize
         the LSP.

         When CSPF is enabled, changes in the network topology may cause
         the existing path of a loose-hop LSP to become sub-optimal. Such
         LSPs can be re-optimized and re-routed through more optimal paths
         by recalculating the path for the LSP at periodic intervals. This
         interval is controlled by the optimize timer.
         
         A value of 0 indicates that optimization has been disabled.

         When the vRtrMplsLspOptimizeTimer bit in vRtrMplsLspInheritance
         is cleared (0), the value returned in the GET request is inherited 
         from vRtrMplsGeneralOptimizeTimer."
    DEFVAL { 0 }
    ::= { vRtrMplsLspEntry 36 }

vRtrMplsLspOperFastReroute  OBJECT-TYPE
    SYNTAX      TruthValue
    MAX-ACCESS  read-only
    STATUS      current
    DESCRIPTION
        "The value of vRtrMplsLspOperFastReroute specifies whether the
         operational LSP has fast reroute enabled or disabled. 

         When make-before-break functionality for the LSP is enabled and
         if the fast reroute setting is changed, the resources for the 
         existing LSP will not be released until a new path with the new 
         attribute settings has been established. While a new path is 
         being signaled, the administrative value and the operational 
         values of fast reroute setting for the LSP may differ. The value
         of vRtrMplsLspFastReroute specifies the setting used for the new
         LSP path trying to be established whereas the value of 
         vRtrMplsLspOperFastReroute specifies the setting for the existing 
         LSP path."
    ::= { vRtrMplsLspEntry 37 }

vRtrMplsLspFRObject  OBJECT-TYPE
    SYNTAX      TruthValue
    MAX-ACCESS  read-create
    STATUS      current
    DESCRIPTION
        "The value of vRtrMplsLspFRObject specifies whether fast reroute,
         for LSPs using 'Facility Backup', is signalled with or without
         the fast reroute object. The value of vRtrMplsLspFRObject is
         ignored if fast reroute is disabled for the LSP or if the LSP
         is using 'One-to-one Backup'.

         When the vRtrMplsLspFRObject bit in vRtrMplsLspInheritance is 
         cleared (0), the value returned in the GET request is inherited 
         from vRtrMplsGeneralFRObject."
    DEFVAL { true }
    ::= { vRtrMplsLspEntry 38 }

vRtrMplsLspHoldTimer  OBJECT-TYPE
    SYNTAX      Unsigned32 (0..10)
    UNITS       "seconds"
    MAX-ACCESS  read-only
    STATUS      current
    DESCRIPTION
        "The value of vRtrMplsLspHoldTimer specifies the time, in 
         seconds, for which the ingress node holds a bit before 
         programming its data plane and declaring the lsp up to  
         the service module. 
        
         The value of vRtrMplsLspHoldTimer is inherited from 
         the value of vRtrMplsGeneralHoldTimer."
    DEFVAL { 1 }
    ::= { vRtrMplsLspEntry 39 }     

vRtrMplsLspCspfTeMetricEnabled         OBJECT-TYPE
    SYNTAX      TruthValue
    MAX-ACCESS  read-create
    STATUS      current
    DESCRIPTION
        "The value of vRtrMplsLspCspfTeMetricEnabled specifies whether the TE 
         metric would be used for the purpose of the LSP path computation by CSPF.
         When the value of this object is 'false', the IGP metric is used to 
         compute the path of the LSP by CSPF."
    DEFVAL { false }
    ::= { vRtrMplsLspEntry 40 }

vRtrMplsLspP2mpId        OBJECT-TYPE
    SYNTAX      Unsigned32 (0|1..65535)
    MAX-ACCESS  read-create
    STATUS      current
    DESCRIPTION
        "The value of vRtrMplsLspP2mpId specifies a unique identifier known as 
        point to multipoint (P2MP) identifier (ID)."
    DEFVAL { 0 }
    ::= { vRtrMplsLspEntry 41 }    

vRtrMplsLspClassType        OBJECT-TYPE
    SYNTAX      TmnxRsvpDSTEClassType
    MAX-ACCESS  read-create
    STATUS      current
    DESCRIPTION
        "The value of vRtrMplsLspClassType specifies the class type (CT) 
         associated with this LSP."
    DEFVAL { 0  }
    ::= { vRtrMplsLspEntry 42 }      

vRtrMplsLspOperMetric        OBJECT-TYPE
    SYNTAX      Unsigned32
    MAX-ACCESS  read-only
    STATUS      current
    DESCRIPTION
        "The value of vRtrMplsLspOperMetric indicates the operational metric 
         for the LSP."
    ::= { vRtrMplsLspEntry 43 }    

vRtrMplsLspLdpOverRsvpInclude        OBJECT-TYPE
    SYNTAX      TruthValue
    MAX-ACCESS  read-create
    STATUS      current
    DESCRIPTION
        "The value of vRtrMplsLspLdpOverRsvpInclude specifies that this LSP can 
         be included by IGP to calculate its SPF tree.  The IGP (OSPF or ISIS) 
         will subsequently provide LDP with all ECMP IGP next-hops and tunnel 
         endpoints that it considers to be the lowest cost path to the 
         destination.  If an IGP calculation and an LDP over RSVP produce the 
         same cost then LDP will always prefer an LDP over RSVP tunnel over an 
         IGP route.

         By default, static and dynamic LSPs will be included when they are 
         created. The default value for p2mp and bypass-only LSPs will be 
         'false'."
    DEFVAL { true  }
    ::= { vRtrMplsLspEntry 44 }      

vRtrMplsLspLeastFill       OBJECT-TYPE
    SYNTAX      TruthValue
    MAX-ACCESS  read-create
    STATUS      current
    DESCRIPTION
        "The value of vRtrMplsLspLeastFill specifies whether the use of the 
         least-fill path selection method for the computation of the path of 
         this LSP is enabled.

         By default, the path of an LSP is randomly chosen among a set of equal 
         cost paths."
    DEFVAL { false  }
    ::= { vRtrMplsLspEntry 45 }       

vRtrMplsLspVprnAutoBindInclude        OBJECT-TYPE
    SYNTAX      TruthValue
    MAX-ACCESS  read-create
    STATUS      current
    DESCRIPTION
        "The value of vRtrMplsLspVprnAutoBindInclude specifies whether the LSP 
         can be used as part of the auto-bind feature for VPRN services. By 
         default a LSP is available for inclusion to be used for the auto-bind 
         feature.
         
         By default, static and dynamic LSPs will be included when they are 
         created.  The default value for p2mp and bypass-only LSPs will 
         be 'false'."
    DEFVAL { true  }
    ::= { vRtrMplsLspEntry 46 }      
   
vRtrMplsLspMainCTRetryLimit        OBJECT-TYPE
    SYNTAX      Unsigned32 (0..10000) 
    MAX-ACCESS  read-create
    STATUS      current
    DESCRIPTION
        "The value of vRtrMplsLspMainCTRetryLimit specifies the number of
         attempts the software should make before it can start using the backup
         class type."
    DEFVAL { 0 }
    ::= { vRtrMplsLspEntry 47 }      

vRtrMplsLspIgpShortcut        OBJECT-TYPE
    SYNTAX      TruthValue 
    MAX-ACCESS  read-create
    STATUS      current
    DESCRIPTION
        "The value of vRtrMplsLspIgpShortcut specifies whether to exclude or 
         include a RSVP LSP from being used as a shortcut while resolving IGP 
         routes.
         
         When the value of vRtrMplsLspIgpShortcut is set to 'true' the RSVP LSP 
         is used as a shortcut while resolving IGP routes. When the value of 
         vRtrMplsLspIgpShortcut is set to 'false' the RSVP LSP is not used as a 
         shortcut while resolving IGP routes."
    DEFVAL { true }
    ::= { vRtrMplsLspEntry 48 }

vRtrMplsLspOriginTemplate  OBJECT-TYPE
    SYNTAX       TNamedItemOrEmpty
    MAX-ACCESS   read-only
    STATUS       current
    DESCRIPTION
        "When the value of the vRtrMplsLspType is 'p2mpAuto', the value of 
         vRtrMplsLspOriginTemplate indicates the LSP Template which was used
         to create this LSP.
      
         For all other types of LSPs, the value of vRtrMplsLspOriginTemplate
         is an empty string."
    ::= { vRtrMplsLspEntry 49 }       

vRtrMplsLspAutoBandwidth  OBJECT-TYPE
    SYNTAX       TruthValue
    MAX-ACCESS   read-create
    STATUS       current
    DESCRIPTION
        "The value of the vRtrMplsLspAutoBandwidth specifies whether automatic 
         bandwidth adjustment has been enabled or disabled for this LSP.
         
         A value of 'true' specifies that automatic bandwidth adjustment has
         been enabled for this LSP and a value of 'false' specifies that 
         automatic bandwidth adjustment has been disabled for this LSP."
    DEFVAL { false }
    ::= { vRtrMplsLspEntry 50 }       

vRtrMplsLspCspfToFirstLoose   OBJECT-TYPE
    SYNTAX      TruthValue
    MAX-ACCESS  read-create
    STATUS      current
    DESCRIPTION
        "The value of the vRtrMplsLspCspfToFirstLoose specifies whether the 
         CSPF calculation till the first loose hop on ingress Label Edge Router
         (LER) is enabled or disabled for this Labeled Switched Path(LSP).
         
         By default, the value of vRtrMplsLspCspfToFirstLoose is 'false' which
         specifies that the CSPF calculation is done to the destination of LSP."
    DEFVAL { false }
    ::= { vRtrMplsLspEntry 51 }

vRtrMplsLspPropAdminGroup   OBJECT-TYPE
    SYNTAX      TruthValue
    MAX-ACCESS  read-create
    STATUS      current
    DESCRIPTION
        "The value of the vRtrMplsLspPropAdminGroup specifies whether the 
         propagation of session attribute object with resource affinity 
         (C-type 1) in PATH message is enabled.

         By default, the value of vRtrMplsLspPropAdminGroup is 'false' which
         specifies the session attribute object without resource affinity 
         (C-Type 7) is propagated in PATH message and the admin-groups are 
         ignored on Label Switched Router(LSR) while doing CSPF calculation."
    DEFVAL { false }
    ::= { vRtrMplsLspEntry 52 }

vRtrMplsLspBgpShortcut        OBJECT-TYPE
    SYNTAX      TruthValue 
    MAX-ACCESS  read-create
    STATUS      current
    DESCRIPTION
        "The value of vRtrMplsLspBgpShortcut specifies whether to exclude or 
         include a RSVP LSP from being used as a shortcut while resolving 
         BGP routes.
         
         When the value of vRtrMplsLspBgpShortcut is set to 'true' the RSVP LSP 
         is used as a shortcut while resolving BGP routes. When the value of 
         vRtrMplsLspBgpShortcut is set to 'false' the RSVP LSP is not used as a 
         shortcut while resolving BGP routes."
    DEFVAL { true }
    ::= { vRtrMplsLspEntry 53 }

vRtrMplsLspBgpTransportTunnel       OBJECT-TYPE
    SYNTAX      TmnxMplsLspBgpRSVPLSPTunState 
    MAX-ACCESS  read-create
    STATUS      current
    DESCRIPTION
        "The value of vRtrMplsLspBgpTransportTunnel specifies whether an RSVP 
         LSP is allowed or blocked in its usage as a transport LSP for BGP 
         tunnel routes.          
         
         When the value of vRtrMplsLspBgpTransportTunnel is set to 'include' an 
         RSVP LSP is allowed to be used as a transport LSP for BGP tunnel 
         routes. When the value of vRtrMplsLspBgpTransportTunnel is set to 
         'exclude' an RSVP LSP is not allowed to be used as a transport LSP 
         for BGP tunnel routes."
    DEFVAL { include }
    ::= { vRtrMplsLspEntry 54 }

vRtrMplsLspSwitchStbyPath  OBJECT-TYPE 
    SYNTAX      TmnxActionType
    MAX-ACCESS  read-create
    STATUS      current
    DESCRIPTION 
        "The value of vRtrMplsLspSwitchStbyPath specifies whether to 
         trigger the switch from the current active standby LSP path to a new
         LSP path as specified by vRtrMplsLspSwitchStbyPathIndex. 

         When SET to the value of 'doAction', if the LSP path is actively on 
         a current standby path, signaling will be initiated to switch to
         the new path.

         If a signal is triggered while a re-signaling is already in 
         progress, the old transient state will be destroyed and a new 
         transaction will be triggered.

         This variable must be set along with vRtrMplsLspSwitchStbyPathIndex
         to indicate the specific path index to switch to.

         An SNMP GET request on this object should return 'notApplicable'." 
    ::= { vRtrMplsLspEntry 55 }

vRtrMplsLspSwitchStbyPathIndex OBJECT-TYPE 
   SYNTAX        MplsTunnelIndex
   MAX-ACCESS    read-create
   STATUS        current
   DESCRIPTION 
        "The value of vRtrMplsLspSwitchStbyPathIndex specifies the 
         index for the new standby LSP path in mplsTunnelTable. 

         vRtrMplsLspSwitchStbyPath must also be set to 'doAction' for
         the new standby LSP path to be selected.

         A value of 0 specifies that the best active path will be selected." 
   DEFVAL { 0 }              
       ::= { vRtrMplsLspEntry 56 }

vRtrMplsLspSwitchStbyPathForce  OBJECT-TYPE 
   SYNTAX      TruthValue
   MAX-ACCESS  read-create
   STATUS      current
   DESCRIPTION 
        "The value of vRtrMplsLspSwitchStbyPathForce specifies whether
         to force a switch from an active LSP path to a new standby path
         as specified by the values of vRtrMplsLspSwitchStbyPathIndex
         and vRtrMplsLspSwitchStbyPath. 
        
         When vRtrMplsLspSwitchStbyPathForce variable is specified
         vRtrMplsLspSwitchStbyPathIndex and vRtrMplsLspSwitchStbyPath must be 
         also be specified.

         A value of 'true' for vRtrMplsLspSwitchStbyPathForce specifies 
         a forced switch.  A value of 'false' specifies no forced switch."
   DEFVAL { false }
       ::= { vRtrMplsLspEntry 57 }    

vRtrMplsLspExcludeNodeAddrType  OBJECT-TYPE
    SYNTAX      InetAddressType
    MAX-ACCESS  read-create
    STATUS      current
    DESCRIPTION
       "The value of vRtrMplsLspExcludeNodeAddrType indicates the type of 
        vRtrMplsLspExcludeNodeAddr."
    ::= { vRtrMplsLspEntry 58 }

vRtrMplsLspExcludeNodeAddr  OBJECT-TYPE
    SYNTAX      InetAddress (SIZE (0|4))
    MAX-ACCESS  read-create
    STATUS      current
    DESCRIPTION
        "When vRtrMplsLspExcludeNodeAddr is set to non-zero value, XRO (Exclude
        Routers) object will be included in bypass path message with supplied
        IP address.

        SET the value to 0.0.0.0 to disable."
    ::= { vRtrMplsLspEntry 59 }

vRtrMplsLspIgpShortcutLfaType OBJECT-TYPE
        SYNTAX      INTEGER {
                        none (0),
                        lfaProtect (1),
                        lfaOnly (2)
                    }
        MAX-ACCESS  read-create
        STATUS      current
        DESCRIPTION
            "The value of vRtrMplsLspIgpShortcutLfaType specifies whether to 
             exclude or include a RSVP LSP from being used as a shortcut while 
             resolving IGP routes in LFA SPF or whether to exclude or include a        
             RSVP LSP from being used as a LFA SPF.
    
             When the value of vRtrMplsLspIgpShortcutLfaType is set to 'lfaProtect' 
             the RSVP LSP is used as a shortcut while resolving IGP routes in LFA 
             SPF as well.
    
             When the value of vRtrMplsLspIgpShortcutLfaType is set to 'lfaOnly'
             the RSVP LSP is used as a LFA SPF and not used as igp-shortcut in 
             regular SPF.
            
             An 'inconsistentValue' error is returned if an attempt is made to
             set this object to a non-default value when the value of the object
             vRtrMplsLspIgpShortcut is not set to 'true'."        
        DEFVAL { none }
        ::= { vRtrMplsLspEntry 60 }

vRtrMplsLspToAddrType     OBJECT-TYPE
    SYNTAX      TmnxMplsLspAddrType 
    MAX-ACCESS  read-create
    STATUS      current
    DESCRIPTION
        "The vRtrMplsLspToAddrType object is an enumerated value that specifies
         the destination address type of the LSP.

         The value of 'ipv4' specifies an IPv4 address and vRtrMplsLspToAddr
         should be configured.

         The value of 'nodeId' specifies an MPLS-TP node id and 
         vRtrMplsLspToNodeId should be configured."
    DEFVAL { ipv4 }
    ::= { vRtrMplsLspEntry 61 }

vRtrMplsLspFromAddrType     OBJECT-TYPE
    SYNTAX      TmnxMplsLspAddrType
    MAX-ACCESS  read-create
    STATUS      current
    DESCRIPTION
        "The vRtrMplsLspFromAddrType object is an enumerated value that 
         specifies the source address type of the LSP.

         When the value of vRtrMplsLspFromAddrType is 'ipv4', it specifies 
         an IPv4 address type and vRtrMplsLspFromAddr should be configured.

         When the value of vRtrMplsLspFromAddrType is 'nodeId', it specifies 
         an MPLS-TP node id type and vRtrMplsLspFromNodeId should be 
         configured."
    DEFVAL { ipv4 }
    ::= { vRtrMplsLspEntry 62 }

vRtrMplsLspToNodeId   OBJECT-TYPE
    SYNTAX      TmnxMplsTpNodeID 
    MAX-ACCESS  read-create
    STATUS      current
    DESCRIPTION
        "The value of vRtrMplsLspToNodeId specifies the destination
         node id of an MPLS-TP Static LSP.
        
         vRtrMplsLspToNodeId is configured when vRtrMplsLspToAddrType is
         set to 'nodeId'." 
    DEFVAL { 0 }
    ::= { vRtrMplsLspEntry 63 }

vRtrMplsLspFromNodeId   OBJECT-TYPE
    SYNTAX      TmnxMplsTpNodeID 
    MAX-ACCESS  read-create
    STATUS      current
    DESCRIPTION
        "The value of vRtrMplsLspFromNodeId specifies the source 
         node id of an MPLS-TP Static LSP.

         vRtrMplsLspFromNodeId is configured when vRtrMplsLspFromAddrType is
         set to 'nodeId'." 
    DEFVAL { 0 }
    ::= { vRtrMplsLspEntry 64 }

vRtrMplsLspDestGlobalId   OBJECT-TYPE
    SYNTAX      TmnxMplsTpGlobalID
    MAX-ACCESS  read-create
    STATUS      current
    DESCRIPTION
        "The value of vRtrMplsLspDestGlobalId specifies the global identifier 
         for an MPLS-TP Static LSP. 

         A value of 0 indicates that a locally configured global identifier
         is to be used."
    DEFVAL { 0 }
    ::= { vRtrMplsLspEntry 65 }

vRtrMplsLspDestTunnelNum   OBJECT-TYPE
    SYNTAX      Unsigned32 (0 | 1..61440)
    MAX-ACCESS  read-create
    STATUS      current
    DESCRIPTION
        "The value of vRtrMplsLspDestTunnelNum specifies the destination
         tunnel number of an MPLS-TP Static LSP." 
    DEFVAL { 0 }
    ::= { vRtrMplsLspEntry 66 }



--
--  The Virtual Router MPLS Labeled Switch Path (LSP) Statistics Table
--
--  Augmentation of the vRtrMplsLspTable.
--  Use of AUGMENTS clause implies a one-to-one dependent relationship 
--  between the base table, vRtrMplsLspTable, and the augmenting table, 
--  vRtrMplsLspStatTable. This in effect extends the vRtrMplsLspTable 
--  with additional columns.  
--  Creation (or deletion) of a row in the vRtrMplsLspTable results in 
--  the same fate for the row in the vRtrMplsLspStatTable.
--

vRtrMplsLspStatTable    OBJECT-TYPE
    SYNTAX      SEQUENCE OF VRtrMplsLspStatEntry
    MAX-ACCESS  not-accessible
    STATUS      current
    DESCRIPTION
        "The vRtrMplsLspStatTable has an entry for each Labeled Switch
         Path (LSP) configured for a virtual router in the system."
    ::= { tnMplsObjs 2 }

vRtrMplsLspStatEntry    OBJECT-TYPE
    SYNTAX      VRtrMplsLspStatEntry
    MAX-ACCESS  not-accessible
    STATUS      current
    DESCRIPTION
        "Each row entry represents a collection of statistics for a
         Labeled Switch Path (LSP) configured for a virtual router in 
         the system.  

         Entries cannot be created and deleted via SNMP SET operations."
    AUGMENTS { vRtrMplsLspEntry }
    ::= { vRtrMplsLspStatTable 1 }

VRtrMplsLspStatEntry ::= SEQUENCE {
    vRtrMplsLspOctets                   Counter64,
    vRtrMplsLspPackets                  Counter64,
    vRtrMplsLspAge                      TimeInterval,
    vRtrMplsLspTimeUp                   TimeInterval,
    vRtrMplsLspTimeDown                 TimeInterval,
    vRtrMplsLspPrimaryTimeUp            TimeInterval,
    vRtrMplsLspTransitions              Counter32,
    vRtrMplsLspLastTransition           TimeInterval,
    vRtrMplsLspPathChanges              Counter32,
    vRtrMplsLspLastPathChange           TimeInterval,
    vRtrMplsLspConfiguredPaths          Integer32,
    vRtrMplsLspStandbyPaths             Integer32,
    vRtrMplsLspOperationalPaths         Integer32,
    vRtrMplsLspConfP2mpInstances        Gauge32
}

vRtrMplsLspOctets   OBJECT-TYPE
    SYNTAX      Counter64
    MAX-ACCESS  read-only
    STATUS      current
    DESCRIPTION
        "The number of octets that have been forwarded over current 
         LSP active path. The number reported is not realtime, may 
         be subject to several minutes delay.  The delay is controllable
         by MPLS statistics gathering interval, which by default is 
         once every 5 minutes.  If MPLS statistics gathering is not
         enabled, this number will not increment."
    ::= { vRtrMplsLspStatEntry 1 }

vRtrMplsLspPackets OBJECT-TYPE
    SYNTAX      Counter64
    MAX-ACCESS  read-only
    STATUS      current
    DESCRIPTION
        "The number of packets that have been forwarded over current 
         LSP active path. The number reported is not realtime, may 
         be subject to several minutes delay.  The delay is controllable
         by MPLS statistics gathering interval, which by default is 
         once every 5 minutes.  If MPLS statistics gathering is not
         enabled, this number will not increment."
    ::= { vRtrMplsLspStatEntry 2 }

vRtrMplsLspAge OBJECT-TYPE
    SYNTAX      TimeInterval
    MAX-ACCESS  read-only
    STATUS      current
    DESCRIPTION
        "The age (i.e., time from creation till now) of this LSP in 
         10-millisecond periods."
    ::= { vRtrMplsLspStatEntry 3 }

vRtrMplsLspTimeUp OBJECT-TYPE
    SYNTAX      TimeInterval
    MAX-ACCESS  read-only
    STATUS      current
    DESCRIPTION
        "The total time in 10-millisecond units that this LSP has been
         been operational.  For example, the percentage up time can be 
         determined by computing (vRtrMplsLspTimeUp/vRtrMplsLspAge * 100 %)."
    ::= { vRtrMplsLspStatEntry 4 }

vRtrMplsLspTimeDown OBJECT-TYPE
    SYNTAX      TimeInterval
    MAX-ACCESS  read-only
    STATUS      current
    DESCRIPTION
        "The total time in 10-millisecond units that this LSP has not 
         been operational."
    ::= { vRtrMplsLspStatEntry 5 }

vRtrMplsLspPrimaryTimeUp OBJECT-TYPE
    SYNTAX      TimeInterval
    MAX-ACCESS  read-only
    STATUS      current
    DESCRIPTION
        "The total time in 10-millisecond units that this LSP's primary 
         path has been operational.  For example, the percentage 
         contribution of the primary path to the operational time is 
         given by (vRtrMplsLspPrimaryTimeUp/vRtrMplsLspTimeUp * 100) %."
    ::= { vRtrMplsLspStatEntry 6 }

vRtrMplsLspTransitions OBJECT-TYPE
    SYNTAX      Counter32
    MAX-ACCESS  read-only
    STATUS      current
    DESCRIPTION
        "The number of state transitions (up -> down and down -> up) 
         this LSP has undergone."
    ::= { vRtrMplsLspStatEntry 7 }

vRtrMplsLspLastTransition OBJECT-TYPE
    SYNTAX      TimeInterval
    MAX-ACCESS  read-only
    STATUS      current
    DESCRIPTION
        "The time in 10-millisecond units since the last transition 
         occurred on this LSP."
    ::= { vRtrMplsLspStatEntry 8 }

vRtrMplsLspPathChanges OBJECT-TYPE
    SYNTAX      Counter32
    MAX-ACCESS  read-only
    STATUS      current
    DESCRIPTION
        "The number of path changes this LSP has had. For every path 
         change (path down, path up, path change), a corresponding 
         syslog/trap (if enabled) is generated for it."
    ::= { vRtrMplsLspStatEntry 9 }

vRtrMplsLspLastPathChange OBJECT-TYPE
    SYNTAX      TimeInterval
    MAX-ACCESS  read-only
    STATUS      current
    DESCRIPTION
        "The time in 10-millisecond units since the last change 
         occurred on this LSP."
    ::= { vRtrMplsLspStatEntry 10 }

vRtrMplsLspConfiguredPaths OBJECT-TYPE
    SYNTAX      Integer32
    MAX-ACCESS  read-only
    STATUS      current
    DESCRIPTION
        "The number of paths configured for this LSP."
    ::= { vRtrMplsLspStatEntry 11 }

vRtrMplsLspStandbyPaths OBJECT-TYPE
    SYNTAX      Integer32
    MAX-ACCESS  read-only
    STATUS      current
    DESCRIPTION
        "The number of standby paths configured for this LSP."
    ::= { vRtrMplsLspStatEntry 12 }

vRtrMplsLspOperationalPaths OBJECT-TYPE
    SYNTAX      Integer32
    MAX-ACCESS  read-only
    STATUS      current
    DESCRIPTION
        "The number of operational paths for this LSP. This includes
         the path currently active, as well as operational standby 
         paths."
    ::= { vRtrMplsLspStatEntry 13 }

vRtrMplsLspConfP2mpInstances OBJECT-TYPE
    SYNTAX      Gauge32
    MAX-ACCESS  read-only
    STATUS      current
    DESCRIPTION
        "The value of vRtrMplsLspConfP2mpInstances indicates the number 
        of p2mp instances configured for this LSP."
    ::= { vRtrMplsLspStatEntry 14 }

--
--  Virtual Router MPLS LSP to Path Mapping Table
--

-- vRtrMplsLspPathTableSpinlock OBJECT-TYPE
--    SYNTAX      TestAndIncr
--    MAX-ACCESS  read-write
--    STATUS      current
--    DESCRIPTION
--        "voluntary serialization control for vRtrMplsLspPathTable.  
--         Primarily used by SNMP manager to coordinate changes to 
--         vRtrMplsLspPathInheritance."
--    DEFVAL { 0 }
--    ::= { tnMplsObjs 3 }
--
--vRtrMplsLspPathTable    OBJECT-TYPE
--    SYNTAX      SEQUENCE OF VRtrMplsLspPathEntry
--    MAX-ACCESS  not-accessible
--    STATUS      current
--    DESCRIPTION
--        "The vRtrMplsLspPathTable provides an association between an
--         LSP and a path.  An LSP can have more than one path association,
--         but only one of those paths can be specified as the primary
--         path type.  Paths are defined in as Tunnel entries in the
--         mplsTunnelTable in the MPLS-TE-MIB."
--    ::= { tnMplsObjs 4 }
--
--vRtrMplsLspPathEntry    OBJECT-TYPE
--    SYNTAX      VRtrMplsLspPathEntry
--    MAX-ACCESS  not-accessible
--    STATUS      current
--    DESCRIPTION
--        "Each row entry represents an association between a Labeled Switch
--         Path (LSP) in the vRtrMplsLspTable and a path (or tunnel) entry in
--         the mplsTunnelTable.  Entries in this table can be created and
--         deleted via SNMP SET operations.  Setting RowStatus to 'active'
--         requires vRtrMplsLspPathType to have been assigned a valid value."
--    INDEX { tnSysSwitchId, vRtrID, vRtrMplsLspIndex, mplsTunnelIndex, mplsTunnelInstance,
--            mplsTunnelIngressLSRId }
--    ::= { vRtrMplsLspPathTable 1 }
--
--VRtrMplsLspPathEntry ::= SEQUENCE {
--    vRtrMplsLspPathRowStatus              RowStatus,
--    vRtrMplsLspPathLastChange             TimeStamp,
--    vRtrMplsLspPathType                   INTEGER,
--    vRtrMplsLspPathCos                    INTEGER,
--    vRtrMplsLspPathProperties             BITS,
--    vRtrMplsLspPathBandwidth              Integer32,
--    vRtrMplsLspPathBwProtect              TruthValue,
--    vRtrMplsLspPathState                  INTEGER,
--    vRtrMplsLspPathPreference             INTEGER,
--    vRtrMplsLspPathCosSource              TruthValue,
--    vRtrMplsLspPathClassOfService         TNamedItemOrEmpty,
--    vRtrMplsLspPathSetupPriority          Unsigned32,
--    vRtrMplsLspPathHoldPriority           Unsigned32,
--    vRtrMplsLspPathRecord                 INTEGER,
--    vRtrMplsLspPathHopLimit               Unsigned32,
--    vRtrMplsLspPathSharing                TruthValue,
--    vRtrMplsLspPathAdminState             TmnxAdminState,
--    vRtrMplsLspPathOperState              TmnxOperState,
--    vRtrMplsLspPathInheritance            Unsigned32,
--    vRtrMplsLspPathLspId                  MplsLSPID,
--    vRtrMplsLspPathRetryTimeRemaining     Unsigned32,
--    vRtrMplsLspPathTunnelARHopListIndex   Integer32,
--    vRtrMplsLspPathNegotiatedMTU          Unsigned32,
--    vRtrMplsLspPathFailCode               TmnxMplsLspFailCode,
--    vRtrMplsLspPathFailNodeAddr           IpAddress,
--    vRtrMplsLspPathAdminGroupInclude      Unsigned32,
--    vRtrMplsLspPathAdminGroupExclude      Unsigned32,
--    vRtrMplsLspPathAdaptive               TruthValue,
--    vRtrMplsLspPathOptimizeTimer          Unsigned32,
--    vRtrMplsLspPathNextOptimize           Unsigned32,
--    vRtrMplsLspPathOperBandwidth          Integer32,
--    vRtrMplsLspPathMBBState               INTEGER,
--    vRtrMplsLspPathResignal               TmnxActionType,
--    vRtrMplsLspPathTunnelCRHopListIndex   Integer32,
--    vRtrMplsLspPathOperMTU                Unsigned32,
--    vRtrMplsLspPathRecordLabel            INTEGER,
--    vRtrMplsLspPathSrlg                   TruthValue,
--    vRtrMplsLspPathSrlgDisjoint           TruthValue,
--    vRtrMplsLspPathLastResigAttempt       TimeStamp,
--    vRtrMplsLspPathMetric                 Unsigned32,
--    vRtrMplsLspPathLastMBBType            TmnxMplsMBBType,
--    vRtrMplsLspPathLastMBBEnd             TimeStamp,
--    vRtrMplsLspPathLastMBBMetric          Unsigned32,
--    vRtrMplsLspPathLastMBBState           INTEGER,
--    vRtrMplsLspPathMBBTypeInProg          TmnxMplsMBBType,
--    vRtrMplsLspPathMBBStarted             TimeStamp,
--    vRtrMplsLspPathMBBNextRetry           Unsigned32,
--    vRtrMplsLspPathMBBRetryAttempts       Unsigned32,
--    vRtrMplsLspPathMBBFailCode            TmnxMplsLspFailCode,
--    vRtrMplsLspPathMBBFailNodeArType      InetAddressType,
--    vRtrMplsLspPathMBBFailNodeAddr        InetAddress,
--    vRtrMplsLspPathClassType              TmnxRsvpDSTEClassType,
--    vRtrMplsLspPathOperMetric             Unsigned32,
--    vRtrMplsLspPathResignalEligible       TruthValue,
--    vRtrMplsLspPathIsFastRetry            TruthValue,
--    vRtrMplsLspPathBackupCT               Integer32, 
--    vRtrMplsLspPathMainCTRetryRem         Unsigned32,
--    vRtrMplsLspPathOperCT                 Integer32,
--    vRtrMplsLspPathNewPathIndex           MplsTunnelIndex,   
--    vRtrMplsLspPathMBBMainCTRetryRem      Unsigned32,
--    vRtrMplsLspPathSigBWMBBInProg         Unsigned32,
--    vRtrMplsLspPathSigBWLastMBB           Unsigned32,
--    vRtrMplsLspPathActiveByManual         INTEGER,
--    vRtrMplsLspPathTimeoutIn              Unsigned32,
--    vRtrMplsLspPathMBBTimeoutIn           Unsigned32
--    }
--
--vRtrMplsLspPathRowStatus    OBJECT-TYPE
--    SYNTAX      RowStatus
--    MAX-ACCESS  read-create
--    STATUS      current
--    DESCRIPTION
--        "The row status used for creation, deletion, or control
--         of vRtrMplsLspPathTable entries.  Before the row can be
--         placed into the 'active' state vRtrMplsLspPathType must
--         have been assigned a valid value."
--    ::= { vRtrMplsLspPathEntry 1 }
--
--vRtrMplsLspPathLastChange       OBJECT-TYPE
--    SYNTAX      TimeStamp
--    MAX-ACCESS  read-only
--    STATUS      current
--    DESCRIPTION
--        "The sysUpTime when this row was last modified."
--    ::= { vRtrMplsLspPathEntry 2 }
--
--vRtrMplsLspPathType     OBJECT-TYPE
--    SYNTAX      INTEGER {
--                    other (1),
--                    primary (2),
--                    standby (3),
--                    secondary (4)
--                }
--    MAX-ACCESS  read-create
--    STATUS      current
--    DESCRIPTION
--        "This variable is an enum that represents the role this
--         path is taking within this LSP."
--    ::= { vRtrMplsLspPathEntry 3 }
--
--vRtrMplsLspPathCos      OBJECT-TYPE
--    SYNTAX      INTEGER (0..7 | 255)
--    MAX-ACCESS  read-create
--    STATUS      current
--    DESCRIPTION
--        "The configured Class Of Service (COS) for this path.  If
--         the value is between 0 and 7 inclusive, this value
--         will be inserted in the 3 bit COS field in the label.
--         If the value is 255, the value in the COS field of
--         the label will depend on other factors."
--    DEFVAL { 255 }
--    ::= { vRtrMplsLspPathEntry 4 }
--
--vRtrMplsLspPathProperties   OBJECT-TYPE
--    SYNTAX      BITS {
--                    record-route (0),
--                    adaptive (1),
--                    cspf (2),
--                    mergeable (3),
--                    fast-reroute (4)
--                }
--    MAX-ACCESS  read-only
--    STATUS      current
--    DESCRIPTION
--        "The set of configured properties for this path expressed
--         as a bit map.  For example, if the path is an adaptive
--         path, the bit corresponding to bit value 1 is set."
--    ::= { vRtrMplsLspPathEntry 5 }
--
--vRtrMplsLspPathBandwidth    OBJECT-TYPE
--    SYNTAX      Integer32
--    UNITS       "mega-bits per second"
--    MAX-ACCESS  read-create
--    STATUS      current
--    DESCRIPTION
--        "The value of vRtrMplsLspPathBandwidth specifies the amount
--         of bandwidth in mega-bits per seconds (Mbps) to be reserved
--         for this LSP path.  A value of zero (0) indicates that no
--         bandwidth is reserved."
--    DEFVAL { 0 }
--    ::= { vRtrMplsLspPathEntry 6 }
--
--vRtrMplsLspPathBwProtect    OBJECT-TYPE
--    SYNTAX      TruthValue
--    MAX-ACCESS  read-create
--    STATUS      current
--    DESCRIPTION
--        "When vRtrMplsLspPathBwProtect has a value of 'true', bandwidth
--         protection is enabled on a LSP.  LSPs that reserve bandwidth
--         will be used for EF services where customers need guaranteed
--         bandwidth.  It is expected that multiple EF services will be
--         assigned to a single LSP.  When bandwidth protection is
--         enabled on an LSP, each time this LSP is used for a certain
--         service the bandwidth allocated on that service is deducted
--         from the bandwidth reserved for the LSP.  Once the bandwidth is
--         exhausted on the LSP, the ESR will provide feedback to the
--         provider indicating that this LSP has exhausted its resources."
--    DEFVAL { false }
--    ::= { vRtrMplsLspPathEntry 7 }
--
--vRtrMplsLspPathState    OBJECT-TYPE
--    SYNTAX      INTEGER {
--                    unknown (1),
--                    active (2),
--                    inactive (3)
--                }
--    MAX-ACCESS  read-only
--    STATUS      current
--    DESCRIPTION
--        "The current working state of this path within this LSP."
--    DEFVAL { unknown }
--    ::= { vRtrMplsLspPathEntry 8 }
--
--vRtrMplsLspPathPreference   OBJECT-TYPE
--    SYNTAX      INTEGER (0..255)
--    MAX-ACCESS  read-create
--    STATUS      current
--    DESCRIPTION
--        "When there is no path in the LSP with vRtrMplsLspPathType
--         value of 'primary', 'secondary' type paths of this LSP 
--         with the same value of vRtrMplsLspPathPreference are used
--         for load sharing.  When a 'primary' type path exists in
--         the LSP, vRtrMplsLspPathPreference is used to denote at
--         which priority one 'secondary' path will supercede another
--         when the 'primary' fails. 1 indicates the highest priority 
--         value.
--         
--         For LSP with vRtrMplsLspPathType value of 'standby' type paths 
--         the value of vRtrMplsLspPathPreference is in the range of (1..255). 
--         For path type 'primary' the value of vRtrMplsLspPathPreference 
--         is set to 0. For path type 'secondary' the value of vRtrMplsLspPathPreference
--         is set to 255."
--    DEFVAL { 255 }
--    ::= { vRtrMplsLspPathEntry 9 }
--
--vRtrMplsLspPathCosSource        OBJECT-TYPE
--    SYNTAX      TruthValue
--    MAX-ACCESS  read-create
--    STATUS      current
--    DESCRIPTION
--        "When vRtrMplsLspPathCosSource is set to 'true', the value of
--         vRtrMplsLspPathClassOfService overrides vRtrMplsLspClassOfService.
--         When 'false', the value of vRtrMplsLspClassOfService is used."
--    DEFVAL { false }
--    ::= { vRtrMplsLspPathEntry 10 }
--
--vRtrMplsLspPathClassOfService   OBJECT-TYPE
--    SYNTAX      TNamedItemOrEmpty
--    MAX-ACCESS  read-create
--    STATUS      current
--    DESCRIPTION
--        "The name of the class of service value to be assigned to all
--         packets on the LSP is specified with vRtrMplsLspPathClassOfService.
--         The EXP bits in the MPLS header are set based on the global
--         mapping table that specified the mapping between the forwarding
--         class and the EXP bits.  When class of service is specified,
--         all packets will be marked with the same EXP bits that match
--         the vRtrMplsLspPathClassOfService name in the mapping table.
--         
--         An empty string, ''H, specifies no class of service.  Packets
--         are assigned EXP bits based on the same mapping table, however
--         each packet is marked with EXP bits based on the forwarding
--         class from which it is serviced."
--    DEFVAL { ''H }
--    ::= { vRtrMplsLspPathEntry 11 }
--        
--vRtrMplsLspPathSetupPriority    OBJECT-TYPE
--    SYNTAX      Unsigned32 (0..7)
--    MAX-ACCESS  read-create
--    STATUS      current
--    DESCRIPTION
--        "The value of vRtrMplsLspPathSetupPriority specifies the setup 
--         priority to use when insufficient bandwidth is available to setup 
--         a LSP.  The setup priority is compared against the hold priority of
--         existing LSPs.  If the setup priority is higher than the hold
--         priority of the established LSPs, this LSP may preempt the other
--         LSPs.  A value of zero (0) is the highest priority and a value
--         of seven (7) is the lowest priority."
--    DEFVAL { 7 }
--    ::= { vRtrMplsLspPathEntry 12 }
--        
--vRtrMplsLspPathHoldPriority     OBJECT-TYPE
--    SYNTAX      Unsigned32 (0..7)
--    MAX-ACCESS  read-create
--    STATUS      current
--    DESCRIPTION
--        "The value of vRtrMplsLspPathHoldPriority specifies the hold 
--         priority to use when insufficient bandwidth is available to setup 
--         a LSP.  The setup priority is compared against the hold priority of
--         existing LSPs.  If the setup priority is higher than the hold
--         priority of the established LSPs, this LSP may preempt the other
--         LSPs.  A value of zero (0) is the highest priority and a value
--         of seven (7) is the lowest priority."
--    DEFVAL { 0 }
--    ::= { vRtrMplsLspPathEntry 13 }
--
--vRtrMplsLspPathRecord       OBJECT-TYPE
--    SYNTAX      INTEGER {
--                    record (1),
--                    noRecord (2)
--                }
--    MAX-ACCESS  read-create
--    STATUS      current
--    DESCRIPTION
--        "When the value of vRtrMplsLspPathRecord is 'record', recording of 
--         all the hops that a LSP traverses is enabled.
--         
--         When the value of vRtrMplsLspPathRecord is 'noRecord', recording 
--         of all the hops that a LSP traverses is disabled."
--    DEFVAL { record }
--    ::= { vRtrMplsLspPathEntry 14 }       
--
--vRtrMplsLspPathHopLimit     OBJECT-TYPE
--    SYNTAX      Unsigned32 (2..255)
--    MAX-ACCESS  read-create
--    STATUS      current
--    DESCRIPTION
--        "The value of vRtrMplsLspPathHopLimit specifies the maximum number
--         of hops that a LSP will traverse including the ingress and
--         egress ESRs.  A LSP will not be setup if the hop limit is
--         exceeded.  
--         
--         When the vRtrMplsLspPathHopLimit bit in vRtrMplsLspPathInheritance 
--         is cleared (0), the value returned to a GET request is inherited 
--         from vRtrMplsLspHopLimit."
--    DEFVAL { 255 }
--    ::= { vRtrMplsLspPathEntry 15 }
--
--vRtrMplsLspPathSharing  OBJECT-TYPE
--    SYNTAX      TruthValue
--    MAX-ACCESS  read-create
--    STATUS      current
--    DESCRIPTION
--        "When vRtrMplsLspPathSharing has a value of 'true', path-sharing
--         is enabled for the secondary path.  Path-sharing is used to
--         control the hops of the secondary path.
--         
--         When vRtrMplsLspPathSharing have a value of 'false', CSPF attempts
--         to find a path for the secondary that does not include any node
--         or link that is common to the active primary path.
--         
--         This variable is valid only if vRtrMplsLspPathType is set to
--         'secondary'."
--    DEFVAL { false }
--    ::= { vRtrMplsLspPathEntry 16 }
--
--vRtrMplsLspPathAdminState       OBJECT-TYPE
--    SYNTAX      TmnxAdminState
--    MAX-ACCESS  read-create
--    STATUS      current
--    DESCRIPTION
--        "The desired administrative state for this LSP path."
--    DEFVAL { inService }
--    ::= { vRtrMplsLspPathEntry 17 }
--
--vRtrMplsLspPathOperState        OBJECT-TYPE
--    SYNTAX      TmnxOperState
--    MAX-ACCESS  read-only
--    STATUS      current
--    DESCRIPTION
--        "The current operational state of this LSP path."
--    ::= { vRtrMplsLspPathEntry 18 }
--
--vRtrMplsLspPathInheritance OBJECT-TYPE
--    SYNTAX      Unsigned32
--    MAX-ACCESS  read-create
--    STATUS      current
--    DESCRIPTION
--        "For each writable object in this row that can be configured to
--         inherit its value from its corresponding object in the 
--         vRtrMplsLspTable, controls whether to inherit the operational value 
--         of that object, or use the administratively set value.
--        
--         Non mask bits will always have value of zero, and any attempt to
--         change the value will be silently discarded.
--        
--         This object is a bit-mask, with the following positions:
--
--         vRtrMplsLspPathHopLimit              0x2000
--         vRtrMplsLspPathAdminGroupInclude    0x20000
--         vRtrMplsLspPathAdminGroupExclude    0x40000
--         vRtrMplsLspPathAdaptive             0x80000
--         vRtrMplsLspPathOptimizeTimer       0x100000
--         vRtrMplsLspPathClassType           0x1000000
--
--         When the bit for an object is set to one, then the
--         object's administrative and operational value are whatever
--         the DEFVAL or most recently SET value is. The corresponding 
--         mask bit will be changed to one when SNMP SET is performed 
--         on any of the inherited objects (vRtrMplsLspPathHopLimit,
--         vRtrMplsLspPathAdminGroupInclude, etc).
--        
--         When the bit for an object is set to zero, then the
--         object's administrative and operational value are inherited
--         from the corresponding object in vRtrMplsLspTable."
--    DEFVAL { 0 }  by default inherit everything from vRtrMplsLspTable
--    ::= { vRtrMplsLspPathEntry 19 }
--
--vRtrMplsLspPathLspId OBJECT-TYPE
--    SYNTAX      MplsLSPID
--    MAX-ACCESS  read-only
--    STATUS      current
--    DESCRIPTION
--        "This value identifies the label switched path that
--         is signaled for this entry."
--    ::= { vRtrMplsLspPathEntry 20 }
--
--vRtrMplsLspPathRetryTimeRemaining       OBJECT-TYPE
--    SYNTAX      Unsigned32
--    MAX-ACCESS  read-only
--    STATUS      current
--    DESCRIPTION
--        "The time in 10-millisecond units to signal this path."
--    ::= { vRtrMplsLspPathEntry 21 }
--
--vRtrMplsLspPathTunnelARHopListIndex   OBJECT-TYPE
--    SYNTAX      Integer32 (0|1..2147483647)
--    MAX-ACCESS  read-only
--    STATUS      current
--    DESCRIPTION
--        "Primary index into the mplsTunnelARHopTable identifying a
--         particular recorded hop list. A value of 0 implies that there
--         is no recored hop list associated with this LSP path."
--    ::= { vRtrMplsLspPathEntry 22 }
--
--vRtrMplsLspPathNegotiatedMTU     OBJECT-TYPE
--    SYNTAX      Unsigned32
--    MAX-ACCESS  read-only
--    STATUS      current
--    DESCRIPTION
--        "The value of vRtrMplsLspPathNegotiatedMTU specifies the size 
--         for the Maximum transmission unit (MTU) that is negotiated
--         during establishment of this LSP Path."
--    DEFVAL { 0 }
--    ::= { vRtrMplsLspPathEntry 23 }
--
--vRtrMplsLspPathFailCode     OBJECT-TYPE
--    SYNTAX      TmnxMplsLspFailCode
--    MAX-ACCESS  read-only
--    STATUS      current
--    DESCRIPTION
--        "The value of vRtrMplsLspPathFailCode specifies the reason code
--         for LSP Path failure. A value of 0 indicates that no failure 
--         has occurred."
--    ::= { vRtrMplsLspPathEntry 24 }
--
--vRtrMplsLspPathFailNodeAddr     OBJECT-TYPE
--    SYNTAX      IpAddress
--    MAX-ACCESS  read-only
--    STATUS      current
--    DESCRIPTION
--        "The value of vRtrMplsLspPathFailNodeAddr specifies the IP address
--         of the node in the LSP path at which the LSP path failed. When 
--         no failure has occurred, this value is 0."
--    ::= { vRtrMplsLspPathEntry 25 }
--
--vRtrMplsLspPathAdminGroupInclude   OBJECT-TYPE
--    SYNTAX      Unsigned32
--    MAX-ACCESS  read-create
--    STATUS      current
--    DESCRIPTION
--        "The value of vRtrMplsLspPathAdminGroupInclude is a bit-map that
--         specifies a list of admin groups that should be included when
--         this LSP path is setup. If bit 'n' is set, then the admin group 
--         with value 'n' is included for this LSP path. This implies that 
--         each link that this LSP path goes through must be associated with  
--         at least one of the admin groups in the include list.
--
--         When the vRtrMplsLspPathAdminGroupInclude bit in 
--         vRtrMplsLspPathInheritance is cleared (0), the value returned 
--         to a GET request is inherited from vRtrMplsLspAdminGroupInclude."
--    DEFVAL { '00000000'H }
--    ::= { vRtrMplsLspPathEntry 26 }
--
--vRtrMplsLspPathAdminGroupExclude   OBJECT-TYPE
--    SYNTAX      Unsigned32
--    MAX-ACCESS  read-create
--    STATUS      current
--    DESCRIPTION
--        "The value of vRtrMplsLspPathAdminGroupExclude is a bit-map that
--         specifies a list of admin groups that should be excluded when
--         this LSP path is setup. If bit 'n' is set, then the admin group 
--         with value 'n' is excluded for this LSP path. This implies that 
--         each link that this LSP path goes through must not be associated
--         with any of the admin groups in the exclude list.
--
--         When the vRtrMplsLspPathAdminGroupExclude bit in 
--         vRtrMplsLspPathInheritance is cleared (0), the value returned 
--         to a GET request is inherited from vRtrMplsLspAdminGroupExclude."
--    DEFVAL { '00000000'H }
--    ::= { vRtrMplsLspPathEntry 27 }
--
--vRtrMplsLspPathAdaptive   OBJECT-TYPE
--    SYNTAX      TruthValue
--    MAX-ACCESS  read-create
--    STATUS      current
--    DESCRIPTION
--        "Setting the value of vRtrMplsLspPathAdaptive to 'true', enables
--         make-before-break functionality for the LSP path.          
--         
--         Setting the value to 'false', disables make-before-break 
--         functionality for the path.
--
--         When the vRtrMplsLspPathAdaptive bit in vRtrMplsLspPathInheritance 
--         is cleared (0), the value returned to a GET request is inherited 
--         from vRtrMplsLspAdaptive."
--    DEFVAL { true }
--    ::= { vRtrMplsLspPathEntry 28 }
--
--vRtrMplsLspPathOptimizeTimer   OBJECT-TYPE
--    SYNTAX      Unsigned32 (0..65535)
--    UNITS       "seconds"
--    MAX-ACCESS  read-create
--    STATUS      current
--    DESCRIPTION
--        "The value of vRtrMplsLspPathOptimizeTimer specifies the time, in 
--         seconds, the software will wait before attempting to re-optimize
--         the LSP path.
--
--         When CSPF is enabled, changes in the network topology may cause
--         the existing path of a loose-hop LSP to become sub-optimal. Such
--         LSPs can be re-optimized and re-routed through more optimal paths
--         by recalculating the path for the LSP at periodic intervals. This
--         interval is controlled by the optimize timer.
--         
--         A value of 0 indicates that optimization has been disabled.
--
--         When the vRtrMplsLspPathOptimizeTimer bit in 
--         vRtrMplsLspPathInheritance is cleared (0), the value returned in
--         the GET request is inherited from vRtrMplsLspOptimizeTimer."
--    DEFVAL { 0 }
--    ::= { vRtrMplsLspPathEntry 29 }
--
--vRtrMplsLspPathNextOptimize   OBJECT-TYPE
--    SYNTAX      Unsigned32 (0..65535)
--    UNITS       "seconds"
--    MAX-ACCESS  read-only
--    STATUS      current
--    DESCRIPTION
--        "The value of vRtrMplsLspPathNextOptimize specifies the current value
--         of the optimize timer. This is the time, in seconds, remaining till
--         the optimize timer will expire and optimization will be started for
--         the LSP path."
--    ::= { vRtrMplsLspPathEntry 30 }
--
--vRtrMplsLspPathOperBandwidth  OBJECT-TYPE
--    SYNTAX      Integer32
--    UNITS       "mega-bits per second"
--    MAX-ACCESS  read-only
--    STATUS      current
--    DESCRIPTION
--        "The value of vRtrMplsLspPathOperBandwidth specifies the amount of
--         bandwidth in mega-bits per seconds (Mbps) that has been reserved
--         for the operational LSP path.
--
--         When make-before-break functionality for the LSP is enabled and 
--         if the path bandwidth is changed, the resources allocated to the 
--         existing LSP paths will not be released until a new path with 
--         the new bandwidth settings has been established. While a new path 
--         is being signaled, the administrative value and the operational 
--         values of the path bandwidth may differ. The value of 
--         vRtrMplsLspPathBandwidth specifies the bandwidth requirements for 
--         the new LSP path trying to be established whereas the value of 
--         vRtrMplsLspPathOperBandwidth specifies the bandwidth reserved 
--         for the existing LSP path."
--    ::= { vRtrMplsLspPathEntry 31 }
--
--vRtrMplsLspPathMBBState  OBJECT-TYPE
--    SYNTAX      INTEGER {
--                    none (1),
--                    success (2), 
--                    inProgress (3),
--                    fail (4)
--                }
--    MAX-ACCESS  read-only
--    STATUS      obsolete
--    DESCRIPTION
--        "The value of vRtrMplsLspPathMBBState specifies the state of the 
--         most recent invocation of the make-before-break functionality. 
--
--         Possible states are:
--
--         none (1)        - no make-before-break invoked 
--         success (2)     - make-before-break successful
--         inProgress (3)  - make-before-break in progress 
--         fail (4)        - make-before-break failed.
--
--         This object was made obsolete in release 6.0 R4 and replaced 
--         with vRtrMplsLspPathLastMBBState."
--    ::= { vRtrMplsLspPathEntry 32 }
--
--vRtrMplsLspPathResignal   OBJECT-TYPE
--    SYNTAX      TmnxActionType
--    MAX-ACCESS  read-create
--    STATUS      current
--    DESCRIPTION
--        "Setting the value of vRtrMplsLspPathResignal to 'doAction' triggers
--         the re-signaling of the LSP path. 
--
--         If the LSP path is operationally down either due to network failure
--         or due to the retry attempts count being exceeded, setting this 
--         variable to 'doAction' will initiate the signaling for the path. A 
--         make-before-break signaling for the path will be initiated if the 
--         LSP is operationally up but the make-before-break retry attempts 
--         count was exceeded. Make-before-break signaling will also be 
--         initiated for any LSP that is operationally up. This may be used 
--         to cause a loose-hop LSP to be optimized. 
--
--         If a re-signal is triggered while a re-signaling is already in 
--         progress, the old transient state will be destroyed and a new 
--         transaction being triggered.
--         
--         An SNMP GET request on this object should return 'notApplicable'."
--    ::= { vRtrMplsLspPathEntry 33 }
--
--vRtrMplsLspPathTunnelCRHopListIndex   OBJECT-TYPE
--    SYNTAX      Integer32 (0|1..2147483647)
--    MAX-ACCESS  read-only
--    STATUS      current
--    DESCRIPTION
--        "Primary index into the vRtrMplsTunnelCHopTable identifying a
--         particular computed hop list. A value of 0 implies that there
--         is no computed hop list associated with this LSP path."
--    ::= { vRtrMplsLspPathEntry 34 }
--
--vRtrMplsLspPathOperMTU     OBJECT-TYPE
--    SYNTAX      Unsigned32
--    MAX-ACCESS  read-only
--    STATUS      current
--    DESCRIPTION
--        "The value of vRtrMplsLspPathOperMTU specifies the size 
--         for the Maximum transmission unit (MTU) that is currently
--         operation for this LSP Path."
--    ::= { vRtrMplsLspPathEntry 35 }
--
--vRtrMplsLspPathRecordLabel       OBJECT-TYPE
--    SYNTAX      INTEGER {
--                    record (1),
--                    noRecord (2)
--                }
--    MAX-ACCESS  read-create
--    STATUS      current
--    DESCRIPTION
--        "When the value of vRtrMplsLspPathRecordLabel is 'record', 
--         recording of labels at each node that a LSP traverses is 
--         enabled.
--         
--         When the value of vRtrMplsLspPathRecordLabel is 'noRecord', 
--         recording of labels at each node that a LSP traverses is 
--         disabled."
--    DEFVAL { record }
--    ::= { vRtrMplsLspPathEntry 36 }  
--
--vRtrMplsLspPathSrlg       OBJECT-TYPE
--    SYNTAX      TruthValue
--    MAX-ACCESS  read-create
--    STATUS      current
--    DESCRIPTION
--        "The value of vRtrMplsLspPathSrlg specifies whether the use of 
--         SRLG constraint in the computation of a secondary path for an 
--         LSP at the head-end Label Edge Router (LER) is enabled.
--         
--         The value vRtrMplsLspPathSrlg is used only when the value of 
--         vRtrMplsLspPathType is 'secondary'.  When the value of 
--         vRtrMplsLspPathSrlg is true, the use of SRLG constraint in the
--         computation of a secondary path is enabled."
--    DEFVAL { false }
--    ::= { vRtrMplsLspPathEntry 37 }       
--
--vRtrMplsLspPathSrlgDisjoint       OBJECT-TYPE
--    SYNTAX      TruthValue
--    MAX-ACCESS  read-only
--    STATUS      current
--    DESCRIPTION
--        "The value of vRtrMplsLspPathSrlgDisjoint specifies whether the 
--         relevant standby lsp path is SRLG disjoint from the associated primary 
--         lsp path for an LSP at the head-end Label Edge Router (LER).
--         
--         The value vRtrMplsLspPathSrlgDisjoint is used only when the 
--         value of vRtrMplsLspPathType is 'standby'.  When the value of 
--         vRtrMplsLspPathSrlgDisjoint is 'true', primary and standby lsp 
--         path do not have SRLG membership in common.  When the value of 
--         vRtrMplsLspPathSrlgDisjoint is 'false', primary and standby lsp 
--         path have SRLG membership in common."
--     ::= { vRtrMplsLspPathEntry 38 }
--
--vRtrMplsLspPathLastResigAttempt       OBJECT-TYPE
--    SYNTAX      TimeStamp
--    MAX-ACCESS  read-only
--    STATUS      current
--    DESCRIPTION
--        "The value of vRtrMplsLspPathLastResigAttempt indicates the 
--         sysUpTime when the last attempt to resignal this LSP was made."
--    ::= { vRtrMplsLspPathEntry 39 } 
--
--vRtrMplsLspPathMetric       OBJECT-TYPE
--    SYNTAX      Unsigned32
--    MAX-ACCESS  read-only
--    STATUS      current
--    DESCRIPTION
--        "The value of vRtrMplsLspPathMetric indicates the cost of the traffic 
--         engineered path returned by the IGP."
--     ::= { vRtrMplsLspPathEntry 40 } 
--
--vRtrMplsLspPathLastMBBType      OBJECT-TYPE
--    SYNTAX      TmnxMplsMBBType
--    MAX-ACCESS  read-only
--    STATUS      current
--    DESCRIPTION
--        "The value of vRtrMplsLspPathLastMBBType indicates the type of 
--         last Make-before-break (MBB).  If 'none', then no MBB has been
--         attempted."
--    ::= { vRtrMplsLspPathEntry 41 } 
--
--vRtrMplsLspPathLastMBBEnd       OBJECT-TYPE
--    SYNTAX      TimeStamp
--    MAX-ACCESS  read-only
--    STATUS      current
--    DESCRIPTION
--        "The value of vRtrMplsLspPathLastMBBEnd indicates the 
--         sysUpTime when the last MBB ended."
--    ::= { vRtrMplsLspPathEntry 42 } 
--
--vRtrMplsLspPathLastMBBMetric              OBJECT-TYPE
--    SYNTAX      Unsigned32
--    MAX-ACCESS  read-only
--    STATUS      current
--    DESCRIPTION
--        "The value of vRtrMplsLspPathLastMBBMetric  indicates  the 
--         cost of the traffic engineered path for the LSP path prior to MBB."
--    ::= { vRtrMplsLspPathEntry 43 }     
--
--vRtrMplsLspPathLastMBBState  OBJECT-TYPE
--    SYNTAX      INTEGER {
--                    none (1),
--                    success (2), 
--                    fail(3)
--                }
--    MAX-ACCESS  read-only
--    STATUS      current
--    DESCRIPTION
--        "The value of vRtrMplsLspPathLastMBBState specifies whether the last 
--         Make-before-break was successful or failed. 
--         Possible states are:
--         none (1)        - no make-before-break invoked 
--         success (2)     - make-before-break successful
--         fail (3)        - make-before-break failed."
--    ::= { vRtrMplsLspPathEntry 44 }    
--
--vRtrMplsLspPathMBBTypeInProg      OBJECT-TYPE
--    SYNTAX      TmnxMplsMBBType
--    MAX-ACCESS  read-only
--    STATUS      current
--    DESCRIPTION
--        "The value of vRtrMplsLspPathMBBTypeInProg indicates the type of the
--         Make-before-break (MBB) that is in progress. If 'none', then no MBB
--         is in progress."
--   ::= { vRtrMplsLspPathEntry 45 } 
--
--vRtrMplsLspPathMBBStarted       OBJECT-TYPE
--    SYNTAX      TimeStamp
--    MAX-ACCESS  read-only
--    STATUS      current
--    DESCRIPTION
--        "The value of vRtrMplsLspPathMBBStarted indicates the 
--         sysUpTime when the in-progress MBB started."
--    ::= { vRtrMplsLspPathEntry 46 } 
--    
--vRtrMplsLspPathMBBNextRetry      OBJECT-TYPE
--    SYNTAX      Unsigned32
--    UNITS       "seconds"     
--    MAX-ACCESS  read-only
--    STATUS      current
--    DESCRIPTION
--        "The value of vRtrMplsLspPathMBBNextRetry indicates the amount 
--         of time remaining in seconds before the next attempt is made to retry 
--         the in-progress MBB."
--    ::= { vRtrMplsLspPathEntry 47 } 
--
--vRtrMplsLspPathMBBRetryAttempts       OBJECT-TYPE
--    SYNTAX      Unsigned32
--    MAX-ACCESS  read-only
--    STATUS      current
--    DESCRIPTION
--        "The value of vRtrMplsLspPathMBBRetryAttempts indicates 'n' where
--         nth attempt for the MBB is in progress."
--    ::= { vRtrMplsLspPathEntry 48 }         
--
--vRtrMplsLspPathMBBFailCode     OBJECT-TYPE
--    SYNTAX      TmnxMplsLspFailCode
--    MAX-ACCESS  read-only
--    STATUS      current
--    DESCRIPTION
--        "The value of vRtrMplsLspPathMBBFailCode specifies the reason code
--         for in-progress MBB failure. A value of 'none' indicates that no failure 
--         has occurred."
--    ::= { vRtrMplsLspPathEntry 49 }
--
--vRtrMplsLspPathMBBFailNodeArType OBJECT-TYPE
--     SYNTAX     InetAddressType
--     MAX-ACCESS read-only
--     STATUS     current
--     DESCRIPTION
--       "The value of vRtrMplsLspPathMBBFailNodeArType indicates the type of 
--        vRtrMplsLspPathMBBFailNodeAddr. A value of 'unknown' indicates that no failure 
--        has occurred."
--     ::= { vRtrMplsLspPathEntry 50 }   
--     
--vRtrMplsLspPathMBBFailNodeAddr     OBJECT-TYPE
--    SYNTAX      InetAddress (SIZE (0|4))
--    MAX-ACCESS  read-only
--    STATUS      current
--    DESCRIPTION
--        "The value of vRtrMplsLspPathMBBFailNodeAddr specifies the IP address
--         of the node in the LSP path at which the in-progress MBB failed. A value of 'unknown' 
--         for vRtrMplsLspPathMBBFailNodeArType and empty string for 
--         vRtrMplsLspPathMBBFailNodeAddr indicates that no failure has occurred."
--    ::= { vRtrMplsLspPathEntry 51 }
--
--vRtrMplsLspPathClassType        OBJECT-TYPE
--    SYNTAX      TmnxRsvpDSTEClassType
--    MAX-ACCESS  read-create
--    STATUS      current
--    DESCRIPTION
--        "The value of vRtrMplsLspPathClassType specifies the class type (CT) 
--         associated with this LSP path.   When the vRtrMplsLspPathClassType 
--         bit in vRtrMplsLspPathInheritance is cleared (0), the value returned to 
--         a GET request is inherited from vRtrMplsLspClassType."
--    DEFVAL { 0 }
--    ::= { vRtrMplsLspPathEntry 52 } 
--
--vRtrMplsLspPathOperMetric            OBJECT-TYPE
--    SYNTAX      Unsigned32
--    MAX-ACCESS  read-only
--    STATUS      current
--    DESCRIPTION
--        "The value of vRtrMplsLspPathOperMetric indicates the operational 
--        metric for the LSP path."
--    ::= { vRtrMplsLspPathEntry 53 }    
--
--vRtrMplsLspPathResignalEligible            OBJECT-TYPE
--    SYNTAX      TruthValue
--    MAX-ACCESS  read-only
--    STATUS      current
--    DESCRIPTION
--        "The value of vRtrMplsLspPathResignalEligible indicates that the LSP path 
--        is eligible for re-signaling on the basis of available bandwidth."
--    ::= { vRtrMplsLspPathEntry 54 }        
--   
--vRtrMplsLspPathIsFastRetry      OBJECT-TYPE
--    SYNTAX      TruthValue
--    MAX-ACCESS  read-only
--    STATUS      current
--    DESCRIPTION
--        "The value of vRtrMplsLspPathIsFastRetry indicates which retry 
--         timer is being referred to by vRtrMplsLspPathRetryTimeRemaining. 
--
--         When the value of vRtrMplsLspPathIsFastRetry is set to 'true', 
--         vRtrMplsLspPathRetryTimeRemaining is referring to either the P2P
--         active path fast timer, vRtrMplsGenP2pActPathFastRetry or the
--         secondary fast retry timer, vRtrMplsGeneralSecFastRetryTimer.
--
--         When the value of vRtrMplsLspPathIsFastRetry is set to 'false', 
--         vRtrMplsLspPathRetryTimeRemaining is referring to the LSP retry timer, 
--         vRtrMplsLspRetryTimer."
--    ::= { vRtrMplsLspPathEntry 55 }
--
--vRtrMplsLspPathBackupCT        OBJECT-TYPE
--    SYNTAX      Integer32 (-1|0..7) 
--    MAX-ACCESS  read-create
--    STATUS      current
--    DESCRIPTION
--        "The value of vRtrMplsLspPathBackupCT specifies the backup class type (CT) 
--         associated with the LSP. A value of -1 indicates that no backup class type
--         has been configured for the LSP." 
--    DEFVAL { -1 }
--    ::= { vRtrMplsLspPathEntry 56 }      
--
--vRtrMplsLspPathMainCTRetryRem        OBJECT-TYPE
--    SYNTAX      Unsigned32  
--    MAX-ACCESS  read-only
--    STATUS      current
--    DESCRIPTION
--        "The value of vRtrMplsLspPathMainCTRetryRem specifies the number of
--         remaining attempts the software should make before it can start using
--         the backup class type for the LSP."
--    ::= { vRtrMplsLspPathEntry 57 }      
--
--vRtrMplsLspPathOperCT        OBJECT-TYPE
--    SYNTAX      Integer32 (-1|0..7)  
--    MAX-ACCESS  read-only
--    STATUS      current
--    DESCRIPTION
--        "The value of vRtrMplsLspMainCTRetryLimit specifies operational 
--         class type (CT) associated with the LSP. A value of -1 indicates
--         that no operational class type has been configured for the LSP"
--    ::= { vRtrMplsLspPathEntry 58 }      
--
--vRtrMplsLspPathNewPathIndex OBJECT-TYPE
--   SYNTAX        MplsTunnelIndex
--   MAX-ACCESS    read-create
--   STATUS        current
--   DESCRIPTION
--        "The value of vRtrMplsLspPathNewPathIndex specifies the index for the 
--         new path in mplsTunnelTable."
--   DEFVAL { 0 }
--   ::= { vRtrMplsLspPathEntry 59 }
--
--vRtrMplsLspPathMBBMainCTRetryRem        OBJECT-TYPE
--    SYNTAX      Unsigned32  
--    MAX-ACCESS  read-only
--    STATUS      current
--    DESCRIPTION
--        "The value of vRtrMplsLspPathMBBMainCTRetryRem indicates the number of
--         remaining attempts the software should make before it can start using
--         the backup class type for the LSP."
--    ::= { vRtrMplsLspPathEntry 60 }      
--
--vRtrMplsLspPathSigBWMBBInProg        OBJECT-TYPE
--    SYNTAX      Unsigned32
--    MAX-ACCESS  read-only
--    STATUS      current
--    DESCRIPTION
--        "The value of vRtrMplsLspPathSigBWMBBInProg indicates the bandwidth 
--         used to signal the MBB currently in progress."
--    ::= { vRtrMplsLspPathEntry 61 }
--
--vRtrMplsLspPathSigBWLastMBB        OBJECT-TYPE
--    SYNTAX      Unsigned32
--    MAX-ACCESS  read-only
--    STATUS      current
--    DESCRIPTION
--        "The value of vRtrMplsLspPathSigBWLastMBB indicates the bandwidth 
--         used to signal the last MBB that occurred."
--    ::= { vRtrMplsLspPathEntry 62 }
--
--vRtrMplsLspPathActiveByManual     OBJECT-TYPE
--    SYNTAX      INTEGER { 
--                    notApplicable (0),
--                    noForce (1),
--                    force (2)
--                }
--    MAX-ACCESS  read-only
--    STATUS      current
--    DESCRIPTION
--        "The value of vRtrMplsLspPathActiveByManual indicates whether
--         a secondary standby path has become the active LSP path 
--         due to manual intervention.  When vRtrMplsLspSwitchStbyPath is set 
--         to 'doAction' a manual switch is attempted. When
--         vRtrMplsLspSwitchStbyPathForce is set to 'true' the manual switch is
--         forced.
--
--         When the value of vRtrMplsLspPathActiveByManual is set to 
--         'notApplicable', the LSP path is active but not due to any manual 
--         intervention.
--
--         When the value of vRtrMplsLspPathActiveByManual is set to 'noForce', 
--         the LSP path has become active by a manual switch specified
--         by the user.
--
--         When the value of vRtrMplsLspPathActiveByManual is set to 'force', 
--         the LSP path has become active by a forced manual switch executed
--         by the user."
--    ::= { vRtrMplsLspPathEntry 63 }
--
--vRtrMplsLspPathTimeoutIn        OBJECT-TYPE
--    SYNTAX      Unsigned32
--    UNITS       "seconds"
--    MAX-ACCESS  read-only
--    STATUS      current
--    DESCRIPTION
--        "The value of vRtrMplsLspPathTimeoutIn specifies the amount of time
--         remaining, in seconds, for the LSP path state to time out after the
--         initial PATH message has been sent. If the timer expires and the LSP
--         path has not become operationally up, the LSP path is torn down and
--         the retry timer is started to schedule a new retry cycle."
--    ::= { vRtrMplsLspPathEntry 64 }
--
--vRtrMplsLspPathMBBTimeoutIn        OBJECT-TYPE
--    SYNTAX      Unsigned32
--    UNITS       "seconds"
--    MAX-ACCESS  read-only
--    STATUS      current
--    DESCRIPTION
--        "The value of vRtrMplsLspPathMBBTimeoutIn specifies the amount of time
--         remaining, in seconds, for the in-progress MBB path state to time out
--         after the initial PATH message has been sent. If the timer expires and
--         the in-progress MBB path has not become operationally up, the MBB path
--         is torn down and the retry timer is started to schedule a new retry
--         cycle."
--    ::= { vRtrMplsLspPathEntry 65 }
--
--  The Virtual Router MPLS LSP Path Statistics Table
--
--  Augmentation of the vRtrMplsLspPathTable.
--  Use of AUGMENTS clause implies a one-to-one dependent relationship 
--  between the base table, vRtrMplsLspPathTable, and the augmenting table, 
--  vRtrMplsLspPathStatTable. This in effect extends the vRtrMplsLspPathTable
--  with additional columns.  
--  Creation (or deletion) of a row in the vRtrMplsLspPathTable results in 
--  the same fate for the row in the vRtrMplsLspPathStatTable.
--

--vRtrMplsLspPathStatTable    OBJECT-TYPE
--    SYNTAX      SEQUENCE OF VRtrMplsLspPathStatEntry
--    MAX-ACCESS  not-accessible
--    STATUS      current
--    DESCRIPTION
--        "The vRtrMplsLspPathStatTable has an entry for an association 
--         between a Labeled Switch Path (LSP) in the vRtrMplsLspTable 
--         and a path (or tunnel) entry in the mplsTunnelTable."
--    ::= { tnMplsObjs 5 }
--
--vRtrMplsLspPathStatEntry    OBJECT-TYPE
--    SYNTAX      VRtrMplsLspPathStatEntry
--    MAX-ACCESS  not-accessible
--    STATUS      current
--    DESCRIPTION
--        "Each row entry represents a collection of statistics for 
--         an association between a Labeled Switch Path (LSP) in the 
--         vRtrMplsLspTable and a path (or tunnel) entry in the 
--         mplsTunnelTable. 
--
--         Entries cannot be created and deleted via SNMP SET operations."
--    AUGMENTS { vRtrMplsLspPathEntry }
--    ::= { vRtrMplsLspPathStatTable 1 }
--
--VRtrMplsLspPathStatEntry ::= SEQUENCE {
--    vRtrMplsLspPathTimeUp                 TimeInterval,
--    vRtrMplsLspPathTimeDown               TimeInterval,
--    vRtrMplsLspPathRetryAttempts          Unsigned32,
--    vRtrMplsLspPathTransitionCount        Counter32,
--    vRtrMplsLspPathCspfQueries            Counter32
--}
--
--vRtrMplsLspPathTimeUp   OBJECT-TYPE
--    SYNTAX      TimeInterval
--    MAX-ACCESS  read-only
--    STATUS      current
--    DESCRIPTION
--        "The total time in 10-millisecond units that this LSP path has
--         been operational.  For example, the percentage up time can be
--         determined by computing (vRtrMplsLspPathTimeUp/vRtrMplsLspAge * 100 %)."
--    ::= { vRtrMplsLspPathStatEntry 1 }
--        
--vRtrMplsLspPathTimeDown OBJECT-TYPE
--    SYNTAX      TimeInterval
--    MAX-ACCESS  read-only
--    STATUS      current
--    DESCRIPTION
--        "The total time in 10-millisecond units that this LSP Path has 
--         not been operational."
--    ::= { vRtrMplsLspPathStatEntry 2 }
--
--vRtrMplsLspPathRetryAttempts       OBJECT-TYPE
--    SYNTAX      Unsigned32
--    MAX-ACCESS  read-only
--    STATUS      current
--    DESCRIPTION
--        "The number of unsuccessful attempts which have been made to 
--         signal this path. As soon as the path gets signalled, this is
--         set to 0."
--    ::= { vRtrMplsLspPathStatEntry 3 }
--
--vRtrMplsLspPathTransitionCount    OBJECT-TYPE
--    SYNTAX      Counter32
--    MAX-ACCESS  read-only
--    STATUS      current
--    DESCRIPTION
--        "The object vRtrMplsLspPathTransitionCount maintains the number
--         of transitions that have occurred for this LSP."
--    ::= { vRtrMplsLspPathStatEntry 4 }
--
--vRtrMplsLspPathCspfQueries     OBJECT-TYPE
--    SYNTAX      Counter32
--    MAX-ACCESS  read-only
--    STATUS      current
--    DESCRIPTION
--        "The value of vRtrMplsLspPathCspfQueries specifies the number 
--         of CSPF queries that have been made for this LSP path."
--    ::= { vRtrMplsLspPathStatEntry 5 }


--
--  Virtual Router MPLS LSP to Cross-connect Mapping Table
--

-- vRtrMplsXCTable  OBJECT-TYPE
--    SYNTAX      SEQUENCE OF VRtrMplsXCEntry
--    MAX-ACCESS  not-accessible
--    STATUS      current
--    DESCRIPTION
--        "This table has an entry for each mplsXCEntry
--         in the mplsXCTable.  It serves as an another
--         indirect index to the mplsXCTable."
--    ::= { tnMplsObjs 6 }
--
--vRtrMplsXCEntry  OBJECT-TYPE
--    SYNTAX      VRtrMplsXCEntry
--    MAX-ACCESS  not-accessible
--    STATUS      current
--    DESCRIPTION
--        "An entry in this table represents the indices
--         to be used to search the mplsXCTable."
--    INDEX { tnSysSwitchId, mplsXCLspId }
--
--    ::= { vRtrMplsXCTable 1 }
--
--VRtrMplsXCEntry ::= SEQUENCE {
--    vRtrMplsXCIndex                 Integer32,
--    vRtrMplsInSegmentIfIndex        InterfaceIndexOrZero,
--    vRtrMplsInSegmentLabel          MplsLabel,
--    vRtrMplsOutSegmentIndex         Integer32,
--    vRtrMplsERHopTunnelIndex        Integer32, 
--    vRtrMplsARHopTunnelIndex        Integer32, 
--    vRtrMplsRsvpSessionIndex        Unsigned32,
--    vRtrMplsXCFailCode              TmnxMplsLspFailCode,
--    vRtrMplsXCCHopTableIndex        Integer32
--}
--
--vRtrMplsXCIndex OBJECT-TYPE
--    SYNTAX      Integer32 (1..2147483647)
--    MAX-ACCESS  read-only
--    STATUS      current
--    DESCRIPTION
--        "An index of the mplsXCTable. It represents 
--         mplsXCIndex, a field of the mplsXCTable."
--    ::= { vRtrMplsXCEntry 1 }
--
--vRtrMplsInSegmentIfIndex OBJECT-TYPE
--    SYNTAX      InterfaceIndexOrZero
--    MAX-ACCESS  read-only
--    STATUS      current
--    DESCRIPTION
--        "An index of the mplsXCTable.  It represents
--         mplsInSegmentIfIndex of the mplsInSegmentTable." 
--    ::= { vRtrMplsXCEntry 2 }
--
--vRtrMplsInSegmentLabel OBJECT-TYPE
--    SYNTAX      MplsLabel
--    MAX-ACCESS  read-only
--    STATUS      current
--    DESCRIPTION
--        "An index of the mplsXCTable. It represents 
--         mplsInSegmentLabel of the mplsInSegmentTable."
--    ::= { vRtrMplsXCEntry 3 }
--
--vRtrMplsOutSegmentIndex OBJECT-TYPE
--    SYNTAX      Integer32 (0..2147483647)
--    MAX-ACCESS  read-only
--    STATUS      current
--    DESCRIPTION
--        "An index of the mplsXCTable. It represents 
--         mplsOutSegmentIndex of the mplsOutSegmentTable."
--    ::= { vRtrMplsXCEntry 4 }
--
--vRtrMplsERHopTunnelIndex OBJECT-TYPE
--    SYNTAX      Integer32 
--    MAX-ACCESS  read-only
--    STATUS      current
--    DESCRIPTION
--        "Primary index into the mplsTunnelHopTable identifying a particular
--         recorded hop list (stores ERO in LSR)."
--    ::= { vRtrMplsXCEntry 5 }
--
--vRtrMplsARHopTunnelIndex OBJECT-TYPE
--    SYNTAX      Integer32 
--    MAX-ACCESS  read-only
--    STATUS      current
--    DESCRIPTION
--        "Primary index into the mplsTunnelARHopTable identifying a particular
--         recorded hop list (stores RRO in LSR)."
--    ::= { vRtrMplsXCEntry 6 }
--
--vRtrMplsRsvpSessionIndex OBJECT-TYPE
--    SYNTAX      Unsigned32
--    MAX-ACCESS  read-only
--    STATUS      current
--    DESCRIPTION
--        "An index into the TIMETRA-RSVP-MIB::vRtrRsvpSessionTable identifying
--         a particular RSVP session."
--    ::= { vRtrMplsXCEntry 7 }
--
--vRtrMplsXCFailCode     OBJECT-TYPE
--    SYNTAX      TmnxMplsLspFailCode
--    MAX-ACCESS  read-only
--    STATUS      current
--    DESCRIPTION
--        "The value of vRtrMplsXCFailCode specifies the reason code for
--         cross-connect failure. A value of 0 indicates that no failure 
--         occurred."
--    ::= { vRtrMplsXCEntry 8 }
--            
--vRtrMplsXCCHopTableIndex OBJECT-TYPE
--    SYNTAX      Integer32
--    MAX-ACCESS  read-only
--    STATUS      current
--    DESCRIPTION
--        "Index to the vRtrMplsTunnelCHopTable entries that specify 
--         the hops for the CSPF path for a detour LSP for this tunnel."
--    ::= { vRtrMplsXCEntry 9 }
--

--
--  Virtual Router MPLS General Table
--

vRtrMplsGeneralTable    OBJECT-TYPE
    SYNTAX      SEQUENCE OF VRtrMplsGeneralEntry
    MAX-ACCESS  not-accessible
    STATUS      current
    DESCRIPTION
        "The vRtrMplsGeneralTable contains objects for general control and
         management of an MPLS protocol instance within a virtual router."
    ::= { tnMplsObjs 7 }

vRtrMplsGeneralEntry    OBJECT-TYPE
    SYNTAX      VRtrMplsGeneralEntry
    MAX-ACCESS  not-accessible
    STATUS      current
    DESCRIPTION
        "Each row entry represents an instance of the MPLS protocol running
         within a virtual router.  Entries in this table cannot be 
         created and deleted via SNMP SET operations.  An entry in this table
         is created by the agent when vRtrMplsStatus in the vRtrConfTable is
         set to 'create'.  The entry is destroyed when vRtrMplsStatus is set
         to 'delete'"
    INDEX { tnSysSwitchId, vRtrID }
    ::= { vRtrMplsGeneralTable 1 }

VRtrMplsGeneralEntry ::= SEQUENCE {
    vRtrMplsGeneralLastChange          TimeStamp,
    vRtrMplsGeneralAdminState          TmnxAdminState,
    vRtrMplsGeneralOperState           TmnxOperState,
    vRtrMplsGeneralPropagateTtl        TruthValue,
    vRtrMplsGeneralTE                  INTEGER,
    vRtrMplsGeneralNewLspIndex         TestAndIncr,
    vRtrMplsGeneralOptimizeTimer       Unsigned32,
    vRtrMplsGeneralFRObject            TruthValue,
    vRtrMplsGeneralResignalTimer       Unsigned32,
    vRtrMplsGeneralHoldTimer           Unsigned32,
    vRtrMplsGeneralDynamicBypass       TruthValue,
    vRtrMplsGeneralNextResignal        Unsigned32,
    vRtrMplsGeneralOperDownReason      TmnxMplsOperDownReasonCode,
    vRtrMplsGeneralSrlgFrr             TruthValue,
    vRtrMplsGeneralSrlgFrrStrict       TruthValue,
    vRtrMplsGeneralNewP2mpInstIndex    TestAndIncr,
    vRtrMplsGeneralLeastFillMinThd     Unsigned32,
    vRtrMplsGenLeastFillReoptiThd      Unsigned32,
    vRtrMplsGeneralUseSrlgDB           TruthValue,
    vRtrMplsGeneralP2mpResigTimer      Unsigned32,
    vRtrMplsGeneralP2mpNextResignal    Unsigned32,        
    vRtrMplsGeneralSecFastRetryTimer   Unsigned32,
    vRtrMplsGeneralShortTTLPropLocal   TruthValue,
    vRtrMplsGeneralShortTTLPropTrans   TruthValue,
    vRtrMplsGeneralStaticLspFRTimer    Unsigned32,
    vRtrMplsGeneralAutoBWDefSampMul    Unsigned32,
    vRtrMplsGeneralAutoBWDefAdjMul     Unsigned32,
    vRtrMplsGeneralExpBackoffRetry     TruthValue,
    vRtrMplsGeneralCspfOnLooseHop      TruthValue,
    vRtrMplsGeneralP2PMaxByPassAssoc   Unsigned32,
    vRtrMplsGenP2pActPathFastRetry     Unsigned32,
    vRtrMplsGenP2mpS2lFastRetry        Unsigned32,
    vRtrMplsGenLspInitRetryTimeout     Unsigned32,
    vRtrMplsLoggerEventBundling        TruthValue,
    vRtrMplsGenIssuMplsLockdown        TruthValue
}

vRtrMplsGeneralLastChange       OBJECT-TYPE
    SYNTAX      TimeStamp
    MAX-ACCESS  read-only
    STATUS      current
    DESCRIPTION
        "The sysUpTime when this row was last modified."
    ::= { vRtrMplsGeneralEntry 1 }

vRtrMplsGeneralAdminState   OBJECT-TYPE
    SYNTAX      TmnxAdminState
    MAX-ACCESS  read-create
    STATUS      current
    DESCRIPTION
        "When vRtrMplsGeneralAdminState is set to 'inService', the agent
         attempts to enable the MPLS protocol instance on this router.
         
         When vRtrMplsGeneralAdminState is set to 'outOfService', the
         agent attempts to disable the MPLS protocol instance on this
         router."
    DEFVAL { inService }
    ::= { vRtrMplsGeneralEntry 2 }
                   
vRtrMplsGeneralOperState    OBJECT-TYPE
    SYNTAX      TmnxOperState
    MAX-ACCESS  read-only
    STATUS      current
    DESCRIPTION
        "vRtrMplsGeneralOperState indicates the current operating state
         of this MPLS protocol instance on this router."
    ::= { vRtrMplsGeneralEntry 3 }
             
vRtrMplsGeneralPropagateTtl OBJECT-TYPE
    SYNTAX      TruthValue
    MAX-ACCESS  read-create
    STATUS      current
    DESCRIPTION
        "When vRtrMplsGeneralPropagateTtl is set to 'true', for all LSPs,
         the ingress ESR writes the TTL of the IP packet in the label and 
         each transit ESR decrements the TTL in the label.  At the egress 
         ESR the TTL value from the label is written into the IP packet.
         
         When vRtrMplsGeneralPropagateTtl is set to 'false', the ingress
         ESR ignores the IP packet TTl and writes the value of 255 into
         the label, while the egress ESR does not write the label TTL
         into the IP packet.  This assumes that all ESRs have been
         configured to have vRtrMplsGeneralPropagateTtl set to 'false',
         or this may result in unpredictable behavior."
    DEFVAL { true }
    ::= { vRtrMplsGeneralEntry 4 }
        
vRtrMplsGeneralTE       OBJECT-TYPE
    SYNTAX      INTEGER {
                    none (1),
                    bgp (2),
                    bgpigp (3)
                }
    MAX-ACCESS  read-create
    STATUS      current
    DESCRIPTION
        "The value of vRtrMplsGeneralTE specifies the type of traffic
         engineering used with this MPLS instance."
    DEFVAL { none }
    ::= { vRtrMplsGeneralEntry 5 }

vRtrMplsGeneralNewLspIndex  OBJECT-TYPE
    SYNTAX      TestAndIncr
    MAX-ACCESS  read-create
    STATUS      current
    DESCRIPTION
        "This object is used to assign values to vRtrMplsLspIndex as
         described in 'Textual Conventions for SNMPv2'.  The network
         manager reads the object, and then writes the value back
         in the SET request that creates a new instance of 
         vRtrMplsLspEntry.  If the SET fails with the code 
         'inconsistentValue', then the process must be repeated.  
         If the the SET succeeds, then the object is incremented 
         and the new instance is created according to the manager's 
         directions."
    ::= { vRtrMplsGeneralEntry 6 }

vRtrMplsGeneralOptimizeTimer   OBJECT-TYPE
    SYNTAX      Unsigned32 (0..65535)
    UNITS       "seconds"
    MAX-ACCESS  read-create
    STATUS      current
    DESCRIPTION
        "The value of vRtrMplsGeneralOptimizeTimer specifies the time, in 
         seconds, the software will wait before attempting to re-optimize
         the LSPs.

         When CSPF is enabled, changes in the network topology may cause
         the existing path of a loose-hop LSP to become sub-optimal. Such
         LSPs can be re-optimized and re-routed through more optimal paths
         by recalculating the path for the LSP at periodic intervals. This
         interval is controlled by the optimize timer.
         
         A value of 0 indicates that optimization has been disabled.

         The value for vRtrMplsGeneralOptimizeTimer is by default inherited 
         by all LSPs and their paths."
    DEFVAL { 0 }
    ::= { vRtrMplsGeneralEntry 7 }

vRtrMplsGeneralFRObject   OBJECT-TYPE
    SYNTAX      TruthValue
    MAX-ACCESS  read-create
    STATUS      current
    DESCRIPTION
        "The value of vRtrMplsGeneralFRObject specifies whether fast reroute, 
         for LSPs using 'Facility Backup', is signalled with or without the
         fast reroute object. The value of vRtrMplsGeneralFRObject is ignored
         if fast reroute is disabled for the LSP or if the LSP is using
         'One-to-one Backup'.

         The value for vRtrMplsGeneralFRObject is by default inherited by
         all LSPs."
    DEFVAL { true }
    ::= { vRtrMplsGeneralEntry 8 }

vRtrMplsGeneralResignalTimer   OBJECT-TYPE
    SYNTAX      Unsigned32 (0|30..10080)
    UNITS       "minutes"
    MAX-ACCESS  read-create
    STATUS      current
    DESCRIPTION
        "The value of vRtrMplsGeneralResignalTimer specifies the value 
         for the P2P (point-to-point) LSP resignal timer, that is the time, in minutes, the 
         software will wait before attempting to resignal the P2P LSPs. 

         When the resignal timer expires, if the new recorded hop list
         (RRO) for an P2P LSP has a better metric than the current recorded 
         hop list, an attempt will be made to resignal that P2P LSP using
         the make-before-break mechanism. If the attempt to resignal
         an P2P LSP fails, the P2P LSP will continue to use the existing path 
         and a resignal will be attempted the next time the timer expires.
         
         A value of 0 for the resignal timer indicates that timer-based
         P2P LSP resignalling has been disabled."
    DEFVAL { 0 }
    ::= { vRtrMplsGeneralEntry 9 }

vRtrMplsGeneralHoldTimer   OBJECT-TYPE
    SYNTAX      Unsigned32 (0..10)
    UNITS       "seconds"
    MAX-ACCESS  read-create
    STATUS      current
    DESCRIPTION
        "The value of vRtrMplsGeneralHoldTimer specifies the time, in 
        seconds, for which the ingress node holds a bit before 
        programming its data plane and declaring the lsp up to 
        the service module. 
        
        A value of 0 indicates that the hold timer has been disabled."       
    DEFVAL { 1 }
    ::= { vRtrMplsGeneralEntry 10 }

vRtrMplsGeneralDynamicBypass   OBJECT-TYPE
    SYNTAX      TruthValue
    MAX-ACCESS  read-create
    STATUS      current
    DESCRIPTION
        "The value of vRtrMplsGeneralDynamicBypass specifies whether 
         dynamic bypass tunnels are enabled.  

         By default, dynamic bypass tunnels are enabled."
    DEFVAL { true }
    ::= { vRtrMplsGeneralEntry 11 }

vRtrMplsGeneralNextResignal   OBJECT-TYPE
    SYNTAX      Unsigned32
    MAX-ACCESS  read-only
    STATUS      current
    DESCRIPTION
        "The value of vRtrMplsGeneralNextResignal indicates the time 
        remaining, in minutes, for the vRtrMplsGeneralResignalTimer to expire."
    ::= { vRtrMplsGeneralEntry 12 }

vRtrMplsGeneralOperDownReason   OBJECT-TYPE
    SYNTAX      TmnxMplsOperDownReasonCode
    MAX-ACCESS  read-only
    STATUS      current
    DESCRIPTION
        "The value of vRtrMplsGeneralOperDownReason indicates the reason 
         due to which the MPLS instance is operationally down." 
    ::= { vRtrMplsGeneralEntry 13 }

vRtrMplsGeneralSrlgFrr   OBJECT-TYPE
    SYNTAX      TruthValue
    MAX-ACCESS  read-create
    STATUS      current
    DESCRIPTION
        "The value of vRtrMplsGeneralSrlgFrr specifies whether Shared Risk
         Link Group (SRLG) constraint will be used in the computation of 
         FRR bypass or detour to be associated with any primary LSP path 
         on the system.  When the value of vRtrMplsGeneralSrlgFrr is 
         'true' the use of SRLG constraint is enabled. 

         By default, the use of SRLG constraint is disabled."
    DEFVAL { false }
    ::= { vRtrMplsGeneralEntry 14 }

vRtrMplsGeneralSrlgFrrStrict   OBJECT-TYPE
    SYNTAX      TruthValue
    MAX-ACCESS  read-create
    STATUS      current
    DESCRIPTION
        "The value of vRtrMplsGeneralSrlgFrrStrict specifies whether 
         to associate the LSP with a bypass or signal a detour if a 
         bypass or detour satisfies all other constraints except the SRLG 
         constraints.  When the value of vRtrMplsGeneralSrlgFrrStrict is
         'true' and a path that meets SRLG constraints is not found, the 
         bypass or detour is not setup. If this value is set to 'true'
         when vRtrMplsGeneralSrlgFrr is set to 'false', vRtrMplsGeneralSrlgFrr
         is set to 'true' also.

         By default, the value of vRtrMplsGeneralSrlgFrrStrict is 'false'."
    DEFVAL { false }
    ::= { vRtrMplsGeneralEntry 15 }

vRtrMplsGeneralNewP2mpInstIndex  OBJECT-TYPE
    SYNTAX      TestAndIncr
    MAX-ACCESS  read-create
    STATUS      current
    DESCRIPTION
        "The value of vRtrMplsGeneralNewP2mpInstIndex specifies the object that is used to assign
        values to vRtrMplsP2mpInstIndex as described in 'Textual Conventions for SNMPv2'.  The 
        network manager reads the object, and then writes the value back in the SET request that 
        creates a new instance of vRtrMplsP2mpInstEntry.  If the SET fails with the code 
        'inconsistentValue', then the process must be repeated.  If the the SET succeeds, then the 
        object is incremented and the new instance is created according to the manager's 
        directions."
    ::= { vRtrMplsGeneralEntry 16 }   

vRtrMplsGeneralLeastFillMinThd  OBJECT-TYPE
    SYNTAX      Unsigned32 (1..100)
    MAX-ACCESS  read-create
    STATUS      current
    DESCRIPTION
        "The value of vRtrMplsGeneralLeastFillMinThd specifies in percentage the least 
        minimum threshold parameter used in the least-fill path selection process. When 
        comparing the percentage of least available link bandwidth across the sorted paths, 
        whenever two percentages differ by less than the value configured as the
        vRtrMplsGeneralLeastFillMinThd, CSPF will consider them equal and will apply a random 
        number generator to select the path among these paths. "
    DEFVAL { 5 }    
    ::= { vRtrMplsGeneralEntry 17 }       
       
vRtrMplsGenLeastFillReoptiThd  OBJECT-TYPE
    SYNTAX      Unsigned32 (1..100)
    MAX-ACCESS  read-create
    STATUS      current
    DESCRIPTION
        "The value of vRtrMplsGenLeastFillReoptiThd specifies in percentage the least 
        reoptimization threshold parameter used in the least-fill path selection process.

        During a timer-based re-signaling of an LSP path which has 
        vRtrMplsLspLeastFill enabled, CSPF will first update the least-available bandwidth figure 
        for the current path of this LSP. It then applies the least-fill path 
        selection method to select a new path for this LSP. If the new computed path 
        has the same cost as the current path, it will compare the least-available 
        bandwidth figures of the two paths and if the difference exceeds 
        vRtrMplsGenLeastFillReoptiThd, a trap will be generated to indicate that 
        a better least-fill path is available for this LSP. "
    DEFVAL { 10 }    
    ::= { vRtrMplsGeneralEntry 18 }    

vRtrMplsGeneralUseSrlgDB   OBJECT-TYPE
    SYNTAX      TruthValue
    MAX-ACCESS  read-create
    STATUS      current
    DESCRIPTION
        "The value of vRtrMplsGeneralUseSrlgDB specifies whether the use of the user SRLG 
         database by CSPF is enabled."
    DEFVAL { false }
    ::= { vRtrMplsGeneralEntry 19}

vRtrMplsGeneralP2mpResigTimer   OBJECT-TYPE
    SYNTAX      Unsigned32 (0|60..10080)
    UNITS       "minutes"
    MAX-ACCESS  read-create
    STATUS      current
    DESCRIPTION
        "The value of vRtrMplsGeneralP2mpResigTimer specifies the value 
         for the P2MP (point to multi point) LSP resignal timer, that is the time, 
         in minutes, the software will wait before attempting to resignal the 
         P2MP LSPs. 

         When the resignal timer expires, an attempt to resignal the entire P2MP 
         instance comprising all source to leaf (S2Ls) are done, the IGP or TE metric
         of the S2Ls are not taken into consideration.

         If the attempt to resignal an P2MP LSP fails, the P2MP LSP will continue to use the
         existing S2Ls and a resignal will be attempted the next time the timer expires.
         
         A value of 0 for the resignal timer indicates that timer-based P2MP
         LSP resignalling has been disabled."
    DEFVAL { 0 }
    ::= { vRtrMplsGeneralEntry 20 }    

vRtrMplsGeneralP2mpNextResignal   OBJECT-TYPE
    SYNTAX      Unsigned32
    MAX-ACCESS  read-only
    STATUS      current
    DESCRIPTION
        "The value of vRtrMplsGeneralP2mpNextResignal indicates the time 
        remaining, in minutes, for the vRtrMplsGeneralP2mpResigTimer to expire."
    ::= { vRtrMplsGeneralEntry 21 }    

vRtrMplsGeneralSecFastRetryTimer    OBJECT-TYPE
    SYNTAX      Unsigned32 (0..10)
    UNITS       "seconds"
    MAX-ACCESS  read-create
    STATUS      current
    DESCRIPTION
        "The value of vRtrMplsGeneralSecFastRetryTimer specifies the value, in 
         seconds, used as fast retry timer for a secondary path. If the first 
         attempt to setup a secondary path fails due to a path error, the fast 
         retry timer will be started for the secondary path so that the path can
         be retried sooner. If the next attempt also fails, further retries for 
         the path will use the configured value for LSP retry timer, 
         vRtrMplsLspRetryTimer.

         If retry-timer for the LSP is configured to be less than the MPLS
         secondary-fast-retry-timer, all retries for the secondary path will 
         use the LSP retry-timer.

         A value of 0 indicates that fast retry for secondary paths has been 
         disabled."
    DEFVAL { 0 }
    ::= { vRtrMplsGeneralEntry 22 }

vRtrMplsGeneralShortTTLPropLocal   OBJECT-TYPE
    SYNTAX      TruthValue
    MAX-ACCESS  read-create
    STATUS      current
    DESCRIPTION
        "The value of vRtrMplsGeneralShortTTLPropLocal specifies whether or not
         to enable the propagation of time to live (TTL) from the IP packet
         header into the header of the resulting MPLS packet for all local 
         packets forwarded over a LSP shortcut. When the value is 'true' TTL 
         is propagated from the IP packet header into the header of the
         resulting MPLS packet."
    DEFVAL { true }    
    ::= { vRtrMplsGeneralEntry 23 }    

vRtrMplsGeneralShortTTLPropTrans   OBJECT-TYPE
    SYNTAX      TruthValue
    MAX-ACCESS  read-create
    STATUS      current
    DESCRIPTION
        "The value of vRtrMplsGeneralShortTTLPropTrans specifies whether or not
         to enable the propagation of time to live (TTL) from the IP packet
         header into the header of the resulting MPLS packet for all transit 
         packets forwarded over a LSP shortcut. When the value is 'true' TTL 
         is propagated from the IP packet header into the header of the
         resulting MPLS packet."
    DEFVAL { true }    
    ::= { vRtrMplsGeneralEntry 24 }    

vRtrMplsGeneralStaticLspFRTimer     OBJECT-TYPE
    SYNTAX      Unsigned32 (1..30)
    UNITS       "seconds"
    MAX-ACCESS  read-create
    STATUS      current
    DESCRIPTION
        "The value of vRtrMplsGeneralStaticLspFRTimer specifies the audit time
         for static LSPs which are not currently up."
    DEFVAL { 30 }
    ::= { vRtrMplsGeneralEntry 25 }

vRtrMplsGeneralAutoBWDefSampMul     OBJECT-TYPE
    SYNTAX      Unsigned32 (1..511)
    MAX-ACCESS  read-create
    STATUS      current
    DESCRIPTION
        "The value of vRtrMplsGeneralAutoBWDefSampMul specifies the global
         default for collection intervals in a sample interval."
    DEFVAL { 1 }
    ::= { vRtrMplsGeneralEntry 26 }

vRtrMplsGeneralAutoBWDefAdjMul     OBJECT-TYPE
    SYNTAX      Unsigned32 (1..16383)
    MAX-ACCESS  read-create
    STATUS      current
    DESCRIPTION
        "The value of vRtrMplsGeneralAutoBWDefAdjMul specifies the global
         default for collection intervals in an adjust interval."
    DEFVAL { 288 }
    ::= { vRtrMplsGeneralEntry 27 }

vRtrMplsGeneralExpBackoffRetry     OBJECT-TYPE
    SYNTAX      TruthValue
    MAX-ACCESS  read-create
    STATUS      current
    DESCRIPTION
        "The value of vRtrMplsGeneralExpBackoffRetry specifies the state of
         Exponential Backoff Retry mechanism."
    DEFVAL { false }
    ::= { vRtrMplsGeneralEntry 28 }   

vRtrMplsGeneralCspfOnLooseHop     OBJECT-TYPE
    SYNTAX      TruthValue
    MAX-ACCESS  read-create
    STATUS      current
    DESCRIPTION
        "The value of vRtrMplsGeneralCspfOnLooseHop specifies whether the 
         Constrained Shortest Path First (CSPF) calculation till the next 
         loose hop is enabled or not."
    DEFVAL { false }
    ::= { vRtrMplsGeneralEntry 29 }

vRtrMplsGeneralP2PMaxByPassAssoc     OBJECT-TYPE
    SYNTAX      Unsigned32 (100..131072)
    MAX-ACCESS  read-create
    STATUS      current
    DESCRIPTION
        "The value of vRtrMplsGeneralP2PMaxByPassAssoc specifies the maximum
        number of LSP primary paths that can associate with each manual or
        dynamic bypass point-to-point (P2P) LSP."
    DEFVAL { 1000 }
    ::= { vRtrMplsGeneralEntry 30 }

vRtrMplsGenP2pActPathFastRetry    OBJECT-TYPE
    SYNTAX      Unsigned32 (0..10)
    UNITS       "seconds"
    MAX-ACCESS  read-create
    STATUS      current
    DESCRIPTION
        "The value of vRtrMplsGenP2pActPathFastRetry specifies the time, in
         seconds, active path point-to-point (P2P) LSP waits before it attempts
         to re-establish itself. This timer is started after first attempt to
         setup active path P2P LSP fails.
        
         When vRtrMplsGenP2pActPathFastRetry is set to 0, fast retry timer
         for active path P2P LSP is disabled."

    DEFVAL { 0 }
    ::= { vRtrMplsGeneralEntry 31 }

vRtrMplsGenP2mpS2lFastRetry    OBJECT-TYPE
    SYNTAX      Unsigned32 (0..10)
    UNITS       "seconds"
    MAX-ACCESS  read-create
    STATUS      current
    DESCRIPTION
        "The value of vRtrMplsGenP2mpS2lFastRetry specifies the time, in
         seconds, active path point to multipoint (P2MP) source to leaf (S2L)
         LSP waits before it attempts to re-establish itself. This timer is
         started after first attempt to setup active path P2MP S2L LSP fails.
        
         When vRtrMplsGenP2mpS2lFastRetry is set to 0, fast retry timer
         for active path P2MP S2L LSP is disabled."

    DEFVAL { 0 }
    ::= { vRtrMplsGeneralEntry 32 }

vRtrMplsGenLspInitRetryTimeout    OBJECT-TYPE
    SYNTAX      Unsigned32 (10..600)
    UNITS       "seconds"
    MAX-ACCESS  read-create
    STATUS      current
    DESCRIPTION
        "The value of vRtrMplsGenLspInitRetryTimeout specifies the amount of
         time in seconds the software waits for an LSP path to come up after
         sending out the initial Path message. If the initial retry timeout
         period expires and the LSP path is not up, it is torn down and the LSP
         retry timer is started to schedule a new retry cycle using a new
         LSP-id."

    DEFVAL { 30 }
    ::= { vRtrMplsGeneralEntry 33 }

vRtrMplsLoggerEventBundling   OBJECT-TYPE
    SYNTAX      TruthValue
    MAX-ACCESS  read-create
    STATUS      current
    DESCRIPTION
        "The value of vRtrMplsLoggerEventBundling specifies whether or not
         the notification bundling mechanism is enabled.
 
         When the value of vRtrMplsLoggerEventBundling is set to 'true',
         all TIMETRA-SYSTEM-MIB::tmnxConfigCreate and 
         TIMETRA-SYSTEM-MIB::tmnxConfigDelete notifications that are generated
         because of creation or deletion of entries in the vRtrMplsXCTable 
         during quiet period of 2 minutes are bundled in a single notification.

         An entry is created or deleted in vRtrMplsXCTable when a RSVP session
         is created or deleted on this ingress, transit or egress router
         instance causing creation or deletion of an entry in
         TIMETRA-RSVP-MIB::vRtrRsvpSessionTable.
 
         A vRtrMplsXCBundleChange notification is generated after every quiet
         interval of 2 minutes if one or more RSVP session changed state and 
         retained that state during the quiet interval. However if the state of
         the RSVP sessions does not remain stable for an entire quiet interval,
         the notification is generated after the maximum interval period of 10
         minutes has elapsed."
    DEFVAL { false }
    ::= { vRtrMplsGeneralEntry 34 }

vRtrMplsGenIssuMplsLockdown     OBJECT-TYPE
    SYNTAX      TruthValue
    MAX-ACCESS  read-only
    STATUS      current
    DESCRIPTION
        "The value of vRtrMplsGenIssuMplsLockdown indicates if MPLS has entered 
         the state of not accepting new requests for creation of 
         LSP's(local/transit) during the minor ISSU(In Service Software Update) 
         operation."
    ::= { vRtrMplsGeneralEntry 39 }

--
--  Virtual Router MPLS General Statistics Table
--
--  Augmentation of the vRtrMplsGeneralTable.
--  Use of AUGMENTS clause implies a one-to-one dependent relationship 
--  between the base table, vRtrMplsGeneralTable, and the augmenting table, 
--  vRtrMplsGeneralStatTable. This in effect extends the vRtrMplsGeneralTable
--  with additional columns.  
--  Creation (or deletion) of a row in the vRtrMplsGeneralTable results in 
--  the same fate for the row in the vRtrMplsGeneralStatTable.
--

--vRtrMplsGeneralStatTable    OBJECT-TYPE
--    SYNTAX      SEQUENCE OF VRtrMplsGeneralStatEntry
--    MAX-ACCESS  not-accessible
--    STATUS      current
--    DESCRIPTION
--        "The vRtrMplsGeneralStatTable contains statistics for an MPLS 
--         protocol instance within a virtual router."
--    ::= { tnMplsObjs 8 }
--
--vRtrMplsGeneralStatEntry    OBJECT-TYPE
--    SYNTAX      VRtrMplsGeneralStatEntry
--    MAX-ACCESS  not-accessible
--    STATUS      current
--    DESCRIPTION
--        "Each row entry represents a collection of statistics for an 
--         instance of the MPLS protocol running within a virtual router.
--
--         Entries cannot be created and deleted via SNMP SET operations."
--    AUGMENTS { vRtrMplsGeneralEntry }
--    ::= { vRtrMplsGeneralStatTable 1 }
--
--VRtrMplsGeneralStatEntry ::= SEQUENCE {
--    vRtrMplsGeneralStaticLspOriginate  Gauge32,
--    vRtrMplsGeneralStaticLspTransit    Gauge32,
--    vRtrMplsGeneralStaticLspTerminate  Gauge32,
--    vRtrMplsGeneralDynamicLspOriginate Gauge32,
--    vRtrMplsGeneralDynamicLspTransit   Gauge32,
--    vRtrMplsGeneralDynamicLspTerminate Gauge32,
--    vRtrMplsGeneralDetourLspOriginate  Gauge32,
--    vRtrMplsGeneralDetourLspTransit    Gauge32,
--    vRtrMplsGeneralDetourLspTerminate  Gauge32,
--    vRtrMplsGeneralS2lOriginate        Gauge32,
--    vRtrMplsGeneralS2lTransit          Gauge32,
--    vRtrMplsGeneralS2lTerminate        Gauge32,
--    vRtrMplsGeneralLspEgrStatCount     Counter32,
--    vRtrMplsGeneralLspIgrStatCount     Counter32,
--    vRtrMplsGenMplsTpLspOriginate      Gauge32,
--    vRtrMplsGenMplsTpLspTransit        Gauge32,
--    vRtrMplsGenMplsTpLspTerminate      Gauge32,
--    vRtrMplsGenMplsTpOrigPathInst      Gauge32,
--    vRtrMplsGenMplsTpTranPathInst      Gauge32,
--    vRtrMplsGenMplsTpTermPathInst      Gauge32
--}
--
--vRtrMplsGeneralStaticLspOriginate  OBJECT-TYPE
--    SYNTAX      Gauge32
--    MAX-ACCESS  read-only
--    STATUS      current
--    DESCRIPTION
--        "The value of vRtrMplsGeneralStaticLspOriginate indicates the number of static LSPs that 
--        originate at this virtual router."
--    ::= { vRtrMplsGeneralStatEntry 1 }
--
--vRtrMplsGeneralStaticLspTransit    OBJECT-TYPE
--    SYNTAX      Gauge32
--    MAX-ACCESS  read-only
--    STATUS      current
--    DESCRIPTION
--        "The value of vRtrMplsGeneralStaticLspTransit indicates the number of static LSPs that 
--        transit through this virtual router."
--    ::= { vRtrMplsGeneralStatEntry 2 }
--
--vRtrMplsGeneralStaticLspTerminate  OBJECT-TYPE
--    SYNTAX      Gauge32
--    MAX-ACCESS  read-only
--    STATUS      current
--    DESCRIPTION
--        "The value of vRtrMplsGeneralStaticLspTerminate indicates the number of static LSPs that 
--        terminate at this virtual router."
--    ::= { vRtrMplsGeneralStatEntry 3 }
--
--vRtrMplsGeneralDynamicLspOriginate  OBJECT-TYPE
--    SYNTAX      Gauge32
--    MAX-ACCESS  read-only
--    STATUS      current
--    DESCRIPTION
--        "The value of vRtrMplsGeneralDynamicLspOriginate indicates the number of dynamic LSPs 
--        that originate at this virtual router."
--    ::= { vRtrMplsGeneralStatEntry 4 }
--
--vRtrMplsGeneralDynamicLspTransit    OBJECT-TYPE
--    SYNTAX      Gauge32
--    MAX-ACCESS  read-only
--    STATUS      current
--    DESCRIPTION
--        "The value of vRtrMplsGeneralDynamicLspTransit indicates the number of dynamic LSPs 
--        that transit  through this virtual router."
--    ::= { vRtrMplsGeneralStatEntry 5 }
--
--vRtrMplsGeneralDynamicLspTerminate  OBJECT-TYPE
--    SYNTAX      Gauge32
--    MAX-ACCESS  read-only
--    STATUS      current
--    DESCRIPTION
--        "The value of vRtrMplsGeneralDynamicLspTerminate indicates the number of dynamic LSPs
--        that terminate at this virtual router."
--    ::= { vRtrMplsGeneralStatEntry 6 }
--
--vRtrMplsGeneralDetourLspOriginate  OBJECT-TYPE
--    SYNTAX      Gauge32
--    MAX-ACCESS  read-only
--    STATUS      current
--    DESCRIPTION
--        "The value of vRtrMplsGeneralDetourLspOriginate indicates the number of detour LSPs 
--        that originate at this virtual router."
--    ::= { vRtrMplsGeneralStatEntry 7 }
--
--vRtrMplsGeneralDetourLspTransit    OBJECT-TYPE
--    SYNTAX      Gauge32
--    MAX-ACCESS  read-only
--    STATUS      current
--    DESCRIPTION
--        "The value of vRtrMplsGeneralDetourLspTransit indicates the number of detour LSPs 
--        that transit through this virtual router."
--    ::= { vRtrMplsGeneralStatEntry 8 }
--
--vRtrMplsGeneralDetourLspTerminate  OBJECT-TYPE
--    SYNTAX      Gauge32
--    MAX-ACCESS  read-only
--    STATUS      current
--    DESCRIPTION
--        "The value of vRtrMplsGeneralDetourLspTerminate indicates the number of detour LSPs 
--        that terminate at this virtual router."
--    ::= { vRtrMplsGeneralStatEntry 9 }
--
--vRtrMplsGeneralS2lOriginate  OBJECT-TYPE
--    SYNTAX      Gauge32
--    MAX-ACCESS  read-only
--    STATUS      current
--    DESCRIPTION
--        "The value of vRtrMplsGeneralS2lOriginate indicates the number of source to leaf (S2L) 
--         sub LSP path called as S2L here that originate at this virtual router."
--    ::= { vRtrMplsGeneralStatEntry 10 }
--
--vRtrMplsGeneralS2lTransit    OBJECT-TYPE
--    SYNTAX      Gauge32
--    MAX-ACCESS  read-only
--    STATUS      current
--    DESCRIPTION
--        "The value of vRtrMplsGeneralS2lOriginate indicates the number of S2Ls that 
--        transit  through this virtual router."
--    ::= { vRtrMplsGeneralStatEntry 11 }
--
--vRtrMplsGeneralS2lTerminate  OBJECT-TYPE
--    SYNTAX      Gauge32
--    MAX-ACCESS  read-only
--    STATUS      current
--    DESCRIPTION
--        "The value of vRtrMplsGeneralS2lOriginate indicates the number of S2Ls that 
--        terminate at this virtual router."         
--    ::= { vRtrMplsGeneralStatEntry 12 }
--
--vRtrMplsGeneralLspEgrStatCount  OBJECT-TYPE
--    SYNTAX      Counter32
--    MAX-ACCESS  read-only
--    STATUS      current
--    DESCRIPTION
--        "The value of vRtrMplsGeneralLspEgrStatCount indicates the number of LSP egress
--         statistics configured on this virtual router." 
--    ::= { vRtrMplsGeneralStatEntry 13 }
--
--vRtrMplsGeneralLspIgrStatCount  OBJECT-TYPE
--    SYNTAX      Counter32
--    MAX-ACCESS  read-only
--    STATUS      current
--    DESCRIPTION
--        "The value of vRtrMplsGeneralLspIgrStatCount indicates the number of LSP ingress 
--         statistics configured on this virtual router."         
--    ::= { vRtrMplsGeneralStatEntry 14 }
--vRtrMplsGenMplsTpLspOriginate  OBJECT-TYPE
--    SYNTAX      Gauge32
--    MAX-ACCESS  read-only
--    STATUS      current
--    DESCRIPTION
--        "The value of vRtrMplsGenMplsTpLspOriginate indicates the number of 
--         MPLS TP LSPs that originate at this virtual router."
--    ::= { vRtrMplsGeneralStatEntry 15 }
--
--vRtrMplsGenMplsTpLspTransit    OBJECT-TYPE
--    SYNTAX      Gauge32
--    MAX-ACCESS  read-only
--    STATUS      current
--    DESCRIPTION
--        "The value of vRtrMplsGenMplsTpLspTransit indicates the number of 
--         MPLS TP LSPs that transit through this virtual router."
--    ::= { vRtrMplsGeneralStatEntry 16 }
--
--vRtrMplsGenMplsTpLspTerminate  OBJECT-TYPE
--    SYNTAX      Gauge32
--    MAX-ACCESS  read-only
--    STATUS      current
--    DESCRIPTION
--        "The value of vRtrMplsGenMplsTpLspTerminate indicates the number of 
--         MPLS TP LSPs that terminate at this virtual router."
--    ::= { vRtrMplsGeneralStatEntry 17 }
--
--vRtrMplsGenMplsTpOrigPathInst  OBJECT-TYPE
--    SYNTAX      Gauge32
--    MAX-ACCESS  read-only
--    STATUS      current
--    DESCRIPTION
--        "The value of vRtrMplsGenMplsTpOrigPathInst indicates the number of 
--         MPLS TP LSPs originate path instances."
--    ::= { vRtrMplsGeneralStatEntry 18 }
--
--vRtrMplsGenMplsTpTranPathInst  OBJECT-TYPE
--    SYNTAX      Gauge32
--    MAX-ACCESS  read-only
--    STATUS      current
--    DESCRIPTION
--        "The value of vRtrMplsGenMplsTpTranPathInst indicates the number of 
--         MPLS TP LSPs transit path instances."
--    ::= { vRtrMplsGeneralStatEntry 19 }
--
--vRtrMplsGenMplsTpTermPathInst  OBJECT-TYPE
--    SYNTAX      Gauge32
--    MAX-ACCESS  read-only
--    STATUS      current
--    DESCRIPTION
--        "The value of vRtrMplsGenMplsTpTermPathInst indicates the number of 
--         MPLS TP LSPs terminated path instances."
--    ::= { vRtrMplsGeneralStatEntry 20 }


--
--  Virtual Router MPLS Interface Table
--

vRtrMplsIfTable OBJECT-TYPE
    SYNTAX      SEQUENCE OF VRtrMplsIfEntry
    MAX-ACCESS  not-accessible
    STATUS      current
    DESCRIPTION
        "The vRtrMplsIfTable has an entry for each router interface 
         configured for MPLS in the system."
    ::= { tnMplsObjs 9 }

vRtrMplsIfEntry      OBJECT-TYPE
    SYNTAX      VRtrMplsIfEntry
    MAX-ACCESS  not-accessible
    STATUS      current
    DESCRIPTION
        "Each row entry represents an interface on this virtual router
         that participates in the MPLS protocol.  A row cannot be created
         or deleted via SNMP SET requests.  A row with default attribute
         values is created by setting the vRtrIfEntry attribute, 
         vRtrIfMplsStatus, to 'create'.  A row is removed if 
         vRtrIfMplsStatus is set to 'delete'.  However, an attempt to 
         destroy a row will fail if vRtrMplsIfAdminState has
         not first been set to 'outOfService'."
    INDEX { tnSysSwitchId, vRtrID, vRtrIfIndex }
    ::= { vRtrMplsIfTable 1 }

VRtrMplsIfEntry ::= SEQUENCE {
    vRtrMplsIfAdminState        TmnxAdminState,
    vRtrMplsIfOperState         TmnxOperState,
    vRtrMplsIfAdminGroup        Unsigned32,
    vRtrMplsIfTeMetric          Unsigned32
}

vRtrMplsIfAdminState OBJECT-TYPE
    SYNTAX      TmnxAdminState
    MAX-ACCESS  read-create
    STATUS      current
    DESCRIPTION
        "The desired administrative state for the MPLS protocol
         running on this MPLS interface."
    DEFVAL { outOfService }
    ::= { vRtrMplsIfEntry 1 }

vRtrMplsIfOperState  OBJECT-TYPE
    SYNTAX      TmnxOperState
    MAX-ACCESS  read-only
    STATUS      current
    DESCRIPTION
        "This variable indicates the current status of the MPLS protocol
         running on this MPLS interface. When the TIMETRA-VRTR-MIB::vRtrIfPortID
         object of this interface is set to a loopback port identifier, the 
         operational state is not relevant and an SNMP GET request on this 
         object will return 'unknown'."
    ::= { vRtrMplsIfEntry 2 }

vRtrMplsIfAdminGroup  OBJECT-TYPE
    SYNTAX      Unsigned32
    MAX-ACCESS  read-create
    STATUS      current
    DESCRIPTION
        "The value of vRtrMplsIfAdminGroup is a bit-map that identifies the
         admin groups to which the interface belongs. If bit 'n' is set,
         then the interface belongs to the admin group with value 'n'. 
         
         By default, the interface does not belong to any admin groups."
    DEFVAL { '00000000'H }
    ::= { vRtrMplsIfEntry 3 }

vRtrMplsIfTeMetric  OBJECT-TYPE
    SYNTAX      Unsigned32 (0|1..16777215)
    MAX-ACCESS  read-create
    STATUS      current
    DESCRIPTION        
        "The value of vRtrMplsIfTeMetric specifies the traffic engineering metric
         for this interface. The TE metric is exchanged in addition to the IGP 
         metric by the IGPs. Depending on the value configured for 
         vRtrMplsLspCspfTeMetricEnabled, either the TE metric or the native 
         IGP metric is used in CSPF computations of the LSP paths. The maximum 
         value that can be configured is a 24 bit value."
    DEFVAL { 0 }
    ::= { vRtrMplsIfEntry 4 }

--
--   Virtual Router MPLS Interface Statistics Table
--
--  Augmentation of the vRtrMplsIfTable.
--  Use of AUGMENTS clause implies a one-to-one dependent relationship 
--  between the base table, vRtrMplsIfTable, and the augmenting table, 
--  vRtrMplsIfStatTable. This in effect extends the vRtrMplsIfTable 
--  with additional columns.  
--  Creation (or deletion) of a row in the vRtrMplsIfTable results in 
--  the same fate for the row in the vRtrMplsIfStatTable.
--

vRtrMplsIfStatTable    OBJECT-TYPE
    SYNTAX      SEQUENCE OF VRtrMplsIfStatEntry
    MAX-ACCESS  not-accessible
    STATUS      current
    DESCRIPTION
        "The vRtrMplsIfStatTable has an entry for each router interface 
         configured for MPLS in the system."
    ::= { tnMplsObjs 10 }

vRtrMplsIfStatEntry    OBJECT-TYPE
    SYNTAX      VRtrMplsIfStatEntry
    MAX-ACCESS  not-accessible
    STATUS      current
    DESCRIPTION
        "Each row entry represents a collection of statistics for an
         interface on this virtual router that participates in the 
         MPLS protocol.  

         Entries cannot be created and deleted via SNMP SET operations."
    AUGMENTS { vRtrMplsIfEntry }
    ::= { vRtrMplsIfStatTable 1 }

VRtrMplsIfStatEntry ::= SEQUENCE {
    vRtrMplsIfTxPktCount        Counter64,
    vRtrMplsIfRxPktCount        Counter64,
    vRtrMplsIfTxOctetCount      Counter64,
    vRtrMplsIfRxOctetCount      Counter64
}

vRtrMplsIfTxPktCount    OBJECT-TYPE
    SYNTAX      Counter64
    MAX-ACCESS  read-only
    STATUS      current
    DESCRIPTION
        "The total number of MPLS labeled packets transmitted from this
         interface."
    ::= { vRtrMplsIfStatEntry 1 }

vRtrMplsIfRxPktCount    OBJECT-TYPE
    SYNTAX      Counter64
    MAX-ACCESS  read-only
    STATUS      current
    DESCRIPTION
        "The total number of MPLS labeled packets received on this
         interface."
    ::= { vRtrMplsIfStatEntry 2 }

vRtrMplsIfTxOctetCount  OBJECT-TYPE
    SYNTAX      Counter64
    MAX-ACCESS  read-only
    STATUS      current
    DESCRIPTION
        "The total number of bytes in MPLS labeled packets transmitted
         on this interface."
    ::= { vRtrMplsIfStatEntry 3 }

vRtrMplsIfRxOctetCount  OBJECT-TYPE
    SYNTAX      Counter64
    MAX-ACCESS  read-only
    STATUS      current
    DESCRIPTION
        "The total number of bytes in MPLS labeled packets received on
         this interface."
    ::= { vRtrMplsIfStatEntry 4 }

--
--   Virtual Router MPLS Tunnel AR Hop Table
--
--  Augmentation of the mplsTunnelARHopEntry.
--  Use of AUGMENTS clause implies a one-to-one dependent relationship 
--  between the base table, mplsTunnelARHopEntry, and the augmenting table, 
--  vRtrMplsTunnelARHopTable. This in effect extends the mplsTunnelARHopEntry
--  with additional columns.  
--  Creation (or deletion) of a row in the mplsTunnelARHopEntry results in 
--  the same fate for the row in the vRtrMplsTunnelARHopTable.
--

--vRtrMplsTunnelARHopTable OBJECT-TYPE
--    SYNTAX      SEQUENCE OF VRtrMplsTunnelARHopEntry
--    MAX-ACCESS  not-accessible
--    STATUS      current
--    DESCRIPTION
--        "The vRtrMplsTunnelARHopTable augments the mplsTunnelARHopEntry  
--         in the MPLS-TE-MIB."
--    ::= { tnMplsObjs 11 }
--
--vRtrMplsTunnelARHopEntry OBJECT-TYPE
--    SYNTAX      VRtrMplsTunnelARHopEntry
--    MAX-ACCESS  not-accessible
--    STATUS      current
--    DESCRIPTION
--        "A row entry in this table corresponds to a row entry in the 
--         mplsTunnelARHopTable and adds to the information contained in 
--         that table"
--    AUGMENTS { mplsTunnelARHopEntry }
--    ::= { vRtrMplsTunnelARHopTable 1 }
--
--VRtrMplsTunnelARHopEntry ::= SEQUENCE {
--    vRtrMplsTunnelARHopProtection       BITS,
--    vRtrMplsTunnelARHopRecordLabel      MplsLabel,
--    vRtrMplsTunnelARHopRouterId         IpAddress
--}
--
--vRtrMplsTunnelARHopProtection OBJECT-TYPE
--    SYNTAX      BITS {
--                    localAvailable (0),
--                    localInUse (1),
--                    bandwidthProtected (2),
--                    nodeProtected (3),
--                    preemptionPending (4),
--                    nodeId (5)
--                    }
--    MAX-ACCESS  read-only
--    STATUS      current
--    DESCRIPTION
--        "If the 'localAvailable' bit is set, it indicates that the link 
--         downstream of this node has been protected by means of a local
--         repair mechanism. This mechanism can be either the one-to-one 
--         backup method or the facility backup method.
--         
--         If the 'localInUse' bit is set, then it indicates that the local
--         protection mechanism is being used to maintain this tunnel.
--
--         If the 'bandwidthProtected' bit is set, then it indicates that 
--         the backup path is guaranteed to provide the desired bandwidth.
--         
--         If the 'nodeProtected' bit is set, then it indicates that the
--         backup path provides protection against the failure of the next
--         LSR along the LSP.
--         
--         If the 'nodeId' bit is set, it indicates that the address specified
--         in the Record Route Object's IPv4 or IPv6 sub-object is a node-id
--         address."
--    ::= { vRtrMplsTunnelARHopEntry 1 }    
--
--vRtrMplsTunnelARHopRecordLabel OBJECT-TYPE
--    SYNTAX      MplsLabel
--    MAX-ACCESS  read-only
--    STATUS      current
--    DESCRIPTION
--        "If label recording is enabled, vRtrMplsTunnelARHopRecordLabel 
--         specifies the label that is advertised to the previous hop in 
--         the hop list. If label recording is disabled, 
--         vRtrMplsTunnelARHopRecordLabel will have a value of 4294967295"
--    ::= { vRtrMplsTunnelARHopEntry 2 }  
--  
--vRtrMplsTunnelARHopRouterId OBJECT-TYPE
--    SYNTAX      IpAddress
--    MAX-ACCESS  read-only
--    STATUS      current
--    DESCRIPTION
--        "vRtrMplsTunnelARHopRouterId specifies the router ID of the node
--         corresponding to this hop."
--    ::= { vRtrMplsTunnelARHopEntry 3 }    
--
--
--   Virtual Router MPLS CSPF Tunnel Hop Table
--

--vRtrMplsTunnelCHopTable  OBJECT-TYPE
--    SYNTAX      SEQUENCE OF VRtrMplsTunnelCHopEntry
--    MAX-ACCESS  not-accessible
--    STATUS      current
--    DESCRIPTION
--        "The vRtrMplsTunnelCHopTable is used to hold the CSPF
--         path for a detour LSP. Each entry indicates a single
--         hop.
--
--         Primary index is the vRtrMplsTunnelCHopListIndex which associates 
--         multiple entries (hops) in the vRtrMplsTunnelCHopTable to a single 
--         mplsTunnelEntry specified in the mplsTunnelTable.
--
--         The first row in the table is the first hop after the
--         origination point of the tunnel."
--    ::= { tnMplsObjs 12 } 
--
--vRtrMplsTunnelCHopEntry  OBJECT-TYPE
--    SYNTAX      VRtrMplsTunnelCHopEntry
--    MAX-ACCESS  not-accessible
--    STATUS      current
--    DESCRIPTION
--        "An entry in this table represents a CSPF tunnel hop.
--         Entries are created and deleted by the system."
--    INDEX { tnSysSwitchId, vRtrMplsTunnelCHopListIndex, vRtrMplsTunnelCHopIndex }
--    ::= { vRtrMplsTunnelCHopTable 1 }
--
--VRtrMplsTunnelCHopEntry ::= SEQUENCE {
--    vRtrMplsTunnelCHopListIndex          Integer32,
--    vRtrMplsTunnelCHopIndex              Integer32,
--    vRtrMplsTunnelCHopAddrType           INTEGER,
--    vRtrMplsTunnelCHopIpv4Addr           IpAddress,
--    vRtrMplsTunnelCHopIpv4PrefixLen      INTEGER,
--    vRtrMplsTunnelCHopIpv6Addr           InetAddressIPv6,
--    vRtrMplsTunnelCHopIpv6PrefixLen      INTEGER,
--    vRtrMplsTunnelCHopAsNumber           INTEGER,
--    vRtrMplsTunnelCHopLspId              MplsLSPID,
--    vRtrMplsTunnelCHopStrictOrLoose      INTEGER
--}
--
--vRtrMplsTunnelCHopListIndex OBJECT-TYPE
--    SYNTAX      Integer32 (1..2147483647)
--    MAX-ACCESS  not-accessible
--    STATUS      current
--    DESCRIPTION
--        "Primary index into this table identifying a particular explicit route
--         object."
--    ::= { vRtrMplsTunnelCHopEntry 1 }
--
--vRtrMplsTunnelCHopIndex OBJECT-TYPE
--    SYNTAX      Integer32 (1..2147483647)
--    MAX-ACCESS  not-accessible
--    STATUS      current
--    DESCRIPTION
--        "Secondary index into this table identifying a particular hop."
--    ::= { vRtrMplsTunnelCHopEntry 2 }
--
--vRtrMplsTunnelCHopAddrType OBJECT-TYPE
--    SYNTAX      INTEGER {
--                    ipV4(1),
--                    ipV6(2),
--                    asNumber(3),
--                    lspid(4)
--                }
--    MAX-ACCESS  read-only
--    STATUS      current
--    DESCRIPTION
--        "Denotes the address type of this tunnel hop."
--    DEFVAL { ipV4 }
--    ::= { vRtrMplsTunnelCHopEntry 3 }
--
--vRtrMplsTunnelCHopIpv4Addr OBJECT-TYPE
--    SYNTAX      IpAddress
--    MAX-ACCESS  read-only
--    STATUS      current
--    DESCRIPTION
--        "If vRtrMplsTunnelCHopAddrType is set to ipV4(1), then this value will
--         contain the IPv4 address of this hop. This object is otherwise 
--         insignificant and should contain a value of 0."
--    ::= { vRtrMplsTunnelCHopEntry 4 }
--
--vRtrMplsTunnelCHopIpv4PrefixLen OBJECT-TYPE
--    SYNTAX      INTEGER (1..32)
--    MAX-ACCESS  read-only
--    STATUS      current
--    DESCRIPTION
--        "If vRtrMplsTunnelCHopAddrType is ipV4(1), then the prefix length for 
--         this hop's IPv4 address is contained herein. This object is otherwise
--         insignificant and should contain a value of 0."
--    ::= { vRtrMplsTunnelCHopEntry 5 }
--
--vRtrMplsTunnelCHopIpv6Addr OBJECT-TYPE
--    SYNTAX      InetAddressIPv6
--    MAX-ACCESS  read-only
--    STATUS      current
--    DESCRIPTION
--        "If the vRtrMplsTunnelCHopAddrType is set to ipV6(2), then this 
--         variable contains the IPv6 address of this hop. This object is 
--         otherwise insignificant and should contain a value of 0."
--    ::= { vRtrMplsTunnelCHopEntry 6 }
--
--vRtrMplsTunnelCHopIpv6PrefixLen OBJECT-TYPE
--    SYNTAX      INTEGER (1..128)
--    MAX-ACCESS  read-only
--    STATUS      current
--    DESCRIPTION
--        "If vRtrMplsTunnelCHopAddrType is set to ipV6(2), this value will 
--         contain the prefix length for this hop's IPv6 address. This object is
--         otherwise insignificant and should contain a value of 0."
--    ::= { vRtrMplsTunnelCHopEntry 7 }
--
--vRtrMplsTunnelCHopAsNumber OBJECT-TYPE
--    SYNTAX      INTEGER (0..65535)
--    MAX-ACCESS  read-only
--    STATUS      current
--    DESCRIPTION
--        "If vRtrMplsTunnelCHopAddrType is set to asNumber(3), then this value 
--         will contain the AS number of this hop. This object is otherwise     
--         insignificant and should contain a value of 0 to indicate this fact."
--    ::= { vRtrMplsTunnelCHopEntry 8 }
--
--vRtrMplsTunnelCHopLspId OBJECT-TYPE
--    SYNTAX      MplsLSPID
--    MAX-ACCESS  read-only
--    STATUS      current
--    DESCRIPTION
--        "If vRtrMplsTunnelCHopAddrType is set to lspid(4), then this value will
--         contain the LSPID of a tunnel of this hop. The present tunnel being 
--         configured is tunneled through this hop (using label stacking). This 
--         object is otherwise insignificant and should contain a value of 0 to
--         indicate this fact."
--    ::= { vRtrMplsTunnelCHopEntry 9 }
--
--vRtrMplsTunnelCHopStrictOrLoose OBJECT-TYPE
--    SYNTAX      INTEGER {
--                    strict(1),
--                    loose(2)
--                } 
--    MAX-ACCESS  read-only
--    STATUS      current
--    DESCRIPTION
--        "Denotes whether this tunnel hop is routed in a strict or loose 
--         fashion."
--    ::= { vRtrMplsTunnelCHopEntry 10 }
   
--
--  Virtual Router MPLS Administrative Group Table
--

--vRtrMplsAdminGroupTable    OBJECT-TYPE
--    SYNTAX      SEQUENCE OF VRtrMplsAdminGroupEntry
--    MAX-ACCESS  not-accessible
--    STATUS      current
--    DESCRIPTION
--        "The vRtrMplsAdminGroupTable has an entry for each administrative
--         group configured for the virtual router in the system. 
--         
--         Administrative groups are resource constructs that define a link
--         color or resource class. They provide the ability to classify 
--         network resources (links) into groups or colors based on zones, 
--         geographic location, link location, etc. By doing so, network
--         administrators are able to do more granular traffic engineering
--         of LSPs."
--    ::= { tnMplsObjs 13 }
--
--vRtrMplsAdminGroupEntry    OBJECT-TYPE
--    SYNTAX      VRtrMplsAdminGroupEntry
--    MAX-ACCESS  not-accessible
--    STATUS      current
--    DESCRIPTION
--        "Each row entry in the vRtrMplsAdminGroupTable represents an 
--         administrative group which is simply a mapping between a group
--         name (an ASCII string) and a group value (a number in the range
--         0 to 31).
--         
--         Entries in this table are created and deleted via SNMP SET 
--         operations. An entry is created by setting the value of 
--         vRtrMplsAdminGroupRowStatus to 'createAndWait'. The row status
--         for this entry can be set to active only once the value of 
--         vRtrMplsAdminGroupValue has been set to a valid number in the
--         range 0 to 31. The entry is destroyed when 
--         vRtrMplsAdminGroupRowStatus is set to 'destroy'."
--    INDEX { tnSysSwitchId, vRtrID, IMPLIED vRtrMplsAdminGroupName }
--    ::= { vRtrMplsAdminGroupTable 1 }
--
--VRtrMplsAdminGroupEntry ::= SEQUENCE {
--     vRtrMplsAdminGroupName          TNamedItem,
--     vRtrMplsAdminGroupRowStatus     RowStatus,
--     vRtrMplsAdminGroupValue         Integer32
--}
--
--vRtrMplsAdminGroupName    OBJECT-TYPE
--    SYNTAX      TNamedItem
--    MAX-ACCESS  not-accessible
--    STATUS      current
--    DESCRIPTION
--        "The value of vRtrMplsAdminGroupName uniquely identifies the
--         name of the administrative group within a virtual router 
--         instance."
--    ::= { vRtrMplsAdminGroupEntry 1 }
--
--vRtrMplsAdminGroupRowStatus    OBJECT-TYPE
--    SYNTAX      RowStatus
--    MAX-ACCESS  read-create
--    STATUS      current
--    DESCRIPTION
--        "vRtrMplsAdminGroupRowStatus is used to create, delete or 
--         control entries in the vRtrMplsAdminGroupTable. To create 
--         a row entry, the row status should be set to 'createAndWait'. 
--         Before the row can be placed into the 'active' state, 
--         vRtrMplsAdminGroupValue must be set to a value between 0 
--         and 31. To delete a row entry, the row status should be set
--         to 'destroy'"
--    ::= { vRtrMplsAdminGroupEntry 2 }
--
--vRtrMplsAdminGroupValue    OBJECT-TYPE
--    SYNTAX      Integer32 (-1|0..31)
--    MAX-ACCESS  read-create
--    STATUS      current
--    DESCRIPTION
--        "The value of vRtrMplsAdminGroupValue specifies the group value
--         associated with this administrative group. This value is unique 
--         within a virtual router instance.
--
--         A value of -1 indicates that the group value for this entry has
--         not been set."
--    ::= { vRtrMplsAdminGroupEntry 3 }

--
--  Virtual Router MPLS Fate Sharing Group Table
--

--vRtrMplsFSGroupTable    OBJECT-TYPE
--    SYNTAX      SEQUENCE OF VRtrMplsFSGroupEntry
--    MAX-ACCESS  not-accessible
--    STATUS      obsolete
--    DESCRIPTION
--        "The vRtrMplsFSGroupTable has an entry for each group that is 
--         a part of the fate sharing database configured for the virtual 
--         router in the system. 
--         
--         A fate sharing group is used to define a group of links and 
--         nodes in the network that share common risk attributes. To
--         minimize a single point of failure, backup paths can be created
--         that not only avoid the nodes and links of the primary path but
--         also any other nodes and links that share risk with the nodes 
--         and links of the primary path."
--    ::= { tnMplsObjs 14 }
--
--vRtrMplsFSGroupEntry    OBJECT-TYPE
--    SYNTAX      VRtrMplsFSGroupEntry
--    MAX-ACCESS  not-accessible
--    STATUS      obsolete
--    DESCRIPTION
--        "Each row entry in the vRtrMplsFSGroupTable represents a 
--         fate sharing group which is a database of nodes and links 
--         that share common risk attributes.
--         
--         Entries in this table are created and deleted via SNMP SET 
--         operations. An entry is created by setting the value of 
--         vRtrMplsFSGroupRowStatus to 'createAndGo'. An entry can 
--         be deleted by setting vRtrMplsFSGroupRowStatus to 'destroy'."
--    INDEX { tnSysSwitchId, vRtrID, vRtrMplsFSGroupName }
--    ::= { vRtrMplsFSGroupTable 1 }
--
--VRtrMplsFSGroupEntry ::= SEQUENCE {
--     vRtrMplsFSGroupName          TNamedItem,
--     vRtrMplsFSGroupRowStatus     RowStatus,
--     vRtrMplsFSGroupCost          Unsigned32
--}
--
--vRtrMplsFSGroupName    OBJECT-TYPE
--    SYNTAX      TNamedItem
--    MAX-ACCESS  not-accessible
--    STATUS      obsolete
--    DESCRIPTION
--        "The value of vRtrMplsFSGroupName uniquely identifies the
--         name of the fate sharing group within a virtual router 
--         instance."
--    ::= { vRtrMplsFSGroupEntry 1 }
--
--vRtrMplsFSGroupRowStatus    OBJECT-TYPE
--    SYNTAX      RowStatus
--    MAX-ACCESS  read-create
--    STATUS      obsolete
--    DESCRIPTION
--        "vRtrMplsFSGroupRowStatus is used to create, delete or 
--         control entries in the vRtrMplsFSGroupTable. To create 
--         a row entry, the row status should be set to 'createAndGo'. 
--         To delete a row entry, the row status should be set to
--         'destroy'"
--    ::= { vRtrMplsFSGroupEntry 2 }
--
--vRtrMplsFSGroupCost    OBJECT-TYPE
--    SYNTAX      Unsigned32 (1..65535)
--    MAX-ACCESS  read-create
--    STATUS      obsolete
--    DESCRIPTION
--        "The value of vRtrMplsFSGroupCost specifies the cost assigned 
--         to the fate sharing group. This cost is applied to all nodes 
--         and links that are part of this group and used for CSPF 
--         calculations. The higher the cost of the node or link, the 
--         lesser its chance of being selected as part of the path."
--    DEFVAL { 1 }
--    ::= { vRtrMplsFSGroupEntry 3 }

--
--  Virtual Router MPLS Fate Sharing Group Params Table
--

-- vRtrMplsFSGroupParamsTable    OBJECT-TYPE
--     SYNTAX      SEQUENCE OF VRtrMplsFSGroupParamsEntry
--     MAX-ACCESS  not-accessible
--     STATUS      obsolete
--     DESCRIPTION
--         "The vRtrMplsFSGroupParamsTable has an entry for each node
--          or link that is part of a fate sharing group on this virtual 
--          router."
--     ::= { tnMplsObjs 15 }
-- 
-- vRtrMplsFSGroupParamsEntry    OBJECT-TYPE
--     SYNTAX      VRtrMplsFSGroupParamsEntry
--     MAX-ACCESS  not-accessible
--     STATUS      obsolete
--     DESCRIPTION
--         "Each row entry in the vRtrMplsFSGroupParamsTable represents
--          either a node or a link that is a part of a fate sharing group
--          defined in the vRtrMplsFSGroupTable.
--          
--          Entries in this table are created and deleted via SNMP SET 
--          operations. An entry is created by setting the value of 
--          vRtrMplsFSGroupParamsRowStatus to 'createAndGo'. An entry 
--          can be deleted by setting vRtrMplsFSGroupParamsRowStatus to
--          'destroy'.
--          
--          To configure a node to be part of the group, create an entry
--          in this table with vRtrMplsFSGroupParamsFromAddr set to a 
--          valid non-zero IP address and vRtrMplsFSGroupParamsToAddr set
--          to 0. To configure a link to be part of the group, create an
--          entry in this table with both vRtrMplsFSGroupParamsFromAddr
--          and vRtrMplsFSGroupParamsToAddr set to valid non-zero IP 
--          addresses."
--     INDEX { tnSysSwitchId,
--             vRtrID, 
--             vRtrMplsFSGroupName, 
--             vRtrMplsFSGroupParamsFromAddr,
--             vRtrMplsFSGroupParamsToAddr }
--     ::= { vRtrMplsFSGroupParamsTable 1 }
-- 
-- VRtrMplsFSGroupParamsEntry ::= SEQUENCE {
--      vRtrMplsFSGroupParamsFromAddr      IpAddress,
--      vRtrMplsFSGroupParamsToAddr        IpAddress,
--      vRtrMplsFSGroupParamsRowStatus     RowStatus
-- }
-- 
-- vRtrMplsFSGroupParamsFromAddr    OBJECT-TYPE
--     SYNTAX      IpAddress
--     MAX-ACCESS  not-accessible
--     STATUS      obsolete
--     DESCRIPTION
--         "The value of vRtrMplsFSGroupParamsFromAddr along with the 
--          value of vRtrMplsFSGroupParamsToAddr uniquely identifies a 
--          link or node within a fate sharing group. 
-- 
--          This value must be non-zero for all row entries whether it
--          represents a node or a link."
--     ::= { vRtrMplsFSGroupParamsEntry 1 }
-- 
-- vRtrMplsFSGroupParamsToAddr    OBJECT-TYPE
--     SYNTAX      IpAddress
--     MAX-ACCESS  not-accessible
--     STATUS      obsolete
--     DESCRIPTION
--         "The value of vRtrMplsFSGroupParamsToAddr along with the 
--          value of vRtrMplsFSGroupParamsFromAddr uniquely identifies 
--          a link or node within a fate sharing group. 
--          
--          This value must be 0 for row entries that represent a node
--          and must be non-zero for row entries that represent a link."
--     ::= { vRtrMplsFSGroupParamsEntry 2 }
-- 
-- vRtrMplsFSGroupParamsRowStatus    OBJECT-TYPE
--     SYNTAX      RowStatus
--     MAX-ACCESS  read-create
--     STATUS      obsolete
--     DESCRIPTION
--         "vRtrMplsFSGroupParamsRowStatus is used to create, delete or 
--          control entries in the vRtrMplsFSGroupParamsTable. To create 
--          a row entry, the row status should be set to 'createAndGo'. 
--          To delete a row entry, the row status should be set to
--          'destroy'"
--     ::= { vRtrMplsFSGroupParamsEntry 3 }

--
--  MPLS Label Range Table
--

vRtrMplsLabelRangeTable    OBJECT-TYPE
    SYNTAX      SEQUENCE OF VRtrMplsLabelRangeEntry
    MAX-ACCESS  not-accessible
    STATUS      current
    DESCRIPTION
        "The vRtrMplsLabelRangeTable has an entry for each type of
         label, the minimum and maximum value in the label range and 
         information on total available and aging labels in each range.
         
         This is a read-only table."
    ::= { tnMplsObjs 17 }

vRtrMplsLabelRangeEntry    OBJECT-TYPE
    SYNTAX      VRtrMplsLabelRangeEntry
    MAX-ACCESS  not-accessible
    STATUS      current
    DESCRIPTION
        "Each row entry in the vRtrMplsLabelRangeTable represents 
         a type of label. Each entry contains the label range used 
         by that label type and the number of aging and allocated 
         labels in the range."
    INDEX { tnSysSwitchId, vRtrID, vRtrMplsLabelType } 
    ::= { vRtrMplsLabelRangeTable 1 }

VRtrMplsLabelRangeEntry ::= SEQUENCE {
     vRtrMplsLabelType                  INTEGER,
     vRtrMplsLabelRangeMin              Unsigned32,
     vRtrMplsLabelRangeMax              Unsigned32,
     vRtrMplsLabelRangeAging            Unsigned32,    
     vRtrMplsLabelRangeAvailable        Unsigned32
}

vRtrMplsLabelType    OBJECT-TYPE
    SYNTAX      INTEGER {
                   staticLsp (1),
                   staticSvc (2),
                   dynamic (3)
               }
    MAX-ACCESS  not-accessible
    STATUS      current
    DESCRIPTION
        "The value of vRtrMplsLabelType specifies the type of
        label and is the index for this table."
    ::= { vRtrMplsLabelRangeEntry 1 }

vRtrMplsLabelRangeMin    OBJECT-TYPE
    SYNTAX      Unsigned32
    MAX-ACCESS  read-only
    STATUS      current
    DESCRIPTION
        "The value of vRtrMplsLabelRangeMin specifies the minimum
        label value in the range for a particular label type."
    ::= { vRtrMplsLabelRangeEntry 2 }

vRtrMplsLabelRangeMax    OBJECT-TYPE
    SYNTAX      Unsigned32
    MAX-ACCESS  read-only
    STATUS      current
    DESCRIPTION
        "The value of vRtrMplsLabelRangeMax specifies the maximum
        label value in the range for a particular label type."
    ::= { vRtrMplsLabelRangeEntry 3 }

vRtrMplsLabelRangeAging    OBJECT-TYPE
    SYNTAX      Unsigned32
    MAX-ACCESS  read-only
    STATUS      current
    DESCRIPTION
        "The value of vRtrMplsLabelRangeAging represents the 
        number of labels that are currently allocated and aging."
    ::= { vRtrMplsLabelRangeEntry 4 }

vRtrMplsLabelRangeAvailable    OBJECT-TYPE
    SYNTAX      Unsigned32
    MAX-ACCESS  read-only
    STATUS      current
    DESCRIPTION
        "The value of vRtrMplsLabelRangeAvailable represents the 
        number of labels that are currently available for each 
        label type."
    ::= { vRtrMplsLabelRangeEntry 5 }

--
--  MPLS Static LSP Label Table
--

vRtrMplsStaticLSPLabelTable    OBJECT-TYPE
    SYNTAX      SEQUENCE OF VRtrMplsStaticLSPLabelEntry
    MAX-ACCESS  not-accessible
    STATUS      current
    DESCRIPTION
        "The vRtrMplsStaticLSPLabelTable has an entry for each allocated 
        label that is part of the static LSP label range. This is a 
        read-only table." 
    ::= { tnMplsObjs 18 }

vRtrMplsStaticLSPLabelEntry    OBJECT-TYPE
    SYNTAX      VRtrMplsStaticLSPLabelEntry
    MAX-ACCESS  not-accessible
    STATUS      current
    DESCRIPTION
        "Each row entry in the vRtrMplsStaticLSPLabelTable represents 
         a label of type static LSP that is currently allocated.
         The entry includes information about the current owner
         for that label."
         
    INDEX { tnSysSwitchId, vRtrID, vRtrMplsStaticLSPLabel } 
    ::= { vRtrMplsStaticLSPLabelTable 1 }

VRtrMplsStaticLSPLabelEntry ::= SEQUENCE {
     vRtrMplsStaticLSPLabel             MplsLabel,
     vRtrMplsStaticLSPLabelOwner        TmnxMplsLabelOwner
}

vRtrMplsStaticLSPLabel    OBJECT-TYPE
    SYNTAX      MplsLabel (32..262112)
    MAX-ACCESS  not-accessible
    STATUS      current
    DESCRIPTION
        "The value of vRtrMplsStaticLSPLabel specifies the label
         value for a static LSP.
       
         The range of vRtrMplsStaticLSPLabel is dynamic and
         depends on the value of vRtrMplsLabelMaxStaticLspLabels.

         If vRtrMplsLabelMaxStaticLspLabels is 0, static LSP labels
         cannot be configured.

         If vRtrMplsLabelMaxStaticLspLabels is 1, vRtrMplsStaticLSPLabel
         can only be 32.

         The normal range of vRtrMplsStaticLSPLabel starts at 32 and ends at
         the value of vRtrMplsLabelMaxStaticLspLabels."
    ::= { vRtrMplsStaticLSPLabelEntry 1 }

vRtrMplsStaticLSPLabelOwner    OBJECT-TYPE
    SYNTAX      TmnxMplsLabelOwner 
    MAX-ACCESS  read-only
    STATUS      current
    DESCRIPTION
        "The value of vRtrMplsStaticLSPLabelOwner specifies the owner
        for the label value vRtrMplsStaticLSPLabel."
    ::= { vRtrMplsStaticLSPLabelEntry 2 }

--
--  MPLS Static Service Label Table
--

vRtrMplsStaticSvcLabelTable    OBJECT-TYPE
    SYNTAX      SEQUENCE OF VRtrMplsStaticSvcLabelEntry
    MAX-ACCESS  not-accessible
    STATUS      current
    DESCRIPTION
        "The vRtrMplsStaticSvcLabelTable has an entry for each allocated 
        label that is part of the static service label range. This 
        is a read-only table." 
    ::= { tnMplsObjs 19 }

vRtrMplsStaticSvcLabelEntry    OBJECT-TYPE
    SYNTAX      VRtrMplsStaticSvcLabelEntry
    MAX-ACCESS  not-accessible
    STATUS      current
    DESCRIPTION
        "Each row entry in the vRtrMplsStaticSvcLabelTable represents 
         a label of type static-svc that is currently allocated.
         The entry includes information about the current owner
         for that label."
         
    INDEX { tnSysSwitchId, vRtrID, vRtrMplsStaticSvcLabel } 
    ::= { vRtrMplsStaticSvcLabelTable 1 }

VRtrMplsStaticSvcLabelEntry ::= SEQUENCE {
     vRtrMplsStaticSvcLabel             MplsLabel,
     vRtrMplsStaticSvcLabelOwner        TmnxMplsLabelOwner
}

vRtrMplsStaticSvcLabel    OBJECT-TYPE
    SYNTAX      MplsLabel (32..262112)
    MAX-ACCESS  not-accessible
    STATUS      current
    DESCRIPTION
        "The value of vRtrMplsStaticSvcLabel specifies the label
         value for a static SVC.

         The range of vRtrMplsStaticSvcLabel is dynamic and
         depends on the value of vRtrMplsLabelMaxStaticLspLabels 
         and vRtrMplsLabelMaxStaticSvcLabels.

         If vRtrMplsLabelMaxStaticSvcLabels is 0, static SVC labels
         cannot be configured.

         The range for vRtrMplsStaticSvcLabel starts at 
         32 + vRtrMplsLabelMaxStaticLspLabels and ends at
         32 + vRtrMplsLabelMaxStaticSvcLabels + vRtrMplsLabelMaxStaticSvcLabels."
    ::= { vRtrMplsStaticSvcLabelEntry 1 }

vRtrMplsStaticSvcLabelOwner    OBJECT-TYPE
    SYNTAX      TmnxMplsLabelOwner   
    MAX-ACCESS  read-only
    STATUS      current
    DESCRIPTION
        "The value of vRtrMplsStaticSvcLabelOwner specifies 
        the owner for the label value vRtrMplsStaticSvcLabel."
    DEFVAL { none }
    ::= { vRtrMplsStaticSvcLabelEntry 2 }

--
--  Virtual Router MPLS SRLG group Table
--
-- vRtrMplsSrlgGrpTableLastChanged OBJECT-TYPE
--     SYNTAX      TimeStamp
--     MAX-ACCESS  read-only
--     STATUS      current
--     DESCRIPTION
--         "The value of vRtrMplsSrlgGrpTableLastChanged indicates the
--          sysUpTime at the time of the last modification to 
--          vRtrMplsSrlgGrpTable by adding, deleting an entry or change
--          to a writable object in the table.
-- 
--          If no changes were made to the table since the last 
--          re-initialization of the local network management subsystem, 
--          then this object contains a zero value."
--     ::= { tnMplsObjs 20 } 
--  
-- vRtrMplsSrlgGrpTable OBJECT-TYPE
--     SYNTAX      SEQUENCE OF VRtrMplsSrlgGrpEntry
--     MAX-ACCESS  not-accessible
--     STATUS      current
--     DESCRIPTION
--         "The vRtrMplsSrlgGrpTable has an entry for each Shared Risk Link 
--          Groups (SRLG) group configured for MPLS in the system."
--     ::= { tnMplsObjs 21 }
-- 
-- vRtrMplsSrlgGrpEntry      OBJECT-TYPE
--     SYNTAX      VRtrMplsSrlgGrpEntry
--     MAX-ACCESS  not-accessible
--     STATUS      current
--     DESCRIPTION
--         "Each row entry represents a SRLG group on this virtual router
--          that participates in the MPLS protocol.  A row can be created
--          or deleted via SNMP SET requests." 
--     INDEX { tnSysSwitchId, vRtrID, IMPLIED vRtrMplsSrlgGrpName }
--     ::= { vRtrMplsSrlgGrpTable 1 }
-- 
-- VRtrMplsSrlgGrpEntry ::= SEQUENCE {
--     vRtrMplsSrlgGrpName                  TNamedItem,
--     vRtrMplsSrlgGrpRowStatus             RowStatus,
--     vRtrMplsSrlgGrpLastChanged           TimeStamp,
--     vRtrMplsSrlgGrpValue                 Unsigned32                          
-- }
-- 
-- vRtrMplsSrlgGrpName  OBJECT-TYPE
--     SYNTAX     TNamedItem
--     MAX-ACCESS not-accessible
--     STATUS     current
--     DESCRIPTION
--         "The value of vRtrMplsSrlgGrpName indicates the SRLG group name."
--     ::= { vRtrMplsSrlgGrpEntry 1 }
-- 
-- vRtrMplsSrlgGrpRowStatus    OBJECT-TYPE
--     SYNTAX      RowStatus
--     MAX-ACCESS  read-create
--     STATUS      current
--     DESCRIPTION
--         "vRtrMplsSrlgGrpRowStatus is used to create, delete or 
--          control entries in the vRtrMplsSrlgGrpTable.  A value must 
--          also be set for vRtrMplsSrlgGrpValue before the row entry can
--          transition to the 'active' state."
--     ::= { vRtrMplsSrlgGrpEntry 2 }
-- 
-- vRtrMplsSrlgGrpLastChanged  OBJECT-TYPE
--     SYNTAX      TimeStamp
--     MAX-ACCESS  read-only
--     STATUS      current
--     DESCRIPTION
--         "The value of vRtrMplsSrlgGrpLastChanged indicates the timestamp of 
--          last change to this row in vRtrMplsSrlgGrpTable."
--     ::= { vRtrMplsSrlgGrpEntry 3 }
-- 
-- vRtrMplsSrlgGrpValue OBJECT-TYPE
--     SYNTAX      Unsigned32
--     MAX-ACCESS  read-create
--     STATUS      current
--     DESCRIPTION
--         "The value of vRtrMplsSrlgGrpValue specifies the group value 
--          associated with vRtrMplsSrlgGrpName.  This value is unique 
--          within a virtual router instance.
-- 
--          At the time of row creation, a value for vRtrMplsSrlgGrpValue 
--          must be specified or else row creation would fail."
--     ::= { vRtrMplsSrlgGrpEntry 4 }

--
--  Virtual Router MPLS Interface SRLG Group Table
--
-- vRtrMplsIfSrlgGrpTblLastChanged OBJECT-TYPE
--     SYNTAX      TimeStamp
--     MAX-ACCESS  read-only
--     STATUS      current
--     DESCRIPTION
--         "The value of vRtrMplsIfSrlgGrpTblLastChanged indicates the
--          sysUpTime at the time of the last modification to 
--          vRtrMplsIfSrlgGrpTable by adding, deleting an entry or change
--          to a writable object in the table.
-- 
--          If no changes were made to the table since the last 
--          re-initialization of the local network management subsystem, 
--          then this object contains a zero value."
--     ::= { tnMplsObjs 22 } 
-- 
-- vRtrMplsIfSrlgGrpTable OBJECT-TYPE
--     SYNTAX      SEQUENCE OF VRtrMplsIfSrlgGrpEntry
--     MAX-ACCESS  not-accessible
--     STATUS      current
--     DESCRIPTION
--         "The vRtrMplsIfSrlgGrpTable has an entry for each Shared Risk 
--          Link Group (SRLG) groups associated with a router interface 
--          configured for MPLS in the system."
--     ::= { tnMplsObjs 23 }
-- 
-- vRtrMplsIfSrlgGrpEntry      OBJECT-TYPE
--     SYNTAX      VRtrMplsIfSrlgGrpEntry
--     MAX-ACCESS  not-accessible
--     STATUS      current
--     DESCRIPTION
--         "Each row entry represents an SRLG group associated with a interface
--          on this virtual router that participates in the MPLS protocol.
--   
--          A row can be created or deleted via SNMP SET requests."
--     INDEX { tnSysSwitchId, vRtrID, vRtrIfIndex, IMPLIED vRtrMplsIfSrlgGrpName }
--     ::= { vRtrMplsIfSrlgGrpTable 1 }
-- 
-- VRtrMplsIfSrlgGrpEntry ::= SEQUENCE {
--     vRtrMplsIfSrlgGrpName              TNamedItem,
--     vRtrMplsIfSrlgGrpRowStatus         RowStatus,
--     vRtrMplsIfSrlgGrpLastChanged       TimeStamp    
-- }
-- 
-- vRtrMplsIfSrlgGrpName OBJECT-TYPE
--     SYNTAX      TNamedItem
--     MAX-ACCESS  not-accessible
--     STATUS      current
--     DESCRIPTION
--         "The value of vRtrMplsIfSrlgGrpName indicates the SRLG group name."
--     ::= { vRtrMplsIfSrlgGrpEntry 1 }
-- 
-- vRtrMplsIfSrlgGrpRowStatus    OBJECT-TYPE
--     SYNTAX      RowStatus
--     MAX-ACCESS  read-create
--     STATUS      current
--     DESCRIPTION
--         "vRtrMplsIfSrlgGrpRowStatus is used to create, delete or 
--          control entries in the vRtrMplsIfSrlgGrpTable."
--     ::= { vRtrMplsIfSrlgGrpEntry 2 }
-- 
-- vRtrMplsIfSrlgGrpLastChanged  OBJECT-TYPE
--     SYNTAX      TimeStamp
--     MAX-ACCESS  read-only
--     STATUS      current
--     DESCRIPTION
--         "The value of vRtrMplsIfSrlgGrpLastChanged indicates the timestamp
--          of last change to this row in vRtrMplsIfSrlgGrpTable."
--     ::= { vRtrMplsIfSrlgGrpEntry 3 }

--
-- P2MP Instance Table
--

-- vRtrMplsP2mpInstTblLastChanged OBJECT-TYPE
--     SYNTAX      TimeStamp
--     MAX-ACCESS  read-only
--     STATUS      current
--     DESCRIPTION
--         "The value of vRtrMplsP2mpInstTblLastChanged indicates the
--          sysUpTime at the time of the last modification to 
--          vRtrMplsP2mpInstTable by adding, deleting an entry or change
--          to a writable object in the table.
-- 
--          If no changes were made to the table since the last 
--          re-initialization of the local network management subsystem, 
--          then this object contains a zero value."
--     ::= { tnMplsObjs 24 } 
--     
-- vRtrMplsP2mpInstTable OBJECT-TYPE
--     SYNTAX      SEQUENCE OF VRtrMplsP2mpInstEntry
--     MAX-ACCESS  not-accessible
--     STATUS      current
--     DESCRIPTION 
--         "vRtrMplsP2mpInstTable contains configuration information for 
--          the Mpls Point to Multipoint (P2MP) Instance on a virtual router."
--     ::= { tnMplsObjs 25 }
-- 
-- vRtrMplsP2mpInstEntry OBJECT-TYPE
--     SYNTAX      VRtrMplsP2mpInstEntry
--     MAX-ACCESS  not-accessible
--     STATUS      current
--     DESCRIPTION
--         "vRtrMplsP2mpInstEntry is an entry (conceptual row) in the
--          vRtrMplsP2mpInstTable. Each entry represents the configuration
--          for a Mpls Point to Multipoint (P2MP) Instance.
-- 
--          Entries in this table can be created and deleted via SNMP SET
--          operations. "
--      INDEX { tnSysSwitchId, vRtrID, vRtrMplsLspIndex, vRtrMplsP2mpInstIndex }
--     ::= { vRtrMplsP2mpInstTable 1 }
-- 
-- VRtrMplsP2mpInstEntry ::= SEQUENCE {
--     vRtrMplsP2mpInstIndex                  TmnxVRtrMplsLspID,
--     vRtrMplsP2mpInstRowStatus              RowStatus,
--     vRtrMplsP2mpInstLastChange             TimeStamp,
--     vRtrMplsP2mpInstName                   TNamedItemOrEmpty,
--     vRtrMplsP2mpInstType                   INTEGER,
--     vRtrMplsP2mpInstProperties             BITS,
--     vRtrMplsP2mpInstBandwidth              Unsigned32,
--     vRtrMplsP2mpInstState                  INTEGER,
--     vRtrMplsP2mpInstSetupPriority          Unsigned32,
--     vRtrMplsP2mpInstHoldPriority           Unsigned32,
--     vRtrMplsP2mpInstRecord                 TruthValue,
--     vRtrMplsP2mpInstHopLimit               Unsigned32,
--     vRtrMplsP2mpInstAdminState             TmnxAdminState,
--     vRtrMplsP2mpInstOperState              TmnxOperState,
--     vRtrMplsP2mpInstInheritance            Unsigned32,
--     vRtrMplsP2mpInstLspId                  MplsLSPID,
--     vRtrMplsP2mpInstNegotiatedMTU          Unsigned32,
--     vRtrMplsP2mpInstFailCode               TmnxMplsLspFailCode,
--     vRtrMplsP2mpInstFailNodeArType         InetAddressType,
--     vRtrMplsP2mpInstFailNodeAddr           InetAddress,
--     vRtrMplsP2mpInstAdminGrpInclude        Unsigned32,
--     vRtrMplsP2mpInstAdminGrpExclude        Unsigned32,
--     vRtrMplsP2mpInstAdaptive               TruthValue,
--     vRtrMplsP2mpInstOperBandwidth          Integer32,
--     vRtrMplsP2mpInstResignal               TmnxActionType,
--     vRtrMplsP2mpInstOperMTU                Unsigned32,
--     vRtrMplsP2mpInstRecordLabel            INTEGER,
--     vRtrMplsP2mpInstLastResigAttpt         TimeStamp,
--     vRtrMplsP2mpInstMetric                 Unsigned32,
--     vRtrMplsP2mpInstLastMBBType            TmnxMplsMBBType,
--     vRtrMplsP2mpInstLastMBBEnd             TimeStamp,
--     vRtrMplsP2mpInstLastMBBMetric          Unsigned32,
--     vRtrMplsP2mpInstLastMBBState           INTEGER,
--     vRtrMplsP2mpInstMBBTypeInProg          TmnxMplsMBBType,
--     vRtrMplsP2mpInstMBBStarted             TimeStamp,
--     vRtrMplsP2mpInstMBBNextRetry           Unsigned32,
--     vRtrMplsP2mpInstMBBRetryAttpts         Unsigned32,
--     vRtrMplsP2mpInstMBBFailCode            TmnxMplsLspFailCode,
--     vRtrMplsP2mpInstMBBFailNodeType        InetAddressType,
--     vRtrMplsP2mpInstMBBFailNodeAddr        InetAddress
--     }
-- 
-- vRtrMplsP2mpInstIndex OBJECT-TYPE
--     SYNTAX      TmnxVRtrMplsLspID
--     MAX-ACCESS  not-accessible
--     STATUS      current
--     DESCRIPTION
--         "The unique value which identifies this Point to Multipoint Labeled 
--          Switch Path (P2MP LSP) for this virtual router in the Nokia 
--          SROS system.  It is a unique value among entries with the 
--          same value of vRtrID."    
--     ::= { vRtrMplsP2mpInstEntry 1 }
-- 
-- vRtrMplsP2mpInstRowStatus    OBJECT-TYPE
--     SYNTAX      RowStatus
--     MAX-ACCESS  read-create
--     STATUS      current
--     DESCRIPTION
--         "vRtrMplsP2mpInstRowStatus is used to create, delete or 
--          control entries in the vRtrMplsP2mpInstTable."
--     ::= { vRtrMplsP2mpInstEntry 2 }
-- 
-- vRtrMplsP2mpInstLastChange  OBJECT-TYPE
--     SYNTAX      TimeStamp
--     MAX-ACCESS  read-only
--     STATUS      current
--     DESCRIPTION
--         "The value of vRtrMplsP2mpInstLastChange indicates the timestamp
--          of last change to this row in vRtrMplsP2mpInstTable."
--     ::= { vRtrMplsP2mpInstEntry 3 }
-- 
-- vRtrMplsP2mpInstName     OBJECT-TYPE
--     SYNTAX      TNamedItemOrEmpty
--     MAX-ACCESS  read-create
--     STATUS      current
--     DESCRIPTION
--         "The value of vRtrMplsP2mpInstName specifies the administrative name 
--         for the P2MP instance which must be unique within a virtual router instance."
--     ::= { vRtrMplsP2mpInstEntry 4 }    
--     
-- vRtrMplsP2mpInstType     OBJECT-TYPE
--     SYNTAX      INTEGER {
--                     other (1),
--                     primary (2)
--                 }
--     MAX-ACCESS  read-create
--     STATUS      current
--     DESCRIPTION
--         "The value of vRtrMplsP2mpInstType specifies the type of P2MP LSP 
--          instance."
--     DEFVAL { primary }
--     ::= { vRtrMplsP2mpInstEntry 5 }      
-- 
-- vRtrMplsP2mpInstProperties   OBJECT-TYPE
--     SYNTAX      BITS {
--                     recordRoute (0),
--                     adaptive (1),
--                     cspf (2),
--                     mergeable (3),
--                     fastReroute (4)
--                 }
--     MAX-ACCESS  read-only
--     STATUS      current
--     DESCRIPTION
--         "The value of vRtrMplsP2mpInstProperties indicates the set of configured
--         properties for this path expressed as a bit map.  For example, if the 
--         path is an adaptive path, the bit corresponding to bit value 1 is set."
--     ::= { vRtrMplsP2mpInstEntry 6 }
-- 
-- vRtrMplsP2mpInstBandwidth    OBJECT-TYPE
--     SYNTAX      Unsigned32
--     UNITS       "mega-bits per second"
--     MAX-ACCESS  read-create
--     STATUS      current
--     DESCRIPTION
--         "The value of vRtrMplsP2mpInstBandwidth specifies the amount of
--          bandwidth in mega-bits per second (Mbps) to be reserved for the P2MP 
--          LSP."
--     DEFVAL { 0 }
--     ::= { vRtrMplsP2mpInstEntry 7 }    
-- 
-- vRtrMplsP2mpInstState    OBJECT-TYPE
--     SYNTAX      INTEGER {
--                     unknown (1),
--                     active (2),
--                     inactive (3)
--                 }
--     MAX-ACCESS  read-only
--     STATUS      current
--     DESCRIPTION
--         "The value of vRtrMplsP2mpInstState indicates the current working state
--         of this path within this P2MP LSP."
--     ::= { vRtrMplsP2mpInstEntry 8 }
-- 
-- vRtrMplsP2mpInstSetupPriority    OBJECT-TYPE
--     SYNTAX      Unsigned32 (0..7)
--     MAX-ACCESS  read-only
--     STATUS      current
--     DESCRIPTION
--         "The value of vRtrMplsP2mpInstSetupPriority indicates the setup 
--          priority to use when insufficient bandwidth is available to setup 
--          a P2MP LSP.  The setup priority is compared against the hold priority 
--          of existing LSPs.  If the setup priority is higher than the hold
--          priority of the established LSPs, this P2MP LSP may preempt the other
--          LSPs.  A value of zero (0) is the highest priority and a value
--          of seven (7) is the lowest priority.
--          
--          When the vRtrMplsP2mpInstHopLimit bit in vRtrMplsP2mpInstInheritance 
--          is cleared (0), the value returned to a GET request is inherited 
--          from vRtrMplsLspHopLimit."
--     ::= { vRtrMplsP2mpInstEntry 9 }
--         
-- vRtrMplsP2mpInstHoldPriority     OBJECT-TYPE
--     SYNTAX      Unsigned32 (0..7)
--     MAX-ACCESS  read-only
--     STATUS      current
--     DESCRIPTION
--         "The value of vRtrMplsP2mpInstHoldPriority indicates the hold 
--          priority to use when insufficient bandwidth is available to setup 
--          a P2MP LSP.  The setup priority is compared against the hold priority 
--          of existing LSPs.  If the setup priority is higher than the hold 
--          priority of the established LSPs, this P2MP LSP may preempt the other
--          LSPs.  A value of zero (0) is the highest priority and a value
--          of seven (7) is the lowest priority.
--          
--          When the vRtrMplsP2mpInstHopLimit bit in vRtrMplsP2mpInstInheritance 
--          is cleared (0), the value returned to a GET request is inherited 
--          from vRtrMplsLspHopLimit."
--     ::= { vRtrMplsP2mpInstEntry 10 }
--     
-- vRtrMplsP2mpInstRecord       OBJECT-TYPE
--     SYNTAX      TruthValue
--     MAX-ACCESS  read-create
--     STATUS      current
--     DESCRIPTION
--         "The value of vRtrMplsP2mpInstRecord specifies whether recording of 
--         all hops that a P2MP LSP traverses is enabled. When the value of 
--         vRtrMplsP2mpInstRecord is 'true', recording of all the hops that a 
--         P2MP LSP traverses is enabled.
--          
--         When the value of vRtrMplsP2mpInstRecord is 'false, recording of all
--         the hops that a P2MP LSP traverses is disabled."
--     DEFVAL { true }
--     ::= { vRtrMplsP2mpInstEntry 11 }       
-- 
-- vRtrMplsP2mpInstHopLimit     OBJECT-TYPE
--     SYNTAX      Unsigned32 (2..255)
--     MAX-ACCESS  read-create
--     STATUS      current
--     DESCRIPTION
--         "The value of vRtrMplsP2mpInstHopLimit specifies the maximum number
--          of hops that a P2MP LSP will traverse including the ingress and
--          egress ESRs.  A P2MP LSP will not be setup if the hop limit is
--          exceeded.  
--          
--          When the vRtrMplsP2mpInstHopLimit bit in vRtrMplsP2mpInstInheritance 
--          is cleared (0), the value returned to a GET request is inherited 
--          from vRtrMplsLspHopLimit."
--     DEFVAL { 255 }
--     ::= { vRtrMplsP2mpInstEntry 12 }
-- 
-- vRtrMplsP2mpInstAdminState       OBJECT-TYPE
--     SYNTAX      TmnxAdminState
--     MAX-ACCESS  read-create
--     STATUS      current
--     DESCRIPTION
--         "The value of vRtrMplsP2mpInstAdminState specifies desired 
--          administrative state for this P2MP LSP."
--     DEFVAL { inService }
--     ::= { vRtrMplsP2mpInstEntry 13 }
-- 
-- vRtrMplsP2mpInstOperState        OBJECT-TYPE
--     SYNTAX      TmnxOperState
--     MAX-ACCESS  read-only
--     STATUS      current
--     DESCRIPTION
--         "The value of vRtrMplsP2mpInstOperState indicates the current 
--          operational state of this P2MP LSP."
--     ::= { vRtrMplsP2mpInstEntry 14 }    
-- 
-- vRtrMplsP2mpInstInheritance OBJECT-TYPE
--     SYNTAX      Unsigned32
--     MAX-ACCESS  read-create
--     STATUS      current
--     DESCRIPTION
--         "The value of vRtrMplsP2mpInstInheritance specifies whether or not
--          each writable object in this row inherits its value from its 
--          corresponding object in the vRtrMplsLspTable.  This object controls 
--          whether to inherit the operational value of that associated object, 
--          or use the administrative value configured in this row.
--  
--          Non mask bits will always have value of zero, and any attempt to
--          change the value will be silently discarded.
-- 
--          This object is a bit-mask, with the following positions:
-- 
--          vRtrMplsP2mpInstHopLimit              0x40
--          vRtrMplsP2mpInstAdminGrpInclude       0x200
--          vRtrMplsP2mpInstAdminGrpExclude       0x400
--          vRtrMplsP2mpInstAdaptive              0x800
--   
--          When the bit for an object is set to one, then the
--          object's administrative and operational value are whatever
--          the DEFVAL or most recently SET value is. The corresponding
--          mask bit will be changed to one when SNMP SET is performed
--          on any of the inherited objects (vRtrMplsP2mpInstHopLimit,
--          vRtrMplsP2mpInstAdminGrpInclude, etc).
--         
--          When the bit for an object is set to zero, then the
--          object's administrative and operational value are inherited
--          from the corresponding object in vRtrMplsLspTable."
--     DEFVAL { 0 } 
--     ::= { vRtrMplsP2mpInstEntry 15 }
-- 
-- vRtrMplsP2mpInstLspId OBJECT-TYPE
--     SYNTAX      MplsLSPID
--     MAX-ACCESS  read-only
--     STATUS      current
--     DESCRIPTION
--         "The value of vRtrMplsP2mpInstLspId indicates the value which identifies
--         the label switched path that is signaled for this entry."
--     ::= { vRtrMplsP2mpInstEntry 16 }
-- 
-- vRtrMplsP2mpInstNegotiatedMTU     OBJECT-TYPE
--     SYNTAX      Unsigned32
--     MAX-ACCESS  read-only
--     STATUS      current
--     DESCRIPTION
--         "The value of vRtrMplsP2mpInstNegotiatedMTU indicates the size 
--          for the Maximum transmission unit (MTU) that is negotiated
--          during establishment of this P2MP LSP path."
--     ::= { vRtrMplsP2mpInstEntry 17 }
-- 
-- vRtrMplsP2mpInstFailCode     OBJECT-TYPE
--     SYNTAX      TmnxMplsLspFailCode
--     MAX-ACCESS  read-only
--     STATUS      current
--     DESCRIPTION
--         "The value of vRtrMplsP2mpInstFailCode indicates the reason code
--          for P2MP LSP Path failure. A value of 0 indicates that no failure 
--          has occurred."
--     ::= { vRtrMplsP2mpInstEntry 18 }
-- 
-- vRtrMplsP2mpInstFailNodeArType     OBJECT-TYPE
--     SYNTAX      InetAddressType
--     MAX-ACCESS  read-only
--     STATUS      current
--     DESCRIPTION
--         "The value of vRtrMplsP2mpInstFailNodeArType indicates the type of 
--          vRtrMplsP2mpInstFailNodeAddr.  When no failure has occurred, 
--          vRtrMplsP2mpInstFailNodeArType is 0."
--     ::= { vRtrMplsP2mpInstEntry 19 }
--     
-- vRtrMplsP2mpInstFailNodeAddr     OBJECT-TYPE
--     SYNTAX      InetAddress (SIZE (0|4))
--     MAX-ACCESS  read-only
--     STATUS      current
--     DESCRIPTION
--         "The value of vRtrMplsP2mpInstFailNodeAddr indicates the IP address
--          of the node in the P2MP LSP path at which the P2MP LSP path failed."
--     ::= { vRtrMplsP2mpInstEntry 20 }
-- 
-- vRtrMplsP2mpInstAdminGrpInclude   OBJECT-TYPE
--     SYNTAX      Unsigned32
--     MAX-ACCESS  read-create
--     STATUS      current
--     DESCRIPTION
--         "The value of vRtrMplsP2mpInstAdminGrpInclude is a bit-map that
--          specifies a list of admin groups that should be included when
--          this P2MP LSP is setup. If bit 'n' is set, then the admin group 
--          with value 'n' is included for this P2MP LSP. This implies that 
--          each link that this P2MP LSP goes through must be associated with  
--          at least one of the admin groups in the include list.
-- 
--          By default, all admin groups are in the include list."
--     DEFVAL { '00000000'H }
--     ::= { vRtrMplsP2mpInstEntry 21 }
-- 
-- vRtrMplsP2mpInstAdminGrpExclude   OBJECT-TYPE
--     SYNTAX      Unsigned32
--     MAX-ACCESS  read-create
--     STATUS      current
--     DESCRIPTION
--         "The value of vRtrMplsP2mpInstAdminGrpExclude is a bit-map that
--          specifies a list of admin groups that should be excluded when
--          this P2MP LSP is setup. If bit 'n' is set, then the admin group 
--          with value 'n' is excluded for this P2MP LSP. This implies that 
--          each link that this P2MP LSP goes through must not be associated
--          with any of the admin groups in the exclude list.
-- 
--          By default, no admin groups are in the exclude list."
--     DEFVAL { '00000000'H }
--     ::= { vRtrMplsP2mpInstEntry 22 }
--     
-- vRtrMplsP2mpInstAdaptive   OBJECT-TYPE
--     SYNTAX      TruthValue
--     MAX-ACCESS  read-create
--     STATUS      current
--     DESCRIPTION
--         "The value of vRtrMplsP2mpInstAdaptive specifies whether 
--         make-before-break functionality is enabled. If the value of 
--         vRtrMplsP2mpInstAdaptive is set to 'true', it enables make-before-break 
--         functionality for the P2MP LSP. 
--         
--         When the attributes of an already established P2MP LSP are changed, 
--         either through manual configuration or due to a change in network 
--         topology, make-before-break functionality ensures that the resources of 
--         the existing P2MP LSP will not be released until a new path (with the
--         same P2MP LSP Id) has been established and traffic flowing over the 
--         existing path is seamlessly transferred to the new path.
--          
--         If the value of vRtrMplsP2mpInstAdaptive is set to 'false', it 
--         disables make-before-break functionality."
--     DEFVAL { true }
--     ::= { vRtrMplsP2mpInstEntry 23 }
-- 
-- vRtrMplsP2mpInstOperBandwidth  OBJECT-TYPE
--     SYNTAX      Integer32
--     UNITS       "mega-bits per second"
--     MAX-ACCESS  read-only
--     STATUS      current
--     DESCRIPTION
--         "The value of vRtrMplsP2mpInstOperBandwidth indicates the amount of
--          bandwidth in mega-bits per seconds (Mbps) that has been reserved
--          for the operational P2MP LSP path.
-- 
--          When make-before-break functionality for the P2MP LSP is enabled and 
--          if the path bandwidth is changed, the resources allocated to the 
--          existing P2MP LSP paths will not be released until a new path with 
--          the new bandwidth settings has been established. While a new path 
--          is being signaled, the administrative value and the operational 
--          values of the path bandwidth may differ. The value of 
--          vRtrMplsP2mpInstBandwidth specifies the bandwidth requirements for 
--          the new P2MP LSP path trying to be established whereas the value of 
--          vRtrMplsP2mpInstOperBandwidth specifies the bandwidth reserved 
--          for the existing P2MP LSP path."
--     ::= { vRtrMplsP2mpInstEntry 24 }
-- 
-- vRtrMplsP2mpInstResignal   OBJECT-TYPE
--     SYNTAX      TmnxActionType
--     MAX-ACCESS  read-create
--     STATUS      current
--     DESCRIPTION
--         "Setting the value of vRtrMplsP2mpInstResignal to 'doAction' triggers
--          the re-signaling of the P2MP LSP path. 
-- 
--          If the P2MP LSP path is operationally down either due to network 
--          failure or due to the retry attempts count being exceeded, setting this 
--          variable to 'doAction' will initiate the signaling for the path. A 
--          make-before-break signaling for the path will be initiated if the 
--          P2MP LSP is operationally up but the make-before-break retry attempts 
--          count was exceeded. Make-before-break signaling will also be 
--          initiated for any P2MP LSP that is operationally up. This may be used 
--          to cause a loose-hop P2MP LSP to be optimized. 
-- 
--          If a re-signal is triggered while a re-signaling is already in 
--          progress, the old transient state will be destroyed and a new 
--          transaction being triggered.
--          
--          An SNMP GET request on this object should return 'notApplicable'."
--     DEFVAL { notApplicable }     
--     ::= { vRtrMplsP2mpInstEntry 25 }
-- 
-- vRtrMplsP2mpInstOperMTU     OBJECT-TYPE
--     SYNTAX      Unsigned32
--     MAX-ACCESS  read-only
--     STATUS      current
--     DESCRIPTION
--         "The value of vRtrMplsP2mpInstOperMTU indicates the size 
--          for the Maximum transmission unit (MTU) that is currently
--          in operation for this P2MP LSP Path."
--     ::= { vRtrMplsP2mpInstEntry 26 }
-- 
-- vRtrMplsP2mpInstRecordLabel       OBJECT-TYPE
--     SYNTAX      INTEGER {
--                     record (1),
--                     noRecord (2)
--                 }
--     MAX-ACCESS  read-create
--     STATUS      current
--     DESCRIPTION
--         "The value of vRtrMplsP2mpInstRecordLabel specifies when the value of 
--          vRtrMplsP2mpInstRecordLabel is 'record', recording of labels at each 
--          node that a P2MP LSP traverses is enabled.
-- 
--          When the value of vRtrMplsP2mpInstRecordLabel is 'noRecord', 
--          recording of labels at each node that a P2MP LSP traverses is 
--          disabled."
--     DEFVAL { record }
--     ::= { vRtrMplsP2mpInstEntry 27 }  
-- 
-- vRtrMplsP2mpInstLastResigAttpt       OBJECT-TYPE
--     SYNTAX      TimeStamp
--     MAX-ACCESS  read-only
--     STATUS      current
--     DESCRIPTION
--         "The value of vRtrMplsP2mpInstLastResigAttpt indicates the 
--          sysUpTime when the last attempt to resignal this P2MP LSP was made."
--     ::= { vRtrMplsP2mpInstEntry 28 } 
-- 
-- vRtrMplsP2mpInstMetric       OBJECT-TYPE
--     SYNTAX      Unsigned32
--     MAX-ACCESS  read-only
--     STATUS      current
--     DESCRIPTION
--         "The value of vRtrMplsP2mpInstMetric indicates the cost of the traffic 
--          engineered path returned by the IGP."
--      ::= { vRtrMplsP2mpInstEntry 29 } 
-- 
-- vRtrMplsP2mpInstLastMBBType      OBJECT-TYPE
--     SYNTAX      TmnxMplsMBBType
--     MAX-ACCESS  read-only
--     STATUS      current
--     DESCRIPTION
--         "The value of vRtrMplsP2mpInstLastMBBType indicates the type of 
--          last Make-before-break (MBB).  If 'none', then no MBB has been
--          attempted."
--     ::= { vRtrMplsP2mpInstEntry 30 } 
-- 
-- vRtrMplsP2mpInstLastMBBEnd       OBJECT-TYPE
--     SYNTAX      TimeStamp
--     MAX-ACCESS  read-only
--     STATUS      current
--     DESCRIPTION
--         "The value of vRtrMplsP2mpInstLastMBBEnd indicates the 
--          sysUpTime when the last MBB ended."
--     ::= { vRtrMplsP2mpInstEntry 31 } 
-- 
-- vRtrMplsP2mpInstLastMBBMetric              OBJECT-TYPE
--     SYNTAX      Unsigned32
--     MAX-ACCESS  read-only
--     STATUS      current
--     DESCRIPTION
--         "The value of vRtrMplsP2mpInstLastMBBMetric  indicates  the 
--          cost of the traffic engineered path for the P2MP LSP path prior to 
--          MBB."
--     ::= { vRtrMplsP2mpInstEntry 32 }     
-- 
-- vRtrMplsP2mpInstLastMBBState  OBJECT-TYPE
--     SYNTAX      INTEGER {
--                     none (1),
--                     success (2), 
--                     fail(3)
--                 }
--     MAX-ACCESS  read-only
--     STATUS      current
--     DESCRIPTION
--         "The value of vRtrMplsP2mpInstLastMBBState specifies whether the last 
--          Make-before-break was successful or failed. 
--          Possible states are:
--          none (1)        - no make-before-break invoked 
--          success (2)     - make-before-break successful
--          fail (3)        - make-before-break failed."
--     ::= { vRtrMplsP2mpInstEntry 33 }    
-- 
-- vRtrMplsP2mpInstMBBTypeInProg      OBJECT-TYPE
--     SYNTAX      TmnxMplsMBBType
--     MAX-ACCESS  read-only
--     STATUS      current
--     DESCRIPTION
--         "The value of vRtrMplsP2mpInstMBBTypeInProg indicates the type of the
--          Make-before-break (MBB) that is in progress. If 'none', then no MBB
--          is in progress."
--    ::= { vRtrMplsP2mpInstEntry 34 } 
-- 
-- vRtrMplsP2mpInstMBBStarted       OBJECT-TYPE
--     SYNTAX      TimeStamp
--     MAX-ACCESS  read-only
--     STATUS      current
--     DESCRIPTION
--         "The value of vRtrMplsP2mpInstMBBStarted indicates the 
--          sysUpTime when the in-progress MBB started."
--     ::= { vRtrMplsP2mpInstEntry 35 } 
--     
-- vRtrMplsP2mpInstMBBNextRetry      OBJECT-TYPE
--     SYNTAX      Unsigned32
--     UNITS       "seconds"     
--     MAX-ACCESS  read-only
--     STATUS      current
--     DESCRIPTION
--         "The value of vRtrMplsP2mpInstMBBNextRetry indicates the amount 
--          of time remaining in seconds before the next attempt is made to retry 
--          the in-progress MBB."
--     ::= { vRtrMplsP2mpInstEntry 36 } 
-- 
-- vRtrMplsP2mpInstMBBRetryAttpts       OBJECT-TYPE
--     SYNTAX      Unsigned32
--     MAX-ACCESS  read-only
--     STATUS      current
--     DESCRIPTION
--         "The value of vRtrMplsP2mpInstMBBRetryAttpts indicates 'n' where
--          nth attempt for the MBB is in progress."
--     ::= { vRtrMplsP2mpInstEntry 37 }         
-- 
-- vRtrMplsP2mpInstMBBFailCode     OBJECT-TYPE
--     SYNTAX      TmnxMplsLspFailCode
--     MAX-ACCESS  read-only
--     STATUS      current
--     DESCRIPTION
--         "The value of vRtrMplsP2mpInstMBBFailCode indicates the reason code
--          for in-progress MBB failure. A value of 'none' indicates that no 
--          failure has occurred."
--     ::= { vRtrMplsP2mpInstEntry 38 }
-- 
-- vRtrMplsP2mpInstMBBFailNodeType OBJECT-TYPE
--      SYNTAX     InetAddressType
--      MAX-ACCESS read-only
--      STATUS     current
--      DESCRIPTION
--        "The value of vRtrMplsP2mpInstMBBFailNodeType indicates the type of 
--         vRtrMplsP2mpInstMBBFailNodeAddr. A value of 'unknown' indicates that 
--         no failure has occurred."
--      ::= { vRtrMplsP2mpInstEntry 39 }   
--      
-- vRtrMplsP2mpInstMBBFailNodeAddr     OBJECT-TYPE
--     SYNTAX      InetAddress (SIZE (0|4))
--     MAX-ACCESS  read-only
--     STATUS      current
--     DESCRIPTION
--         "The value of vRtrMplsP2mpInstMBBFailNodeAddr indicates the IP address
--          of the node in the P2MP LSP path at which the in-progress MBB failed. 
--          A value of 'unknown' for vRtrMplsP2mpInstMBBFailNodeType and empty 
--          string for vRtrMplsP2mpInstMBBFailNodeAddr indicates that no failure 
--          has occurred."
--     ::= { vRtrMplsP2mpInstEntry 40 }


--
--  The Virtual Router MPLS P2MP Labeled Switch Path (LSP) Statistics Table
--
--  Augmentation of the vRtrMplsP2mpInstTable.
--  Use of AUGMENTS clause implies a one-to-one dependent relationship 
--  between the base table, vRtrMplsP2mpInstTable, and the augmenting table, 
--  vRtrMplsP2mpInstStatTable. This in effect extends the vRtrMplsP2mpInstTable 
--  with additional columns.  
--  Creation (or deletion) of a row in the vRtrMplsP2mpInstTable results in 
--  the same fate for the row in the vRtrMplsP2mpInstStatTable.
--

-- vRtrMplsP2mpInstStatTable    OBJECT-TYPE
--     SYNTAX      SEQUENCE OF VRtrMplsP2mpInstStatEntry
--     MAX-ACCESS  not-accessible
--     STATUS      current
--     DESCRIPTION
--         "The vRtrMplsP2mpInstStatTable has an entry for each Labeled Switch
--          Path (LSP) configured for a virtual router in the system."
--     ::= { tnMplsObjs 26 }
-- 
-- vRtrMplsP2mpInstStatEntry    OBJECT-TYPE
--     SYNTAX      VRtrMplsP2mpInstStatEntry
--     MAX-ACCESS  not-accessible
--     STATUS      current
--     DESCRIPTION
--         "Each row entry represents a collection of statistics for a P2MP
--          Labeled Switch Path (LSP) configured for a virtual router in 
--          the system.  
-- 
--          Entries cannot be created and deleted via SNMP SET operations."
--     AUGMENTS { vRtrMplsP2mpInstEntry }
--     ::= { vRtrMplsP2mpInstStatTable 1 }
-- 
-- VRtrMplsP2mpInstStatEntry ::= SEQUENCE {
--     vRtrMplsP2mpInstStatS2lChanges              Counter32,
--     vRtrMplsP2mpInstStatLastS2lChange           TimeInterval,
--     vRtrMplsP2mpInstStatConfiguredS2ls          Gauge32,
--     vRtrMplsP2mpInstStatOperationalS2ls         Gauge32,
--     vRtrMplsP2mpInstStatLastS2lTimeUp           TimeInterval,
--     vRtrMplsP2mpInstStatLastS2lTimeDown         TimeInterval,
--     vRtrMplsP2mpInstStatTimeUp                  TimeInterval,
--     vRtrMplsP2mpInstStatTimeDown                TimeInterval,
--     vRtrMplsP2mpInstStatTransitions             Counter32,
--     vRtrMplsP2mpInstStatLastTrans               TimeInterval
--     }
-- 
-- vRtrMplsP2mpInstStatS2lChanges OBJECT-TYPE
--     SYNTAX      Counter32
--     MAX-ACCESS  read-only
--     STATUS      current
--     DESCRIPTION
--         "The value of vRtrMplsP2mpInstStatS2lChanges indicates the number of S2l
--         changes this P2MP LSP has had. For every S2l change (S2l down, S2l up, 
--         S2l change), a corresponding syslog/trap (if enabled) is generated for 
--         it."
--     ::= { vRtrMplsP2mpInstStatEntry 1 }
-- 
-- vRtrMplsP2mpInstStatLastS2lChange OBJECT-TYPE
--     SYNTAX      TimeInterval
--     UNITS       "10-milliseconds"  
--     MAX-ACCESS  read-only
--     STATUS      current
--     DESCRIPTION
--         "The value of vRtrMplsP2mpInstStatLastS2lChange indicates the time 
--         since the last change occurred on this P2MP LSP."
--     ::= { vRtrMplsP2mpInstStatEntry 2 }
-- 
-- vRtrMplsP2mpInstStatConfiguredS2ls OBJECT-TYPE
--     SYNTAX      Gauge32
--     MAX-ACCESS  read-only
--     STATUS      current
--     DESCRIPTION
--         "The value of vRtrMplsP2mpInstStatConfiguredS2ls indicates the number 
--         of S2ls configured for this P2MP LSP."
--     ::= { vRtrMplsP2mpInstStatEntry 3 }
-- 
-- vRtrMplsP2mpInstStatOperationalS2ls OBJECT-TYPE
--     SYNTAX      Gauge32
--     MAX-ACCESS  read-only
--     STATUS      current
--     DESCRIPTION
--         "The value of vRtrMplsP2mpInstStatOperationalS2ls indicates the number 
--         of operational S2ls for this P2MP LSP. This includes the S2ls currently
--         active."
--     ::= { vRtrMplsP2mpInstStatEntry 4 }
-- 
--  vRtrMplsP2mpInstStatLastS2lTimeUp   OBJECT-TYPE
--     SYNTAX      TimeInterval
--     UNITS       "10-milliseconds"  
--     MAX-ACCESS  read-only
--     STATUS      current
--     DESCRIPTION
--         "The value of vRtrMplsP2mpInstStatLastS2lTimeUp indicates the total time 
--         that this S2l has been operational."
--     ::= { vRtrMplsP2mpInstStatEntry 5 }
--         
-- vRtrMplsP2mpInstStatLastS2lTimeDown OBJECT-TYPE
--     SYNTAX      TimeInterval
--     MAX-ACCESS  read-only
--     STATUS      current
--     DESCRIPTION
--         "The value of vRtrMplsP2mpInstStatLastS2lTimeDown indicates the total time 
--         that this S2l has not been operational."
--     ::= { vRtrMplsP2mpInstStatEntry 6 }
-- 
-- vRtrMplsP2mpInstStatTimeUp   OBJECT-TYPE
--     SYNTAX      TimeInterval
--     UNITS       "10-milliseconds"  
--     MAX-ACCESS  read-only
--     STATUS      current
--     DESCRIPTION
--         "The value of vRtrMplsP2mpInstStatTimeUp indicates the total time 
--         that this P2MP instance has been operational."
--     ::= { vRtrMplsP2mpInstStatEntry 7 }
--         
-- vRtrMplsP2mpInstStatTimeDown OBJECT-TYPE
--     SYNTAX      TimeInterval
--     MAX-ACCESS  read-only
--     STATUS      current
--     DESCRIPTION
--         "The value of vRtrMplsP2mpInstStatTimeDown indicates the total time 
--         that this P2MP instance has not been operational."
--     ::= { vRtrMplsP2mpInstStatEntry 8 }    
-- 
-- vRtrMplsP2mpInstStatTransitions OBJECT-TYPE
--     SYNTAX      Counter32
--     MAX-ACCESS  read-only
--     STATUS      current
--     DESCRIPTION
--         "The The value of vRtrMplsP2mpInstStatTransitions indicates the number of state transitions 
--         (up -> down and down -> up) this P2mp instance has undergone."
--     ::= { vRtrMplsP2mpInstStatEntry 9 }
-- 
-- vRtrMplsP2mpInstStatLastTrans OBJECT-TYPE
--     SYNTAX      TimeInterval
--     UNITS        "ten-milliseconds"
--     MAX-ACCESS  read-only
--     STATUS      current
--     DESCRIPTION
--         "The value of vRtrMplsP2mpInstStatLastTrans indicates the time since the last transition 
--          occurred on this P2mp instance."
--     ::= { vRtrMplsP2mpInstStatEntry 10 }    
    
--
-- S2L SUB LSP Table
--

-- vRtrMplsS2lSubLspTblLastChanged OBJECT-TYPE
--     SYNTAX      TimeStamp
--     MAX-ACCESS  read-only
--     STATUS      current
--     DESCRIPTION
--         "The value of vRtrMplsS2lSubLspTblLastChanged indicates the
--          sysUpTime at the time of the last modification to 
--          vRtrMplsS2lSubLspTable by adding, deleting an entry or change
--          to a writable object in the table.
-- 
--          If no changes were made to the table since the last 
--          re-initialization of the local network management subsystem, 
--          then this object contains a zero value."
--     ::= { tnMplsObjs 27 } 
--     
-- vRtrMplsS2lSubLspTable    OBJECT-TYPE
--     SYNTAX      SEQUENCE OF VRtrMplsS2lSubLspEntry
--     MAX-ACCESS  not-accessible
--     STATUS      current
--     DESCRIPTION
--         "The vRtrMplsS2lSubLspTable provides an association between an
--          P2MP LSP and a source to leaf (S2L) sub LSP path called as S2L here.  
--          A P2MP LSP can have more than one S2L sub LSP association."
--     ::= { tnMplsObjs 28 }
-- 
-- vRtrMplsS2lSubLspEntry    OBJECT-TYPE
--     SYNTAX      VRtrMplsS2lSubLspEntry
--     MAX-ACCESS  not-accessible
--     STATUS      current
--     DESCRIPTION
--         "Each row entry represents an association between a Labeled Switch
--          Path (P2MP LSP) in the vRtrMplsP2mpInstTable and a S2L sub LSP entry in
--          the vRtrMplsS2lSubLspTable.  Entries in this table can be created and
--          deleted via SNMP SET operations.  Setting RowStatus to 'active'
--          requires vRtrMplsS2lSubLspType to have been assigned a valid value."
--     INDEX {      tnSysSwitchId,
--                  vRtrID, 
--                  vRtrMplsLspIndex, 
--                  vRtrMplsP2mpInstIndex , 
--                  mplsTunnelIndex, 
--                  mplsTunnelInstance,
--                  mplsTunnelIngressLSRId,
--                  vRtrMplsS2lSubLspDstAddrType,
--                  vRtrMplsS2lSubLspDstAddr }
--     ::= { vRtrMplsS2lSubLspTable 1 }
-- 
-- VRtrMplsS2lSubLspEntry ::= SEQUENCE {
--     vRtrMplsS2lSubLspDstAddrType            InetAddressType,
--     vRtrMplsS2lSubLspDstAddr                InetAddress,
--     vRtrMplsS2lSubLspRowStatus              RowStatus,
--     vRtrMplsS2lSubLspLastChange             TimeStamp,
--     vRtrMplsS2lSubLspType                   INTEGER,
--     vRtrMplsS2lSubLspProperties             BITS,
--     vRtrMplsS2lSubLspState                  INTEGER,
--     vRtrMplsS2lSubLspAdminState             TmnxAdminState,
--     vRtrMplsS2lSubLspOperState              TmnxOperState,
--     vRtrMplsS2lSubGroupId                   Unsigned32,
--     vRtrMplsS2lSubLspId                     MplsLSPID,
--     vRtrMplsS2lSubLspRetryTimeRemain        Unsigned32,
--     vRtrMplsS2lSubLspTunARHopLtIndex        Integer32,
--     vRtrMplsS2lSubLspNegotiatedMTU          Unsigned32,
--     vRtrMplsS2lSubLspFailCode               TmnxMplsLspFailCode,
--     vRtrMplsS2lSubLspFailNodeArType         InetAddressType,
--     vRtrMplsS2lSubLspFailNodeAddr           InetAddress,
--     vRtrMplsS2lSubLspOperBandwidth          Integer32,
--     vRtrMplsS2lSubLspTunCRHopLtIndex        Integer32,
--     vRtrMplsS2lSubLspOperMTU                Unsigned32,
--     vRtrMplsS2lSubLspLastResigAttpt         TimeStamp,
--     vRtrMplsS2lSubLspLastMBBType            TmnxMplsMBBType,
--     vRtrMplsS2lSubLspLastMBBEnd             TimeStamp,
--     vRtrMplsS2lSubLspLastMBBMetric          Unsigned32,
--     vRtrMplsS2lSubLspLastMBBState           INTEGER,
--     vRtrMplsS2lSubLspMBBTypeInProg          TmnxMplsMBBType,
--     vRtrMplsS2lSubLspMBBStarted             TimeStamp,
--     vRtrMplsS2lSubLspMBBNextRetry           Unsigned32,
--     vRtrMplsS2lSubLspMBBRetryAttpts         Unsigned32,
--     vRtrMplsS2lSubLspMBBFailCode            TmnxMplsLspFailCode,
--     vRtrMplsS2lSubLspMBBFailNodeType        InetAddressType,
--     vRtrMplsS2lSubLspMBBFailNodeAddr        InetAddress,
--     vRtrMplsS2lSubLspUpTime                 TimeStamp,
--     vRtrMplsS2lSubLspDownTime               TimeStamp,
--     vRtrMplsS2lSubLspIsFastRetry            TruthValue,
--     vRtrMplsS2lSubLspTimeoutIn              Unsigned32,
--     vRtrMplsS2lSubLspMBBTimeoutIn           Unsigned32
--     } 
-- 
-- vRtrMplsS2lSubLspDstAddrType OBJECT-TYPE
--      SYNTAX     InetAddressType
--      MAX-ACCESS not-accessible
--      STATUS     current
--      DESCRIPTION
--        "The value of vRtrMplsS2lSubLspDstAddrType indicates the type of 
--         vRtrMplsS2lSubLspDstAddr."
--      ::= { vRtrMplsS2lSubLspEntry 1 }   
--      
-- vRtrMplsS2lSubLspDstAddr     OBJECT-TYPE
--     SYNTAX      InetAddress (SIZE (0|4))
--     MAX-ACCESS  not-accessible
--     STATUS      current
--     DESCRIPTION
--         "The value of vRtrMplsS2lSubLspDstAddr indicates the IP address
--          of the destination address of the S2L sub LSP. "
--     ::= { vRtrMplsS2lSubLspEntry 2 }
--     
-- vRtrMplsS2lSubLspRowStatus    OBJECT-TYPE
--     SYNTAX      RowStatus
--     MAX-ACCESS  read-create
--     STATUS      current
--     DESCRIPTION
--         "The value of vRtrMplsS2lSubLspRowStatus specifies row status used for 
--         creation, deletion, or control of vRtrMplsLspPathTable entries.  Before
--         the row can be placed into the 'active' state vRtrMplsS2lSubLspType must
--         have been assigned a valid value."
--     ::= { vRtrMplsS2lSubLspEntry 3 }
-- 
-- vRtrMplsS2lSubLspLastChange       OBJECT-TYPE
--     SYNTAX      TimeStamp
--     MAX-ACCESS  read-only
--     STATUS      current
--     DESCRIPTION
--         "The value of vRtrMplsS2lSubLspRowStatus indicates the sysUpTime when 
--         this row was last modified."
--     ::= { vRtrMplsS2lSubLspEntry 4}
-- 
-- vRtrMplsS2lSubLspType     OBJECT-TYPE
--     SYNTAX      INTEGER {
--                     s2lPath (1)
--                 }
--     MAX-ACCESS  read-only
--     STATUS      current
--     DESCRIPTION
--         "The value of vRtrMplsS2lSubLspRowStatus indicates the value that 
--         represents the role this S2L sub LSP is taking within this P2MP LSP."
--     ::= { vRtrMplsS2lSubLspEntry 5 }
-- 
-- vRtrMplsS2lSubLspProperties   OBJECT-TYPE
--     SYNTAX      BITS {
--                     recordRoute (0),
--                     adaptive (1),
--                     cspf (2),
--                     mergeable (3),
--                     fastReroute (4)
--                 }
--     MAX-ACCESS  read-only
--     STATUS      current
--     DESCRIPTION
--         "The value of vRtrMplsS2lSubLspProperties indicates the set of 
--          configured properties.  For example, if the S2L sub LSP is an adaptive
--          S2L sub LSP, the bit corresponding to bit value 1 is set."
--     ::= { vRtrMplsS2lSubLspEntry 6 }
-- 
-- vRtrMplsS2lSubLspState    OBJECT-TYPE
--     SYNTAX      INTEGER {
--                     unknown (1),
--                     active (2),
--                     inactive (3)
--                 }
--     MAX-ACCESS  read-only
--     STATUS      current
--     DESCRIPTION
--         "The value of vRtrMplsS2lSubLspState indicates the  current working 
--         state of this S2L sub LSP within this LSP."
--     DEFVAL { unknown }
--     ::= { vRtrMplsS2lSubLspEntry 7 }
--      
-- vRtrMplsS2lSubLspAdminState       OBJECT-TYPE
--     SYNTAX      TmnxAdminState
--     MAX-ACCESS  read-create
--     STATUS      current
--     DESCRIPTION
--         "The value of vRtrMplsS2lSubLspAdminState specifies the desired 
--         administrative state for this P2MP S2L sub LSP."
--     DEFVAL { inService }
--     ::= { vRtrMplsS2lSubLspEntry 8 }
-- 
-- vRtrMplsS2lSubLspOperState        OBJECT-TYPE
--     SYNTAX      TmnxOperState
--     MAX-ACCESS  read-only
--     STATUS      current
--     DESCRIPTION
--         "The value of vRtrMplsS2lSubLspAdminState indicates the current 
--         operational state of this P2MP S2L sub LSP."
--     ::= { vRtrMplsS2lSubLspEntry 9 }
-- 
-- vRtrMplsS2lSubGroupId OBJECT-TYPE
--     SYNTAX      Unsigned32
--     MAX-ACCESS  read-only
--     STATUS      current
--     DESCRIPTION
--         "The value of vRtrMplsS2lSubGroupId indicates the value which 
--         identifies the group for this entry."
--     ::= { vRtrMplsS2lSubLspEntry  10 }
-- 
-- vRtrMplsS2lSubLspId OBJECT-TYPE
--     SYNTAX      MplsLSPID
--     MAX-ACCESS  read-only
--     STATUS      current
--     DESCRIPTION
--         "The value of vRtrMplsS2lSubLspId indicates the value which identifies 
--         the label switched path that is signaled for this entry."
--     ::= { vRtrMplsS2lSubLspEntry 11 }    
--     
-- vRtrMplsS2lSubLspRetryTimeRemain       OBJECT-TYPE
--     SYNTAX      Unsigned32
--     UNITS        "10-milliseconds"
--     MAX-ACCESS  read-only
--     STATUS      current
--     DESCRIPTION
--         "The value of vRtrMplsS2lSubLspRetryTimeRemain indicates the time 
--         to signal this S2L sub LSP."
--     ::= { vRtrMplsS2lSubLspEntry 12 }
-- 
-- vRtrMplsS2lSubLspTunARHopLtIndex   OBJECT-TYPE
--     SYNTAX      Integer32 (0|1..2147483647)
--     MAX-ACCESS  read-only
--     STATUS      current
--     DESCRIPTION
--         "The value of vRtrMplsS2lSubLspTunARHopLtIndex indicates Primary index 
--         into the mplsTunnelARHopTable identifying a particular recorded hop 
--         list. A value of 0 implies that there is no recored hop list associated
--         with this P2MP LSP path."
--     ::= { vRtrMplsS2lSubLspEntry 13 }
--     
-- vRtrMplsS2lSubLspNegotiatedMTU     OBJECT-TYPE
--     SYNTAX      Unsigned32
--     MAX-ACCESS  read-only
--     STATUS      current
--     DESCRIPTION
--         "The value of vRtrMplsS2lSubLspNegotiatedMTU indicates the size 
--          for the Maximum transmission unit (MTU) that is negotiated
--          during establishment of this P2MP LSP Path."
--     DEFVAL { 0 }
--     ::= { vRtrMplsS2lSubLspEntry 14 }
-- 
-- vRtrMplsS2lSubLspFailCode     OBJECT-TYPE
--     SYNTAX      TmnxMplsLspFailCode
--     MAX-ACCESS  read-only
--     STATUS      current
--     DESCRIPTION
--         "The value of vRtrMplsS2lSubLspFailCode indicates the reason code
--          for P2MP LSP Path failure. A value of 0 indicates that no failure 
--          has occurred."
--     ::= { vRtrMplsS2lSubLspEntry 15 }
-- 
-- vRtrMplsS2lSubLspFailNodeArType     OBJECT-TYPE
--     SYNTAX      InetAddressType
--     MAX-ACCESS  read-only
--     STATUS      current
--     DESCRIPTION
--         "The value of vRtrMplsS2lSubLspFailNodeArType indicates type of 
--          vRtrMplsS2lSubLspFailNodeAddr. When no failure has occurred, this value is 0."
--     ::= { vRtrMplsS2lSubLspEntry 16 }    
-- 
-- vRtrMplsS2lSubLspFailNodeAddr     OBJECT-TYPE
--     SYNTAX      InetAddress (SIZE (0|4))
--     MAX-ACCESS  read-only
--     STATUS      current
--     DESCRIPTION
--         "The value of vRtrMplsS2lSubLspFailNodeAddr indicates the IP address
--          of the node in the P2MP S2L sub LSP at which the P2MP S2L sub LSP 
--          failed."
--     ::= { vRtrMplsS2lSubLspEntry 17 }
--   
-- vRtrMplsS2lSubLspOperBandwidth  OBJECT-TYPE
--     SYNTAX      Integer32
--     UNITS       "mega-bits per second"
--     MAX-ACCESS  read-only
--     STATUS      current
--     DESCRIPTION
--         "The value of vRtrMplsS2lSubLspOperBandwidth indicates the amount of
--          bandwidth in mega-bits per seconds (Mbps) that has been reserved
--          for the operational P2MP S2L sub LSP.
-- 
--          When make-before-break functionality for the P2MP LSP is enabled and 
--          if the S2L sub LSP bandwidth is changed, the resources allocated to the
--          existing P2MP LSP paths will not be released until a new S2L sub LSP 
--          with the new bandwidth settings has been established. While a new S2L 
--          sub LSP is being signaled, the administrative value and the operational 
--          values of the S2L sub LSP bandwidth may differ. The value of 
--          vRtrMplsS2lSubLspOperBandwidth specifies the bandwidth requirements for
--          the new P2MP S2L sub LSP trying to be established whereas the value of 
--          vRtrMplsS2lSubLspOperBandwidth specifies the bandwidth reserved 
--          for the existing P2MP S2L sub LSP."
--     ::= { vRtrMplsS2lSubLspEntry 18 }
-- 
-- vRtrMplsS2lSubLspTunCRHopLtIndex   OBJECT-TYPE
--     SYNTAX      Integer32 (0|1..2147483647)
--     MAX-ACCESS  read-only
--     STATUS      current
--     DESCRIPTION
--         "The value of vRtrMplsS2lSubLspTunCRHopLtIndex indicates
--          primary index into the vRtrMplsTunnelCHopTable identifying a
--          particular computed hop list. A value of 0 implies that there
--          is no computed hop list associated with this LSP path."
--     ::= { vRtrMplsS2lSubLspEntry 19 }
--     
-- vRtrMplsS2lSubLspOperMTU     OBJECT-TYPE
--     SYNTAX      Unsigned32
--     MAX-ACCESS  read-only
--     STATUS      current
--     DESCRIPTION
--         "The value of vRtrMplsS2lSubLspOperMTU indicates the size 
--          for the Maximum transmission unit (MTU) that is currently
--          operation for this P2MP LSP Path."
--     ::= { vRtrMplsS2lSubLspEntry 20 }
--     
-- vRtrMplsS2lSubLspLastResigAttpt       OBJECT-TYPE
--     SYNTAX      TimeStamp
--     MAX-ACCESS  read-only
--     STATUS      current
--     DESCRIPTION
--         "The value of vRtrMplsS2lSubLspLastResigAttpt indicates the 
--          sysUpTime when the last attempt to resignal this LSP was made."
--     ::= { vRtrMplsS2lSubLspEntry 21 } 
-- 
-- vRtrMplsS2lSubLspLastMBBType      OBJECT-TYPE
--     SYNTAX      TmnxMplsMBBType
--     MAX-ACCESS  read-only
--     STATUS      current
--     DESCRIPTION
--         "The value of vRtrMplsS2lSubLspLastMBBType indicates the type of 
--          last Make-before-break (MBB).  If 'none', then no MBB has been
--          attempted." 
--     ::= { vRtrMplsS2lSubLspEntry 22 } 
-- 
-- vRtrMplsS2lSubLspLastMBBEnd       OBJECT-TYPE
--     SYNTAX      TimeStamp
--     MAX-ACCESS  read-only
--     STATUS      current
--     DESCRIPTION
--         "The value of vRtrMplsS2lSubLspLastMBBEnd indicates the 
--          sysUpTime when the last MBB ended."
--     ::= { vRtrMplsS2lSubLspEntry 23 } 
-- 
-- vRtrMplsS2lSubLspLastMBBMetric              OBJECT-TYPE
--     SYNTAX      Unsigned32
--     MAX-ACCESS  read-only
--     STATUS      current
--     DESCRIPTION
--         "The value of vRtrMplsS2lSubLspLastMBBMetric  indicates  the 
--          cost of the traffic engineered S2L sub LSP for the S2L sub LSP 
--          prior to MBB."
--     ::= { vRtrMplsS2lSubLspEntry 24 }     
-- 
-- vRtrMplsS2lSubLspLastMBBState  OBJECT-TYPE
--     SYNTAX      INTEGER {
--                     none (1),
--                     success (2), 
--                     fail(3)
--                 }
--     MAX-ACCESS  read-only
--     STATUS      current
--     DESCRIPTION
--         "The value of vRtrMplsS2lSubLspLastMBBState indicates whether the last 
--          Make-before-break was successful or failed. 
--          Possible states are:
--          none (1)        - no make-before-break invoked 
--          success (2)     - make-before-break successful
--          fail (3)        - make-before-break failed."
--     ::= { vRtrMplsS2lSubLspEntry 25 }    
-- 
-- vRtrMplsS2lSubLspMBBTypeInProg      OBJECT-TYPE
--     SYNTAX      TmnxMplsMBBType
--     MAX-ACCESS  read-only
--     STATUS      current
--     DESCRIPTION
--         "The value of vRtrMplsS2lSubLspMBBTypeInProg indicates the type of the
--          Make-before-break (MBB) that is in progress. If 'none', then no MBB
--          is in progress."
--    ::= { vRtrMplsS2lSubLspEntry 26 } 
-- 
-- vRtrMplsS2lSubLspMBBStarted       OBJECT-TYPE
--     SYNTAX      TimeStamp
--     MAX-ACCESS  read-only
--     STATUS      current
--     DESCRIPTION
--         "The value of vRtrMplsS2lSubLspMBBStarted indicates the 
--          sysUpTime when the in-progress MBB started."
--     ::= { vRtrMplsS2lSubLspEntry 27 } 
--     
-- vRtrMplsS2lSubLspMBBNextRetry      OBJECT-TYPE
--     SYNTAX      Unsigned32
--     UNITS       "seconds"     
--     MAX-ACCESS  read-only
--     STATUS      current
--     DESCRIPTION
--         "The value of vRtrMplsS2lSubLspMBBNextRetry indicates the amount 
--          of time remaining in seconds before the next attempt is made to retry 
--          the in-progress MBB."
--     ::= { vRtrMplsS2lSubLspEntry 28 } 
-- 
-- vRtrMplsS2lSubLspMBBRetryAttpts       OBJECT-TYPE
--     SYNTAX      Unsigned32
--     MAX-ACCESS  read-only
--     STATUS      current
--     DESCRIPTION
--         "The value of vRtrMplsS2lSubLspMBBRetryAttpts indicates 'n' where
--          nth attempt for the MBB is in progress."
--     ::= { vRtrMplsS2lSubLspEntry 29 }         
-- 
-- vRtrMplsS2lSubLspMBBFailCode     OBJECT-TYPE
--     SYNTAX      TmnxMplsLspFailCode
--     MAX-ACCESS  read-only
--     STATUS      current
--     DESCRIPTION
--         "The value of vRtrMplsS2lSubLspMBBFailCode indicates the reason code
--          for in-progress MBB failure. A value of 'none' indicates that no 
--          failure has occurred."
--     ::= { vRtrMplsS2lSubLspEntry 30 }
-- 
-- vRtrMplsS2lSubLspMBBFailNodeType OBJECT-TYPE
--      SYNTAX     InetAddressType
--      MAX-ACCESS read-only
--      STATUS     current
--      DESCRIPTION
--        "The value of vRtrMplsS2lSubLspMBBFailNodeType indicates the type of 
--         vRtrMplsS2lSubLspMBBFailNodeAddr. A value of 'unknown' indicates that 
--         no failure has occurred."
--      ::= { vRtrMplsS2lSubLspEntry 31 }   
--      
-- vRtrMplsS2lSubLspMBBFailNodeAddr     OBJECT-TYPE
--     SYNTAX      InetAddress (SIZE (0|4))
--     MAX-ACCESS  read-only
--     STATUS      current
--     DESCRIPTION
--         "The value of vRtrMplsS2lSubLspMBBFailNodeAddr indicates the IP address
--          of the node in the S2L sub LSP at which the in-progress MBB failed. A 
--          value of 'unknown' for vRtrMplsS2lSubLspMBBFailNodeType and empty 
--          string for vRtrMplsS2lSubLspMBBFailNodeAddr indicates that no failure 
--          has occurred."
--     ::= { vRtrMplsS2lSubLspEntry  32 }
-- 
-- vRtrMplsS2lSubLspUpTime OBJECT-TYPE
--     SYNTAX      TimeStamp
--     MAX-ACCESS  read-only
--     STATUS      current
--     DESCRIPTION
--         "The value of vRtrMplsS2lSubLspUpTime indicates the timestamp
--          when the S2l came up."
--     ::= { vRtrMplsS2lSubLspEntry 33 }
-- 
-- vRtrMplsS2lSubLspDownTime  OBJECT-TYPE
--     SYNTAX      TimeStamp
--     MAX-ACCESS  read-only
--     STATUS      current
--     DESCRIPTION
--         "The value of vRtrMplsS2lSubLspDownTime indicates the timestamp
--          when the S2l went down."
--     ::= { vRtrMplsS2lSubLspEntry 34 }    
-- 
-- vRtrMplsS2lSubLspIsFastRetry      OBJECT-TYPE
--     SYNTAX      TruthValue
--     MAX-ACCESS  read-only
--     STATUS      current
--     DESCRIPTION
--         "The value of vRtrMplsS2lSubLspIsFastRetry indicates which retry 
--          timer is being referred to by vRtrMplsS2lSubLspRetryTimeRemain. 
-- 
--          When the value of vRtrMplsLspPathIsFastRetry is set to 'true', 
--          vRtrMplsLspPathRetryTimeRemaining is referring to the P2MP
--          S2L path fast timer, vRtrMplsGenP2mpS2lFastRetry.
-- 
--          When the value of vRtrMplsLspPathIsFastRetry is set to 'false', 
--          vRtrMplsS2lSubLspRetryTimeRemain is referring to the LSP retry timer, 
--          vRtrMplsLspRetryTimer."
--     ::= { vRtrMplsS2lSubLspEntry 35 }
-- 
-- vRtrMplsS2lSubLspTimeoutIn      OBJECT-TYPE
--     SYNTAX      Unsigned32
--     UNITS       "seconds"
--     MAX-ACCESS  read-only
--     STATUS      current
--     DESCRIPTION
--         "The value of vRtrMplsS2lSubLspTimeoutIn specifies the amount of time
--          remaining, in seconds, for the S2L path state to time out after the
--          initial PATH message has been sent. If the timer expires and the S2L
--          path has not become operationally up, the S2L path is torn down and
--          the retry timer is started to schedule a new retry cycle."
--     ::= { vRtrMplsS2lSubLspEntry 36 }
-- 
-- vRtrMplsS2lSubLspMBBTimeoutIn   OBJECT-TYPE
--     SYNTAX      Unsigned32
--     UNITS       "seconds"
--     MAX-ACCESS  read-only
--     STATUS      current
--     DESCRIPTION
--         "The value of vRtrMplsS2lSubLspMBBTimeoutIn specifies the amount of
--          time remaining, in seconds, for the in-progress S2L MBB path state to
--          time out after the initial PATH message has been sent. If the timer
--          expires and the in-progress S2L MBB path has not become operationally
--          up, the S2L MBB path is torn down and the retry timer is started to
--          schedule a new retry cycle."
--     ::= { vRtrMplsS2lSubLspEntry 37 }
--
--  The Virtual Router MPLS P2MP S2L SUB LSP Statistics Table
--
--  Augmentation of the vRtrMplsS2lSubLspTable.
--  Use of AUGMENTS clause implies a one-to-one dependent relationship 
--  between the base table, vRtrMplsS2lSubLspTable, and the augmenting table, 
--  vRtrMplsS2lSubLspStatTable. This in effect extends the vRtrMplsS2lSubLspTable 
--  with additional columns.  
--  Creation (or deletion) of a row in the vRtrMplsS2lSubLspTable results in 
--  the same fate for the row in the vRtrMplsS2lSubLspStatTable.
--

-- vRtrMplsS2lSubLspStatTable    OBJECT-TYPE
--     SYNTAX      SEQUENCE OF VRtrMplsS2lSubLspStatEntry
--     MAX-ACCESS  not-accessible
--     STATUS      current
--     DESCRIPTION
--         "The vRtrMplsS2lSubLspStatTable has an entry for each Labeled Switch
--          Path (LSP) configured for a virtual router in the system."
--     ::= { tnMplsObjs 29 }
-- 
-- vRtrMplsS2lSubLspStatEntry    OBJECT-TYPE
--     SYNTAX      VRtrMplsS2lSubLspStatEntry
--     MAX-ACCESS  not-accessible
--     STATUS      current
--     DESCRIPTION
--         "Each row entry represents a collection of statistics for a P2MP
--          Source to Leaf (S2L) Sub Labeled Switch Path (LSP) configured for a i
--          virtual router in the system.  
-- 
--          Entries cannot be created and deleted via SNMP SET operations."
--     AUGMENTS { vRtrMplsS2lSubLspEntry }
--     ::= { vRtrMplsS2lSubLspStatTable 1 }
-- 
-- VRtrMplsS2lSubLspStatEntry ::= SEQUENCE {
--     vRtrMplsS2lSubLspTimeUp                 TimeInterval, 
--     vRtrMplsS2lSubLspTimeDown               TimeInterval, 
--     vRtrMplsS2lSubLspRetryAttempts          Counter32, 
--     vRtrMplsS2lSubLspTransitionCount        Counter32, 
--     vRtrMplsS2lSubLspCspfQueries            Counter32
-- }
-- 
-- vRtrMplsS2lSubLspTimeUp   OBJECT-TYPE
--     SYNTAX      TimeInterval
--     UNITS       "10-milliseconds"    
--     MAX-ACCESS  read-only
--     STATUS      current
--     DESCRIPTION
--         "The value of vRtrMplsS2lSubLspTimeUp indicates the total time that 
--          this LSP S2l has been operational.  For example, the percentage up 
--          time can be determined by computing 
--          (vRtrMplsS2lSubLspTimeUp/vRtrMplsLspAge * 100 %)."
--     ::= { vRtrMplsS2lSubLspStatEntry 1 }
--         
-- vRtrMplsS2lSubLspTimeDown OBJECT-TYPE
--     SYNTAX      TimeInterval
--     UNITS       "10-milliseconds"    
--     MAX-ACCESS  read-only
--     STATUS      current
--     DESCRIPTION
--         "The value of vRtrMplsS2lSubLspTimeUp indicates the total time that 
--         this LSP S2l has not been operational."
--     ::= { vRtrMplsS2lSubLspStatEntry 2 }
-- 
-- vRtrMplsS2lSubLspRetryAttempts       OBJECT-TYPE
--     SYNTAX      Counter32
--     MAX-ACCESS  read-only
--     STATUS      current
--     DESCRIPTION
--          "The value of vRtrMplsS2lSubLspRetryAttempts indicates 
--          the number of unsuccessful attempts which have been made to 
--          signal this S2l. As soon as the S2l gets signalled, this is
--          set to 0."
--     ::= { vRtrMplsS2lSubLspStatEntry 3 }
-- 
-- vRtrMplsS2lSubLspTransitionCount    OBJECT-TYPE
--     SYNTAX      Counter32
--     MAX-ACCESS  read-only
--     STATUS      current
--     DESCRIPTION
--         "The value of vRtrMplsS2lSubLspTransitionCount indicates the number
--          of transitions that have occurred for this LSP."
--     ::= { vRtrMplsS2lSubLspStatEntry 4 }
-- 
-- vRtrMplsS2lSubLspCspfQueries     OBJECT-TYPE
--     SYNTAX      Counter32
--     MAX-ACCESS  read-only
--     STATUS      current
--     DESCRIPTION
--         "The value of vRtrMplsS2lSubLspCspfQueries indicates the number 
--          of CSPF queries that have been made for this LSP S2l."
--     ::= { vRtrMplsS2lSubLspStatEntry 5 }

--
-- SRLG Database RouterID Table
--

-- vRtrMplsSrlgDBRtrIdTblLastChg OBJECT-TYPE
--     SYNTAX      TimeStamp
--     MAX-ACCESS  read-only
--     STATUS      current
--     DESCRIPTION
--         "The value of vRtrMplsSrlgDBRtrIdTblLastChg indicates the
--          sysUpTime at the time of the last modification to 
--          vRtrMplsSrlgDBRtrIdTable by adding, deleting an entry or change
--          to a writable object in the table.
-- 
--          If no changes were made to the table since the last 
--          re-initialization of the local network management subsystem, 
--          then this object contains a zero value."
--     ::= { tnMplsObjs 30 } 
-- 
-- vRtrMplsSrlgDBRtrIdTable OBJECT-TYPE
--     SYNTAX      SEQUENCE OF VRtrMplsSrlgDBRtrIdEntry
--     MAX-ACCESS  not-accessible
--     STATUS      current
--     DESCRIPTION
--         "The vRtrMplsSrlgDBRtrIdTable has an entry for each router-id 
--         configured under user Shared Risk Link Group (SRLG) database. The user 
--          manually enters the SRLG membership information for any link
--          in the network, into the user SRLG database."
--     ::= { tnMplsObjs 31 }
-- 
-- vRtrMplsSrlgDBRtrIdEntry      OBJECT-TYPE
--     SYNTAX      VRtrMplsSrlgDBRtrIdEntry
--     MAX-ACCESS  not-accessible
--     STATUS      current
--     DESCRIPTION
--         "Each row entry represents a router ID under which interface entries 
--         would be configured for the SRLG database table.
--   
--          A row can be created or deleted via SNMP SET requests."
--     INDEX { tnSysSwitchId, vRtrID, 
--             vRtrMplsSrlgDBRtrIdRouterID
--               }
--     ::= { vRtrMplsSrlgDBRtrIdTable 1 }
-- 
-- VRtrMplsSrlgDBRtrIdEntry ::= SEQUENCE {
--     vRtrMplsSrlgDBRtrIdRouterID                     TmnxMplsRouterId,
--     vRtrMplsSrlgDBRtrIdRowStatus                    RowStatus,
--     vRtrMplsSrlgDBRtrIdAdminState                   TmnxAdminState,
--     vRtrMplsSrlgDBRtrIdLastChanged                  TimeStamp
-- }
-- 
-- vRtrMplsSrlgDBRtrIdRouterID OBJECT-TYPE 
--     SYNTAX      TmnxMplsRouterId 
--     MAX-ACCESS  not-accessible 
--     STATUS      current 
--     DESCRIPTION 
--         "The value of vRtrMplsSrlgDBRtrIdRouterID specifies a 32-bit integer uniquely
--          identifying the router in the Autonomous System.  By convention 
--          to ensure uniqueness, this may default to the value of one of the 
--          router's IPv4 host addresses, represented as a 32-bit unsigned 
--          integer, if IPv4 is configured on the router. The router-id can be 
--          either the local one or some remote router." 
--     ::= { vRtrMplsSrlgDBRtrIdEntry 1 } 
-- 
-- vRtrMplsSrlgDBRtrIdRowStatus    OBJECT-TYPE
--     SYNTAX      RowStatus
--     MAX-ACCESS  read-create
--     STATUS      current
--     DESCRIPTION
--         "vRtrMplsSrlgDBRtrIdRowStatus is used to create, delete or 
--          control entries in the vRtrMplsSrlgDBRtrIdTable."
--     ::= { vRtrMplsSrlgDBRtrIdEntry 2 }
-- 
-- vRtrMplsSrlgDBRtrIdAdminState       OBJECT-TYPE
--     SYNTAX      TmnxAdminState
--     MAX-ACCESS  read-create
--     STATUS      current
--     DESCRIPTION
--         "The value of vRtrMplsSrlgDBRtrIdAdminState specifies the desired 
--         administrative state for the router-id entry in the vRtrMplsSrlgDBRtrIdTable."
--     DEFVAL { outOfService }
--     ::= { vRtrMplsSrlgDBRtrIdEntry 3 }
-- 
-- vRtrMplsSrlgDBRtrIdLastChanged  OBJECT-TYPE
--     SYNTAX      TimeStamp
--     MAX-ACCESS  read-only
--     STATUS      current
--     DESCRIPTION
--         "The value of vRtrMplsSrlgDBRtrIdLastChanged indicates the timestamp
--          of last change to this row in vRtrMplsSrlgDBRtrIdTable."
--     ::= { vRtrMplsSrlgDBRtrIdEntry 4 }
    
--
-- SRLG Database Interface Table
--

-- vRtrMplsSrlgDBIfTblLastChanged OBJECT-TYPE
--     SYNTAX      TimeStamp
--     MAX-ACCESS  read-only
--     STATUS      current
--     DESCRIPTION
--         "The value of vRtrMplsSrlgDBIfTblLastChanged indicates the
--          sysUpTime at the time of the last modification to 
--          vRtrMplsSrlgDBIfTable by adding, deleting an entry or change
--          to a writable object in the table.
-- 
--          If no changes were made to the table since the last 
--          re-initialization of the local network management subsystem, 
--          then this object contains a zero value."
--     ::= { tnMplsObjs 32 } 
-- 
-- vRtrMplsSrlgDBIfTable OBJECT-TYPE
--     SYNTAX      SEQUENCE OF VRtrMplsSrlgDBIfEntry
--     MAX-ACCESS  not-accessible
--     STATUS      current
--     DESCRIPTION
--         "The vRtrMplsSrlgDBIfTable has an entry for each Shared Risk 
--          Link Group (SRLG) groups associated with a interface which is 
--          validated as part of a router ID in the routing table. The user 
--          manually enters the SRLG membership information for any link
--          in the network, into the user SRLG database."
--     ::= { tnMplsObjs 33 }
-- 
-- vRtrMplsSrlgDBIfEntry      OBJECT-TYPE
--     SYNTAX      VRtrMplsSrlgDBIfEntry
--     MAX-ACCESS  not-accessible
--     STATUS      current
--     DESCRIPTION
--         "Each row entry represents an SRLG group associated with a interface
--          which is validated as part of a router ID in the routing table.
--   
--          A row can be created or deleted via SNMP SET requests."
--     INDEX { tnSysSwitchId, vRtrID, 
--             vRtrMplsSrlgDBRtrIdRouterID,
--             vRtrMplsSrlgDBIfIntIpAddrType, 
--             vRtrMplsSrlgDBIfIntIpAddr, 
--             IMPLIED vRtrMplsSrlgDBIfSrlgGroupName 
--               }
--     ::= { vRtrMplsSrlgDBIfTable 1 }
-- 
-- VRtrMplsSrlgDBIfEntry ::= SEQUENCE {
--     vRtrMplsSrlgDBIfIntIpAddrType                InetAddressType,
--     vRtrMplsSrlgDBIfIntIpAddr                    InetAddress,
--     vRtrMplsSrlgDBIfSrlgGroupName                TNamedItem,
--     vRtrMplsSrlgDBIfRowStatus                    RowStatus,
--     vRtrMplsSrlgDBIfLastChanged                  TimeStamp
-- }
-- 
-- vRtrMplsSrlgDBIfIntIpAddrType OBJECT-TYPE
--      SYNTAX     InetAddressType
--      MAX-ACCESS not-accessible
--      STATUS     current
--      DESCRIPTION
--        "The value of vRtrMplsSrlgDBIfIntIpAddrType indicates the type of 
--         vRtrMplsSrlgDBIfIntIpAddr."
--      ::= { vRtrMplsSrlgDBIfEntry 1 }   
--      
-- vRtrMplsSrlgDBIfIntIpAddr     OBJECT-TYPE
--     SYNTAX      InetAddress (SIZE (0|4))
--     MAX-ACCESS  not-accessible
--     STATUS      current
--     DESCRIPTION
--         "The value of vRtrMplsSrlgDBIfIntIpAddr indicates the IP address
--          of the interface."
--     ::= { vRtrMplsSrlgDBIfEntry 2 }
--     
-- vRtrMplsSrlgDBIfSrlgGroupName OBJECT-TYPE
--     SYNTAX      TNamedItem
--     MAX-ACCESS  not-accessible
--     STATUS      current
--     DESCRIPTION
--         "The value of vRtrMplsSrlgDBIfSrlgGroupName indicates the SRLG group name."
--     ::= { vRtrMplsSrlgDBIfEntry 3 }
-- 
-- vRtrMplsSrlgDBIfRowStatus    OBJECT-TYPE
--     SYNTAX      RowStatus
--     MAX-ACCESS  read-create
--     STATUS      current
--     DESCRIPTION
--         "vRtrMplsSrlgDBIfRowStatus is used to create, delete or 
--          control entries in the vRtrMplsSrlgDBIfTable."
--     ::= { vRtrMplsSrlgDBIfEntry 4 }
-- 
-- vRtrMplsSrlgDBIfLastChanged  OBJECT-TYPE
--     SYNTAX      TimeStamp
--     MAX-ACCESS  read-only
--     STATUS      current
--     DESCRIPTION
--         "The value of vRtrMplsSrlgDBIfLastChanged indicates the timestamp
--          of last change to this row in vRtrMplsSrlgDBIfTable."
--     ::= { vRtrMplsSrlgDBIfEntry 5 }

--
--   Virtual Router MPLS InSegment Table
--
--  Augmentation of the mplsInSegmentTable.
--  Use of AUGMENTS clause implies a one-to-one dependent relationship 
--  between the base table, mplsInSegmentTable, and the augmenting table, 
--  vRtrMplsInSegmentTable. This in effect extends the mplsInSegmentTable
--  with additional columns.  
--  Creation (or deletion) of a row in the mplsInSegmentTable results in 
--  the same fate for the row in the vRtrMplsInSegmentTable.
--

-- vRtrMplsInSegmentTable OBJECT-TYPE
--     SYNTAX      SEQUENCE OF VRtrMplsInSegmentEntry
--     MAX-ACCESS  not-accessible
--     STATUS      current
--     DESCRIPTION
--         "The vRtrMplsInSegmentTable augments the mplsInSegmentTable  
--          in the MPLS-LSR-MIB."
--     ::= { tnMplsObjs 34 }
-- 
-- vRtrMplsInSegmentEntry OBJECT-TYPE
--     SYNTAX      VRtrMplsInSegmentEntry
--     MAX-ACCESS  not-accessible
--     STATUS      current
--     DESCRIPTION
--         "A row entry in this table corresponds to a row entry in the 
--          mplsInSegmentTable and adds to the information contained in 
--          that table."
--     AUGMENTS { mplsInSegmentEntry }
--     ::= { vRtrMplsInSegmentTable 1 }
-- 
-- VRtrMplsInSegmentEntry ::= SEQUENCE {
--     vRtrMplsInSegmentNumS2ls       Unsigned32
-- }
-- 
-- vRtrMplsInSegmentNumS2ls OBJECT-TYPE
--     SYNTAX      Unsigned32
--     MAX-ACCESS  read-only
--     STATUS      current
--     DESCRIPTION
--         "The value of vRtrMplsInSegmentNumS2ls specifies number of S2Ls
--           on the insegment."
--     ::= { vRtrMplsInSegmentEntry 1 }    

--
--   Virtual Router MPLS OutSegment Table
--
--  Augmentation of the mplsOutSegmentTable.
--  Use of AUGMENTS clause implies a one-to-one dependent relationship 
--  between the base table, mplsOutSegmentTable, and the augmenting table, 
--  vRtrMplsOutSegmentTable. This in effect extends the mplsOutSegmentTable
--  with additional columns.  
--  Creation (or deletion) of a row in the mplsOutSegmentTable results in 
--  the same fate for the row in the vRtrMplsOutSegmentTable.
--

-- vRtrMplsOutSegmentTable OBJECT-TYPE
--     SYNTAX      SEQUENCE OF VRtrMplsOutSegmentEntry
--     MAX-ACCESS  not-accessible
--     STATUS      current
--     DESCRIPTION
--         "The vRtrMplsOutSegmentTable augments the mplsOutSegmentTable  
--          in the MPLS-LSR-MIB."
--     ::= { tnMplsObjs 35 }
-- 
-- vRtrMplsOutSegmentEntry OBJECT-TYPE
--     SYNTAX      VRtrMplsOutSegmentEntry
--     MAX-ACCESS  not-accessible
--     STATUS      current
--     DESCRIPTION
--         "A row entry in this table corresponds to a row entry in the 
--          mplsOutSegmentTable and adds to the information contained in 
--          that table."
--     AUGMENTS { mplsOutSegmentEntry }
--     ::= { vRtrMplsOutSegmentTable 1 }
-- 
-- VRtrMplsOutSegmentEntry ::= SEQUENCE {
--     vRtrMplsOutSegmentNumS2ls       Unsigned32
-- }
-- 
-- vRtrMplsOutSegmentNumS2ls OBJECT-TYPE
--     SYNTAX      Unsigned32
--     MAX-ACCESS  read-only
--     STATUS      current
--     DESCRIPTION
--         "The value of vRtrMplsOutSegmentNumS2ls specifies number of S2Ls
--           on the outsegment."
--     ::= { vRtrMplsOutSegmentEntry 1 }    

--
--  The MPLS Label Switched Path (LSP) Egress/Ingress Statistics Table
--

vRtrMplsLspStatsTblLastChgd OBJECT-TYPE
    SYNTAX      TimeStamp
    MAX-ACCESS  read-only
    STATUS      current
    DESCRIPTION
        "Timestamp of the last change to the vRtrMplsLspStatsTable
         either from adding a row or removing a row."
    ::= { tnMplsObjs 37 }

vRtrMplsLspStatsTable    OBJECT-TYPE
    SYNTAX      SEQUENCE OF VRtrMplsLspStatsEntry
    MAX-ACCESS  not-accessible
    STATUS      current
    DESCRIPTION
         "vRtrMplsLspStatsTable controls Statsistics in the ess data-path
          at the ingress Label Switched Path (LSP) for an Mpls-Lsp FEC."
    ::= { tnMplsObjs 38 }

vRtrMplsLspStatsEntry    OBJECT-TYPE
    SYNTAX      VRtrMplsLspStatsEntry
    MAX-ACCESS  not-accessible
    STATUS      current
    DESCRIPTION
        "A row in this table represents information about the Statistics
        collection per MPLS LSP."
    INDEX  { tnSysSwitchId,
             vRtrID,
             vRtrMplsLspStatsType, 
             vRtrMplsLspStatsSenderAddrType,
             vRtrMplsLspStatsSenderAddr,
             vRtrMplsLspStatsLspName }
    ::= { vRtrMplsLspStatsTable 1 }

VRtrMplsLspStatsEntry ::= SEQUENCE {
    vRtrMplsLspStatsType                    INTEGER,
    vRtrMplsLspStatsSenderAddrType          InetAddressType,
    vRtrMplsLspStatsSenderAddr              InetAddress,
    vRtrMplsLspStatsLspName                 TNamedItem,
    vRtrMplsLspStatsRowStatus               RowStatus,
    vRtrMplsLspStatsLastChanged             TimeStamp,
    vRtrMplsLspStatsCollectStats            TruthValue,
    vRtrMplsLspStatsAccntingPolicy          Unsigned32,
    vRtrMplsLspStatsAdminState              TmnxAdminState
}

vRtrMplsLspStatsType                 OBJECT-TYPE  
    SYNTAX       INTEGER {  
                             egress (0),
                             ingress (1)
                         }   
    MAX-ACCESS   not-accessible  
    STATUS       current  
    DESCRIPTION  
        "The value of vRtrMplsLspStatsType indicates the type of statistics." 
    ::= { vRtrMplsLspStatsEntry 1 }   
    
vRtrMplsLspStatsSenderAddrType OBJECT-TYPE  
    SYNTAX       InetAddressType  
    MAX-ACCESS   not-accessible  
    STATUS       current  
    DESCRIPTION  
        "The value of vRtrMplsLspStatsSenderAddrType indicates address type of 
        vRtrMplsLspStatsSenderAddr." 
    ::= { vRtrMplsLspStatsEntry 2 }   

vRtrMplsLspStatsSenderAddr  OBJECT-TYPE
    SYNTAX       InetAddress (SIZE (4|16)) 
    MAX-ACCESS   not-accessible
    STATUS       current
    DESCRIPTION 
        "The value of vRtrMplsLspStatsSenderAddr indicates the sender address."
    ::= { vRtrMplsLspStatsEntry 3 } 

vRtrMplsLspStatsLspName     OBJECT-TYPE
    SYNTAX      TNamedItem
    MAX-ACCESS  not-accessible
    STATUS      current
    DESCRIPTION
        "The value of vRtrMplsLspStatsLspName indicates the lsp name."
    ::= { vRtrMplsLspStatsEntry 4 }    

vRtrMplsLspStatsRowStatus  OBJECT-TYPE
    SYNTAX       RowStatus
    MAX-ACCESS   read-create
    STATUS       current
    DESCRIPTION 
        "vRtrMplsLspStatsRowStatus is used for the creation or deletion
         of entries in the vRtrMplsLspStatsTable."
    ::= { vRtrMplsLspStatsEntry 5 } 

vRtrMplsLspStatsLastChanged  OBJECT-TYPE
    SYNTAX       TimeStamp
    MAX-ACCESS   read-only
    STATUS       current
    DESCRIPTION 
        "The value of vRtrMplsLspStatsLastChanged indicates the
         time stamp of the last change to this row of this table."
    ::= { vRtrMplsLspStatsEntry 6 } 

vRtrMplsLspStatsCollectStats OBJECT-TYPE
    SYNTAX      TruthValue
    MAX-ACCESS  read-create
    STATUS      current
    DESCRIPTION
        "The value of vRtrMplsLspStatsCollectStats specifies whether to
        collect statistics for this prefix."
    DEFVAL { false }    
    ::= { vRtrMplsLspStatsEntry 7 }
    
vRtrMplsLspStatsAccntingPolicy OBJECT-TYPE
    SYNTAX      Unsigned32 (0 | 1..99)
    MAX-ACCESS  read-create
    STATUS      current
    DESCRIPTION
        "The value of vRtrMplsLspStatsAccntingPolicy specifies the accounting
        policy to be used for this entry.

        A value of zero indicates that the default accounting policy should be
        used."
    DEFVAL { 0 }    
    ::= { vRtrMplsLspStatsEntry 8 }

vRtrMplsLspStatsAdminState OBJECT-TYPE
    SYNTAX      TmnxAdminState
    MAX-ACCESS  read-create
    STATUS      current
    DESCRIPTION
        "The value of vRtrMplsLspStatsAdminState specifies whether egress 
        statistics are enabled for this lsp."
    DEFVAL { outOfService }    
    ::= { vRtrMplsLspStatsEntry 9 }    

--
--  The MPLS Labeled Switch Path (LSP) Statistics Table
--
--  Augmentation of the vRtrMplsLspStatsTable.
--  Use of AUGMENTS clause implies a one-to-one dependent relationship 
--  between the base table, vRtrMplsLspStatsTable, and the augmenting table, 
--  vRtrMplsLspStatisticsTable. This in effect extends the vRtrMplsLspStatsTable 
--  with additional columns.  
--  Creation (or deletion) of a row in the vRtrMplsLspStatsTable results in 
--  the same fate for the row in the vRtrMplsLspStatisticsTable.
--

--vRtrMplsLspStatisticsTable    OBJECT-TYPE
--    SYNTAX      SEQUENCE OF VRtrMplsLspStatisticsEntry
--    MAX-ACCESS  not-accessible
--    STATUS      current
--    DESCRIPTION
--        "The vRtrMplsLspStatisticsTable has an entry for each Labeled Switch
--         Path (LSP) configured for a virtual router in the system."
--    ::= { tnMplsObjs 39 }
--
--vRtrMplsLspStatisticsEntry    OBJECT-TYPE
--    SYNTAX      VRtrMplsLspStatisticsEntry
--    MAX-ACCESS  not-accessible
--    STATUS      current
--    DESCRIPTION
--        "Each row entry represents a collection of statistics for a
--         Labeled Switch Path (LSP) configured for a virtual router in 
--         the system.  
--
--         Entries cannot be created and deleted via SNMP SET operations."
--    AUGMENTS { vRtrMplsLspStatsEntry }
--    ::= { vRtrMplsLspStatisticsTable 1 }
--
--VRtrMplsLspStatisticsEntry ::= SEQUENCE {
--    vRtrMplsInProfilePktsFc0                  Counter64,
--    vRtrMplsInProfilePktsFc0Low32             Counter32,
--    vRtrMplsInProfilePktsFc0High32            Counter32,
--    vRtrMplsInProfilePktsFc1                  Counter64,
--    vRtrMplsInProfilePktsFc1Low32             Counter32,
--    vRtrMplsInProfilePktsFc1High32            Counter32,
--    vRtrMplsInProfilePktsFc2                  Counter64,
--    vRtrMplsInProfilePktsFc2Low32             Counter32,
--    vRtrMplsInProfilePktsFc2High32            Counter32,
--    vRtrMplsInProfilePktsFc3                  Counter64,
--    vRtrMplsInProfilePktsFc3Low32             Counter32,
--    vRtrMplsInProfilePktsFc3High32            Counter32,
--    vRtrMplsInProfilePktsFc4                  Counter64,
--    vRtrMplsInProfilePktsFc4Low32             Counter32,
--    vRtrMplsInProfilePktsFc4High32            Counter32,
--    vRtrMplsInProfilePktsFc5                  Counter64,
--    vRtrMplsInProfilePktsFc5Low32             Counter32,
--    vRtrMplsInProfilePktsFc5High32            Counter32,
--    vRtrMplsInProfilePktsFc6                  Counter64,
--    vRtrMplsInProfilePktsFc6Low32             Counter32,
--    vRtrMplsInProfilePktsFc6High32            Counter32,
--    vRtrMplsInProfilePktsFc7                  Counter64,
--    vRtrMplsInProfilePktsFc7Low32             Counter32,
--    vRtrMplsInProfilePktsFc7High32            Counter32,
--    vRtrMplsInProfileOctetsFc0                Counter64,
--    vRtrMplsInProfileOctetsFc0Low32           Counter32,
--    vRtrMplsInProfileOctetsFc0High32          Counter32,
--    vRtrMplsInProfileOctetsFc1                Counter64,
--    vRtrMplsInProfileOctetsFc1Low32           Counter32,
--    vRtrMplsInProfileOctetsFc1High32          Counter32,
--    vRtrMplsInProfileOctetsFc2                Counter64,
--    vRtrMplsInProfileOctetsFc2Low32           Counter32,
--    vRtrMplsInProfileOctetsFc2High32          Counter32,
--    vRtrMplsInProfileOctetsFc3                Counter64,
--    vRtrMplsInProfileOctetsFc3Low32           Counter32,
--    vRtrMplsInProfileOctetsFc3High32          Counter32,
--    vRtrMplsInProfileOctetsFc4                Counter64,
--    vRtrMplsInProfileOctetsFc4Low32           Counter32,
--    vRtrMplsInProfileOctetsFc4High32          Counter32,
--    vRtrMplsInProfileOctetsFc5                Counter64,
--    vRtrMplsInProfileOctetsFc5Low32           Counter32,
--    vRtrMplsInProfileOctetsFc5High32          Counter32,
--    vRtrMplsInProfileOctetsFc6                Counter64,
--    vRtrMplsInProfileOctetsFc6Low32           Counter32,
--    vRtrMplsInProfileOctetsFc6High32          Counter32,
--    vRtrMplsInProfileOctetsFc7                Counter64,
--    vRtrMplsInProfileOctetsFc7Low32           Counter32,
--    vRtrMplsInProfileOctetsFc7High32          Counter32,
--    vRtrMplsOutOfProfPktsFc0                  Counter64,
--    vRtrMplsOutOfProfPktsFc0Low32             Counter32,
--    vRtrMplsOutOfProfPktsFc0High32            Counter32,
--    vRtrMplsOutOfProfPktsFc1                  Counter64,
--    vRtrMplsOutOfProfPktsFc1Low32             Counter32,
--    vRtrMplsOutOfProfPktsFc1High32            Counter32,
--    vRtrMplsOutOfProfPktsFc2                  Counter64,
--    vRtrMplsOutOfProfPktsFc2Low32             Counter32,
--    vRtrMplsOutOfProfPktsFc2High32            Counter32,
--    vRtrMplsOutOfProfPktsFc3                  Counter64,
--    vRtrMplsOutOfProfPktsFc3Low32             Counter32,
--    vRtrMplsOutOfProfPktsFc3High32            Counter32,
--    vRtrMplsOutOfProfPktsFc4                  Counter64,
--    vRtrMplsOutOfProfPktsFc4Low32             Counter32,
--    vRtrMplsOutOfProfPktsFc4High32            Counter32,
--    vRtrMplsOutOfProfPktsFc5                  Counter64,
--    vRtrMplsOutOfProfPktsFc5Low32             Counter32,
--    vRtrMplsOutOfProfPktsFc5High32            Counter32,
--    vRtrMplsOutOfProfPktsFc6                  Counter64,
--    vRtrMplsOutOfProfPktsFc6Low32             Counter32,
--    vRtrMplsOutOfProfPktsFc6High32            Counter32,
--    vRtrMplsOutOfProfPktsFc7                  Counter64,
--    vRtrMplsOutOfProfPktsFc7Low32             Counter32,
--    vRtrMplsOutOfProfPktsFc7High32            Counter32,
--    vRtrMplsOutOfProfOctetsFc0                Counter64,
--    vRtrMplsOutOfProfOctetsFc0Low32           Counter32,
--    vRtrMplsOutOfProfOctetsFc0High32          Counter32,
--    vRtrMplsOutOfProfOctetsFc1                Counter64,
--    vRtrMplsOutOfProfOctetsFc1Low32           Counter32,
--    vRtrMplsOutOfProfOctetsFc1High32          Counter32,
--    vRtrMplsOutOfProfOctetsFc2                Counter64,
--    vRtrMplsOutOfProfOctetsFc2Low32           Counter32,
--    vRtrMplsOutOfProfOctetsFc2High32          Counter32,
--    vRtrMplsOutOfProfOctetsFc3                Counter64,
--    vRtrMplsOutOfProfOctetsFc3Low32           Counter32,
--    vRtrMplsOutOfProfOctetsFc3High32          Counter32,
--    vRtrMplsOutOfProfOctetsFc4                Counter64,
--    vRtrMplsOutOfProfOctetsFc4Low32           Counter32,
--    vRtrMplsOutOfProfOctetsFc4High32          Counter32,
--    vRtrMplsOutOfProfOctetsFc5                Counter64,
--    vRtrMplsOutOfProfOctetsFc5Low32           Counter32,
--    vRtrMplsOutOfProfOctetsFc5High32          Counter32,
--    vRtrMplsOutOfProfOctetsFc6                Counter64,
--    vRtrMplsOutOfProfOctetsFc6Low32           Counter32,
--    vRtrMplsOutOfProfOctetsFc6High32          Counter32,
--    vRtrMplsOutOfProfOctetsFc7                Counter64, 
--    vRtrMplsOutOfProfOctetsFc7Low32           Counter32,
--    vRtrMplsOutOfProfOctetsFc7High32          Counter32,
--    vRtrMplsLspStatsPSBMatch                  TruthValue,
--    vRtrMplsLspStatsTpOnly                    TruthValue
--}
--
--vRtrMplsInProfilePktsFc0   OBJECT-TYPE
--    SYNTAX      Counter64
--    MAX-ACCESS  read-only
--    STATUS      current
--    DESCRIPTION
--        "The value of vRtrMplsInProfilePktsFc0 indicates the number of in 
--        profile packets received for Forwarding Class 0."
--    ::= { vRtrMplsLspStatisticsEntry 1 }
--
--vRtrMplsInProfilePktsFc0Low32   OBJECT-TYPE
--    SYNTAX      Counter32
--    MAX-ACCESS  read-only
--    STATUS      current
--    DESCRIPTION
--        "The value of vRtrMplsInProfilePktsFc0 indicates the lower 
--         32 bits of the value of vRtrMplsInProfilePktsFc0."
--    ::= { vRtrMplsLspStatisticsEntry 2 }
--
--vRtrMplsInProfilePktsFc0High32   OBJECT-TYPE
--    SYNTAX      Counter32
--    MAX-ACCESS  read-only
--    STATUS      current
--    DESCRIPTION
--        "The value of vRtrMplsInProfilePktsFc0 indicates the higher 
--         32 bits of the value of vRtrMplsInProfilePktsFc0."
--    ::= { vRtrMplsLspStatisticsEntry 3 }
--    
--vRtrMplsInProfilePktsFc1   OBJECT-TYPE
--    SYNTAX      Counter64
--    MAX-ACCESS  read-only
--    STATUS      current
--    DESCRIPTION
--        "The value of vRtrMplsInProfilePktsFc1 indicates the number of in 
--        profile packets received for Forwarding Class 1."
--    ::= { vRtrMplsLspStatisticsEntry 4 }
--
--vRtrMplsInProfilePktsFc1Low32   OBJECT-TYPE
--    SYNTAX      Counter32
--    MAX-ACCESS  read-only
--    STATUS      current
--    DESCRIPTION
--        "The value of vRtrMplsInProfilePktsFc1 indicates the lower 
--         32 bits of the value of vRtrMplsInProfilePktsFc1."
--    ::= { vRtrMplsLspStatisticsEntry 5 }
--
--vRtrMplsInProfilePktsFc1High32   OBJECT-TYPE
--    SYNTAX      Counter32
--    MAX-ACCESS  read-only
--    STATUS      current
--    DESCRIPTION
--        "The value of vRtrMplsInProfilePktsFc1 indicates the higher 
--         32 bits of the value of vRtrMplsInProfilePktsFc1."
--    ::= { vRtrMplsLspStatisticsEntry 6 }    
--
--vRtrMplsInProfilePktsFc2   OBJECT-TYPE
--    SYNTAX      Counter64
--    MAX-ACCESS  read-only
--    STATUS      current
--    DESCRIPTION
--        "The value of vRtrMplsInProfilePktsFc2 indicates the number of in 
--        profile packets received for Forwarding Class 2."
--    ::= { vRtrMplsLspStatisticsEntry 7 }
--
--vRtrMplsInProfilePktsFc2Low32   OBJECT-TYPE
--    SYNTAX      Counter32
--    MAX-ACCESS  read-only
--    STATUS      current
--    DESCRIPTION
--        "The value of vRtrMplsInProfilePktsFc2 indicates the lower 
--         32 bits of the value of vRtrMplsInProfilePktsFc2."
--    ::= { vRtrMplsLspStatisticsEntry 8 }
--
--vRtrMplsInProfilePktsFc2High32   OBJECT-TYPE
--    SYNTAX      Counter32
--    MAX-ACCESS  read-only
--    STATUS      current
--    DESCRIPTION
--        "The value of vRtrMplsInProfilePktsFc2 indicates the higher 
--         32 bits of the value of vRtrMplsInProfilePktsFc2."
--    ::= { vRtrMplsLspStatisticsEntry 9 }    
--
--vRtrMplsInProfilePktsFc3   OBJECT-TYPE
--    SYNTAX      Counter64
--    MAX-ACCESS  read-only
--    STATUS      current
--    DESCRIPTION
--        "The value of vRtrMplsInProfilePktsFc3 indicates the number of in 
--        profile packets received for Forwarding Class 3."
--    ::= { vRtrMplsLspStatisticsEntry 10 }
--
--vRtrMplsInProfilePktsFc3Low32   OBJECT-TYPE
--    SYNTAX      Counter32
--    MAX-ACCESS  read-only
--    STATUS      current
--    DESCRIPTION
--        "The value of vRtrMplsInProfilePktsFc3 indicates the lower 
--         32 bits of the value of vRtrMplsInProfilePktsFc3."
--    ::= { vRtrMplsLspStatisticsEntry 11 }
--
--vRtrMplsInProfilePktsFc3High32   OBJECT-TYPE
--    SYNTAX      Counter32
--    MAX-ACCESS  read-only
--    STATUS      current
--    DESCRIPTION
--        "The value of vRtrMplsInProfilePktsFc3 indicates the higher 
--         32 bits of the value of vRtrMplsInProfilePktsFc3."
--    ::= { vRtrMplsLspStatisticsEntry 12 }    
--
--vRtrMplsInProfilePktsFc4   OBJECT-TYPE
--    SYNTAX      Counter64
--    MAX-ACCESS  read-only
--    STATUS      current
--    DESCRIPTION
--        "The value of vRtrMplsInProfilePktsFc4 indicates the number of in 
--        profile packets received for Forwarding Class 4."
--    ::= { vRtrMplsLspStatisticsEntry 13 }
--
--vRtrMplsInProfilePktsFc4Low32   OBJECT-TYPE
--    SYNTAX      Counter32
--    MAX-ACCESS  read-only
--    STATUS      current
--    DESCRIPTION
--        "The value of vRtrMplsInProfilePktsFc4 indicates the lower 
--         32 bits of the value of vRtrMplsInProfilePktsFc4."
--    ::= { vRtrMplsLspStatisticsEntry 14 }
--
--vRtrMplsInProfilePktsFc4High32   OBJECT-TYPE
--    SYNTAX      Counter32
--    MAX-ACCESS  read-only
--    STATUS      current
--    DESCRIPTION
--        "The value of vRtrMplsInProfilePktsFc4 indicates the higher 
--         32 bits of the value of vRtrMplsInProfilePktsFc4."
--    ::= { vRtrMplsLspStatisticsEntry 15 }    
--
--vRtrMplsInProfilePktsFc5  OBJECT-TYPE
--    SYNTAX      Counter64
--    MAX-ACCESS  read-only
--    STATUS      current
--    DESCRIPTION
--        "The value of vRtrMplsInProfilePktsFc5 indicates the number of in 
--        profile packets received for Forwarding Class 5."
--    ::= { vRtrMplsLspStatisticsEntry 16 }
--
--vRtrMplsInProfilePktsFc5Low32   OBJECT-TYPE
--    SYNTAX      Counter32
--    MAX-ACCESS  read-only
--    STATUS      current
--    DESCRIPTION
--        "The value of vRtrMplsInProfilePktsFc5 indicates the lower 
--         32 bits of the value of vRtrMplsInProfilePktsFc5."
--    ::= { vRtrMplsLspStatisticsEntry 17 }
--
--vRtrMplsInProfilePktsFc5High32   OBJECT-TYPE
--    SYNTAX      Counter32
--    MAX-ACCESS  read-only
--    STATUS      current
--    DESCRIPTION
--        "The value of vRtrMplsInProfilePktsFc5 indicates the higher 
--         32 bits of the value of vRtrMplsInProfilePktsFc5."
--    ::= { vRtrMplsLspStatisticsEntry 18 }    
--
--vRtrMplsInProfilePktsFc6   OBJECT-TYPE
--    SYNTAX      Counter64
--    MAX-ACCESS  read-only
--    STATUS      current
--    DESCRIPTION
--        "The value of vRtrMplsInProfilePktsFc6 indicates the number of in 
--        profile packets received for Forwarding Class 6."
--    ::= { vRtrMplsLspStatisticsEntry 19 }
--
--vRtrMplsInProfilePktsFc6Low32   OBJECT-TYPE
--    SYNTAX      Counter32
--    MAX-ACCESS  read-only
--    STATUS      current
--    DESCRIPTION
--        "The value of vRtrMplsInProfilePktsFc6 indicates the lower 
--         32 bits of the value of vRtrMplsInProfilePktsFc6."
--    ::= { vRtrMplsLspStatisticsEntry 20 }
--
--vRtrMplsInProfilePktsFc6High32   OBJECT-TYPE
--    SYNTAX      Counter32
--    MAX-ACCESS  read-only
--    STATUS      current
--    DESCRIPTION
--        "The value of vRtrMplsInProfilePktsFc6 indicates the higher 
--         32 bits of the value of vRtrMplsInProfilePktsFc6."
--    ::= { vRtrMplsLspStatisticsEntry 21 }    
--
--vRtrMplsInProfilePktsFc7   OBJECT-TYPE
--    SYNTAX      Counter64
--    MAX-ACCESS  read-only
--    STATUS      current
--    DESCRIPTION
--        "The value of vRtrMplsInProfilePktsFc7 indicates the number of in 
--        profile packets received for Forwarding Class 7."
--    ::= { vRtrMplsLspStatisticsEntry 22 }
--
--vRtrMplsInProfilePktsFc7Low32   OBJECT-TYPE
--    SYNTAX      Counter32
--    MAX-ACCESS  read-only
--    STATUS      current
--    DESCRIPTION
--        "The value of vRtrMplsInProfilePktsFc7 indicates the lower 
--         32 bits of the value of vRtrMplsInProfilePktsFc7."
--    ::= { vRtrMplsLspStatisticsEntry 23 }
--
--vRtrMplsInProfilePktsFc7High32   OBJECT-TYPE
--    SYNTAX      Counter32
--    MAX-ACCESS  read-only
--    STATUS      current
--    DESCRIPTION
--        "The value of vRtrMplsInProfilePktsFc7 indicates the higher 
--         32 bits of the value of vRtrMplsInProfilePktsFc7."
--    ::= { vRtrMplsLspStatisticsEntry 24 }    
--
--vRtrMplsInProfileOctetsFc0   OBJECT-TYPE
--    SYNTAX      Counter64
--    MAX-ACCESS  read-only
--    STATUS      current
--    DESCRIPTION
--        "The value of vRtrMplsInProfileOctetsFc0 indicates the number of in 
--        profile octets received for Forwarding Class 0."
--    ::= { vRtrMplsLspStatisticsEntry 25 }
--
--vRtrMplsInProfileOctetsFc0Low32   OBJECT-TYPE
--    SYNTAX      Counter32
--    MAX-ACCESS  read-only
--    STATUS      current
--    DESCRIPTION
--        "The value of vRtrMplsInProfileOctetsFc0 indicates the lower 
--         32 bits of the value of vRtrMplsInProfileOctetsFc0."
--    ::= { vRtrMplsLspStatisticsEntry 26 }
--
--vRtrMplsInProfileOctetsFc0High32   OBJECT-TYPE
--    SYNTAX      Counter32
--    MAX-ACCESS  read-only
--    STATUS      current
--    DESCRIPTION
--        "The value of vRtrMplsInProfileOctetsFc0 indicates the higher 
--         32 bits of the value of vRtrMplsInProfileOctetsFc0."
--    ::= { vRtrMplsLspStatisticsEntry 27 }    
--
--vRtrMplsInProfileOctetsFc1   OBJECT-TYPE
--    SYNTAX      Counter64
--    MAX-ACCESS  read-only
--    STATUS      current
--    DESCRIPTION
--        "The value of vRtrMplsInProfileOctetsFc1 indicates the number of in 
--        profile octets received for Forwarding Class 1."
--    ::= { vRtrMplsLspStatisticsEntry 28 }
--
--vRtrMplsInProfileOctetsFc1Low32   OBJECT-TYPE
--    SYNTAX      Counter32
--    MAX-ACCESS  read-only
--    STATUS      current
--    DESCRIPTION
--        "The value of vRtrMplsInProfileOctetsFc1 indicates the lower 
--         32 bits of the value of vRtrMplsInProfileOctetsFc1."
--    ::= { vRtrMplsLspStatisticsEntry 29 }
--
--vRtrMplsInProfileOctetsFc1High32   OBJECT-TYPE
--    SYNTAX      Counter32
--    MAX-ACCESS  read-only
--    STATUS      current
--    DESCRIPTION
--        "The value of vRtrMplsInProfileOctetsFc1 indicates the higher 
--         32 bits of the value of vRtrMplsInProfileOctetsFc1."
--    ::= { vRtrMplsLspStatisticsEntry 30 }        
--
--vRtrMplsInProfileOctetsFc2   OBJECT-TYPE
--    SYNTAX      Counter64
--    MAX-ACCESS  read-only
--    STATUS      current
--    DESCRIPTION
--        "The value of vRtrMplsInProfileOctetsFc2 indicates the number of in 
--        profile octets received for Forwarding Class 2."
--    ::= { vRtrMplsLspStatisticsEntry 31 }
--
--vRtrMplsInProfileOctetsFc2Low32   OBJECT-TYPE
--    SYNTAX      Counter32
--    MAX-ACCESS  read-only
--    STATUS      current
--    DESCRIPTION
--        "The value of vRtrMplsInProfileOctetsFc2 indicates the lower 
--         32 bits of the value of vRtrMplsInProfileOctetsFc2."
--    ::= { vRtrMplsLspStatisticsEntry 32 }
--
--vRtrMplsInProfileOctetsFc2High32   OBJECT-TYPE
--    SYNTAX      Counter32
--    MAX-ACCESS  read-only
--    STATUS      current
--    DESCRIPTION
--        "The value of vRtrMplsInProfileOctetsFc2 indicates the higher 
--         32 bits of the value of vRtrMplsInProfileOctetsFc2."
--    ::= { vRtrMplsLspStatisticsEntry 33 }        
--
--vRtrMplsInProfileOctetsFc3   OBJECT-TYPE
--    SYNTAX      Counter64
--    MAX-ACCESS  read-only
--    STATUS      current
--    DESCRIPTION
--        "The value of vRtrMplsInProfileOctetsFc3 indicates the number of in 
--        profile octets received for Forwarding Class 3."
--    ::= { vRtrMplsLspStatisticsEntry 34 }
--
--vRtrMplsInProfileOctetsFc3Low32   OBJECT-TYPE
--    SYNTAX      Counter32
--    MAX-ACCESS  read-only
--    STATUS      current
--    DESCRIPTION
--        "The value of vRtrMplsInProfileOctetsFc3 indicates the lower 
--         32 bits of the value of vRtrMplsInProfileOctetsFc3."
--    ::= { vRtrMplsLspStatisticsEntry 35 }
--
--vRtrMplsInProfileOctetsFc3High32   OBJECT-TYPE
--    SYNTAX      Counter32
--    MAX-ACCESS  read-only
--    STATUS      current
--    DESCRIPTION
--        "The value of vRtrMplsInProfileOctetsFc3 indicates the higher 
--         32 bits of the value of vRtrMplsInProfileOctetsFc3."
--    ::= { vRtrMplsLspStatisticsEntry 36 }        
--
--vRtrMplsInProfileOctetsFc4   OBJECT-TYPE
--    SYNTAX      Counter64
--    MAX-ACCESS  read-only
--    STATUS      current
--    DESCRIPTION
--        "The value of vRtrMplsInProfileOctetsFc4 indicates the number of in 
--        profile octets received for Forwarding Class 4."
--    ::= { vRtrMplsLspStatisticsEntry 37 }
--
--vRtrMplsInProfileOctetsFc4Low32   OBJECT-TYPE
--    SYNTAX      Counter32
--    MAX-ACCESS  read-only
--    STATUS      current
--    DESCRIPTION
--        "The value of vRtrMplsInProfileOctetsFc4 indicates the lower 
--         32 bits of the value of vRtrMplsInProfileOctetsFc4."
--    ::= { vRtrMplsLspStatisticsEntry 38 }
--
--vRtrMplsInProfileOctetsFc4High32   OBJECT-TYPE
--    SYNTAX      Counter32
--    MAX-ACCESS  read-only
--    STATUS      current
--    DESCRIPTION
--        "The value of vRtrMplsInProfileOctetsFc4 indicates the higher 
--         32 bits of the value of vRtrMplsInProfileOctetsFc4."
--    ::= { vRtrMplsLspStatisticsEntry 39 }  
--    
--vRtrMplsInProfileOctetsFc5  OBJECT-TYPE
--    SYNTAX      Counter64
--    MAX-ACCESS  read-only
--    STATUS      current
--    DESCRIPTION
--        "The value of vRtrMplsInProfileOctetsFc5 indicates the number of in 
--        profile octets received for Forwarding Class 5."
--    ::= { vRtrMplsLspStatisticsEntry 40 }
--
--vRtrMplsInProfileOctetsFc5Low32   OBJECT-TYPE
--    SYNTAX      Counter32
--    MAX-ACCESS  read-only
--    STATUS      current
--    DESCRIPTION
--        "The value of vRtrMplsInProfileOctetsFc5 indicates the lower 
--         32 bits of the value of vRtrMplsInProfileOctetsFc5."
--    ::= { vRtrMplsLspStatisticsEntry 41 }
--
--vRtrMplsInProfileOctetsFc5High32   OBJECT-TYPE
--    SYNTAX      Counter32
--    MAX-ACCESS  read-only
--    STATUS      current
--    DESCRIPTION
--        "The value of vRtrMplsInProfileOctetsFc5 indicates the higher 
--         32 bits of the value of vRtrMplsInProfileOctetsFc5."
--    ::= { vRtrMplsLspStatisticsEntry 42 }        
--
--vRtrMplsInProfileOctetsFc6   OBJECT-TYPE
--    SYNTAX      Counter64
--    MAX-ACCESS  read-only
--    STATUS      current
--    DESCRIPTION
--        "The value of vRtrMplsInProfileOctetsFc6 indicates the number of in 
--        profile octets received for Forwarding Class 6."
--    ::= { vRtrMplsLspStatisticsEntry 43 }
--
--vRtrMplsInProfileOctetsFc6Low32   OBJECT-TYPE
--    SYNTAX      Counter32
--    MAX-ACCESS  read-only
--    STATUS      current
--    DESCRIPTION
--        "The value of vRtrMplsInProfileOctetsFc6 indicates the lower 
--         32 bits of the value of vRtrMplsInProfileOctetsFc6."
--    ::= { vRtrMplsLspStatisticsEntry 44 }
--
--vRtrMplsInProfileOctetsFc6High32   OBJECT-TYPE
--    SYNTAX      Counter32
--    MAX-ACCESS  read-only
--    STATUS      current
--    DESCRIPTION
--        "The value of vRtrMplsInProfileOctetsFc6 indicates the higher 
--         32 bits of the value of vRtrMplsInProfileOctetsFc6."
--    ::= { vRtrMplsLspStatisticsEntry 45 }    
--    
--vRtrMplsInProfileOctetsFc7   OBJECT-TYPE
--    SYNTAX      Counter64
--    MAX-ACCESS  read-only
--    STATUS      current
--    DESCRIPTION
--        "The value of vRtrMplsInProfileOctetsFc7 indicates the number of in 
--        profile octets received for Forwarding Class 7."
--    ::= { vRtrMplsLspStatisticsEntry 46 }
--
--vRtrMplsInProfileOctetsFc7Low32   OBJECT-TYPE
--    SYNTAX      Counter32
--    MAX-ACCESS  read-only
--    STATUS      current
--    DESCRIPTION
--        "The value of vRtrMplsInProfileOctetsFc7 indicates the lower 
--         32 bits of the value of vRtrMplsInProfileOctetsFc7."
--    ::= { vRtrMplsLspStatisticsEntry 47 }
--
--vRtrMplsInProfileOctetsFc7High32   OBJECT-TYPE
--    SYNTAX      Counter32
--    MAX-ACCESS  read-only
--    STATUS      current
--    DESCRIPTION
--        "The value of vRtrMplsInProfileOctetsFc7 indicates the higher 
--         32 bits of the value of vRtrMplsInProfileOctetsFc7."
--    ::= { vRtrMplsLspStatisticsEntry 48 }        
--   
--vRtrMplsOutOfProfPktsFc0   OBJECT-TYPE
--    SYNTAX      Counter64
--    MAX-ACCESS  read-only
--    STATUS      current
--    DESCRIPTION
--        "The value of vRtrMplsOutOfProfPktsFc0 indicates the number of out of 
--        profile packets received for Forwarding Class 0."
--    ::= { vRtrMplsLspStatisticsEntry 49 }
--
--vRtrMplsOutOfProfPktsFc0Low32   OBJECT-TYPE
--    SYNTAX      Counter32
--    MAX-ACCESS  read-only
--    STATUS      current
--    DESCRIPTION
--        "The value of vRtrMplsOutOfProfPktsFc0 indicates the lower 
--         32 bits of the value of vRtrMplsOutOfProfPktsFc0."
--    ::= { vRtrMplsLspStatisticsEntry 50 }
--
--vRtrMplsOutOfProfPktsFc0High32   OBJECT-TYPE
--    SYNTAX      Counter32
--    MAX-ACCESS  read-only
--    STATUS      current
--    DESCRIPTION
--        "The value of vRtrMplsOutOfProfPktsFc0 indicates the higher 
--         32 bits of the value of vRtrMplsOutOfProfPktsFc0."
--    ::= { vRtrMplsLspStatisticsEntry 51 }        
--
--vRtrMplsOutOfProfPktsFc1   OBJECT-TYPE
--    SYNTAX      Counter64
--    MAX-ACCESS  read-only
--    STATUS      current
--    DESCRIPTION
--        "The value of vRtrMplsOutOfProfPktsFc1 indicates the number of out of 
--        profile packets received for Forwarding Class 1."
--    ::= { vRtrMplsLspStatisticsEntry 52 }
--
--vRtrMplsOutOfProfPktsFc1Low32   OBJECT-TYPE
--    SYNTAX      Counter32
--    MAX-ACCESS  read-only
--    STATUS      current
--    DESCRIPTION
--        "The value of vRtrMplsOutOfProfPktsFc1 indicates the lower 
--         32 bits of the value of vRtrMplsOutOfProfPktsFc1."
--    ::= { vRtrMplsLspStatisticsEntry 53 }
--
--vRtrMplsOutOfProfPktsFc1High32   OBJECT-TYPE
--    SYNTAX      Counter32
--    MAX-ACCESS  read-only
--    STATUS      current
--    DESCRIPTION
--        "The value of vRtrMplsOutOfProfPktsFc1 indicates the higher 
--         32 bits of the value of vRtrMplsOutOfProfPktsFc1."
--    ::= { vRtrMplsLspStatisticsEntry 54 }        
--    
--vRtrMplsOutOfProfPktsFc2   OBJECT-TYPE
--    SYNTAX      Counter64
--    MAX-ACCESS  read-only
--    STATUS      current
--    DESCRIPTION
--        "The value of vRtrMplsOutOfProfPktsFc2 indicates the number of out of 
--        profile packets received for Forwarding Class 2."
--    ::= { vRtrMplsLspStatisticsEntry 55 }
--
--vRtrMplsOutOfProfPktsFc2Low32   OBJECT-TYPE
--    SYNTAX      Counter32
--    MAX-ACCESS  read-only
--    STATUS      current
--    DESCRIPTION
--        "The value of vRtrMplsOutOfProfPktsFc2 indicates the lower 
--         32 bits of the value of vRtrMplsOutOfProfPktsFc2."
--    ::= { vRtrMplsLspStatisticsEntry 56 }
--
--vRtrMplsOutOfProfPktsFc2High32   OBJECT-TYPE
--    SYNTAX      Counter32
--    MAX-ACCESS  read-only
--    STATUS      current
--    DESCRIPTION
--        "The value of vRtrMplsOutOfProfPktsFc2 indicates the higher 
--         32 bits of the value of vRtrMplsOutOfProfPktsFc2."
--    ::= { vRtrMplsLspStatisticsEntry 57 }            
--
--vRtrMplsOutOfProfPktsFc3   OBJECT-TYPE
--    SYNTAX      Counter64
--    MAX-ACCESS  read-only
--    STATUS      current
--    DESCRIPTION
--        "The value of vRtrMplsOutOfProfPktsFc3 indicates the number of out of 
--        profile packets received for Forwarding Class 3."
--    ::= { vRtrMplsLspStatisticsEntry 58 }
--
--vRtrMplsOutOfProfPktsFc3Low32   OBJECT-TYPE
--    SYNTAX      Counter32
--    MAX-ACCESS  read-only
--    STATUS      current
--    DESCRIPTION
--        "The value of vRtrMplsOutOfProfPktsFc3 indicates the lower 
--         32 bits of the value of vRtrMplsOutOfProfPktsFc3."
--    ::= { vRtrMplsLspStatisticsEntry 59 }
--
--vRtrMplsOutOfProfPktsFc3High32   OBJECT-TYPE
--    SYNTAX      Counter32
--    MAX-ACCESS  read-only
--    STATUS      current
--    DESCRIPTION
--        "The value of vRtrMplsOutOfProfPktsFc3 indicates the higher 
--         32 bits of the value of vRtrMplsOutOfProfPktsFc3."
--    ::= { vRtrMplsLspStatisticsEntry 60 }            
--
--vRtrMplsOutOfProfPktsFc4   OBJECT-TYPE
--    SYNTAX      Counter64
--    MAX-ACCESS  read-only
--    STATUS      current
--    DESCRIPTION
--        "The value of vRtrMplsOutOfProfPktsFc4 indicates the number of out of 
--        profile packets received for Forwarding Class 4."
--    ::= { vRtrMplsLspStatisticsEntry 61 }
--
--vRtrMplsOutOfProfPktsFc4Low32   OBJECT-TYPE
--    SYNTAX      Counter32
--    MAX-ACCESS  read-only
--    STATUS      current
--    DESCRIPTION
--        "The value of vRtrMplsOutOfProfPktsFc4 indicates the lower 
--         32 bits of the value of vRtrMplsOutOfProfPktsFc4."
--    ::= { vRtrMplsLspStatisticsEntry 62 }
--
--vRtrMplsOutOfProfPktsFc4High32   OBJECT-TYPE
--    SYNTAX      Counter32
--    MAX-ACCESS  read-only
--    STATUS      current
--    DESCRIPTION
--        "The value of vRtrMplsOutOfProfPktsFc4 indicates the higher 
--         32 bits of the value of vRtrMplsOutOfProfPktsFc4."
--    ::= { vRtrMplsLspStatisticsEntry 63 }        
--
--vRtrMplsOutOfProfPktsFc5  OBJECT-TYPE
--    SYNTAX      Counter64
--    MAX-ACCESS  read-only
--    STATUS      current
--    DESCRIPTION
--        "The value of vRtrMplsOutOfProfPktsFc5 indicates the number of out of 
--        profile packets received for Forwarding Class 5."
--    ::= { vRtrMplsLspStatisticsEntry 64 }
--
--vRtrMplsOutOfProfPktsFc5Low32   OBJECT-TYPE
--    SYNTAX      Counter32
--    MAX-ACCESS  read-only
--    STATUS      current
--    DESCRIPTION
--        "The value of vRtrMplsOutOfProfPktsFc5 indicates the lower 
--         32 bits of the value of vRtrMplsOutOfProfPktsFc5."
--    ::= { vRtrMplsLspStatisticsEntry 65 }
--
--vRtrMplsOutOfProfPktsFc5High32   OBJECT-TYPE
--    SYNTAX      Counter32
--    MAX-ACCESS  read-only
--    STATUS      current
--    DESCRIPTION
--        "The value of vRtrMplsOutOfProfPktsFc5 indicates the higher 
--         32 bits of the value of vRtrMplsOutOfProfPktsFc5."
--    ::= { vRtrMplsLspStatisticsEntry 66 }        
--    
--vRtrMplsOutOfProfPktsFc6   OBJECT-TYPE
--    SYNTAX      Counter64
--    MAX-ACCESS  read-only
--    STATUS      current
--    DESCRIPTION
--        "The value of vRtrMplsOutOfProfPktsFc6 indicates the number of out of 
--        profile packets received for Forwarding Class 6."
--    ::= { vRtrMplsLspStatisticsEntry 67 }
--
--vRtrMplsOutOfProfPktsFc6Low32   OBJECT-TYPE
--    SYNTAX      Counter32
--    MAX-ACCESS  read-only
--    STATUS      current
--    DESCRIPTION
--        "The value of vRtrMplsOutOfProfPktsFc6 indicates the lower 
--         32 bits of the value of vRtrMplsOutOfProfPktsFc6."
--    ::= { vRtrMplsLspStatisticsEntry 68 }
--
--vRtrMplsOutOfProfPktsFc6High32   OBJECT-TYPE
--    SYNTAX      Counter32
--    MAX-ACCESS  read-only
--    STATUS      current
--    DESCRIPTION
--        "The value of vRtrMplsOutOfProfPktsFc6 indicates the higher 
--         32 bits of the value of vRtrMplsOutOfProfPktsFc6."
--    ::= { vRtrMplsLspStatisticsEntry 69 }           
--
--vRtrMplsOutOfProfPktsFc7   OBJECT-TYPE
--    SYNTAX      Counter64
--    MAX-ACCESS  read-only
--    STATUS      current
--    DESCRIPTION
--        "The value of vRtrMplsOutOfProfPktsFc7 indicates the number of out of 
--        profile packets received for Forwarding Class 7."
--    ::= { vRtrMplsLspStatisticsEntry 70 }    
--
--vRtrMplsOutOfProfPktsFc7Low32   OBJECT-TYPE
--    SYNTAX      Counter32
--    MAX-ACCESS  read-only
--    STATUS      current
--    DESCRIPTION
--        "The value of vRtrMplsOutOfProfPktsFc7 indicates the lower 
--         32 bits of the value of vRtrMplsOutOfProfPktsFc7."
--    ::= { vRtrMplsLspStatisticsEntry 71 }
--
--vRtrMplsOutOfProfPktsFc7High32   OBJECT-TYPE
--    SYNTAX      Counter32
--    MAX-ACCESS  read-only
--    STATUS      current
--    DESCRIPTION
--        "The value of vRtrMplsOutOfProfPktsFc7 indicates the higher 
--         32 bits of the value of vRtrMplsOutOfProfPktsFc7."
--    ::= { vRtrMplsLspStatisticsEntry 72 }          
--
--vRtrMplsOutOfProfOctetsFc0   OBJECT-TYPE
--    SYNTAX      Counter64
--    MAX-ACCESS  read-only
--    STATUS      current
--    DESCRIPTION
--        "The value of vRtrMplsOutOfProfOctetsFc0 indicates the number of out of 
--        profile octets received for Forwarding Class 0."
--    ::= { vRtrMplsLspStatisticsEntry 73 }
--
--vRtrMplsOutOfProfOctetsFc0Low32   OBJECT-TYPE
--    SYNTAX      Counter32
--    MAX-ACCESS  read-only
--    STATUS      current
--    DESCRIPTION
--        "The value of vRtrMplsOutOfProfOctetsFc0 indicates the lower 
--         32 bits of the value of vRtrMplsOutOfProfOctetsFc0."
--    ::= { vRtrMplsLspStatisticsEntry 74 }
--
--vRtrMplsOutOfProfOctetsFc0High32   OBJECT-TYPE
--    SYNTAX      Counter32
--    MAX-ACCESS  read-only
--    STATUS      current
--    DESCRIPTION
--        "The value of vRtrMplsOutOfProfOctetsFc0 indicates the higher 
--         32 bits of the value of vRtrMplsOutOfProfOctetsFc0."
--    ::= { vRtrMplsLspStatisticsEntry 75 }        
--
--vRtrMplsOutOfProfOctetsFc1   OBJECT-TYPE
--    SYNTAX      Counter64
--    MAX-ACCESS  read-only
--    STATUS      current
--    DESCRIPTION
--        "The value of vRtrMplsOutOfProfOctetsFc1 indicates the number of out of 
--        profile octets received for Forwarding Class 1."
--    ::= { vRtrMplsLspStatisticsEntry 76 }
--
--vRtrMplsOutOfProfOctetsFc1Low32   OBJECT-TYPE
--    SYNTAX      Counter32
--    MAX-ACCESS  read-only
--    STATUS      current
--    DESCRIPTION
--        "The value of vRtrMplsOutOfProfOctetsFc1 indicates the lower 
--         32 bits of the value of vRtrMplsOutOfProfOctetsFc1."
--    ::= { vRtrMplsLspStatisticsEntry 77 }
--
--vRtrMplsOutOfProfOctetsFc1High32   OBJECT-TYPE
--    SYNTAX      Counter32
--    MAX-ACCESS  read-only
--    STATUS      current
--    DESCRIPTION
--        "The value of vRtrMplsOutOfProfOctetsFc1 indicates the higher 
--         32 bits of the value of vRtrMplsOutOfProfOctetsFc1."
--    ::= { vRtrMplsLspStatisticsEntry 78 }            
--
--vRtrMplsOutOfProfOctetsFc2   OBJECT-TYPE
--    SYNTAX      Counter64
--    MAX-ACCESS  read-only
--    STATUS      current
--    DESCRIPTION
--        "The value of vRtrMplsOutOfProfOctetsFc2 indicates the number of out of 
--        profile octets received for Forwarding Class 2."
--    ::= { vRtrMplsLspStatisticsEntry 79 }
--
--vRtrMplsOutOfProfOctetsFc2Low32   OBJECT-TYPE
--    SYNTAX      Counter32
--    MAX-ACCESS  read-only
--    STATUS      current
--    DESCRIPTION
--        "The value of vRtrMplsOutOfProfOctetsFc2 indicates the lower 
--         32 bits of the value of vRtrMplsOutOfProfOctetsFc2."
--    ::= { vRtrMplsLspStatisticsEntry 80 }
--
--vRtrMplsOutOfProfOctetsFc2High32   OBJECT-TYPE
--    SYNTAX      Counter32
--    MAX-ACCESS  read-only
--    STATUS      current
--    DESCRIPTION
--        "The value of vRtrMplsOutOfProfOctetsFc2 indicates the higher 
--         32 bits of the value of vRtrMplsOutOfProfOctetsFc2."
--    ::= { vRtrMplsLspStatisticsEntry 81 }            
--
--vRtrMplsOutOfProfOctetsFc3   OBJECT-TYPE
--    SYNTAX      Counter64
--    MAX-ACCESS  read-only
--    STATUS      current
--    DESCRIPTION
--        "The value of vRtrMplsOutOfProfOctetsFc3 indicates the number of out of 
--        profile octets received for Forwarding Class 3."
--    ::= { vRtrMplsLspStatisticsEntry 82 }
--
--vRtrMplsOutOfProfOctetsFc3Low32   OBJECT-TYPE
--    SYNTAX      Counter32
--    MAX-ACCESS  read-only
--    STATUS      current
--    DESCRIPTION
--        "The value of vRtrMplsOutOfProfOctetsFc3 indicates the lower 
--         32 bits of the value of vRtrMplsOutOfProfOctetsFc3."
--    ::= { vRtrMplsLspStatisticsEntry 83 }
--
--vRtrMplsOutOfProfOctetsFc3High32   OBJECT-TYPE
--    SYNTAX      Counter32
--    MAX-ACCESS  read-only
--    STATUS      current
--    DESCRIPTION
--        "The value of vRtrMplsOutOfProfOctetsFc3 indicates the higher 
--         32 bits of the value of vRtrMplsOutOfProfOctetsFc3."
--    ::= { vRtrMplsLspStatisticsEntry 84 }        
--    
--vRtrMplsOutOfProfOctetsFc4   OBJECT-TYPE
--    SYNTAX      Counter64
--    MAX-ACCESS  read-only
--    STATUS      current
--    DESCRIPTION
--        "The value of vRtrMplsOutOfProfOctetsFc4 indicates the number of out of 
--        profile octets received for Forwarding Class 4."
--    ::= { vRtrMplsLspStatisticsEntry 85 }
--
--vRtrMplsOutOfProfOctetsFc4Low32   OBJECT-TYPE
--    SYNTAX      Counter32
--    MAX-ACCESS  read-only
--    STATUS      current
--    DESCRIPTION
--        "The value of vRtrMplsOutOfProfOctetsFc4 indicates the lower 
--         32 bits of the value of vRtrMplsOutOfProfOctetsFc4."
--    ::= { vRtrMplsLspStatisticsEntry 86 }
--
--vRtrMplsOutOfProfOctetsFc4High32   OBJECT-TYPE
--    SYNTAX      Counter32
--    MAX-ACCESS  read-only
--    STATUS      current
--    DESCRIPTION
--        "The value of vRtrMplsOutOfProfOctetsFc4 indicates the higher 
--         32 bits of the value of vRtrMplsOutOfProfOctetsFc4."
--    ::= { vRtrMplsLspStatisticsEntry 87 }            
--
--vRtrMplsOutOfProfOctetsFc5  OBJECT-TYPE
--    SYNTAX      Counter64
--    MAX-ACCESS  read-only
--    STATUS      current
--    DESCRIPTION
--        "The value of vRtrMplsOutOfProfOctetsFc5 indicates the number of out of 
--        profile octets received for Forwarding Class 5."
--    ::= { vRtrMplsLspStatisticsEntry 88 }
--
--vRtrMplsOutOfProfOctetsFc5Low32   OBJECT-TYPE
--    SYNTAX      Counter32
--    MAX-ACCESS  read-only
--    STATUS      current
--    DESCRIPTION
--        "The value of vRtrMplsOutOfProfOctetsFc5 indicates the lower 
--         32 bits of the value of vRtrMplsOutOfProfOctetsFc5."
--    ::= { vRtrMplsLspStatisticsEntry 89 }
--
--vRtrMplsOutOfProfOctetsFc5High32   OBJECT-TYPE
--    SYNTAX      Counter32
--    MAX-ACCESS  read-only
--    STATUS      current
--    DESCRIPTION
--        "The value of vRtrMplsOutOfProfOctetsFc5 indicates the higher 
--         32 bits of the value of vRtrMplsOutOfProfOctetsFc5."
--    ::= { vRtrMplsLspStatisticsEntry 90 }            
--
--vRtrMplsOutOfProfOctetsFc6   OBJECT-TYPE
--    SYNTAX      Counter64
--    MAX-ACCESS  read-only
--    STATUS      current
--    DESCRIPTION
--        "The value of vRtrMplsOutOfProfOctetsFc6 indicates the number of out of 
--        profile octets received for Forwarding Class 6."
--    ::= { vRtrMplsLspStatisticsEntry 91 }
--
--vRtrMplsOutOfProfOctetsFc6Low32   OBJECT-TYPE
--    SYNTAX      Counter32
--    MAX-ACCESS  read-only
--    STATUS      current
--    DESCRIPTION
--        "The value of vRtrMplsOutOfProfOctetsFc6 indicates the lower 
--         32 bits of the value of vRtrMplsOutOfProfOctetsFc6."
--    ::= { vRtrMplsLspStatisticsEntry 92 }
--
--vRtrMplsOutOfProfOctetsFc6High32   OBJECT-TYPE
--    SYNTAX      Counter32
--    MAX-ACCESS  read-only
--    STATUS      current
--    DESCRIPTION
--        "The value of vRtrMplsOutOfProfOctetsFc6 indicates the higher 
--         32 bits of the value of vRtrMplsOutOfProfOctetsFc6."
--    ::= { vRtrMplsLspStatisticsEntry 93 }            
--
--vRtrMplsOutOfProfOctetsFc7   OBJECT-TYPE
--    SYNTAX      Counter64
--    MAX-ACCESS  read-only
--    STATUS      current
--    DESCRIPTION
--        "The value of vRtrMplsOutOfProfOctetsFc7 indicates the number of out of 
--        profile octets received for Forwarding Class 7."
--    ::= { vRtrMplsLspStatisticsEntry 94 }
--
--vRtrMplsOutOfProfOctetsFc7Low32   OBJECT-TYPE
--    SYNTAX      Counter32
--    MAX-ACCESS  read-only
--    STATUS      current
--    DESCRIPTION
--        "The value of vRtrMplsOutOfProfOctetsFc7 indicates the lower 
--         32 bits of the value of vRtrMplsOutOfProfOctetsFc7."
--    ::= { vRtrMplsLspStatisticsEntry 95 }
--
--vRtrMplsOutOfProfOctetsFc7High32   OBJECT-TYPE
--    SYNTAX      Counter32
--    MAX-ACCESS  read-only
--    STATUS      current
--    DESCRIPTION
--        "The value of vRtrMplsOutOfProfOctetsFc7 indicates the higher 
--         32 bits of the value of vRtrMplsOutOfProfOctetsFc7."
--    ::= { vRtrMplsLspStatisticsEntry 96 }      
--
--vRtrMplsLspStatsPSBMatch            OBJECT-TYPE
--    SYNTAX      TruthValue
--    MAX-ACCESS  read-only
--    STATUS      current
--    DESCRIPTION
--        "The value of vRtrMplsLspStatsPSBMatch indicates if a path state block 
--        (PSB) match was made against this LSP name."
--    ::= { vRtrMplsLspStatisticsEntry 97 }      
--vRtrMplsLspStatsTpOnly  OBJECT-TYPE
--    SYNTAX      TruthValue
--    MAX-ACCESS  read-only
--    STATUS      current
--    DESCRIPTION
--        "The value of vRtrMplsLspStatsTpOnly indicates whether the statistics 
--         apply to mpls-tp lsp or for regular rsvp-te signalled terminating LSP.
--
--         The value of 'true' indicates the statistics apply to mpls-tp LSP only.
--         
--         The value of 'false' indicates the statistics apply for regular rsvp-te
--         signalled terminating LSP."
--    ::= { vRtrMplsLspStatisticsEntry 98 }  
 
----
--  The Virtual Router MPLS Labeled Switch Path Template(Lsp-Template) Table
----
-- vRtrMplsLspTemplateTblLastChgd OBJECT-TYPE
--     SYNTAX      TimeStamp
--     MAX-ACCESS  read-only
--     STATUS      current
--     DESCRIPTION
--         "The value of vRtrMplsLspTemplateTblLastChgd indicates the
--          sysUpTime at the time of the last modification of an entry
--          in the vRtrMplsLspTemplateTable. 
--          
--          If no changes were made to the table since the last
--          re-initialization of the local network management subsystem,
--          then this object contains a zero value."
--     ::= { tnMplsObjs 40 }
--  
-- vRtrMplsLspTemplateTable    OBJECT-TYPE
--     SYNTAX      SEQUENCE OF VRtrMplsLspTemplateEntry
--     MAX-ACCESS  not-accessible
--     STATUS      current
--     DESCRIPTION
--         "The vRtrMplsLspTemplateTable has an entry for each Labeled Switch
--          Path Template(LSP Template) configured for a virtual router in the system.
--          
--          The table contains a list of LSP Templates that are referenced when
--          dynamic LSP creation is required."
--     ::= { tnMplsObjs 41 }
-- 
-- vRtrMplsLspTemplateEntry    OBJECT-TYPE
--     SYNTAX      VRtrMplsLspTemplateEntry
--     MAX-ACCESS  not-accessible
--     STATUS      current
--     DESCRIPTION
--         "Each row entry represents a Labeled Switch Path Template (LSP Template)
--          configured for a virtual router in the system.
--          
--          Entries in this table can be created and deleted via SNMP SET operations."
--     INDEX { tnSysSwitchId, vRtrID,
--             vRtrMplsLspTemplateName }
--     ::= { vRtrMplsLspTemplateTable 1 }
-- 
-- VRtrMplsLspTemplateEntry ::= SEQUENCE {
--     vRtrMplsLspTemplateName             TNamedItem,
--     vRtrMplsLspTemplateRowStatus        RowStatus,
--     vRtrMplsLspTemplateLastChanged      TimeStamp,
--     vRtrMplsLspTemplateAdminState       TmnxAdminState,
--     vRtrMplsLspTemplateType             INTEGER,     
--     vRtrMplsLspTemplateAdaptive         TruthValue,
--     vRtrMplsLspTemplateBandwidth        Integer32,
--     vRtrMplsLspTemplateCspf             TruthValue,
--     vRtrMplsLspTemplateDefaultPath      MplsTunnelIndex,
--     vRtrMplsLspTemplateAdmGrpIncl       Unsigned32,
--     vRtrMplsLspTemplateAdmGrpExcl       Unsigned32,
--     vRtrMplsLspTemplateFastReroute      TruthValue,
--     vRtrMplsLspTemplateFRMethod         INTEGER, 
--     vRtrMplsLspTemplateFRHopLimit       Unsigned32,
--     vRtrMplsLspTemplateHopLimit         Unsigned32,
--     vRtrMplsLspTemplateRecord           INTEGER,
--     vRtrMplsLspTemplateRecordLabel      INTEGER,
--     vRtrMplsLspTemplateRetryLimit       Unsigned32,
--     vRtrMplsLspTemplateRetryTimer       Unsigned32,
--     vRtrMplsLspTemplateCspfTeMetric     TruthValue,
--     vRtrMplsLspTemplateLspCount         Gauge32,
--     vRtrMplsLspTemplateMvpnRefCount     Gauge32
-- }
-- 
-- vRtrMplsLspTemplateName  OBJECT-TYPE
--     SYNTAX      TNamedItem
--     MAX-ACCESS  not-accessible
--     STATUS      current
--     DESCRIPTION
--         "The value of the object vRtrMplsLspTemplateName specifies the name of
--          the LSP Template which is used as a guideline to create and signal
--          multiple LSP instances when dynamic LSP creation is required."
--     ::= { vRtrMplsLspTemplateEntry 1 }   
--     
-- vRtrMplsLspTemplateRowStatus  OBJECT-TYPE
--     SYNTAX       RowStatus
--     MAX-ACCESS   read-create
--     STATUS       current
--     DESCRIPTION
--         "The value of vRtrMplsLspTemplateRowStatus specifies the Row Status
--          for this entry."
--     ::= { vRtrMplsLspTemplateEntry 2 }
-- 
-- vRtrMplsLspTemplateLastChanged  OBJECT-TYPE
--     SYNTAX       TimeStamp
--     MAX-ACCESS   read-only
--     STATUS       current
--     DESCRIPTION
--         "The value of vRtrMplsLspTemplateLastChanged indicates the 
--          timestamp of last change to this row in vRtrMplsLspTemplateTable."
--     ::= { vRtrMplsLspTemplateEntry 3 } 
--     
-- vRtrMplsLspTemplateAdminState  OBJECT-TYPE
--     SYNTAX      TmnxAdminState
--     MAX-ACCESS  read-create
--     STATUS      current
--     DESCRIPTION
--         "The value of vRtrMplsLspTemplateAdminState specifies the current 
--          administrative state of the LSP Template."
--     DEFVAL { outOfService }
--     ::= { vRtrMplsLspTemplateEntry 4 }   
-- 
-- vRtrMplsLspTemplateType  OBJECT-TYPE
--     SYNTAX      INTEGER {
--                     p2mp (1)
--                 }
--     MAX-ACCESS  read-create
--     STATUS      current
--     DESCRIPTION
--             "The value of vRtrMplsLspTemplateType specifies the type of the
--              LSP template.
--                        
--              When the value of vRtrMplsLspTemplateType is set to 'p2mp',
--              the template is used for auto creation of P2MP LSPs."  
--     DEFVAL { p2mp }             
--     ::= { vRtrMplsLspTemplateEntry 5 }      
--        
-- vRtrMplsLspTemplateAdaptive  OBJECT-TYPE
--     SYNTAX      TruthValue
--     MAX-ACCESS  read-create
--     STATUS      current
--     DESCRIPTION
--         "The value of vRtrMplsLspTemplateAdaptive specifies whether the 
--          make-before-break functionality is enabled for the LSPs that
--          are dynamically created using this LSP template.
--          
--          When the value of vRtrMplsLspTemplateAdaptive is set to 'true',
--          make-before-break functionality is enabled. When the value is 
--          set to 'false' make-before-break functionality is disabled."
--     DEFVAL { true }
--     ::= { vRtrMplsLspTemplateEntry 6 }    
--     
-- vRtrMplsLspTemplateBandwidth  OBJECT-TYPE
--     SYNTAX      Integer32 (0..100000)
--     UNITS       "mega-bits per second"
--     MAX-ACCESS  read-create
--     STATUS      current
--     DESCRIPTION
--         "The value of vRtrMplsLspTemplateBandwidth specifies the amount
--          of bandwidth in mega-bits per seconds (Mbps) to be reserved
--          for the LSPs that are dynamically created using this LSP template.
--          A value of zero (0) indicates that no bandwidth is reserved."
--     DEFVAL { 0 }
--     ::= { vRtrMplsLspTemplateEntry 7 }       
--     
-- vRtrMplsLspTemplateCspf  OBJECT-TYPE
--     SYNTAX      TruthValue
--     MAX-ACCESS  read-create
--     STATUS      current
--     DESCRIPTION
--         "The value of vRtrMplsLspTemplateCspf specifies whether the 
--          CSPF computation for constrained-path LSP is enabled for 
--          the LSPs that are dynamically created using this LSP template.
--          
--          When the value of vRtrMplsLspTemplateCspf is set to 'true',
--          CSPF computation for constrained-path is enabled. 
--          When the value is set to 'false', CSPF computation for
--          constrained-path is disabled."  
--     DEFVAL { false }
--    ::= { vRtrMplsLspTemplateEntry 8 }       
--    
-- vRtrMplsLspTemplateDefaultPath  OBJECT-TYPE
--     SYNTAX      MplsTunnelIndex
--     MAX-ACCESS  read-create
--     STATUS      current
--     DESCRIPTION
--         "The value of vRtrMplsLspTemplateDefaultPath specifies the default
--          path used to signal LSPs that are dynamically created using this
--          LSP template.
--          
--          If a corresponding index does not exist in MPLS-TE-MIB::mplsTunnelTable,
--          an 'inconsistentValue' error will be returned. "               
--     DEFVAL { 0 }
--    ::= { vRtrMplsLspTemplateEntry 9 }  
--    
-- vRtrMplsLspTemplateAdmGrpIncl   OBJECT-TYPE
--     SYNTAX      Unsigned32
--     MAX-ACCESS  read-create
--     STATUS      current
--     DESCRIPTION
--         "The value of vRtrMplsLspTemplateAdmGrpIncl specifies a bit-map 
--          of admin groups that are included when the dynamically created
--          LSPs using this template are setup . 
--          
--          If bit 'n' is set, then the admin group with value 'n' is included. 
--          This implies that each link that the LSP goes through must be associated 
--          with  at least one of the admin groups in the include list.
-- 
--          By default, all admin groups are in the include list."         
--      DEFVAL { '00000000'H }
--     ::= { vRtrMplsLspTemplateEntry 10 }   
--     
-- vRtrMplsLspTemplateAdmGrpExcl  OBJECT-TYPE
--     SYNTAX      Unsigned32
--     MAX-ACCESS  read-create
--     STATUS      current
--     DESCRIPTION
--         "The value of vRtrMplsLspTemplateAdmGrpExcl specifies a bit-map 
--          of admin groups that are excluded when the dynamically created
--          LSPs using this template are setup. 
--          
--          If bit 'n' is set, then the admin group with value 'n' is excluded.
--          This implies that each link that the LSP goes through must not be associated
--          with any of the admin groups in the exclude list.
-- 
--          By default, no admin groups are in the exclude list."
--     DEFVAL { '00000000'H }
--     ::= { vRtrMplsLspTemplateEntry 11 }       
--     
-- vRtrMplsLspTemplateFastReroute  OBJECT-TYPE
--     SYNTAX      TruthValue
--     MAX-ACCESS  read-create
--     STATUS      current
--     DESCRIPTION
--         "The value of vRtrMplsLspTemplateFastReroute specifies whether 
--          fast reroute is enabled for the LSPs that are dynamically created
--          using this LSP template.
--         
--          When the value of vRtrMplsLspTemplateFastReroute is set to 'true',
--          fast reroute is enabled for the LSP. When the value of
--          vRtrMplsLspTemplateFastReroute is set to'false', fast reroute
--          is disabled."
--     DEFVAL { false }
--     ::= { vRtrMplsLspTemplateEntry 12 }       
--           
-- vRtrMplsLspTemplateFRMethod  OBJECT-TYPE
--     SYNTAX      INTEGER {
--                     oneToOneBackup(1),
--                     facilityBackup(2)
--                 }
--     MAX-ACCESS  read-create
--     STATUS      current
--     DESCRIPTION
--             "The value of vRtrMplsLspTemplateFRMethod specifies the fast reroute
--              method used for the LSPs that are dynamically created using this LSP template.
--             
--              When the value of vRtrMplsLspTemplateFRMethod is set to 'oneToOneBackup',
--              a backup LSP is established which will intersect the original LSP somewhere 
--              downstream of the point of link or node failure. For each LSP that is 
--              backed up, a separate backup LSP is established.
-- 
--              When the value of vRtrMplsLspTemplateFRMethod is set to 'facilityBackup',
--              Instead of creating a separateLSP for every LSP that is to be backed up,
--              a single LSP is created which serves as a backup for a set of LSPs.             
--              
--              For LSP templates of type P2MP, oneToOneBackup is not supported."
--     DEFVAL { facilityBackup }
--     ::= { vRtrMplsLspTemplateEntry 13 }     
--     
-- vRtrMplsLspTemplateFRHopLimit  OBJECT-TYPE
--     SYNTAX      Unsigned32 (0..255)
--     MAX-ACCESS  read-create
--     STATUS      current
--     DESCRIPTION
--         "The value of vRtrMplsLspTemplateFRHopLimit specifies the total number
--          of hops a detour or backup LSP can take before merging back onto the
--          main LSP path."
--     DEFVAL { 16 }
--     ::= { vRtrMplsLspTemplateEntry 14 }
-- 
-- vRtrMplsLspTemplateHopLimit  OBJECT-TYPE
--     SYNTAX      Unsigned32 (2..255)
--     MAX-ACCESS  read-create
--     STATUS      current
--     DESCRIPTION
--         "The value of vRtrMplsLspTemplateHopLimit specifies the maximum number
--          of hops that a dynamically created LSP will traverse including the
--          ingress and egress ESRs. A LSP will not be set up if the hop limit 
--          is exceeded."
--     DEFVAL { 255 }
--     ::= { vRtrMplsLspTemplateEntry 15 }  
-- 
-- vRtrMplsLspTemplateRecord  OBJECT-TYPE
--     SYNTAX      INTEGER {
--                     record (1),
--                     noRecord (2)
--                 }
--     MAX-ACCESS  read-create
--     STATUS      current
--     DESCRIPTION
--         "The value of vRtrMplsLspTemplateRecord  specifies whether the
--          recording of all the hops is enabled for LSPs that are dynamically 
--          created using this template.
--          
--          When the value of vRtrMplsLspTemplateRecord is set to 'record', recording 
--          of all the hops that a LSP traverses is enabled. When the value of 
--          vRtrMplsLspTemplateRecord is set to 'noRecord', recording of all the hops that 
--          a LSP traverses is disabled."
--     DEFVAL { record }
--     ::= { vRtrMplsLspTemplateEntry 16 }       
--     
-- vRtrMplsLspTemplateRecordLabel  OBJECT-TYPE
--     SYNTAX      INTEGER {
--                     record (1),
--                     noRecord (2)
--                 }
--     MAX-ACCESS  read-create
--     STATUS      current
--     DESCRIPTION
--         "The value of vRtrMplsLspTemplateRecordLabel specifies whether the
--          recording of labels is enabled for LSPs that are dynamically 
--          created using this LSP template .
--          
--          When the value of vRtrMplsLspTemplateRecordLabel is set to 'record',
--          recording of labels at each node that a LSP traverses is enabled.
--          When the value of vRtrMplsLspTemplateRecordLabel is set to 'noRecord',
--          recording of labels at each node that a LSP traverses is disabled."
--     DEFVAL { record }
--     ::= { vRtrMplsLspTemplateEntry 17 } 
--     
-- vRtrMplsLspTemplateRetryLimit  OBJECT-TYPE
--     SYNTAX      Unsigned32 (0..10000)
--     MAX-ACCESS  read-create
--     STATUS      current
--     DESCRIPTION
--         "The value of vRtrMplsLspTemplateRetryLimit specifies the maximum number of
--          attempts made to establish an LSP that is dynamically created using this template.
--          A value of zero(0) specifies that an infinite number of retry attempts
--          should be made."
--     DEFVAL { 0 }
--     ::= { vRtrMplsLspTemplateEntry 18 }
--     
-- vRtrMplsLspTemplateRetryTimer   OBJECT-TYPE
--     SYNTAX      Unsigned32 (1..600)
--     UNITS       "seconds"
--     MAX-ACCESS  read-create
--     STATUS      current
--     DESCRIPTION
--         "The value of vRtrMplsLspTemplateRetryTimer specifies the time in seconds
--          a dynamically created Lsp waits before it attempts to re-establish itself."
--     DEFVAL { 30 }
--     ::= { vRtrMplsLspTemplateEntry 19 }   
--     
-- vRtrMplsLspTemplateCspfTeMetric  OBJECT-TYPE
--     SYNTAX      TruthValue
--     MAX-ACCESS  read-create
--     STATUS      current
--     DESCRIPTION
--         "The value of vRtrMplsLspTemplateCspfTeMetric specifies whether the TE
--          metric is used for the purpose of the LSP path computation by 
--          CSPF (Constrained Shortest Path First).  
--          
--          When the value of vRtrMplsLspTemplateCspfTeMetric  is set to 'true', the 
--          TE metric is used to compute the path of the LSP by CSPF. When the value of 
--          vRtrMplsLspTemplateCspfTeMetric  is set to 'false', IGP metric is used to
--          compute the path of the LSP by CSPF."
--     DEFVAL { false }
--     ::= { vRtrMplsLspTemplateEntry 20 }            
-- 
-- vRtrMplsLspTemplateLspCount  OBJECT-TYPE
--     SYNTAX       Gauge32
--     MAX-ACCESS   read-only
--     STATUS       current
--     DESCRIPTION
--         "The value of vRtrMplsLspTemplateLspCount indicates the number of
--          LSPs of type 'p2mpAuto' that are created using this template."
--     ::= { vRtrMplsLspTemplateEntry 21 }     
-- 
-- vRtrMplsLspTemplateMvpnRefCount  OBJECT-TYPE
--     SYNTAX       Gauge32
--     MAX-ACCESS   read-only
--     STATUS       current
--     DESCRIPTION
--         "The value of vRtrMplsLspTemplateMvpnRefCount indicates the number of
--          MVPNs as well as number of P2MP LSP users associated to this template."
--     ::= { vRtrMplsLspTemplateEntry 22 }   

--
--  The Virtual Router MPLS Labeled Switch Path (LSP) Auto Bandwidth Table
--
-- vRtrMplsLspAutoBWTableLastChg OBJECT-TYPE
--     SYNTAX      TimeStamp
--     MAX-ACCESS  read-only
--     STATUS      current
--     DESCRIPTION
--         "The value of vRtrMplsLspAutoBWTableLastChg indicates the
--          sysUpTime at the time of the last modification to 
--          vRtrMplsLspAutoBandwidthTable by adding, deleting an entry or change
--          to a writable object in the table.
-- 
--          If no changes were made to the table since the last 
--          re-initialization of the local network management subsystem, 
--          then this object contains a zero value."
--     ::= { tnMplsObjs 42 } 
-- 
-- vRtrMplsLspAutoBandwidthTable    OBJECT-TYPE
--     SYNTAX      SEQUENCE OF VRtrMplsLspAutoBandwidthEntry
--     MAX-ACCESS  not-accessible
--     STATUS      current
--     DESCRIPTION
--         "The vRtrMplsLspAutoBandwidthTable has an entry for auto bandwidth
--          configuration for each Labeled Switch Path (LSP) configured for a
--          virtual router in the system."
--     ::= { tnMplsObjs 43 }
-- 
-- vRtrMplsLspAutoBandwidthEntry    OBJECT-TYPE
--     SYNTAX      VRtrMplsLspAutoBandwidthEntry
--     MAX-ACCESS  not-accessible
--     STATUS      current
--     DESCRIPTION
--         "Each row entry represents auto bandwidth configuration
--          for a Labeled Switch Path (LSP) configured
--          for a virtual router in the system."
--     INDEX { tnSysSwitchId, vRtrID, vRtrMplsLspAutoBWLspName }
--     ::= { vRtrMplsLspAutoBandwidthTable 1 }
-- 
-- VRtrMplsLspAutoBandwidthEntry ::= SEQUENCE {
--     vRtrMplsLspAutoBWLspName            TNamedItem,
--     vRtrMplsLspAutoBWLastChange         TimeStamp,
--     vRtrMplsLspAutoBWAdjDNPercent       Unsigned32,
--     vRtrMplsLspAutoBWAdjDNMbps          Unsigned32,
--     vRtrMplsLspAutoBWAdjMultiplier      Unsigned32,
--     vRtrMplsLspAutoBWAdjUPPercent       Unsigned32,
--     vRtrMplsLspAutoBWAdjUPMbps          Unsigned32,
--     vRtrMplsLspAutoBWMaxBW              Unsigned32,
--     vRtrMplsLspAutoBWMinBW              Unsigned32,
--     vRtrMplsLspAutoBWMonitorBW          TruthValue,
--     vRtrMplsLspAutoBWOverFlow           Unsigned32,
--     vRtrMplsLspAutoBWOvrFlwThreshold    Unsigned32,
--     vRtrMplsLspAutoBWOvrFlwBW           Unsigned32,
--     vRtrMplsLspAutoBWSampMultiplier     Unsigned32,
--     vRtrMplsLspAutoBWSampTime           Unsigned32,
--     vRtrMplsLspAutoBWLastAdj            TimeStamp,
--     vRtrMplsLspAutoBWLastAdjCause       TmnxMplsLspAutoBWLastAdjCause,
--     vRtrMplsLspAutoBWNextAdj            Unsigned32,
--     vRtrMplsLspAutoBWMaxAvgRate         Unsigned32,
--     vRtrMplsLspAutoBWLastAvgRate        Unsigned32,
--     vRtrMplsLspAutoBWInheritance        Unsigned32,
--     vRtrMplsLspAutoBWCurrentBW          Unsigned32,
--     vRtrMplsLspAutoBWAdjTime            Unsigned32,
--     vRtrMplsLspAutoBWOvrFlwCount        Unsigned32,
--     vRtrMplsLspAutoBWSampCount          Unsigned32,
--     vRtrMplsLspAutoBWAdjCount           Unsigned32,
--     vRtrMplsLspAutoBWOperState          TmnxEnabledDisabled,
--     vRtrMplsLspAutoBWSampInterval       Unsigned32
-- 
--     }
-- 
-- vRtrMplsLspAutoBWLspName    OBJECT-TYPE
--     SYNTAX      TNamedItem
--     MAX-ACCESS  not-accessible
--     STATUS      current
--     DESCRIPTION
--         "The value of vRtrMplsLspAutoBWLspName uniquely identifies a
--          row in the vRtrMplsLspAutoBandwidthTable." 
--     ::= { vRtrMplsLspAutoBandwidthEntry 1 }
--     
-- vRtrMplsLspAutoBWLastChange       OBJECT-TYPE
--     SYNTAX      TimeStamp
--     MAX-ACCESS  read-only
--     STATUS      current
--     DESCRIPTION
--         "The sysUpTime when this row was last modified."
--     ::= { vRtrMplsLspAutoBandwidthEntry 2 }
-- 
-- vRtrMplsLspAutoBWAdjDNPercent   OBJECT-TYPE
--     SYNTAX      Unsigned32 (0..100)
--     UNITS       "percent"
--     MAX-ACCESS  read-write
--     STATUS      current
--     DESCRIPTION
--         "The value of vRtrMplsLspAutoBWAdjDNPercent specifies minimum
--          difference between the current bandwidth reservation of the
--          LSP and the (measured) maximum average data rate, expressed
--          as a percentage of the current bandwidth, for decreasing
--          the bandwidth of the LSP. At the adjust interval expiry, if
--          the measured bandwidth falls below the current bandwidth by 
--          the value of vRtrMplsLspAutoBWAdjDNPercent it can cause 
--          a re-signaling attempt for the LSP
--          
--          When the value of vRtrMplsLspAutoBWAdjDNPercent is 0 it means 
--          that this threshold check is always true for any measured 
--          bandwidth less than current bandwidth"
-- 
--     DEFVAL { 5 }
--     ::= { vRtrMplsLspAutoBandwidthEntry 3 }   
-- 
-- vRtrMplsLspAutoBWAdjDNMbps   OBJECT-TYPE
--     SYNTAX      Unsigned32 (0..100000) 
--     UNITS       "Mbps"
--     MAX-ACCESS  read-write
--     STATUS      current
--     DESCRIPTION
--         "The value of vRtrMplsLspAutoBWAdjDNMbps specifies the minimum
--          difference between the current bandwidth reservation of the LSP 
--          and the (measured) maximum average data rate, expressed as an 
--          absolute bandwidth (Mbps), for decreasing the bandwidth 
--          of the LSP." 
--     DEFVAL { 0 }
--     ::= { vRtrMplsLspAutoBandwidthEntry 4 }   
-- 
-- vRtrMplsLspAutoBWAdjMultiplier   OBJECT-TYPE
--     SYNTAX      Unsigned32 (1..16383)
--     MAX-ACCESS  read-write
--     STATUS      current
--     DESCRIPTION
--         "The value of vRtrMplsLspAutoBWAdjMultiplier specifies the number 
--          of collection intervals in the adjust interval.
--          
--          The default value is derived from vRtrMplsGeneralAutoBWDefAdjMul
--          and vRtrMplsLspAutoBWAdjCount."
--     DEFVAL { 288 }
--     ::= { vRtrMplsLspAutoBandwidthEntry 5 }   
-- 
-- vRtrMplsLspAutoBWAdjUPPercent   OBJECT-TYPE
--     SYNTAX      Unsigned32 (0..100)
--     UNITS       "percent"
--     MAX-ACCESS  read-write
--     STATUS      current
--     DESCRIPTION
--         "The value of vRtrMplsLspAutoBWAdjUPPercent specifies minimum
--          difference between the current bandwidth reservation of the
--          LSP and the (measured) maximum average data rate, expressed
--          as a percentage of the current bandwidth, for increasing
--          the bandwidth of the LSP. At the adjust interval expiry, if
--          the measured bandwidth exceeds the current bandwidth by 
--          the value of vRtrMplsLspAutoBWAdjUPPercent it can cause 
--          a re-signaling attempt for the LSP
--          
--          When the value of vRtrMplsLspAutoBWAdjUPPercent is 0 it means 
--          that this threshold check is always true for any measured 
--          bandwidth greater than current bandwidth"
-- 
--     DEFVAL { 5 }
--     ::= { vRtrMplsLspAutoBandwidthEntry 6 }   
-- 
-- vRtrMplsLspAutoBWAdjUPMbps   OBJECT-TYPE
--     SYNTAX      Unsigned32 (0..100000)
--     UNITS       "Mbps"
--     MAX-ACCESS  read-write
--     STATUS      current
--     DESCRIPTION
--         "The value of vRtrMplsLspAutoBWAdjDNMbps specifies the minimum
--          difference between the current bandwidth reservation of the LSP 
--          and the (measured) maximum average data rate, expressed as an 
--          absolute bandwidth (Mbps), for increasing the bandwidth 
--          of the LSP." 
--     DEFVAL { 0 }
--     ::= { vRtrMplsLspAutoBandwidthEntry 7 }   
-- 
-- vRtrMplsLspAutoBWMaxBW   OBJECT-TYPE
--     SYNTAX      Unsigned32 (0..100000)
--     UNITS       "Mbps"
--     MAX-ACCESS  read-write
--     STATUS      current
--     DESCRIPTION
--         "The value of vRtrMplsLspAutoBWMaxBW specifies the maximum
--          that auto-bandwidth allocation is allowed to request for a LSP." 
--     DEFVAL { 100000 }
--     ::= { vRtrMplsLspAutoBandwidthEntry 8 }   
-- 
-- vRtrMplsLspAutoBWMinBW   OBJECT-TYPE
--     SYNTAX      Unsigned32 (0..100000)
--     UNITS       "Mbps"
--     MAX-ACCESS  read-write
--     STATUS      current
--     DESCRIPTION
--         "The value of vRtrMplsLspAutoBWMinBW specifies the minimum
--          that auto-bandwidth allocation is allowed to request for a LSP." 
--     DEFVAL { 0 }
--     ::= { vRtrMplsLspAutoBandwidthEntry 9 }   
-- 
-- vRtrMplsLspAutoBWMonitorBW   OBJECT-TYPE
--     SYNTAX      TruthValue
--     UNITS       "Mbps" 
--     MAX-ACCESS  read-write
--     STATUS      current
--     DESCRIPTION
--         "The value of vRtrMplsLspAutoBWMonitorBW specifies whether the 
--          collection and display of auto-bandwidth measurements is 
--          enabled or disabled for the LSP.
--          
--          When the value of vRtrMplsLspAutoBWMonitorBW is 'true' the 
--          collection and display of auto-bandwidth measurements is enabled
--          and when the value is 'false' it is disabled." 
--     DEFVAL { false }
--     ::= { vRtrMplsLspAutoBandwidthEntry 10 }   
-- 
-- vRtrMplsLspAutoBWOverFlow   OBJECT-TYPE
--     SYNTAX      Unsigned32 (0|1..10)
--     MAX-ACCESS  read-write
--     STATUS      current
--     DESCRIPTION
--         "The value of vRtrMplsLspAutoBWOverFlow specifies number 
--          of overflow samples that triggers an overflow auto-bandwidth 
--          adjustment attempt."
--     DEFVAL { 0 }
--     ::= { vRtrMplsLspAutoBandwidthEntry 11 }   
-- 
-- vRtrMplsLspAutoBWOvrFlwThreshold   OBJECT-TYPE
--     SYNTAX      Unsigned32 (0|1..100)
--     UNITS       "percent"
--     MAX-ACCESS  read-write
--     STATUS      current
--     DESCRIPTION
--         "The value of vRtrMplsLspAutoBWOvrFlwThreshold specifies the 
--          minimum difference between the current bandwidth of the LSP 
--          and the sampled data rate, expressed as a percentage of the 
--          current bandwidth, for counting an overflow sample." 
--     DEFVAL { 0 }
--     ::= { vRtrMplsLspAutoBandwidthEntry 12 }   
-- 
-- vRtrMplsLspAutoBWOvrFlwBW   OBJECT-TYPE
--     SYNTAX      Unsigned32 (0..100000)
--     UNITS       "Mbps"
--     MAX-ACCESS  read-write
--     STATUS      current
--     DESCRIPTION
--         "The value of vRtrMplsLspAutoBWOvrFlwBW specifies the 
--          minimum difference between the current bandwidth of the LSP 
--          and the sampled data rate, expressed as an absolute bandwidth 
--          (Mbps), for counting an overflow sample." 
--     DEFVAL { 0 }
--     ::= { vRtrMplsLspAutoBandwidthEntry 13 }   
-- 
-- vRtrMplsLspAutoBWSampMultiplier   OBJECT-TYPE
--     SYNTAX      Unsigned32 (1..511)
--     MAX-ACCESS  read-write
--     STATUS      current
--     DESCRIPTION
--         "The value of vRtrMplsLspAutoBWSampMultiplier specifies the 
--          mulitplier for collection intervals in a sample interval."
--     DEFVAL { 1 }
--     ::= { vRtrMplsLspAutoBandwidthEntry 14 }   
-- 
-- vRtrMplsLspAutoBWSampTime   OBJECT-TYPE
--     SYNTAX      Unsigned32
--     UNITS       "minutes"  
--     MAX-ACCESS  read-only
--     STATUS      current
--     DESCRIPTION
--         "The value of vRtrMplsLspAutoBWSampTime indicates the 
--          sample multipler times the collection interval."
--     ::= { vRtrMplsLspAutoBandwidthEntry 15 }   
-- 
-- vRtrMplsLspAutoBWLastAdj   OBJECT-TYPE
--     SYNTAX      TimeStamp
--     MAX-ACCESS  read-only
--     STATUS      current
--     DESCRIPTION
--         "The value of vRtrMplsLspAutoBWLastAdj indicates the 
--          system time for the last auto-bandwidth
--          adjustment."
--     ::= { vRtrMplsLspAutoBandwidthEntry 16 }   
-- 
-- vRtrMplsLspAutoBWLastAdjCause   OBJECT-TYPE
--     SYNTAX      TmnxMplsLspAutoBWLastAdjCause
--     MAX-ACCESS  read-only
--     STATUS      current
--     DESCRIPTION
--         "The value of vRtrMplsLspAutoBWLastAdjCause indicates the 
--          cause for the last auto-bandwidth adjustment."
--     ::= { vRtrMplsLspAutoBandwidthEntry 17 }   
-- 
-- vRtrMplsLspAutoBWNextAdj   OBJECT-TYPE
--     SYNTAX      Unsigned32
--     UNITS       "minutes"  
--     MAX-ACCESS  read-only
--     STATUS      current
--     DESCRIPTION
--         "The value of vRtrMplsLspAutoBWNextAdj indicates the 
--          system time when then adjust-timer will expire."
--     ::= { vRtrMplsLspAutoBandwidthEntry 18 }   
-- 
-- vRtrMplsLspAutoBWMaxAvgRate   OBJECT-TYPE
--     SYNTAX      Unsigned32
--     UNITS       "Mbps"    
--     MAX-ACCESS  read-only
--     STATUS      current
--     DESCRIPTION
--         "The value of vRtrMplsLspAutoBWMaxAvgRate indicates the 
--          maximum average data rate in any sample interval of the
--          current adjust interval."
--     ::= { vRtrMplsLspAutoBandwidthEntry 19 }   
-- 
-- vRtrMplsLspAutoBWLastAvgRate   OBJECT-TYPE
--     SYNTAX      Unsigned32
--     UNITS       "Mbps"
--     MAX-ACCESS  read-only
--     STATUS      current
--     DESCRIPTION
--         "The value of vRtrMplsLspAutoBWLastAvgRate indicates the 
--          avegare data rate in the sample interval that ended most
--          recently."
--     ::= { vRtrMplsLspAutoBandwidthEntry 20 }   
-- 
-- vRtrMplsLspAutoBWInheritance   OBJECT-TYPE
--     SYNTAX      Unsigned32
--     MAX-ACCESS  read-write
--     STATUS      current
--     DESCRIPTION
--         "For each writable object in this row that can be configured to
--          inherit its value from the corresponding object in the 
--          vRtrMplsGeneralTable, there is bit within vRtrMplsLspAutoBWInheritance
--          that controls whether to inherit the operational value of the
--          object or use the administratively set value. 
-- 
--          This object is a bit-mask, with the following positions:
-- 
--          vRtrMplsLspAutoBWAdjMultiplier          0x1
--          vRtrMplsLspAutoBWSampMultiplier         0x2
-- 
--          When the bit for an object is set to one, then the object's 
--          administrative and operational value are whatever the DEFVAL 
--          or most recently SET value is.
--          
--          When the bit for an object is set to zero, then the object's 
--          administrative and operational value are inherited from the 
--          corresponding object in vRtrMplsGeneralTable."
--     DEFVAL { 0 }
--     ::= { vRtrMplsLspAutoBandwidthEntry 21 }
-- 
-- vRtrMplsLspAutoBWCurrentBW   OBJECT-TYPE
--     SYNTAX      Unsigned32
--     UNITS       "Mbps"
--     MAX-ACCESS  read-only
--     STATUS      current
--     DESCRIPTION
--         "The value of vRtrMplsLspAutoBWCurrentBW indicates the 
--          current bandwidth reserved along the primary path."
--     ::= { vRtrMplsLspAutoBandwidthEntry 22 }   
-- 
-- vRtrMplsLspAutoBWAdjTime   OBJECT-TYPE
--     SYNTAX      Unsigned32
--     UNITS       "minutes" 
--     MAX-ACCESS  read-only
--     STATUS      current
--     DESCRIPTION
--         "The value of vRtrMplsLspAutoBWAdjTime indicates the 
--          adjust multipler times the collection interval."
--     ::= { vRtrMplsLspAutoBandwidthEntry 23 }   
-- 
-- vRtrMplsLspAutoBWOvrFlwCount   OBJECT-TYPE
--     SYNTAX      Unsigned32
--     MAX-ACCESS  read-only
--     STATUS      current
--     DESCRIPTION
--         "The value of vRtrMplsLspAutoBWOvrFlwCount indicates the 
--          number of overflow samples since the last reset."
--     ::= { vRtrMplsLspAutoBandwidthEntry 24 }   
-- 
-- vRtrMplsLspAutoBWSampCount   OBJECT-TYPE
--     SYNTAX      Unsigned32
--     MAX-ACCESS  read-only
--     STATUS      current
--     DESCRIPTION
--         "The value of vRtrMplsLspAutoBWSampCount indicates the 
--          count in the sample interval."
--     ::= { vRtrMplsLspAutoBandwidthEntry 25 }   
-- 
-- vRtrMplsLspAutoBWAdjCount   OBJECT-TYPE
--     SYNTAX      Unsigned32
--     MAX-ACCESS  read-only
--     STATUS      current
--     DESCRIPTION
--         "The value of vRtrMplsLspAutoBWAdjCount indicates the 
--          count in the adjust interval."
--     ::= { vRtrMplsLspAutoBandwidthEntry 26 }   
-- 
-- vRtrMplsLspAutoBWOperState   OBJECT-TYPE
--     SYNTAX      TmnxEnabledDisabled
--     MAX-ACCESS  read-only
--     STATUS      current
--     DESCRIPTION
--         "The value of vRtrMplsLspAutoBWOperState indicates the 
--          opertional status for the LSP."
--     ::= { vRtrMplsLspAutoBandwidthEntry 27 }   
-- 
-- vRtrMplsLspAutoBWSampInterval   OBJECT-TYPE
--     SYNTAX      Unsigned32
--     MAX-ACCESS  read-only
--     STATUS      current
--     DESCRIPTION
--         "The value of vRtrMplsLspAutoBWSampInterval indicates the 
--          number of sample intervals."
--     ::= { vRtrMplsLspAutoBandwidthEntry 28 }   

--
--  The Virtual Router MPLS LSP Path Operational Status Table
--
--  Augmentation of the vRtrMplsLspPathTable.
--  Use of AUGMENTS clause implies a one-to-one dependent relationship 
--  between the base table, vRtrMplsLspPathTable, and the augmenting table, 
--  vRtrMplsLspPathOperTable. This in effect extends the vRtrMplsLspPathTable
--  with additional columns.  
--  Creation (or deletion) of a row in the vRtrMplsLspPathTable results in 
--  the same fate for the row in the vRtrMplsLspPathOperTable.
--

--vRtrMplsLspPathOperTable    OBJECT-TYPE
--    SYNTAX      SEQUENCE OF VRtrMplsLspPathOperEntry
--    MAX-ACCESS  not-accessible
--    STATUS      current
--    DESCRIPTION
--        "The vRtrMplsLspPathOperTable has an entry for an association 
--         between a Labeled Switch Path (LSP) in the vRtrMplsLspTable 
--         and a path (or tunnel) entry in the mplsTunnelTable."
--    ::= { tnMplsObjs 44 }
--
--vRtrMplsLspPathOperEntry    OBJECT-TYPE
--    SYNTAX      VRtrMplsLspPathOperEntry
--    MAX-ACCESS  not-accessible
--    STATUS      current
--    DESCRIPTION
--        "Each row entry represents an operational status for an 
--         association between a Labeled Switch Path (LSP) in the
--         vRtrMplsLspTable and a path (or tunnel) entry in the 
--         mplsTunnelTable. 
--
--         Entries cannot be created and deleted via SNMP SET operations.
--         
--         A row entry will have valid operational status info when
--         vRtrMplsLspPathOperState is set to inService."
--    AUGMENTS { vRtrMplsLspPathEntry }
--    ::= { vRtrMplsLspPathOperTable 1 }
--
--VRtrMplsLspPathOperEntry ::= SEQUENCE {
--    vRtrMplsLspPathOperSetupPriority        Unsigned32,
--    vRtrMplsLspPathOperHoldPriority         Unsigned32,
--    vRtrMplsLspPathOperRecord               INTEGER,
--    vRtrMplsLspPathOperRecordLabel          INTEGER,
--    vRtrMplsLspPathOperHopLimit             Unsigned32,
--    vRtrMplsLspPathOperAdminGrpIncl         Unsigned32,
--    vRtrMplsLspPathOperAdminGrExcld         Unsigned32,
--    vRtrMplsLspPathOperCspf                 TruthValue,
--    vRtrMplsLspPathOperCspfToFrstLs         TruthValue,
--    vRtrMplsLspPathOperLeastFill            TruthValue,
--    vRtrMplsLspPathOperRsvpAdspec           TruthValue,
--    vRtrMplsLspPathOperFRNodeProtect        TruthValue,
--    vRtrMplsLspPathOperPropAdminGrp         TruthValue,
--    vRtrMplsLspPathOperFRHopLimit           Unsigned32
--}
--
--vRtrMplsLspPathOperSetupPriority    OBJECT-TYPE
--    SYNTAX      Unsigned32 (0..7)
--    MAX-ACCESS  read-only
--    STATUS      current
--    DESCRIPTION
--        "The value of vRtrMplsLspPathOperSetupPriority specifies the
--         setup priority used by the operational LSP path.
--
--         When make-before-break functionality for the LSP is enabled and 
--         if the path setup priority is changed, the resources allocated 
--         to the existing LSP paths will not be released until a new path
--         with the new setup priority settings has been established. While
--         a new path is being signaled, the administrative value and the
--         operational values of the path setup priority may differ. The 
--         value of vRtrMplsLspPathSetupPriority specifies the setup 
--         priority for the new LSP path trying to be established whereas
--         the value of vRtrMplsLspPathOperSetupPriority specifies the 
--         setup priority for the existing LSP path."
--    ::= { vRtrMplsLspPathOperEntry 1 } 
--
--vRtrMplsLspPathOperHoldPriority     OBJECT-TYPE
--    SYNTAX      Unsigned32 (0..7)
--    MAX-ACCESS  read-only
--    STATUS      current
--    DESCRIPTION
--        "The value of vRtrMplsLspPathOperHoldPriority specifies the
--         hold priority used by the operational LSP path.
--
--         When make-before-break functionality for the LSP is enabled and 
--         if the path hold priority is changed, the resources allocated
--         to the existing LSP paths will not be released until a new path
--         with the new hold priority settings has been established. While
--         a new path is being signaled, the administrative value and the
--         operational values of the path hold priority may differ. The 
--         value of vRtrMplsLspPathHoldPriority specifies the hold priority
--         for the new LSP path trying to be established whereas the value
--         of vRtrMplsLspPathOperHoldPriority specifies the hold priority
--         for the existing LSP path."
--    ::= { vRtrMplsLspPathOperEntry 2 } 
--
--vRtrMplsLspPathOperRecord       OBJECT-TYPE
--    SYNTAX      INTEGER {
--                    record (1),
--                    noRecord (2)
--                }
--    MAX-ACCESS  read-only
--    STATUS      current
--    DESCRIPTION
--        "The value of vRtrMplsLspPathOperRecord specifies whether the
--         operational LSP path is recording or not recording all the
--         traversed hops.
--
--         When make-before-break functionality for the LSP is enabled and if the
--         path hops recording setting is changed, the resources allocated to the
--         existing LSP paths will not be released until a new path with the new
--         settings has been established. While a new path is being signaled, the
--         administrative value and the operational values of hops recording
--         setting of the path may differ. The value of vRtrMplsLspPathRecord
--         specifies the hops recording setting for the new LSP path trying to be
--         established whereas the value of vRtrMplsLspPathOperRecord specifies
--         the hops recording setting for the existing LSP path."
--    ::= { vRtrMplsLspPathOperEntry 3 } 
--
--vRtrMplsLspPathOperRecordLabel      OBJECT-TYPE
--    SYNTAX      INTEGER {
--                    record (1),
--                    noRecord (2)
--                }
--    MAX-ACCESS  read-only
--    STATUS      current
--    DESCRIPTION
--        "The value of vRtrMplsLspPathOperRecordLabel specifies whether
--         the currently operational LSP path is recording or not
--         recording the label allocated at each traversed node.
--
--         When make-before-break functionality for the LSP is enabled and 
--         if the path label recording setting is changed, the resources 
--         allocated to the existing LSP paths will not be released until
--         a new path with the new settings has been established. While a 
--         new path is being signaled, the administrative value and the 
--         operational values of label recording setting of the path may 
--         differ. The value of vRtrMplsLspPathRecordLabel specifies the 
--         label recording setting for the new LSP path trying to be 
--         established whereas the value of vRtrMplsLspPathOperRecordLabel
--         specifies the label recording setting for the existing LSP path."
--    ::= { vRtrMplsLspPathOperEntry 4 } 
--
--vRtrMplsLspPathOperHopLimit     OBJECT-TYPE
--    SYNTAX      Unsigned32 (2..255)
--    MAX-ACCESS  read-only
--    STATUS      current
--    DESCRIPTION
--        "The value of vRtrMplsLspPathOperHopLimit specifies the maximum
--         hops limit used by the currently operational LSP path.
--         
--         When make-before-break functionality for the LSP is enabled and if
--         the hop limit is changed at either LSP or LSP path level, the
--         resources allocated to the existing LSP paths will not be released
--         until a new path with the new settings has been established. While
--         a new path is being signaled, the administrative value and the
--         operational values of the path hop limit may differ. The value of
--         either vRtrMplsLspHopLimit or vRtrMplsLspPathHopLimit specifies
--         the hop limit for the new LSP path trying to be established
--         whereas the value of vRtrMplsLspPathOperHopLimit specifies the hop
--         limit for the existing LSP path."
--    ::= { vRtrMplsLspPathOperEntry 5 } 
--
--vRtrMplsLspPathOperAdminGrpIncl    OBJECT-TYPE
--    SYNTAX      Unsigned32
--    MAX-ACCESS  read-only
--    STATUS      current
--    DESCRIPTION
--        "The value of vRtrMplsLspPathOperAdminGrpIncl is a bit-map
--         which specifies a list of admin groups included by the
--         currently operational LSP path.
--
--         When make-before-break functionality for the LSP is enabled and if
--         the list of included admin groups is changed at either LSP or LSP
--         path level, the resources allocated to the existing LSP paths will
--         not be released until a new path with the new settings has been
--         established.  While a new path is being signaled, the
--         administrative value and the operational values of the path may
--         differ. The value of either vRtrMplsLspAdminGroupInclude or
--         vRtrMplsLspPathAdminGroupInclude specifies the include admin groups
--         bit-map for the new LSP path trying to be established whereas the
--         value of vRtrMplsLspPathOperAdminGrpIncl specifies the include admin
--         groups bit-map for the existing LSP path."
--    ::= { vRtrMplsLspPathOperEntry 6 }
--
--vRtrMplsLspPathOperAdminGrExcld    OBJECT-TYPE
--    SYNTAX      Unsigned32
--    MAX-ACCESS  read-only
--    STATUS      current
--    DESCRIPTION
--        "The value of vRtrMplsLspPathOperAdminGrExcld is a bit-map
--         which specifies a list of admin groups excluded by the
--         currently operational LSP path.
--
--         When make-before-break functionality for the LSP is enabled and if the
--         list of excluded admin groups is changed at either LSP or LSP path
--         level, the resources allocated to the existing LSP paths will not be
--         released until a new path with the new settings has been established.
--         While a new path is being signaled, the administrative value and the
--         operational values of the path may differ. The value of either
--         vRtrMplsLspAdminGroupExclude or vRtrMplsLspPathAdminGroupExclude
--         specifies the exclude admin groups bit-map for the new LSP path trying
--         to be established whereas the value of vRtrMplsLspPathOperAdminGrExcld
--         specifies the exclude admin groups bit-map for the existing LSP path."
--    ::= { vRtrMplsLspPathOperEntry 7 }
--
--vRtrMplsLspPathOperCspf     OBJECT-TYPE
--    SYNTAX      TruthValue
--    MAX-ACCESS  read-only
--    STATUS      current
--    DESCRIPTION
--        "The value of vRtrMplsLspPathOperCspf specifies whether the
--         currently operational LSP path has used CSPF computation for
--         constrained-path enabled or disabled.
--
--         When make-before-break functionality for the LSP is enabled and if the
--         LSP CSPF setting is changed, the resources allocated to the existing
--         LSP paths will not be released until a new path with the new settings
--         has been established. While a new path is being signaled, the
--         administrative value and the operational values of the path may
--         differ. The value of vRtrMplsLspCspf specifies the CSPF setting for
--         the new LSP path trying to be established whereas the value of
--         vRtrMplsLspPathOperCspf specifies the CSPF setting for the existing
--         LSP path."
--    ::= { vRtrMplsLspPathOperEntry 8 }
--
--vRtrMplsLspPathOperCspfToFrstLs     OBJECT-TYPE
--    SYNTAX      TruthValue
--    MAX-ACCESS  read-only
--    STATUS      current
--    DESCRIPTION
--        "The value of vRtrMplsLspPathOperCspfToFrstLs specifies whether
--         the currently operational LSP path had CSPF to first loose hop
--         enabled or disabled.
--
--         When make-before-break functionality for the LSP is enabled
--         and if the LSP CSPF to First Loose Hop setting is changed, 
--         the resources allocated to the existing LSP paths will not be 
--         released until a new path with the new settings has been 
--         established. While a new path is being signaled, the administrative
--         value and the operational values of the path may differ. The 
--         value of vRtrMplsLspCspfToFirstLoose specifies the CSPF to First
--         Loose Hop setting for the new LSP path trying to be established
--         whereas the value of vRtrMplsLspPathOperCspfToFrstLs specifies
--         the CSPF to First Loose Hop setting for the existing LSP path."
--    ::= { vRtrMplsLspPathOperEntry 9 } 
--
--vRtrMplsLspPathOperLeastFill    OBJECT-TYPE
--    SYNTAX      TruthValue
--    MAX-ACCESS  read-only
--    STATUS      current
--    DESCRIPTION
--        "The value of vRtrMplsLspPathOperLeastFill specifies whether
--         the currently operational LSP path was computed with the least-fill
--         path selection method.
--
--         When make-before-break functionality for the LSP is enabled and if the
--         LSP least-fill setting is changed, the resources allocated to the
--         existing LSP paths will not be released until a new path with the new
--         settings has been established. While a new path is being signaled, the
--         administrative value and the operational values of the path may
--         differ. The value of vRtrMplsLspLeastFill specifies the least-fill
--         setting for the new LSP path trying to be established whereas the
--         value of vRtrMplsLspPathOperLeastFill specifies the least-fill
--         setting for the existing LSP path."
--    ::= { vRtrMplsLspPathOperEntry 10 }
--
--vRtrMplsLspPathOperRsvpAdspec       OBJECT-TYPE
--    SYNTAX      TruthValue
--    MAX-ACCESS  read-only
--    STATUS      current
--    DESCRIPTION
--        "The value of vRtrMplsLspPathOperRsvpAdspec specifies whether
--         the currently operational LSP path has ADSPEC object included
--         in RSVP messages or not.
--
--         When make-before-break functionality for the LSP is enabled and if the
--         LSP adspec setting is changed, the resources allocated to the existing
--         LSP paths will not be released until a new path with the new settings
--         has been established. While a new path is being signaled, the
--         administrative value and the operational values of the path may
--         differ. The value of vRtrMplsLspRsvpAdspec specifies the adspec
--         setting for the new LSP path trying to be established whereas the
--         value of vRtrMplsLspPathOperRsvpAdspec specifies the adspec setting
--         for the existing LSP path."
--         
--    ::= { vRtrMplsLspPathOperEntry 11 }
--
--vRtrMplsLspPathOperFRNodeProtect    OBJECT-TYPE
--    SYNTAX      TruthValue
--    MAX-ACCESS  read-only
--    STATUS      current
--    DESCRIPTION
--        "The value of vRtrMplsLspPathOperFRNodeProtect specifies
--         whether the currently operational LSP path has node protection
--         enabled or disabled.
--
--         When make-before-break functionality for the LSP is enabled and if the
--         LSP node protection setting is changed, the resources allocated to the
--         existing LSP paths will not be released until a new path with the new
--         settings has been established. While a new path is being signaled, the
--         administrative value and the operational values of the path may
--         differ. The value of vRtrMplsLspFRNodeProtect specifies the node
--         protection setting for the new LSP path trying to be established
--         whereas the value of vRtrMplsLspPathOperFRNodeProtect specifies the
--         node protection setting for the existing LSP path."
--    ::= { vRtrMplsLspPathOperEntry 12 }
--
--vRtrMplsLspPathOperPropAdminGrp       OBJECT-TYPE
--    SYNTAX      TruthValue
--    MAX-ACCESS  read-only
--    STATUS      current
--    DESCRIPTION
--        "The value of vRtrMplsLspPathOperPropAdminGrp specifies
--         whether the currently operational LSP path has propagation
--         admin-groups enabled or disabled.
--
--         When make-before-break functionality for the LSP is enabled and if the
--         LSP propagate admin groups setting is changed, the resources allocated
--         to the existing LSP paths will not be released until a new path with
--         the new settings has been established. While a new path is being
--         signaled, the administrative value and the operational values of the
--         path may differ. The value of vRtrMplsLspPropAdminGroup specifies the
--         propagate admin groups setting for the new LSP path trying to be
--         established whereas the value of vRtrMplsLspPathOperPropAdminGrp
--         specifies the propagate admin groups setting for the existing LSP
--         path."
--    ::= { vRtrMplsLspPathOperEntry 13 }
--
--vRtrMplsLspPathOperFRHopLimit   OBJECT-TYPE
--    SYNTAX      Unsigned32 (0..255)
--    MAX-ACCESS  read-only
--    STATUS      current
--    DESCRIPTION
--        "The value of vRtrMplsLspPathOperFRHopLimit indicates the total number
--         of hops to be used by detour LSP before merging to currently
--         operational LSP path.
--
--         When make-before-break functionality for the LSP is enabled and if the
--         LSP FR Hop Limit setting is changed, the resources allocated
--         to the existing LSP paths will not be released until a new path with
--         the new settings has been established. While a new path is being
--         signaled, the administrative value and the operational values of the
--         path may differ. The value of vRtrMplsLspFRHopLimit specifies the
--         FR Hop Limit setting for the new LSP path trying to be
--         established whereas the value of vRtrMplsLspPathOperFRHopLimit
--         specifies the FR Hop Limit setting for the existing LSP
--         path."
--    ::= { vRtrMplsLspPathOperEntry 14 }


--
--
-- Mpls Label Information
--

-- For PSS 1830, the attributes vRtrMplsLabelMaxStaticLspLabels and 
-- vRtrMplsLabelMaxStaticSvcLabels have been moved into a MPLS
-- System Table.
 
vRtrMplsSystemConfigTable    OBJECT-TYPE
    SYNTAX      SEQUENCE OF VRtrMplsSystemConfigEntry
    MAX-ACCESS  not-accessible
    STATUS      current
    DESCRIPTION
        "The vRtrMplsSystemConfigTable contains system level entities
         required for MPLS."
    ::= { tnMplsObjs 45 }

vRtrMplsSystemConfigEntry    OBJECT-TYPE
    SYNTAX      VRtrMplsSystemConfigEntry
    MAX-ACCESS  not-accessible
    STATUS      current
    DESCRIPTION
        "Each row entry in the vRtrMplsSystemConfigTable  represents 
         system level entities required for MPLS on a virtual router
         basis."
         
    INDEX { tnSysSwitchId, vRtrID } 
    ::= { vRtrMplsSystemConfigTable 1 }

VRtrMplsSystemConfigEntry ::= SEQUENCE {
     vRtrMplsLabelMaxStaticLspLabels    Unsigned32,
     vRtrMplsLabelMaxStaticSvcLabels    Unsigned32 
}

vRtrMplsLabelMaxStaticLspLabels     OBJECT-TYPE
    SYNTAX      Unsigned32 (0..262112)
    MAX-ACCESS  read-write
    STATUS      current
    DESCRIPTION
        "The value of vRtrMplsLabelMaxStaticLspLabels specifies the maximum
         number of Static LSP labels available on a virtual router.
         
         vRtrMplsLabelMaxStaticLspLabels must be set along with 
         vRtrMplsLabelMaxStaticSvcLabels. The total of both values 
         should equal the maximum value allowed of 131040 or 262112 depending
         on the system.
        
         The maximum value of vRtrMplsLabelMaxStaticLspLabels value for 
         most systems is 113040 labels (128 * 1024 less 32 reserved labels).

         The maximum value of vRtrMplsLabelMaxStaticLspLabels value for
         chassis mode D systems is 262112 labels (256 * 1024 less 32 reserved
         labels)."
    DEFVAL { 2016 }
    ::= { vRtrMplsSystemConfigEntry 1 }

vRtrMplsLabelMaxStaticSvcLabels     OBJECT-TYPE
    SYNTAX      Unsigned32 (0..262112)
    MAX-ACCESS  read-write
    STATUS      current
    DESCRIPTION
        "The value of vRtrMplsLabelMaxStaticSvcLabels specifies the maximum
         number of Static SVC labels available on a virtual router.
       
         vRtrMplsLabelMaxStaticSvcLabels must be set along with
         vRtrMplsLabelMaxStaticLspLabels. The total of both values 
         should equal the maximum value allowed of 113040 or 262112 depending
         on the system.

         The maximum value of vRtrMplsLabelMaxStaticLspLabels value for 
         most systems is 113040 labels (128 * 1024 less 32 reserved labels).

         The maximum value of vRtrMplsLabelMaxStaticLspLabels value for
         chassis mode D systems is 262112 labels (256 * 1024 less 32 reserved
         labels)."
    DEFVAL { 16384 }
    ::= { vRtrMplsSystemConfigEntry 2 }

--------------------------------------------------------------------------------------------------
-- Introduce the new MIB table vRtrMplsLspNameTable to more efficiently map an LSP name to the LSP ID.
--------------------------------------------------------------------------------------------------
--
-- The Virtual Router MPLS Labeled Switch Path (LSP) Name to LSP ID Mapping Table
-- Table
--

vRtrMplsLspNameTable OBJECT-TYPE
    SYNTAX SEQUENCE OF VRtrMplsLspNameEntry
    MAX-ACCESS not-accessible
    STATUS current
    DESCRIPTION
        "This is a read-only table, each row of which represents a one to one
        equivalence between an Labeled Switch Path name (vRtrMplsLspName) and
        its corresponding index in the vRtrMplsLspTable (vRtrMplsLspIndex)."
    ::= { tnMplsObjs 46 }

vRtrMplsLspNameEntry OBJECT-TYPE
    SYNTAX VRtrMplsLspNameEntry
    MAX-ACCESS not-accessible
    STATUS current
    DESCRIPTION
        "Each row entry in the vRtrMplsLspNameTable corresponds to a row
        in the vRtrMplsLspTable. When an entry is created or deleted in the
        vRtrMplsLspTable, a corresponding entry is created or deleted in this
        table."
    INDEX { tnSysSwitchId, vRtrID, IMPLIED vRtrMplsLspName }
    ::= { vRtrMplsLspNameTable 1 }

VRtrMplsLspNameEntry ::= SEQUENCE
    { vRtrMplsLspNameIndex TmnxVRtrMplsLspID }

vRtrMplsLspNameIndex OBJECT-TYPE
    SYNTAX TmnxVRtrMplsLspID
    MAX-ACCESS read-only
    STATUS current
    DESCRIPTION
        "The value of vRtrMplsLspNameIndex gives the value of vRtrMplsLspIndex
        for a row in the vRtrMplsLspTable. This row corresponds to the
        Labeled Switch Path which has the administrative name as
        vRtrMplsLspName. Every vRtrMplsLspName is unique within a virtual
        router instance."
    ::= { vRtrMplsLspNameEntry 1 } 

--
--
-- Notification Information and Compliance Information deleted from Original MIB.
--

  vRtrMplsLspScalar1 OBJECT-TYPE
      SYNTAX      Unsigned32
      MAX-ACCESS  read-only
      STATUS      current
      DESCRIPTION
          "A dummy scalar that satisfies a SNMP get request quickly.Otherwise,
      it has to traverse the remaining MIB to get to the next applicable
           item."
      ::= { tnMplsObjs 101 }

  vRtrMplsLspScalar2 OBJECT-TYPE
      SYNTAX      Unsigned32
      MAX-ACCESS  read-only
      STATUS      current
      DESCRIPTION
          ""
      ::= { tnMplsObjs 102 }

END
