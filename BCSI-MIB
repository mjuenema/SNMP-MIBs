BCSI-MIB DEFINITIONS ::= BEGIN

IMPORTS MODULE-IDENTITY, enterprises FROM SNMPv2-SMI;

bcsi MODULE-IDENTITY
        LAST-UPDATED    "201010040000Z"
        ORGANIZATION    "Blue Coat Systems, Inc."
        CONTACT-INFO    "support.services@bluecoat.com
                         http://www.bluecoat.com"
        DESCRIPTION     "The root MIB module for Blue Coat Systems."
        REVISION        "201010040000Z"
        DESCRIPTION     "Fixed incorrect enterprise number."
        REVISION        "200910040000Z"
        DESCRIPTION     "Initial revision of this MIB."
        ::= { enterprises 14501 }

-- namespace for Blue Coat Systems CacheFlow appliances
cacheflow   	OBJECT IDENTIFIER ::= { bcsi 3 }

cfloProducts 	OBJECT IDENTIFIER ::= { cacheflow 1 }
cf5000		 	OBJECT IDENTIFIER ::= { cfloProducts 1 }

END  -- bcsi
