-- *****************************************************************************
-- Juniper-PPP-PROFILE-MIB
--
-- Juniper Networks Enterprise MIB
--   PPP Profile MIB
--
-- Copyright (c) 2001, 2002 Unisphere Networks, Inc.
-- Copyright (c) 2002, 2003 Juniper Networks, Inc.
--   All Rights Reserved.
-- *****************************************************************************

Juniper-PPP-PROFILE-MIB  DEFINITIONS ::= BEGIN

IMPORTS
    MODULE-IDENTITY, OBJECT-TYPE, Integer32, Unsigned32
        FROM SNMPv2-SMI
    MODULE-COMPLIANCE, OBJECT-GROUP
        FROM SNMPv2-CONF
    juniMibs
        FROM Juniper-MIBs
    JuniEnable, JuniSetMap, JuniName
        FROM Juniper-TC
    JuniPppAuthentication
        FROM Juniper-PPP-MIB;

juniPppProfileMIB  MODULE-IDENTITY
    LAST-UPDATED "200311032110Z"  -- 03-Nov-03 04:10 PM EST
    ORGANIZATION "Juniper Networks, Inc."
    CONTACT-INFO
        "       Juniper Networks, Inc.
        Postal: 10 Technology Park Drive
                Westford, MA  01886-3146
                USA
        Tel:    +1 978 589 5800
        Email:  mib@Juniper.net"
    DESCRIPTION
        "The Point-to-Point Protocol (PPP) Profile MIB for the Juniper Netowrks
        enterprise.  This MIB provides configuration parameters that extend the
        tables found in the Juniper-PROFILE-MIB to support profiles for PPP
        interfaces."
    -- Revision History
    REVISION    "200311032110Z"  -- 03-Nov-03 04:10 PM EST  - JUNOSe 5.3
    DESCRIPTION
        "Added support for MLPPP fragmentation and reassembly."
    REVISION    "200309291858Z"  -- 29-Sep-03 02:58 PM EDT  - JUNOSe 5.2
    DESCRIPTION
        "Increased the maximum range of the PPP Profile LCP keep-alive time."
    REVISION    "200303112159Z"  -- 11-Mar-03 04:59 PM EST  - JUNOSe 5.1
    DESCRIPTION
        "Added juniPppProfileInitiateIp and juniPppProfileInitiateIpv6."
    REVISION    "200209162144Z"  -- 16-Sep-02 05:44 PM EDT  - JUNOSe 5.0
    DESCRIPTION
        "Replaced Unisphere names with Juniper names."
    REVISION    "200209032238Z"  -- 03-Sep-02 06:38 PM EDT  - JUNOSe 4.1
    DESCRIPTION
        "Added juniPppProfileAaaProfile."
    REVISION    "200201251400Z"  -- 25-Jan-02 09:00 AM EST  - JUNOSe 4.0
    DESCRIPTION
        "Added juniPppProfileAuthenticatorVirtualRouter."
    REVISION    "200201161758Z"  -- 16-Jan-02 12:58 PM EST  - JUNOSe 3.4
    DESCRIPTION
        "Added support for negotiation of the IPCP option netmask."
    REVISION    "200201081943Z"  -- 08-Jan-02 02:43 PM EST  - JUNOSe 3.3
    DESCRIPTION
        "Added support for dynamic multilink PPP (MLPPP) interfaces."
    REVISION    "200110021241Z"  -- 02-Oct-01 08:41 AM EDT  - JUNOSe 3.0
    DESCRIPTION
        "Initial version of this MIB module."
    ::= { juniMibs 45 }


-- +++++++++++++++++++++++++++++++++++++++++++++++++++++++++++++++++++++++++++++
-- Managed objects
-- +++++++++++++++++++++++++++++++++++++++++++++++++++++++++++++++++++++++++++++
juniPppProfileObjects     OBJECT IDENTIFIER ::= { juniPppProfileMIB 1 }
juniPppProfile            OBJECT IDENTIFIER ::= { juniPppProfileObjects 1 }

--
-- This MIB defines configuration profile structure for PPP interfaces.
-- The creation/deletion of profiles and mapping of profile names to profile
-- indices is coordinated in the Juniper-PROFILE-MIB.
--
--
-- The PPP Profile Table
--
juniPppProfileTable  OBJECT-TYPE
    SYNTAX      SEQUENCE OF JuniPppProfileEntry
    MAX-ACCESS  not-accessible
    STATUS      current
    DESCRIPTION
        "This table contains profiles for configuring PPP interfaces.

        Entries in this table are created/deleted as a side-effect of
        corresponding operations to the juniProfileNameTable in the
        Juniper-PROFILE-MIB."
    ::= { juniPppProfile 1 }

juniPppProfileEntry  OBJECT-TYPE
    SYNTAX      JuniPppProfileEntry
    MAX-ACCESS  not-accessible
    STATUS      current
    DESCRIPTION
        "A profile describing configuration of a PPP interface."
    INDEX     { juniPppProfileId }
    ::= { juniPppProfileTable 1 }

JuniPppProfileEntry ::= SEQUENCE {
    juniPppProfileId                           Unsigned32,
    juniPppProfileSetMap                       JuniSetMap,
    juniPppProfileLcpMagicNumber               INTEGER,
    juniPppProfileLcpKeepalive                 Integer32,
    juniPppProfileLcpAuthentication            JuniPppAuthentication,
    juniPppProfileIpPeerDnsPriority            JuniEnable,
    juniPppProfileIpPeerWinsPriority           JuniEnable,
    juniPppProfileLcpInitialMRU                Integer32,
    juniPppProfilePacketLog                    JuniEnable,
    juniPppProfileStateLog                     JuniEnable,
    juniPppProfileChapMinChallengeLength       Integer32,
    juniPppProfileChapMaxChallengeLength       Integer32,
    juniPppProfilePassiveMode                  JuniEnable,
    juniPppProfileMlppp                        JuniEnable,
    juniPppProfileIpcpNetmask                  JuniEnable,
    juniPppProfileAuthenticatorVirtualRouter   JuniName,
    juniPppProfileAaaProfile                   JuniName,
    juniPppProfileInitiateIp                   JuniEnable,
    juniPppProfileInitiateIpv6                 JuniEnable,
    juniPppProfileFragmentation                JuniEnable,
    juniPppProfileReassembly                   JuniEnable,
    juniPppProfileMaxReceiveReconstructedUnit  Integer32,
    juniPppProfileFragmentSize                 Integer32 }

juniPppProfileId  OBJECT-TYPE
    SYNTAX      Unsigned32
    MAX-ACCESS  not-accessible
    STATUS      current
    DESCRIPTION
        "The integer identifier associated with this profile.  A value for this
        identifier is determined by locating or creating a profile name in the
        Juniper-PROFILE-MIB.juniProfileNameTable."
    ::= { juniPppProfileEntry 1 }

juniPppProfileSetMap  OBJECT-TYPE
    SYNTAX      JuniSetMap
    MAX-ACCESS  read-write
    STATUS      current
    DESCRIPTION
        "A bitmap representing which objects in this entry have been explicitly
        configured.  See the definition of the JuniSetMap TEXTUAL-CONVENTION for
        details of use.

        The INDEX object(s) and this object are excluded from representation
        (i.e. their bits are never set).

        When a SET request does not explicitly configure JuniSetMap, bits in
        JuniSetMap are set as a side-effect of configuring other profile
        attributes in the same entry.

        If, however, a SET request explicitly configures JuniSetMap, the
        explicitly configured value overrides 1) any previous bit settings, and
        2) any simultaneous 'side-effect' settings that would otherwise occur.

        Once set, bits can only be cleared by explicitly configuring
        JuniSetMap."
    ::= { juniPppProfileEntry 2 }

juniPppProfileLcpMagicNumber  OBJECT-TYPE
    SYNTAX      INTEGER {
                    false(1),
                    true(2) }
    MAX-ACCESS  read-write
    STATUS      current
    DESCRIPTION
        "If true(2) then the local node will attempt to perform Magic Number
        negotiation with the remote node.  If false(1) then this negotiation is
        not performed.  In any event, the local node will comply with any magic
        number negotiations attempted by the remote node, per the PPP
        specification."
    DEFVAL    { false }
    ::= { juniPppProfileEntry 3 }

juniPppProfileLcpKeepalive  OBJECT-TYPE
    SYNTAX      Integer32 (0|30..64800)
    UNITS       "seconds"
    MAX-ACCESS  read-write
    STATUS      current
    DESCRIPTION
        "Keepalive interval in seconds.  A value of zero disables keepalive.
        Keepalive is performed using LCP Echo."
    DEFVAL    { 30 }
    ::= { juniPppProfileEntry 4 }

juniPppProfileLcpAuthentication  OBJECT-TYPE
    SYNTAX      JuniPppAuthentication
    MAX-ACCESS  read-write
    STATUS      current
    DESCRIPTION
        "Specifies the type(s) of authentication, if any, to be negotiated with
        the peer:
          none      No authentication is negotiated.
          pap       PAP negotiation only.
          chap      CHAP negotiation only.
          papChap   PAP negotiation is attempted first; if fails, attempt CHAP.
          chapPap   CHAP negotiation is attempted first; if fails, attempt PAP.

        Setting this object to none will set the
        juniPppProfileAuthenticatorVirtualRouter object to an empty string."
    DEFVAL    { none }
    ::= { juniPppProfileEntry 5 }

juniPppProfileIpPeerDnsPriority  OBJECT-TYPE
    SYNTAX      JuniEnable
    MAX-ACCESS  read-write
    STATUS      current
    DESCRIPTION
        "When enabled, allows peer's DNS address to prevail in the event of a
        negotiation conflict; when disabled, the local PPP interface's DNS
        address prevails."
    DEFVAL    { disable }
    ::= { juniPppProfileEntry 6 }

juniPppProfileIpPeerWinsPriority  OBJECT-TYPE
    SYNTAX      JuniEnable
    MAX-ACCESS  read-write
    STATUS      current
    DESCRIPTION
        "When enabled, allows peer's WINS address to prevail in the event of a
        negotiation conflict; when disabled, the local PPP interface's WINS
        address prevails."
    DEFVAL    { disable }
    ::= { juniPppProfileEntry 7 }

juniPppProfileLcpInitialMRU  OBJECT-TYPE
    SYNTAX      Integer32 (1|64..65535)
    MAX-ACCESS  read-write
    STATUS      current
    DESCRIPTION
        "The initial Maximum Receive Unit (MRU) that the local PPP entity will
        advertise to the remote entity.

        If the value of this variable is 1 then the local PPP entity will
        advertise an MRU value determined by its underlying media interface."
    DEFVAL    { 1 }
    ::= { juniPppProfileEntry 8 }

juniPppProfilePacketLog  OBJECT-TYPE
    SYNTAX      JuniEnable
    MAX-ACCESS  read-write
    STATUS      current
    DESCRIPTION
        "When enabled, allows packet logging on dynamic PPP interfaces."
    DEFVAL    { disable }
    ::= { juniPppProfileEntry 9 }

juniPppProfileStateLog  OBJECT-TYPE
    SYNTAX      JuniEnable
    MAX-ACCESS  read-write
    STATUS      current
    DESCRIPTION
        "When enabled, allows state machine logging on dynamic PPP interfaces."
    DEFVAL    { disable }
    ::= { juniPppProfileEntry 10 }

juniPppProfileChapMinChallengeLength  OBJECT-TYPE
    SYNTAX      Integer32 (8..63)
    MAX-ACCESS  read-write
    STATUS      current
    DESCRIPTION
        "Minimum value of the CHAP authenticator challenge length value.  This
        value is never allowed to be set to a value greater than
        juniPppProfileChapMaxChallengeLength."
    DEFVAL    { 16 }
    ::= { juniPppProfileEntry 11 }

juniPppProfileChapMaxChallengeLength  OBJECT-TYPE
    SYNTAX      Integer32 (8..63)
    MAX-ACCESS  read-write
    STATUS      current
    DESCRIPTION
        "Maximum value of the CHAP authenticator challenge length value. This
        value is never allowed to be set to a value less than
        juniPppLinkConfigChapMinChallengeLength."
    DEFVAL    { 32 }
    ::= { juniPppProfileEntry 12 }

juniPppProfilePassiveMode  OBJECT-TYPE
    SYNTAX      JuniEnable
    MAX-ACCESS  read-write
    STATUS      current
    DESCRIPTION
        "When enabled, LCP state machine is forced into passive mode on lower
        layer UP message.  It adds compatibility with slow and buggy clients."
    DEFVAL    { disable }
    ::= { juniPppProfileEntry 13 }

juniPppProfileMlppp  OBJECT-TYPE
    SYNTAX      JuniEnable
    MAX-ACCESS  read-write
    STATUS      current
    DESCRIPTION
        "Enables the creation of dynamic multi-link PPP interfaces."
    DEFVAL    { disable }
    ::= { juniPppProfileEntry 14 }

juniPppProfileIpcpNetmask  OBJECT-TYPE
    SYNTAX      JuniEnable
    MAX-ACCESS  read-write
    STATUS      current
    DESCRIPTION
        "Enables the negotiation of the IPCP option netmask (0x90) during IPCP
        negotiation."
    DEFVAL { disable }
    ::= { juniPppProfileEntry 15 }

juniPppProfileAuthenticatorVirtualRouter  OBJECT-TYPE
    SYNTAX      JuniName
    MAX-ACCESS  read-write
    STATUS      current
    DESCRIPTION
        "The name of the virtual router (Juniper-ROUTER-MIB.juniRouterName) to
        be used for authentication on the PPP interface.  Setting this object
        statically binds the authenticating virtual router with the PPP
        interface.  If this object is not explicitly set or it is set to null
        string, then this object is ignored and the virtual router used for
        authentication is determined by other means.  On a Set operation, if the
        value of this object is not null and does not correspond to an existing
        virtual router, then an inconsistentValue error is returned.

        Setting this object to non null string returns inconsistentValue value
        error if juniPppProfileConfigAuthentication object is none or not
        configured."
    ::= { juniPppProfileEntry 16 }

juniPppProfileAaaProfile  OBJECT-TYPE
    SYNTAX      JuniName
    MAX-ACCESS  read-write
    STATUS      current
    DESCRIPTION
        "The name of the AAA profile to be used for authentication on the PPP
        interface.  Setting this object statically binds the aaa profile with
        the PPP interface.  If this object is not explicitly set or it is set to
        null string, then this object is ignored.  On a Set operation, if the
        value of this object is not null and does not correspond to an existing
        AAA profile, then an inconsistentValue error is returned."
    ::= { juniPppProfileEntry 17 }

juniPppProfileInitiateIp  OBJECT-TYPE
    SYNTAX      JuniEnable
    MAX-ACCESS  read-write
    STATUS      current
    DESCRIPTION
        "If enabled, PPP interface will initiate negotiation of IPCP;
        if disabled, PPP interface will rely on remote PPP client to
        initiate negotiation of IPCP."
    DEFVAL    { disable }
    ::= { juniPppProfileEntry 18 }

juniPppProfileInitiateIpv6  OBJECT-TYPE
    SYNTAX      JuniEnable
    MAX-ACCESS  read-write
    STATUS      current
    DESCRIPTION
        "If enabled, PPP interface will initiate negotiation of IPv6CP;
        if disabled, PPP interface will rely on remote PPP client to
        initiate negotiation of IPv6CP."
    DEFVAL    { disable }
    ::= { juniPppProfileEntry 19 }

juniPppProfileFragmentation  OBJECT-TYPE
    SYNTAX      JuniEnable
    MAX-ACCESS  read-write
    STATUS      current
    DESCRIPTION
        "Enables MLPPP fragmentation."
    DEFVAL    { disable }
    ::= { juniPppProfileEntry 20 }

juniPppProfileReassembly  OBJECT-TYPE
    SYNTAX      JuniEnable
    MAX-ACCESS  read-write
    STATUS      current
    DESCRIPTION
        "Enables MLPPP reassembly."
    DEFVAL    { disable }
    ::= { juniPppProfileEntry 21 }

juniPppProfileMaxReceiveReconstructedUnit  OBJECT-TYPE
    SYNTAX      Integer32 (1|64..65535)
    MAX-ACCESS  read-write
    STATUS      current
    DESCRIPTION
        "The Maximum Received Reconstructed Unit (MRRU) that the local PPP
        entity will advertise to the remote entity.  If the value of this
        variable is 1, then the MRRU is set to the local MRU value."
    DEFVAL    { 1 }
    ::= { juniPppProfileEntry 22 }

juniPppProfileFragmentSize  OBJECT-TYPE
    SYNTAX      Integer32 (1|128..65535)
    MAX-ACCESS  read-write
    STATUS      current
    DESCRIPTION
        "The size of fragments transmitted by the local PPP entity.  If the
        value of this variable is 1, then the fragment size is set to the link's
        MTU value."
    DEFVAL    { 1 }
    ::= { juniPppProfileEntry 23 }


-- +++++++++++++++++++++++++++++++++++++++++++++++++++++++++++++++++++++++++++++
-- Notifications
-- +++++++++++++++++++++++++++++++++++++++++++++++++++++++++++++++++++++++++++++
-- No notifications are defined in this MIB.


-- +++++++++++++++++++++++++++++++++++++++++++++++++++++++++++++++++++++++++++++
-- Conformance information
-- +++++++++++++++++++++++++++++++++++++++++++++++++++++++++++++++++++++++++++++
juniPppProfileConformance OBJECT IDENTIFIER ::= { juniPppProfileMIB 4 }
juniPppProfileCompliances OBJECT IDENTIFIER ::= { juniPppProfileConformance 1 }
juniPppProfileGroups      OBJECT IDENTIFIER ::= { juniPppProfileConformance 2 }

--
-- compliance statements
--
juniPppProfileCompliance  MODULE-COMPLIANCE
    STATUS      obsolete
    DESCRIPTION
        "Obsolete compliance statement for entities which implement the Juniper
        PPP Profile MIB.  This statement became obsolete when support was added
        for multi-link PPP interfaces."
    MODULE   -- this module
        MANDATORY-GROUPS {
            juniPppProfileGroup }
    ::= { juniPppProfileCompliances 1 }                            -- JUNOSe 3.0

juniPppProfileCompliance2  MODULE-COMPLIANCE
    STATUS      obsolete
    DESCRIPTION
        "Obsolete compliance statement for entities which implement the Juniper
        PPP Profile MIB.  This statement became obsolete when support was added
        for negotiation of IPCP option netmask."
    MODULE   -- this module
        MANDATORY-GROUPS {
            juniPppProfileGroup2 }
    ::= { juniPppProfileCompliances 2 }                            -- JUNOSe 3.3

juniPppProfileCompliance3  MODULE-COMPLIANCE
    STATUS      obsolete
    DESCRIPTION
        "Obsolete compliance statement for entities which implement the Juniper
        PPP Profile MIB.  This statement became obsolete when the
        juniPppProfileAuthenticatorVirtualRouter object was added."
    MODULE   -- this module
        MANDATORY-GROUPS {
            juniPppProfileGroup3 }
    ::= { juniPppProfileCompliances 3 }                            -- JUNOSe 3.4

juniPppProfileCompliance4  MODULE-COMPLIANCE
    STATUS      obsolete
    DESCRIPTION
        "Obsolete compliance statement for entities which implement the Juniper
        PPP Profile MIB.  This statement became obsolete when the
        juniPppProfileAaaProfile object was added."
    MODULE   -- this module
        MANDATORY-GROUPS {
            juniPppProfileGroup4 }
    ::= { juniPppProfileCompliances 4 }                            -- JUNOSe 4.0

juniPppProfileCompliance5  MODULE-COMPLIANCE
    STATUS      obsolete
    DESCRIPTION
        "Obsolete compliance statement for entities which implement the Juniper
        PPP Profile MIB.  This statement became obsolete when the
        juniPppProfileInitiateIp and juniPppProfileInitiateIpv6 objects were
        added."
    MODULE   -- this module
        MANDATORY-GROUPS {
            juniPppProfileGroup5 }
    ::= { juniPppProfileCompliances 5 }                            -- JUNOSe 4.1

juniPppProfileCompliance6  MODULE-COMPLIANCE
    STATUS      obsolete
    DESCRIPTION
        "Obsolete compliance statement for entities which implement the Juniper
        PPP Profile MIB.  This statement became obsolete when fragmentation and
        reassembly support was added."
    MODULE   -- this module
        MANDATORY-GROUPS {
            juniPppProfileGroup6 }
    ::= { juniPppProfileCompliances 6 }                            -- JUNOSe 5.1

juniPppProfileCompliance7  MODULE-COMPLIANCE
    STATUS      current
    DESCRIPTION
        "The compliance statement for entities which implement the Juniper PPP
        Profile MIB."
    MODULE   -- this module
        MANDATORY-GROUPS {
            juniPppProfileGroup7 }
    ::= { juniPppProfileCompliances 7 }                            -- JUNOSe 5.3


--
-- units of conformance
--
juniPppProfileGroup  OBJECT-GROUP
    OBJECTS {
        juniPppProfileSetMap,
        juniPppProfileLcpMagicNumber,
        juniPppProfileLcpKeepalive,
        juniPppProfileLcpAuthentication,
        juniPppProfileIpPeerDnsPriority,
        juniPppProfileIpPeerWinsPriority,
        juniPppProfileLcpInitialMRU,
        juniPppProfilePacketLog,
        juniPppProfileStateLog,
        juniPppProfileChapMinChallengeLength,
        juniPppProfileChapMaxChallengeLength,
        juniPppProfilePassiveMode }
    STATUS      obsolete
    DESCRIPTION
        "Obsolete collection of objects providing management of profile
        functionality for PPP interfaces in a Juniper product.  This group
        became obsolete when support was added for MLPPP."
    ::= { juniPppProfileGroups 1 }                                 -- JUNOSe 3.0

juniPppProfileGroup2  OBJECT-GROUP
    OBJECTS {
        juniPppProfileSetMap,
        juniPppProfileLcpMagicNumber,
        juniPppProfileLcpKeepalive,
        juniPppProfileLcpAuthentication,
        juniPppProfileIpPeerDnsPriority,
        juniPppProfileIpPeerWinsPriority,
        juniPppProfileLcpInitialMRU,
        juniPppProfilePacketLog,
        juniPppProfileStateLog,
        juniPppProfileChapMinChallengeLength,
        juniPppProfileChapMaxChallengeLength,
        juniPppProfilePassiveMode,
        juniPppProfileMlppp }
    STATUS      obsolete
    DESCRIPTION
        "Obsolete collection of objects providing management of profile
        functionality for PPP interfaces in a Juniper product.  This group
        became obsolete when support was added for negotiation of IPCP option
        netmask."
    ::= { juniPppProfileGroups 2 }                                 -- JUNOSe 3.3

juniPppProfileGroup3  OBJECT-GROUP
    OBJECTS {
        juniPppProfileSetMap,
        juniPppProfileLcpMagicNumber,
        juniPppProfileLcpKeepalive,
        juniPppProfileLcpAuthentication,
        juniPppProfileIpPeerDnsPriority,
        juniPppProfileIpPeerWinsPriority,
        juniPppProfileLcpInitialMRU,
        juniPppProfilePacketLog,
        juniPppProfileStateLog,
        juniPppProfileChapMinChallengeLength,
        juniPppProfileChapMaxChallengeLength,
        juniPppProfilePassiveMode,
        juniPppProfileMlppp,
        juniPppProfileIpcpNetmask }
    STATUS      obsolete
    DESCRIPTION
        "Obsolete collection of objects providing management of profile
        functionality for PPP interfaces in a Juniper product.  This group
        became obsolete when the juniPppProfileAuthenticatorVirtualRouter object
        was added."
    ::= { juniPppProfileGroups 3 }                                 -- JUNOSe 3.4

juniPppProfileGroup4  OBJECT-GROUP
    OBJECTS {
        juniPppProfileSetMap,
        juniPppProfileLcpMagicNumber,
        juniPppProfileLcpKeepalive,
        juniPppProfileLcpAuthentication,
        juniPppProfileIpPeerDnsPriority,
        juniPppProfileIpPeerWinsPriority,
        juniPppProfileLcpInitialMRU,
        juniPppProfilePacketLog,
        juniPppProfileStateLog,
        juniPppProfileChapMinChallengeLength,
        juniPppProfileChapMaxChallengeLength,
        juniPppProfilePassiveMode,
        juniPppProfileMlppp,
        juniPppProfileIpcpNetmask,
        juniPppProfileAuthenticatorVirtualRouter }
    STATUS      obsolete
    DESCRIPTION
        "Obsolete collection of objects providing management of profile
        functionality for PPP interfaces in a Juniper product.  This group
        became obsolete when the juniPppProfileAaaProfile object was added."
    ::= { juniPppProfileGroups 4 }                                 -- JUNOSe 4.0

juniPppProfileGroup5  OBJECT-GROUP
    OBJECTS {
        juniPppProfileSetMap,
        juniPppProfileLcpMagicNumber,
        juniPppProfileLcpKeepalive,
        juniPppProfileLcpAuthentication,
        juniPppProfileIpPeerDnsPriority,
        juniPppProfileIpPeerWinsPriority,
        juniPppProfileLcpInitialMRU,
        juniPppProfilePacketLog,
        juniPppProfileStateLog,
        juniPppProfileChapMinChallengeLength,
        juniPppProfileChapMaxChallengeLength,
        juniPppProfilePassiveMode,
        juniPppProfileMlppp,
        juniPppProfileIpcpNetmask,
        juniPppProfileAuthenticatorVirtualRouter,
        juniPppProfileAaaProfile }
    STATUS      obsolete
    DESCRIPTION
        "Obsolete collection of objects providing management of profile
        functionality for PPP interfaces in a Juniper product.  This group
        became obsolete when the juniPppProfileInitiateIp and
        juniPppProfileInitiateIpv6 objects were added."
    ::= { juniPppProfileGroups 5 }                                 -- JUNOSe 4.1

juniPppProfileGroup6  OBJECT-GROUP
    OBJECTS {
        juniPppProfileSetMap,
        juniPppProfileLcpMagicNumber,
        juniPppProfileLcpKeepalive,
        juniPppProfileLcpAuthentication,
        juniPppProfileIpPeerDnsPriority,
        juniPppProfileIpPeerWinsPriority,
        juniPppProfileLcpInitialMRU,
        juniPppProfilePacketLog,
        juniPppProfileStateLog,
        juniPppProfileChapMinChallengeLength,
        juniPppProfileChapMaxChallengeLength,
        juniPppProfilePassiveMode,
        juniPppProfileMlppp,
        juniPppProfileIpcpNetmask,
        juniPppProfileAuthenticatorVirtualRouter,
        juniPppProfileAaaProfile,
        juniPppProfileInitiateIp,
        juniPppProfileInitiateIpv6 }
    STATUS      obsolete
    DESCRIPTION
        "Obsolete collection of objects providing management of profile
        functionality for PPP interfaces in a Juniper product.  This group
        became obsolete when support was added for fragmentation and
        reassembly."
    ::= { juniPppProfileGroups 6 }                                 -- JUNOSe 5.1

juniPppProfileGroup7  OBJECT-GROUP
    OBJECTS {
        juniPppProfileSetMap,
        juniPppProfileLcpMagicNumber,
        juniPppProfileLcpKeepalive,
        juniPppProfileLcpAuthentication,
        juniPppProfileIpPeerDnsPriority,
        juniPppProfileIpPeerWinsPriority,
        juniPppProfileLcpInitialMRU,
        juniPppProfilePacketLog,
        juniPppProfileStateLog,
        juniPppProfileChapMinChallengeLength,
        juniPppProfileChapMaxChallengeLength,
        juniPppProfilePassiveMode,
        juniPppProfileMlppp,
        juniPppProfileIpcpNetmask,
        juniPppProfileAuthenticatorVirtualRouter,
        juniPppProfileAaaProfile,
        juniPppProfileInitiateIp,
        juniPppProfileInitiateIpv6,
        juniPppProfileFragmentation,
        juniPppProfileReassembly,
        juniPppProfileMaxReceiveReconstructedUnit,
        juniPppProfileFragmentSize }
    STATUS      current
    DESCRIPTION
        "A collection of objects providing management of profile functionality
        for PPP interfaces in a Juniper product."
    ::= { juniPppProfileGroups 7 }                                 -- JUNOSe 5.3

END
