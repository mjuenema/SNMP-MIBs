-- Version 1.0 

-- **********************************************************
-- Copyright 2007 VMware, Inc.  All rights reserved. 
--
--  This MIB module reports environmental diagnostics state
--  
-- **********************************************************

VMWARE-ENV-MIB DEFINITIONS ::= BEGIN

IMPORTS
   OBJECT-TYPE
      FROM RFC-1212
   TimeTicks
      FROM RFC1155-SMI
   DisplayString
      FROM RFC1213-MIB
   TRAP-TYPE 
      FROM RFC-1215
   VmwSubsystemTypes, VmwSubsystemStatus
      FROM VMWARE-TC-MIB
   vmware, vmwProductSpecific
      FROM VMWARE-ROOT-MIB;

-- OID root for this MIB module
  vmwEnv OBJECT IDENTIFIER ::= { vmwProductSpecific 20 }

  vmwEnvNumber OBJECT-TYPE
      SYNTAX  INTEGER
      ACCESS  read-only
      STATUS  mandatory
      DESCRIPTION
          "Count of number of conceptual rows in vmwEnvTable"
      ::= { vmwEnv  1 }

  vmwEnvLastChange OBJECT-TYPE
      SYNTAX  TimeTicks
      ACCESS  read-only
      STATUS  mandatory
      DESCRIPTION
          "The value of sysUptime when a conceptual row was added
          or deleted from this table"
      ::= { vmwEnv  2 }

  vmwEnvTable OBJECT-TYPE
      SYNTAX  SEQUENCE OF VmwEnvEntry
      ACCESS  not-accessible
      STATUS  mandatory
      DESCRIPTION
          "This table is populated from monitoring subsystems such as IPMI
          One conceptual row is maintained for each reporting component.
          Conceptual rows are not persistent across device resets"
      ::= { vmwEnv  3 }
  
  vmwEnvEntry OBJECT-TYPE
      SYNTAX  VmwEnvEntry
      ACCESS  not-accessible
      STATUS  mandatory
      DESCRIPTION
          "One entry for each physical component reporting its
          status to ESX Operating System"
      INDEX   { vmwEnvIndex }
      ::= { vmwEnvTable 1 }
  
  VmwEnvEntry ::= SEQUENCE {
    vmwEnvIndex INTEGER,
    vmwSubsystemType VmwSubsystemTypes,
    vmwHardwareStatus VmwSubsystemStatus,
    vmwEventDescription DisplayString,
    vmwEnvHardwareTime TimeTicks
  }
  
  vmwEnvIndex OBJECT-TYPE
      SYNTAX  INTEGER (1..1000)
      ACCESS  read-only
      STATUS  mandatory
      DESCRIPTION
          "A unique identifier that does not persist across management restarts"
      ::= { vmwEnvEntry 1 }
  
  vmwSubsystemType OBJECT-TYPE
      SYNTAX  VmwSubsystemTypes
      ACCESS  read-only
      STATUS  mandatory
      DESCRIPTION
          "Hardware component reporting environmental state"
      ::= { vmwEnvEntry 2 }
  
  vmwHardwareStatus OBJECT-TYPE
      SYNTAX VmwSubsystemStatus
      ACCESS read-only
      STATUS mandatory
      DESCRIPTION
          "Last reported state of this component"
      ::= { vmwEnvEntry 3 }

  vmwEventDescription OBJECT-TYPE
      SYNTAX DisplayString
      ACCESS read-only
      STATUS mandatory
      DESCRIPTION
          "Human readable description of this event"
      ::= { vmwEnvEntry 4 }
  
  vmwEnvHardwareTime OBJECT-TYPE
      SYNTAX  TimeTicks
      ACCESS  read-only
      STATUS  mandatory
      DESCRIPTION
          "Value of sysUptime when vmwHardwareStatus was obtained"
      ::= { vmwEnvEntry 5 }
  
-- Notifications
  
  vmwEnvHardwareEvent TRAP-TYPE 
      ENTERPRISE vmware 
      VARIABLES { vmwSubsystemType, vmwHardwareStatus, vmwEventDescription, vmwEnvHardwareTime }
      DESCRIPTION 
          "This notification, if the agent is so configured, may be sent when 
           the ESX Operating System has detected a material change in 
           physical condition of the hardware" 
      ::= 301 


END
