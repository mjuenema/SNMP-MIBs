-- **********************************************************
-- Copyright 2007 VMware, Inc.  All rights reserved. 
-- 
--  This MIB Module provides common textual conventions for
--  VMware Management
--
-- **********************************************************
-- Version 1.0 

VMWARE-TC-MIB DEFINITIONS ::= BEGIN

VmwSubsystemTypes ::= INTEGER {
      unknown(1), -- reporting subsystem is not one of the following
      chassis(2),
      powerSupply(3),
      fan(4),
      cpu(5),
      memory(6),
      battery(7),
      temperatureSensor(8),
      raidController(9),
      voltage(10)
      }

VmwSubsystemStatus ::= INTEGER {
      unknown(1),  -- unable to match to one of the following states
      normal(2), 
      marginal(3),
      critical(4),
      failed(5)
      }

END
