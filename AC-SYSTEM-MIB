AC-SYSTEM-MIB DEFINITIONS ::= BEGIN


    IMPORTS
       

        OBJECT-TYPE, 
        MODULE-IDENTITY                             FROM SNMPv2-SMI
        TAddress, 
        DisplayString, 
        DateAndTime, TEXTUAL-CONVENTION             FROM SNMPv2-TC
        IpAddress                                   FROM RFC1155-SMI
        Unsigned32,
		Integer32,
        enterprises                                 FROM SNMPv2-SMI
		RowStatus      								FROM SNMPv2-TC
		SnmpAdminString								FROM SNMP-FRAMEWORK-MIB
		audioCodes,       
		acRegistrations,
		acGeneric, 
		acProducts,acBoardMibs						FROM AUDIOCODES-TYPES-MIB
		InetAddress, InetAddressType				FROM INET-ADDRESS-MIB;

       
acSystem  MODULE-IDENTITY       
    LAST-UPDATED "201001241133Z"          --Sunday, January 24, 2010
    ORGANIZATION "AudioCodes Ltd"
    CONTACT-INFO
    "Postal: Support
	     AudioCodes LTD
             1 Hayarden Street
             Airport City 
	     Lod, ISRAEL 70151
     Tel:    972-3-9764000
     Fax:    972-3-9764040
     Email:  support@audiocodes.com
     Web:    www.audiocodes.com"		

    DESCRIPTION       
    ""



    ::= {acBoardMibs 10}  

     acSystemConfiguration OBJECT IDENTIFIER ::= {acSystem 1}


     acSysControl OBJECT IDENTIFIER ::= {acSystemConfiguration 1}


     acSysControlProtocolType OBJECT-TYPE
       SYNTAX INTEGER {
                  controlProtocol-None(0)
,
                  controlProtocol-MGCP(1)
,
                  controlProtocol-MEGACO(2)
,
                  controlProtocol-H323(4)
,
                  controlProtocol-SIP(8)

                  }
       MAX-ACCESS read-write
       STATUS current
       DESCRIPTION
           "Defines the control protocol type. 
Choose either:
0 = None
1 = MGCP
2 = MEGACO
4 = H.323 
8 = SIP.
Access: Offline.
AC INI-Param: MGCONTROLPROTOCOLTYPE"
       ::= {acSysControl 1}



     acSysControlTrunkingToAnalogFunctionalityProfile OBJECT-TYPE
       SYNTAX INTEGER {
                  disable(0)
,
                  cASAnalog(1)

                  }
       MAX-ACCESS read-write
       STATUS current
       DESCRIPTION
           "This parameter defines the Trunking to Analog Functionality
Profile. 
0 = Disable
1 = Enable MelCAS/LoopStart/GroundStart to Analog Functionality
Refer to the enumerator acTrunkingToAnalogFunctionalityProfile
enum for the possible values.
Access: Offline.
AC INI-Param: TrunkingToAnalogFunctionalityProfile"
       ::= {acSysControl 2}



     acSysTDM OBJECT IDENTIFIER ::= {acSystemConfiguration 2}


     acSysTDMClock OBJECT IDENTIFIER ::= {acSysTDM 1}


     acSysTDMClockSource OBJECT-TYPE
       SYNTAX INTEGER {
                  internal(1)
,
                  mVIP(3)
,
                  network(4)
,
                  h110-A(8)
,
                  h110-B(9)
,
                  netReference1(10)
,
                  netReference2(11)
,
                  sC-2M(12)
,
                  sC-4M(13)
,
                  sC-8M(14)
,
                  bITS(15)
,
                  network-b(16)
,
                  aTM-OC3(17)
,
                  aTM-OC3-B(18)
,
                  aTM-OC12(19)
,
                  network-DS3-1(20)
,
                  network-DS3-2(21)
,
                  network-DS3-3(22)

                  }
       MAX-ACCESS read-write
       STATUS current
       DESCRIPTION
           "Selects the clock source on which the board synchronizes.
1 = Local oscillator
3 = MVIP
4 = PSTN Network
8 = H.110A
9 = H.110B
10 = NetRef1
11 = NetRef2
12 = SC2M
13 = SC4M
14 = SC8M
15 = BITS
16 = Network-B
17 = ATM-OC3
18 = ATM-OC3-B
19 = ATM-OC12
20 = Network-DS3-1
21 = Network-DS3-2
22 = Network-DS3-3
Default = 1
TP-1610 = 3.
Access: Online.
AC INI-Param: TDMBUSCLOCKSOURCE"
       ::= {acSysTDMClock 1}



     acSysTDMClockEnableFallBack OBJECT-TYPE
       SYNTAX INTEGER {
                  manual(0)
,
                  autoNon-Revertive(1)
,
                  auto-Revertive(2)

                  }
       MAX-ACCESS read-write
       STATUS current
       DESCRIPTION
           "Defines the auto fallback of the clock. 
Range: 
0 = Manual
1 = Auto Non-Revertive
2 = Auto Revertive.
Access: Online.
AC INI-Param: TDMBUSENABLEFALLBACK"
       ::= {acSysTDMClock 2}



     acSysTDMClockLocalReference OBJECT-TYPE
       SYNTAX Unsigned32 (0..256)
       MAX-ACCESS read-write
       STATUS current
       DESCRIPTION
           "When the clock source is set to Network, this parameter selects
the Trunk ID to be used as the clock synchronization source
of the board.
When using H.110/H.100 bus, this parameter also selects the
trunk used as the clock source for the NetRef clock generation
(in this case, the clock source must not be set to Network.
Range = 0 to (MAX_TRUNK _NUM-1).
Access: Online.
AC INI-Param: TDMBusLocalReference"
       ::= {acSysTDMClock 3}



     acSysTDMClockMasterSlaveSelection OBJECT-TYPE
       SYNTAX INTEGER {
                  acTDMBusSlaveMode(0)
,
                  acTDMBusMasterMode(1)
,
                  acH110BusSecondaryMasterMode(2)

                  }
       MAX-ACCESS read-write
       STATUS current
       DESCRIPTION
           "Sets SC/MVIP/H.100/H.110 to either: 

0 = Slave mode (another board in the system must supply the
clock to the TDM bus) or Master mode (the board is the clock
source for the TDM bus) or Secondary Master mode (for H100/H110
Bus only).  
1 = H110A Master in Master mode
2 = H.110B Master.
Access: Online.
AC INI-Param: TDMBUSMASTERSLAVESELECTION"
       ::= {acSysTDMClock 4}



     acSysTDMClockNetRefSpeed OBJECT-TYPE
       SYNTAX INTEGER {
                  acTH110BusNetRefSpeed-8khz(0)
,
                  acTH110BusNetRefSpeed-1544khz(1)
,
                  acTH110BusNetRefSpeed-20488khz(2)

                  }
       MAX-ACCESS read-write
       STATUS current
       DESCRIPTION
           "Determines the NetRef frequency (for both generation and synchronization).
0 = 8 kHz
1 = 1.544 MHz
2 = 2.048 MHz.
Access: Online.
AC INI-Param: TDMBUSNETREFSPEED"
       ::= {acSysTDMClock 5}



     acSysTDMClockAutoFallBackEnable OBJECT-TYPE
       SYNTAX INTEGER {
                  disable(0)
,
                  enable(1)

                  }
       MAX-ACCESS read-write
       STATUS current
       DESCRIPTION
           "Enables or disables the PSTN trunk auto-fallback feature.
Access: Offline.
AC INI-Param: TDMBusPSTNAutoClockEnable"
       ::= {acSysTDMClock 6}



     acSysTDMClockAutoFallBackRevertingEnable OBJECT-TYPE
       SYNTAX INTEGER {
                  disable(0)
,
                  enable(1)

                  }
       MAX-ACCESS read-write
       STATUS current
       DESCRIPTION
           "Enables/disables the PSTN trunk auto-fallback reverting feature.
Access: Offline.
AC INI-Param: TDMBusPSTNAutoClockRevertingEnable"
       ::= {acSysTDMClock 7}



     acSysTDMClockBitsReference OBJECT-TYPE
       SYNTAX Unsigned32 (1..2)
       MAX-ACCESS read-write
       STATUS current
       DESCRIPTION
           "Configures the BITS clock reference when the board source clock
is set to BITS and Fallback is set to manual or non-revertive.


1 = REF_1 
2 = REF_2.
Access: Online.
AC INI-Param: TDMBITSClockReference"
       ::= {acSysTDMClock 8}



     acSysTDMClockPLLOutOfRange OBJECT-TYPE
       SYNTAX INTEGER {
                  oor-9-2to12ppm(0)
,
                  oor-40to52ppm(1)
,
                  oor-100to130ppm(2)
,
                  oor-64to83ppm(3)
,
                  oor-13-8to18ppm(4)
,
                  oor-24-6to32ppm(5)
,
                  oor-36-6to47-5ppm(6)
,
                  oor-52to67-5ppm(7)

                  }
       MAX-ACCESS read-write
       STATUS current
       DESCRIPTION
           "Determines the valid PPM range outside the Stratum 3 standard.
This parameter is only relevant for the TP8410 on the Mediant
3000. This parameter is enabled when bspTimingModuleCfgTimingMode
is set to TM_External_MODE(1).

One of the following possible values: OOR_9_2to12ppm(0),OOR_40to52ppm(1),OOR_100to130ppm(2),OOR_64to83ppm(3),OOR_13_8to18ppm(4),OOR_24_6to32ppm(5),OOR_36_6to47_5ppm(6),OOR_52to67_5ppm(7).
Access: Online.
AC INI-Param: PLLOutOfRange"
       ::= {acSysTDMClock 9}



     acSysTDMClockFallbackClock OBJECT-TYPE
       SYNTAX INTEGER {
                  network(4)
,
                  h110-A(8)
,
                  h110-B(9)
,
                  netReference1(10)
,
                  netReference2(11)

                  }
       MAX-ACCESS read-write
       STATUS current
       DESCRIPTION
           "Selects the fallback clock source on which board synchronizes
in the event of clock failure.
4 = PSTN Network
8 = H.110A
9 = H.110B
10 = NetRef1
11 = NetRef2.
Access: Online.
AC INI-Param: TDMBusFallbackClock"
       ::= {acSysTDMClock 10}



     acSysTDMBus OBJECT IDENTIFIER ::= {acSysTDM 2}


     acSysTDMBusType OBJECT-TYPE
       SYNTAX INTEGER {
                  mVIP-BUS(0)
,
                  sC-BUS(1)
,
                  uSE-FRAMERS(2)
,
                  qSLAC-BUS(3)
,
                  uSE-H110-BUS(4)
,
                  uSE-EXT-BUS(5)
,
                  aNALOG-BUS(6)
,
                  uSE-PSTN-SW-ONLY(8)

                  }
       MAX-ACCESS read-write
       STATUS current
       DESCRIPTION
           "Selects the TDM bus interface to be used (only one TDM bus interface
can be enabled at one time although more than one can
physically exist on the board).
Range:
0 = acMVIP_BUS
1 = acSC_BUS
2 = acFRAMERS
4 = acH100_BUS
5 = EXT TDM
6 = Analog
8 = SW Pstn

Default:
TP-1610 and TP-2810 = 2
 TPM-1100 = 5
 TP-260 = 1.
Access: Offline.
AC INI-Param: TDMBUSTYPE"
       ::= {acSysTDMBus 1}



     acSysTDMBusSpeed OBJECT-TYPE
       SYNTAX INTEGER {
                  acTDMBusSpeed-2Mbps(0)
,
                  acTDMBusSpeed-4Mbps(2)
,
                  acTDMBusSpeed-8Mbps(3)
,
                  acTDMBusSpeed-16Mbps(4)

                  }
       MAX-ACCESS read-write
       STATUS current
       DESCRIPTION
           "Selects the TDM bus speed according to the Bus Type as follows:

SC = 0/2/3
H.110/H.100 = 3
MVIP = 0
Where: 

0 = 2048 kbps
2 = 4096 kbps
3 = 8192 kbps
4 = 16384 kbps
Default: TP-260 = 2
 All other boards = 3.
Access: Offline.
AC INI-Param: TDMBUSSPEED"
       ::= {acSysTDMBus 2}



     acSysTDMBusOutputPort OBJECT-TYPE
       SYNTAX Unsigned32 (0..31)
       MAX-ACCESS read-write
       STATUS current
       DESCRIPTION
           "Defines the SC/MVIP/H.100/H.110 output port to be used for the
board's channel #0. All other channels then occupy the next
timeslots sequentially.
Range:
0 to 15 for SC/MVIP
0 to 31 for H.110.
Access: Offline.
AC INI-Param: TDMBUSOUTPUTPORT"
       ::= {acSysTDMBus 3}



     acSysTDMBusOutputStartingChannel OBJECT-TYPE
       SYNTAX Unsigned32 (0..127)
       MAX-ACCESS read-write
       STATUS current
       DESCRIPTION
           "Defines the outgoing TDM Timeslot for board's channel #0. The
remaining channels are organized sequentially.
Access: Offline.
AC INI-Param: TDMBUSOUTPUTSTARTINGCHANNEL"
       ::= {acSysTDMBus 4}



     acSysPCM OBJECT IDENTIFIER ::= {acSysTDM 3}


     acSysPCMLawSelect OBJECT-TYPE
       SYNTAX INTEGER {
                  muLaw(3)
,
                  aLaw(1)
,
                  automatic(0)

                  }
       MAX-ACCESS read-write
       STATUS current
       DESCRIPTION
           "Selects the type of PCM companding law in input/output TDM bus
(TDM bus is defined using the TDMBusType parameter).

1 = A-law
3 = Mu-Law.
Access: Offline.
AC INI-Param: PCMLAWSELECT"
       ::= {acSysPCM 1}



     acSysPCMIdlePattern OBJECT-TYPE
       SYNTAX Unsigned32 (0..255)
       MAX-ACCESS read-write
       STATUS current
       DESCRIPTION
           "Defines the PCM pattern applied to the E1/T1 timeslot (B-channel)
when the channel is idle. 
Default:
0xFF if PCMLawSelect is Mu-Law
0xD5 if PCMLawSelect is A-Law
Range = 0x00 to 0xFF.
Access: Offline.
AC INI-Param: IDLEPCMPATTERN"
       ::= {acSysPCM 2}



     acSysPCMIdleABCDPattern OBJECT-TYPE
       SYNTAX Unsigned32 (0..255)
       MAX-ACCESS read-write
       STATUS current
       DESCRIPTION
           "Defines the ABCD (CAS) pattern to be applied on the signaling
bus before it is changed by the user or the PSTN protocol.
This is only relevant when using PSTN interface with CAS protocols.
Range = 0x0 to 0xF.
Access: Offline.
AC INI-Param: IDLEABCDPATTERN"
       ::= {acSysPCM 3}



     acSysPCMSerialPortAuditIntervalMin OBJECT-TYPE
       SYNTAX Unsigned32 (0..60)
       MAX-ACCESS read-write
       STATUS current
       DESCRIPTION
           "Interval timeout in minutes, of the Serial Port audit. In case
of 0 value, the audit isn't running.
Access: Offline.
AC INI-Param: SerialPortAuditIntervalMin"
       ::= {acSysPCM 4}



     acSysNetworkConfig OBJECT IDENTIFIER ::= {acSystemConfiguration 3}


     acSysIP OBJECT IDENTIFIER ::= {acSysNetworkConfig 1}


     acSysIPAddress OBJECT-TYPE
       SYNTAX IpAddress
       MAX-ACCESS read-write
       STATUS current
       DESCRIPTION
           "Board IP Address.  In human readable form.
 in host byte order
e.g. 192.10.1.2 = 0xc00a0102). 
  Users should set the subnet
mask to a valid value per the IP address.
Access: Online.
AC INI-Param: N/A"
       ::= {acSysIP 1}



     acSysIPSubNetAddress OBJECT-TYPE
       SYNTAX IpAddress
       MAX-ACCESS read-write
       STATUS current
       DESCRIPTION
           "Board SubNet Address.  In human readable form.
  (in host byte
order e.g. 255.255.255.0 = 0xffffff00). 
  default =255.255.255.0.
Access: Online.
AC INI-Param: N/A"
       ::= {acSysIP 2}



     acSysIPDefaultGatewayAddress OBJECT-TYPE
       SYNTAX IpAddress
       MAX-ACCESS read-write
       STATUS current
       DESCRIPTION
           "Default Gateway Address.
 Board's Default Gateway IP address.
 In human readable form.
 (in host byte order e.g. 192.10.1.255
= 0xc00a01ff).
Access: Online.
AC INI-Param: N/A"
       ::= {acSysIP 3}



     acSysIPDHCPEnable OBJECT-TYPE
       SYNTAX INTEGER {
                  disable(0)
,
                  enable(1)

                  }
       MAX-ACCESS read-write
       STATUS current
       DESCRIPTION
           "Enables/disables DHCP support. 

0 = Disable
1 = Enable

After the gateway is powered up, it attempts to communicate
with a BootP server. If a BootP server does not respond and
if DHCP is enabled, the gateway attempts to obtain its IP address
and other network parameters from the DHCP server. 
Note that throughout the DHCP procedure, the BootP/TFTP application
must be deactivated. If it isn’t deactivated, the gateway
receives a response from the BootP server instead of
the DHCP server. 
For additional information on DHCP, refer to the product documentation.

Note: DHCPEnable is a special ‘Hidden’ parameter. Once defined
and saved in flash memory, its assigned value doesn’t revert
to its default even if the parameter doesn't appear in
the INI file.
Access: Online.
AC INI-Param: DHCPEnable"
       ::= {acSysIP 4}



     acSysIPDHCPSpeedFactor OBJECT-TYPE
       SYNTAX Unsigned32 (0..10)
       MAX-ACCESS read-write
       STATUS current
       DESCRIPTION
           "Controls the DHCP renewal speed. When set to 0, the DHCP lease
renewal is disabled. Otherwise, the renewal time is divided
by this factor. Some DHCP-enabled routers perform better
when set to 4.

0 = Disable DHCP 
1 = Normal 
2 to 10 = Fast.
Access: Offline.
AC INI-Param: DHCPSpeedFactor"
       ::= {acSysIP 5}



     acSysIPDnsPrimaryServerType OBJECT-TYPE
       SYNTAX INTEGER {
                  ipv4(1)

                  }
       MAX-ACCESS read-write
       STATUS current
       DESCRIPTION
           "This parameter defines the DNS primary server's IP address type.
Access: Offline.
AC INI-Param: N/A"
       ::= {acSysIP 6}



     acSysIPDnsPrimaryServer OBJECT-TYPE
       SYNTAX InetAddress
       MAX-ACCESS read-write
       STATUS current
       DESCRIPTION
           "This parameter defines the DNS primary server's IP address.
Range = Legal IP address.
Access: Offline.
AC INI-Param: DNSPriServerIP"
       ::= {acSysIP 7}



     acSysIPDnsSecondaryServerType OBJECT-TYPE
       SYNTAX INTEGER {
                  ipv4(1)

                  }
       MAX-ACCESS read-write
       STATUS current
       DESCRIPTION
           "This parameter defines the DNS secondary server's IP address
type.
Access: Offline.
AC INI-Param: N/A"
       ::= {acSysIP 8}



     acSysIPDnsSecondaryServer OBJECT-TYPE
       SYNTAX InetAddress
       MAX-ACCESS read-write
       STATUS current
       DESCRIPTION
           "This parameter defines the DNS secondary server's IP address.
Range = Legal IP address.
Access: Offline.
AC INI-Param: DNSSecServerIP"
       ::= {acSysIP 9}



     acSysIPDHCPLeaseRenewalEnable OBJECT-TYPE
       SYNTAX INTEGER {
                  disable(0)
,
                  enable(1)

                  }
       MAX-ACCESS read-write
       STATUS current
       DESCRIPTION
           "Enables/disables DHCP renewal support. 
This paramater  will only take effect if DHCPEnable = 0.

After the gateway is powered up, it attempts to communicate
with a BootP server. If a BootP server does not respond and
if DHCP is disabled, the gateway will boot from flash. It will
then attempt to communicate with the DHCP server to renew
the lease. 
Note that throughout the DHCP procedure, the BootP/TFTP application
must be deactivated. If it isn’t deactivated, the gateway
receives a response from the BootP server instead of
the DHCP server. 
For additional information on DHCP, refer to the product documentation.


For cases where the booting the board via DHCP is not desirable,
but renewing DHCP leasing is. if DHCPEnable = 1, this
paramater will not have any effect.
Access: Online.
AC INI-Param: EnableDHCPLeaseRenewal"
       ::= {acSysIP 10}



     acMultipleIP OBJECT IDENTIFIER ::= {acSysIP 30}


     acMultipleIPEnable OBJECT-TYPE
       SYNTAX INTEGER {
                  disable(0)
,
                  enable(1)

                  }
       MAX-ACCESS read-write
       STATUS obsolete
       DESCRIPTION
           "Enables the multiple IPs feature. 

0 = Disable 
1 = Enable.
Access: Offline.
AC INI-Param: EnableMultipleIPs"
       ::= {acMultipleIP 1}



     acMultipleIPEnableTPNCPasOAM OBJECT-TYPE
       SYNTAX INTEGER {
                  disable(0)
,
                  enable(1)

                  }
       MAX-ACCESS read-write
       STATUS current
       DESCRIPTION
           "Sets the TPNCP location on the Operation, Administration and
Management (OAM) network, when operating in multiple IPs mode.
If this parameter is set and the machine is working in multiple
IPs mode, TPNCP is located on the OAM network.

0 = TPNCP on Control network
1 = TPNCP on OAM network.
Access: Offline.
AC INI-Param: EnableTPNCPasOAM"
       ::= {acMultipleIP 2}



     acMultipleIPEnableDNSasOAM OBJECT-TYPE
       SYNTAX INTEGER {
                  disable(0)
,
                  enable(1)

                  }
       MAX-ACCESS read-write
       STATUS current
       DESCRIPTION
           "Sets the location of the DNS. If this parameter is set and the
machine is functioning in multiple IPs mode, the DNS is located
on the OAM network. If not, the DNS is on the control
network.

0 = Disable
1 = Enable.
Access: Offline.
AC INI-Param: EnableDNSasOAM"
       ::= {acMultipleIP 3}



     acMultipleIPEnableNTPasOAM OBJECT-TYPE
       SYNTAX INTEGER {
                  disable(0)
,
                  enable(1)

                  }
       MAX-ACCESS read-write
       STATUS current
       DESCRIPTION
           "Sets the location of the Network Time Protocol (NTP). If this
parameter is set and the machine is functioning in multiple
IPs mode, the NTP is located on the OAM network. If not, the
NTP is located on the control network.

0 = Disable
1 = Enable.
Access: Offline.
AC INI-Param: EnableNTPasOAM"
       ::= {acMultipleIP 4}



     acMultipleIPEnableSCTPasControl OBJECT-TYPE
       SYNTAX INTEGER {
                  disable(0)
,
                  enable(1)

                  }
       MAX-ACCESS read-write
       STATUS current
       DESCRIPTION
           "Sets the location of the Stream Control Transmission Protocol
(SCTP). If this parameter is set and the machine is functioning
in multiple IPs mode, the SCTP is located on the control
network. If not, the SCTP is located on the OAM network.

0 = Default
1 = Enable.
Access: Offline.
AC INI-Param: EnableSCTPasControl"
       ::= {acMultipleIP 5}



     acMultipleIPEnableNetwotkSeparation OBJECT-TYPE
       SYNTAX INTEGER {
                  disable(0)
,
                  enable(1)

                  }
       MAX-ACCESS read-write
       STATUS current
       DESCRIPTION
           "Enables Network Physical Separation. Allows the user to have
separate port for each Network. Requires suitable hardware.

0 = Disabled 
1 = Enabled.
Access: Offline.
AC INI-Param: ENABLENETWORKPHYSICALSEPARATION"
       ::= {acMultipleIP 6}



     acMultipleIPInterfaceTableAction OBJECT-TYPE
       SYNTAX INTEGER {
                  done(1)
,
                  validateConfiguration(2)

                  }
       MAX-ACCESS read-write
       STATUS current
       DESCRIPTION
           "This is an action object. Set this to validateConfiguration(2)
when you want the configuration in the acSysInterfaceTable
to be validated immediately (as opposed to at reset).  done(1)
is the default value for any GET on this object. The results
of the action should be followed in the syslog.
Access: Instant.
AC INI-Param: N/A"
       ::= {acMultipleIP 7}



     -- ****************************************
     -- acNetworkIP table declaration
     -- ****************************************
     acNetworkIPTable OBJECT-TYPE
       SYNTAX SEQUENCE OF AcNetworkIPEntry
       MAX-ACCESS not-accessible
       STATUS obsolete
       DESCRIPTION
           "IP control table. Enables to add, remove or configure the device's networks."
       ::= {acMultipleIP 21}



     -- ****************************************
     -- acNetworkIP table entry
     -- ****************************************
     acNetworkIPEntry OBJECT-TYPE
       SYNTAX AcNetworkIPEntry
       MAX-ACCESS not-accessible
       STATUS obsolete
       DESCRIPTION
           ""
       INDEX {acNetworkIPIndex}
       ::= {acNetworkIPTable 1}



     -- ****************************************
     -- acNetworkIP TABLE
     -- ****************************************
     AcNetworkIPEntry ::= SEQUENCE {
       acNetworkIPIndex                                INTEGER,
       acNetworkIPIfIndex                              Unsigned32,
       acNetworkIPLocalIPAddress                       IpAddress,
       acNetworkIPLocalSubnetMask                      IpAddress,
       acNetworkIPLocalDefGW                           IpAddress,
       acNetworkIPAdminState                           INTEGER
     }



     acNetworkIPIndex OBJECT-TYPE
       SYNTAX INTEGER {
                  oam(1)
,
                  media(2)
,
                  control(3)

                  }
       MAX-ACCESS not-accessible
       STATUS obsolete
       DESCRIPTION
           "The row's index.
AC INI-Param: N/A"
       ::= {acNetworkIPEntry 1}



     acNetworkIPIfIndex OBJECT-TYPE
       SYNTAX Unsigned32 (0..2)
       MAX-ACCESS read-only
       STATUS obsolete
       DESCRIPTION
           "The row's index in the IF MIB.
The IF MIB is not yet supported and so for now this is the
same as the ipCidrRouteIfIndex object.
0 = OAM
1 = Media
2 = Control.
AC INI-Param: N/A"
       ::= {acNetworkIPEntry 2}



     acNetworkIPLocalIPAddress OBJECT-TYPE
       SYNTAX IpAddress
       MAX-ACCESS read-write
       STATUS obsolete
       DESCRIPTION
           "Sets the IP address of the OAM (Operation, Administration &
Management) when operating in multiple IPs mode.

Range: Legal IP address
Default = 0.0.0.0.
Access: Online.
AC INI-Param: N/A"
       ::= {acNetworkIPEntry 3}



     acNetworkIPLocalSubnetMask OBJECT-TYPE
       SYNTAX IpAddress
       MAX-ACCESS read-write
       STATUS obsolete
       DESCRIPTION
           "Sets the Subnet Mask for the OAM interface, when operating in
multiple IPs mode.

Range: Legal Subnet
Default = 0.0.0.0.
Access: Online.
AC INI-Param: N/A"
       ::= {acNetworkIPEntry 4}



     acNetworkIPLocalDefGW OBJECT-TYPE
       SYNTAX IpAddress
       MAX-ACCESS read-write
       STATUS obsolete
       DESCRIPTION
           "Sets the Default gateway for the OAM interface when operating
in multiple IPs mode.

Range: Legal IP address in subnet
Default = 0.0.0.0.
Access: Online.
AC INI-Param: N/A"
       ::= {acNetworkIPEntry 5}



     acNetworkIPAdminState OBJECT-TYPE
       SYNTAX INTEGER {
                  lock(1)
,
                  unLock(2)

                  }
       MAX-ACCESS read-write
       STATUS obsolete
       DESCRIPTION
           "Determines if a row is currentely active or not.
Lock(1) - the row is in configuration (non active) state.
UnLock(2) - row is in active state.
Access: Online.
AC INI-Param: N/A"
       ::= {acNetworkIPEntry 6}



     -- ****************************************
     -- acSysInterface table declaration
     -- ****************************************
     acSysInterfaceTable OBJECT-TYPE
       SYNTAX SEQUENCE OF AcSysInterfaceEntry
       MAX-ACCESS not-accessible
       STATUS current
       DESCRIPTION
           "Multiple Interfaces' Interface Table"
       ::= {acMultipleIP 22}



     -- ****************************************
     -- acSysInterface table entry
     -- ****************************************
     acSysInterfaceEntry OBJECT-TYPE
       SYNTAX AcSysInterfaceEntry
       MAX-ACCESS not-accessible
       STATUS current
       DESCRIPTION
           ""
       INDEX {acSysInterfaceIndex}
       ::= {acSysInterfaceTable 1}



     -- ****************************************
     -- acSysInterface TABLE
     -- ****************************************
     AcSysInterfaceEntry ::= SEQUENCE {
       acSysInterfaceIndex                             Unsigned32,
       acSysInterfaceRowStatus                         RowStatus,
       acSysInterfaceAction                            INTEGER,
       acSysInterfaceActionRes                         INTEGER,
       acSysInterfaceApplicationTypes                  INTEGER,
       acSysInterfaceMode                              INTEGER,
       acSysInterfaceIPAddress                         SnmpAdminString,
       acSysInterfacePrefixLength                      Unsigned32,
       acSysInterfaceGateway                           SnmpAdminString,
       acSysInterfaceVlanID                            Unsigned32,
       acSysInterfaceName                              SnmpAdminString
     }



     acSysInterfaceIndex OBJECT-TYPE
       SYNTAX Unsigned32 (0..15)
       MAX-ACCESS not-accessible
       STATUS current
       DESCRIPTION
           "Index Field for line.
AC INI-Param: InterfaceTable_Index"
       ::= {acSysInterfaceEntry 1}



     acSysInterfaceRowStatus OBJECT-TYPE
       SYNTAX RowStatus
       MAX-ACCESS read-create
       STATUS current
       DESCRIPTION
           "ROWSTATUS Field for line.
AC INI-Param: InterfaceTable_RowStatus"
       ::= {acSysInterfaceEntry 2}



     acSysInterfaceAction OBJECT-TYPE
       SYNTAX INTEGER {
                  none(0)

                  }
       MAX-ACCESS read-create
       STATUS current
       DESCRIPTION
           "Mangement Field for ACTIONS.
AC INI-Param: InterfaceTable_Action"
       ::= {acSysInterfaceEntry 3}



     acSysInterfaceActionRes OBJECT-TYPE
       SYNTAX INTEGER {
                  succeeded(0)

                  }
       MAX-ACCESS read-only
       STATUS current
       DESCRIPTION
           "Mangement Field for ACTIONS RESULT.
AC INI-Param: InterfaceTable_ActionRes"
       ::= {acSysInterfaceEntry 4}



     acSysInterfaceApplicationTypes OBJECT-TYPE
       SYNTAX INTEGER {
                  oam(0)
,
                  media(1)
,
                  control(2)
,
                  oamAndMedia(3)
,
                  oamAndControl(4)
,
                  mediaAndControl(5)
,
                  oamAndMediaAndControl(6)

                  }
       MAX-ACCESS read-create
       STATUS current
       DESCRIPTION
           "The type assigned to the interface.
Access: Offline.
AC INI-Param: InterfaceTable_ApplicationTypes"
       ::= {acSysInterfaceEntry 5}



     acSysInterfaceMode OBJECT-TYPE
       SYNTAX INTEGER {
                  iPv6PrefixManual(3)
,
                  iPv6Manual(4)
,
                  iPv4Manual(10)

                  }
       MAX-ACCESS read-create
       STATUS current
       DESCRIPTION
           "Interface configuration mode.
Access: Offline.
AC INI-Param: InterfaceTable_InterfaceMode"
       ::= {acSysInterfaceEntry 6}



     acSysInterfaceIPAddress OBJECT-TYPE
       SYNTAX SnmpAdminString (SIZE (0..45))
       MAX-ACCESS read-create
       STATUS current
       DESCRIPTION
           "IP Address (can be either IPv4 or IPv6) for this interface.
Access: Online.
AC INI-Param: InterfaceTable_IPAddress"
       ::= {acSysInterfaceEntry 7}



     acSysInterfacePrefixLength OBJECT-TYPE
       SYNTAX Unsigned32 (0..128)
       MAX-ACCESS read-create
       STATUS current
       DESCRIPTION
           "The number of ‘1’ bits in this interface’s netmask.
Access: Offline.
AC INI-Param: InterfaceTable_PrefixLength"
       ::= {acSysInterfaceEntry 8}



     acSysInterfaceGateway OBJECT-TYPE
       SYNTAX SnmpAdminString (SIZE (0..45))
       MAX-ACCESS read-create
       STATUS current
       DESCRIPTION
           "Default Gateway. Filled in one row only. 0 in others.
Access: Offline.
AC INI-Param: InterfaceTable_Gateway"
       ::= {acSysInterfaceEntry 9}



     acSysInterfaceVlanID OBJECT-TYPE
       SYNTAX Unsigned32 (0..4094)
       MAX-ACCESS read-create
       STATUS current
       DESCRIPTION
           "VLAN ID of this interface.
Access: Offline.
AC INI-Param: InterfaceTable_VlanID"
       ::= {acSysInterfaceEntry 10}



     acSysInterfaceName OBJECT-TYPE
       SYNTAX SnmpAdminString (SIZE (0..16))
       MAX-ACCESS read-create
       STATUS current
       DESCRIPTION
           "a 16 character string of this interface’s name.
Access: Offline.
AC INI-Param: InterfaceTable_InterfaceName"
       ::= {acSysInterfaceEntry 11}



     acSyslog OBJECT IDENTIFIER ::= {acSysNetworkConfig 2}


     acSyslogServerIPAddress  OBJECT-TYPE
       SYNTAX IpAddress
       MAX-ACCESS read-write
       STATUS current
       DESCRIPTION
           "This parameter defines the IP address in dotted format notation.
e.g., 192.10.1.255
Range = Legal IP address.
Access: Instant.
AC INI-Param: SYSLOGSERVERIP"
       ::= {acSyslog 1}



     acSyslogEnable OBJECT-TYPE
       SYNTAX INTEGER {
                  disable(0)
,
                  enable(1)

                  }
       MAX-ACCESS read-write
       STATUS current
       DESCRIPTION
           "Enable SysLog protocol log.
Access: Online.
AC INI-Param: ENABLESYSLOG"
       ::= {acSyslog 2}



     acSyslogAcSyslogServerPortNumber OBJECT-TYPE
       SYNTAX Unsigned32 (0..65535)
       MAX-ACCESS read-write
       STATUS current
       DESCRIPTION
           "Defines the Port number of the Syslog Server.
Range = Legal Port Number.
Access: Instant.
AC INI-Param: SyslogServerPort"
       ::= {acSyslog 3}



     acSysNTP OBJECT IDENTIFIER ::= {acSysNetworkConfig 3}


     acSysNTPServerIPAddress OBJECT-TYPE
       SYNTAX IpAddress
       MAX-ACCESS read-write
       STATUS current
       DESCRIPTION
           "This parameter is used to define the NTP server's IP address.
Range = Legal IP address.
Access: Instant.
AC INI-Param: NTPServerIP"
       ::= {acSysNTP 1}



     acSysNTPUtcOffset OBJECT-TYPE
       SYNTAX Integer32 (-43200..43200)
       MAX-ACCESS read-write
       STATUS current
       DESCRIPTION
           "This parameter is used to define the NTP time to offset, in
seconds.

Default = 0
Range = -43200 to +43200 seconds.
Access: Instant.
AC INI-Param: NTPServerUTCOffset"
       ::= {acSysNTP 2}



     acSysNTPUpdateInterval OBJECT-TYPE
       SYNTAX Unsigned32 (1..2147483647)
       MAX-ACCESS read-write
       STATUS current
       DESCRIPTION
           "This parameter defines the NTP update interval, in seconds.
It's inadvisable to set it exceeding 1 month (2592000 seconds).
Range = 0 to 2592000 seconds
Default = 86400 seconds.
Access: Instant.
AC INI-Param: NTPUpdateInterval"
       ::= {acSysNTP 3}



     acSysDayLightSavingTime OBJECT IDENTIFIER ::= {acSysNTP 21}


     acSysDayLightSavingTimeMode OBJECT-TYPE
       SYNTAX INTEGER {
                  disable(0)
,
                  enable(1)

                  }
       MAX-ACCESS read-write
       STATUS current
       DESCRIPTION
           "Determines whether to enable the time ajustment to day light
saving time while update time from NTP server.
Access: Instant.
AC INI-Param: DayLightSavingTimeEnable"
       ::= {acSysDayLightSavingTime 1}



     acSysDayLightSavingTimeOffset OBJECT-TYPE
       SYNTAX Unsigned32 (0..120)
       MAX-ACCESS read-write
       STATUS current
       DESCRIPTION
           "when DayLightSavingTimeEnable is Enable, this parametes determine
the fix size in minutes: 0-120.
Access: Instant.
AC INI-Param: DayLightSavingTimeOffset"
       ::= {acSysDayLightSavingTime 2}



     acSysDayLightSavingTimeStart OBJECT-TYPE
       SYNTAX SnmpAdminString (SIZE (0..11))
       MAX-ACCESS read-write
       STATUS current
       DESCRIPTION
           "This parameter defines the date and time of starting day light
time in current year.
Format mo:dd:hh:mm.
Access: Instant.
AC INI-Param: DayLightSavingTimeStart"
       ::= {acSysDayLightSavingTime 3}



     acSysDayLightSavingTimeEnd OBJECT-TYPE
       SYNTAX SnmpAdminString (SIZE (0..11))
       MAX-ACCESS read-write
       STATUS current
       DESCRIPTION
           "This parameter defines the date and time of ending day light
time in current year.
Format mo:dd:hh:mm.
Access: Instant.
AC INI-Param: DayLightSavingTimeEnd"
       ::= {acSysDayLightSavingTime 4}



     acSysWEB OBJECT IDENTIFIER ::= {acSysNetworkConfig 4}


     acSysWEBConfigDisable OBJECT-TYPE
       SYNTAX INTEGER {
                  enable(0)
,
                  disable(1)

                  }
       MAX-ACCESS read-write
       STATUS current
       DESCRIPTION
           "Enables or disables Web Configuration. 
0 = Read & Write mode (default) 
1 = Read Only mode.
Access: Offline.
AC INI-Param: DISABLEWEBCONFIG"
       ::= {acSysWEB 1}



     acSysWEBHTTPSOnly OBJECT-TYPE
       SYNTAX INTEGER {
                  disable(0)
,
                  enable(1)

                  }
       MAX-ACCESS read-write
       STATUS current
       DESCRIPTION
           "Use this parameter to allow only HTTPS connections (force security).
When set to 1, unencrypted HTTP (normally, port 80)
is blocked.
Access: Offline.
AC INI-Param: HTTPSOnly"
       ::= {acSysWEB 2}



     acSysWEBHTTPSPort OBJECT-TYPE
       SYNTAX Unsigned32 (0..65535)
       MAX-ACCESS read-write
       STATUS current
       DESCRIPTION
           "Determine the local Secure HTTPS port of the device.
The default port is 443.
Range = 1-65535 (other restrictions may apply in this range).
Access: Offline.
AC INI-Param: HTTPSPORT"
       ::= {acSysWEB 3}



     acSysWEBWebUseRadiusLogin OBJECT-TYPE
       SYNTAX INTEGER {
                  disable(0)
,
                  enable(1)

                  }
       MAX-ACCESS read-write
       STATUS current
       DESCRIPTION
           "Uses the RADIUS (Remote Authentication Dial-In User Server/Service)
for Web interface authentication. 
Make sure that ENABLERADIUS is on. 
Use of this parameter without HTTPSONLY = 1 is not recommended.
Access: Instant.
AC INI-Param: WEBRADIUSLOGIN"
       ::= {acSysWEB 4}



     acSysWEBHTTPSCipherString OBJECT-TYPE
       SYNTAX SnmpAdminString (SIZE (0..200))
       MAX-ACCESS read-write
       STATUS current
       DESCRIPTION
           "Requires client certificates for HTTPS connection. The client
certificate must be preloaded on the gateway, and its matching
private key must be installed on the managing computer.
Time and date must be correctly set on the gateway, for the
client certificate to be verified.
Access: Offline.
AC INI-Param: HTTPSCipherString"
       ::= {acSysWEB 5}



     acSysWEBDenyAuthenticationTimer OBJECT-TYPE
       SYNTAX Unsigned32 (0..86400)
       MAX-ACCESS read-write
       STATUS current
       DESCRIPTION
           "Defines the time the next authentication attempt from the last
authentication faild IP should be denied.

The range can be any value from 0 - 86400 in seconds.
Access: Online.
AC INI-Param: DenyAuthenticationTimer "
       ::= {acSysWEB 6}



     acSysWEBWanHttpPort OBJECT-TYPE
       SYNTAX Unsigned32 (0..65535)
       MAX-ACCESS read-write
       STATUS current
       DESCRIPTION
           "Determines the WAN HTTP port of the device.
If set to 0, WAN HTTP access will not be possible.
Range = 0 to 65535 (other restrictions may apply in this range).
Access: Offline.
AC INI-Param: WanMgmtHttpPort"
       ::= {acSysWEB 7}



     acSysWEBWanHttpsPort OBJECT-TYPE
       SYNTAX Unsigned32 (0..65535)
       MAX-ACCESS read-write
       STATUS current
       DESCRIPTION
           "Determines the WAN HTTPS port of the device.
If set to 0, WAN HTTPS access will not be possible.
Range = 0 to 65535 (other restrictions may apply in this range).
Access: Offline.
AC INI-Param: WanMgmtHttpsPort"
       ::= {acSysWEB 8}



     -- ****************************************
     -- acSysWEBACL table declaration
     -- ****************************************
     acSysWEBACLTable OBJECT-TYPE
       SYNTAX SEQUENCE OF AcSysWEBACLEntry
       MAX-ACCESS not-accessible
       STATUS current
       DESCRIPTION
           "Access control list for the WEB."
       ::= {acSysWEB 21}



     -- ****************************************
     -- acSysWEBACL table entry
     -- ****************************************
     acSysWEBACLEntry OBJECT-TYPE
       SYNTAX AcSysWEBACLEntry
       MAX-ACCESS not-accessible
       STATUS current
       DESCRIPTION
           ""
       INDEX {acSysWEBACLIndex}
       ::= {acSysWEBACLTable 1}



     -- ****************************************
     -- acSysWEBACL TABLE
     -- ****************************************
     AcSysWEBACLEntry ::= SEQUENCE {
       acSysWEBACLIndex                                Unsigned32,
       acSysWEBACLIP                                   IpAddress
     }



     acSysWEBACLIndex OBJECT-TYPE
       SYNTAX Unsigned32 (0..9)
       MAX-ACCESS read-only
       STATUS current
       DESCRIPTION
           "WEB ACL (Access Control List) index.
AC INI-Param: N/A"
       ::= {acSysWEBACLEntry 1}



     acSysWEBACLIP OBJECT-TYPE
       SYNTAX IpAddress
       MAX-ACCESS read-write
       STATUS current
       DESCRIPTION
           "Allows IP addresses to connect to the Web interface. Set to
zeroes to allow all IP addresses.
Range: Valid IP address
.
Access: Instant.
AC INI-Param: WEBACCESSLIST"
       ::= {acSysWEBACLEntry 2}



     acSysWEBAccess OBJECT IDENTIFIER ::= {acSysNetworkConfig 5}


     -- ****************************************
     -- acSysWEBAccess table declaration
     -- ****************************************
     acSysWEBAccessTable OBJECT-TYPE
       SYNTAX SEQUENCE OF AcSysWEBAccessEntry
       MAX-ACCESS not-accessible
       STATUS current
       DESCRIPTION
           ""
       ::= {acSysWEBAccess 1}



     -- ****************************************
     -- acSysWEBAccess table entry
     -- ****************************************
     acSysWEBAccessEntry OBJECT-TYPE
       SYNTAX AcSysWEBAccessEntry
       MAX-ACCESS not-accessible
       STATUS current
       DESCRIPTION
           ""
       INDEX {acSysWEBAccessIndex}
       ::= {acSysWEBAccessTable 1}



     -- ****************************************
     -- acSysWEBAccess TABLE
     -- ****************************************
     AcSysWEBAccessEntry ::= SEQUENCE {
       acSysWEBAccessRowStatus                         Unsigned32,
       acSysWEBAccessAction                            Unsigned32,
       acSysWEBAccessActionResult                      Unsigned32,
       acSysWEBAccessIndex                             INTEGER,
       acSysWEBAccessUserName                          SnmpAdminString,
       acSysWEBAccessUserCode                          SnmpAdminString,
       acSysWEBAccessWebAuthMode                       INTEGER
     }



     acSysWEBAccessRowStatus OBJECT-TYPE
       SYNTAX Unsigned32 (1..1)
       MAX-ACCESS read-write
       STATUS current
       DESCRIPTION
           "WEB Basic row-status.
AC INI-Param: WEBAccessRowStatus"
       ::= {acSysWEBAccessEntry 1}



     acSysWEBAccessAction OBJECT-TYPE
       SYNTAX Unsigned32 (0..0)
       MAX-ACCESS read-create
       STATUS current
       DESCRIPTION
           "WEB Access action.
AC INI-Param: WEBAccessAction"
       ::= {acSysWEBAccessEntry 2}



     acSysWEBAccessActionResult OBJECT-TYPE
       SYNTAX Unsigned32 (0..0)
       MAX-ACCESS read-only
       STATUS current
       DESCRIPTION
           "WEB Access action result.
AC INI-Param: N/A"
       ::= {acSysWEBAccessEntry 3}



     acSysWEBAccessIndex OBJECT-TYPE
       SYNTAX INTEGER {
                  administrator(0)
,
                  monitoringLevel(1)

                  }
       MAX-ACCESS read-only
       STATUS current
       DESCRIPTION
           "WEB Access index.
AC INI-Param: N/A"
       ::= {acSysWEBAccessEntry 4}



     acSysWEBAccessUserName OBJECT-TYPE
       SYNTAX SnmpAdminString (SIZE (0..60))
       MAX-ACCESS read-create
       STATUS current
       DESCRIPTION
           "WEB Basic user name. Range = String[26].
Access: Instant.
AC INI-Param: WEBAccessUserName "
       ::= {acSysWEBAccessEntry 5}



     acSysWEBAccessUserCode OBJECT-TYPE
       SYNTAX SnmpAdminString (SIZE (0..60))
       MAX-ACCESS read-create
       STATUS current
       DESCRIPTION
           "WEB Basic userAccess.
Access: Instant.
AC INI-Param: WEBAccessUserCode "
       ::= {acSysWEBAccessEntry 6}



     acSysWEBAccessWebAuthMode OBJECT-TYPE
       SYNTAX INTEGER {
                  basicMode(0)
,
                  digestModeWhenPossible(1)
,
                  digestModeHTTPOnly(2)

                  }
       MAX-ACCESS read-create
       STATUS current
       DESCRIPTION
           "Selects HTTP basic (clear text) or digest (MD5) authentication
for the web interface.
When set to 0, basic authentication (clear text) will be used.
When set to 1, digest authentication (MD5) will be used.
When set to 2, digest authentication (MD5) will be used for
HTTP, while basic authentication will be used for HTTPS.
Note that turning on RADIUS login forces basic authentication.
Access: Instant.
AC INI-Param: WebAuthMode"
       ::= {acSysWEBAccessEntry 7}



     acSysNATTraversal OBJECT IDENTIFIER ::= {acSysNetworkConfig 6}


     acSysTelnet OBJECT IDENTIFIER ::= {acSysNetworkConfig 7}


     acSysTelnetServerEnable OBJECT-TYPE
       SYNTAX INTEGER {
                  disable(0)
,
                  enable(1)
,
                  ssl(2)

                  }
       MAX-ACCESS read-write
       STATUS current
       DESCRIPTION
           "Enables or disables the embedded Telnet server. Telnet is disabled
by default for security reasons.
0 = Disable
1= Enable
2 = SSL mode (if available - requires an SSL-aware Telnet client
software) 
SSL mode is not available on the MP-108 / MP-124 media gateways.
Access: Instant.
AC INI-Param: TelnetServerEnable"
       ::= {acSysTelnet 1}



     acSysTelnetServerPort OBJECT-TYPE
       SYNTAX Unsigned32 (0..65535)
       MAX-ACCESS read-write
       STATUS current
       DESCRIPTION
           "Defines the port number for the embedded Telnet server.
Range = Valid port number.
Access: Online.
AC INI-Param: TELNETSERVERPORT"
       ::= {acSysTelnet 2}



     acSysTelnetServerIdleDisconnect OBJECT-TYPE
       SYNTAX Unsigned32 (0..2147483647)
       MAX-ACCESS read-write
       STATUS current
       DESCRIPTION
           "This parameter is used to set the timeout for disconnection
of an idle Telnet session (minutes). When set to zero, idle
sessions are not disconnected.

Range: Any number.
Access: Offline.
AC INI-Param: TelnetServerIdleDisconnect"
       ::= {acSysTelnet 3}



     acSysTelnetSSHServerPort OBJECT-TYPE
       SYNTAX Unsigned32 (0..65535)
       MAX-ACCESS read-write
       STATUS current
       DESCRIPTION
           "Defines the port number for the embedded SSH server.
Range = Valid port number.
Access: Online.
AC INI-Param: SSHServerPort"
       ::= {acSysTelnet 4}



     acSysTelnetSSHServerEnable OBJECT-TYPE
       SYNTAX INTEGER {
                  disable(0)
,
                  enable(1)

                  }
       MAX-ACCESS read-write
       STATUS current
       DESCRIPTION
           "Enables or disables the embedded SSH server.
0 = Disable
1= Enable
.
Access: Online.
AC INI-Param: SSHServerEnable"
       ::= {acSysTelnet 5}



     acSysTelnetSSHAdminKey OBJECT-TYPE
       SYNTAX SnmpAdminString (SIZE (0..510))
       MAX-ACCESS read-write
       STATUS current
       DESCRIPTION
           "This parameter holds an RSA public key for strong authentication
to the SSH interface (if enabled).
The value should be a base64-encoded string
 see the Security appendix for additional information.
Access: Instant.
AC INI-Param: SSHAdminKey"
       ::= {acSysTelnet 6}



     acSysTelnetSSHRequirePublicKey OBJECT-TYPE
       SYNTAX INTEGER {
                  disable(0)
,
                  enable(1)

                  }
       MAX-ACCESS read-write
       STATUS current
       DESCRIPTION
           "Enables or disables RSA public keys in SSH.
When set to 0, RSA public keys are optional (if SSHAdminKey
is set).
When set to 1, RSA public keys are mandatory.
Access: Instant.
AC INI-Param: SSHRequirePublicKey"
       ::= {acSysTelnet 7}



     acSysTelnetServerWanPort OBJECT-TYPE
       SYNTAX Unsigned32 (0..65535)
       MAX-ACCESS read-write
       STATUS current
       DESCRIPTION
           "Determines the WAN Telnet port of the device.
If set to 0, WAN Telnet access will not be possible.
Range = 0 to 65535 (other restrictions may apply in this range).
Access: Offline.
AC INI-Param: WanMgmtTelnetPort"
       ::= {acSysTelnet 8}



     acSysTelnetWanSSHServerPort OBJECT-TYPE
       SYNTAX Unsigned32 (0..65535)
       MAX-ACCESS read-write
       STATUS current
       DESCRIPTION
           "Determines the WAN Telnet port of the device.
If set to 0, WAN Telnet access will not be possible.
Range = 0 to 65535 (other restrictions may apply in this range).
Access: Offline.
AC INI-Param: WanMgmtSSHPort"
       ::= {acSysTelnet 9}



     acSysHTTPClient OBJECT IDENTIFIER ::= {acSysNetworkConfig 8}


     acSysHTTPClientAutoUpdatePredefinedTime OBJECT-TYPE
       SYNTAX SnmpAdminString (SIZE (0..6))
       MAX-ACCESS read-write
       STATUS current
       DESCRIPTION
           "Schedules an automatic update to a predefined time of the day.
The range is 'HH:MM' (24-hour format).
For example: 20:18
.
Access: Offline.
AC INI-Param: AutoUpdatePredefinedTime"
       ::= {acSysHTTPClient 1}



     acSysHTTPClientAutoUpdateFrequency OBJECT-TYPE
       SYNTAX Unsigned32 (0..65536)
       MAX-ACCESS read-write
       STATUS current
       DESCRIPTION
           "Determines the number of minutes the gateway waits between automatic
updates.

The default value is 0 (the update at fixed intervals mechanism
is disabled).

Range: Any number
.
Access: Offline.
AC INI-Param: AutoUpdateFrequency"
       ::= {acSysHTTPClient 2}



     acSysHTTPClientAutoUpdateCmpFile OBJECT-TYPE
       SYNTAX INTEGER {
                  disable(0)
,
                  enable(1)

                  }
       MAX-ACCESS read-write
       STATUS current
       DESCRIPTION
           "Enables / disables the automatic update mechanism for the cmp
file.

0 = The automatic update mechanism doesn't apply to the cmp
file (default).
1 = The automatic update mechanism includes the cmp file.
Access: Offline.
AC INI-Param: AutoUpdateCmpFile"
       ::= {acSysHTTPClient 3}



     acSysHTTPClientCmpFileURL OBJECT-TYPE
       SYNTAX SnmpAdminString (SIZE (0..254))
       MAX-ACCESS read-write
       STATUS current
       DESCRIPTION
           "This parameter provides a  link to a software image (CMP file)
to be downloaded from a remote server.
.
Access: Offline.
AC INI-Param: CmpFileURL"
       ::= {acSysHTTPClient 4}



     acSysHTTPClientIniFileURL OBJECT-TYPE
       SYNTAX SnmpAdminString (SIZE (0..254))
       MAX-ACCESS read-write
       STATUS current
       DESCRIPTION
           "This parameter provides a link to an ini file to be downloaded
from a remote server.
.
Access: Offline.
AC INI-Param: IniFileURL"
       ::= {acSysHTTPClient 5}



     acSysHTTPClientIniFileTemplateURL OBJECT-TYPE
       SYNTAX SnmpAdminString (SIZE (0..254))
       MAX-ACCESS read-write
       STATUS current
       DESCRIPTION
           "Provides a link to an ini file to be downloaded from a remote
server, in addition to IniFileUrl.
Range = http://server_name/file, https://server_name/file.
Access: Offline.
AC INI-Param: IniFileTemplateUrl"
       ::= {acSysHTTPClient 6}



     acSysHTTPClientCPTFileURL OBJECT-TYPE
       SYNTAX SnmpAdminString (SIZE (0..254))
       MAX-ACCESS read-write
       STATUS current
       DESCRIPTION
           "Provides a link to a Call Progress Tones (CPT) file to be downloaded
from a remote server.
Range = http://server_name/file, https://server_name/file.
Access: Instant.
AC INI-Param: CptFileUrl"
       ::= {acSysHTTPClient 7}



     acSysHTTPClientVPFileURL OBJECT-TYPE
       SYNTAX SnmpAdminString (SIZE (0..254))
       MAX-ACCESS read-write
       STATUS current
       DESCRIPTION
           "Provides a link to a Voice Prompts file to be downloaded from
a remote server.
Range = http://server_name/file, https://server_name/file.
Access: Instant.
AC INI-Param: VpFileUrl"
       ::= {acSysHTTPClient 8}



     acSysHTTPClientPRTFileURL OBJECT-TYPE
       SYNTAX SnmpAdminString (SIZE (0..254))
       MAX-ACCESS read-write
       STATUS current
       DESCRIPTION
           "Provides a link to a prerecorded tones dat file, to be downloaded
from a remote server.
Range = http://server_name/file, https://server_name/file.
Access: Instant.
AC INI-Param: PrtFileUrl"
       ::= {acSysHTTPClient 9}



     acSysHTTPClientFXSCoeffFileURL OBJECT-TYPE
       SYNTAX SnmpAdminString (SIZE (0..254))
       MAX-ACCESS read-write
       STATUS deprecated
       DESCRIPTION
           "Provides a link to an FXS coefficients file, to be downloaded
from a remote server.
Range = http://server_name/file, https://server_name/file.
Access: Instant.
AC INI-Param: FXSCoeffFileUrl"
       ::= {acSysHTTPClient 10}



     acSysHTTPClientFXOCoeffFileURL OBJECT-TYPE
       SYNTAX SnmpAdminString (SIZE (0..254))
       MAX-ACCESS read-write
       STATUS deprecated
       DESCRIPTION
           "Provides a link to an FXO coefficients file, to be downloaded
from a remote server.
Range = http://server_name/file, https://server_name/file.
Access: Instant.
AC INI-Param: FXOCoeffFileUrl"
       ::= {acSysHTTPClient 11}



     acSysHTTPClientCASFileURL OBJECT-TYPE
       SYNTAX SnmpAdminString (SIZE (0..254))
       MAX-ACCESS read-write
       STATUS current
       DESCRIPTION
           "Provides a link to a Channel Associated Signaling (CAS) file
to be downloaded from a remote server.
Range = http://server_name/file, https://server_name/file.
Access: Instant.
AC INI-Param: CasFileUrl"
       ::= {acSysHTTPClient 12}



     acSysHTTPClientXMLFileUrl OBJECT-TYPE
       SYNTAX SnmpAdminString (SIZE (0..254))
       MAX-ACCESS read-write
       STATUS current
       DESCRIPTION
           "Provides a link to an XML segments file, to be downloaded from
a remote server.
See the chapter 'Automatic Update Facility' for supported URL
options.
Access: Instant.
AC INI-Param: APSSegmentsFileUrl "
       ::= {acSysHTTPClient 13}



     acSysHTTPClientCoderTableFileUrl OBJECT-TYPE
       SYNTAX SnmpAdminString (SIZE (0..254))
       MAX-ACCESS read-write
       STATUS current
       DESCRIPTION
           "Provides a link to a coder table (CTBL) file that is to be downloaded
from a remote server.
.
Access: Instant.
AC INI-Param: CoderTableFileUrl"
       ::= {acSysHTTPClient 14}



     acSysHTTPClientUserInfoFileURL OBJECT-TYPE
       SYNTAX SnmpAdminString (SIZE (0..254))
       MAX-ACCESS read-write
       STATUS current
       DESCRIPTION
           "Provides a link to the user information file, to be downloaded
using Automatic Update.
Relevant only for H323 or SIP controlled devices.
Access: Offline.
AC INI-Param: UserInfoFileUrl"
       ::= {acSysHTTPClient 15}



     acSysHTTPClientDialPlanFileURL OBJECT-TYPE
       SYNTAX SnmpAdminString (SIZE (0..254))
       MAX-ACCESS read-write
       STATUS current
       DESCRIPTION
           "URL for downloading a Dial Plan file using the Automatic Update
facility.
Access: Instant.
AC INI-Param: DialPlanFileUrl"
       ::= {acSysHTTPClient 16}



     acSysHTTPClientTLSPkeyFileUrl OBJECT-TYPE
       SYNTAX SnmpAdminString (SIZE (0..254))
       MAX-ACCESS read-write
       STATUS current
       DESCRIPTION
           "URL for downloading a TLS private key file using the Automatic
Update facility.
Access: Offline.
AC INI-Param: TLSPkeyFileUrl"
       ::= {acSysHTTPClient 17}



     acSysHTTPClientTLSCertFileUrl OBJECT-TYPE
       SYNTAX SnmpAdminString (SIZE (0..254))
       MAX-ACCESS read-write
       STATUS current
       DESCRIPTION
           "URL for downloading a TLS certificate file using the Automatic
Update facility.
Access: Offline.
AC INI-Param: TLSCertFileUrl"
       ::= {acSysHTTPClient 18}



     acSysHTTPClientTLSRootFileUrl OBJECT-TYPE
       SYNTAX SnmpAdminString (SIZE (0..254))
       MAX-ACCESS read-write
       STATUS current
       DESCRIPTION
           "URL for downloading a TLS trusted root certificate file using
the Automatic Update facility.
Access: Offline.
AC INI-Param: TLSRootFileUrl"
       ::= {acSysHTTPClient 19}



     acSysHTTPClientWebLogoFileUrl OBJECT-TYPE
       SYNTAX SnmpAdminString (SIZE (0..254))
       MAX-ACCESS read-write
       STATUS current
       DESCRIPTION
           "URL for downloading a logo file for the web interface using
the Automatic Update facility.
Access: Offline.
AC INI-Param: WebLogoFileUrl"
       ::= {acSysHTTPClient 20}



     acSysHTTPClientVideoFontFileURL OBJECT-TYPE
       SYNTAX SnmpAdminString (SIZE (0..254))
       MAX-ACCESS read-write
       STATUS current
       DESCRIPTION
           "Indicates the URL for downloading a logo file for the web interface
using the Automatic Update facility.
Access: Offline.
AC INI-Param: VideoFontFileUrl"
       ::= {acSysHTTPClient 21}



     acSysHTTPClientV5PortConfFileURL OBJECT-TYPE
       SYNTAX SnmpAdminString (SIZE (0..254))
       MAX-ACCESS read-write
       STATUS current
       DESCRIPTION
           "Provides a link to a software (V5PortConfiguration file) to
be downloaded from a remote server.
Access: Instant.
AC INI-Param: V5PortConfigurationFileURL"
       ::= {acSysHTTPClient 22}



     acSysHTTPClientDataConfigurationFileUrl OBJECT-TYPE
       SYNTAX SnmpAdminString (SIZE (0..254))
       MAX-ACCESS read-write
       STATUS current
       DESCRIPTION
           "Provides a link to a data configuration file to be downloaded
from a remote server using the Automatic Update facility.
Access: Instant.
AC INI-Param: RGCONFFILEURL"
       ::= {acSysHTTPClient 23}



     acSysSNMP OBJECT IDENTIFIER ::= {acSysNetworkConfig 9}


     acSysSNMPKeepAliveTrapPort OBJECT-TYPE
       SYNTAX Unsigned32 (0..65334)
       MAX-ACCESS read-write
       STATUS current
       DESCRIPTION
           "The port to which the keep alive traps are sent to.
Access: Instant.
AC INI-Param: KeepAliveTrapPort"
       ::= {acSysSNMP 1}



     acSysSNMPEmsColdStrartIndication OBJECT-TYPE
       SYNTAX Unsigned32 (0..2147483647)
       MAX-ACCESS read-write
       STATUS current
       DESCRIPTION
           "EMS object to be used as indication to the device's state in
the 'eyes' of the EMS.
 Default - 0.
Access: Instant.
AC INI-Param: N/A"
       ::= {acSysSNMP 2}



     acSysSNMPWanPort OBJECT-TYPE
       SYNTAX Unsigned32 (0..65534)
       MAX-ACCESS read-write
       STATUS current
       DESCRIPTION
           "This parameter specifies the WAN port number for SNMP requests
and responses.
If set to 0, WAN access to SNMP is disabled.
Range = 0 to 65535.
Access: Offline.
AC INI-Param: WanMgmtSnmpPort"
       ::= {acSysSNMP 3}



     acSysVLAN OBJECT IDENTIFIER ::= {acSysNetworkConfig 10}


     acSysVLANOamVlanId OBJECT-TYPE
       SYNTAX Unsigned32 (1..4094)
       MAX-ACCESS read-write
       STATUS obsolete
       DESCRIPTION
           "Sets the OAMP (Operation, Administration, Management and Provisioning)
VLAN identifier.

Range:  1 to 4094.
Access: Online.
AC INI-Param: VLANOAMVLANID"
       ::= {acSysVLAN 1}



     acSysVLANControlVlanId OBJECT-TYPE
       SYNTAX Unsigned32 (1..4094)
       MAX-ACCESS read-write
       STATUS obsolete
       DESCRIPTION
           "Sets the control VLAN identifier.

Range: 1 to 4094.
Access: Online.
AC INI-Param: VLANCONTROLVLANID"
       ::= {acSysVLAN 2}



     acSysVLANMediaVlanId OBJECT-TYPE
       SYNTAX Unsigned32 (1..4094)
       MAX-ACCESS read-write
       STATUS obsolete
       DESCRIPTION
           "Sets the media VLAN identifier. 

Range: 1 to 4094.
Access: Online.
AC INI-Param: VLANMEDIAVLANID"
       ::= {acSysVLAN 3}



     acSysVLANNetworkServiceClassPriority OBJECT-TYPE
       SYNTAX Unsigned32 (0..7)
       MAX-ACCESS read-write
       STATUS deprecated
       DESCRIPTION
           "This parameter is used to set the priority for Network service
class content. 

Range =  0 to 7
Default = 7.
Access: Online.
AC INI-Param: VLANNETWORKSERVICECLASSPRIORITY"
       ::= {acSysVLAN 4}



     acSysVLANPremiumServiceClassMediaPriority OBJECT-TYPE
       SYNTAX Unsigned32 (0..7)
       MAX-ACCESS read-write
       STATUS deprecated
       DESCRIPTION
           "Sets the priority for the Premium service class content and
media traffic. 
Range =  0 to 7
Default = 6.
Access: Online.
AC INI-Param: VLANPREMIUMSERVICECLASSMEDIAPRIORITY"
       ::= {acSysVLAN 5}



     acSysVLANGoldServiceClassPriority OBJECT-TYPE
       SYNTAX Unsigned32 (0..7)
       MAX-ACCESS read-write
       STATUS deprecated
       DESCRIPTION
           "Sets the priority for the Gold service class content.

Range =  0 to 7
Default = 4.
Access: Online.
AC INI-Param: VLANGOLDSERVICECLASSPRIORITY"
       ::= {acSysVLAN 6}



     acSysVLANBronzeServiceClassPriority OBJECT-TYPE
       SYNTAX Unsigned32 (0..7)
       MAX-ACCESS read-write
       STATUS deprecated
       DESCRIPTION
           "Sets the priority for the Bronze service class content.

Range =  0 to 7
Default = 2.
Access: Online.
AC INI-Param: VLANBRONZESERVICECLASSPRIORITY"
       ::= {acSysVLAN 7}



     acSysVLANPremiumServiceClassControlPriority OBJECT-TYPE
       SYNTAX Unsigned32 (0..7)
       MAX-ACCESS read-write
       STATUS deprecated
       DESCRIPTION
           "Sets the priority for the Premium service class content and
control traffic. 

Range =  0 to 7
Default = 6.
Access: Online.
AC INI-Param: VLANPREMIUMSERVICECLASSCONTROLPRIORITY"
       ::= {acSysVLAN 8}



     acSysVLANNetworkServiceClassDiffServ OBJECT-TYPE
       SYNTAX Unsigned32 (0..63)
       MAX-ACCESS read-write
       STATUS current
       DESCRIPTION
           "This parameter is used to set the DiffServ for Network service
class content.

Range =  0 to 63
Default = 48.
Access: Online.
AC INI-Param: NETWORKSERVICECLASSDIFFSERV"
       ::= {acSysVLAN 9}



     acSysVLANPremiumServiceClassMediaDiffServ OBJECT-TYPE
       SYNTAX Unsigned32 (0..63)
       MAX-ACCESS read-write
       STATUS current
       DESCRIPTION
           "This parameter is used to set the DiffServ for Premium service
class content and media traffic.

Range = 0 to 63.
Access: Online.
AC INI-Param: PREMIUMSERVICECLASSMEDIADIFFSERV"
       ::= {acSysVLAN 10}



     acSysVLANPremiumServiceClassControlDiffServ OBJECT-TYPE
       SYNTAX Unsigned32 (0..63)
       MAX-ACCESS read-write
       STATUS current
       DESCRIPTION
           "Sets the DiffServ for the Premium service class content and
control traffic.

Range:  0 to 63.
Access: Online.
AC INI-Param: PREMIUMSERVICECLASSCONTROLDIFFSERV"
       ::= {acSysVLAN 11}



     acSysVLANGoldServiceClassDiffServ OBJECT-TYPE
       SYNTAX Unsigned32 (0..63)
       MAX-ACCESS read-write
       STATUS current
       DESCRIPTION
           "Sets the DiffServ for the Gold service class content.

Range =  0 to 63
Default = 26.
Access: Online.
AC INI-Param: GOLDSERVICECLASSDIFFSERV"
       ::= {acSysVLAN 12}



     acSysVLANBronzeServiceClassDiffServ OBJECT-TYPE
       SYNTAX Unsigned32 (0..63)
       MAX-ACCESS read-write
       STATUS current
       DESCRIPTION
           "Sets the DiffServ for the Bronze service class content.

Range =  0 to 63
Default = 10.
Access: Online.
AC INI-Param: BRONZESERVICECLASSDIFFSERV"
       ::= {acSysVLAN 13}



     acSysVLANVlanNativeVlanId OBJECT-TYPE
       SYNTAX Unsigned32 (1..4094)
       MAX-ACCESS read-write
       STATUS current
       DESCRIPTION
           "Sets the native VLAN identifier.
Access: Online.
AC INI-Param: VLANNATIVEVLANID"
       ::= {acSysVLAN 14}



     acSysVLANMode OBJECT-TYPE
       SYNTAX Unsigned32 (0..1)
       MAX-ACCESS read-write
       STATUS current
       DESCRIPTION
           "Sets the VLAN functionality.

0 = Disable 
1 = Enable.
Access: Offline.
AC INI-Param: VLANMODE"
       ::= {acSysVLAN 15}



     -- ****************************************
     -- acSysVlanMap table declaration
     -- ****************************************
     acSysVlanMapTable OBJECT-TYPE
       SYNTAX SEQUENCE OF AcSysVlanMapEntry
       MAX-ACCESS not-accessible
       STATUS current
       DESCRIPTION
           ""
       ::= {acSysVLAN 21}



     -- ****************************************
     -- acSysVlanMap table entry
     -- ****************************************
     acSysVlanMapEntry OBJECT-TYPE
       SYNTAX AcSysVlanMapEntry
       MAX-ACCESS not-accessible
       STATUS current
       DESCRIPTION
           ""
       INDEX {acSysVlanMapIndex}
       ::= {acSysVlanMapTable 1}



     -- ****************************************
     -- acSysVlanMap TABLE
     -- ****************************************
     AcSysVlanMapEntry ::= SEQUENCE {
       acSysVlanMapIndex                               Unsigned32,
       acSysVlanMapRowStatus                           RowStatus,
       acSysVlanMapAction                              INTEGER,
       acSysVlanMapActionRes                           INTEGER,
       acSysVlanMapDiffServ                            Unsigned32,
       acSysVlanMapVlanPriority                        Unsigned32
     }



     acSysVlanMapIndex OBJECT-TYPE
       SYNTAX Unsigned32 (0..63)
       MAX-ACCESS not-accessible
       STATUS current
       DESCRIPTION
           "Index Field for line. Internal parameter.
AC INI-Param: DiffServToVlanPriority_Index"
       ::= {acSysVlanMapEntry 1}



     acSysVlanMapRowStatus OBJECT-TYPE
       SYNTAX RowStatus
       MAX-ACCESS read-create
       STATUS current
       DESCRIPTION
           "ROWSTATUS field for line. Internal parameter.
AC INI-Param: N/A"
       ::= {acSysVlanMapEntry 2}



     acSysVlanMapAction OBJECT-TYPE
       SYNTAX INTEGER {
                  none(0)

                  }
       MAX-ACCESS read-create
       STATUS current
       DESCRIPTION
           "Mangement Field for ACTIONS. Internal parameter.
AC INI-Param: N/A"
       ::= {acSysVlanMapEntry 3}



     acSysVlanMapActionRes OBJECT-TYPE
       SYNTAX INTEGER {
                  succeeded(0)

                  }
       MAX-ACCESS read-only
       STATUS current
       DESCRIPTION
           "Mangement Field for ACTIONS RESULT. Internal parameter.
AC INI-Param: N/A"
       ::= {acSysVlanMapEntry 4}



     acSysVlanMapDiffServ OBJECT-TYPE
       SYNTAX Unsigned32 (0..63)
       MAX-ACCESS read-create
       STATUS current
       DESCRIPTION
           "Mapping of DiffServ (DSCP) to Vlan Priorities (IEEE 802.1p).
Access: Online.
AC INI-Param: DiffServToVlanPriority_DiffServ"
       ::= {acSysVlanMapEntry 5}



     acSysVlanMapVlanPriority OBJECT-TYPE
       SYNTAX Unsigned32 (0..7)
       MAX-ACCESS read-create
       STATUS current
       DESCRIPTION
           "Mapping of DiffServ (DSCP) to Vlan Priorities (IEEE 802.1p).
Access: Online.
AC INI-Param: DiffServToVlanPriority_VlanPriority"
       ::= {acSysVlanMapEntry 6}



     acSysSCTP OBJECT IDENTIFIER ::= {acSysNetworkConfig 11}


     acSysSCTPHeartBeatInterval OBJECT-TYPE
       SYNTAX Unsigned32 (0..3600)
       MAX-ACCESS read-write
       STATUS current
       DESCRIPTION
           "Defines the SCTP heartbeat interval.

Range: 1 to 3600.
Access: Offline.
AC INI-Param: SCTPHBInterval"
       ::= {acSysSCTP 1}



     acSysSCTPT4SACKTimer OBJECT-TYPE
       SYNTAX Unsigned32 (1..5)
       MAX-ACCESS read-write
       STATUS current
       DESCRIPTION
           "Defines the SCTP T4 SACK timer interval.

Range: 1 to 5.
Access: Offline.
AC INI-Param: SCTPT4SAckTimer"
       ::= {acSysSCTP 2}



     acSysSCTPCheckSumMethod OBJECT-TYPE
       SYNTAX INTEGER {
                  adler(0)
,
                  crc(1)

                  }
       MAX-ACCESS read-write
       STATUS current
       DESCRIPTION
           "Stream Control Transmission Protocol  (SCTP) uses a checksum
mechanism in order to authenticate packets on both sides (the
receiving side and the transmitting side). 

Presently, two checksum mechanisms are available: 

0 = adler32 checksum mechanism
1 = crc32c checksum mechanism (improved mechanism).
Access: Offline.
AC INI-Param: SCTPChecksumMethod"
       ::= {acSysSCTP 3}



     acSysSCTPHostName OBJECT-TYPE
       SYNTAX SnmpAdminString (SIZE (0..255))
       MAX-ACCESS read-write
       STATUS current
       DESCRIPTION
           "When this parameter is set to any value other than an empty
string, SCTP (Stream Control Transmission Protocol) uses the
value as the value of the FQDN (Fully Qualified Domain Name)
parameter attached to the INIT chunk. In this case, the FQDN
parameter replaces any IP address parameters in the INIT
chunk.

This feature enables overcoming NAT problems where the original
IP addresses belonging to the endpoint supports are converted
into pseudo addresses. When this parameter is not set
(default), the INIT chunk is sent without any FQDN parameter.

Range = String[42].
Access: Offline.
AC INI-Param: SCTPHOSTNAME"
       ::= {acSysSCTP 4}



     acSysSCTPAssociationsNum OBJECT-TYPE
       SYNTAX Unsigned32 (1..8)
       MAX-ACCESS read-write
       STATUS current
       DESCRIPTION
           "Defines the maximum number of Stream Control Transmission Protocol
(SCTP) associations that can be opened.
Range: 1 to 8.
Access: Offline.
AC INI-Param: SCTPAssociationsNum"
       ::= {acSysSCTP 5}



     acSysEthernetPort OBJECT IDENTIFIER ::= {acSysNetworkConfig 12}


     acSysEthernetPortPhyConfiguration OBJECT-TYPE
       SYNTAX INTEGER {
                  halfDuplex10BaseT(0)
,
                  fullDuplex10BaseT(1)
,
                  halfDuplex100BaseT(2)
,
                  fullDuplex100BaseT(3)
,
                  autoNegotiate(4)
,
                  fullDuplex1000BaseT(7)

                  }
       MAX-ACCESS read-write
       STATUS current
       DESCRIPTION
           "Controls the Ethernet connection mode type. Auto-negotiate falls
back to Half-Duplex mode (HD) when the opposite port is
not in Auto-negotiate mode. The speed (10 Base-T or 100 Base-TX)
in this mode is always configured correctly.

0 = 10 Base-T half-duplex
1 = 10 Base-T full-duplex
2 = 100 Base-TX half-duplex
3 = 100 Base-TX full-duplex
4 = Auto-negotiate.
Access: Offline.
AC INI-Param: EthernetPhyConfiguration"
       ::= {acSysEthernetPort 1}



     acSysSTUN OBJECT IDENTIFIER ::= {acSysNATTraversal 21}


     acSysSTUNEnable OBJECT-TYPE
       SYNTAX INTEGER {
                  disable(0)
,
                  enable(1)

                  }
       MAX-ACCESS read-write
       STATUS current
       DESCRIPTION
           "This parameter is used to enable the STUN module, used for NAT
traversal of UDP packets.
Access: Offline.
AC INI-Param: ENABLESTUN"
       ::= {acSysSTUN 1}



     acSysSTUNPrimaryServerIP OBJECT-TYPE
       SYNTAX IpAddress
       MAX-ACCESS read-write
       STATUS current
       DESCRIPTION
           "Defines the primary STUN Server IP address.
Range = Legal IP address.
Access: Offline.
AC INI-Param: STUNSERVERPRIMARYIP"
       ::= {acSysSTUN 2}



     acSysSTUNSecondaryServerIP OBJECT-TYPE
       SYNTAX IpAddress
       MAX-ACCESS read-write
       STATUS current
       DESCRIPTION
           "Defines the secondary STUN server IP address.
Range = Legal IP address.
Access: Offline.
AC INI-Param: STUNSERVERSECONDARYIP"
       ::= {acSysSTUN 3}



     acSysSTUNBindingLifeTime OBJECT-TYPE
       SYNTAX Unsigned32 (0..2147483647)
       MAX-ACCESS read-write
       STATUS current
       DESCRIPTION
           "This parameter is used to define the NAT binding lifetime, in
seconds. STUN refreshes the binding information after this
time expires.
Range = 0 - 2592000.
Access: Offline.
AC INI-Param: NATBINDINGDEFAULTTIMEOUT"
       ::= {acSysSTUN 4}



     acSysMiscConfig OBJECT IDENTIFIER ::= {acSystemConfiguration 4}


     acSysDiagnostics OBJECT IDENTIFIER ::= {acSysMiscConfig 1}


     acSysDiagnosticsEnable OBJECT-TYPE
       SYNTAX INTEGER {
                  disabled(0)
,
                  builtInTest(1)
,
                  builtInTestwithPartialFlash(2)
,
                  builtInTestWithSDRAM(3)
,
                  builtInTestOnUtopiaVxb(4)
,
                  internalUse(99)

                  }
       MAX-ACCESS read-write
       STATUS current
       DESCRIPTION
           "Checks the correct functionality of the different hardware components
on the board. On completion of the check, the board
sends an EV_END_BIT value, which contains information on the
test results of each hardware component.

0 = No diagnostics (default)
1 = Perform diagnostics (full test of DSPs, PCM, Switch, LAN,
PHY and Flash)
2 = Perform diagnostics (full test of DSPs, PCM, Switch, LAN,
PHY, but partial, test of Flash, a quicker mode).
Access: Offline.
AC INI-Param: ENABLEDIAGNOSTICS"
       ::= {acSysDiagnostics 1}



     acSysDiagnosticsEnablePerformanceThresholdAlarms OBJECT-TYPE
       SYNTAX INTEGER {
                  disable(0)
,
                  enable(1)

                  }
       MAX-ACCESS read-write
       STATUS current
       DESCRIPTION
           "This parameter enables sending SNMP traps and Syslog messages
when performance of the device is degraded (according to the
configured thresholds).
Access: Instant.
AC INI-Param: PM_EnableThresholdAlarms"
       ::= {acSysDiagnostics 2}



     acSysDiagnosticsListOfActivitiesToLog OBJECT-TYPE
       SYNTAX SnmpAdminString (SIZE (0..32))
       MAX-ACCESS read-write
       STATUS current
       DESCRIPTION
           "This parameter defines what activities are to be reported by
the device in the form of a log message. Parameter format is
 x,y,z-... where x,y,z are activity codes to be reported by
the device.
Supported activity codes:
PVC - Parameter Value Changes.
AFL - Auxiliary Files Loading.
DR - Device Reset.
FB - Flash Burning.
SWU - SoftWareUpdate.
ARD - Access to Restricted Domains.
NAA - Non Authorized Access.
SPC - Sensitive Parameters Changes.
Access: Online.
AC INI-Param: ActivityListToLog"
       ::= {acSysDiagnostics 3}



     acSysGenericINI OBJECT IDENTIFIER ::= {acSysMiscConfig 2}


     acSysGenericINILine OBJECT-TYPE
       SYNTAX SnmpAdminString (SIZE (0..255))
       MAX-ACCESS read-write
       STATUS current
       DESCRIPTION
           "Flexible INI file line.
Access: Offline.
AC INI-Param: N/A"
       ::= {acSysGenericINI 1}



     acSysGenericINISecureStartup OBJECT-TYPE
       SYNTAX INTEGER {
                  disable(0)
,
                  enable(1)

                  }
       MAX-ACCESS read-write
       STATUS current
       DESCRIPTION
           "Enables or disables secure startup mode. In this mode, downloading
of the INI file is restricted to a URL provided in prior
configuration (see parameter IniFileURL) or via DHCP.
Access: Offline.
AC INI-Param: EnableSecureStartup"
       ::= {acSysGenericINI 2}



     acSysLicenseKey OBJECT IDENTIFIER ::= {acSystemConfiguration 5}


     acSysLicenseKeyString OBJECT-TYPE
       SYNTAX SnmpAdminString (SIZE (0..256))
       MAX-ACCESS read-write
       STATUS current
       DESCRIPTION
           "Coded Key specific for board and required features.
Access: Offline.
AC INI-Param: N/A"
       ::= {acSysLicenseKey 1}



     acSysLicenseKeyActiveList OBJECT-TYPE
       SYNTAX SnmpAdminString (SIZE (0..484))
       MAX-ACCESS read-only
       STATUS current
       DESCRIPTION
           "List of all avtivated features.
AC INI-Param: N/A"
       ::= {acSysLicenseKey 2}



     acSysFile OBJECT IDENTIFIER ::= {acSystemConfiguration 6}


     acSysFileCpt OBJECT-TYPE
       SYNTAX SnmpAdminString (SIZE (0..47))
       MAX-ACCESS read-only
       STATUS current
       DESCRIPTION
           "Defines Call Progress Tone filenames (downloaded by TFTP).
AC INI-Param: CALLPROGRESSTONESFILENAME"
       ::= {acSysFile 1}



     acSysFileVp OBJECT-TYPE
       SYNTAX SnmpAdminString (SIZE (0..47))
       MAX-ACCESS read-only
       STATUS current
       DESCRIPTION
           "Defines the name (and path) of the file containing the Voice
Prompts.

Range = String of ASCII characters.
AC INI-Param: VOICEPROMPTSFILENAME"
       ::= {acSysFile 2}



     acSysFilePrerecordedTones OBJECT-TYPE
       SYNTAX SnmpAdminString (SIZE (0..47))
       MAX-ACCESS read-only
       STATUS current
       DESCRIPTION
           "Defines the name (and path) of the file containing the Prerecorded
Tones.
Range = String of ASCII characters.
AC INI-Param: PrerecordedTonesFileName"
       ::= {acSysFile 3}



     acSysFileXml OBJECT-TYPE
       SYNTAX SnmpAdminString (SIZE (0..47))
       MAX-ACCESS read-only
       STATUS current
       DESCRIPTION
           "This parameter is used to indicate the name  of the file containing
the XML file.
AC INI-Param: XMLFileName"
       ::= {acSysFile 4}



     acSysFileExternalCoder OBJECT-TYPE
       SYNTAX SnmpAdminString (SIZE (0..47))
       MAX-ACCESS read-only
       STATUS current
       DESCRIPTION
           "Coders table file name.
AC INI-Param: CODERTBLFILENAME"
       ::= {acSysFile 5}



     acSysFileUserInfo OBJECT-TYPE
       SYNTAX SnmpAdminString (SIZE (0..47))
       MAX-ACCESS read-only
       STATUS current
       DESCRIPTION
           "The file name to be loaded.
AC INI-Param: N/A"
       ::= {acSysFile 6}



     acSysFileDialPlanFileName OBJECT-TYPE
       SYNTAX SnmpAdminString (SIZE (0..47))
       MAX-ACCESS read-only
       STATUS current
       DESCRIPTION
           "This parameter is used to indicate the name of the file containing
the Dial Plan.
AC INI-Param: gDialPlanFileName"
       ::= {acSysFile 7}



     acSysFileTLSPkeyFileName OBJECT-TYPE
       SYNTAX SnmpAdminString (SIZE (0..47))
       MAX-ACCESS read-only
       STATUS current
       DESCRIPTION
           "This parameter defines the name of a private key file (internal).
Set to blank to regenerate the key and certificate.
AC INI-Param: HTTPSPkeyFileName"
       ::= {acSysFile 8}



     acSysFileTLSCertFileName OBJECT-TYPE
       SYNTAX SnmpAdminString (SIZE (0..47))
       MAX-ACCESS read-only
       STATUS current
       DESCRIPTION
           "Defines the name of the HTTPS server certificate file to be
downloaded via TFTP. The file must be in base64-encoded PEM
format.
Range = String[47].
AC INI-Param: HTTPSCertFileName"
       ::= {acSysFile 9}



     acSysFileTLSRootFileName OBJECT-TYPE
       SYNTAX SnmpAdminString (SIZE (0..47))
       MAX-ACCESS read-only
       STATUS current
       DESCRIPTION
           "Defines the name of the HTTPS trusted root certificate file
to be downloaded via TFTP. The file must be in base64-encoded
PEM format.
Range = String[47].
AC INI-Param: HTTPSRootFileName"
       ::= {acSysFile 10}



     acSysFileFirstVideoFontFileName OBJECT-TYPE
       SYNTAX SnmpAdminString (SIZE (0..47))
       MAX-ACCESS read-only
       STATUS current
       DESCRIPTION
           "Indicates the name of the first file containing the Video Font
file index.
AC INI-Param: VideoFontFIleName"
       ::= {acSysFile 11}



     acSysFileSecondVideoFontFileName OBJECT-TYPE
       SYNTAX SnmpAdminString (SIZE (0..47))
       MAX-ACCESS read-only
       STATUS current
       DESCRIPTION
           "Indicates the name of the second file containing the Video Font
file index.
AC INI-Param: VideoFontFIleName"
       ::= {acSysFile 12}



     acSysFileThirdVideoFontFileName OBJECT-TYPE
       SYNTAX SnmpAdminString (SIZE (0..47))
       MAX-ACCESS read-only
       STATUS current
       DESCRIPTION
           "Indicates the name of the first file containing the Video Font
file index.
AC INI-Param: VideoFontFIleName"
       ::= {acSysFile 13}



     acSysFileV5PortConfFileName OBJECT-TYPE
       SYNTAX SnmpAdminString (SIZE (0..47))
       MAX-ACCESS read-only
       STATUS current
       DESCRIPTION
           "Indicates the name and location of the V5 Port Configuration
file.
AC INI-Param: V5PortConfigurationFileName"
       ::= {acSysFile 14}



     acSysSecurity OBJECT IDENTIFIER ::= {acSystemConfiguration 7}


     acSysSecurityTLSVersion OBJECT-TYPE
       SYNTAX Unsigned32 (0..1)
       MAX-ACCESS read-write
       STATUS current
       DESCRIPTION
           "This parameter defines the supported versions of SSL/TLS. 
When set to 0, SSL/TLS handshakes always start with SSL 2.0
and switch to TLS 1.0 if both peers support it. 
When set to 1, TLS 1.0 is the only version supported
 clients attempting to contact the device using SSL 2.0 will
be rejected.

Possible values:
0 = SSL 2.0, SSL 3.0, and TLS 1.0 are supported (default)
1 = TLS 1.0 will always be used.
Access: Offline.
AC INI-Param: TLSVersion"
       ::= {acSysSecurity 1}



     acSysSecurityOcspEnable OBJECT-TYPE
       SYNTAX INTEGER {
                  disabled(0)
,
                  enabled(1)

                  }
       MAX-ACCESS read-write
       STATUS current
       DESCRIPTION
           "Enables or disables certificate checking via OCSP.
Access: Instant.
AC INI-Param: OcspEnable"
       ::= {acSysSecurity 2}



     acSysSecurityOcspServerIPType OBJECT-TYPE
       SYNTAX InetAddressType
       MAX-ACCESS read-write
       STATUS current
       DESCRIPTION
           "This parameter defines the OCSP server's IP address Type.
Currently - IPv4 only.
Access: Instant.
AC INI-Param: N/A"
       ::= {acSysSecurity 3}



     acSysSecurityOcspServerIP OBJECT-TYPE
       SYNTAX InetAddress
       MAX-ACCESS read-write
       STATUS current
       DESCRIPTION
           "This parameter defines the OCSP server's IP address.
Range = Legal IP address.
Access: Instant.
AC INI-Param: OcspServerIP"
       ::= {acSysSecurity 4}



     acSysSecurityOcspServerPort OBJECT-TYPE
       SYNTAX Unsigned32 (1..32767)
       MAX-ACCESS read-write
       STATUS current
       DESCRIPTION
           "This parameter defines the OCSP server's TCP port number.
Range = 1 to 32767
.
Access: Instant.
AC INI-Param: OcspServerPort"
       ::= {acSysSecurity 5}



     acSysSecurityOcspDefaultResponse OBJECT-TYPE
       SYNTAX INTEGER {
                  rejectPeerCertificate(0)
,
                  allowPeerCertificate(1)

                  }
       MAX-ACCESS read-write
       STATUS current
       DESCRIPTION
           "Determines default OCSP behavior when the server cannot be contacted.
0 = reject peer certificate.
1 = allow peer certificate.
.
Access: Instant.
AC INI-Param: OcspDefaultResponse"
       ::= {acSysSecurity 6}



     acSysSecurityTLSFIPS140Mode OBJECT-TYPE
       SYNTAX INTEGER {
                  disabled(0)
,
                  enabled(1)

                  }
       MAX-ACCESS read-write
       STATUS current
       DESCRIPTION
           "Determines whether to enable the FIPS140 mode for TLS.
Access: Offline.
AC INI-Param: TLS_Fips140_Mode"
       ::= {acSysSecurity 7}



     acSysSecurityGenCsrSubjectName OBJECT-TYPE
       SYNTAX SnmpAdminString (SIZE (0..600))
       MAX-ACCESS read-write
       STATUS current
       DESCRIPTION
           "generate CSR Subject Name.
Access: Instant.
AC INI-Param: N/A"
       ::= {acSysSecurity 8}



     acSysSecuritySelfSignedCertificateSubjectName OBJECT-TYPE
       SYNTAX SnmpAdminString (SIZE (0..64))
       MAX-ACCESS read-write
       STATUS current
       DESCRIPTION
           "
Access: Instant.
AC INI-Param: N/A"
       ::= {acSysSecurity 9}



     acSysSecurityOcspSecondaryServerIPType OBJECT-TYPE
       SYNTAX InetAddressType
       MAX-ACCESS read-write
       STATUS current
       DESCRIPTION
           "This parameter defines the OCSP secondary server's IP address
Type.
Currently - IPv4 only.
Access: Instant.
AC INI-Param: N/A"
       ::= {acSysSecurity 10}



     acSysSecurityOcspSecondaryServerIP OBJECT-TYPE
       SYNTAX InetAddress
       MAX-ACCESS read-write
       STATUS current
       DESCRIPTION
           "This parameter defines the OCSP secondary server IP address.
Range = Legal IP address.
Access: Instant.
AC INI-Param: OcspSecondaryServerIP"
       ::= {acSysSecurity 11}



     acSysSecurityHTTPSRequireClientCertificate OBJECT-TYPE
       SYNTAX INTEGER {
                  disable(0)
,
                  enable(1)

                  }
       MAX-ACCESS read-write
       STATUS current
       DESCRIPTION
           "Requires client certificates for HTTPS connection.
The client certificate must be preloaded on the gateway, and
its matching private key must be installed on the managing
computer.
Time and date must be correctly set on the gateway, for the
client certificate to be verified.
Access: Offline.
AC INI-Param: HTTPSRequireClientCertificate"
       ::= {acSysSecurity 12}



     acSysSecurityAUPDVerifyCertificates OBJECT-TYPE
       SYNTAX INTEGER {
                  disable(0)
,
                  enable(1)

                  }
       MAX-ACCESS read-write
       STATUS current
       DESCRIPTION
           "This parameter configures the AutoUpdate facility to verify
server certificates when using HTTPS.
Access: Offline.
AC INI-Param: AUPDVerifyCertificates"
       ::= {acSysSecurity 13}



     acSysIKE OBJECT IDENTIFIER ::= {acSysSecurity 21}


     -- ****************************************
     -- acSysIKEPolicy table declaration
     -- ****************************************
     acSysIKEPolicyTable OBJECT-TYPE
       SYNTAX SEQUENCE OF AcSysIKEPolicyEntry
       MAX-ACCESS not-accessible
       STATUS deprecated
       DESCRIPTION
           ""
       ::= {acSysIKE 1}



     -- ****************************************
     -- acSysIKEPolicy table entry
     -- ****************************************
     acSysIKEPolicyEntry OBJECT-TYPE
       SYNTAX AcSysIKEPolicyEntry
       MAX-ACCESS not-accessible
       STATUS deprecated
       DESCRIPTION
           ""
       INDEX {acSysIKEPolicyIndex}
       ::= {acSysIKEPolicyTable 1}



     -- ****************************************
     -- acSysIKEPolicy TABLE
     -- ****************************************
     AcSysIKEPolicyEntry ::= SEQUENCE {
       acSysIKEPolicyIndex                             Unsigned32,
       acSysIKEPolicyRowStatus                         RowStatus,
       acSysIKEPolicyAction                            INTEGER,
       acSysIKEPolicyActionRes                         INTEGER,
       acSysIKEPolicyShardKey                          SnmpAdminString,
       acSysIKEPolicyLifeInSeconds                     Unsigned32,
       acSysIKEPolicyLifeInKB                          Unsigned32,
       acSysIKEPolicyProposal0Encryption               INTEGER,
       acSysIKEPolicyProposal1Encryption               INTEGER,
       acSysIKEPolicyProposal2Encryption               INTEGER,
       acSysIKEPolicyProposal3Encryption               INTEGER,
       acSysIKEPolicyProposal0Authentication           INTEGER,
       acSysIKEPolicyProposal1Authentication           INTEGER,
       acSysIKEPolicyProposal2Authentication           INTEGER,
       acSysIKEPolicyProposal3Authentication           INTEGER,
       acSysIKEPolicyProposal0DHGroup                  INTEGER,
       acSysIKEPolicyProposal1DHGroup                  INTEGER,
       acSysIKEPolicyProposal2DHGroup                  INTEGER,
       acSysIKEPolicyProposal3DHGroup                  INTEGER,
       acSysIKEPolicyAuthenticationMethod              INTEGER
     }



     acSysIKEPolicyIndex OBJECT-TYPE
       SYNTAX Unsigned32 (0..19)
       MAX-ACCESS not-accessible
       STATUS deprecated
       DESCRIPTION
           "This parameter is used for the Internet Key Encryption (IKE)
Index Field for line. Internal parameter.
AC INI-Param: IKE_DB_INDEX"
       ::= {acSysIKEPolicyEntry 1}



     acSysIKEPolicyRowStatus OBJECT-TYPE
       SYNTAX RowStatus
       MAX-ACCESS read-create
       STATUS deprecated
       DESCRIPTION
           "This parameter is used for the Internet Key Encryption (IKE)
ROWSTATUS Field for line. Internal parameter.
AC INI-Param: IKE_DB_ROWSTATUS"
       ::= {acSysIKEPolicyEntry 2}



     acSysIKEPolicyAction OBJECT-TYPE
       SYNTAX INTEGER {
                  none(0)

                  }
       MAX-ACCESS read-create
       STATUS deprecated
       DESCRIPTION
           "This parameter is used for the Internet Key Encryption (IKE)
Mangement Field for ACTIONS. Internal parameter.
AC INI-Param: IKE_DB_ACTION"
       ::= {acSysIKEPolicyEntry 3}



     acSysIKEPolicyActionRes OBJECT-TYPE
       SYNTAX INTEGER {
                  succeeded(0)

                  }
       MAX-ACCESS read-only
       STATUS deprecated
       DESCRIPTION
           "This parameter is used for the Internet Key Encryption (IKE)
Mangement Field for ACTIONS RESULT. Internal parameter.
AC INI-Param: IKE_DB_ACTION_RESULT"
       ::= {acSysIKEPolicyEntry 4}



     acSysIKEPolicyShardKey OBJECT-TYPE
       SYNTAX SnmpAdminString (SIZE (0..80))
       MAX-ACCESS read-create
       STATUS deprecated
       DESCRIPTION
           "IKE Policy - Shared Key.
Access: Instant.
AC INI-Param: IKEPOLICYSHAREDKEY"
       ::= {acSysIKEPolicyEntry 5}



     acSysIKEPolicyLifeInSeconds OBJECT-TYPE
       SYNTAX Unsigned32 (0..2147483647)
       MAX-ACCESS read-create
       STATUS deprecated
       DESCRIPTION
           "IKE Policy - IKE SA LifeTime in seconds.
Access: Instant.
AC INI-Param: IKEPOLICYLIFEINSEC"
       ::= {acSysIKEPolicyEntry 6}



     acSysIKEPolicyLifeInKB OBJECT-TYPE
       SYNTAX Unsigned32 (0..2147483647)
       MAX-ACCESS read-create
       STATUS deprecated
       DESCRIPTION
           "IKE Policy - IKE SA LifeTime in KB.
Access: Instant.
AC INI-Param: IKEPOLICYLIFEINKB"
       ::= {acSysIKEPolicyEntry 7}



     acSysIKEPolicyProposal0Encryption OBJECT-TYPE
       SYNTAX INTEGER {
                  dES-CBC(1)
,
                  triple-DES-CBC(2)
,
                  aES(3)
,
                  not-set(10)

                  }
       MAX-ACCESS read-create
       STATUS deprecated
       DESCRIPTION
           "IKE Policy - Proposal 0 encryption type.
Access: Instant.
AC INI-Param: IKEPOLICYPROPOSALENCRYPTION_0"
       ::= {acSysIKEPolicyEntry 8}



     acSysIKEPolicyProposal1Encryption OBJECT-TYPE
       SYNTAX INTEGER {
                  dES-CBC(1)
,
                  triple-DES-CBC(2)
,
                  aES(3)
,
                  not-set(10)

                  }
       MAX-ACCESS read-create
       STATUS deprecated
       DESCRIPTION
           "IKE Policy - Proposal 1 encryption type.
Access: Instant.
AC INI-Param: IKEPOLICYPROPOSALENCRYPTION_1"
       ::= {acSysIKEPolicyEntry 9}



     acSysIKEPolicyProposal2Encryption OBJECT-TYPE
       SYNTAX INTEGER {
                  dES-CBC(1)
,
                  triple-DES-CBC(2)
,
                  aES(3)
,
                  not-set(10)

                  }
       MAX-ACCESS read-create
       STATUS deprecated
       DESCRIPTION
           "IKE Policy - Proposal 2 encryption type.
Access: Instant.
AC INI-Param: IKEPOLICYPROPOSALENCRYPTION_2"
       ::= {acSysIKEPolicyEntry 10}



     acSysIKEPolicyProposal3Encryption OBJECT-TYPE
       SYNTAX INTEGER {
                  dES-CBC(1)
,
                  triple-DES-CBC(2)
,
                  aES(3)
,
                  not-set(10)

                  }
       MAX-ACCESS read-create
       STATUS deprecated
       DESCRIPTION
           "IKE Policy - Proposal 3 encryption type.
Access: Instant.
AC INI-Param: IKEPOLICYPROPOSALENCRYPTION_3"
       ::= {acSysIKEPolicyEntry 11}



     acSysIKEPolicyProposal0Authentication OBJECT-TYPE
       SYNTAX INTEGER {
                  hMAC-SHA-1-96(2)
,
                  hMAC-MD5-96(4)
,
                  not-set(10)

                  }
       MAX-ACCESS read-create
       STATUS deprecated
       DESCRIPTION
           "IKE Policy - Proposal 0 authentication type.
Access: Instant.
AC INI-Param: IKEPOLICYPROPOSALAUTHENTICATION_0"
       ::= {acSysIKEPolicyEntry 12}



     acSysIKEPolicyProposal1Authentication OBJECT-TYPE
       SYNTAX INTEGER {
                  hMAC-SHA-1-96(2)
,
                  hMAC-MD5-96(4)
,
                  not-set(10)

                  }
       MAX-ACCESS read-create
       STATUS deprecated
       DESCRIPTION
           "IKE Policy - Proposal 1 authentication type.
Access: Instant.
AC INI-Param: IKEPOLICYPROPOSALAUTHENTICATION_1"
       ::= {acSysIKEPolicyEntry 13}



     acSysIKEPolicyProposal2Authentication OBJECT-TYPE
       SYNTAX INTEGER {
                  hMAC-SHA-1-96(2)
,
                  hMAC-MD5-96(4)
,
                  not-set(10)

                  }
       MAX-ACCESS read-create
       STATUS deprecated
       DESCRIPTION
           "IKE Policy - Proposal 2 authentication type.
Access: Instant.
AC INI-Param: IKEPOLICYPROPOSALAUTHENTICATION_2"
       ::= {acSysIKEPolicyEntry 14}



     acSysIKEPolicyProposal3Authentication OBJECT-TYPE
       SYNTAX INTEGER {
                  hMAC-SHA-1-96(2)
,
                  hMAC-MD5-96(4)
,
                  not-set(10)

                  }
       MAX-ACCESS read-create
       STATUS deprecated
       DESCRIPTION
           "IKE Policy - Proposal 3 authentication type.
Access: Instant.
AC INI-Param: IKEPOLICYPROPOSALAUTHENTICATION_3"
       ::= {acSysIKEPolicyEntry 15}



     acSysIKEPolicyProposal0DHGroup OBJECT-TYPE
       SYNTAX INTEGER {
                  dH-786-BIT(0)
,
                  dH-1024-BIT(1)
,
                  not-set(10)

                  }
       MAX-ACCESS read-create
       STATUS deprecated
       DESCRIPTION
           "IKE Policy - Proposal 0 Diffie Hellman Group.
Access: Instant.
AC INI-Param: IKEPOLICYPROPOSALDHGROUP_0"
       ::= {acSysIKEPolicyEntry 16}



     acSysIKEPolicyProposal1DHGroup OBJECT-TYPE
       SYNTAX INTEGER {
                  dH-786-BIT(0)
,
                  dH-1024-BIT(1)
,
                  not-set(10)

                  }
       MAX-ACCESS read-create
       STATUS deprecated
       DESCRIPTION
           "IKE Policy - Proposal 1 Diffie Hellman Group.
Access: Instant.
AC INI-Param: IKEPOLICYPROPOSALDHGROUP_1"
       ::= {acSysIKEPolicyEntry 17}



     acSysIKEPolicyProposal2DHGroup OBJECT-TYPE
       SYNTAX INTEGER {
                  dH-786-BIT(0)
,
                  dH-1024-BIT(1)
,
                  not-set(10)

                  }
       MAX-ACCESS read-create
       STATUS deprecated
       DESCRIPTION
           "IKE Policy - Proposal 2 Diffie Hellman Group.
Access: Instant.
AC INI-Param: IKEPOLICYPROPOSALDHGROUP_2"
       ::= {acSysIKEPolicyEntry 18}



     acSysIKEPolicyProposal3DHGroup OBJECT-TYPE
       SYNTAX INTEGER {
                  dH-786-BIT(0)
,
                  dH-1024-BIT(1)
,
                  not-set(10)

                  }
       MAX-ACCESS read-create
       STATUS deprecated
       DESCRIPTION
           "IKE Policy - Proposal 3 Diffie Hellman Group.
Access: Instant.
AC INI-Param: IKEPOLICYPROPOSALDHGROUP_3"
       ::= {acSysIKEPolicyEntry 19}



     acSysIKEPolicyAuthenticationMethod OBJECT-TYPE
       SYNTAX INTEGER {
                  presharedKey(0)
,
                  rsaSignature(1)

                  }
       MAX-ACCESS read-create
       STATUS deprecated
       DESCRIPTION
           "This parameter is used for Internet Key Encryption (IKE) Policy
- IKE Authentication Method (Preshared key/ RSA).
Access: Offline.
AC INI-Param: IKEPOLICYAUTHENTICATIONMETHOD"
       ::= {acSysIKEPolicyEntry 20}



     acSysIPSec OBJECT IDENTIFIER ::= {acSysSecurity 22}


     acSysIPSecEnable OBJECT-TYPE
       SYNTAX INTEGER {
                  no(0)
,
                  yes(1)

                  }
       MAX-ACCESS read-write
       STATUS current
       DESCRIPTION
           "IPsec Enable flag.
Access: Offline.
AC INI-Param: ENABLEIPSEC"
       ::= {acSysIPSec 1}



     acSysIPSecDpdMode OBJECT-TYPE
       SYNTAX INTEGER {
                   disabled(0)
,
                  periodic(1)
,
                  ondemand(2)

                  }
       MAX-ACCESS read-write
       STATUS current
       DESCRIPTION
           "IPsec Dead Peer Detection (RFC 3706) - Mode of Operation.
One of the following values: '0' - Disabled (Default)
 '1' - Periodic
 '2' - On demand.
Access: Instant.
AC INI-Param: IPSECDPDMODE"
       ::= {acSysIPSec 2}



     acSysIPSecIKECertificateExtValidate OBJECT-TYPE
       SYNTAX INTEGER {
                  disabled(0)
,
                  enabled(1)

                  }
       MAX-ACCESS read-write
       STATUS current
       DESCRIPTION
           "Enables or disables certificate extension checking for IKE.
Access: Instant.
AC INI-Param: IKEcertificateExtValidate"
       ::= {acSysIPSec 3}



     -- ****************************************
     -- acSysIPSecSPD table declaration
     -- ****************************************
     acSysIPSecSPDTable OBJECT-TYPE
       SYNTAX SEQUENCE OF AcSysIPSecSPDEntry
       MAX-ACCESS not-accessible
       STATUS deprecated
       DESCRIPTION
           ""
       ::= {acSysIPSec 21}



     -- ****************************************
     -- acSysIPSecSPD table entry
     -- ****************************************
     acSysIPSecSPDEntry OBJECT-TYPE
       SYNTAX AcSysIPSecSPDEntry
       MAX-ACCESS not-accessible
       STATUS deprecated
       DESCRIPTION
           ""
       INDEX {acSysIPSecSPDIndex}
       ::= {acSysIPSecSPDTable 1}



     -- ****************************************
     -- acSysIPSecSPD TABLE
     -- ****************************************
     AcSysIPSecSPDEntry ::= SEQUENCE {
       acSysIPSecSPDIndex                              Unsigned32,
       acSysIPSecSPDRowStatus                          RowStatus,
       acSysIPSecSPDAction                             INTEGER,
       acSysIPSecSPDActionRes                          INTEGER,
       acSysIPSecSPDPolicyRemoteIPAddr                 SnmpAdminString,
       acSysIPSecSPDPolicySrcPort                      Unsigned32,
       acSysIPSecSPDPolicyDestPort                     Unsigned32,
       acSysIPSecSPDPolicyProtocol                     Unsigned32,
       acSysIPSecSPDKeyExchangeMethodIndex             Unsigned32,
       acSysIPSecSPDLifeInSeconds                      Unsigned32,
       acSysIPSecSPDLifeInKB                           Unsigned32,
       acSysIPSecSPDProposal0Encryption                INTEGER,
       acSysIPSecSPDProposal1Encryption                INTEGER,
       acSysIPSecSPDProposal2Encryption                INTEGER,
       acSysIPSecSPDProposal3Encryption                INTEGER,
       acSysIPSecSPDProposal0Authentication            INTEGER,
       acSysIPSecSPDProposal1Authentication            INTEGER,
       acSysIPSecSPDProposal2Authentication            INTEGER,
       acSysIPSecSPDProposal3Authentication            INTEGER,
       acSysIPSecSPDPolicyLocalIPAddrType              INTEGER,
       acSysIPSecSPDMode                               INTEGER,
       acSysIPSecSPDPolicyRemoteTunnelIPAddress        IpAddress,
       acSysIPSecSPDPolicyLocalTunnelIPAddress         IpAddress,
       acSysIPSecSPDPolicyRemoteTunnelSubnetMask       IpAddress
     }



     acSysIPSecSPDIndex OBJECT-TYPE
       SYNTAX Unsigned32 (0..19)
       MAX-ACCESS not-accessible
       STATUS deprecated
       DESCRIPTION
           "Security Policy Database (SPD) Index Field for line. Internal
parameter.
AC INI-Param: SPD_INDEX"
       ::= {acSysIPSecSPDEntry 1}



     acSysIPSecSPDRowStatus OBJECT-TYPE
       SYNTAX RowStatus
       MAX-ACCESS read-create
       STATUS deprecated
       DESCRIPTION
           "Security Policy Database (SPD) ROWSTATUS field for line. Internal
parameter.
AC INI-Param: SPD_ROWSTATUS"
       ::= {acSysIPSecSPDEntry 2}



     acSysIPSecSPDAction OBJECT-TYPE
       SYNTAX INTEGER {
                  none(0)

                  }
       MAX-ACCESS read-create
       STATUS deprecated
       DESCRIPTION
           "Security Policy Database (SPD) Mangement Field for ACTIONS.
Internal parameter.
AC INI-Param: SPD_ACTION"
       ::= {acSysIPSecSPDEntry 3}



     acSysIPSecSPDActionRes OBJECT-TYPE
       SYNTAX INTEGER {
                  succeeded(0)

                  }
       MAX-ACCESS read-only
       STATUS deprecated
       DESCRIPTION
           "Security Policy Database (SPD) Mangement Field for ACTIONS RESULT.
Internal parameter.
AC INI-Param: SPD_ACTION_RESULT"
       ::= {acSysIPSecSPDEntry 4}



     acSysIPSecSPDPolicyRemoteIPAddr OBJECT-TYPE
       SYNTAX SnmpAdminString (SIZE (0..99))
       MAX-ACCESS read-create
       STATUS deprecated
       DESCRIPTION
           "This parameter is used for Secure Internet Protocol (IPsec)
Policy Policy - Remote IP address as IP or Host Name.
Access: Instant.
AC INI-Param: IPSECPOLICYREMOTEIPADDRESS"
       ::= {acSysIPSecSPDEntry 5}



     acSysIPSecSPDPolicySrcPort OBJECT-TYPE
       SYNTAX Unsigned32 (0..65536)
       MAX-ACCESS read-create
       STATUS deprecated
       DESCRIPTION
           "This parameter is used for Secure Internet Protocol (IPsec)
Policy Policy - Source Port.
Access: Instant.
AC INI-Param: IPSECPOLICYSRCPORT"
       ::= {acSysIPSecSPDEntry 6}



     acSysIPSecSPDPolicyDestPort OBJECT-TYPE
       SYNTAX Unsigned32 (0..65536)
       MAX-ACCESS read-create
       STATUS deprecated
       DESCRIPTION
           "This parameter is used for Secure Internet Protocol (IPsec)
Policy Policy - Destination Port.
Access: Instant.
AC INI-Param: IPSECPOLICYDSTPORT"
       ::= {acSysIPSecSPDEntry 7}



     acSysIPSecSPDPolicyProtocol OBJECT-TYPE
       SYNTAX Unsigned32 (0..255)
       MAX-ACCESS read-create
       STATUS deprecated
       DESCRIPTION
           "This parameter is used for Secure Internet Protocol (IPsec)
Policy Policy - Protocol.
Access: Instant.
AC INI-Param: IPSECPOLICYPROTOCOL"
       ::= {acSysIPSecSPDEntry 8}



     acSysIPSecSPDKeyExchangeMethodIndex OBJECT-TYPE
       SYNTAX Unsigned32 (0..2147483647)
       MAX-ACCESS read-create
       STATUS deprecated
       DESCRIPTION
           "This parameter is used for the Secure Internet Protocol (IPsec)
Policy - Index into the Key Exchange Method Table (IKE Table).
Access: Offline.
AC INI-Param: IPSECPOLICYKEYEXCHANGEMETHODINDEX"
       ::= {acSysIPSecSPDEntry 9}



     acSysIPSecSPDLifeInSeconds OBJECT-TYPE
       SYNTAX Unsigned32 (0..2147483647)
       MAX-ACCESS read-create
       STATUS deprecated
       DESCRIPTION
           "IPsec Policy - IPSec SA LifeTime in seconds.
Access: Instant.
AC INI-Param: IPSECPOLICYLIFEINSEC"
       ::= {acSysIPSecSPDEntry 10}



     acSysIPSecSPDLifeInKB OBJECT-TYPE
       SYNTAX Unsigned32 (0..2147483647)
       MAX-ACCESS read-create
       STATUS deprecated
       DESCRIPTION
           "IPsec Policy - IPSec SA LifeTime in KB.
Access: Instant.
AC INI-Param: IPSECPOLICYLIFEINKB"
       ::= {acSysIPSecSPDEntry 11}



     acSysIPSecSPDProposal0Encryption OBJECT-TYPE
       SYNTAX INTEGER {
                  none(0)
,
                  dES-CBC(1)
,
                  triple-DES-CBC(2)
,
                  aES(3)
,
                  not-set(10)

                  }
       MAX-ACCESS read-create
       STATUS deprecated
       DESCRIPTION
           "IPsec Policy - Proposal 0 encryption type.
Access: Instant.
AC INI-Param: IPSECPOLICYPROPOSALENCRYPTION_0"
       ::= {acSysIPSecSPDEntry 12}



     acSysIPSecSPDProposal1Encryption OBJECT-TYPE
       SYNTAX INTEGER {
                  none(0)
,
                  dES-CBC(1)
,
                  triple-DES-CBC(2)
,
                  aES(3)
,
                  not-set(10)

                  }
       MAX-ACCESS read-create
       STATUS deprecated
       DESCRIPTION
           "IPsec Policy - Proposal 1 encryption type.
Access: Instant.
AC INI-Param: IPSECPOLICYPROPOSALENCRYPTION_1"
       ::= {acSysIPSecSPDEntry 13}



     acSysIPSecSPDProposal2Encryption OBJECT-TYPE
       SYNTAX INTEGER {
                  none(0)
,
                  dES-CBC(1)
,
                  triple-DES-CBC(2)
,
                  aES(3)
,
                  not-set(10)

                  }
       MAX-ACCESS read-create
       STATUS deprecated
       DESCRIPTION
           "IPsec Policy - Proposal 2 encryption type.
Access: Instant.
AC INI-Param: IPSECPOLICYPROPOSALENCRYPTION_2"
       ::= {acSysIPSecSPDEntry 14}



     acSysIPSecSPDProposal3Encryption OBJECT-TYPE
       SYNTAX INTEGER {
                  none(0)
,
                  dES-CBC(1)
,
                  triple-DES-CBC(2)
,
                  aES(3)
,
                  not-set(10)

                  }
       MAX-ACCESS read-create
       STATUS deprecated
       DESCRIPTION
           "IPsec Policy - Proposal 3 encryption type.
Access: Instant.
AC INI-Param: IPSECPOLICYPROPOSALENCRYPTION_3"
       ::= {acSysIPSecSPDEntry 15}



     acSysIPSecSPDProposal0Authentication OBJECT-TYPE
       SYNTAX INTEGER {
                  hMAC-SHA-1-96(2)
,
                  hMAC-MD5-96(4)
,
                  not-set(10)

                  }
       MAX-ACCESS read-create
       STATUS deprecated
       DESCRIPTION
           "IPsec Policy - Proposal 0 authentication type.
Access: Instant.
AC INI-Param: IPSECPOLICYPROPOSALAUTHENTICATION_0"
       ::= {acSysIPSecSPDEntry 16}



     acSysIPSecSPDProposal1Authentication OBJECT-TYPE
       SYNTAX INTEGER {
                  hMAC-SHA-1-96(2)
,
                  hMAC-MD5-96(4)
,
                  not-set(10)

                  }
       MAX-ACCESS read-create
       STATUS deprecated
       DESCRIPTION
           "IPsec Policy - Proposal 0 authentication type.
Access: Instant.
AC INI-Param: IPSECPOLICYPROPOSALAUTHENTICATION_1"
       ::= {acSysIPSecSPDEntry 17}



     acSysIPSecSPDProposal2Authentication OBJECT-TYPE
       SYNTAX INTEGER {
                  hMAC-SHA-1-96(2)
,
                  hMAC-MD5-96(4)
,
                  not-set(10)

                  }
       MAX-ACCESS read-create
       STATUS deprecated
       DESCRIPTION
           "IPsec Policy - Proposal 0 authentication type.
Access: Instant.
AC INI-Param: IPSECPOLICYPROPOSALAUTHENTICATION_2"
       ::= {acSysIPSecSPDEntry 18}



     acSysIPSecSPDProposal3Authentication OBJECT-TYPE
       SYNTAX INTEGER {
                  hMAC-SHA-1-96(2)
,
                  hMAC-MD5-96(4)
,
                  not-set(10)

                  }
       MAX-ACCESS read-create
       STATUS deprecated
       DESCRIPTION
           "IPsec Policy - Proposal 0 authentication type.
Access: Instant.
AC INI-Param: IPSECPOLICYPROPOSALAUTHENTICATION_3"
       ::= {acSysIPSecSPDEntry 19}



     acSysIPSecSPDPolicyLocalIPAddrType OBJECT-TYPE
       SYNTAX INTEGER {
                  oam(0)
,
                  control(2)

                  }
       MAX-ACCESS read-create
       STATUS deprecated
       DESCRIPTION
           "This parameter is used for Secure Internet Protocol (IPsec)
Policy - Local IP address type (OAM/Control).
Access: Offline.
AC INI-Param: IPSECPOLICYLOCALIPADDRESSTYPE"
       ::= {acSysIPSecSPDEntry 20}



     acSysIPSecSPDMode OBJECT-TYPE
       SYNTAX INTEGER {
                  transport(0)
,
                  tunneling(1)

                  }
       MAX-ACCESS read-create
       STATUS deprecated
       DESCRIPTION
           "This parameter is used for Secure Internet Protocol (IPsec)
Policy - Mode of Operation (Transport/Tunneling). '0' - Transport
 '1' - Tunneling.
Access: Instant.
AC INI-Param: IPSECMODE"
       ::= {acSysIPSecSPDEntry 21}



     acSysIPSecSPDPolicyRemoteTunnelIPAddress OBJECT-TYPE
       SYNTAX IpAddress
       MAX-ACCESS read-create
       STATUS deprecated
       DESCRIPTION
           "This parameter is used for Secure Internet Protocol (IPsec)
Policy - IP Address of the Remote IPSec Tunnel Endpoint.
Access: Instant.
AC INI-Param: IPSECPOLICYREMOTETUNNELIPADDRESS"
       ::= {acSysIPSecSPDEntry 22}



     acSysIPSecSPDPolicyLocalTunnelIPAddress OBJECT-TYPE
       SYNTAX IpAddress
       MAX-ACCESS read-create
       STATUS deprecated
       DESCRIPTION
           "This parameter is used for Secure Internet Protocol (IPsec)
Policy - IP Address of the Remote IPSec Tunnel Endpoint.
Access: Instant.
AC INI-Param: IPSECPOLICYLOCALTUNNELIPADDRESS"
       ::= {acSysIPSecSPDEntry 23}



     acSysIPSecSPDPolicyRemoteTunnelSubnetMask OBJECT-TYPE
       SYNTAX IpAddress
       MAX-ACCESS read-create
       STATUS deprecated
       DESCRIPTION
           "This parameter is used for Secure Internet Protocol (IPsec)
Policy - Subnet Mask of the Remote IPSec Address.
Access: Instant.
AC INI-Param: IPSECPOLICYREMOTESUBNETMASK"
       ::= {acSysIPSecSPDEntry 24}



     -- ****************************************
     -- acSysIPsecProposal table declaration
     -- ****************************************
     acSysIPsecProposalTable OBJECT-TYPE
       SYNTAX SEQUENCE OF AcSysIPsecProposalEntry
       MAX-ACCESS not-accessible
       STATUS current
       DESCRIPTION
           "IPsec Proposal table"
       ::= {acSysIPSec 22}



     -- ****************************************
     -- acSysIPsecProposal table entry
     -- ****************************************
     acSysIPsecProposalEntry OBJECT-TYPE
       SYNTAX AcSysIPsecProposalEntry
       MAX-ACCESS not-accessible
       STATUS current
       DESCRIPTION
           ""
       INDEX {acSysIPsecProposalIndex}
       ::= {acSysIPsecProposalTable 1}



     -- ****************************************
     -- acSysIPsecProposal TABLE
     -- ****************************************
     AcSysIPsecProposalEntry ::= SEQUENCE {
       acSysIPsecProposalIndex                         Unsigned32,
       acSysIPsecProposalRowStatus                     RowStatus,
       acSysIPsecProposalAction                        INTEGER,
       acSysIPsecProposalActionRes                     INTEGER,
       acSysIPsecProposalEncryptionAlgorithm           INTEGER,
       acSysIPsecProposalAuthenticationAlgorithm       INTEGER,
       acSysIPsecProposalDiffieHellmanGroup            INTEGER
     }



     acSysIPsecProposalIndex OBJECT-TYPE
       SYNTAX Unsigned32 (0..4)
       MAX-ACCESS not-accessible
       STATUS current
       DESCRIPTION
           "Index Field for line.
AC INI-Param: IPsecProposalTable_Index"
       ::= {acSysIPsecProposalEntry 1}



     acSysIPsecProposalRowStatus OBJECT-TYPE
       SYNTAX RowStatus
       MAX-ACCESS read-create
       STATUS current
       DESCRIPTION
           "ROWSTATUS Field for line.
AC INI-Param: IPsecProposalTable_RowStatus"
       ::= {acSysIPsecProposalEntry 2}



     acSysIPsecProposalAction OBJECT-TYPE
       SYNTAX INTEGER {
                  none(0)

                  }
       MAX-ACCESS read-create
       STATUS current
       DESCRIPTION
           "Mangement Field for ACTIONS.
AC INI-Param: IPsecProposalTable_Action"
       ::= {acSysIPsecProposalEntry 3}



     acSysIPsecProposalActionRes OBJECT-TYPE
       SYNTAX INTEGER {
                  succeeded(0)

                  }
       MAX-ACCESS read-only
       STATUS current
       DESCRIPTION
           "Mangement Field for ACTIONS RESULT.
AC INI-Param: IPsecProposalTable_ActionRes"
       ::= {acSysIPsecProposalEntry 4}



     acSysIPsecProposalEncryptionAlgorithm OBJECT-TYPE
       SYNTAX INTEGER {
                  none(0)
,
                  desCbc(1)
,
                  tripleDesCbc(2)
,
                  aes(3)

                  }
       MAX-ACCESS read-create
       STATUS current
       DESCRIPTION
           "Selects the encryption (privacy) algorithm to use.
Access: Online.
AC INI-Param: IPsecProposalTable_EncryptionAlgorithm"
       ::= {acSysIPsecProposalEntry 5}



     acSysIPsecProposalAuthenticationAlgorithm OBJECT-TYPE
       SYNTAX INTEGER {
                  none(0)
,
                  hmacSha1-96(2)
,
                  hmacMd5-96(4)

                  }
       MAX-ACCESS read-create
       STATUS current
       DESCRIPTION
           "Selects the message authentication (integrity) algorithm to
use.
Access: Online.
AC INI-Param: IPsecProposalTable_AuthenticationAlgorithm"
       ::= {acSysIPsecProposalEntry 6}



     acSysIPsecProposalDiffieHellmanGroup OBJECT-TYPE
       SYNTAX INTEGER {
                  group1-768Bits(0)
,
                  group2-1024Bits(1)

                  }
       MAX-ACCESS read-create
       STATUS current
       DESCRIPTION
           "Selects the Diffie-Hellman group to use.
Access: Online.
AC INI-Param: IPsecProposalTable_DHGroup"
       ::= {acSysIPsecProposalEntry 7}



     -- ****************************************
     -- acSysIPsecSA table declaration
     -- ****************************************
     acSysIPsecSATable OBJECT-TYPE
       SYNTAX SEQUENCE OF AcSysIPsecSAEntry
       MAX-ACCESS not-accessible
       STATUS current
       DESCRIPTION
           "IPsec SA table"
       ::= {acSysIPSec 23}



     -- ****************************************
     -- acSysIPsecSA table entry
     -- ****************************************
     acSysIPsecSAEntry OBJECT-TYPE
       SYNTAX AcSysIPsecSAEntry
       MAX-ACCESS not-accessible
       STATUS current
       DESCRIPTION
           ""
       INDEX {acSysIPsecSAIndex}
       ::= {acSysIPsecSATable 1}



     -- ****************************************
     -- acSysIPsecSA TABLE
     -- ****************************************
     AcSysIPsecSAEntry ::= SEQUENCE {
       acSysIPsecSAIndex                               Unsigned32,
       acSysIPsecSARowStatus                           RowStatus,
       acSysIPsecSAAction                              Unsigned32,
       acSysIPsecSAActionRes                           Unsigned32,
       acSysIPsecSARemoteEndpointAddress               SnmpAdminString,
       acSysIPsecSAAuthenticationMethod                INTEGER,
       acSysIPsecSASharedKey                           SnmpAdminString,
       acSysIPsecSASourcePort                          Unsigned32,
       acSysIPsecSADestPort                            Unsigned32,
       acSysIPsecSAProtocol                            Unsigned32,
       acSysIPsecSAPhase1SaLifetimeInSec               Unsigned32,
       acSysIPsecSAPhase2SaLifetimeInSec               Unsigned32,
       acSysIPsecSAPhase2SaLifetimeInKB                Unsigned32,
       acSysIPsecSADPDmode                             INTEGER,
       acSysIPsecSAIPsecMode                           INTEGER,
       acSysIPsecSARemoteTunnelAddress                 SnmpAdminString,
       acSysIPsecSARemoteSubnetIPAddress               SnmpAdminString,
       acSysIPsecSARemoteSubnetPrefixLength            Unsigned32
     }



     acSysIPsecSAIndex OBJECT-TYPE
       SYNTAX Unsigned32 (0..20)
       MAX-ACCESS not-accessible
       STATUS current
       DESCRIPTION
           "Index Field for line.
AC INI-Param: IPsecSATable_Index"
       ::= {acSysIPsecSAEntry 1}



     acSysIPsecSARowStatus OBJECT-TYPE
       SYNTAX RowStatus
       MAX-ACCESS read-create
       STATUS current
       DESCRIPTION
           "ROWSTATUS Field for line.
AC INI-Param: IPsecSATable_RowStatus"
       ::= {acSysIPsecSAEntry 2}



     acSysIPsecSAAction OBJECT-TYPE
       SYNTAX Unsigned32 (0..0)
       MAX-ACCESS read-create
       STATUS current
       DESCRIPTION
           "Mangement Field for ACTIONS.
AC INI-Param: IPsecSATable_Action"
       ::= {acSysIPsecSAEntry 3}



     acSysIPsecSAActionRes OBJECT-TYPE
       SYNTAX Unsigned32 (0..0)
       MAX-ACCESS read-only
       STATUS current
       DESCRIPTION
           "Mangement Field for ACTIONS RESULT.
AC INI-Param: IPsecSATable_ActionRes"
       ::= {acSysIPsecSAEntry 4}



     acSysIPsecSARemoteEndpointAddress OBJECT-TYPE
       SYNTAX SnmpAdminString (SIZE (0..98))
       MAX-ACCESS read-create
       STATUS current
       DESCRIPTION
           "IP address or DNS host name of the peer.
Access: Online.
AC INI-Param: IPsecSATable_RemoteEndpointAddressOrName"
       ::= {acSysIPsecSAEntry 5}



     acSysIPsecSAAuthenticationMethod OBJECT-TYPE
       SYNTAX INTEGER {
                  presharedKey(0)
,
                  rSASignature(1)

                  }
       MAX-ACCESS read-create
       STATUS current
       DESCRIPTION
           "Selects the method used for peer authentication during IKE main
mode.
Access: Online.
AC INI-Param: IPsecSATable_AuthenticationMethod"
       ::= {acSysIPsecSAEntry 6}



     acSysIPsecSASharedKey OBJECT-TYPE
       SYNTAX SnmpAdminString (SIZE (0..79))
       MAX-ACCESS read-create
       STATUS current
       DESCRIPTION
           "Defines the pre-shared key (in textual format).
Access: Online.
AC INI-Param: IPsecSATable_SharedKey"
       ::= {acSysIPsecSAEntry 7}



     acSysIPsecSASourcePort OBJECT-TYPE
       SYNTAX Unsigned32 (0..65535)
       MAX-ACCESS read-create
       STATUS current
       DESCRIPTION
           "Defines the source port to which this configuration applies.
Access: Online.
AC INI-Param: IPsecSATable_SourcePort"
       ::= {acSysIPsecSAEntry 8}



     acSysIPsecSADestPort OBJECT-TYPE
       SYNTAX Unsigned32 (0..65535)
       MAX-ACCESS read-create
       STATUS current
       DESCRIPTION
           "Defines the destination port to which this configuration applies.
Access: Online.
AC INI-Param: IPsecSATable_DestPort"
       ::= {acSysIPsecSAEntry 9}



     acSysIPsecSAProtocol OBJECT-TYPE
       SYNTAX Unsigned32 (0..255)
       MAX-ACCESS read-create
       STATUS current
       DESCRIPTION
           "Defines the protocol type to which this configuration applies.
Standard IP protocol numbers should be used, e.g.:
0 = Any protocol (default)
17 = UDP
6 = TCP
.
Access: Online.
AC INI-Param: IPsecSATable_Protocol"
       ::= {acSysIPsecSAEntry 10}



     acSysIPsecSAPhase1SaLifetimeInSec OBJECT-TYPE
       SYNTAX Unsigned32 (0..2147483647)
       MAX-ACCESS read-create
       STATUS current
       DESCRIPTION
           "Determines the duration (in seconds) for which the negotiated
IKE SA (main mode) is valid. After the time expires, the SA
is re-negotiated.
Access: Online.
AC INI-Param: IPsecSATable_Phase1SaLifetimeInSec"
       ::= {acSysIPsecSAEntry 11}



     acSysIPsecSAPhase2SaLifetimeInSec OBJECT-TYPE
       SYNTAX Unsigned32 (0..2147483647)
       MAX-ACCESS read-create
       STATUS current
       DESCRIPTION
           "Determines the duration (in seconds) for which the negotiated
IPSec SA (quick mode) is valid. After the time expires, the
SA is re-negotiated.
Access: Online.
AC INI-Param: IPsecSATable_Phase2SaLifetimeInSec"
       ::= {acSysIPsecSAEntry 12}



     acSysIPsecSAPhase2SaLifetimeInKB OBJECT-TYPE
       SYNTAX Unsigned32 (0..2147483647)
       MAX-ACCESS read-create
       STATUS current
       DESCRIPTION
           "Determines the maximum volume of traffic (in kilobytes) for
which the negotiated IPSec SA (quick mode) is valid.
Access: Online.
AC INI-Param: IPsecSATable_Phase2SaLifetimeInKB"
       ::= {acSysIPsecSAEntry 13}



     acSysIPsecSADPDmode OBJECT-TYPE
       SYNTAX INTEGER {
                  dPDDisabled(0)
,
                  dPDPeriodic(1)
,
                  dPDOnDemand(2)

                  }
       MAX-ACCESS read-create
       STATUS current
       DESCRIPTION
           "Controls dead peer detection (DPD) as per RFC 3706.
Access: Online.
AC INI-Param: IPsecSATable_DPDmode"
       ::= {acSysIPsecSAEntry 14}



     acSysIPsecSAIPsecMode OBJECT-TYPE
       SYNTAX INTEGER {
                  transport(0)
,
                  tunnel(1)

                  }
       MAX-ACCESS read-create
       STATUS current
       DESCRIPTION
           "Selects the IPSec mode of operation.
0 = Transport mode (default)
1 = Tunnel mode
.
Access: Online.
AC INI-Param: IPsecSATable_IPsecMode"
       ::= {acSysIPsecSAEntry 15}



     acSysIPsecSARemoteTunnelAddress OBJECT-TYPE
       SYNTAX SnmpAdminString (SIZE (0..45))
       MAX-ACCESS read-create
       STATUS current
       DESCRIPTION
           "IP address of the peer router.
Access: Online.
AC INI-Param: IPsecSATable_RemoteTunnelAddress"
       ::= {acSysIPsecSAEntry 16}



     acSysIPsecSARemoteSubnetIPAddress OBJECT-TYPE
       SYNTAX SnmpAdminString (SIZE (0..45))
       MAX-ACCESS read-create
       STATUS current
       DESCRIPTION
           "IP address of the remote subnetwork.
Access: Online.
AC INI-Param: IPsecSATable_RemoteSubnetIPAddress"
       ::= {acSysIPsecSAEntry 17}



     acSysIPsecSARemoteSubnetPrefixLength OBJECT-TYPE
       SYNTAX Unsigned32 (0..128)
       MAX-ACCESS read-create
       STATUS current
       DESCRIPTION
           "Prefix length of the Remote Subnet IP Address parameter (in
bits).
Access: Online.
AC INI-Param: IPsecSATable_RemoteSubnetPrefixLength"
       ::= {acSysIPsecSAEntry 18}



     acFirewall OBJECT IDENTIFIER ::= {acSysSecurity 23}


     -- ****************************************
     -- acSysAccessList table declaration
     -- ****************************************
     acSysAccessListTable OBJECT-TYPE
       SYNTAX SEQUENCE OF AcSysAccessListEntry
       MAX-ACCESS not-accessible
       STATUS current
       DESCRIPTION
           ""
       ::= {acFirewall 1}



     -- ****************************************
     -- acSysAccessList table entry
     -- ****************************************
     acSysAccessListEntry OBJECT-TYPE
       SYNTAX AcSysAccessListEntry
       MAX-ACCESS not-accessible
       STATUS current
       DESCRIPTION
           ""
       INDEX {acSysAccessListIndex}
       ::= {acSysAccessListTable 1}



     -- ****************************************
     -- acSysAccessList TABLE
     -- ****************************************
     AcSysAccessListEntry ::= SEQUENCE {
       acSysAccessListIndex                            Unsigned32,
       acSysAccessListRowStatus                        RowStatus,
       acSysAccessListAction                           INTEGER,
       acSysAccessListActionRes                        INTEGER,
       acSysAccessListSourceIP                         SnmpAdminString,
       acSysAccessListNetMask                          IpAddress,
       acSysAccessListStartPort                        Unsigned32,
       acSysAccessListEndPort                          Unsigned32,
       acSysAccessListProtocol                         SnmpAdminString,
       acSysAccessListPacketSize                       Unsigned32,
       acSysAccessListByteRate                         Unsigned32,
       acSysAccessListByteBurst                        Unsigned32,
       acSysAccessListAllowType                        INTEGER,
       acSysAccessListMatchCount                       Unsigned32
     }



     acSysAccessListIndex OBJECT-TYPE
       SYNTAX Unsigned32 (1..50)
       MAX-ACCESS not-accessible
       STATUS current
       DESCRIPTION
           "Index Field for line. Internal parameter.
AC INI-Param: ACCESSLIST_Index"
       ::= {acSysAccessListEntry 1}



     acSysAccessListRowStatus OBJECT-TYPE
       SYNTAX RowStatus
       MAX-ACCESS read-create
       STATUS current
       DESCRIPTION
           "ROWSTATUS field for line. Internal parameter.
AC INI-Param: N/A"
       ::= {acSysAccessListEntry 2}



     acSysAccessListAction OBJECT-TYPE
       SYNTAX INTEGER {
                  none(0)

                  }
       MAX-ACCESS read-create
       STATUS current
       DESCRIPTION
           "Mangement Field for ACTIONS. Internal parameter.
AC INI-Param: N/A"
       ::= {acSysAccessListEntry 3}



     acSysAccessListActionRes OBJECT-TYPE
       SYNTAX INTEGER {
                  succeeded(0)

                  }
       MAX-ACCESS read-only
       STATUS current
       DESCRIPTION
           "Mangement Field for ACTIONS RESULT. Internal parameter.
AC INI-Param: N/A"
       ::= {acSysAccessListEntry 4}



     acSysAccessListSourceIP OBJECT-TYPE
       SYNTAX SnmpAdminString (SIZE (0..60))
       MAX-ACCESS read-create
       STATUS current
       DESCRIPTION
           "Source IP for access rule.
Access: Online.
AC INI-Param: ACCESSLIST_Source_IP"
       ::= {acSysAccessListEntry 5}



     acSysAccessListNetMask OBJECT-TYPE
       SYNTAX IpAddress
       MAX-ACCESS read-create
       STATUS current
       DESCRIPTION
           "Mask for this access rule (bitwise ANDed with the source IP
of the packet).
Access: Online.
AC INI-Param: ACCESSLIST_Net_Mask"
       ::= {acSysAccessListEntry 6}



     acSysAccessListStartPort OBJECT-TYPE
       SYNTAX Unsigned32 (0..65535)
       MAX-ACCESS read-create
       STATUS current
       DESCRIPTION
           "Port range - start.
Access: Online.
AC INI-Param: ACCESSLIST_Start_Port"
       ::= {acSysAccessListEntry 7}



     acSysAccessListEndPort OBJECT-TYPE
       SYNTAX Unsigned32 (0..65535)
       MAX-ACCESS read-create
       STATUS current
       DESCRIPTION
           "Port range - end.
Access: Online.
AC INI-Param: ACCESSLIST_End_Port"
       ::= {acSysAccessListEntry 8}



     acSysAccessListProtocol OBJECT-TYPE
       SYNTAX SnmpAdminString (SIZE (0..10))
       MAX-ACCESS read-create
       STATUS current
       DESCRIPTION
           "IP user-level protocol (TCP, UDP, ICMP, ESP, SIP, MGCP, TPNCP,
ANY or numeric value).
Access: Online.
AC INI-Param: ACCESSLIST_Protocol"
       ::= {acSysAccessListEntry 9}



     acSysAccessListPacketSize OBJECT-TYPE
       SYNTAX Unsigned32 (0..65535)
       MAX-ACCESS read-create
       STATUS current
       DESCRIPTION
           "Maximum packet size (0 = unused).
Access: Online.
AC INI-Param: ACCESSLIST_Packet_Size"
       ::= {acSysAccessListEntry 10}



     acSysAccessListByteRate OBJECT-TYPE
       SYNTAX Unsigned32 (0..2147483647)
       MAX-ACCESS read-create
       STATUS current
       DESCRIPTION
           "Allowed traffic in bytes per second (0 = unused).
Access: Online.
AC INI-Param: ACCESSLIST_Byte_Rate"
       ::= {acSysAccessListEntry 11}



     acSysAccessListByteBurst OBJECT-TYPE
       SYNTAX Unsigned32 (0..2147483647)
       MAX-ACCESS read-create
       STATUS current
       DESCRIPTION
           "Allowed traffic burst in bytes (0 = unused).
Access: Online.
AC INI-Param: ACCESSLIST_Byte_Burst"
       ::= {acSysAccessListEntry 12}



     acSysAccessListAllowType OBJECT-TYPE
       SYNTAX INTEGER {
                  notSet(0)
,
                  allow(1)
,
                  block(2)

                  }
       MAX-ACCESS read-create
       STATUS current
       DESCRIPTION
           "Allow or block traffic matching this rule.
Access: Online.
AC INI-Param: ACCESSLIST_Allow_Type"
       ::= {acSysAccessListEntry 13}



     acSysAccessListMatchCount OBJECT-TYPE
       SYNTAX Unsigned32 (0..65535)
       MAX-ACCESS read-only
       STATUS current
       DESCRIPTION
           "Statistics: number of matched packets.
AC INI-Param: ACCESSLIST_MatchCount"
       ::= {acSysAccessListEntry 14}



     acSysMediaEncription OBJECT IDENTIFIER ::= {acSysSecurity 24}


     acSysMediaEncriptionRTPAuthenticationDisableTx OBJECT-TYPE
       SYNTAX INTEGER {
                  inactive(0)
,
                  active(1)

                  }
       MAX-ACCESS read-write
       STATUS current
       DESCRIPTION
           "On a secured RTP session, determines whether to enable Authentication
on transmitted RTP packets. 

One of the following values: 

0 = Enable
1 = Disable.
Access: Online.
AC INI-Param: RTPAuthenticationDisableTx"
       ::= {acSysMediaEncription 1}



     acSysMediaEncriptionRTPAuthenticationDisableRx OBJECT-TYPE
       SYNTAX INTEGER {
                  inactive(0)
,
                  active(1)

                  }
       MAX-ACCESS read-write
       STATUS current
       DESCRIPTION
           "On a secured RTP session, determines whether to enable Authentication
on received RTP packets 
0 = Enable
1 = Disable.
Access: Online.
AC INI-Param: RTPAuthenticationDisableRx"
       ::= {acSysMediaEncription 2}



     acSysMediaEncriptionRTPEncryptionDisableTx OBJECT-TYPE
       SYNTAX INTEGER {
                  inactive(0)
,
                  active(1)

                  }
       MAX-ACCESS read-write
       STATUS current
       DESCRIPTION
           "On a secured RTP session, determines whether to enable Encryption
on transmitted RTP packets. One of the following values:

0 = Enable
1 = Disable.
Access: Online.
AC INI-Param: RTPEncryptionDisableTx"
       ::= {acSysMediaEncription 3}



     acSysMediaEncriptionRTPEncryptionDisableRx OBJECT-TYPE
       SYNTAX INTEGER {
                  inactive(0)
,
                  active(1)

                  }
       MAX-ACCESS read-write
       STATUS current
       DESCRIPTION
           "On a secured RTP session, determines whether to enable Encryption
on transmitted RTP packets.
One of the following values:

0 = Enable
1 = Disable.
Access: Online.
AC INI-Param: RTPEncryptionDisableRx"
       ::= {acSysMediaEncription 4}



     acSysMediaEncriptionRTCPEncryptionDisableTx OBJECT-TYPE
       SYNTAX INTEGER {
                  inactive(0)
,
                  active(1)

                  }
       MAX-ACCESS read-write
       STATUS current
       DESCRIPTION
           "On a secured RTP session, determines whether to enable Encryption
on transmitted RTCP packets.
One of the following values:
 
0 = Enable
1 = Disable.
Access: Online.
AC INI-Param: RTCPEncryptionDisableTx"
       ::= {acSysMediaEncription 5}



     acSysMediaEncriptionRTCPEncryptionDisableRx OBJECT-TYPE
       SYNTAX INTEGER {
                  inactive(0)
,
                  active(1)

                  }
       MAX-ACCESS read-write
       STATUS current
       DESCRIPTION
           "On a secured RTP session, determines whether to enable Encryption
on received RTCP packets. 

One of the following values:

0 = Enable
1 = Disable.
Access: Online.
AC INI-Param: RTCPEncryptionDisableRx"
       ::= {acSysMediaEncription 6}



     acSys802dot1x OBJECT IDENTIFIER ::= {acSysSecurity 25}


     acSys802dot1xMode OBJECT-TYPE
       SYNTAX INTEGER {
                  disabled(0)
,
                  eapMd5(1)
,
                  protectedEap(2)
,
                  eapTls(3)

                  }
       MAX-ACCESS read-write
       STATUS current
       DESCRIPTION
           "Enables support for IEEE 802.1x physical port security.
0 = Disabled
1 = EAP-MD5
2 = Protected EAP (PEAP)
3 = EAP-TLS
.
Access: Instant.
AC INI-Param: 802.1xMode"
       ::= {acSys802dot1x 1}



     acSys802dot1xUsername OBJECT-TYPE
       SYNTAX SnmpAdminString (SIZE (0..31))
       MAX-ACCESS read-write
       STATUS current
       DESCRIPTION
           "Username for IEEE 802.1x support.
Access: Instant.
AC INI-Param: 802.1xUsername"
       ::= {acSys802dot1x 2}



     acSys802dot1xPassword OBJECT-TYPE
       SYNTAX SnmpAdminString (SIZE (0..31))
       MAX-ACCESS read-write
       STATUS current
       DESCRIPTION
           "Password for IEEE 802.1x support.
Access: Instant.
AC INI-Param: 802.1xPassword"
       ::= {acSys802dot1x 3}



     acSys802dot1xVerifyPeerCertificate OBJECT-TYPE
       SYNTAX INTEGER {
                  disable(0)
,
                  enable(1)

                  }
       MAX-ACCESS read-write
       STATUS current
       DESCRIPTION
           "Verify Peer Certificate for IEEE 802.1x support.
Access: Instant.
AC INI-Param: 802.1xVerifyPeerCertificate"
       ::= {acSys802dot1x 4}



     acSysSRTP OBJECT IDENTIFIER ::= {acSysMediaEncription 21}


     acSysSRTPPacketMKISize OBJECT-TYPE
       SYNTAX Unsigned32 (0..4)
       MAX-ACCESS read-write
       STATUS current
       DESCRIPTION
           "Determines the size of the parameter Master Key Identifier (MKI)
in SRTP Tx packets. 

One of the following values: 

0 = MKI Disabled
1 - 4 = size (bytes of MKI).
Access: Online.
AC INI-Param: SRTPTxPacketMKISize"
       ::= {acSysSRTP 1}



     acSysSerialIF OBJECT IDENTIFIER ::= {acSystemConfiguration 8}


     acSysSerialIFBaudRate OBJECT-TYPE
       SYNTAX Unsigned32 (0..115200)
       MAX-ACCESS read-write
       STATUS current
       DESCRIPTION
           "Enables changes to the Serial Baud Rate for Simplified Message
Desk Interface (SMDI).

Range = Any value accepted. 
Recommended standard values: 1200, 2400, 9600, 14400, 19200,
38400, 57600, 115200.
Access: Offline.
AC INI-Param: SerialBaudRate"
       ::= {acSysSerialIF 1}



     acSysSerialIFData OBJECT-TYPE
       SYNTAX Unsigned32 (7..8)
       MAX-ACCESS read-write
       STATUS current
       DESCRIPTION
           "Changes the serial data bit for the Simplified Message Desk
Interface (SMDI). 

7 = 7 Bit
8 = 8 Bit.
Access: Offline.
AC INI-Param: SerialData"
       ::= {acSysSerialIF 2}



     acSysSerialIFParity OBJECT-TYPE
       SYNTAX INTEGER {
                  none(0)
,
                  odd(1)
,
                  even(2)

                  }
       MAX-ACCESS read-write
       STATUS current
       DESCRIPTION
           "Changes the serial parity for the Simplified Message Desk Interface
(SMDI). 

0 = None 
1 = Odd 
2 = Even.
Access: Offline.
AC INI-Param: SerialParity"
       ::= {acSysSerialIF 3}



     acSysSerialIFStop OBJECT-TYPE
       SYNTAX Unsigned32 (1..2)
       MAX-ACCESS read-write
       STATUS current
       DESCRIPTION
           "Changes the serial stop for the Simplified Message Desk Interface
(SMDI).

1 = 1 Bit 
2 = 2 Bit.
Access: Offline.
AC INI-Param: SerialStop"
       ::= {acSysSerialIF 4}



     acSysSerialIFFlowControl OBJECT-TYPE
       SYNTAX INTEGER {
                  none(0)
,
                  hardware(1)

                  }
       MAX-ACCESS read-write
       STATUS current
       DESCRIPTION
           "Changes the serial flow control for the Simplified Message Desk
Interface (SMDI). 

0 = None
1 = Hardware.
Access: Offline.
AC INI-Param: SerialFlowControl"
       ::= {acSysSerialIF 5}



     acVoiceStream OBJECT IDENTIFIER ::= {acSystemConfiguration 9}


     acVoiceStreamStatus OBJECT-TYPE
       SYNTAX INTEGER {
                  disabled(0)
,
                  enabled(1)

                  }
       MAX-ACCESS read-write
       STATUS current
       DESCRIPTION
           "Enables/disables the voice streaming for all voice source types
(HTTP, NFS, Local Storage). When enabled, the module requires
some system resources, such as tasks and memory allocation.

0 = Disable
1 = Enable.
Access: Offline.
AC INI-Param: N/A"
       ::= {acVoiceStream 1}



     acVoiceStreamUploadMethod OBJECT-TYPE
       SYNTAX INTEGER {
                  httpPostMethod(0)
,
                  httpPutMethod(1)

                  }
       MAX-ACCESS read-write
       STATUS current
       DESCRIPTION
           "Defines the HTTP request type for uploading the voice stream
to the file server.

0 = POST
1 = PUT.
Access: Offline.
AC INI-Param: N/A"
       ::= {acVoiceStream 2}



     acVoiceStreamUploadPostUri OBJECT-TYPE
       SYNTAX SnmpAdminString (SIZE (0..59))
       MAX-ACCESS read-write
       STATUS current
       DESCRIPTION
           "Defines the URI used on the POST request, to upload voice data
from the media server to a web server.
This parameter is used only when using the HTTP POST for recording
and the command is not issued by the Lib (tpncp protocol).
The path needs to be set to the upload script on the web server.

.
Access: Offline.
AC INI-Param: N/A"
       ::= {acVoiceStream 3}



     acSysAMS OBJECT IDENTIFIER ::= {acSystemConfiguration 10}


     acSysAMSProfile OBJECT-TYPE
       SYNTAX Unsigned32 (0..7)
       MAX-ACCESS read-write
       STATUS current
       DESCRIPTION
           "Enable/Disable AMS Advanced IVR play functionality.
0 = Disable
1 = Enable.
Access: Offline.
AC INI-Param: AMSProfile"
       ::= {acSysAMS 1}



     acSysAMSApsIpAddress OBJECT-TYPE
       SYNTAX IpAddress
       MAX-ACCESS read-write
       STATUS current
       DESCRIPTION
           "Sets the destination UDP port to which the Heartbeat Packets
are sent.
Range =  IP address in dotted notation 
xxx.xxx.xxx.xxx
Default = 0.0.0.0.
Access: Offline.
AC INI-Param: HeartbeatDestIP"
       ::= {acSysAMS 2}



     acSysAMSApsPort OBJECT-TYPE
       SYNTAX Unsigned32 (0..64000)
       MAX-ACCESS read-write
       STATUS current
       DESCRIPTION
           "Sets the destination UDP port to which the heartbeat packets
are sent.
Access: Offline.
AC INI-Param: HeartbeatDestPort"
       ::= {acSysAMS 3}



     acSysAMSPrimaryLanguage OBJECT-TYPE
       SYNTAX SnmpAdminString (SIZE (0..3))
       MAX-ACCESS read-write
       STATUS current
       DESCRIPTION
           "Defines the Primary Language for the AMS. 
Range = String[3] - language ISO string.
Access: Instant.
AC INI-Param: AMSPrimaryLanguage"
       ::= {acSysAMS 4}



     acSysAMSSecondaryLanguage OBJECT-TYPE
       SYNTAX SnmpAdminString (SIZE (0..3))
       MAX-ACCESS read-write
       STATUS current
       DESCRIPTION
           "Defines the Secondary Language for the AMS. 
Range = String[3] - language ISO string.
Access: Instant.
AC INI-Param: AMSSecondaryLanguage"
       ::= {acSysAMS 5}



     acSysAMSAPSProfile OBJECT-TYPE
       SYNTAX INTEGER {
                  vpDatProvidedAudio(0)
,
                  apsProvidedAudio(1)

                  }
       MAX-ACCESS read-write
       STATUS current
       DESCRIPTION
           "Indicates if the system should expect to use APS bundle (vp.dat
and segments.xml files), or if the system should expect
the vp.dat file only. A 1 means that an APS bundle should be
used. A 0 means that the system should use vp.dat only. The
default setting is 1, meaning expect APS bundle.
Access: Offline.
AC INI-Param: APSEnabled"
       ::= {acSysAMS 6}



     acSysAMSForceRepositoryEnable OBJECT-TYPE
       SYNTAX INTEGER {
                  disable(0)
,
                  enable(1)

                  }
       MAX-ACCESS read-write
       STATUS current
       DESCRIPTION
           "Indicates that a new audio repository (consisting of VP and
XML files) should always be uploaded to the board regardless
of whether signals are still being played on the old repository.
Access: Instant.
AC INI-Param: AMSForceRepositoryUpdateEnabled"
       ::= {acSysAMS 7}



     acSysNetworkFileSystem OBJECT IDENTIFIER ::= {acSystemConfiguration 11}


     -- ****************************************
     -- acSysNFS table declaration
     -- ****************************************
     acSysNFSTable OBJECT-TYPE
       SYNTAX SEQUENCE OF AcSysNFSEntry
       MAX-ACCESS not-accessible
       STATUS current
       DESCRIPTION
           ""
       ::= {acSysNetworkFileSystem 21}



     -- ****************************************
     -- acSysNFS table entry
     -- ****************************************
     acSysNFSEntry OBJECT-TYPE
       SYNTAX AcSysNFSEntry
       MAX-ACCESS not-accessible
       STATUS current
       DESCRIPTION
           ""
       INDEX {acSysNFSIndex}
       ::= {acSysNFSTable 1}



     -- ****************************************
     -- acSysNFS TABLE
     -- ****************************************
     AcSysNFSEntry ::= SEQUENCE {
       acSysNFSIndex                                   Unsigned32,
       acSysNFSRowStatus                               RowStatus,
       acSysNFSAction                                  INTEGER,
       acSysNFSActionRes                               INTEGER,
       acSysNFSHostOrIP                                SnmpAdminString,
       acSysNFSRootPath                                SnmpAdminString,
       acSysNFSNfsVersion                              INTEGER,
       acSysNFSAuthType                                INTEGER,
       acSysNFSUID                                     Unsigned32,
       acSysNFSGID                                     Unsigned32,
       acSysNFSVlanType                                INTEGER
     }



     acSysNFSIndex OBJECT-TYPE
       SYNTAX Unsigned32 (0..15)
       MAX-ACCESS not-accessible
       STATUS current
       DESCRIPTION
           "Index Field for line. Internal parameter.
AC INI-Param: NFSServers_Index"
       ::= {acSysNFSEntry 1}



     acSysNFSRowStatus OBJECT-TYPE
       SYNTAX RowStatus
       MAX-ACCESS read-create
       STATUS current
       DESCRIPTION
           "ROWSTATUS field for line. Internal parameter.
AC INI-Param: N/A"
       ::= {acSysNFSEntry 2}



     acSysNFSAction OBJECT-TYPE
       SYNTAX INTEGER {
                  none(0)

                  }
       MAX-ACCESS read-create
       STATUS current
       DESCRIPTION
           "Mangement Field for ACTIONS. Internal parameter.
AC INI-Param: N/A"
       ::= {acSysNFSEntry 3}



     acSysNFSActionRes OBJECT-TYPE
       SYNTAX INTEGER {
                  succeeded(0)

                  }
       MAX-ACCESS read-only
       STATUS current
       DESCRIPTION
           "Mangement Field for ACTIONS RESULT. Internal parameter.
AC INI-Param: N/A"
       ::= {acSysNFSEntry 4}



     acSysNFSHostOrIP OBJECT-TYPE
       SYNTAX SnmpAdminString (SIZE (0..40))
       MAX-ACCESS read-create
       STATUS current
       DESCRIPTION
           "The domain name or IP address of the NFS server. If a domain
name is provided, then a DNS server must be configured.
Access: Online.
AC INI-Param: NFSServers_HostOrIP"
       ::= {acSysNFSEntry 5}



     acSysNFSRootPath OBJECT-TYPE
       SYNTAX SnmpAdminString (SIZE (0..100))
       MAX-ACCESS read-create
       STATUS current
       DESCRIPTION
           "Path to the root of the exported file system.
Access: Online.
AC INI-Param: NFSServers_RootPath"
       ::= {acSysNFSEntry 6}



     acSysNFSNfsVersion OBJECT-TYPE
       SYNTAX INTEGER {
                  v2(2)
,
                  v3(3)

                  }
       MAX-ACCESS read-create
       STATUS current
       DESCRIPTION
           "NFS version to use with this remote file system, 2 or 3 (default).
Access: Online.
AC INI-Param: NFSServers_NfsVersion"
       ::= {acSysNFSEntry 7}



     acSysNFSAuthType OBJECT-TYPE
       SYNTAX INTEGER {
                  null(0)
,
                  unix(1)

                  }
       MAX-ACCESS read-create
       STATUS current
       DESCRIPTION
           "Identifies the authentication method used with this remote file
system, 0 for AUTH_NULL, 1 for AUTH_UNIX (default).
Access: Online.
AC INI-Param: NFSServers_AuthType"
       ::= {acSysNFSEntry 8}



     acSysNFSUID OBJECT-TYPE
       SYNTAX Unsigned32 (0..2147483647)
       MAX-ACCESS read-create
       STATUS current
       DESCRIPTION
           "User ID used in authentication if using AUTH_UNIX. The default
is 0.
Access: Online.
AC INI-Param: NFSServers_UID"
       ::= {acSysNFSEntry 9}



     acSysNFSGID OBJECT-TYPE
       SYNTAX Unsigned32 (0..2147483647)
       MAX-ACCESS read-create
       STATUS current
       DESCRIPTION
           "Group ID used in authentication if using AUTH_UNIX. The default
is 1.
Access: Online.
AC INI-Param: NFSServers_GID"
       ::= {acSysNFSEntry 10}



     acSysNFSVlanType OBJECT-TYPE
       SYNTAX INTEGER {
                  oam(0)
,
                  media(1)

                  }
       MAX-ACCESS read-create
       STATUS current
       DESCRIPTION
           "The VLAN, OAM(0) or Media(1), to use when accessing this remote
file system. The default is to use
the media VLAN. This parameters applies only if multiple IP
addresses are configured on this board.
Access: Online.
AC INI-Param: NFSServers_VlanType"
       ::= {acSysNFSEntry 11}



     acSysHA OBJECT IDENTIFIER ::= {acSystemConfiguration 12}


     acSysHAGlobalIPAddress OBJECT-TYPE
       SYNTAX IpAddress
       MAX-ACCESS read-write
       STATUS obsolete
       DESCRIPTION
           "Defines the M3K global IP address to be used by the active module
in HA system. (Dotted format notation. e.g., 192.10.1.255).
Range = Legal IP address.
Access: Offline.
AC INI-Param: M3KGlobalIpAddr"
       ::= {acSysHA 1}



     acSysTransmission OBJECT IDENTIFIER ::= {acSystemConfiguration 13}


     acSysTransmissionType OBJECT-TYPE
       SYNTAX INTEGER {
                  none(0)
,
                   opticalSonetSdh(1)
,
                  copperDs3(2)
,
                  copperE1Ds1(3)

                  }
       MAX-ACCESS read-write
       STATUS current
       DESCRIPTION
           "Sets the PSTN Transmission type for the board: optical SONET
/ SDH or copper DS3.
Access: Offline.
AC INI-Param: PSTNTransmissionType"
       ::= {acSysTransmission 1}



     acSysTiming OBJECT IDENTIFIER ::= {acSystemConfiguration 14}


     acSysTimingMode OBJECT-TYPE
       SYNTAX INTEGER {
                  standAlone(0)
,
                  external(1)
,
                  lineSync(2)

                  }
       MAX-ACCESS read-write
       STATUS current
       DESCRIPTION
           "Determines the PSTN Timing synchonization mode of the Gateway.
One of the following values: TM_External_MODE(1)
-External Timing mode - use the SAT trunks Centralized Line
Timing to synchronize the Gateway with one of the PSTN interfaces.
TM_LineSync_MODE(2)
-Distributed Line Timing mode (for the 1610 boards)- without
using the SAT timing module. TM_Standalone_MODE(0)
-Non-synchronized mode - each board or TPM is synchronized
internally from one of the PSTN interfaces without using the
SAT timing module.
Access: Online.
AC INI-Param: TMMode"
       ::= {acSysTiming 1}



     acSysTimingValidationTime OBJECT-TYPE
       SYNTAX Unsigned32 (0..15)
       MAX-ACCESS read-write
       STATUS current
       DESCRIPTION
           "Reference validation time. Applicable for External timing and
Line timing timing references. Range: 0 - 15 minutes. Resolution:
1 minute.
Access: Online.
AC INI-Param: TMReferenceValidationTime"
       ::= {acSysTiming 2}



     acSysTimingClockToDeriveA OBJECT-TYPE
       SYNTAX INTEGER {
                  deriveREFFromLineClock1(0)
,
                  deriveInternalClock(4)
,
                  clockFromReceiveSide(7)



                  }
       MAX-ACCESS read-write
       STATUS obsolete
       DESCRIPTION
           "Which Clock to use in sync mode.
Access: Online.
AC INI-Param: TMClockToDerive_A"
       ::= {acSysTiming 3}



     acSysTimingClockToDeriveB OBJECT-TYPE
       SYNTAX INTEGER {
                  deriveREFFromLineClock1(0)
,
                  deriveInternalClock(4)
,
                  clockFromReceiveSide(7)



                  }
       MAX-ACCESS read-write
       STATUS obsolete
       DESCRIPTION
           "Which Clock to use in sync mode.
Access: Online.
AC INI-Param: TMClockToDerive_B"
       ::= {acSysTiming 4}



     acSysTimingExternalIFType OBJECT-TYPE
       SYNTAX INTEGER {
                  e1CRC4(0)
,
                  e1CAS(1)
,
                  e1FAS(2)
,
                  t1D4(3)
,
                  t1ESF(4)
,
                  t12(5)

                  }
       MAX-ACCESS read-write
       STATUS current
       DESCRIPTION
           "Defines the external line reference (BITS) transmission format.
Access: Online.
AC INI-Param: TMExternalIFType"
       ::= {acSysTiming 5}



     acSysTimingLoopBackRef1 OBJECT-TYPE
       SYNTAX INTEGER {
                  loopDisable(0)
,
                  loopEnable(1)

                  }
       MAX-ACCESS read-write
       STATUS current
       DESCRIPTION
           "Enables loopback state, by connecting Rx path towards Tx path.
Access: Online.
AC INI-Param: TMLoopBackExternalRef1"
       ::= {acSysTiming 6}



     acSysTimingLoopBackRef2 OBJECT-TYPE
       SYNTAX INTEGER {
                  loopDisable(0)
,
                  loopEnable(1)

                  }
       MAX-ACCESS read-write
       STATUS current
       DESCRIPTION
           "Enables loopback state, by connecting Rx path towards Tx path.
Access: Online.
AC INI-Param: TMLoopBackExternalRef2"
       ::= {acSysTiming 7}



     acSysTimingTransmitControl OBJECT-TYPE
       SYNTAX INTEGER {
                  systemClock(0)
,
                  aIS(1)
,
                  disableTransmit(2)

                  }
       MAX-ACCESS read-write
       STATUS obsolete
       DESCRIPTION
           "Enables loopback state, by connecting Rx path towards Tx path.
Access: Online.
AC INI-Param: TMTransmitControl"
       ::= {acSysTiming 8}



     acSysTimingE1LineBuildOut OBJECT-TYPE
       SYNTAX INTEGER {
                  tm75OhmNormal(0)
,
                  tm120OhmNormal(1)
,
                  tm75OhmHighReturnLoss(4)
,
                  tm120OhmHighReturnLoss(5)
,
                  tm75OhmNormalGappedClock(6)
,
                  tm120OhmNormalGappedClock(7)

                  }
       MAX-ACCESS read-write
       STATUS obsolete
       DESCRIPTION
           "Sets the transmission power between the timing module on the
SAT and the E1 external reference clock (ohms). This parameter
is only relevant for the Mediant 3000.This parameter is
enabled when bspTimingModuleCfgTimingMode is set to TM_External_MODE(1).

One of the following values: E_75_OHM_with_high_return_loss(4),E_120_OHM_with_high_return_loss(5),E_75_OHM_normal_PLUS_enable_transmit_and_receive_gapped_clock(6),E_120_OHM_normal_PLUS_enable_transmit_and_receive_gapped_clock(7),E_75_OHM_normal(0),E_120_OHM_normal(1).
Access: Online.
AC INI-Param: TME1LineBuildOut "
       ::= {acSysTiming 9}



     acSysTimingT1LineBuildOut OBJECT-TYPE
       SYNTAX INTEGER {
                  dSX10to133feet0dBCSU(0)
,
                  dSX1133to266feet(1)
,
                  dSX1266to399feet(2)
,
                  dSX1399to533feet(3)
,
                  dSX1533to655feet(4)
,
                  dSX10to133ft0dBgappedclock(7)

                  }
       MAX-ACCESS read-write
       STATUS obsolete
       DESCRIPTION
           "External Reference Transmit Line Build Out.
Access: Online.
AC INI-Param: TMT1LineBuildOut"
       ::= {acSysTiming 10}



     acSysLDAP OBJECT IDENTIFIER ::= {acSystemConfiguration 15}


     acSysLDAPServerIp OBJECT-TYPE
       SYNTAX IpAddress
       MAX-ACCESS read-write
       STATUS current
       DESCRIPTION
           "This parameter defines the IP address in dotted format notation.
e.g., 192.10.1.255
Range = Legal IP address.
Access: Online.
AC INI-Param: LDAPSERVERIP"
       ::= {acSysLDAP 1}



     acSysLDAPServerPort OBJECT-TYPE
       SYNTAX Unsigned32 (0..65535)
       MAX-ACCESS read-write
       STATUS current
       DESCRIPTION
           "Defines the port number for the LDAP server.
Range = Valid port number.
Access: Online.
AC INI-Param: LDAPSERVERPORT"
       ::= {acSysLDAP 2}



     acSysLDAPServerMaxRespondTime OBJECT-TYPE
       SYNTAX Unsigned32 (0..86400)
       MAX-ACCESS read-write
       STATUS current
       DESCRIPTION
           "Defines the period of time the module  will wait for LDAP server
response (seconds).
Access: Online.
AC INI-Param: LDAPSERVERMAXRESPONDTIME"
       ::= {acSysLDAP 3}



     acSysLDAPServerDomainName OBJECT-TYPE
       SYNTAX SnmpAdminString (SIZE (0..255))
       MAX-ACCESS read-write
       STATUS current
       DESCRIPTION
           "This parameter is used to indicate the name of LDAP server.
Access: Online.
AC INI-Param: LDAPSERVERDOMAINNAME"
       ::= {acSysLDAP 4}



     acSysLDAPSearchDN OBJECT-TYPE
       SYNTAX SnmpAdminString (SIZE (0..255))
       MAX-ACCESS read-write
       STATUS current
       DESCRIPTION
           "This parameter is used to indicate the search DN for LDAP search
request.
Access: Online.
AC INI-Param: LDAPSEARCHDN"
       ::= {acSysLDAP 5}



     acSysLDAPPassword OBJECT-TYPE
       SYNTAX SnmpAdminString (SIZE (0..255))
       MAX-ACCESS read-write
       STATUS current
       DESCRIPTION
           "This parameter is used to indicate the user password of LDAP
server.
Access: Online.
AC INI-Param: LDAPPASSWORD"
       ::= {acSysLDAP 6}



     acSysLDAPBindDN OBJECT-TYPE
       SYNTAX SnmpAdminString (SIZE (0..255))
       MAX-ACCESS read-write
       STATUS current
       DESCRIPTION
           "This parameter is used to indicate the of LDAP server bind DN.
Access: Online.
AC INI-Param: LDAPBINDDN"
       ::= {acSysLDAP 7}



     acSysLDAPServiceEnable OBJECT-TYPE
       SYNTAX INTEGER {
                  disable(0)
,
                  enable(1)

                  }
       MAX-ACCESS read-write
       STATUS current
       DESCRIPTION
           "Used to either enable or disable LDAP service.
0- disable (default)
1 - enable.
Access: Offline.
AC INI-Param: LDAPSERVICEENABLE"
       ::= {acSysLDAP 8}



     acSystemStatus OBJECT IDENTIFIER ::= {acSystem 2}


     acSysType OBJECT IDENTIFIER ::= {acSystemStatus 1}


     acSysTypeProduct OBJECT-TYPE
       SYNTAX INTEGER {
                  acUnknown(0)
,
                  acTrunkPack-08(1)
,
                  acMediaPack-108(2)
,
                  acMediaPack-124(3)
,
                  acTrunkPack-1600(20)
,
                  acTPM1100(22)
,
                  acTrunkPack-260-IpMedia(23)
,
                  acTrunkPack-1610(24)
,
                  acMediaPack-104(25)
,
                  acMediaPack-102(26)
,
                  acTrunkPack-1610-SB(29)
,
                  acTrunkPack-1610-IpMedia(30)
,
                  acTrunkPack-MEDIANT2000(31)
,
                  acTrunkPack-STRETTO2000(32)
,
                  acTrunkPack-IPMServer2000(33)
,
                  acTrunkPack-2810(34)
,
                  acTrunkPack-260-UN-IpMedia (35)
,
                  acTrunkPack-260-IpMedia-30Ch(36)
,
                  acTrunkPack-260-IpMedia-60Ch(37)
,
                  acTrunkPack-260-IpMedia-120Ch(38)
,
                  acTrunkPack-260RT-IpMedia-30Ch(39)
,
                  acTrunkPack-260RT-IpMedia-60Ch(40)
,
                  acTrunkPack-260RT-IpMedia-120Ch(41)
,
                  acTrunkPack-260(42)
,
                  acTrunkPack-260-UN (43)
,
                  acTPM1100-PCM(44)
,
                  acTrunkPack-6310(45)
,
                  acTPM6300(46)
,
                  acMediant1000(47)
,
                  acIPMedia3000(48)
,
                  acMediant3000(49)
,
                  acStretto3000(50)
,
                  acTrunkPack-6310-IpMedia(51)
,
                  acTrunkPack-6310-SB(52)
,
                  acATP-1610(53)
,
                  acATP-260(54)
,
                  acATP-260-UN(55)
,
                  acMediaPack-118(56)
,
                  acMediaPack114(57)
,
                  acMediaPack112(58)
,
                   acTrunkPack-6310-T3(59)
,
                  acMediant3000-T3(60)
,
                  acIPmedia3000-T3(61)
,
                  acTrunkPack-6310-T3-IpMedia(62)
,
                  acTrunkPack-8410(63)
,
                  acTrunkPack-8410-IpMedia(64)
,
                  acMediant-600(65)
,
                  acTrunkPack-12610(66)
,
                  acMediant1000-MSBG(67)
,
                  acMediant-600-MSBG(68)
,
                  acMediaPack-500-MSBG(69)

                  }
       MAX-ACCESS read-only
       STATUS current
       DESCRIPTION
           "The type of the Board.
AC INI-Param: N/A"
       ::= {acSysType 1}



     acSysTypeDSP OBJECT-TYPE
       SYNTAX Unsigned32 (0..2147483647)
       MAX-ACCESS read-only
       STATUS current
       DESCRIPTION
           "Dsp Type.
AC INI-Param: N/A"
       ::= {acSysType 2}



     acSysTypeModule OBJECT-TYPE
       SYNTAX INTEGER {
                  soloist (0)
,
                  second(1)
,
                  first(2)

                  }
       MAX-ACCESS read-only
       STATUS current
       DESCRIPTION
           "
AC INI-Param: N/A"
       ::= {acSysType 3}



     acSysTypeCPUSpeed OBJECT-TYPE
       SYNTAX Unsigned32 (0..2147483647)
       MAX-ACCESS read-only
       STATUS current
       DESCRIPTION
           "CPU Speed.
AC INI-Param: N/A"
       ::= {acSysType 4}



     acSysVersion OBJECT IDENTIFIER ::= {acSystemStatus 2}


     acSysVersionSoftware OBJECT-TYPE
       SYNTAX SnmpAdminString (SIZE (0..20))
       MAX-ACCESS read-only
       STATUS current
       DESCRIPTION
           "TrunkPack Software Version.
AC INI-Param: N/A"
       ::= {acSysVersion 1}



     acSysVersionFlash OBJECT-TYPE
       SYNTAX Unsigned32 (0..2147483647)
       MAX-ACCESS read-only
       STATUS current
       DESCRIPTION
           "Flash [BootLoader] Version.
AC INI-Param: N/A"
       ::= {acSysVersion 2}



     acSysVersionIniFile OBJECT-TYPE
       SYNTAX Unsigned32 (0..2147483647)
       MAX-ACCESS read-only
       STATUS current
       DESCRIPTION
           "Ini file version.
AC INI-Param: INIFileVersion"
       ::= {acSysVersion 3}



     acSysVersionSoftwareDate OBJECT-TYPE
       SYNTAX SnmpAdminString (SIZE (0..40))
       MAX-ACCESS read-only
       STATUS current
       DESCRIPTION
           "TrunkPack Software Date.
AC INI-Param: N/A"
       ::= {acSysVersion 4}



     acSysId OBJECT IDENTIFIER ::= {acSystemStatus 3}


     acSysIdName OBJECT-TYPE
       SYNTAX SnmpAdminString (SIZE (0..20))
       MAX-ACCESS read-only
       STATUS current
       DESCRIPTION
           "The name fo the board.
AC INI-Param: N/A"
       ::= {acSysId 1}



     acSysIdSerialNumber OBJECT-TYPE
       SYNTAX Unsigned32 (0..2147483647)
       MAX-ACCESS read-only
       STATUS current
       DESCRIPTION
           "serial number of board.
AC INI-Param: N/A"
       ::= {acSysId 2}



     acSysIdSlotNumber OBJECT-TYPE
       SYNTAX Unsigned32 (0..2147483647)
       MAX-ACCESS read-only
       STATUS current
       DESCRIPTION
           "Slot number.
AC INI-Param: N/A"
       ::= {acSysId 3}



     acSysIdFirstSerialNumber OBJECT-TYPE
       SYNTAX Unsigned32 (0..2147483647)
       MAX-ACCESS read-only
       STATUS current
       DESCRIPTION
           "The device's first serial number.
When the device is part of a dual module board this is the
first module's serial number.
When the device is the first module in a dual module or the
device is not in a dual module board, the values for asSysIdSerialNumber
and acSysIdFirstSerialNumber are the same.
AC INI-Param: N/A"
       ::= {acSysId 4}



     acSysCount OBJECT IDENTIFIER ::= {acSystemStatus 4}


     acSysCountDSPs OBJECT-TYPE
       SYNTAX Unsigned32 (0..2147483647)
       MAX-ACCESS read-only
       STATUS current
       DESCRIPTION
           "DSP Count.
AC INI-Param: N/A"
       ::= {acSysCount 1}



     acSysCountChannels OBJECT-TYPE
       SYNTAX Unsigned32 (0..2147483647)
       MAX-ACCESS read-only
       STATUS current
       DESCRIPTION
           "Channel Count.
AC INI-Param: N/A"
       ::= {acSysCount 2}



     acSysCountTrunks OBJECT-TYPE
       SYNTAX Unsigned32 (0..2147483647)
       MAX-ACCESS read-only
       STATUS current
       DESCRIPTION
           "Trunks Count.
AC INI-Param: N/A"
       ::= {acSysCount 3}



     acSysState OBJECT IDENTIFIER ::= {acSystemStatus 5}


     acSysStateTemperature OBJECT-TYPE
       SYNTAX Unsigned32 (0..100)
       MAX-ACCESS read-only
       STATUS current
       DESCRIPTION
           "Temperature of the board in degrees Celsius, should not go higher
then 60!.
AC INI-Param: N/A"
       ::= {acSysState 1}



     acSysStateOperational OBJECT-TYPE
       SYNTAX INTEGER {
                  disabled(1)
,
                  enabled(2)

                  }
       MAX-ACCESS read-only
       STATUS current
       DESCRIPTION
           "The operational state of the gateway.
AC INI-Param: N/A"
       ::= {acSysState 2}



     acSysStateHAupdateInProgress OBJECT-TYPE
       SYNTAX INTEGER {
                  updateDone(1)
,
                  updateInProgress(2)

                  }
       MAX-ACCESS read-only
       STATUS current
       DESCRIPTION
           "Indicates during update process, which done between active and
redundant boards.
AC INI-Param: N/A"
       ::= {acSysState 3}



     acSysStateGWSeverity OBJECT-TYPE
       SYNTAX INTEGER {
                  noAlarm(0)
,
                  indeterminate(1)
,
                  warning(2)
,
                  minor(3)
,
                  major(4)
,
                  critical(5)

                  }
       MAX-ACCESS read-only
       STATUS current
       DESCRIPTION
           "The highest alarm severity on the device.
AC INI-Param: N/A"
       ::= {acSysState 4}



     acSysStateIsPstnManagementEnable OBJECT-TYPE
       SYNTAX INTEGER {
                  disable(0)
,
                  enable(1)

                  }
       MAX-ACCESS read-only
       STATUS current
       DESCRIPTION
           "Is Pstn Management Enable
0 - Disable
1 - Enable.
AC INI-Param: N/A"
       ::= {acSysState 5}



     acSysNetwork OBJECT IDENTIFIER ::= {acSystemStatus 6}


     acSysEthernet OBJECT IDENTIFIER ::= {acSysNetwork 1}


     acSysEthernetFirstPortDuplexMode OBJECT-TYPE
       SYNTAX INTEGER {
                  halfDuplex(0)
,
                  fullDuplex(1)
,
                  forceModeValue(2)
,
                  notAvailable(3)

                  }
       MAX-ACCESS read-only
       STATUS current
       DESCRIPTION
           "full-duplex or half-duplex connection.
AC INI-Param: N/A"
       ::= {acSysEthernet 1}



     acSysEthernetFirstPortSpeed OBJECT-TYPE
       SYNTAX INTEGER {
                  forceModeValue(2)
,
                  notAvailable(3)
,
                  ac10Mbps(10)
,
                  ac100Mbps(100)
,
                  ac1000Mbps(1000)

                  }
       MAX-ACCESS read-only
       STATUS current
       DESCRIPTION
           "
AC INI-Param: N/A"
       ::= {acSysEthernet 2}



     acSysEthernetSecondPortDuplexMode OBJECT-TYPE
       SYNTAX INTEGER {
                  halfDuplex(0)
,
                  fullDuplex(1)
,
                  forceModeValue(2)
,
                  notAvailable(3)

                  }
       MAX-ACCESS read-only
       STATUS current
       DESCRIPTION
           "full-duplex or half-duplex connection.
AC INI-Param: N/A"
       ::= {acSysEthernet 3}



     acSysEthernetSecondPortSpeed OBJECT-TYPE
       SYNTAX INTEGER {
                  forceModeValue(2)
,
                  notAvailable(3)
,
                  ac10Mbps(10)
,
                  ac100Mbps(100)
,
                  ac1000Mbps(1000)

                  }
       MAX-ACCESS read-only
       STATUS current
       DESCRIPTION
           "
AC INI-Param: N/A"
       ::= {acSysEthernet 4}



     acSysEthernetActivePortNumber OBJECT-TYPE
       SYNTAX Unsigned32 (0..2)
       MAX-ACCESS read-only
       STATUS current
       DESCRIPTION
           "Display the current active ethernet port number.
0 - not relevant.
AC INI-Param: N/A"
       ::= {acSysEthernet 5}



     -- ****************************************
     -- acSysEthernetStatus table declaration
     -- ****************************************
     acSysEthernetStatusTable OBJECT-TYPE
       SYNTAX SEQUENCE OF AcSysEthernetStatusEntry
       MAX-ACCESS not-accessible
       STATUS current
       DESCRIPTION
           "Ethernet relevant information"
       ::= {acSysEthernet 21}



     -- ****************************************
     -- acSysEthernetStatus table entry
     -- ****************************************
     acSysEthernetStatusEntry OBJECT-TYPE
       SYNTAX AcSysEthernetStatusEntry
       MAX-ACCESS not-accessible
       STATUS current
       DESCRIPTION
           ""
       INDEX {acSysEthernetStatusIndex}
       ::= {acSysEthernetStatusTable 1}



     -- ****************************************
     -- acSysEthernetStatus TABLE
     -- ****************************************
     AcSysEthernetStatusEntry ::= SEQUENCE {
       acSysEthernetStatusIndex                        Unsigned32,
       acSysEthernetStatusPortDuplexMode               INTEGER,
       acSysEthernetStatusPortSpeed                    INTEGER,
       acSysEthernetStatusActivePortNumber             INTEGER,
       acSysEthernetStatusPortState                    INTEGER,
       acSysEthernetStatusPowerOverEthernet            INTEGER
     }



     acSysEthernetStatusIndex OBJECT-TYPE
       SYNTAX Unsigned32 (0..12)
       MAX-ACCESS not-accessible
       STATUS current
       DESCRIPTION
           "The row's index.
On 8410 Systems:
Index 1 – related to GBE port no.1 in the TER (Media).
Index 2 – related to GBE port no.2 in the TER (Media).
Index 3 – related to port 1A in PEM #1 (Control).
 Index 4 – related to port 1B in PEM #2 (Control).
Index 5 – related to port 2A in PEM #1 (OAM).
Index 6 – related to port 2B in PEM #2 (OAM). 
On MSBG only:
0 - WAN interface.
1-12 LAN interfaces.
AC INI-Param: N/A"
       ::= {acSysEthernetStatusEntry 1}



     acSysEthernetStatusPortDuplexMode OBJECT-TYPE
       SYNTAX INTEGER {
                  halfDuplex(0)
,
                  fullDuplex(1)
,
                  forceModeValue(2)
,
                  notAvailable(3)

                  }
       MAX-ACCESS read-only
       STATUS current
       DESCRIPTION
           "full-duplex or half-duplex connection.
AC INI-Param: N/A"
       ::= {acSysEthernetStatusEntry 2}



     acSysEthernetStatusPortSpeed OBJECT-TYPE
       SYNTAX INTEGER {
                  forceModeValue(2)
,
                  notAvailable(3)
,
                  ac10Mbps(10)
,
                  ac100Mbps(100)
,
                  ac1000Mbps(1000)

                  }
       MAX-ACCESS read-only
       STATUS current
       DESCRIPTION
           "port speed.
AC INI-Param: N/A"
       ::= {acSysEthernetStatusEntry 3}



     acSysEthernetStatusActivePortNumber OBJECT-TYPE
       SYNTAX INTEGER {
                  notActive(0)
,
                  active(1)

                  }
       MAX-ACCESS read-only
       STATUS current
       DESCRIPTION
           "Status of ethernet port - active or not active.
AC INI-Param: N/A"
       ::= {acSysEthernetStatusEntry 4}



     acSysEthernetStatusPortState OBJECT-TYPE
       SYNTAX INTEGER {
                  disabled(0)
,
                  blocking(1)
,
                  learning(2)
,
                  forwarding(3)
,
                  notApplicable(10)

                  }
       MAX-ACCESS read-only
       STATUS current
       DESCRIPTION
           "Port State.
AC INI-Param: N/A"
       ::= {acSysEthernetStatusEntry 5}



     acSysEthernetStatusPowerOverEthernet OBJECT-TYPE
       SYNTAX INTEGER {
                  notApplicable(0)
,
                  active(1)
,
                  notActive(2)

                  }
       MAX-ACCESS read-only
       STATUS current
       DESCRIPTION
           "Power over Ethernet interface status.
AC INI-Param: N/A"
       ::= {acSysEthernetStatusEntry 6}



     acSysNAT OBJECT IDENTIFIER ::= {acSysNetwork 2}


     acSysNATType OBJECT-TYPE
       SYNTAX INTEGER {
                  stunDisabled(-1)
,
                  none(0)
,
                  fullCone(1)
,
                  restricted(2)
,
                  portRestricted(3)
,
                  symmetric(4)
,
                  symmetricFireWall(5)
,
                  blocked(6)
,
                  unknown(7)
,
                  natIdentificationInProgress(10)

                  }
       MAX-ACCESS read-only
       STATUS current
       DESCRIPTION
           "Identified NAT type.
-1 - STUN client is disabled
0 - None
1 - FullCone
2 - Restricted
3 - PortRestricted
4 - Symmetric
5 - SymmetricFireWall
6 - Blocked
7 - Unknown
10 - NAT identification in progress.
AC INI-Param: N/A"
       ::= {acSysNAT 1}



     acSysWebStat OBJECT IDENTIFIER ::= {acSysNetwork 3}


     acSysWebStatPasswordControlViaSNMP OBJECT-TYPE
       SYNTAX INTEGER {
                  disabled(0)
,
                  enabled(1)

                  }
       MAX-ACCESS read-only
       STATUS current
       DESCRIPTION
           "If set to 1 it will allow changing the web interface username
and password via SNMP.
AC INI-Param: WEBPasswordControlViaSNMP "
       ::= {acSysWebStat 1}



     acSysIPStatus OBJECT IDENTIFIER ::= {acSysNetwork 4}


     -- ****************************************
     -- acSysInterfaceStatus table declaration
     -- ****************************************
     acSysInterfaceStatusTable OBJECT-TYPE
       SYNTAX SEQUENCE OF AcSysInterfaceStatusEntry
       MAX-ACCESS not-accessible
       STATUS current
       DESCRIPTION
           ""
       ::= {acSysIPStatus 21}



     -- ****************************************
     -- acSysInterfaceStatus table entry
     -- ****************************************
     acSysInterfaceStatusEntry OBJECT-TYPE
       SYNTAX AcSysInterfaceStatusEntry
       MAX-ACCESS not-accessible
       STATUS current
       DESCRIPTION
           ""
       INDEX {acSysInterfaceStatusEntryIndex,acSysInterfaceStatusTypeIndex}
       ::= {acSysInterfaceStatusTable 1}



     -- ****************************************
     -- acSysInterfaceStatus TABLE
     -- ****************************************
     AcSysInterfaceStatusEntry ::= SEQUENCE {
       acSysInterfaceStatusEntryIndex                  Unsigned32,
       acSysInterfaceStatusTypeIndex                   Unsigned32,
       acSysInterfaceStatusApplicationTypes            INTEGER,
       acSysInterfaceStatusMode                        INTEGER,
       acSysInterfaceStatusIPAddress                   SnmpAdminString,
       acSysInterfaceStatusPrefixLength                Unsigned32,
       acSysInterfaceStatusGateway                     SnmpAdminString,
       acSysInterfaceStatusVlanID                      Unsigned32,
       acSysInterfaceStatusName                        SnmpAdminString
     }



     acSysInterfaceStatusEntryIndex OBJECT-TYPE
       SYNTAX Unsigned32 (0..15)
       MAX-ACCESS not-accessible
       STATUS current
       DESCRIPTION
           "Related Interface index in the interface configuration table
(in case the table is empty - meaning there is only single
IP the index will appear with 0).
AC INI-Param: N/A"
       ::= {acSysInterfaceStatusEntry 1}



     acSysInterfaceStatusTypeIndex OBJECT-TYPE
       SYNTAX Unsigned32 (1..2)
       MAX-ACCESS not-accessible
       STATUS current
       DESCRIPTION
           "
1 - IP Address.
2 - IPv6 Link-Local Address.
AC INI-Param: N/A"
       ::= {acSysInterfaceStatusEntry 2}



     acSysInterfaceStatusApplicationTypes OBJECT-TYPE
       SYNTAX INTEGER {
                  oam(0)
,
                  media(1)
,
                  control(2)
,
                  oamAndMedia(3)
,
                  oamAndControl(4)
,
                  mediaAndControl(5)
,
                  oamAndMediaAndControl(6)
,
                  data(11)

                  }
       MAX-ACCESS read-only
       STATUS current
       DESCRIPTION
           "The type assigned to the interface.
AC INI-Param: N/A"
       ::= {acSysInterfaceStatusEntry 3}



     acSysInterfaceStatusMode OBJECT-TYPE
       SYNTAX INTEGER {
                  iPv6PrefixManual(3)
,
                  iPv6Manual(4)
,
                  iPv4Manual(10)

                  }
       MAX-ACCESS read-only
       STATUS current
       DESCRIPTION
           "Interface configuration mode.
AC INI-Param: N/A"
       ::= {acSysInterfaceStatusEntry 4}



     acSysInterfaceStatusIPAddress OBJECT-TYPE
       SYNTAX SnmpAdminString (SIZE (0..45))
       MAX-ACCESS read-only
       STATUS current
       DESCRIPTION
           "IP Address (can be either IPv4 or IPv6) for this interface.
AC INI-Param: N/A"
       ::= {acSysInterfaceStatusEntry 5}



     acSysInterfaceStatusPrefixLength OBJECT-TYPE
       SYNTAX Unsigned32 (0..128)
       MAX-ACCESS read-only
       STATUS current
       DESCRIPTION
           "The number of ‘1’ bits in this interface’s netmask.
AC INI-Param: N/A"
       ::= {acSysInterfaceStatusEntry 6}



     acSysInterfaceStatusGateway OBJECT-TYPE
       SYNTAX SnmpAdminString (SIZE (0..45))
       MAX-ACCESS read-only
       STATUS current
       DESCRIPTION
           "Default Gateway.
AC INI-Param: N/A"
       ::= {acSysInterfaceStatusEntry 7}



     acSysInterfaceStatusVlanID OBJECT-TYPE
       SYNTAX Unsigned32 (0..4094)
       MAX-ACCESS read-only
       STATUS current
       DESCRIPTION
           "VLAN ID of this interface.
AC INI-Param: N/A"
       ::= {acSysInterfaceStatusEntry 8}



     acSysInterfaceStatusName OBJECT-TYPE
       SYNTAX SnmpAdminString (SIZE (0..16))
       MAX-ACCESS read-only
       STATUS current
       DESCRIPTION
           "16 character string of this interface’s name.
AC INI-Param: N/A"
       ::= {acSysInterfaceStatusEntry 9}



     acSysTime OBJECT IDENTIFIER ::= {acSystemStatus 7}


     acSysTimeUp OBJECT-TYPE
       SYNTAX Unsigned32 (0..2147483647)
       MAX-ACCESS read-only
       STATUS current
       DESCRIPTION
           "Time (in Seconds) that the board is alive.
AC INI-Param: N/A"
       ::= {acSysTime 1}



     acSysVoicePrompt OBJECT IDENTIFIER ::= {acSystemStatus 8}


     acSysVoicePromptTotalMemorySize OBJECT-TYPE
       SYNTAX Unsigned32 (0..2147483647)
       MAX-ACCESS read-only
       STATUS current
       DESCRIPTION
           "Get the total voice prompt memory size.
AC INI-Param: N/A"
       ::= {acSysVoicePrompt 1}



     acSysVoicePromptMaxFreeMemorySize OBJECT-TYPE
       SYNTAX Unsigned32 (0..2147483647)
       MAX-ACCESS read-only
       STATUS current
       DESCRIPTION
           "Get the maximu voice prompt memory free size.
AC INI-Param: N/A"
       ::= {acSysVoicePrompt 2}



     acSysRepositoryAMS OBJECT IDENTIFIER ::= {acSystemStatus 9}


     acSysRepositoryAMSIsReadyForUpdate OBJECT-TYPE
       SYNTAX INTEGER {
                  false(0)
,
                  true(1)

                  }
       MAX-ACCESS read-only
       STATUS current
       DESCRIPTION
           "Verify if the old repository is free or there are signals still
using it.
AC INI-Param: N/A"
       ::= {acSysRepositoryAMS 1}



     acSysHAStatus OBJECT IDENTIFIER ::= {acSystemStatus 10}


     acSysHAStatusReady OBJECT-TYPE
       SYNTAX INTEGER {
                  notApplicable(1)
,
                  yes(2)
,
                  no(3)

                  }
       MAX-ACCESS read-only
       STATUS current
       DESCRIPTION
           "Defines whether the M3K system supports HA or not.
AC INI-Param: N/A"
       ::= {acSysHAStatus 1}



     acSysLDAPStatus OBJECT IDENTIFIER ::= {acSystemStatus 11}


     acSysLDAPStatusServerMode OBJECT-TYPE
       SYNTAX INTEGER {
                  notApplicable(0)
,
                  connectionBroken(1)
,
                  connecting(2)
,
                  connected(3)

                  }
       MAX-ACCESS read-only
       STATUS current
       DESCRIPTION
           "LDAP server status.
AC INI-Param: N/A"
       ::= {acSysLDAPStatus 1}



     acSystemAction OBJECT IDENTIFIER ::= {acSystem 3}


     acSysAction OBJECT IDENTIFIER ::= {acSystemAction 1}


     acSysActionSet OBJECT IDENTIFIER ::= {acSysAction 1}


     acSysActionSetReset OBJECT-TYPE
       SYNTAX Unsigned32 (0..1)
       MAX-ACCESS read-write
       STATUS current
       DESCRIPTION
           "remote Reset.  To remote reset the board, set the value of this
object to 1.
Note: Before Reset, The current boardConfiguration parameters
will be burned to the board.
Access: Instant.
AC INI-Param: N/A"
       ::= {acSysActionSet 1}



     acSysActionSetResetControl OBJECT-TYPE
       SYNTAX INTEGER {
                  resetFromFlashAfterBurn(1)
,
                   resetFromFlashNoBurn(2)
,
                   resetFromBootP(3)

                  }
       MAX-ACCESS read-write
       STATUS current
       DESCRIPTION
           "Determines the remote reset action.
1 - burn staged load image, if any, and config to flash, perform
a reset, and load from flash
2 - perform a reset, and load from flash (staged load image,
if any, and config is not burned to flash)
3 - perform a reset, and load from bootp/tftp (staged load
image, if any, and config burn is not needed)
* - an error is returned for any other value
Note: The staged load image is an image of a cmp file that
was previously loaded to a area in RAM via an HTTP upload.
Access: Instant.
AC INI-Param: RemoteResetControl"
       ::= {acSysActionSet 2}



     acSysActionSetDefaults OBJECT-TYPE
       SYNTAX Unsigned32 (0..1)
       MAX-ACCESS read-write
       STATUS current
       DESCRIPTION
           "To set the board to default values, set the value of this object
to 1.
Access: Instant.
AC INI-Param: N/A"
       ::= {acSysActionSet 3}



     acSysActionSetSaveConfig OBJECT-TYPE
       SYNTAX Unsigned32 (0..1)
       MAX-ACCESS read-write
       STATUS current
       DESCRIPTION
           "To save all current configuration in the board onto the flash,
set the value of this object to 1.
NOTE: Do NOT save the configuration while voice is running
- this will cause a delay.
Access: Instant.
AC INI-Param: N/A"
       ::= {acSysActionSet 4}



     acSysActionSetAutoUpdate OBJECT-TYPE
       SYNTAX Unsigned32 (0..1)
       MAX-ACCESS read-write
       STATUS current
       DESCRIPTION
           "To update the system configuration according to the provisioned
IniFileUrl, set the value of this object to 1.
Access: Instant.
AC INI-Param: N/A"
       ::= {acSysActionSet 5}



     acSysActionSetGetTimeFromNTPServer OBJECT-TYPE
       SYNTAX Unsigned32 (0..1)
       MAX-ACCESS read-write
       STATUS current
       DESCRIPTION
           "Initiates an immediate NTP time fetch.
Access: Instant.
AC INI-Param: N/A"
       ::= {acSysActionSet 6}



     acSysActionSetSwUpgrade OBJECT-TYPE
       SYNTAX INTEGER {
                  hitLessUpGrade(1)
,
                  systemResetUpGrade(2)

                  }
       MAX-ACCESS read-write
       STATUS current
       DESCRIPTION
           "Defines the type of SW upgrade in M3K HA system (Hitless or
system reset).
Access: Instant.
AC INI-Param: M3KHASwUpgradeMode"
       ::= {acSysActionSet 7}



     acSysActionSetOnLineChangesApply OBJECT-TYPE
       SYNTAX INTEGER {
                  defaultValue(0)
,
                  applyChanges(1)

                  }
       MAX-ACCESS read-write
       STATUS current
       DESCRIPTION
           "Applies the board on line changed params.
Access: Instant.
AC INI-Param: N/A"
       ::= {acSysActionSet 8}



     acSysActionSetIPSecTLSUpgrade OBJECT-TYPE
       SYNTAX INTEGER {
                  defaultValue(0)
,
                  upDateChanges(1)

                  }
       MAX-ACCESS read-write
       STATUS current
       DESCRIPTION
           "To update the IPSec TLS configuration according to the provisioned
TLS fils URL  set the value of this object to 1.
Access: Instant.
AC INI-Param: N/A"
       ::= {acSysActionSet 9}



     acSysActionSetGWAppTLSUpgrade OBJECT-TYPE
       SYNTAX INTEGER {
                  defaultValue(0)
,
                  upDateChanges(1)

                  }
       MAX-ACCESS read-write
       STATUS current
       DESCRIPTION
           "To update the GWApp TLS configuration according to the provisioned
TLS fils URL  set the value of this object to 1.
Access: Instant.
AC INI-Param: N/A"
       ::= {acSysActionSet 10}



     acSysActionSetConvertNetworkIFsConfiguration OBJECT-TYPE
       SYNTAX INTEGER {
                  defaultValue(0)
,
                  convertAction(1)

                  }
       MAX-ACCESS read-write
       STATUS current
       DESCRIPTION
           "SET to 1 will convert network configuration to advance multiple
network Interfaces mode.
Access: Instant.
AC INI-Param: N/A"
       ::= {acSysActionSet 11}



     acSysActionSetActionId OBJECT-TYPE
       SYNTAX Unsigned32 (0..2147483647)
       MAX-ACCESS read-write
       STATUS current
       DESCRIPTION
           "This field is for management use and is aimed to distinguish
different managers managing a single device.
Access: Instant.
AC INI-Param: N/A"
       ::= {acSysActionSet 12}



     acSysActionSetAutoUpdateActionResult OBJECT-TYPE
       SYNTAX SnmpAdminString (SIZE (0..200))
       MAX-ACCESS read-only
       STATUS current
       DESCRIPTION
           "Indicates the autoupdates operation status in the form of a
string: 'acSysActionId ; <status> ; <reson>'.
The status field can be: 'success'\'failure'\'inProgress'.
The infromation is valid only when downloading one file at
a time.
Note - a second way of following the success of the file downloading
is to see the files name being updated in the acSysFile
subtree.
AC INI-Param: N/A"
       ::= {acSysActionSet 13}



     acSysActionAdmin OBJECT IDENTIFIER ::= {acSysAction 2}


     acSysActionAdminState OBJECT-TYPE
       SYNTAX INTEGER {
                  locked(0)
,
                   shuttingDown(1)
,
                   unlocked(2)

                  }
       MAX-ACCESS read-write
       STATUS current
       DESCRIPTION
           "Determines the gateway's operational state.
0 - locked: Shutdown the GW In the time frame set by acgwAdminStateLockControl.
1 - shuttingDown: (read only) Graceful Shutdown is being carried
out.
2 - unlocked: GW is in service.
Access: Online.
AC INI-Param: N/A"
       ::= {acSysActionAdmin 1}



     acSysActionAdminStateLockTimeout OBJECT-TYPE
       SYNTAX Integer32 (-1..32768)
       MAX-ACCESS read-write
       STATUS current
       DESCRIPTION
           "Defines the time remaining (in seconds) for the shutdown to
complete. 
 0  = immediate shutdown
-1  = waits until all calls drop (infinite)
>0 = the number of seconds to wait.
Access: Offline.
AC INI-Param: N/A"
       ::= {acSysActionAdmin 2}



     acSysUpload OBJECT IDENTIFIER ::= {acSysAction 3}


     acSysUploadActionType OBJECT-TYPE
       SYNTAX INTEGER {
                  none(0)
,
                  upload(1)
,
                  remove(2)
,
                  actionDone(10)

                  }
       MAX-ACCESS read-write
       STATUS current
       DESCRIPTION
           "Action to be carried out. Setting this field triggers the action.
File upload supported for iniFile(1), v5PortFile(16) and DataConfigurationFile(17)
only access is instant.
File removal supported for all other then iniFile(1),  v5PortFile(16)
and DataConfigurationFile(17), (v5PortFile removal
is done via acV5PortActionType) access is offline.
Access: Instant.
AC INI-Param: N/A"
       ::= {acSysUpload 1}



     acSysUploadFileType OBJECT-TYPE
       SYNTAX INTEGER {
                  iniFile(1)
,
                  cptFile(2)
,
                  vpFile(3)
,
                  prerecordedTonesFile(4)
,
                  fxsCoeffFile(5)
,
                  fxoCoeffFile(6)
,
                  casFile(7)
,
                  xmlFile(8)
,
                  externalCoderFile(9)
,
                  userInfoFile(10)
,
                  dialPlanFile(11)
,
                  tlsPKeyFile(12)
,
                  tlsCertFile(13)
,
                  tlsRootFile(14)
,
                  videoFontFile(15)
,
                  v5PortFile(16)
,
                  dataConfigurationFile(17)

                  }
       MAX-ACCESS read-write
       STATUS current
       DESCRIPTION
           "The file type to be uploaded.
Note - for file types with more then one instance (like CAS
files) use the acSysActionFileInstance to specify which instance
you want to upload.
Access: Instant.
AC INI-Param: N/A"
       ::= {acSysUpload 2}



     acSysUploadFileNumber OBJECT-TYPE
       SYNTAX Integer32 (-1..7)
       MAX-ACCESS read-write
       STATUS current
       DESCRIPTION
           "File number for file types that have more then one file instance,
such  as CAS, VideoFont etc'.
Access: Instant.
AC INI-Param: N/A"
       ::= {acSysUpload 3}



     acSysUploadFileURI OBJECT-TYPE
       SYNTAX SnmpAdminString (SIZE (0..254))
       MAX-ACCESS read-write
       STATUS current
       DESCRIPTION
           "URI indicating file location to be downloaded to.
Access: Instant.
AC INI-Param: N/A"
       ::= {acSysUpload 4}



     acSysUploadActionID OBJECT-TYPE
       SYNTAX Unsigned32 (0..2147483647)
       MAX-ACCESS read-write
       STATUS current
       DESCRIPTION
           "This field is for management use and is aimed to distinguish
different managers managing a single device.
Access: Instant.
AC INI-Param: N/A"
       ::= {acSysUpload 5}



     acSysUploadActionResult OBJECT-TYPE
       SYNTAX SnmpAdminString (SIZE (0..40))
       MAX-ACCESS read-only
       STATUS current
       DESCRIPTION
           "Action result. Includes action status (success, failure or inProgress),
action ID.
AC INI-Param: N/A"
       ::= {acSysUpload 6}



     acSystemChassis OBJECT IDENTIFIER ::= {acSystem 4}


     acSystemChassisDryContactsOutStatus OBJECT-TYPE
       SYNTAX BITS {
                  noAlarm(0)
,
                  criticalAlarm(1)
,
                  majorAlarm(2)
,
                  minorAlarm(3)

                  }
       MAX-ACCESS read-only
       STATUS current
       DESCRIPTION
           "Indicates current state of the alarm dry contacts – out signals
(3 signals).  This is a bit-map of possible conditions.
AC INI-Param: N/A"
       ::= {acSystemChassis 1}



     acSystemChassisDryContactsInStatus OBJECT-TYPE
       SYNTAX BITS {
                  noAlarm(0)
,
                  alarm1(1)

                  }
       MAX-ACCESS read-only
       STATUS current
       DESCRIPTION
           "Indicates current state of the alarm dry contacts - in signals
(1 signals). The role of each input signal should be according
to the customer's requirements. This is a bit-map of possible
conditions.
AC INI-Param: N/A"
       ::= {acSystemChassis 2}



     acSystemChassisLastChanged OBJECT-TYPE
       SYNTAX Unsigned32 (0..4294967295)
       MAX-ACCESS read-only
       STATUS current
       DESCRIPTION
           "The value of sysUpTime at the time a row is modified in any
of the acSystemChassis subtree's objects.
AC INI-Param: N/A"
       ::= {acSystemChassis 3}



     -- ****************************************
     -- acSysModule table declaration
     -- ****************************************
     acSysModuleTable OBJECT-TYPE
       SYNTAX SEQUENCE OF AcSysModuleEntry
       MAX-ACCESS not-accessible
       STATUS current
       DESCRIPTION
           " "
       ::= {acSystemChassis 21}



     -- ****************************************
     -- acSysModule table entry
     -- ****************************************
     acSysModuleEntry OBJECT-TYPE
       SYNTAX AcSysModuleEntry
       MAX-ACCESS not-accessible
       STATUS current
       DESCRIPTION
           ""
       INDEX {acSysModuleIndex}
       ::= {acSysModuleTable 1}



     -- ****************************************
     -- acSysModule TABLE
     -- ****************************************
     AcSysModuleEntry ::= SEQUENCE {
       acSysModuleIndex                                Unsigned32,
       acSysModuleGeographicalPosition                 Unsigned32,
       acSysModuleType                                 INTEGER,
       acSysModulePresence                             INTEGER,
       acSysModuleLicenseKeyList                       SnmpAdminString,
       acSysModuleSerialNumber                         Integer32,
       acSysModuleSWVersion                            SnmpAdminString,
       acSysModuleOperationalState                     INTEGER,
       acSysModuleHAStatus                             INTEGER,
       acSysModuleLEDs                                 OCTET STRING,
       acSysModuleTemperature                          Integer32,
       acSysModuleActions                              INTEGER,
       acSysModuleFRUaction                            INTEGER,
       acSysModuleFRUstatus                            INTEGER,
       acSysModuleNumOfPorts                           Unsigned32,
       acSysModuleFirstPortNum                         Unsigned32
     }



     acSysModuleIndex OBJECT-TYPE
       SYNTAX Unsigned32 (1..2147483647)
       MAX-ACCESS not-accessible
       STATUS current
       DESCRIPTION
           "The Module number in the system.
AC INI-Param: N/A"
       ::= {acSysModuleEntry 1}



     acSysModuleGeographicalPosition OBJECT-TYPE
       SYNTAX Unsigned32 (1..4)
       MAX-ACCESS read-only
       STATUS current
       DESCRIPTION
           "The slot number in the chassis. 1 being the bottom slot and
so on.
AC INI-Param: N/A"
       ::= {acSysModuleEntry 2}



     acSysModuleType OBJECT-TYPE
       SYNTAX INTEGER {
                  acUnknown(0)
,
                  acTrunkPack-08(1)
,
                  acMediaPack-108(2)
,
                  acMediaPack-124(3)
,
                  acTrunkPack-1600(20)
,
                  acTPM1100(22)
,
                  acTrunkPack-260-IpMedia(23)
,
                  acTrunkPack-1610(24)
,
                  acMediaPack-104(25)
,
                  acMediaPack-102(26)
,
                  acTrunkPack-1610-SB(29)
,
                  acTrunkPack-1610-IpMedia(30)
,
                  acTrunkPack-MEDIANT2000(31)
,
                  acTrunkPack-STRETTO2000(32)
,
                  acTrunkPack-IPMServer2000(33)
,
                  acTrunkPack-2810(34)
,
                  acTrunkPack-260-UN-IpMedia (35)
,
                  acTrunkPack-260-IpMedia-30Ch(36)
,
                  acTrunkPack-260-IpMedia-60Ch(37)
,
                  acTrunkPack-260-IpMedia-120Ch(38)
,
                  acTrunkPack-260RT-IpMedia-30Ch(39)
,
                  acTrunkPack-260RT-IpMedia-60Ch(40)
,
                  acTrunkPack-260RT-IpMedia-120Ch(41)
,
                  acTrunkPack-260(42)
,
                  acTrunkPack-260-UN (43)
,
                  acTPM1100-PCM(44)
,
                  acTrunkPack-6310(45)
,
                  acTPM6300(46)
,
                  acMediant1000(47)
,
                  acIPMedia3000(48)
,
                  acMediant3000(49)
,
                  acStretto3000(50)
,
                  acTrunkPack-6310-IpMedia(51)
,
                  acTrunkPack-6310-SB(52)
,
                  acATP-1610(53)
,
                  acATP-260(54)
,
                  acATP-260-UN(55)
,
                  acMediaPack-118(56)
,
                  acMediaPack114(57)
,
                  acMediaPack112(58)
,
                  acTrunkPack-6310-T3(59)
,
                  acMediant3000-T3(60)
,
                  acIPmedia3000-T3(61)
,
                  acTrunkPack-6310-T3-IpMedia(62)
,
                  acTrunkPack-8410(63)
,
                  acTrunkPack-8410-IpMedia(64)
,
                  acMediaPack-500-MSBG(69)
,
                  sA1(250)
,
                  sA2(251)
,
                  sA3(252)
,
                  acMediant1000CPUmodule(253)
,
                  acMediant1000IFDigitalModule(254)
,
                  acMediant1000IFAnalogModule(255)
,
                  acMediant1000IFBRIModule(256)
,
                  acMediant1000IPMediaModule(257)
,
                  acMediant600CPUmodule(258)
,
                  acMediant600IFDigitalModule(259)
,
                  acMediant600IFAnalogModule(260)
,
                  acMediant600IFBRIModule(261)
,
                  acMediant600IPMediaModule(262)
,
                  acMediaPack500CPUmodule(265)
,
                  acMediaPack500IFDigitalModule(266)
,
                  acMediaPack500IFAnalogModule(267)
,
                  acMediaPack500IFBRIModule(268)
,
                  acMediaPack500IFWANModule(269)
,
                  acMediaPack500IFWiFiModule(270)
,
                  acMediaPack500IPMediaModule(271)
,
                  acMediaPack500EthernetModule(272)
,
                  acMediaPack500IFT1WANModule(273)
,
                  acMediaPack500IFSHDSLModule(274)
,
                  acMediaPack500IFADSLModule(275)
,
                  acMediant1000IFWANModule(276)
,
                  acMediant1000IFT1WANModule(277)
,
                  acMediant1000IFSHDSLModule(278)
,
                  acMediant1000IFADSLModule(279)

                  }
       MAX-ACCESS read-only
       STATUS current
       DESCRIPTION
           "The module's type.
AC INI-Param: N/A"
       ::= {acSysModuleEntry 3}



     acSysModulePresence OBJECT-TYPE
       SYNTAX INTEGER {
                  present(1)
,
                  missing(2)

                  }
       MAX-ACCESS read-only
       STATUS current
       DESCRIPTION
           "Is the module present or missing.
AC INI-Param: N/A"
       ::= {acSysModuleEntry 4}



     acSysModuleLicenseKeyList OBJECT-TYPE
       SYNTAX SnmpAdminString (SIZE (0..1400))
       MAX-ACCESS read-only
       STATUS current
       DESCRIPTION
           "List of active features as enabled by the license key. SA modules
return NULL.
AC INI-Param: N/A"
       ::= {acSysModuleEntry 5}



     acSysModuleSerialNumber OBJECT-TYPE
       SYNTAX Integer32 (-1..2147483647)
       MAX-ACCESS read-only
       STATUS current
       DESCRIPTION
           "The module's serial number.
For 6310 the serial number is the decimal form of the last
5 characters in the MAC Address.
 SA modules return 0.
 When the modules in the table are unavailable for audit (no
HA) (-1) is returned.
AC INI-Param: N/A"
       ::= {acSysModuleEntry 6}



     acSysModuleSWVersion OBJECT-TYPE
       SYNTAX SnmpAdminString (SIZE (0..20))
       MAX-ACCESS read-only
       STATUS current
       DESCRIPTION
           "The version of the SW being run in the module placed .
 SA Modules return NULL.
AC INI-Param: N/A"
       ::= {acSysModuleEntry 7}



     acSysModuleOperationalState OBJECT-TYPE
       SYNTAX INTEGER {
                  disable(1)
,
                  enable(2)

                  }
       MAX-ACCESS read-only
       STATUS current
       DESCRIPTION
           "The operational state of the module. Determined internally by
the system.
AC INI-Param: N/A"
       ::= {acSysModuleEntry 8}



     acSysModuleHAStatus OBJECT-TYPE
       SYNTAX INTEGER {
                  acitveNonHA(1)
,
                  active(2)
,
                  redundant(3)
,
                  standAlone(4)
,
                  redundantNonHA(5)
,
                  notApplicable(6)

                  }
       MAX-ACCESS read-only
       STATUS current
       DESCRIPTION
           "Modules status with in the system. Designed to define the HA
state.
AC INI-Param: N/A"
       ::= {acSysModuleEntry 9}



     acSysModuleLEDs OBJECT-TYPE
       SYNTAX OCTET STRING (SIZE (0..50))
       MAX-ACCESS read-only
       STATUS current
       DESCRIPTION
           "Bit Field for the LEDs on the front of the module.
LSB in each nibble (half Byte) is 0 - constant, 1 - blinking.
3 MSB are the color -
 0 - none
 1- Green
 2 - Red 
 3 - Yellow
 4 - Orange
 5 - Blue
 7 - Gray (unknown).
AC INI-Param: N/A"
       ::= {acSysModuleEntry 10}



     acSysModuleTemperature OBJECT-TYPE
       SYNTAX Integer32 (-1..100)
       MAX-ACCESS read-only
       STATUS current
       DESCRIPTION
           "Temperature of the board in degrees Celsius. SA Modules return
0.
AC INI-Param: N/A"
       ::= {acSysModuleEntry 11}



     acSysModuleActions OBJECT-TYPE
       SYNTAX INTEGER {
                  reset(1)
,
                  switchOver(2)
,
                  actionDone(3)

                  }
       MAX-ACCESS read-write
       STATUS current
       DESCRIPTION
           "Actions to be performed by the module.
Access: Instant.
AC INI-Param: N/A"
       ::= {acSysModuleEntry 12}



     acSysModuleFRUaction OBJECT-TYPE
       SYNTAX INTEGER {
                  fruActionDone(1)
,
                  fruOutOfServiceAction(2)
,
                  fruBackToServiceAction(3)
,
                  fruNotApplicable(4)

                  }
       MAX-ACCESS read-write
       STATUS current
       DESCRIPTION
           "Field Replace Unit actions
Relevant to IF-Module only.
Access: Instant.
AC INI-Param: N/A"
       ::= {acSysModuleEntry 13}



     acSysModuleFRUstatus OBJECT-TYPE
       SYNTAX INTEGER {
                  moduleNotExist(1)
,
                  moduleExistOk(2)
,
                  moduleOutOfService(3)
,
                  moduleBackToServiceStart(4)
,
                  moduleMismatch(5)
,
                  moduleFaulty(6)
,
                  notApplicable(7)

                  }
       MAX-ACCESS read-only
       STATUS current
       DESCRIPTION
           "Field Replace Unit module's status.
AC INI-Param: N/A"
       ::= {acSysModuleEntry 14}



     acSysModuleNumOfPorts OBJECT-TYPE
       SYNTAX Unsigned32 (1..4)
       MAX-ACCESS read-only
       STATUS current
       DESCRIPTION
           "The number of  physical interfaces in a module, analog or digital.
AC INI-Param: N/A"
       ::= {acSysModuleEntry 15}



     acSysModuleFirstPortNum OBJECT-TYPE
       SYNTAX Unsigned32 (0..19)
       MAX-ACCESS read-only
       STATUS current
       DESCRIPTION
           "The logical number as seen in the general trunk/analog-channel
table of the first port in the module in question.
Since analog and digital ports can be operational at once,
analog and digital ports may have same logical number.
AC INI-Param: N/A"
       ::= {acSysModuleEntry 16}



     -- ****************************************
     -- acSysFanTray table declaration
     -- ****************************************
     acSysFanTrayTable OBJECT-TYPE
       SYNTAX SEQUENCE OF AcSysFanTrayEntry
       MAX-ACCESS not-accessible
       STATUS current
       DESCRIPTION
           ""
       ::= {acSystemChassis 22}



     -- ****************************************
     -- acSysFanTray table entry
     -- ****************************************
     acSysFanTrayEntry OBJECT-TYPE
       SYNTAX AcSysFanTrayEntry
       MAX-ACCESS not-accessible
       STATUS current
       DESCRIPTION
           ""
       INDEX {acSysFanTrayIndex}
       ::= {acSysFanTrayTable 1}



     -- ****************************************
     -- acSysFanTray TABLE
     -- ****************************************
     AcSysFanTrayEntry ::= SEQUENCE {
       acSysFanTrayIndex                               Unsigned32,
       acSysFanTrayGeographicalPosition                Unsigned32,
       acSysFanTrayExistence                           INTEGER,
       acSysFanTrayType                                SnmpAdminString,
       acSysFanTrayLEDs                                OCTET STRING,
       acSysFanTraySeverity                            INTEGER,
       acSysFanTrayFansConfiguredSpeed                 OCTET STRING,
       acSysFanTrayFansCurrentSpeed                    OCTET STRING,
       acSysFanTrayFansStatus                          OCTET STRING
     }



     acSysFanTrayIndex OBJECT-TYPE
       SYNTAX Unsigned32 (1..2147483647)
       MAX-ACCESS not-accessible
       STATUS current
       DESCRIPTION
           "Fan-Tray's index in the system.
AC INI-Param: N/A"
       ::= {acSysFanTrayEntry 1}



     acSysFanTrayGeographicalPosition OBJECT-TYPE
       SYNTAX Unsigned32 (1..1)
       MAX-ACCESS read-only
       STATUS current
       DESCRIPTION
           "The slot number in the chassis.
AC INI-Param: N/A"
       ::= {acSysFanTrayEntry 2}



     acSysFanTrayExistence OBJECT-TYPE
       SYNTAX INTEGER {
                  present(1)
,
                  missing(2)

                  }
       MAX-ACCESS read-only
       STATUS current
       DESCRIPTION
           "Is the Fan-Tray present or missing.
AC INI-Param: N/A"
       ::= {acSysFanTrayEntry 3}



     acSysFanTrayType OBJECT-TYPE
       SYNTAX SnmpAdminString (SIZE (0..50))
       MAX-ACCESS read-only
       STATUS current
       DESCRIPTION
           "The type of the Fan-Tray .
AC INI-Param: N/A"
       ::= {acSysFanTrayEntry 4}



     acSysFanTrayLEDs OBJECT-TYPE
       SYNTAX OCTET STRING (SIZE (0..20))
       MAX-ACCESS read-only
       STATUS current
       DESCRIPTION
           "This object built as a bit-field which represents the Fan-Tray's
LEDs status.
The first four bites represent the System's
LED status and the last four bites represent the Shelf-LED’s
status.
AC INI-Param: N/A"
       ::= {acSysFanTrayEntry 5}



     acSysFanTraySeverity OBJECT-TYPE
       SYNTAX INTEGER {
                  cleared(0)
,
                  indeterminate(1)
,
                  warning(2)
,
                  minor(3)
,
                  major(4)
,
                  critical(5)

                  }
       MAX-ACCESS read-only
       STATUS current
       DESCRIPTION
           "The Severity of the whole fan tray according to the current
active alarm in the alarm table: Critical, Major or cleared.
AC INI-Param: N/A"
       ::= {acSysFanTrayEntry 6}



     acSysFanTrayFansConfiguredSpeed OBJECT-TYPE
       SYNTAX OCTET STRING (SIZE (0..8))
       MAX-ACCESS read-only
       STATUS current
       DESCRIPTION
           "The fan's configured speed in Tach units (RPM/120). Each Byte
represents a fan.
AC INI-Param: N/A"
       ::= {acSysFanTrayEntry 7}



     acSysFanTrayFansCurrentSpeed OBJECT-TYPE
       SYNTAX OCTET STRING (SIZE (0..8))
       MAX-ACCESS read-only
       STATUS current
       DESCRIPTION
           "The fan's mesured speed in Tach units (RPM/120). Each Byte represents
a fan.
AC INI-Param: N/A"
       ::= {acSysFanTrayEntry 8}



     acSysFanTrayFansStatus OBJECT-TYPE
       SYNTAX OCTET STRING (SIZE (0..1))
       MAX-ACCESS read-only
       STATUS current
       DESCRIPTION
           "A bit field which display the working status of each fan in
the Fan-Tray.
0 - Working
1 - Faulty.
AC INI-Param: N/A"
       ::= {acSysFanTrayEntry 9}



     -- ****************************************
     -- acSysPowerSupply table declaration
     -- ****************************************
     acSysPowerSupplyTable OBJECT-TYPE
       SYNTAX SEQUENCE OF AcSysPowerSupplyEntry
       MAX-ACCESS not-accessible
       STATUS current
       DESCRIPTION
           ""
       ::= {acSystemChassis 23}



     -- ****************************************
     -- acSysPowerSupply table entry
     -- ****************************************
     acSysPowerSupplyEntry OBJECT-TYPE
       SYNTAX AcSysPowerSupplyEntry
       MAX-ACCESS not-accessible
       STATUS current
       DESCRIPTION
           ""
       INDEX {acSysPowerSupplyIndex}
       ::= {acSysPowerSupplyTable 1}



     -- ****************************************
     -- acSysPowerSupply TABLE
     -- ****************************************
     AcSysPowerSupplyEntry ::= SEQUENCE {
       acSysPowerSupplyIndex                           Unsigned32,
       acSysPowerSupplyGeographicalPosition            Unsigned32,
       acSysPowerSupplyExistence                       INTEGER,
       acSysPowerSupplyHwversion                       SnmpAdminString,
       acSysPowerSupplyLEDs                            OCTET STRING,
       acSysPowerSupplySeverity                        INTEGER
     }



     acSysPowerSupplyIndex OBJECT-TYPE
       SYNTAX Unsigned32 (1..2147483647)
       MAX-ACCESS not-accessible
       STATUS current
       DESCRIPTION
           "Power-Supply's index in the system.
AC INI-Param: N/A"
       ::= {acSysPowerSupplyEntry 1}



     acSysPowerSupplyGeographicalPosition OBJECT-TYPE
       SYNTAX Unsigned32 (1..2)
       MAX-ACCESS read-only
       STATUS current
       DESCRIPTION
           "The slot number in the chassis.
AC INI-Param: N/A"
       ::= {acSysPowerSupplyEntry 2}



     acSysPowerSupplyExistence OBJECT-TYPE
       SYNTAX INTEGER {
                  present(1)
,
                  missing(2)

                  }
       MAX-ACCESS read-only
       STATUS current
       DESCRIPTION
           "Is the Power-Supply present or missing.
AC INI-Param: N/A"
       ::= {acSysPowerSupplyEntry 3}



     acSysPowerSupplyHwversion OBJECT-TYPE
       SYNTAX SnmpAdminString (SIZE (0..20))
       MAX-ACCESS read-only
       STATUS current
       DESCRIPTION
           "PS’s HW version.
AC INI-Param: N/A"
       ::= {acSysPowerSupplyEntry 4}



     acSysPowerSupplyLEDs OBJECT-TYPE
       SYNTAX OCTET STRING (SIZE (0..20))
       MAX-ACCESS read-only
       STATUS current
       DESCRIPTION
           "A bit-field representation of the Power-Supply LEDs' status.
The first four bites represent the Power-Supply LED's status
and the last four bites represent the Fault LED's status.
AC INI-Param: N/A"
       ::= {acSysPowerSupplyEntry 5}



     acSysPowerSupplySeverity OBJECT-TYPE
       SYNTAX INTEGER {
                  cleared(1)
,
                  indeterminate(2)
,
                  warning(3)
,
                  minor(4)
,
                  major(5)
,
                  critical(6)

                  }
       MAX-ACCESS read-only
       STATUS current
       DESCRIPTION
           "The Severity of the power-supply according to the current active
alarm in the alarm table.
AC INI-Param: N/A"
       ::= {acSysPowerSupplyEntry 6}



     -- ****************************************
     -- acSysPEM table declaration
     -- ****************************************
     acSysPEMTable OBJECT-TYPE
       SYNTAX SEQUENCE OF AcSysPEMEntry
       MAX-ACCESS not-accessible
       STATUS current
       DESCRIPTION
           ""
       ::= {acSystemChassis 24}



     -- ****************************************
     -- acSysPEM table entry
     -- ****************************************
     acSysPEMEntry OBJECT-TYPE
       SYNTAX AcSysPEMEntry
       MAX-ACCESS not-accessible
       STATUS current
       DESCRIPTION
           ""
       INDEX {acSysPEMIndex}
       ::= {acSysPEMTable 1}



     -- ****************************************
     -- acSysPEM TABLE
     -- ****************************************
     AcSysPEMEntry ::= SEQUENCE {
       acSysPEMIndex                                   Unsigned32,
       acSysPEMGeographicalPosition                    Unsigned32,
       acSysPEMExistence                               INTEGER,
       acSysPEMType                                    SnmpAdminString,
       acSysPEMElectricWireConnection                  INTEGER
     }



     acSysPEMIndex OBJECT-TYPE
       SYNTAX Unsigned32 (1..2147483647)
       MAX-ACCESS not-accessible
       STATUS current
       DESCRIPTION
           "PEM-Module's index in the system.
AC INI-Param: N/A"
       ::= {acSysPEMEntry 1}



     acSysPEMGeographicalPosition OBJECT-TYPE
       SYNTAX Unsigned32 (1..2)
       MAX-ACCESS read-only
       STATUS current
       DESCRIPTION
           "The slot number in the chassis.
AC INI-Param: N/A"
       ::= {acSysPEMEntry 2}



     acSysPEMExistence OBJECT-TYPE
       SYNTAX INTEGER {
                  present(1)
,
                  missing(2)

                  }
       MAX-ACCESS read-only
       STATUS current
       DESCRIPTION
           "Is the PEM-Module present or missing.
AC INI-Param: N/A"
       ::= {acSysPEMEntry 3}



     acSysPEMType OBJECT-TYPE
       SYNTAX SnmpAdminString (SIZE (0..20))
       MAX-ACCESS read-only
       STATUS current
       DESCRIPTION
           "PEM’s Type.
AC INI-Param: N/A"
       ::= {acSysPEMEntry 4}



     acSysPEMElectricWireConnection OBJECT-TYPE
       SYNTAX INTEGER {
                  connected(1)
,
                  disconnected(2)

                  }
       MAX-ACCESS read-only
       STATUS current
       DESCRIPTION
           "Present the status of the electricity connector located on the
PEM card.
AC INI-Param: N/A"
       ::= {acSysPEMEntry 5}



     acSysSATModule OBJECT IDENTIFIER ::= {acSystemChassis 25}


     -- ****************************************
     -- acSysSAT table declaration
     -- ****************************************
     acSysSATTable OBJECT-TYPE
       SYNTAX SEQUENCE OF AcSysSATEntry
       MAX-ACCESS not-accessible
       STATUS current
       DESCRIPTION
           ""
       ::= {acSysSATModule 21}



     -- ****************************************
     -- acSysSAT table entry
     -- ****************************************
     acSysSATEntry OBJECT-TYPE
       SYNTAX AcSysSATEntry
       MAX-ACCESS not-accessible
       STATUS current
       DESCRIPTION
           ""
       INDEX {acSysSATSatIndex}
       ::= {acSysSATTable 1}



     -- ****************************************
     -- acSysSAT TABLE
     -- ****************************************
     AcSysSATEntry ::= SEQUENCE {
       acSysSATSatIndex                                Unsigned32,
       acSysSATGeographicalPosition                    Unsigned32,
       acSysSATType                                    SnmpAdminString,
       acSysSATInitInformation                         INTEGER,
       acSysSATTimingUnitExistence                     INTEGER,
       acSysSATTimingRefSelection                      INTEGER
     }



     acSysSATSatIndex OBJECT-TYPE
       SYNTAX Unsigned32 (1..2)
       MAX-ACCESS not-accessible
       STATUS current
       DESCRIPTION
           "SAT-Module's index in the system.
AC INI-Param: N/A"
       ::= {acSysSATEntry 1}



     acSysSATGeographicalPosition OBJECT-TYPE
       SYNTAX Unsigned32 (2..4)
       MAX-ACCESS read-only
       STATUS current
       DESCRIPTION
           "The slot number in the chassis.
AC INI-Param: N/A"
       ::= {acSysSATEntry 2}



     acSysSATType OBJECT-TYPE
       SYNTAX SnmpAdminString (SIZE (0..20))
       MAX-ACCESS read-only
       STATUS current
       DESCRIPTION
           "SAT’s Type.
AC INI-Param: N/A"
       ::= {acSysSATEntry 3}



     acSysSATInitInformation OBJECT-TYPE
       SYNTAX INTEGER {
                  detected(0)
,
                  reConfig(1)
,
                  reConfigTry2(2)
,
                  reConfigTry3(3)
,
                  notInitialized(4)
,
                  initIsMissing(5)
,
                  initWasReset(6)
,
                  initFail(7)
,
                  initInProgress(8)
,
                  initUpdateREFTable(9)
,
                  remoteKeepAlive(10)
,
                  initComplete(11)

                  }
       MAX-ACCESS read-only
       STATUS current
       DESCRIPTION
           "Sat's Init Information.
AC INI-Param: N/A"
       ::= {acSysSATEntry 4}



     acSysSATTimingUnitExistence OBJECT-TYPE
       SYNTAX INTEGER {
                  exist(1)
,
                  notExist(2)

                  }
       MAX-ACCESS read-only
       STATUS current
       DESCRIPTION
           "Is the Timig Unit present or missing.
AC INI-Param: N/A"
       ::= {acSysSATEntry 5}



     acSysSATTimingRefSelection OBJECT-TYPE
       SYNTAX INTEGER {
                  bITSNOREF(0)
,
                  rEFFromBITSA(1)
,
                  rEFFromBITSB(2)
,
                  bITSNOREF1(3)
,
                  rEFFromLineClock1(4)
,
                  rEFFromLineClock2(5)
,
                  rEFFromLineClock3(6)
,
                  rEFFromLineClock7(7)

                  }
       MAX-ACCESS read-only
       STATUS current
       DESCRIPTION
           "SAT's Timing Reference Selection.
AC INI-Param: N/A"
       ::= {acSysSATEntry 6}



     -- ****************************************
     -- acSysSATFramers table declaration
     -- ****************************************
     acSysSATFramersTable OBJECT-TYPE
       SYNTAX SEQUENCE OF AcSysSATFramersEntry
       MAX-ACCESS not-accessible
       STATUS current
       DESCRIPTION
           ""
       ::= {acSysSATModule 22}



     -- ****************************************
     -- acSysSATFramers table entry
     -- ****************************************
     acSysSATFramersEntry OBJECT-TYPE
       SYNTAX AcSysSATFramersEntry
       MAX-ACCESS not-accessible
       STATUS current
       DESCRIPTION
           ""
       INDEX {acSysSATFramersSatIndex,acSysSATFramersFramerIndex}
       ::= {acSysSATFramersTable 1}



     -- ****************************************
     -- acSysSATFramers TABLE
     -- ****************************************
     AcSysSATFramersEntry ::= SEQUENCE {
       acSysSATFramersSatIndex                         Unsigned32,
       acSysSATFramersFramerIndex                      Unsigned32,
       acSysSATFramersFramerInterfaceStatus            INTEGER,
       acSysSATFramersFramerLoopBackRef                INTEGER,
       acSysSATFramersFramerInterfaceType              INTEGER,
       acSysSATFramersFramerTransmitControl            INTEGER,
       acSysSATFramersRxStatus                         INTEGER,
       acSysSATFramersIsUsedAsPLLClock                 INTEGER
     }



     acSysSATFramersSatIndex OBJECT-TYPE
       SYNTAX Unsigned32 (1..2)
       MAX-ACCESS not-accessible
       STATUS current
       DESCRIPTION
           "SAT-Module's index in the system.
AC INI-Param: N/A"
       ::= {acSysSATFramersEntry 1}



     acSysSATFramersFramerIndex OBJECT-TYPE
       SYNTAX Unsigned32 (1..2)
       MAX-ACCESS not-accessible
       STATUS current
       DESCRIPTION
           "Framer's Index.
AC INI-Param: N/A"
       ::= {acSysSATFramersEntry 2}



     acSysSATFramersFramerInterfaceStatus OBJECT-TYPE
       SYNTAX INTEGER {
                  framerInitialized(0)
,
                  framerNotInitialized(1)

                  }
       MAX-ACCESS read-only
       STATUS current
       DESCRIPTION
           "Framer Interface Status.
AC INI-Param: N/A"
       ::= {acSysSATFramersEntry 3}



     acSysSATFramersFramerLoopBackRef OBJECT-TYPE
       SYNTAX INTEGER {
                  loopdisable(0)
,
                  loopenable(1)

                  }
       MAX-ACCESS read-only
       STATUS current
       DESCRIPTION
           "Frame rLoop Back Reference.
AC INI-Param: N/A"
       ::= {acSysSATFramersEntry 4}



     acSysSATFramersFramerInterfaceType OBJECT-TYPE
       SYNTAX INTEGER {
                  e1CRC4(0)
,
                  e1CAS(1)
,
                  e1FAS(2)
,
                  t1D4(3)
,
                  t1ESF(4)
,
                  t12(5)

                  }
       MAX-ACCESS read-only
       STATUS current
       DESCRIPTION
           "Framer Interface Type.
AC INI-Param: N/A"
       ::= {acSysSATFramersEntry 5}



     acSysSATFramersFramerTransmitControl OBJECT-TYPE
       SYNTAX INTEGER {
                  systemClock(0)
,
                  aIS(1)
,
                  disableTransmit(2)

                  }
       MAX-ACCESS read-only
       STATUS current
       DESCRIPTION
           "Framer Transmit Control.
AC INI-Param: N/A"
       ::= {acSysSATFramersEntry 6}



     acSysSATFramersRxStatus OBJECT-TYPE
       SYNTAX INTEGER {
                  alarmClear(0)
,
                  lOFAlarm(1)
,
                  lOSAlarm(2)
,
                  aISAlarm(3)
,
                  aISInit(4)

                  }
       MAX-ACCESS read-only
       STATUS current
       DESCRIPTION
           "Provides the alarm status of the clock interface.
AC INI-Param: N/A"
       ::= {acSysSATFramersEntry 7}



     acSysSATFramersIsUsedAsPLLClock OBJECT-TYPE
       SYNTAX INTEGER {
                  notUsed(0)
,
                  used(1)

                  }
       MAX-ACCESS read-only
       STATUS current
       DESCRIPTION
           "Is Used As PLL Clock indication.
AC INI-Param: N/A"
       ::= {acSysSATFramersEntry 8}



     acSysTimingModule OBJECT IDENTIFIER ::= {acSystemChassis 26}


     -- ****************************************
     -- acSysPLLStatus table declaration
     -- ****************************************
     acSysPLLStatusTable OBJECT-TYPE
       SYNTAX SEQUENCE OF AcSysPLLStatusEntry
       MAX-ACCESS not-accessible
       STATUS current
       DESCRIPTION
           ""
       ::= {acSysTimingModule 21}



     -- ****************************************
     -- acSysPLLStatus table entry
     -- ****************************************
     acSysPLLStatusEntry OBJECT-TYPE
       SYNTAX AcSysPLLStatusEntry
       MAX-ACCESS not-accessible
       STATUS current
       DESCRIPTION
           ""
       INDEX {acSysPLLStatusIndex}
       ::= {acSysPLLStatusTable 1}



     -- ****************************************
     -- acSysPLLStatus TABLE
     -- ****************************************
     AcSysPLLStatusEntry ::= SEQUENCE {
       acSysPLLStatusIndex                             Unsigned32,
       acSysPLLStatusOperatingMode                     INTEGER
     }



     acSysPLLStatusIndex OBJECT-TYPE
       SYNTAX Unsigned32 (0..1)
       MAX-ACCESS not-accessible
       STATUS current
       DESCRIPTION
           "Table's Index.
AC INI-Param: N/A"
       ::= {acSysPLLStatusEntry 1}



     acSysPLLStatusOperatingMode OBJECT-TYPE
       SYNTAX INTEGER {
                  freeRun(0)
,
                  lockToRef1(1)
,
                  lockToRef2(2)
,
                  lockToLocal(3)
,
                  holdOver(4)

                  }
       MAX-ACCESS read-only
       STATUS current
       DESCRIPTION
           "PLL's Current Operating Mode.
AC INI-Param: N/A"
       ::= {acSysPLLStatusEntry 2}





END
