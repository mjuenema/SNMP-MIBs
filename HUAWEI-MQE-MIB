--
-- HUAWEI-MQE-MIB49.mib
-- MIB generated by MG SOFT Visual MIB Builder Version 3.0 Build 253
-- Wednesday, December 15, 2010 at 16:05:18
--

	HUAWEI-MQE-MIB DEFINITIONS ::= BEGIN
 
		IMPORTS
			hwDatacomm			
				FROM HUAWEI-MIB			
			EnabledStatus			
				FROM P-BRIDGE-MIB			
			OBJECT-GROUP, NOTIFICATION-GROUP			
				FROM SNMPv2-CONF			
			IpAddress, Integer32, Unsigned32, Gauge32, BITS, 
			OBJECT-TYPE, MODULE-IDENTITY, NOTIFICATION-TYPE			
				FROM SNMPv2-SMI			
			RowStatus			
				FROM SNMPv2-TC;
	
	
--  June 19, 2009 at 14:53 GMT
		hwMqeMIB MODULE-IDENTITY 
			LAST-UPDATED "200906191453Z"		-- June 19, 2009 at 14:53 GMT
			ORGANIZATION 
				"Huawei Technologies co.,Ltd."
			CONTACT-INFO 
				"Contact-info."
			DESCRIPTION 
				"The Mqe MIB module is defined to manage the configuration for FCC, RET, QoE."
			::= { hwDatacomm 203 }
		
	
	
--
-- Node definitions
--
	
--  Node definitions
-- 
-- 1.3.6.1.4.1.2011.5.25.203.1
		-- 1.3.6.1.4.1.2011.5.25.203.2
		hwMqeObjects OBJECT IDENTIFIER ::= { hwMqeMIB 2 }
		
		-- 1.3.6.1.4.1.2011.5.25.203.2.1
		hwMqeScalar OBJECT IDENTIFIER ::= { hwMqeObjects 1 }
		
		-- 1.3.6.1.4.1.2011.5.25.203.2.1.1
		hwMqeEnable OBJECT-TYPE
			SYNTAX EnabledStatus
			MAX-ACCESS read-write
			STATUS current
			DESCRIPTION
				"Description."
			::= { hwMqeScalar 1 }
		
		-- 1.3.6.1.4.1.2011.5.25.203.2.1.2
		hwMqeTrapEnable OBJECT-TYPE
			SYNTAX BITS
				{
				trapdf(0),
				trapmlr(1),
				trapvmos(2)
				}
			MAX-ACCESS read-write
			STATUS current
			DESCRIPTION
				"Description."
			::= { hwMqeScalar 2 }
		
		-- 1.3.6.1.4.1.2011.5.25.203.2.1.3
		hwMqeFtpEnable OBJECT-TYPE
			SYNTAX EnabledStatus
			MAX-ACCESS read-write
			STATUS current
			DESCRIPTION
				"Description."
			::= { hwMqeScalar 3 }
		
		-- 1.3.6.1.4.1.2011.5.25.203.2.1.4
		hwMqeFtpTimerReset OBJECT-TYPE
			SYNTAX EnabledStatus
			MAX-ACCESS read-write
			STATUS current
			DESCRIPTION
				"Description."
			::= { hwMqeScalar 4 }
		
		-- 1.3.6.1.4.1.2011.5.25.203.2.1.5
		hwMqeSoapEnable OBJECT-TYPE
			SYNTAX EnabledStatus
			MAX-ACCESS read-write
			STATUS current
			DESCRIPTION
				"Description."
			::= { hwMqeScalar 5 }
		
		-- 1.3.6.1.4.1.2011.5.25.203.2.1.6
		hwMqeBtvChnlThreshold OBJECT-TYPE
			SYNTAX Integer32 (300..1500)
			MAX-ACCESS read-write
			STATUS current
			DESCRIPTION
				"Description."
			::= { hwMqeScalar 6 }
		
		-- 1.3.6.1.4.1.2011.5.25.203.2.1.7
		hwMqeChannelCfgAuto OBJECT-TYPE
			SYNTAX EnabledStatus
			MAX-ACCESS read-write
			STATUS current
			DESCRIPTION
				"Description."
			::= { hwMqeScalar 7 }
		
		-- 1.3.6.1.4.1.2011.5.25.203.2.1.8
		hwMqeFtpLocalAddress OBJECT-TYPE
			SYNTAX IpAddress
			MAX-ACCESS read-write
			STATUS current
			DESCRIPTION
				"Description."
			::= { hwMqeScalar 8 }
		
--  1.3.6.1.4.1.2011.5.25.203.1.1
		-- 1.3.6.1.4.1.2011.5.25.203.2.2
		hwVasGroupTable OBJECT-TYPE
			SYNTAX SEQUENCE OF HwVasGroupEntry
			MAX-ACCESS not-accessible
			STATUS current
			DESCRIPTION
				"Vas group configuration table."
			::= { hwMqeObjects 2 }
		
--  1.3.6.1.4.1.2011.5.25.203.1.1.1
		-- 1.3.6.1.4.1.2011.5.25.203.2.3.1
		hwVasGroupEntry OBJECT-TYPE
			SYNTAX HwVasGroupEntry
			MAX-ACCESS not-accessible
			STATUS current
			DESCRIPTION
				"The entry of Vas group function."
			INDEX { hwVasGroupIndex }
			::= { hwVasGroupTable 1 }
		
		HwVasGroupEntry ::=
			SEQUENCE { 
				hwVasGroupIndex
					Integer32,
				hwVasGroupType
					INTEGER,
				hwVasGroupUndoBindSlotID
					EnabledStatus,
				hwVasGroupBindSlotID
					OCTET STRING,
				hwVasGroupUndoBindInterfaceName
					EnabledStatus,
				hwVasGroupBindInterfaceName
					OCTET STRING,
				hwVasGroupBindAddress
					IpAddress,
				hwVasGroupFccRtpDscp
					Integer32,
				hwVasGroupFccRtcpDscp
					Integer32,
				hwVasGroupRetRtpDscp
					Integer32,
				hwVasGroupRetRtcpDscp
					Integer32,
				hwVasGroupMulticastDelay
					Unsigned32,
				hwVasGroupBurstRatio
					Unsigned32,
				hwVasGroupBurstLowRatio
					Unsigned32,
				hwVasGroupServerPort
					Integer32,
				hwVasGroupRowStatus
					RowStatus
			 }

--  1.3.6.1.4.1.2011.5.25.203.1.1.1.1
		-- 1.3.6.1.4.1.2011.5.25.203.2.3.1.1
		hwVasGroupIndex OBJECT-TYPE
			SYNTAX Integer32 (1..4)
			MAX-ACCESS not-accessible
			STATUS current
			DESCRIPTION
				"Value-added service group index"
			::= { hwVasGroupEntry 1 }
		
		-- 1.3.6.1.4.1.2011.5.25.203.2.3.1.2
		hwVasGroupType OBJECT-TYPE
			SYNTAX INTEGER
				{
				mqe(1),
				unknown(3)
				}
			MAX-ACCESS read-write
			STATUS current
			DESCRIPTION
				"Description."
			DEFVAL { unknown }
			::= { hwVasGroupEntry 2 }
		
		-- 1.3.6.1.4.1.2011.5.25.203.2.3.1.3
		hwVasGroupUndoBindSlotID OBJECT-TYPE
			SYNTAX EnabledStatus
			MAX-ACCESS read-write
			STATUS current
			DESCRIPTION
				"Description."
			DEFVAL { disabled }
			::= { hwVasGroupEntry 3 }
		
--  1.3.6.1.4.1.2011.5.25.203.1.1.1.2
		-- 1.3.6.1.4.1.2011.5.25.203.2.3.1.4
		hwVasGroupBindSlotID OBJECT-TYPE
			SYNTAX OCTET STRING (SIZE (0..63))
			MAX-ACCESS read-write
			STATUS current
			DESCRIPTION
				"The ID of boards binding in Vas group.
				"
			::= { hwVasGroupEntry 4 }
		
		-- 1.3.6.1.4.1.2011.5.25.203.2.3.1.5
		hwVasGroupUndoBindInterfaceName OBJECT-TYPE
			SYNTAX EnabledStatus
			MAX-ACCESS read-write
			STATUS current
			DESCRIPTION
				"Description."
			DEFVAL { disabled }
			::= { hwVasGroupEntry 5 }
		
		-- 1.3.6.1.4.1.2011.5.25.203.2.3.1.6
		hwVasGroupBindInterfaceName OBJECT-TYPE
			SYNTAX OCTET STRING (SIZE (0..47))
			MAX-ACCESS read-write
			STATUS current
			DESCRIPTION
				"Description."
			::= { hwVasGroupEntry 6 }
		
--  1.3.6.1.4.1.2011.5.25.203.1.1.1.3
		-- 1.3.6.1.4.1.2011.5.25.203.2.3.1.7
		hwVasGroupBindAddress OBJECT-TYPE
			SYNTAX IpAddress
			MAX-ACCESS read-only
			STATUS current
			DESCRIPTION
				"The ip address bound by Vas group."
			::= { hwVasGroupEntry 7 }
		
--  1.3.6.1.4.1.2011.5.25.203.1.1.1.4
		-- 1.3.6.1.4.1.2011.5.25.203.2.3.1.8
		hwVasGroupFccRtpDscp OBJECT-TYPE
			SYNTAX Integer32 (0..63)
			MAX-ACCESS read-write
			STATUS current
			DESCRIPTION
				"The dscp in ip-formated packet sent by fcc rtp."
			DEFVAL { 0 }
			::= { hwVasGroupEntry 8 }
		
--  1.3.6.1.4.1.2011.5.25.203.1.1.1.5
		-- 1.3.6.1.4.1.2011.5.25.203.2.3.1.9
		hwVasGroupFccRtcpDscp OBJECT-TYPE
			SYNTAX Integer32 (0..63)
			MAX-ACCESS read-write
			STATUS current
			DESCRIPTION
				"The dscp in ip-formated packet sent by fcc rtcp."
			DEFVAL { 6 }
			::= { hwVasGroupEntry 9 }
		
--  1.3.6.1.4.1.2011.5.25.203.1.1.1.6
		-- 1.3.6.1.4.1.2011.5.25.203.2.3.1.10
		hwVasGroupRetRtpDscp OBJECT-TYPE
			SYNTAX Integer32 (0..63)
			MAX-ACCESS read-write
			STATUS current
			DESCRIPTION
				"The dscp in ip-formated packet sent by ret rtp."
			DEFVAL { 0 }
			::= { hwVasGroupEntry 10 }
		
--  1.3.6.1.4.1.2011.5.25.203.1.1.1.7
		-- 1.3.6.1.4.1.2011.5.25.203.2.3.1.11
		hwVasGroupRetRtcpDscp OBJECT-TYPE
			SYNTAX Integer32 (0..63)
			MAX-ACCESS read-write
			STATUS current
			DESCRIPTION
				"The dscp in ip-formated packet sent by ret rtcp."
			DEFVAL { 6 }
			::= { hwVasGroupEntry 11 }
		
--  1.3.6.1.4.1.2011.5.25.203.1.3.1.4
		-- 1.3.6.1.4.1.2011.5.25.203.2.3.1.12
		hwVasGroupMulticastDelay OBJECT-TYPE
			SYNTAX Unsigned32 (0..3000)
			UNITS "ms"
			MAX-ACCESS read-write
			STATUS current
			DESCRIPTION
				"config fcc bust delay time."
			DEFVAL { '100'b }
			::= { hwVasGroupEntry 12 }
		
--  1.3.6.1.4.1.2011.5.25.203.1.1.1.8
		-- 1.3.6.1.4.1.2011.5.25.203.2.3.1.13
		hwVasGroupBurstRatio OBJECT-TYPE
			SYNTAX Unsigned32 (110..180)
			UNITS "%"
			MAX-ACCESS read-write
			STATUS current
			DESCRIPTION
				"The bust rate of media stream sent by fcc."
			DEFVAL { 150 }
			::= { hwVasGroupEntry 13 }
		
		-- 1.3.6.1.4.1.2011.5.25.203.2.3.1.14
		hwVasGroupBurstLowRatio OBJECT-TYPE
			SYNTAX Unsigned32 (10..100)
			UNITS "%"
			MAX-ACCESS read-write
			STATUS current
			DESCRIPTION
				"Description."
			DEFVAL { 30 }
			::= { hwVasGroupEntry 14 }
		
		-- 1.3.6.1.4.1.2011.5.25.203.2.3.1.15
		hwVasGroupServerPort OBJECT-TYPE
			SYNTAX Integer32 (0 | 1025..65535)
			MAX-ACCESS read-write
			STATUS current
			DESCRIPTION
				"Description."
			DEFVAL { 0 }
			::= { hwVasGroupEntry 15 }
		
--  1.3.6.1.4.1.2011.5.25.203.1.1.1.9
		-- 1.3.6.1.4.1.2011.5.25.203.2.3.1.16
		hwVasGroupRowStatus OBJECT-TYPE
			SYNTAX RowStatus
			MAX-ACCESS read-create
			STATUS current
			DESCRIPTION
				"This table can be created and deleted."
			DEFVAL { active }
			::= { hwVasGroupEntry 16 }
		
--  1.3.6.1.4.1.2011.5.25.203.1.2
		-- 1.3.6.1.4.1.2011.5.25.203.2.3
		hwMqeChannelTable OBJECT-TYPE
			SYNTAX SEQUENCE OF HwMqeChannelEntry
			MAX-ACCESS not-accessible
			STATUS current
			DESCRIPTION
				"Media channel configuration table."
			::= { hwMqeObjects 3 }
		
--  1.3.6.1.4.1.2011.5.25.203.1.2.1
		-- 1.3.6.1.4.1.2011.5.25.203.2.4.1
		hwMqeChannelEntry OBJECT-TYPE
			SYNTAX HwMqeChannelEntry
			MAX-ACCESS not-accessible
			STATUS current
			DESCRIPTION
				"The entry of Channel table."
			INDEX { hwMqeChannelIndex }
			::= { hwMqeChannelTable 1 }
		
		HwMqeChannelEntry ::=
			SEQUENCE { 
				hwMqeChannelIndex
					Integer32,
				hwMqeChannelName
					OCTET STRING,
				hwMqeChannelGroupAddress
					IpAddress,
				hwMqeChannelSourceAddress
					IpAddress,
				hwMqeChannelDestPort
					Integer32,
				hwMqeChannelEncapType
					INTEGER,
				hwMqeChannelCacheTime
					Integer32,
				hwMqeChannelMaxGopInterval
					Integer32,
				hwMqeChannelSSRC
					Gauge32,
				hwMqeChannelSelectiveBurst
					INTEGER,
				hwMqeChannelQuickParse
					INTEGER,
				hwMqeChannelRowStatus
					RowStatus,
				hwMqeChannelRate
					Integer32,
				hwMqeChannelCodecType
					INTEGER
			 }

--  1.3.6.1.4.1.2011.5.25.203.1.2.1.1
		-- 1.3.6.1.4.1.2011.5.25.203.2.4.1.1
		hwMqeChannelIndex OBJECT-TYPE
			SYNTAX Integer32 (1..2000)
			MAX-ACCESS not-accessible
			STATUS current
			DESCRIPTION
				"Channel index.
				"
			::= { hwMqeChannelEntry 1 }
		
--  1.3.6.1.4.1.2011.5.25.203.1.2.1.2
		-- 1.3.6.1.4.1.2011.5.25.203.2.4.1.2
		hwMqeChannelName OBJECT-TYPE
			SYNTAX OCTET STRING (SIZE (0..15))
			MAX-ACCESS read-write
			STATUS current
			DESCRIPTION
				"The name of channel."
			::= { hwMqeChannelEntry 2 }
		
--  1.3.6.1.4.1.2011.5.25.203.1.2.1.5
		-- 1.3.6.1.4.1.2011.5.25.203.2.4.1.3
		hwMqeChannelGroupAddress OBJECT-TYPE
			SYNTAX IpAddress
			MAX-ACCESS read-create
			STATUS current
			DESCRIPTION
				"Channel address."
			::= { hwMqeChannelEntry 3 }
		
		-- 1.3.6.1.4.1.2011.5.25.203.2.4.1.4
		hwMqeChannelSourceAddress OBJECT-TYPE
			SYNTAX IpAddress
			MAX-ACCESS read-create
			STATUS current
			DESCRIPTION
				"Description."
			::= { hwMqeChannelEntry 4 }
		
--  1.3.6.1.4.1.2011.5.25.203.1.2.1.6
		-- 1.3.6.1.4.1.2011.5.25.203.2.4.1.5
		hwMqeChannelDestPort OBJECT-TYPE
			SYNTAX Integer32 (1025..65535)
			MAX-ACCESS read-create
			STATUS current
			DESCRIPTION
				"Channel port."
			::= { hwMqeChannelEntry 5 }
		
--  1.3.6.1.4.1.2011.5.25.203.1.2.1.8
		-- 1.3.6.1.4.1.2011.5.25.203.2.4.1.6
		hwMqeChannelEncapType OBJECT-TYPE
			SYNTAX INTEGER
				{
				tsOverRtpOverUdp(1),
				tsOverUdp(2)
				}
			MAX-ACCESS read-create
			STATUS current
			DESCRIPTION
				"The encapsulation of channel."
			DEFVAL { tsOverRtpOverUdp }
			::= { hwMqeChannelEntry 6 }
		
--  1.3.6.1.4.1.2011.5.25.203.1.3.1.3
		-- 1.3.6.1.4.1.2011.5.25.203.2.4.1.7
		hwMqeChannelCacheTime OBJECT-TYPE
			SYNTAX Integer32 (2000..80000)
			UNITS "ms"
			MAX-ACCESS read-write
			STATUS current
			DESCRIPTION
				"Channel cache time."
			DEFVAL { 15000 }
			::= { hwMqeChannelEntry 7 }
		
--  1.3.6.1.4.1.2011.5.25.203.1.3.1.5
		-- 1.3.6.1.4.1.2011.5.25.203.2.4.1.8
		hwMqeChannelMaxGopInterval OBJECT-TYPE
			SYNTAX Integer32 (2000..8000)
			UNITS "ms"
			MAX-ACCESS read-write
			STATUS current
			DESCRIPTION
				"The max interval time of GOP of the channel."
			DEFVAL { 5000 }
			::= { hwMqeChannelEntry 8 }
		
		-- 1.3.6.1.4.1.2011.5.25.203.2.4.1.9
		hwMqeChannelSSRC OBJECT-TYPE
			SYNTAX Gauge32
			MAX-ACCESS read-write
			STATUS current
			DESCRIPTION
				"Description."
			::= { hwMqeChannelEntry 9 }
		
		-- 1.3.6.1.4.1.2011.5.25.203.2.4.1.10
		hwMqeChannelSelectiveBurst OBJECT-TYPE
			SYNTAX INTEGER
				{
				noselectiveburst(0),
				selectiveburst(1)
				}
			MAX-ACCESS read-write
			STATUS current
			DESCRIPTION
				"Description."
			DEFVAL { noselectiveburst }
			::= { hwMqeChannelEntry 10 }
		
		-- 1.3.6.1.4.1.2011.5.25.203.2.4.1.11
		hwMqeChannelQuickParse OBJECT-TYPE
			SYNTAX INTEGER
				{
				nonquickparse(0),
				quickparse(1)
				}
			MAX-ACCESS read-write
			STATUS current
			DESCRIPTION
				"Description."
			DEFVAL { quickparse }
			::= { hwMqeChannelEntry 11 }
		
--  1.3.6.1.4.1.2011.5.25.203.1.2.1.10
		-- 1.3.6.1.4.1.2011.5.25.203.2.4.1.12
		hwMqeChannelRowStatus OBJECT-TYPE
			SYNTAX RowStatus
			MAX-ACCESS read-create
			STATUS current
			DESCRIPTION
				"RowStatus."
			DEFVAL { active }
			::= { hwMqeChannelEntry 12 }
		
		-- 1.3.6.1.4.1.2011.5.25.203.2.4.1.13
		hwMqeChannelRate OBJECT-TYPE
			SYNTAX Integer32 (300..20000)
			UNITS "kbps"
			MAX-ACCESS read-write
			STATUS current
			DESCRIPTION
				"Description."
			::= { hwMqeChannelEntry 13 }
		
		-- 1.3.6.1.4.1.2011.5.25.203.2.4.1.14
		hwMqeChannelCodecType OBJECT-TYPE
			SYNTAX INTEGER
				{
				mpeg2(1),
				mpeg4(2),
				h264(3)
				}
			MAX-ACCESS read-write
			STATUS current
			DESCRIPTION
				"Description."
			DEFVAL { h264 }
			::= { hwMqeChannelEntry 14 }
		
		-- 1.3.6.1.4.1.2011.5.25.203.2.4
		hwMqeChannelCfgTable OBJECT-TYPE
			SYNTAX SEQUENCE OF HwMqeChannelCfgEntry
			MAX-ACCESS not-accessible
			STATUS current
			DESCRIPTION
				"Description."
			::= { hwMqeObjects 4 }
		
		-- 1.3.6.1.4.1.2011.5.25.203.2.5.1
		hwMqeChannelCfgEntry OBJECT-TYPE
			SYNTAX HwMqeChannelCfgEntry
			MAX-ACCESS not-accessible
			STATUS current
			DESCRIPTION
				"Description."
			INDEX { hwMqeChannelIndex }
			::= { hwMqeChannelCfgTable 1 }
		
		HwMqeChannelCfgEntry ::=
			SEQUENCE { 
				hwMqeChannelFccVasGroupID
					OCTET STRING,
				hwMqeChannelFccEnable
					EnabledStatus,
				hwMqeChannelRetVasGroupID
					OCTET STRING,
				hwMqeChannelRetEnable
					EnabledStatus,
				hwMqeChannelMdiVasGroupID
					Integer32,
				hwMqeChannelMdiEnable
					EnabledStatus,
				hwMqeChannelMdiSlotID
					Integer32,
				hwMqeChannelMdiDfThreshold
					Integer32,
				hwMqeChannelMdiMlrThreshold
					Integer32,
				hwMqeChannelVmosVasGroupID
					Integer32,
				hwMqeChannelVmosEnable
					EnabledStatus,
				hwMqeChannelVmosSlotID
					Integer32,
				hwMqeChannelVmosThreshold
					Integer32,
				hwMqeChannelVmosSampleInterval
					Integer32
			 }

--  1.3.6.1.4.1.2011.5.25.203.1.2.1.4
		-- 1.3.6.1.4.1.2011.5.25.203.2.5.1.1
		hwMqeChannelFccVasGroupID OBJECT-TYPE
			SYNTAX OCTET STRING (SIZE (0..8))
			MAX-ACCESS read-write
			STATUS current
			DESCRIPTION
				"Description."
			::= { hwMqeChannelCfgEntry 1 }
		
--  1.3.6.1.4.1.2011.5.25.203.1.3.1.1
		-- 1.3.6.1.4.1.2011.5.25.203.2.5.1.2
		hwMqeChannelFccEnable OBJECT-TYPE
			SYNTAX EnabledStatus
			MAX-ACCESS read-write
			STATUS current
			DESCRIPTION
				"Config FCC function."
			DEFVAL { disabled }
			::= { hwMqeChannelCfgEntry 2 }
		
--  1.3.6.1.4.1.2011.5.25.203.1.2.1.4
		-- 1.3.6.1.4.1.2011.5.25.203.2.5.1.3
		hwMqeChannelRetVasGroupID OBJECT-TYPE
			SYNTAX OCTET STRING (SIZE (0..8))
			MAX-ACCESS read-write
			STATUS current
			DESCRIPTION
				"Description."
			::= { hwMqeChannelCfgEntry 3 }
		
--  1.3.6.1.4.1.2011.5.25.203.1.3.1.2
		-- 1.3.6.1.4.1.2011.5.25.203.2.5.1.4
		hwMqeChannelRetEnable OBJECT-TYPE
			SYNTAX EnabledStatus
			MAX-ACCESS read-write
			STATUS current
			DESCRIPTION
				"Config RET function."
			DEFVAL { disabled }
			::= { hwMqeChannelCfgEntry 4 }
		
--  1.3.6.1.4.1.2011.5.25.203.1.2.1.4
		-- 1.3.6.1.4.1.2011.5.25.203.2.5.1.5
		hwMqeChannelMdiVasGroupID OBJECT-TYPE
			SYNTAX Integer32 (0 | 1..4)
			MAX-ACCESS read-write
			STATUS current
			DESCRIPTION
				"Description."
			DEFVAL { 0 }
			::= { hwMqeChannelCfgEntry 5 }
		
--  1.3.6.1.4.1.2011.5.25.203.1.4.1.1
		-- 1.3.6.1.4.1.2011.5.25.203.2.5.1.6
		hwMqeChannelMdiEnable OBJECT-TYPE
			SYNTAX EnabledStatus
			MAX-ACCESS read-write
			STATUS current
			DESCRIPTION
				"config MDI function."
			DEFVAL { disabled }
			::= { hwMqeChannelCfgEntry 6 }
		
		-- 1.3.6.1.4.1.2011.5.25.203.2.5.1.7
		hwMqeChannelMdiSlotID OBJECT-TYPE
			SYNTAX Integer32
			MAX-ACCESS read-write
			STATUS current
			DESCRIPTION
				"Description."
			DEFVAL { '0'b }
			::= { hwMqeChannelCfgEntry 7 }
		
--  1.3.6.1.4.1.2011.5.25.203.1.4.1.2
		-- 1.3.6.1.4.1.2011.5.25.203.2.5.1.8
		hwMqeChannelMdiDfThreshold OBJECT-TYPE
			SYNTAX Integer32 (0..1000)
			UNITS "ms"
			MAX-ACCESS read-write
			STATUS current
			DESCRIPTION
				"The MDI DF threshold of channel."
			DEFVAL { 50 }
			::= { hwMqeChannelCfgEntry 8 }
		
--  1.3.6.1.4.1.2011.5.25.203.1.4.1.3
		-- 1.3.6.1.4.1.2011.5.25.203.2.5.1.9
		hwMqeChannelMdiMlrThreshold OBJECT-TYPE
			SYNTAX Integer32 (0..1000)
			UNITS "packets/s"
			MAX-ACCESS read-write
			STATUS current
			DESCRIPTION
				"The MDI MLR threshold of channel."
			DEFVAL { 2 }
			::= { hwMqeChannelCfgEntry 9 }
		
--  1.3.6.1.4.1.2011.5.25.203.1.2.1.4
		-- 1.3.6.1.4.1.2011.5.25.203.2.5.1.10
		hwMqeChannelVmosVasGroupID OBJECT-TYPE
			SYNTAX Integer32 (0 | 1..4)
			MAX-ACCESS read-write
			STATUS current
			DESCRIPTION
				"Description."
			DEFVAL { 0 }
			::= { hwMqeChannelCfgEntry 10 }
		
--  1.3.6.1.4.1.2011.5.25.203.1.5.1.1
		-- 1.3.6.1.4.1.2011.5.25.203.2.5.1.11
		hwMqeChannelVmosEnable OBJECT-TYPE
			SYNTAX EnabledStatus
			MAX-ACCESS read-write
			STATUS current
			DESCRIPTION
				"Config VMOS function."
			DEFVAL { disabled }
			::= { hwMqeChannelCfgEntry 11 }
		
		-- 1.3.6.1.4.1.2011.5.25.203.2.5.1.12
		hwMqeChannelVmosSlotID OBJECT-TYPE
			SYNTAX Integer32
			MAX-ACCESS read-write
			STATUS current
			DESCRIPTION
				"Description."
			DEFVAL { '0'b }
			::= { hwMqeChannelCfgEntry 12 }
		
--  1.3.6.1.4.1.2011.5.25.203.1.5.1.2
		-- 1.3.6.1.4.1.2011.5.25.203.2.5.1.13
		hwMqeChannelVmosThreshold OBJECT-TYPE
			SYNTAX Integer32 (100..500)
			MAX-ACCESS read-write
			STATUS current
			DESCRIPTION
				"Description."
			DEFVAL { 300 }
			::= { hwMqeChannelCfgEntry 13 }
		
--  1.3.6.1.4.1.2011.5.25.203.1.5.1.3
		-- 1.3.6.1.4.1.2011.5.25.203.2.5.1.14
		hwMqeChannelVmosSampleInterval OBJECT-TYPE
			SYNTAX Integer32 (1..20)
			UNITS "s"
			MAX-ACCESS read-write
			STATUS current
			DESCRIPTION
				"Description."
			DEFVAL { 15 }
			::= { hwMqeChannelCfgEntry 14 }
		
		-- 1.3.6.1.4.1.2011.5.25.203.2.5
		hwMqeStatTable OBJECT-TYPE
			SYNTAX SEQUENCE OF HwMqeStatEntry
			MAX-ACCESS not-accessible
			STATUS current
			DESCRIPTION
				"Description."
			::= { hwMqeObjects 5 }
		
		-- 1.3.6.1.4.1.2011.5.25.203.2.6.1
		hwMqeStatEntry OBJECT-TYPE
			SYNTAX HwMqeStatEntry
			MAX-ACCESS not-accessible
			STATUS current
			DESCRIPTION
				"Description."
			INDEX { hwMqeStatSlotID, hwMqeStatCpuID }
			::= { hwMqeStatTable 1 }
		
		HwMqeStatEntry ::=
			SEQUENCE { 
				hwMqeStatSlotID
					Integer32,
				hwMqeStatCpuID
					Integer32,
				hwMqeStatFccReqReceived
					Gauge32,
				hwMqeStatFccReqProcessed
					Gauge32,
				hwMqeStatFccReqRefused
					Gauge32,
				hwMqeStatRetReqReceived
					Gauge32,
				hwMqeStatRetReqProcessed
					Gauge32,
				hwMqeStatRetReqRefused
					Gauge32,
				hwMqeStatMdiChannels
					Gauge32,
				hwMqeStatVmosChannels
					Gauge32
			 }

		-- 1.3.6.1.4.1.2011.5.25.203.2.6.1.1
		hwMqeStatSlotID OBJECT-TYPE
			SYNTAX Integer32 (1..256)
			MAX-ACCESS read-only
			STATUS current
			DESCRIPTION
				"Description."
			::= { hwMqeStatEntry 1 }
		
		-- 1.3.6.1.4.1.2011.5.25.203.2.6.1.2
		hwMqeStatCpuID OBJECT-TYPE
			SYNTAX Integer32 (1..2)
			MAX-ACCESS read-only
			STATUS current
			DESCRIPTION
				"Description."
			::= { hwMqeStatEntry 2 }
		
		-- 1.3.6.1.4.1.2011.5.25.203.2.6.1.3
		hwMqeStatFccReqReceived OBJECT-TYPE
			SYNTAX Gauge32
			MAX-ACCESS read-only
			STATUS current
			DESCRIPTION
				"Description."
			::= { hwMqeStatEntry 3 }
		
		-- 1.3.6.1.4.1.2011.5.25.203.2.6.1.4
		hwMqeStatFccReqProcessed OBJECT-TYPE
			SYNTAX Gauge32
			MAX-ACCESS read-only
			STATUS current
			DESCRIPTION
				"Description."
			::= { hwMqeStatEntry 4 }
		
		-- 1.3.6.1.4.1.2011.5.25.203.2.6.1.5
		hwMqeStatFccReqRefused OBJECT-TYPE
			SYNTAX Gauge32
			MAX-ACCESS read-only
			STATUS current
			DESCRIPTION
				"Description."
			::= { hwMqeStatEntry 5 }
		
		-- 1.3.6.1.4.1.2011.5.25.203.2.6.1.6
		hwMqeStatRetReqReceived OBJECT-TYPE
			SYNTAX Gauge32
			MAX-ACCESS read-only
			STATUS current
			DESCRIPTION
				"Description."
			::= { hwMqeStatEntry 6 }
		
		-- 1.3.6.1.4.1.2011.5.25.203.2.6.1.7
		hwMqeStatRetReqProcessed OBJECT-TYPE
			SYNTAX Gauge32
			MAX-ACCESS read-only
			STATUS current
			DESCRIPTION
				"Description."
			::= { hwMqeStatEntry 7 }
		
		-- 1.3.6.1.4.1.2011.5.25.203.2.6.1.8
		hwMqeStatRetReqRefused OBJECT-TYPE
			SYNTAX Gauge32
			MAX-ACCESS read-only
			STATUS current
			DESCRIPTION
				"Description."
			::= { hwMqeStatEntry 8 }
		
		-- 1.3.6.1.4.1.2011.5.25.203.2.6.1.9
		hwMqeStatMdiChannels OBJECT-TYPE
			SYNTAX Gauge32
			MAX-ACCESS read-only
			STATUS current
			DESCRIPTION
				"Description."
			::= { hwMqeStatEntry 9 }
		
		-- 1.3.6.1.4.1.2011.5.25.203.2.6.1.10
		hwMqeStatVmosChannels OBJECT-TYPE
			SYNTAX Gauge32
			MAX-ACCESS read-only
			STATUS current
			DESCRIPTION
				"Description."
			::= { hwMqeStatEntry 10 }
		
		-- 1.3.6.1.4.1.2011.5.25.203.2.6
		hwMqeMdiStatTable OBJECT-TYPE
			SYNTAX SEQUENCE OF HwMqeMdiStatEntry
			MAX-ACCESS not-accessible
			STATUS current
			DESCRIPTION
				"Description."
			::= { hwMqeObjects 6 }
		
		-- 1.3.6.1.4.1.2011.5.25.203.2.7.1
		hwMqeMdiStatEntry OBJECT-TYPE
			SYNTAX HwMqeMdiStatEntry
			MAX-ACCESS not-accessible
			STATUS current
			DESCRIPTION
				"Description."
			INDEX { hwMqeChannelMdiID, hwMqeChannelMdiIntervalNum }
			::= { hwMqeMdiStatTable 1 }
		
		HwMqeMdiStatEntry ::=
			SEQUENCE { 
				hwMqeChannelMdiID
					Integer32,
				hwMqeChannelMdiIntervalNum
					Integer32,
				hwMqeChannelMdiTimeStamp
					Gauge32,
				hwMqeChannelMdiDf
					Gauge32,
				hwMqeChannelMdiMlr
					Gauge32,
				hwMqeChannelMdiMlt15
					Gauge32,
				hwMqeChannelMdiMlt24
					Gauge32,
				hwMqeChannelMdiMR
					Gauge32
			 }

		-- 1.3.6.1.4.1.2011.5.25.203.2.7.1.1
		hwMqeChannelMdiID OBJECT-TYPE
			SYNTAX Integer32 (1..2000 | 5001..5020)
			MAX-ACCESS read-only
			STATUS current
			DESCRIPTION
				"Description."
			::= { hwMqeMdiStatEntry 1 }
		
		-- 1.3.6.1.4.1.2011.5.25.203.2.7.1.2
		hwMqeChannelMdiIntervalNum OBJECT-TYPE
			SYNTAX Integer32 (1..15)
			MAX-ACCESS read-write
			STATUS current
			DESCRIPTION
				"Description."
			::= { hwMqeMdiStatEntry 2 }
		
		-- 1.3.6.1.4.1.2011.5.25.203.2.7.1.3
		hwMqeChannelMdiTimeStamp OBJECT-TYPE
			SYNTAX Gauge32
			MAX-ACCESS read-only
			STATUS current
			DESCRIPTION
				"Description."
			::= { hwMqeMdiStatEntry 3 }
		
		-- 1.3.6.1.4.1.2011.5.25.203.2.7.1.4
		hwMqeChannelMdiDf OBJECT-TYPE
			SYNTAX Gauge32
			UNITS "ms"
			MAX-ACCESS read-only
			STATUS current
			DESCRIPTION
				"Description."
			::= { hwMqeMdiStatEntry 4 }
		
		-- 1.3.6.1.4.1.2011.5.25.203.2.7.1.5
		hwMqeChannelMdiMlr OBJECT-TYPE
			SYNTAX Gauge32
			UNITS "packets/s"
			MAX-ACCESS read-only
			STATUS current
			DESCRIPTION
				"Description."
			::= { hwMqeMdiStatEntry 5 }
		
		-- 1.3.6.1.4.1.2011.5.25.203.2.7.1.6
		hwMqeChannelMdiMlt15 OBJECT-TYPE
			SYNTAX Gauge32
			MAX-ACCESS read-only
			STATUS current
			DESCRIPTION
				"Description."
			::= { hwMqeMdiStatEntry 6 }
		
		-- 1.3.6.1.4.1.2011.5.25.203.2.7.1.7
		hwMqeChannelMdiMlt24 OBJECT-TYPE
			SYNTAX Gauge32
			MAX-ACCESS read-only
			STATUS current
			DESCRIPTION
				"Description."
			::= { hwMqeMdiStatEntry 7 }
		
		-- 1.3.6.1.4.1.2011.5.25.203.2.7.1.8
		hwMqeChannelMdiMR OBJECT-TYPE
			SYNTAX Gauge32
			UNITS "kbit/s"
			MAX-ACCESS read-only
			STATUS current
			DESCRIPTION
				"Description."
			::= { hwMqeMdiStatEntry 8 }
		
--  1.3.6.1.4.1.2011.5.25.203.1.5
		-- 1.3.6.1.4.1.2011.5.25.203.2.7
		hwMqeVmosStatTable OBJECT-TYPE
			SYNTAX SEQUENCE OF HwMqeVmosStatEntry
			MAX-ACCESS not-accessible
			STATUS current
			DESCRIPTION
				"Description."
			::= { hwMqeObjects 7 }
		
--  1.3.6.1.4.1.2011.5.25.203.1.5.1
		-- 1.3.6.1.4.1.2011.5.25.203.2.8.1
		hwMqeVmosStatEntry OBJECT-TYPE
			SYNTAX HwMqeVmosStatEntry
			MAX-ACCESS not-accessible
			STATUS current
			DESCRIPTION
				"Description."
			INDEX { hwMqeChannelVmosID, hwMqeChannelVmosIntervalNum }
			::= { hwMqeVmosStatTable 1 }
		
		HwMqeVmosStatEntry ::=
			SEQUENCE { 
				hwMqeChannelVmosID
					Integer32,
				hwMqeChannelVmosIntervalNum
					Integer32,
				hwMqeChannelVmosTimeStamp
					Gauge32,
				hwMqeChannelVmosPlr
					Gauge32,
				hwMqeChannelVmosPler
					Gauge32,
				hwMqeChannelVmosPler2
					Gauge32,
				hwMqeChannelVmosMaxj
					Gauge32,
				hwMqeChannelVmosMeanj
					Gauge32,
				hwMqeChannelVmosMeanj2
					Gauge32,
				hwMqeChannelVmosValue
					Gauge32
			 }

		-- 1.3.6.1.4.1.2011.5.25.203.2.8.1.1
		hwMqeChannelVmosID OBJECT-TYPE
			SYNTAX Integer32 (1..2000 | 5001..5020)
			MAX-ACCESS read-only
			STATUS current
			DESCRIPTION
				"Description."
			::= { hwMqeVmosStatEntry 1 }
		
		-- 1.3.6.1.4.1.2011.5.25.203.2.8.1.2
		hwMqeChannelVmosIntervalNum OBJECT-TYPE
			SYNTAX Integer32 (1..15)
			MAX-ACCESS read-write
			STATUS current
			DESCRIPTION
				"Description."
			::= { hwMqeVmosStatEntry 2 }
		
		-- 1.3.6.1.4.1.2011.5.25.203.2.8.1.3
		hwMqeChannelVmosTimeStamp OBJECT-TYPE
			SYNTAX Gauge32
			MAX-ACCESS read-only
			STATUS current
			DESCRIPTION
				"Description."
			::= { hwMqeVmosStatEntry 3 }
		
--  1.3.6.1.4.1.2011.5.25.203.1.5.1.4
		-- 1.3.6.1.4.1.2011.5.25.203.2.8.1.4
		hwMqeChannelVmosPlr OBJECT-TYPE
			SYNTAX Gauge32
			UNITS "%"
			MAX-ACCESS read-only
			STATUS current
			DESCRIPTION
				"Description."
			::= { hwMqeVmosStatEntry 4 }
		
--  1.3.6.1.4.1.2011.5.25.203.1.5.1.5
		-- 1.3.6.1.4.1.2011.5.25.203.2.8.1.5
		hwMqeChannelVmosPler OBJECT-TYPE
			SYNTAX Gauge32
			UNITS "nums/s"
			MAX-ACCESS read-only
			STATUS current
			DESCRIPTION
				"Description."
			::= { hwMqeVmosStatEntry 5 }
		
--  1.3.6.1.4.1.2011.5.25.203.1.5.1.6
		-- 1.3.6.1.4.1.2011.5.25.203.2.8.1.6
		hwMqeChannelVmosPler2 OBJECT-TYPE
			SYNTAX Gauge32
			UNITS "nums/s"
			MAX-ACCESS read-only
			STATUS current
			DESCRIPTION
				"Description."
			::= { hwMqeVmosStatEntry 6 }
		
--  1.3.6.1.4.1.2011.5.25.203.1.5.1.7
		-- 1.3.6.1.4.1.2011.5.25.203.2.8.1.7
		hwMqeChannelVmosMaxj OBJECT-TYPE
			SYNTAX Gauge32
			UNITS "s"
			MAX-ACCESS read-only
			STATUS current
			DESCRIPTION
				"Description."
			::= { hwMqeVmosStatEntry 7 }
		
--  1.3.6.1.4.1.2011.5.25.203.1.5.1.8
		-- 1.3.6.1.4.1.2011.5.25.203.2.8.1.8
		hwMqeChannelVmosMeanj OBJECT-TYPE
			SYNTAX Gauge32
			UNITS "s"
			MAX-ACCESS read-only
			STATUS current
			DESCRIPTION
				"Description."
			::= { hwMqeVmosStatEntry 8 }
		
--  1.3.6.1.4.1.2011.5.25.203.1.5.1.9
		-- 1.3.6.1.4.1.2011.5.25.203.2.8.1.9
		hwMqeChannelVmosMeanj2 OBJECT-TYPE
			SYNTAX Gauge32
			UNITS "s"
			MAX-ACCESS read-only
			STATUS current
			DESCRIPTION
				"Description."
			::= { hwMqeVmosStatEntry 9 }
		
--  1.3.6.1.4.1.2011.5.25.203.1.5.1.10
		-- 1.3.6.1.4.1.2011.5.25.203.2.8.1.10
		hwMqeChannelVmosValue OBJECT-TYPE
			SYNTAX Gauge32
			MAX-ACCESS read-only
			STATUS current
			DESCRIPTION
				"Description."
			::= { hwMqeVmosStatEntry 10 }
		
		-- 1.3.6.1.4.1.2011.5.25.203.2.8
		hwMqeVodCfgTable OBJECT-TYPE
			SYNTAX SEQUENCE OF HwMqeVodCfgEntry
			MAX-ACCESS not-accessible
			STATUS current
			DESCRIPTION
				"Description."
			::= { hwMqeObjects 8 }
		
		-- 1.3.6.1.4.1.2011.5.25.203.2.8.1
		hwMqeVodCfgEntry OBJECT-TYPE
			SYNTAX HwMqeVodCfgEntry
			MAX-ACCESS not-accessible
			STATUS current
			DESCRIPTION
				"Description."
			INDEX { hwMqeVodID }
			::= { hwMqeVodCfgTable 1 }
		
		HwMqeVodCfgEntry ::=
			SEQUENCE { 
				hwMqeVodID
					Integer32,
				hwMqeVodSourceAddress
					IpAddress,
				hwMqeVodSourcePort
					Integer32,
				hwMqeVodDestAddress
					IpAddress,
				hwMqeVodDestPort
					Integer32,
				hwMqeVodEncapType
					INTEGER,
				hwMqeVodDescription
					OCTET STRING,
				hwMqeVodMdiEnable
					EnabledStatus,
				hwMqeVodMdiVasGroupID
					Integer32,
				hwMqeVodMdiSlotID
					Integer32,
				hwMqeVodMdiDfThreshold
					Integer32,
				hwMqeVodMdiMlrThreshold
					Integer32,
				hwMqeVodVmosEnable
					EnabledStatus,
				hwMqeVodVmosVasGroupID
					Integer32,
				hwMqeVodVmosSlotID
					Integer32,
				hwMqeVodVmosThreshold
					Integer32,
				hwMqeVodVmosSampleInterval
					Integer32,
				hwMqeVodCfgRowStatus
					RowStatus,
				hwMqeVodVpnInstance
					OCTET STRING,
				hwMqeVodCodecType
					INTEGER
			 }

		-- 1.3.6.1.4.1.2011.5.25.203.2.8.1.1
		hwMqeVodID OBJECT-TYPE
			SYNTAX Integer32 (5001..5020)
			MAX-ACCESS read-only
			STATUS current
			DESCRIPTION
				"Description."
			::= { hwMqeVodCfgEntry 1 }
		
		-- 1.3.6.1.4.1.2011.5.25.203.2.8.1.2
		hwMqeVodSourceAddress OBJECT-TYPE
			SYNTAX IpAddress
			MAX-ACCESS read-write
			STATUS current
			DESCRIPTION
				"Description."
			::= { hwMqeVodCfgEntry 2 }
		
		-- 1.3.6.1.4.1.2011.5.25.203.2.8.1.3
		hwMqeVodSourcePort OBJECT-TYPE
			SYNTAX Integer32 (0 | 1025..65535)
			MAX-ACCESS read-write
			STATUS current
			DESCRIPTION
				"Description."
			DEFVAL { '0'b }
			::= { hwMqeVodCfgEntry 3 }
		
		-- 1.3.6.1.4.1.2011.5.25.203.2.8.1.4
		hwMqeVodDestAddress OBJECT-TYPE
			SYNTAX IpAddress
			MAX-ACCESS read-write
			STATUS current
			DESCRIPTION
				"Description."
			::= { hwMqeVodCfgEntry 4 }
		
		-- 1.3.6.1.4.1.2011.5.25.203.2.8.1.5
		hwMqeVodDestPort OBJECT-TYPE
			SYNTAX Integer32 (1025..65535)
			MAX-ACCESS read-write
			STATUS current
			DESCRIPTION
				"Description."
			::= { hwMqeVodCfgEntry 5 }
		
		-- 1.3.6.1.4.1.2011.5.25.203.2.8.1.6
		hwMqeVodEncapType OBJECT-TYPE
			SYNTAX INTEGER
				{
				tsOverRtpOverUdp(1),
				tsOverUdp(2),
				tsOverRtpOverTcp(3),
				tsOverTcp(4)
				}
			MAX-ACCESS read-write
			STATUS current
			DESCRIPTION
				"Description."
			DEFVAL { tsOverRtpOverUdp }
			::= { hwMqeVodCfgEntry 6 }
		
		-- 1.3.6.1.4.1.2011.5.25.203.2.8.1.7
		hwMqeVodDescription OBJECT-TYPE
			SYNTAX OCTET STRING (SIZE (0..255))
			MAX-ACCESS read-write
			STATUS current
			DESCRIPTION
				"Description."
			::= { hwMqeVodCfgEntry 7 }
		
		-- 1.3.6.1.4.1.2011.5.25.203.2.8.1.8
		hwMqeVodMdiEnable OBJECT-TYPE
			SYNTAX EnabledStatus
			MAX-ACCESS read-write
			STATUS current
			DESCRIPTION
				"Description."
			DEFVAL { disabled }
			::= { hwMqeVodCfgEntry 8 }
		
		-- 1.3.6.1.4.1.2011.5.25.203.2.8.1.9
		hwMqeVodMdiVasGroupID OBJECT-TYPE
			SYNTAX Integer32 (0 | 1..4)
			MAX-ACCESS read-write
			STATUS current
			DESCRIPTION
				"Description."
			DEFVAL { '0'b }
			::= { hwMqeVodCfgEntry 9 }
		
		-- 1.3.6.1.4.1.2011.5.25.203.2.8.1.10
		hwMqeVodMdiSlotID OBJECT-TYPE
			SYNTAX Integer32
			MAX-ACCESS read-write
			STATUS current
			DESCRIPTION
				"Description."
			DEFVAL { '0'b }
			::= { hwMqeVodCfgEntry 10 }
		
		-- 1.3.6.1.4.1.2011.5.25.203.2.8.1.11
		hwMqeVodMdiDfThreshold OBJECT-TYPE
			SYNTAX Integer32 (0..1000)
			UNITS "ms"
			MAX-ACCESS read-write
			STATUS current
			DESCRIPTION
				"Description."
			DEFVAL { 50 }
			::= { hwMqeVodCfgEntry 11 }
		
		-- 1.3.6.1.4.1.2011.5.25.203.2.8.1.12
		hwMqeVodMdiMlrThreshold OBJECT-TYPE
			SYNTAX Integer32 (0..1000)
			UNITS "packets/s"
			MAX-ACCESS read-write
			STATUS current
			DESCRIPTION
				"Description."
			DEFVAL { 2 }
			::= { hwMqeVodCfgEntry 12 }
		
		-- 1.3.6.1.4.1.2011.5.25.203.2.8.1.13
		hwMqeVodVmosEnable OBJECT-TYPE
			SYNTAX EnabledStatus
			MAX-ACCESS read-write
			STATUS current
			DESCRIPTION
				"Description."
			DEFVAL { disabled }
			::= { hwMqeVodCfgEntry 13 }
		
		-- 1.3.6.1.4.1.2011.5.25.203.2.8.1.14
		hwMqeVodVmosVasGroupID OBJECT-TYPE
			SYNTAX Integer32 (0 | 1..4)
			MAX-ACCESS read-write
			STATUS current
			DESCRIPTION
				"Description."
			DEFVAL { '0'b }
			::= { hwMqeVodCfgEntry 14 }
		
		-- 1.3.6.1.4.1.2011.5.25.203.2.8.1.15
		hwMqeVodVmosSlotID OBJECT-TYPE
			SYNTAX Integer32
			MAX-ACCESS read-write
			STATUS current
			DESCRIPTION
				"Description."
			DEFVAL { '0'b }
			::= { hwMqeVodCfgEntry 15 }
		
		-- 1.3.6.1.4.1.2011.5.25.203.2.8.1.16
		hwMqeVodVmosThreshold OBJECT-TYPE
			SYNTAX Integer32 (100..500)
			MAX-ACCESS read-write
			STATUS current
			DESCRIPTION
				"Description."
			DEFVAL { 300 }
			::= { hwMqeVodCfgEntry 16 }
		
		-- 1.3.6.1.4.1.2011.5.25.203.2.8.1.17
		hwMqeVodVmosSampleInterval OBJECT-TYPE
			SYNTAX Integer32 (1..20)
			UNITS "s"
			MAX-ACCESS read-write
			STATUS current
			DESCRIPTION
				"Description."
			DEFVAL { 15 }
			::= { hwMqeVodCfgEntry 17 }
		
		-- 1.3.6.1.4.1.2011.5.25.203.2.8.1.18
		hwMqeVodCfgRowStatus OBJECT-TYPE
			SYNTAX RowStatus
			MAX-ACCESS read-create
			STATUS current
			DESCRIPTION
				"Description."
			DEFVAL { active }
			::= { hwMqeVodCfgEntry 18 }
		
		-- 1.3.6.1.4.1.2011.5.25.203.2.8.1.19
		hwMqeVodVpnInstance OBJECT-TYPE
			SYNTAX OCTET STRING (SIZE (0..30))
			MAX-ACCESS read-write
			STATUS current
			DESCRIPTION
				"Description."
			::= { hwMqeVodCfgEntry 19 }
		
		-- 1.3.6.1.4.1.2011.5.25.203.2.8.1.20
		hwMqeVodCodecType OBJECT-TYPE
			SYNTAX INTEGER
				{
				mpeg2(1),
				mpeg4(2),
				h264(3)
				}
			MAX-ACCESS read-write
			STATUS current
			DESCRIPTION
				"Description."
			DEFVAL { h264 }
			::= { hwMqeVodCfgEntry 20 }
		
		-- 1.3.6.1.4.1.2011.5.25.203.2.9
		hwMqeVodInterceptionTable OBJECT-TYPE
			SYNTAX SEQUENCE OF HwMqeVodInterceptionEntry
			MAX-ACCESS not-accessible
			STATUS current
			DESCRIPTION
				"Description."
			::= { hwMqeObjects 9 }
		
		-- 1.3.6.1.4.1.2011.5.25.203.2.9.1
		hwMqeVodInterceptionEntry OBJECT-TYPE
			SYNTAX HwMqeVodInterceptionEntry
			MAX-ACCESS not-accessible
			STATUS current
			DESCRIPTION
				"Description."
			INDEX { hwMqeVodInterceptionInterfaceName }
			::= { hwMqeVodInterceptionTable 1 }
		
		HwMqeVodInterceptionEntry ::=
			SEQUENCE { 
				hwMqeVodInterceptionInterfaceName
					OCTET STRING,
				hwMqeVodInterceptionRowStatus
					RowStatus
			 }

		-- 1.3.6.1.4.1.2011.5.25.203.2.9.1.1
		hwMqeVodInterceptionInterfaceName OBJECT-TYPE
			SYNTAX OCTET STRING (SIZE (0..47))
			MAX-ACCESS read-only
			STATUS current
			DESCRIPTION
				"Description."
			::= { hwMqeVodInterceptionEntry 1 }
		
		-- 1.3.6.1.4.1.2011.5.25.203.2.9.1.2
		hwMqeVodInterceptionRowStatus OBJECT-TYPE
			SYNTAX RowStatus
			MAX-ACCESS read-create
			STATUS current
			DESCRIPTION
				"Description."
			DEFVAL { active }
			::= { hwMqeVodInterceptionEntry 2 }
		
		-- 1.3.6.1.4.1.2011.5.25.203.2.10
		hwMqeVodMirrorTable OBJECT-TYPE
			SYNTAX SEQUENCE OF HwMqeVodMirrorEntry
			MAX-ACCESS not-accessible
			STATUS current
			DESCRIPTION
				"Description."
			::= { hwMqeObjects 10 }
		
		-- 1.3.6.1.4.1.2011.5.25.203.2.10.1
		hwMqeVodMirrorEntry OBJECT-TYPE
			SYNTAX HwMqeVodMirrorEntry
			MAX-ACCESS not-accessible
			STATUS current
			DESCRIPTION
				"Description."
			INDEX { hwMqeVodID, hwMqeVodMirrorInterfaceName }
			::= { hwMqeVodMirrorTable 1 }
		
		HwMqeVodMirrorEntry ::=
			SEQUENCE { 
				hwMqeVodMirrorInterfaceName
					OCTET STRING,
				hwMqeVodMirrorSlotId
					Integer32,
				hwMqeVodMirrorRowStatus
					RowStatus
			 }

		-- 1.3.6.1.4.1.2011.5.25.203.2.10.1.1
		hwMqeVodMirrorInterfaceName OBJECT-TYPE
			SYNTAX OCTET STRING (SIZE (0..47))
			MAX-ACCESS read-only
			STATUS current
			DESCRIPTION
				"Description."
			::= { hwMqeVodMirrorEntry 1 }
		
		-- 1.3.6.1.4.1.2011.5.25.203.2.10.1.2
		hwMqeVodMirrorSlotId OBJECT-TYPE
			SYNTAX Integer32
			MAX-ACCESS read-write
			STATUS current
			DESCRIPTION
				"Description."
			DEFVAL { '0'b }
			::= { hwMqeVodMirrorEntry 2 }
		
		-- 1.3.6.1.4.1.2011.5.25.203.2.10.1.3
		hwMqeVodMirrorRowStatus OBJECT-TYPE
			SYNTAX RowStatus
			MAX-ACCESS read-create
			STATUS current
			DESCRIPTION
				"Description."
			DEFVAL { active }
			::= { hwMqeVodMirrorEntry 3 }
		
		-- 1.3.6.1.4.1.2011.5.25.203.2.11
		hwMqeFtpCfgTable OBJECT-TYPE
			SYNTAX SEQUENCE OF HwMqeFtpCfgEntry
			MAX-ACCESS not-accessible
			STATUS current
			DESCRIPTION
				"Description."
			::= { hwMqeObjects 11 }
		
		-- 1.3.6.1.4.1.2011.5.25.203.2.11.1
		hwMqeFtpCfgEntry OBJECT-TYPE
			SYNTAX HwMqeFtpCfgEntry
			MAX-ACCESS not-accessible
			STATUS current
			DESCRIPTION
				"Description."
			INDEX { hwMqeFtpCfgServerIp, hwMqeFtpCfgServerPort }
			::= { hwMqeFtpCfgTable 1 }
		
		HwMqeFtpCfgEntry ::=
			SEQUENCE { 
				hwMqeFtpCfgServerIp
					IpAddress,
				hwMqeFtpCfgServerPort
					Integer32,
				hwMqeFtpCfgUserName
					OCTET STRING,
				hwMqeFtpCfgPassword
					OCTET STRING,
				hwMqeFtpCfgItemNum
					Integer32,
				hwMqeFtpCfgTime
					Integer32,
				hwMqeFtpCfgRowStatus
					RowStatus
			 }

		-- 1.3.6.1.4.1.2011.5.25.203.2.11.1.1
		hwMqeFtpCfgServerIp OBJECT-TYPE
			SYNTAX IpAddress
			MAX-ACCESS read-only
			STATUS current
			DESCRIPTION
				"Description."
			::= { hwMqeFtpCfgEntry 1 }
		
		-- 1.3.6.1.4.1.2011.5.25.203.2.11.1.2
		hwMqeFtpCfgServerPort OBJECT-TYPE
			SYNTAX Integer32 (21 | 1025..65535)
			MAX-ACCESS read-only
			STATUS current
			DESCRIPTION
				"Description."
			::= { hwMqeFtpCfgEntry 2 }
		
		-- 1.3.6.1.4.1.2011.5.25.203.2.11.1.3
		hwMqeFtpCfgUserName OBJECT-TYPE
			SYNTAX OCTET STRING (SIZE (0..63))
			MAX-ACCESS read-write
			STATUS current
			DESCRIPTION
				"Description."
			::= { hwMqeFtpCfgEntry 3 }
		
		-- 1.3.6.1.4.1.2011.5.25.203.2.11.1.4
		hwMqeFtpCfgPassword OBJECT-TYPE
			SYNTAX OCTET STRING (SIZE (0..127))
			MAX-ACCESS read-write
			STATUS current
			DESCRIPTION
				"Description."
			::= { hwMqeFtpCfgEntry 4 }
		
		-- 1.3.6.1.4.1.2011.5.25.203.2.11.1.5
		hwMqeFtpCfgItemNum OBJECT-TYPE
			SYNTAX Integer32 (1..1000)
			MAX-ACCESS read-write
			STATUS current
			DESCRIPTION
				"Description."
			::= { hwMqeFtpCfgEntry 5 }
		
		-- 1.3.6.1.4.1.2011.5.25.203.2.11.1.6
		hwMqeFtpCfgTime OBJECT-TYPE
			SYNTAX Integer32 (1..1800)
			MAX-ACCESS read-write
			STATUS current
			DESCRIPTION
				"Description."
			::= { hwMqeFtpCfgEntry 6 }
		
		-- 1.3.6.1.4.1.2011.5.25.203.2.11.1.7
		hwMqeFtpCfgRowStatus OBJECT-TYPE
			SYNTAX RowStatus
			MAX-ACCESS read-create
			STATUS current
			DESCRIPTION
				"Description."
			::= { hwMqeFtpCfgEntry 7 }
		
		-- 1.3.6.1.4.1.2011.5.25.203.2.12
		hwMqeSoapCfgTable OBJECT-TYPE
			SYNTAX SEQUENCE OF HwMqeSoapCfgEntry
			MAX-ACCESS not-accessible
			STATUS current
			DESCRIPTION
				"Description."
			::= { hwMqeObjects 12 }
		
		-- 1.3.6.1.4.1.2011.5.25.203.2.12.1
		hwMqeSoapCfgEntry OBJECT-TYPE
			SYNTAX HwMqeSoapCfgEntry
			MAX-ACCESS not-accessible
			STATUS current
			DESCRIPTION
				"Description."
			INDEX { hwMqeSoapInstanceName }
			::= { hwMqeSoapCfgTable 1 }
		
		HwMqeSoapCfgEntry ::=
			SEQUENCE { 
				hwMqeSoapInstanceName
					OCTET STRING,
				hwMqeSoapLocalAddress
					IpAddress,
				hwMqeSoapLocalPort
					Integer32,
				hwMqeSoapTargetAddress
					IpAddress,
				hwMqeSoapTargetPort
					Integer32,
				hwMqeSoapLRegister
					INTEGER,
				hwMqeSoapLRegVasGroupID
					OCTET STRING,
				hwMqeSoapEcmpPort
					OCTET STRING,
				hwMqeSoapDipPort
					OCTET STRING,
				hwMqeSoapPRegister
					INTEGER,
				hwMqeSoapPRegVasGroupID
					OCTET STRING,
				hwMqeSoapRowStatus
					RowStatus
			 }

		-- 1.3.6.1.4.1.2011.5.25.203.2.12.1.1
		hwMqeSoapInstanceName OBJECT-TYPE
			SYNTAX OCTET STRING (SIZE (0..31))
			MAX-ACCESS read-only
			STATUS current
			DESCRIPTION
				"Description."
			::= { hwMqeSoapCfgEntry 1 }
		
		-- 1.3.6.1.4.1.2011.5.25.203.2.12.1.2
		hwMqeSoapLocalAddress OBJECT-TYPE
			SYNTAX IpAddress
			MAX-ACCESS read-write
			STATUS current
			DESCRIPTION
				"Description."
			::= { hwMqeSoapCfgEntry 2 }
		
		-- 1.3.6.1.4.1.2011.5.25.203.2.12.1.3
		hwMqeSoapLocalPort OBJECT-TYPE
			SYNTAX Integer32 (0 | 1025..65535)
			MAX-ACCESS read-write
			STATUS current
			DESCRIPTION
				"Description."
			DEFVAL { '0'b }
			::= { hwMqeSoapCfgEntry 3 }
		
		-- 1.3.6.1.4.1.2011.5.25.203.2.12.1.4
		hwMqeSoapTargetAddress OBJECT-TYPE
			SYNTAX IpAddress
			MAX-ACCESS read-write
			STATUS current
			DESCRIPTION
				"Description."
			::= { hwMqeSoapCfgEntry 4 }
		
		-- 1.3.6.1.4.1.2011.5.25.203.2.12.1.5
		hwMqeSoapTargetPort OBJECT-TYPE
			SYNTAX Integer32 (0 | 1025..65535)
			MAX-ACCESS read-write
			STATUS current
			DESCRIPTION
				"Description."
			DEFVAL { '0'b }
			::= { hwMqeSoapCfgEntry 5 }
		
		-- 1.3.6.1.4.1.2011.5.25.203.2.12.1.6
		hwMqeSoapLRegister OBJECT-TYPE
			SYNTAX INTEGER
				{
				noregister(0),
				register(1)
				}
			MAX-ACCESS read-write
			STATUS current
			DESCRIPTION
				"Description."
			DEFVAL { noregister }
			::= { hwMqeSoapCfgEntry 6 }
		
		-- 1.3.6.1.4.1.2011.5.25.203.2.12.1.7
		hwMqeSoapLRegVasGroupID OBJECT-TYPE
			SYNTAX OCTET STRING (SIZE (0..8))
			MAX-ACCESS read-write
			STATUS current
			DESCRIPTION
				"Description."
			::= { hwMqeSoapCfgEntry 7 }
		
		-- 1.3.6.1.4.1.2011.5.25.203.2.12.1.8
		hwMqeSoapEcmpPort OBJECT-TYPE
			SYNTAX OCTET STRING (SIZE (0..24))
			MAX-ACCESS read-write
			STATUS current
			DESCRIPTION
				"Description."
			::= { hwMqeSoapCfgEntry 8 }
		
		-- 1.3.6.1.4.1.2011.5.25.203.2.12.1.9
		hwMqeSoapDipPort OBJECT-TYPE
			SYNTAX OCTET STRING (SIZE (0..24))
			MAX-ACCESS read-write
			STATUS current
			DESCRIPTION
				"Description."
			::= { hwMqeSoapCfgEntry 9 }
		
		-- 1.3.6.1.4.1.2011.5.25.203.2.12.1.10
		hwMqeSoapPRegister OBJECT-TYPE
			SYNTAX INTEGER
				{
				noregister(0),
				register(1)
				}
			MAX-ACCESS read-write
			STATUS current
			DESCRIPTION
				"Description."
			DEFVAL { noregister }
			::= { hwMqeSoapCfgEntry 10 }
		
		-- 1.3.6.1.4.1.2011.5.25.203.2.12.1.11
		hwMqeSoapPRegVasGroupID OBJECT-TYPE
			SYNTAX OCTET STRING (SIZE (0..8))
			MAX-ACCESS read-write
			STATUS current
			DESCRIPTION
				"Description."
			::= { hwMqeSoapCfgEntry 11 }
		
		-- 1.3.6.1.4.1.2011.5.25.203.2.12.1.12
		hwMqeSoapRowStatus OBJECT-TYPE
			SYNTAX RowStatus
			MAX-ACCESS read-create
			STATUS current
			DESCRIPTION
				"Description."
			DEFVAL { active }
			::= { hwMqeSoapCfgEntry 12 }
		
--  1.3.6.1.4.1.2011.5.25.203.2
		-- 1.3.6.1.4.1.2011.5.25.203.4
		hwMqeNotifications OBJECT IDENTIFIER ::= { hwMqeMIB 4 }
		
		-- 1.3.6.1.4.1.2011.5.25.203.4.1
		hwMqeOverDfThreshold NOTIFICATION-TYPE
			OBJECTS { hwMqeChannelName, hwMqeChannelGroupAddress, hwMqeChannelSourceAddress, hwMqeChannelMdiDfThreshold, hwMqeChannelMdiDf
				 }
			STATUS current
			DESCRIPTION 
				"Description."
			::= { hwMqeNotifications 1 }
		
		-- 1.3.6.1.4.1.2011.5.25.203.4.2
		hwMqeOverMlrThreshold NOTIFICATION-TYPE
			OBJECTS { hwMqeChannelName, hwMqeChannelGroupAddress, hwMqeChannelSourceAddress, hwMqeChannelMdiMlrThreshold, hwMqeChannelMdiMlr
				 }
			STATUS current
			DESCRIPTION 
				"Description."
			::= { hwMqeNotifications 2 }
		
		-- 1.3.6.1.4.1.2011.5.25.203.4.3
		hwMqeLowVmosThreshold NOTIFICATION-TYPE
			OBJECTS { hwMqeChannelName, hwMqeChannelSourceAddress, hwMqeChannelGroupAddress, hwMqeChannelVmosThreshold, hwMqeChannelVmosValue
				 }
			STATUS current
			DESCRIPTION 
				"Description."
			::= { hwMqeNotifications 3 }
		
--  1.3.6.1.4.1.2011.5.25.203.3
		-- 1.3.6.1.4.1.2011.5.25.203.6
		hwMqeGroup OBJECT IDENTIFIER ::= { hwMqeMIB 6 }
		
		-- 1.3.6.1.4.1.2011.5.25.203.6.1
		hwMqeScalarGroup OBJECT-GROUP
			OBJECTS { hwMqeEnable, hwMqeTrapEnable, hwMqeFtpTimerReset, hwMqeBtvChnlThreshold, hwMqeChannelCfgAuto, 
				hwMqeFtpLocalAddress, hwMqeSoapEnable, hwMqeFtpEnable }
			STATUS current
			DESCRIPTION 
				"Description."
			::= { hwMqeGroup 1 }
		
--  1.3.6.1.4.1.2011.5.25.203.3.1
		-- 1.3.6.1.4.1.2011.5.25.203.6.2
		hwMqeVasGroupGroup OBJECT-GROUP
			OBJECTS { hwVasGroupType, hwVasGroupBindSlotID, hwVasGroupBindAddress, hwVasGroupFccRtpDscp, hwVasGroupFccRtcpDscp, 
				hwVasGroupRetRtpDscp, hwVasGroupRetRtcpDscp, hwVasGroupServerPort, hwVasGroupBindInterfaceName, hwVasGroupUndoBindSlotID, 
				hwVasGroupUndoBindInterfaceName, hwVasGroupRowStatus, hwVasGroupBurstRatio, hwVasGroupBurstLowRatio, hwVasGroupMulticastDelay
				 }
			STATUS current
			DESCRIPTION 
				"Description."
			::= { hwMqeGroup 2 }
		
--  1.3.6.1.4.1.2011.5.25.203.3.2
		-- 1.3.6.1.4.1.2011.5.25.203.6.3
		hwMqeChannelGroup OBJECT-GROUP
			OBJECTS { hwMqeChannelName, hwMqeChannelGroupAddress, hwMqeChannelSourceAddress, hwMqeChannelEncapType, hwMqeChannelCacheTime, 
				hwMqeChannelMaxGopInterval, hwMqeChannelQuickParse, hwMqeChannelRate, hwMqeChannelCodecType, hwMqeChannelRowStatus, 
				hwMqeChannelDestPort, hwMqeChannelSSRC }
			STATUS current
			DESCRIPTION 
				"Description."
			::= { hwMqeGroup 3 }
		
--  1.3.6.1.4.1.2011.5.25.203.3.3
		-- 1.3.6.1.4.1.2011.5.25.203.6.4
		hwMqeChannelCfgGroup OBJECT-GROUP
			OBJECTS { hwMqeChannelFccEnable, hwMqeChannelRetEnable, hwMqeChannelMdiEnable, hwMqeChannelMdiSlotID, hwMqeChannelMdiDfThreshold, 
				hwMqeChannelMdiMlrThreshold, hwMqeChannelVmosEnable, hwMqeChannelVmosSlotID, hwMqeChannelVmosThreshold, hwMqeChannelVmosVasGroupID, 
				hwMqeChannelSelectiveBurst, hwMqeChannelVmosSampleInterval, hwMqeChannelFccVasGroupID, hwMqeChannelRetVasGroupID, hwMqeChannelMdiVasGroupID
				 }
			STATUS current
			DESCRIPTION 
				"Description."
			::= { hwMqeGroup 4 }
		
		-- 1.3.6.1.4.1.2011.5.25.203.6.5
		hwMqeStatGroup OBJECT-GROUP
			OBJECTS { hwMqeStatFccReqReceived, hwMqeStatFccReqProcessed, hwMqeStatFccReqRefused, hwMqeStatRetReqReceived, hwMqeStatRetReqProcessed, 
				hwMqeStatRetReqRefused, hwMqeStatMdiChannels, hwMqeStatVmosChannels, hwMqeStatSlotID, hwMqeStatCpuID
				 }
			STATUS current
			DESCRIPTION 
				"Description."
			::= { hwMqeGroup 5 }
		
--  1.3.6.1.4.1.2011.5.25.203.3.4
		-- 1.3.6.1.4.1.2011.5.25.203.6.6
		hwMqeMdiStatGroup OBJECT-GROUP
			OBJECTS { hwMqeChannelMdiDf, hwMqeChannelMdiMlr, hwMqeChannelMdiTimeStamp, hwMqeChannelMdiMlt15, hwMqeChannelMdiMR, 
				hwMqeChannelMdiMlt24, hwMqeChannelMdiIntervalNum, hwMqeChannelMdiID }
			STATUS current
			DESCRIPTION 
				"Description."
			::= { hwMqeGroup 6 }
		
--  1.3.6.1.4.1.2011.5.25.203.3.5
		-- 1.3.6.1.4.1.2011.5.25.203.6.7
		hwMqeVmosStatGroup OBJECT-GROUP
			OBJECTS { hwMqeChannelVmosPlr, hwMqeChannelVmosPler, hwMqeChannelVmosPler2, hwMqeChannelVmosMaxj, hwMqeChannelVmosMeanj, 
				hwMqeChannelVmosMeanj2, hwMqeChannelVmosValue, hwMqeChannelVmosIntervalNum, hwMqeChannelVmosTimeStamp, hwMqeChannelVmosID
				 }
			STATUS current
			DESCRIPTION 
				"Description."
			::= { hwMqeGroup 7 }
		
		-- 1.3.6.1.4.1.2011.5.25.203.6.8
		hwMqeNotificationGroup NOTIFICATION-GROUP
			NOTIFICATIONS { hwMqeOverDfThreshold, hwMqeOverMlrThreshold, hwMqeLowVmosThreshold }
			STATUS current
			DESCRIPTION 
				"Description."
			::= { hwMqeGroup 8 }
		
		-- 1.3.6.1.4.1.2011.5.25.203.6.9
		hwMqeVodCfgTableGroup OBJECT-GROUP
			OBJECTS { hwMqeVodID, hwMqeVodSourceAddress, hwMqeVodMdiMlrThreshold, hwMqeVodMdiDfThreshold, hwMqeVodDescription, 
				hwMqeVodVmosEnable, hwMqeVodMdiEnable, hwMqeVodVpnInstance, hwMqeVodCodecType, hwMqeVodDestAddress, 
				hwMqeVodSourcePort, hwMqeVodDestPort, hwMqeVodEncapType, hwMqeVodMdiVasGroupID, hwMqeVodMdiSlotID, 
				hwMqeVodVmosVasGroupID, hwMqeVodVmosSlotID, hwMqeVodVmosThreshold, hwMqeVodVmosSampleInterval, hwMqeVodCfgRowStatus
				 }
			STATUS current
			DESCRIPTION 
				"Description."
			::= { hwMqeGroup 9 }
		
		-- 1.3.6.1.4.1.2011.5.25.203.6.10
		hwMqeVodInterceptionTableGroup OBJECT-GROUP
			OBJECTS { hwMqeVodInterceptionInterfaceName, hwMqeVodInterceptionRowStatus }
			STATUS current
			DESCRIPTION 
				"Description."
			::= { hwMqeGroup 10 }
		
		-- 1.3.6.1.4.1.2011.5.25.203.6.11
		hwMqeVodMirrorTableGroup OBJECT-GROUP
			OBJECTS { hwMqeVodMirrorInterfaceName, hwMqeVodMirrorSlotId, hwMqeVodMirrorRowStatus }
			STATUS current
			DESCRIPTION 
				"Description."
			::= { hwMqeGroup 11 }
		
		-- 1.3.6.1.4.1.2011.5.25.203.6.12
		hwMqeSoapCfgTableGroup OBJECT-GROUP
			OBJECTS { hwMqeSoapInstanceName, hwMqeSoapLocalAddress, hwMqeSoapLocalPort, hwMqeSoapTargetAddress, hwMqeSoapTargetPort, 
				hwMqeSoapRowStatus, hwMqeSoapLRegister, hwMqeSoapLRegVasGroupID, hwMqeSoapEcmpPort, hwMqeSoapDipPort, 
				hwMqeSoapPRegister, hwMqeSoapPRegVasGroupID }
			STATUS current
			DESCRIPTION 
				"Description."
			::= { hwMqeGroup 12 }
		
		-- 1.3.6.1.4.1.2011.5.25.203.6.13
		hwMqeFtpCfgTableGroup OBJECT-GROUP
			OBJECTS { hwMqeFtpCfgItemNum, hwMqeFtpCfgPassword, hwMqeFtpCfgUserName, hwMqeFtpCfgRowStatus, hwMqeFtpCfgTime, 
				hwMqeFtpCfgServerIp, hwMqeFtpCfgServerPort }
			STATUS current
			DESCRIPTION 
				"Description."
			::= { hwMqeGroup 13 }
		
	
	END

--
-- HUAWEI-MQE-MIB49.mib
--
