-- file automatically created


TELDAT-TRAP-NTP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ntpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the NTP event subsystem."
    REVISION "201401200930Z"
    DESCRIPTION "Initial implementation"
        ::= { telEventTraps 139 }


ntpEventsGroup	OBJECT IDENTIFIER	::= { ntpTrapsMIB 1 }

ntpNotifications	OBJECT IDENTIFIER	::= { ntpTrapsMIB 2 }
ntpNotificationsPrefix	OBJECT IDENTIFIER	::= { ntpNotifications 0 }

ntpEventObjects1 OBJECT-IDENTITY
    STATUS current
    DESCRIPTION
        "Event NTP.1
        This message is generated when a packet is received from port 123."
    ::= { ntpEventsGroup 1 }

ntp1_ntpsourceadd OBJECT-TYPE
    SYNTAX IpAddress
    MAX-ACCESS accessible-for-notify
    STATUS current
    DESCRIPTION
        "Parameter 'ntpsourceadd' in event NTP.1"
    ::= { ntpEventObjects1 1 }

ntp1_refTime OBJECT-TYPE
    SYNTAX DisplayString
    MAX-ACCESS accessible-for-notify
    STATUS current
    DESCRIPTION
        "Parameter 'refTime' in event NTP.1"
    ::= { ntpEventObjects1 2 }

ntp1_orgTime OBJECT-TYPE
    SYNTAX DisplayString
    MAX-ACCESS accessible-for-notify
    STATUS current
    DESCRIPTION
        "Parameter 'orgTime' in event NTP.1"
    ::= { ntpEventObjects1 3 }

ntp1_recvTime OBJECT-TYPE
    SYNTAX DisplayString
    MAX-ACCESS accessible-for-notify
    STATUS current
    DESCRIPTION
        "Parameter 'recvTime' in event NTP.1"
    ::= { ntpEventObjects1 4 }

ntp1_txTime OBJECT-TYPE
    SYNTAX DisplayString
    MAX-ACCESS accessible-for-notify
    STATUS current
    DESCRIPTION
        "Parameter 'txTime' in event NTP.1"
    ::= { ntpEventObjects1 5 }

ntpEventObjects2 OBJECT-IDENTITY
    STATUS current
    DESCRIPTION
        "Event NTP.2
        This message is generated when a packet is sent to a remote host."
    ::= { ntpEventsGroup 2 }

ntp2_ntpdestadd OBJECT-TYPE
    SYNTAX IpAddress
    MAX-ACCESS accessible-for-notify
    STATUS current
    DESCRIPTION
        "Parameter 'ntpdestadd' in event NTP.2"
    ::= { ntpEventObjects2 1 }

ntp2_refTime OBJECT-TYPE
    SYNTAX DisplayString
    MAX-ACCESS accessible-for-notify
    STATUS current
    DESCRIPTION
        "Parameter 'refTime' in event NTP.2"
    ::= { ntpEventObjects2 2 }

ntp2_orgTime OBJECT-TYPE
    SYNTAX DisplayString
    MAX-ACCESS accessible-for-notify
    STATUS current
    DESCRIPTION
        "Parameter 'orgTime' in event NTP.2"
    ::= { ntpEventObjects2 3 }

ntp2_recvTime OBJECT-TYPE
    SYNTAX DisplayString
    MAX-ACCESS accessible-for-notify
    STATUS current
    DESCRIPTION
        "Parameter 'recvTime' in event NTP.2"
    ::= { ntpEventObjects2 4 }

ntp2_txTime OBJECT-TYPE
    SYNTAX DisplayString
    MAX-ACCESS accessible-for-notify
    STATUS current
    DESCRIPTION
        "Parameter 'txTime' in event NTP.2"
    ::= { ntpEventObjects2 5 }

ntpEventObjects3 OBJECT-IDENTITY
    STATUS current
    DESCRIPTION
        "Event NTP.3
        This message is generated after checking the input packet. Error codes
        are shown below:
        TEST1		0x0001		Duplicate packet received.
        TEST2		0x0002		Bogus packet received.
        TEST3		0x0004		Protocol unsynchronized.
        TEST4		0x0008		Peer delay/dispersion bounds check.
        TEST5		0x0010		Peer authentication failed.
        TEST6       0x0020		Peer clock unsynchronized.
        TEST7		0x0040		Peer stratum out of bounds.
        TEST8		0x0080		Root delay/dispersion bounds check."
    ::= { ntpEventsGroup 3 }

ntp3_ntpsourceadd OBJECT-TYPE
    SYNTAX IpAddress
    MAX-ACCESS accessible-for-notify
    STATUS current
    DESCRIPTION
        "Parameter 'ntpsourceadd' in event NTP.3"
    ::= { ntpEventObjects3 1 }

ntp3_errorcode OBJECT-TYPE
    SYNTAX Integer32
    MAX-ACCESS accessible-for-notify
    STATUS current
    DESCRIPTION
        "Parameter 'errorcode' in event NTP.3"
    ::= { ntpEventObjects3 2 }

ntpEventObjects4 OBJECT-IDENTITY
    STATUS current
    DESCRIPTION
        "Event NTP.4
        This message indicates a wrong NTP version."
    ::= { ntpEventsGroup 4 }

ntp4_versnumber OBJECT-TYPE
    SYNTAX Integer32
    MAX-ACCESS accessible-for-notify
    STATUS current
    DESCRIPTION
        "Parameter 'versnumber' in event NTP.4"
    ::= { ntpEventObjects4 1 }

ntp4_ntpsourceadd OBJECT-TYPE
    SYNTAX IpAddress
    MAX-ACCESS accessible-for-notify
    STATUS current
    DESCRIPTION
        "Parameter 'ntpsourceadd' in event NTP.4"
    ::= { ntpEventObjects4 2 }

ntpEventObjects5 OBJECT-IDENTITY
    STATUS current
    DESCRIPTION
        "Event NTP.5
        This message indicates the received packet is a control packet."
    ::= { ntpEventsGroup 5 }

ntp5_ntpsourceadd OBJECT-TYPE
    SYNTAX IpAddress
    MAX-ACCESS accessible-for-notify
    STATUS current
    DESCRIPTION
        "Parameter 'ntpsourceadd' in event NTP.5"
    ::= { ntpEventObjects5 1 }

ntpEventObjects6 OBJECT-IDENTITY
    STATUS current
    DESCRIPTION
        "Event NTP.6
        This message indicates the received packet is a Broadcast packet."
    ::= { ntpEventsGroup 6 }

ntp6_ntpsourceadd OBJECT-TYPE
    SYNTAX IpAddress
    MAX-ACCESS accessible-for-notify
    STATUS current
    DESCRIPTION
        "Parameter 'ntpsourceadd' in event NTP.6"
    ::= { ntpEventObjects6 1 }

ntpEventObjects8 OBJECT-IDENTITY
    STATUS current
    DESCRIPTION
        "Event NTP.8
        This message indicates the received packet is private packet."
    ::= { ntpEventsGroup 8 }

ntp8_ntpsourceadd OBJECT-TYPE
    SYNTAX IpAddress
    MAX-ACCESS accessible-for-notify
    STATUS current
    DESCRIPTION
        "Parameter 'ntpsourceadd' in event NTP.8"
    ::= { ntpEventObjects8 1 }

ntpEventObjects9 OBJECT-IDENTITY
    STATUS current
    DESCRIPTION
        "Event NTP.9
        This message indicates the received packet is client packet."
    ::= { ntpEventsGroup 9 }

ntp9_ntpsourceadd OBJECT-TYPE
    SYNTAX IpAddress
    MAX-ACCESS accessible-for-notify
    STATUS current
    DESCRIPTION
        "Parameter 'ntpsourceadd' in event NTP.9"
    ::= { ntpEventObjects9 1 }

ntpEventObjects10 OBJECT-IDENTITY
    STATUS current
    DESCRIPTION
        "Event NTP.10
        This message is generated by NTP Fake-Out routine."
    ::= { ntpEventsGroup 10 }

ntp10_ntpsourceadd OBJECT-TYPE
    SYNTAX IpAddress
    MAX-ACCESS accessible-for-notify
    STATUS current
    DESCRIPTION
        "Parameter 'ntpsourceadd' in event NTP.10"
    ::= { ntpEventObjects10 1 }

ntpEventObjects11 OBJECT-IDENTITY
    STATUS current
    DESCRIPTION
        "Event NTP.11
        This message is generated when a packet arrived from an unknown peer."
    ::= { ntpEventsGroup 11 }

ntp11_ntpsourceadd OBJECT-TYPE
    SYNTAX IpAddress
    MAX-ACCESS accessible-for-notify
    STATUS current
    DESCRIPTION
        "Parameter 'ntpsourceadd' in event NTP.11"
    ::= { ntpEventObjects11 1 }

ntpEventObjects12 OBJECT-IDENTITY
    STATUS current
    DESCRIPTION
        "Event NTP.12
        This message indicates the received packet is active mode packet."
    ::= { ntpEventsGroup 12 }

ntp12_ntpsourceadd OBJECT-TYPE
    SYNTAX IpAddress
    MAX-ACCESS accessible-for-notify
    STATUS current
    DESCRIPTION
        "Parameter 'ntpsourceadd' in event NTP.12"
    ::= { ntpEventObjects12 1 }

ntpEventObjects13 OBJECT-IDENTITY
    STATUS current
    DESCRIPTION
        "Event NTP.13
        This message indicates the received packet is passive mode packet."
    ::= { ntpEventsGroup 13 }

ntp13_ntpsourceadd OBJECT-TYPE
    SYNTAX IpAddress
    MAX-ACCESS accessible-for-notify
    STATUS current
    DESCRIPTION
        "Parameter 'ntpsourceadd' in event NTP.13"
    ::= { ntpEventObjects13 1 }

ntpEventObjects14 OBJECT-IDENTITY
    STATUS current
    DESCRIPTION
        "Event NTP.14
        This message indicates the received packet is server mode packet."
    ::= { ntpEventsGroup 14 }

ntp14_ntpsourceadd OBJECT-TYPE
    SYNTAX IpAddress
    MAX-ACCESS accessible-for-notify
    STATUS current
    DESCRIPTION
        "Parameter 'ntpsourceadd' in event NTP.14"
    ::= { ntpEventObjects14 1 }

ntpEventObjects15 OBJECT-IDENTITY
    STATUS current
    DESCRIPTION
        "Event NTP.15
        This message is shown when a clock update has been done."
    ::= { ntpEventsGroup 15 }

ntp15_Delay OBJECT-TYPE
    SYNTAX Integer32
    MAX-ACCESS accessible-for-notify
    STATUS current
    DESCRIPTION
        "Parameter 'Delay' in event NTP.15"
    ::= { ntpEventObjects15 1 }

ntp15_OffsetSign OBJECT-TYPE
    SYNTAX DisplayString
    MAX-ACCESS accessible-for-notify
    STATUS current
    DESCRIPTION
        "Parameter 'OffsetSign' in event NTP.15"
    ::= { ntpEventObjects15 2 }

ntp15_OffsetSeconds OBJECT-TYPE
    SYNTAX Integer32
    MAX-ACCESS accessible-for-notify
    STATUS current
    DESCRIPTION
        "Parameter 'OffsetSeconds' in event NTP.15"
    ::= { ntpEventObjects15 3 }

ntp15_OffsetMillSeconds OBJECT-TYPE
    SYNTAX Integer32
    MAX-ACCESS accessible-for-notify
    STATUS current
    DESCRIPTION
        "Parameter 'OffsetMillSeconds' in event NTP.15"
    ::= { ntpEventObjects15 4 }

ntpEventObjects16 OBJECT-IDENTITY
    STATUS current
    DESCRIPTION
        "Event NTP.16
        This message is shown when a date has been established."
    ::= { ntpEventsGroup 16 }

ntp16_datetostab OBJECT-TYPE
    SYNTAX DisplayString
    MAX-ACCESS accessible-for-notify
    STATUS current
    DESCRIPTION
        "Parameter 'datetostab' in event NTP.16"
    ::= { ntpEventObjects16 1 }

ntp16_stabdate OBJECT-TYPE
    SYNTAX DisplayString
    MAX-ACCESS accessible-for-notify
    STATUS current
    DESCRIPTION
        "Parameter 'stabdate' in event NTP.16"
    ::= { ntpEventObjects16 2 }

ntpEventObjects17 OBJECT-IDENTITY
    STATUS current
    DESCRIPTION
        "Event NTP.17
        This is a debugging message used to know the time since the timer
        was thrown."
    ::= { ntpEventsGroup 17 }

ntp17_secTimer OBJECT-TYPE
    SYNTAX Integer32
    MAX-ACCESS accessible-for-notify
    STATUS current
    DESCRIPTION
        "Parameter 'secTimer' in event NTP.17"
    ::= { ntpEventObjects17 1 }

ntpEventObjects18 OBJECT-IDENTITY
    STATUS current
    DESCRIPTION
        "Event NTP.18
        This message is used to know the clock precision."
    ::= { ntpEventsGroup 18 }

ntp18_millisec OBJECT-TYPE
    SYNTAX Integer32
    MAX-ACCESS accessible-for-notify
    STATUS current
    DESCRIPTION
        "Parameter 'millisec' in event NTP.18"
    ::= { ntpEventObjects18 1 }

ntpEventObjects19 OBJECT-IDENTITY
    STATUS current
    DESCRIPTION
        "Event NTP.19
        Device exact date and time."
    ::= { ntpEventsGroup 19 }

ntp19_datetime OBJECT-TYPE
    SYNTAX DisplayString
    MAX-ACCESS accessible-for-notify
    STATUS current
    DESCRIPTION
        "Parameter 'datetime' in event NTP.19"
    ::= { ntpEventObjects19 1 }

ntp19_millisec OBJECT-TYPE
    SYNTAX Integer32
    MAX-ACCESS accessible-for-notify
    STATUS current
    DESCRIPTION
        "Parameter 'millisec' in event NTP.19"
    ::= { ntpEventObjects19 2 }

ntpEventObjects20 OBJECT-IDENTITY
    STATUS current
    DESCRIPTION
        "Event NTP.20
        This message is generated when NTP client doesn't accept
        NTP broadcast messages from packet source host."
    ::= { ntpEventsGroup 20 }

ntp20_ntpsourceadd OBJECT-TYPE
    SYNTAX IpAddress
    MAX-ACCESS accessible-for-notify
    STATUS current
    DESCRIPTION
        "Parameter 'ntpsourceadd' in event NTP.20"
    ::= { ntpEventObjects20 1 }

ntpEventObjects21 OBJECT-IDENTITY
    STATUS current
    DESCRIPTION
        "Event NTP.21
        NTP transmission date/time."
    ::= { ntpEventsGroup 21 }

ntp21_datetime OBJECT-TYPE
    SYNTAX DisplayString
    MAX-ACCESS accessible-for-notify
    STATUS current
    DESCRIPTION
        "Parameter 'datetime' in event NTP.21"
    ::= { ntpEventObjects21 1 }

ntp21_millisec OBJECT-TYPE
    SYNTAX Integer32
    MAX-ACCESS accessible-for-notify
    STATUS current
    DESCRIPTION
        "Parameter 'millisec' in event NTP.21"
    ::= { ntpEventObjects21 2 }

ntp21_timeticks OBJECT-TYPE
    SYNTAX Integer32
    MAX-ACCESS accessible-for-notify
    STATUS current
    DESCRIPTION
        "Parameter 'timeticks' in event NTP.21"
    ::= { ntpEventObjects21 3 }

ntpEventObjects22 OBJECT-IDENTITY
    STATUS current
    DESCRIPTION
        "Event NTP.22
        NTP reception date/time."
    ::= { ntpEventsGroup 22 }

ntp22_datetime OBJECT-TYPE
    SYNTAX DisplayString
    MAX-ACCESS accessible-for-notify
    STATUS current
    DESCRIPTION
        "Parameter 'datetime' in event NTP.22"
    ::= { ntpEventObjects22 1 }

ntp22_millisec OBJECT-TYPE
    SYNTAX Integer32
    MAX-ACCESS accessible-for-notify
    STATUS current
    DESCRIPTION
        "Parameter 'millisec' in event NTP.22"
    ::= { ntpEventObjects22 2 }

ntp22_timeticks OBJECT-TYPE
    SYNTAX Integer32
    MAX-ACCESS accessible-for-notify
    STATUS current
    DESCRIPTION
        "Parameter 'timeticks' in event NTP.22"
    ::= { ntpEventObjects22 3 }

ntpEventObjects24 OBJECT-IDENTITY
    STATUS current
    DESCRIPTION
        "Event NTP.24
        NTP packets are discarded because NTP client is stopped."
    ::= { ntpEventsGroup 24 }

ntp24_ntpsourceadd OBJECT-TYPE
    SYNTAX IpAddress
    MAX-ACCESS accessible-for-notify
    STATUS current
    DESCRIPTION
        "Parameter 'ntpsourceadd' in event NTP.24"
    ::= { ntpEventObjects24 1 }

ntpEventObjects26 OBJECT-IDENTITY
    STATUS current
    DESCRIPTION
        "Event NTP.26
        This message is generated when a local packet arrived. NTP only accepts
        packets from other hosts."
    ::= { ntpEventsGroup 26 }

ntp26_ntpsourceadd OBJECT-TYPE
    SYNTAX IpAddress
    MAX-ACCESS accessible-for-notify
    STATUS current
    DESCRIPTION
        "Parameter 'ntpsourceadd' in event NTP.26"
    ::= { ntpEventObjects26 1 }

ntpEventObjects27 OBJECT-IDENTITY
    STATUS current
    DESCRIPTION
        "Event NTP.27
        A NTP packet has been received from the specified host, but it was wrong
        because it failed the specidifed test (number, error code and
        description)."
    ::= { ntpEventsGroup 27 }

ntp27_ntpsourceadd OBJECT-TYPE
    SYNTAX IpAddress
    MAX-ACCESS accessible-for-notify
    STATUS current
    DESCRIPTION
        "Parameter 'ntpsourceadd' in event NTP.27"
    ::= { ntpEventObjects27 1 }

ntp27_testnumber OBJECT-TYPE
    SYNTAX Integer32
    MAX-ACCESS accessible-for-notify
    STATUS current
    DESCRIPTION
        "Parameter 'testnumber' in event NTP.27"
    ::= { ntpEventObjects27 2 }

ntp27_testerrorcode OBJECT-TYPE
    SYNTAX Integer32
    MAX-ACCESS accessible-for-notify
    STATUS current
    DESCRIPTION
        "Parameter 'testerrorcode' in event NTP.27"
    ::= { ntpEventObjects27 3 }

ntp27_testdescription OBJECT-TYPE
    SYNTAX DisplayString
    MAX-ACCESS accessible-for-notify
    STATUS current
    DESCRIPTION
        "Parameter 'testdescription' in event NTP.27"
    ::= { ntpEventObjects27 4 }

ntpEventObjects28 OBJECT-IDENTITY
    STATUS current
    DESCRIPTION
        "Event NTP.28
        NTP peer host clock data has been updated by the clock-filter prodedure,
        producing new values for delay, offset and dispersion, as shown in the
        trace."
    ::= { ntpEventsGroup 28 }

ntp28_ntpsourceadd OBJECT-TYPE
    SYNTAX IpAddress
    MAX-ACCESS accessible-for-notify
    STATUS current
    DESCRIPTION
        "Parameter 'ntpsourceadd' in event NTP.28"
    ::= { ntpEventObjects28 1 }

ntp28_delay OBJECT-TYPE
    SYNTAX Integer32
    MAX-ACCESS accessible-for-notify
    STATUS current
    DESCRIPTION
        "Parameter 'delay' in event NTP.28"
    ::= { ntpEventObjects28 2 }

ntp28_offset OBJECT-TYPE
    SYNTAX Integer32
    MAX-ACCESS accessible-for-notify
    STATUS current
    DESCRIPTION
        "Parameter 'offset' in event NTP.28"
    ::= { ntpEventObjects28 3 }

ntp28_dispersion OBJECT-TYPE
    SYNTAX Integer32
    MAX-ACCESS accessible-for-notify
    STATUS current
    DESCRIPTION
        "Parameter 'dispersion' in event NTP.28"
    ::= { ntpEventObjects28 4 }

ntpEventObjects29 OBJECT-IDENTITY
    STATUS current
    DESCRIPTION
        "Event NTP.29
        NTP peer host clock data has been discarded by the clock-selection
        prodedure, and the cause is shown."
    ::= { ntpEventsGroup 29 }

ntp29_ntpsourceadd OBJECT-TYPE
    SYNTAX IpAddress
    MAX-ACCESS accessible-for-notify
    STATUS current
    DESCRIPTION
        "Parameter 'ntpsourceadd' in event NTP.29"
    ::= { ntpEventObjects29 1 }

ntp29_discardcause OBJECT-TYPE
    SYNTAX DisplayString
    MAX-ACCESS accessible-for-notify
    STATUS current
    DESCRIPTION
        "Parameter 'discardcause' in event NTP.29"
    ::= { ntpEventObjects29 2 }

ntpEventObjects30 OBJECT-IDENTITY
    STATUS current
    DESCRIPTION
        "Event NTP.30
        NTP peer host clock data has been selected by the clock-selection
        prodedure."
    ::= { ntpEventsGroup 30 }

ntp30_ntpsourceadd OBJECT-TYPE
    SYNTAX IpAddress
    MAX-ACCESS accessible-for-notify
    STATUS current
    DESCRIPTION
        "Parameter 'ntpsourceadd' in event NTP.30"
    ::= { ntpEventObjects30 1 }

ntpEventObjects32 OBJECT-IDENTITY
    STATUS current
    DESCRIPTION
        "Event NTP.32
        An NTP packet is received or transmitted from or to the given host. Some
        message data is shown. More information is available in other events."
    ::= { ntpEventsGroup 32 }

ntp32_rxtx OBJECT-TYPE
    SYNTAX DisplayString
    MAX-ACCESS accessible-for-notify
    STATUS current
    DESCRIPTION
        "Parameter 'rxtx' in event NTP.32"
    ::= { ntpEventObjects32 1 }

ntp32_peeraddr OBJECT-TYPE
    SYNTAX IpAddress
    MAX-ACCESS accessible-for-notify
    STATUS current
    DESCRIPTION
        "Parameter 'peeraddr' in event NTP.32"
    ::= { ntpEventObjects32 2 }

ntp32_lihigh OBJECT-TYPE
    SYNTAX Integer32
    MAX-ACCESS accessible-for-notify
    STATUS current
    DESCRIPTION
        "Parameter 'lihigh' in event NTP.32"
    ::= { ntpEventObjects32 3 }

ntp32_lilow OBJECT-TYPE
    SYNTAX Integer32
    MAX-ACCESS accessible-for-notify
    STATUS current
    DESCRIPTION
        "Parameter 'lilow' in event NTP.32"
    ::= { ntpEventObjects32 4 }

ntp32_litxt OBJECT-TYPE
    SYNTAX DisplayString
    MAX-ACCESS accessible-for-notify
    STATUS current
    DESCRIPTION
        "Parameter 'litxt' in event NTP.32"
    ::= { ntpEventObjects32 5 }

ntp32_versionnum OBJECT-TYPE
    SYNTAX Integer32
    MAX-ACCESS accessible-for-notify
    STATUS current
    DESCRIPTION
        "Parameter 'versionnum' in event NTP.32"
    ::= { ntpEventObjects32 6 }

ntp32_mode OBJECT-TYPE
    SYNTAX Integer32
    MAX-ACCESS accessible-for-notify
    STATUS current
    DESCRIPTION
        "Parameter 'mode' in event NTP.32"
    ::= { ntpEventObjects32 7 }

ntp32_modetxt OBJECT-TYPE
    SYNTAX DisplayString
    MAX-ACCESS accessible-for-notify
    STATUS current
    DESCRIPTION
        "Parameter 'modetxt' in event NTP.32"
    ::= { ntpEventObjects32 8 }

ntp32_stratum OBJECT-TYPE
    SYNTAX Integer32
    MAX-ACCESS accessible-for-notify
    STATUS current
    DESCRIPTION
        "Parameter 'stratum' in event NTP.32"
    ::= { ntpEventObjects32 9 }

ntp32_poll OBJECT-TYPE
    SYNTAX Integer32
    MAX-ACCESS accessible-for-notify
    STATUS current
    DESCRIPTION
        "Parameter 'poll' in event NTP.32"
    ::= { ntpEventObjects32 10 }

ntp32_polltxt OBJECT-TYPE
    SYNTAX DisplayString
    MAX-ACCESS accessible-for-notify
    STATUS current
    DESCRIPTION
        "Parameter 'polltxt' in event NTP.32"
    ::= { ntpEventObjects32 11 }

ntp32_prec OBJECT-TYPE
    SYNTAX Integer32
    MAX-ACCESS accessible-for-notify
    STATUS current
    DESCRIPTION
        "Parameter 'prec' in event NTP.32"
    ::= { ntpEventObjects32 12 }

ntp32_prectxt OBJECT-TYPE
    SYNTAX DisplayString
    MAX-ACCESS accessible-for-notify
    STATUS current
    DESCRIPTION
        "Parameter 'prectxt' in event NTP.32"
    ::= { ntpEventObjects32 13 }

ntpEventObjects33 OBJECT-IDENTITY
    STATUS current
    DESCRIPTION
        "Event NTP.33
        An NTP packet is received or transmitted from or to the given host. Some
        message data is shown. More information is available in other events."
    ::= { ntpEventsGroup 33 }

ntp33_rxtx OBJECT-TYPE
    SYNTAX DisplayString
    MAX-ACCESS accessible-for-notify
    STATUS current
    DESCRIPTION
        "Parameter 'rxtx' in event NTP.33"
    ::= { ntpEventObjects33 1 }

ntp33_peeraddr OBJECT-TYPE
    SYNTAX IpAddress
    MAX-ACCESS accessible-for-notify
    STATUS current
    DESCRIPTION
        "Parameter 'peeraddr' in event NTP.33"
    ::= { ntpEventObjects33 2 }

ntp33_rootdelay OBJECT-TYPE
    SYNTAX DisplayString
    MAX-ACCESS accessible-for-notify
    STATUS current
    DESCRIPTION
        "Parameter 'rootdelay' in event NTP.33"
    ::= { ntpEventObjects33 3 }

ntp33_rootdispersion OBJECT-TYPE
    SYNTAX DisplayString
    MAX-ACCESS accessible-for-notify
    STATUS current
    DESCRIPTION
        "Parameter 'rootdispersion' in event NTP.33"
    ::= { ntpEventObjects33 4 }

ntp33_referenceid OBJECT-TYPE
    SYNTAX Integer32
    MAX-ACCESS accessible-for-notify
    STATUS current
    DESCRIPTION
        "Parameter 'referenceid' in event NTP.33"
    ::= { ntpEventObjects33 5 }

ntpEventObjects34 OBJECT-IDENTITY
    STATUS current
    DESCRIPTION
        "Event NTP.34
        An NTP packet is received or transmitted from or to the given host. Some
        message data is shown. More information is available in other events."
    ::= { ntpEventsGroup 34 }

ntp34_rxtx OBJECT-TYPE
    SYNTAX DisplayString
    MAX-ACCESS accessible-for-notify
    STATUS current
    DESCRIPTION
        "Parameter 'rxtx' in event NTP.34"
    ::= { ntpEventObjects34 1 }

ntp34_peeraddr OBJECT-TYPE
    SYNTAX IpAddress
    MAX-ACCESS accessible-for-notify
    STATUS current
    DESCRIPTION
        "Parameter 'peeraddr' in event NTP.34"
    ::= { ntpEventObjects34 2 }

ntp34_referencets OBJECT-TYPE
    SYNTAX DisplayString
    MAX-ACCESS accessible-for-notify
    STATUS current
    DESCRIPTION
        "Parameter 'referencets' in event NTP.34"
    ::= { ntpEventObjects34 3 }

ntpEventObjects35 OBJECT-IDENTITY
    STATUS current
    DESCRIPTION
        "Event NTP.35
        An NTP packet is received or transmitted from or to the given host. Some
        message data is shown. More information is available in other events."
    ::= { ntpEventsGroup 35 }

ntp35_rxtx OBJECT-TYPE
    SYNTAX DisplayString
    MAX-ACCESS accessible-for-notify
    STATUS current
    DESCRIPTION
        "Parameter 'rxtx' in event NTP.35"
    ::= { ntpEventObjects35 1 }

ntp35_peeraddr OBJECT-TYPE
    SYNTAX IpAddress
    MAX-ACCESS accessible-for-notify
    STATUS current
    DESCRIPTION
        "Parameter 'peeraddr' in event NTP.35"
    ::= { ntpEventObjects35 2 }

ntp35_originatets OBJECT-TYPE
    SYNTAX DisplayString
    MAX-ACCESS accessible-for-notify
    STATUS current
    DESCRIPTION
        "Parameter 'originatets' in event NTP.35"
    ::= { ntpEventObjects35 3 }

ntpEventObjects36 OBJECT-IDENTITY
    STATUS current
    DESCRIPTION
        "Event NTP.36
        An NTP packet is received or transmitted from or to the given host. Some
        message data is shown. More information is available in other events."
    ::= { ntpEventsGroup 36 }

ntp36_rxtx OBJECT-TYPE
    SYNTAX DisplayString
    MAX-ACCESS accessible-for-notify
    STATUS current
    DESCRIPTION
        "Parameter 'rxtx' in event NTP.36"
    ::= { ntpEventObjects36 1 }

ntp36_peeraddr OBJECT-TYPE
    SYNTAX IpAddress
    MAX-ACCESS accessible-for-notify
    STATUS current
    DESCRIPTION
        "Parameter 'peeraddr' in event NTP.36"
    ::= { ntpEventObjects36 2 }

ntp36_receivets OBJECT-TYPE
    SYNTAX DisplayString
    MAX-ACCESS accessible-for-notify
    STATUS current
    DESCRIPTION
        "Parameter 'receivets' in event NTP.36"
    ::= { ntpEventObjects36 3 }

ntpEventObjects37 OBJECT-IDENTITY
    STATUS current
    DESCRIPTION
        "Event NTP.37
        An NTP packet is received or transmitted from or to the given host. Some
        message data is shown. More information is available in other events."
    ::= { ntpEventsGroup 37 }

ntp37_rxtx OBJECT-TYPE
    SYNTAX DisplayString
    MAX-ACCESS accessible-for-notify
    STATUS current
    DESCRIPTION
        "Parameter 'rxtx' in event NTP.37"
    ::= { ntpEventObjects37 1 }

ntp37_peeraddr OBJECT-TYPE
    SYNTAX IpAddress
    MAX-ACCESS accessible-for-notify
    STATUS current
    DESCRIPTION
        "Parameter 'peeraddr' in event NTP.37"
    ::= { ntpEventObjects37 2 }

ntp37_transmitts OBJECT-TYPE
    SYNTAX DisplayString
    MAX-ACCESS accessible-for-notify
    STATUS current
    DESCRIPTION
        "Parameter 'transmitts' in event NTP.37"
    ::= { ntpEventObjects37 3 }


ntpNotification1 NOTIFICATION-TYPE
    OBJECTS { 
              ntp1_ntpsourceadd, 
              ntp1_refTime,
              ntp1_orgTime,
              ntp1_recvTime,
              ntp1_txTime 
            }
    STATUS current
    DESCRIPTION
        "Notification of Event NTP.1

        Message: 'possible NTP packet received from host $1 ref time $2 org time $3 recv time $4 tx time $5'

        Parameters list:
              $1: ntp1_ntpsourceadd
              $2: ntp1_refTime
              $3: ntp1_orgTime
              $4: ntp1_recvTime
              $5: ntp1_txTime

        This message is generated when a packet is received from port 123."
    ::= { ntpNotificationsPrefix 1 }

ntpNotification2 NOTIFICATION-TYPE
    OBJECTS { 
              ntp2_ntpdestadd, 
              ntp2_refTime,
              ntp2_orgTime,
              ntp2_recvTime,
              ntp2_txTime 
            }
    STATUS current
    DESCRIPTION
        "Notification of Event NTP.2

        Message: 'Sent NTP packet to host $1 ref time $2 org time $3 recv time $4 tx time $5'

        Parameters list:
              $1: ntp2_ntpdestadd
              $2: ntp2_refTime
              $3: ntp2_orgTime
              $4: ntp2_recvTime
              $5: ntp2_txTime

        This message is generated when a packet is sent to a remote host."
    ::= { ntpNotificationsPrefix 2 }

ntpNotification3 NOTIFICATION-TYPE
    OBJECTS { 
              ntp3_ntpsourceadd, 
              ntp3_errorcode 
            }
    STATUS current
    DESCRIPTION
        "Notification of Event NTP.3

        Message: 'Wrong NTP packet received from host $1 (Error Code = $2)'

        Parameters list:
              $1: ntp3_ntpsourceadd
              $2: ntp3_errorcode

        This message is generated after checking the input packet. Error codes
        are shown below:
        TEST1		0x0001		Duplicate packet received.
        TEST2		0x0002		Bogus packet received.
        TEST3		0x0004		Protocol unsynchronized.
        TEST4		0x0008		Peer delay/dispersion bounds check.
        TEST5		0x0010		Peer authentication failed.
        TEST6       0x0020		Peer clock unsynchronized.
        TEST7		0x0040		Peer stratum out of bounds.
        TEST8		0x0080		Root delay/dispersion bounds check."
    ::= { ntpNotificationsPrefix 3 }

ntpNotification4 NOTIFICATION-TYPE
    OBJECTS { 
              ntp4_versnumber, 
              ntp4_ntpsourceadd 
            }
    STATUS current
    DESCRIPTION
        "Notification of Event NTP.4

        Message: 'Packet with version not supported $1 from host $2'

        Parameters list:
              $1: ntp4_versnumber
              $2: ntp4_ntpsourceadd

        This message indicates a wrong NTP version."
    ::= { ntpNotificationsPrefix 4 }

ntpNotification5 NOTIFICATION-TYPE
    OBJECTS { 
              ntp5_ntpsourceadd 
            }
    STATUS current
    DESCRIPTION
        "Notification of Event NTP.5

        Message: 'control packet received from host $1'

        Parameters list:
              $1: ntp5_ntpsourceadd

        This message indicates the received packet is a control packet."
    ::= { ntpNotificationsPrefix 5 }

ntpNotification6 NOTIFICATION-TYPE
    OBJECTS { 
              ntp6_ntpsourceadd 
            }
    STATUS current
    DESCRIPTION
        "Notification of Event NTP.6

        Message: 'Broadcast packet received from host $1'

        Parameters list:
              $1: ntp6_ntpsourceadd

        This message indicates the received packet is a Broadcast packet."
    ::= { ntpNotificationsPrefix 6 }

ntpNotification7 NOTIFICATION-TYPE
    STATUS current
    DESCRIPTION
        "Notification of Event NTP.7

        Message: 'There is no free buffers to store packet'

        This message is generated when NTP protocol handler hasn't enough memory
        to store the packet."
    ::= { ntpNotificationsPrefix 7 }

ntpNotification8 NOTIFICATION-TYPE
    OBJECTS { 
              ntp8_ntpsourceadd 
            }
    STATUS current
    DESCRIPTION
        "Notification of Event NTP.8

        Message: 'Private packet received from host $1'

        Parameters list:
              $1: ntp8_ntpsourceadd

        This message indicates the received packet is private packet."
    ::= { ntpNotificationsPrefix 8 }

ntpNotification9 NOTIFICATION-TYPE
    OBJECTS { 
              ntp9_ntpsourceadd 
            }
    STATUS current
    DESCRIPTION
        "Notification of Event NTP.9

        Message: 'Client packet received from host $1'

        Parameters list:
              $1: ntp9_ntpsourceadd

        This message indicates the received packet is client packet."
    ::= { ntpNotificationsPrefix 9 }

ntpNotification10 NOTIFICATION-TYPE
    OBJECTS { 
              ntp10_ntpsourceadd 
            }
    STATUS current
    DESCRIPTION
        "Notification of Event NTP.10

        Message: 'NULL: packet from host $1 discarded'

        Parameters list:
              $1: ntp10_ntpsourceadd

        This message is generated by NTP Fake-Out routine."
    ::= { ntpNotificationsPrefix 10 }

ntpNotification11 NOTIFICATION-TYPE
    OBJECTS { 
              ntp11_ntpsourceadd 
            }
    STATUS current
    DESCRIPTION
        "Notification of Event NTP.11

        Message: 'NTP packet discarded from host $1 Cause: Unknown peer'

        Parameters list:
              $1: ntp11_ntpsourceadd

        This message is generated when a packet arrived from an unknown peer."
    ::= { ntpNotificationsPrefix 11 }

ntpNotification12 NOTIFICATION-TYPE
    OBJECTS { 
              ntp12_ntpsourceadd 
            }
    STATUS current
    DESCRIPTION
        "Notification of Event NTP.12

        Message: 'NTP Active mode Packet received from host $1'

        Parameters list:
              $1: ntp12_ntpsourceadd

        This message indicates the received packet is active mode packet."
    ::= { ntpNotificationsPrefix 12 }

ntpNotification13 NOTIFICATION-TYPE
    OBJECTS { 
              ntp13_ntpsourceadd 
            }
    STATUS current
    DESCRIPTION
        "Notification of Event NTP.13

        Message: 'NTP Passive mode Packet received from host $1'

        Parameters list:
              $1: ntp13_ntpsourceadd

        This message indicates the received packet is passive mode packet."
    ::= { ntpNotificationsPrefix 13 }

ntpNotification14 NOTIFICATION-TYPE
    OBJECTS { 
              ntp14_ntpsourceadd 
            }
    STATUS current
    DESCRIPTION
        "Notification of Event NTP.14

        Message: 'NTP Server mode Packet received from host $1'

        Parameters list:
              $1: ntp14_ntpsourceadd

        This message indicates the received packet is server mode packet."
    ::= { ntpNotificationsPrefix 14 }

ntpNotification15 NOTIFICATION-TYPE
    OBJECTS { 
              ntp15_Delay, 
              ntp15_OffsetSign,
              ntp15_OffsetSeconds,
              ntp15_OffsetMillSeconds 
            }
    STATUS current
    DESCRIPTION
        "Notification of Event NTP.15

        Message: 'Clock Update   Delay  $1 ms - Offset $2$3.$4 seconds'

        Parameters list:
              $1: ntp15_Delay
              $2: ntp15_OffsetSign
              $3: ntp15_OffsetSeconds
              $4: ntp15_OffsetMillSeconds

        This message is shown when a clock update has been done."
    ::= { ntpNotificationsPrefix 15 }

ntpNotification16 NOTIFICATION-TYPE
    OBJECTS { 
              ntp16_datetostab, 
              ntp16_stabdate 
            }
    STATUS current
    DESCRIPTION
        "Notification of Event NTP.16

        Message: 'Date to Stablish $1 Stablished Date $2'

        Parameters list:
              $1: ntp16_datetostab
              $2: ntp16_stabdate

        This message is shown when a date has been established."
    ::= { ntpNotificationsPrefix 16 }

ntpNotification17 NOTIFICATION-TYPE
    OBJECTS { 
              ntp17_secTimer 
            }
    STATUS current
    DESCRIPTION
        "Notification of Event NTP.17

        Message: 'Time since updating timer was thrown $1 ms'

        Parameters list:
              $1: ntp17_secTimer

        This is a debugging message used to know the time since the timer
        was thrown."
    ::= { ntpNotificationsPrefix 17 }

ntpNotification18 NOTIFICATION-TYPE
    OBJECTS { 
              ntp18_millisec 
            }
    STATUS current
    DESCRIPTION
        "Notification of Event NTP.18

        Message: 'Device Clock Milliseconds Value $1'

        Parameters list:
              $1: ntp18_millisec

        This message is used to know the clock precision."
    ::= { ntpNotificationsPrefix 18 }

ntpNotification19 NOTIFICATION-TYPE
    OBJECTS { 
              ntp19_datetime, 
              ntp19_millisec 
            }
    STATUS current
    DESCRIPTION
        "Notification of Event NTP.19

        Message: 'Device Exact Date/Time $1 $2'

        Parameters list:
              $1: ntp19_datetime
              $2: ntp19_millisec

        Device exact date and time."
    ::= { ntpNotificationsPrefix 19 }

ntpNotification20 NOTIFICATION-TYPE
    OBJECTS { 
              ntp20_ntpsourceadd 
            }
    STATUS current
    DESCRIPTION
        "Notification of Event NTP.20

        Message: 'NTP client doesn't accept NTP Broadcasts from host $1'

        Parameters list:
              $1: ntp20_ntpsourceadd

        This message is generated when NTP client doesn't accept
        NTP broadcast messages from packet source host."
    ::= { ntpNotificationsPrefix 20 }

ntpNotification21 NOTIFICATION-TYPE
    OBJECTS { 
              ntp21_datetime, 
              ntp21_millisec,
              ntp21_timeticks 
            }
    STATUS current
    DESCRIPTION
        "Notification of Event NTP.21

        Message: 'NTP Transmission Date/Time  $1 $2 ms $3 ticks'

        Parameters list:
              $1: ntp21_datetime
              $2: ntp21_millisec
              $3: ntp21_timeticks

        NTP transmission date/time."
    ::= { ntpNotificationsPrefix 21 }

ntpNotification22 NOTIFICATION-TYPE
    OBJECTS { 
              ntp22_datetime, 
              ntp22_millisec,
              ntp22_timeticks 
            }
    STATUS current
    DESCRIPTION
        "Notification of Event NTP.22

        Message: 'NTP Reception Date/Time  $1 $2 ms $3 ticks'

        Parameters list:
              $1: ntp22_datetime
              $2: ntp22_millisec
              $3: ntp22_timeticks

        NTP reception date/time."
    ::= { ntpNotificationsPrefix 22 }

ntpNotification23 NOTIFICATION-TYPE
    STATUS current
    DESCRIPTION
        "Notification of Event NTP.23

        Message: 'Clt NTP Stopped- Skew Time too large'

        Clt NTP Stopped- Skew Time too large."
    ::= { ntpNotificationsPrefix 23 }

ntpNotification24 NOTIFICATION-TYPE
    OBJECTS { 
              ntp24_ntpsourceadd 
            }
    STATUS current
    DESCRIPTION
        "Notification of Event NTP.24

        Message: 'Discarded NTP packet from host $1 Stopped NTP Client'

        Parameters list:
              $1: ntp24_ntpsourceadd

        NTP packets are discarded because NTP client is stopped."
    ::= { ntpNotificationsPrefix 24 }

ntpNotification25 NOTIFICATION-TYPE
    STATUS current
    DESCRIPTION
        "Notification of Event NTP.25

        Message: 'NTP Client stopped : IP not enabled'

        NTP Client stopped while IP disabled."
    ::= { ntpNotificationsPrefix 25 }

ntpNotification26 NOTIFICATION-TYPE
    OBJECTS { 
              ntp26_ntpsourceadd 
            }
    STATUS current
    DESCRIPTION
        "Notification of Event NTP.26

        Message: 'NTP packet discarded from host $1 Cause: local packet'

        Parameters list:
              $1: ntp26_ntpsourceadd

        This message is generated when a local packet arrived. NTP only accepts
        packets from other hosts."
    ::= { ntpNotificationsPrefix 26 }

ntpNotification27 NOTIFICATION-TYPE
    OBJECTS { 
              ntp27_ntpsourceadd, 
              ntp27_testnumber,
              ntp27_testerrorcode,
              ntp27_testdescription 
            }
    STATUS current
    DESCRIPTION
        "Notification of Event NTP.27

        Message: 'Wrong NTP packet received from host $1, failed test $2 code $3: $4'

        Parameters list:
              $1: ntp27_ntpsourceadd
              $2: ntp27_testnumber
              $3: ntp27_testerrorcode
              $4: ntp27_testdescription

        A NTP packet has been received from the specified host, but it was wrong
        because it failed the specidifed test (number, error code and
        description)."
    ::= { ntpNotificationsPrefix 27 }

ntpNotification28 NOTIFICATION-TYPE
    OBJECTS { 
              ntp28_ntpsourceadd, 
              ntp28_delay,
              ntp28_offset,
              ntp28_dispersion 
            }
    STATUS current
    DESCRIPTION
        "Notification of Event NTP.28

        Message: 'NTP host $1 clock filter: new delay $2, offset $3, dispersion $4'

        Parameters list:
              $1: ntp28_ntpsourceadd
              $2: ntp28_delay
              $3: ntp28_offset
              $4: ntp28_dispersion

        NTP peer host clock data has been updated by the clock-filter prodedure,
        producing new values for delay, offset and dispersion, as shown in the
        trace."
    ::= { ntpNotificationsPrefix 28 }

ntpNotification29 NOTIFICATION-TYPE
    OBJECTS { 
              ntp29_ntpsourceadd, 
              ntp29_discardcause 
            }
    STATUS current
    DESCRIPTION
        "Notification of Event NTP.29

        Message: 'NTP host $1 clock selection discarded: $2'

        Parameters list:
              $1: ntp29_ntpsourceadd
              $2: ntp29_discardcause

        NTP peer host clock data has been discarded by the clock-selection
        prodedure, and the cause is shown."
    ::= { ntpNotificationsPrefix 29 }

ntpNotification30 NOTIFICATION-TYPE
    OBJECTS { 
              ntp30_ntpsourceadd 
            }
    STATUS current
    DESCRIPTION
        "Notification of Event NTP.30

        Message: 'NTP host $1 clock selected'

        Parameters list:
              $1: ntp30_ntpsourceadd

        NTP peer host clock data has been selected by the clock-selection
        prodedure."
    ::= { ntpNotificationsPrefix 30 }

ntpNotification31 NOTIFICATION-TYPE
    STATUS current
    DESCRIPTION
        "Notification of Event NTP.31

        Message: 'NTP no host selected'

        NTP clock-selection prodedure has found no suitable time server from any
        known host."
    ::= { ntpNotificationsPrefix 31 }

ntpNotification32 NOTIFICATION-TYPE
    OBJECTS { 
              ntp32_rxtx, 
              ntp32_peeraddr,
              ntp32_lihigh,
              ntp32_lilow,
              ntp32_litxt,
              ntp32_versionnum,
              ntp32_mode,
              ntp32_modetxt,
              ntp32_stratum,
              ntp32_poll,
              ntp32_polltxt,
              ntp32_prec,
              ntp32_prectxt 
            }
    STATUS current
    DESCRIPTION
        "Notification of Event NTP.32

        Message: '$1 host $2: LI $3$4 ($5) VN $6 Mode $7 ($8), Stratum $9, Poll Interval $10 ($11), Precision $12 ($13)'

        Parameters list:
              $1: ntp32_rxtx
              $2: ntp32_peeraddr
              $3: ntp32_lihigh
              $4: ntp32_lilow
              $5: ntp32_litxt
              $6: ntp32_versionnum
              $7: ntp32_mode
              $8: ntp32_modetxt
              $9: ntp32_stratum
              $10: ntp32_poll
              $11: ntp32_polltxt
              $12: ntp32_prec
              $13: ntp32_prectxt

        An NTP packet is received or transmitted from or to the given host. Some
        message data is shown. More information is available in other events."
    ::= { ntpNotificationsPrefix 32 }

ntpNotification33 NOTIFICATION-TYPE
    OBJECTS { 
              ntp33_rxtx, 
              ntp33_peeraddr,
              ntp33_rootdelay,
              ntp33_rootdispersion,
              ntp33_referenceid 
            }
    STATUS current
    DESCRIPTION
        "Notification of Event NTP.33

        Message: '$1 host $2: Root Delay $3, Root Dispersion $4, Reference Identifier $5'

        Parameters list:
              $1: ntp33_rxtx
              $2: ntp33_peeraddr
              $3: ntp33_rootdelay
              $4: ntp33_rootdispersion
              $5: ntp33_referenceid

        An NTP packet is received or transmitted from or to the given host. Some
        message data is shown. More information is available in other events."
    ::= { ntpNotificationsPrefix 33 }

ntpNotification34 NOTIFICATION-TYPE
    OBJECTS { 
              ntp34_rxtx, 
              ntp34_peeraddr,
              ntp34_referencets 
            }
    STATUS current
    DESCRIPTION
        "Notification of Event NTP.34

        Message: '$1 host $2: Reference Timestamp $3'

        Parameters list:
              $1: ntp34_rxtx
              $2: ntp34_peeraddr
              $3: ntp34_referencets

        An NTP packet is received or transmitted from or to the given host. Some
        message data is shown. More information is available in other events."
    ::= { ntpNotificationsPrefix 34 }

ntpNotification35 NOTIFICATION-TYPE
    OBJECTS { 
              ntp35_rxtx, 
              ntp35_peeraddr,
              ntp35_originatets 
            }
    STATUS current
    DESCRIPTION
        "Notification of Event NTP.35

        Message: '$1 host $2: Originate Timestamp $3'

        Parameters list:
              $1: ntp35_rxtx
              $2: ntp35_peeraddr
              $3: ntp35_originatets

        An NTP packet is received or transmitted from or to the given host. Some
        message data is shown. More information is available in other events."
    ::= { ntpNotificationsPrefix 35 }

ntpNotification36 NOTIFICATION-TYPE
    OBJECTS { 
              ntp36_rxtx, 
              ntp36_peeraddr,
              ntp36_receivets 
            }
    STATUS current
    DESCRIPTION
        "Notification of Event NTP.36

        Message: '$1 host $2: Receive Timestamp $3'

        Parameters list:
              $1: ntp36_rxtx
              $2: ntp36_peeraddr
              $3: ntp36_receivets

        An NTP packet is received or transmitted from or to the given host. Some
        message data is shown. More information is available in other events."
    ::= { ntpNotificationsPrefix 36 }

ntpNotification37 NOTIFICATION-TYPE
    OBJECTS { 
              ntp37_rxtx, 
              ntp37_peeraddr,
              ntp37_transmitts 
            }
    STATUS current
    DESCRIPTION
        "Notification of Event NTP.37

        Message: '$1 host $2: Transmit Timestamp $3'

        Parameters list:
              $1: ntp37_rxtx
              $2: ntp37_peeraddr
              $3: ntp37_transmitts

        An NTP packet is received or transmitted from or to the given host. Some
        message data is shown. More information is available in other events."
    ::= { ntpNotificationsPrefix 37 }


END
