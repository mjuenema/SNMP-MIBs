-- file automatically created


TELDAT-TRAP-NOE-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


noeTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the NOE event subsystem."
    REVISION "201401200930Z"
    DESCRIPTION "Initial implementation"
        ::= { telEventTraps 198 }


noeEventsGroup	OBJECT IDENTIFIER	::= { noeTrapsMIB 1 }

noeNotifications	OBJECT IDENTIFIER	::= { noeTrapsMIB 2 }
noeNotificationsPrefix	OBJECT IDENTIFIER	::= { noeNotifications 0 }

noeEventObjects1 OBJECT-IDENTITY
    STATUS current
    DESCRIPTION
        "Event NOE.1
        NOE Application error."
    ::= { noeEventsGroup 1 }

noe1_error OBJECT-TYPE
    SYNTAX DisplayString
    MAX-ACCESS accessible-for-notify
    STATUS current
    DESCRIPTION
        "Parameter 'error' in event NOE.1"
    ::= { noeEventObjects1 1 }

noe1_connetion-id OBJECT-TYPE
    SYNTAX Integer32
    MAX-ACCESS accessible-for-notify
    STATUS current
    DESCRIPTION
        "Parameter 'connetion-id' in event NOE.1"
    ::= { noeEventObjects1 2 }

noeEventObjects2 OBJECT-IDENTITY
    STATUS current
    DESCRIPTION
        "Event NOE.2
        NOE Application information."
    ::= { noeEventsGroup 2 }

noe2_info OBJECT-TYPE
    SYNTAX DisplayString
    MAX-ACCESS accessible-for-notify
    STATUS current
    DESCRIPTION
        "Parameter 'info' in event NOE.2"
    ::= { noeEventObjects2 1 }

noe2_connetion-id OBJECT-TYPE
    SYNTAX Integer32
    MAX-ACCESS accessible-for-notify
    STATUS current
    DESCRIPTION
        "Parameter 'connetion-id' in event NOE.2"
    ::= { noeEventObjects2 2 }

noeEventObjects3 OBJECT-IDENTITY
    STATUS current
    DESCRIPTION
        "Event NOE.3
        NOE Application warning."
    ::= { noeEventsGroup 3 }

noe3_warning OBJECT-TYPE
    SYNTAX DisplayString
    MAX-ACCESS accessible-for-notify
    STATUS current
    DESCRIPTION
        "Parameter 'warning' in event NOE.3"
    ::= { noeEventObjects3 1 }

noe3_connetion-id OBJECT-TYPE
    SYNTAX Integer32
    MAX-ACCESS accessible-for-notify
    STATUS current
    DESCRIPTION
        "Parameter 'connetion-id' in event NOE.3"
    ::= { noeEventObjects3 2 }

noeEventObjects4 OBJECT-IDENTITY
    STATUS current
    DESCRIPTION
        "Event NOE.4
        Terminal connection event."
    ::= { noeEventsGroup 4 }

noe4_event OBJECT-TYPE
    SYNTAX DisplayString
    MAX-ACCESS accessible-for-notify
    STATUS current
    DESCRIPTION
        "Parameter 'event' in event NOE.4"
    ::= { noeEventObjects4 1 }

noe4_description OBJECT-TYPE
    SYNTAX DisplayString
    MAX-ACCESS accessible-for-notify
    STATUS current
    DESCRIPTION
        "Parameter 'description' in event NOE.4"
    ::= { noeEventObjects4 2 }

noe4_connetion-id OBJECT-TYPE
    SYNTAX Integer32
    MAX-ACCESS accessible-for-notify
    STATUS current
    DESCRIPTION
        "Parameter 'connetion-id' in event NOE.4"
    ::= { noeEventObjects4 3 }

noeEventObjects5 OBJECT-IDENTITY
    STATUS current
    DESCRIPTION
        "Event NOE.5
        Event related with application state."
    ::= { noeEventsGroup 5 }

noe5_state OBJECT-TYPE
    SYNTAX DisplayString
    MAX-ACCESS accessible-for-notify
    STATUS current
    DESCRIPTION
        "Parameter 'state' in event NOE.5"
    ::= { noeEventObjects5 1 }

noeEventObjects6 OBJECT-IDENTITY
    STATUS current
    DESCRIPTION
        "Event NOE.6
        UAUDP data message received with sequences <expected-seq> and <sent-seq>
        content size <size> in connection <connection-id>"
    ::= { noeEventsGroup 6 }

noe6_expected-seq OBJECT-TYPE
    SYNTAX Integer32
    MAX-ACCESS accessible-for-notify
    STATUS current
    DESCRIPTION
        "Parameter 'expected-seq' in event NOE.6"
    ::= { noeEventObjects6 1 }

noe6_sent-seq OBJECT-TYPE
    SYNTAX Integer32
    MAX-ACCESS accessible-for-notify
    STATUS current
    DESCRIPTION
        "Parameter 'sent-seq' in event NOE.6"
    ::= { noeEventObjects6 2 }

noe6_size OBJECT-TYPE
    SYNTAX Integer32
    MAX-ACCESS accessible-for-notify
    STATUS current
    DESCRIPTION
        "Parameter 'size' in event NOE.6"
    ::= { noeEventObjects6 3 }

noe6_connection-id OBJECT-TYPE
    SYNTAX Integer32
    MAX-ACCESS accessible-for-notify
    STATUS current
    DESCRIPTION
        "Parameter 'connection-id' in event NOE.6"
    ::= { noeEventObjects6 4 }

noe6_contents OBJECT-TYPE
    SYNTAX DisplayString
    MAX-ACCESS accessible-for-notify
    STATUS current
    DESCRIPTION
        "Parameter 'contents' in event NOE.6"
    ::= { noeEventObjects6 5 }

noeEventObjects7 OBJECT-IDENTITY
    STATUS current
    DESCRIPTION
        "Event NOE.7
        UAUDP NACK message received with expected sequence <expected-seq> in 
        connection <connection-id>"
    ::= { noeEventsGroup 7 }

noe7_expected-seq OBJECT-TYPE
    SYNTAX Integer32
    MAX-ACCESS accessible-for-notify
    STATUS current
    DESCRIPTION
        "Parameter 'expected-seq' in event NOE.7"
    ::= { noeEventObjects7 1 }

noe7_connection-id OBJECT-TYPE
    SYNTAX Integer32
    MAX-ACCESS accessible-for-notify
    STATUS current
    DESCRIPTION
        "Parameter 'connection-id' in event NOE.7"
    ::= { noeEventObjects7 2 }

noeEventObjects8 OBJECT-IDENTITY
    STATUS current
    DESCRIPTION
        "Event NOE.8
        UAUDP KEEPALIVEACK message received in connetion-id."
    ::= { noeEventsGroup 8 }

noe8_connection-id OBJECT-TYPE
    SYNTAX Integer32
    MAX-ACCESS accessible-for-notify
    STATUS current
    DESCRIPTION
        "Parameter 'connection-id' in event NOE.8"
    ::= { noeEventObjects8 1 }

noeEventObjects9 OBJECT-IDENTITY
    STATUS current
    DESCRIPTION
        "Event NOE.9
        UAUDP RELEASE message received in connetion-id."
    ::= { noeEventsGroup 9 }

noe9_connection-id OBJECT-TYPE
    SYNTAX Integer32
    MAX-ACCESS accessible-for-notify
    STATUS current
    DESCRIPTION
        "Parameter 'connection-id' in event NOE.9"
    ::= { noeEventObjects9 1 }

noeEventObjects10 OBJECT-IDENTITY
    STATUS current
    DESCRIPTION
        "Event NOE.10
        UAUDP RELEASE message received in connetion-id."
    ::= { noeEventsGroup 10 }

noe10_connection-id OBJECT-TYPE
    SYNTAX Integer32
    MAX-ACCESS accessible-for-notify
    STATUS current
    DESCRIPTION
        "Parameter 'connection-id' in event NOE.10"
    ::= { noeEventObjects10 1 }

noeEventObjects11 OBJECT-IDENTITY
    STATUS current
    DESCRIPTION
        "Event NOE.11
        UAUDP UNKNOWN message with size received in connetion-id."
    ::= { noeEventsGroup 11 }

noe11_size OBJECT-TYPE
    SYNTAX Integer32
    MAX-ACCESS accessible-for-notify
    STATUS current
    DESCRIPTION
        "Parameter 'size' in event NOE.11"
    ::= { noeEventObjects11 1 }

noe11_connection-id OBJECT-TYPE
    SYNTAX Integer32
    MAX-ACCESS accessible-for-notify
    STATUS current
    DESCRIPTION
        "Parameter 'connection-id' in event NOE.11"
    ::= { noeEventObjects11 2 }

noe11_contents OBJECT-TYPE
    SYNTAX DisplayString
    MAX-ACCESS accessible-for-notify
    STATUS current
    DESCRIPTION
        "Parameter 'contents' in event NOE.11"
    ::= { noeEventObjects11 3 }

noeEventObjects12 OBJECT-IDENTITY
    STATUS current
    DESCRIPTION
        "Event NOE.12
        UAUDP data message sent with sequences <expected-seq> and <sent-seq>
        content size <size> in connection <connection-id>"
    ::= { noeEventsGroup 12 }

noe12_expected-seq OBJECT-TYPE
    SYNTAX Integer32
    MAX-ACCESS accessible-for-notify
    STATUS current
    DESCRIPTION
        "Parameter 'expected-seq' in event NOE.12"
    ::= { noeEventObjects12 1 }

noe12_sent-seq OBJECT-TYPE
    SYNTAX Integer32
    MAX-ACCESS accessible-for-notify
    STATUS current
    DESCRIPTION
        "Parameter 'sent-seq' in event NOE.12"
    ::= { noeEventObjects12 2 }

noe12_size OBJECT-TYPE
    SYNTAX Integer32
    MAX-ACCESS accessible-for-notify
    STATUS current
    DESCRIPTION
        "Parameter 'size' in event NOE.12"
    ::= { noeEventObjects12 3 }

noe12_connection-id OBJECT-TYPE
    SYNTAX Integer32
    MAX-ACCESS accessible-for-notify
    STATUS current
    DESCRIPTION
        "Parameter 'connection-id' in event NOE.12"
    ::= { noeEventObjects12 4 }

noe12_contents OBJECT-TYPE
    SYNTAX DisplayString
    MAX-ACCESS accessible-for-notify
    STATUS current
    DESCRIPTION
        "Parameter 'contents' in event NOE.12"
    ::= { noeEventObjects12 5 }

noeEventObjects13 OBJECT-IDENTITY
    STATUS current
    DESCRIPTION
        "Event NOE.13
        UAUDP NACK message sent with expected sequence <expected-seq> in 
        connection <connection-id>"
    ::= { noeEventsGroup 13 }

noe13_expected-seq OBJECT-TYPE
    SYNTAX Integer32
    MAX-ACCESS accessible-for-notify
    STATUS current
    DESCRIPTION
        "Parameter 'expected-seq' in event NOE.13"
    ::= { noeEventObjects13 1 }

noe13_connection-id OBJECT-TYPE
    SYNTAX Integer32
    MAX-ACCESS accessible-for-notify
    STATUS current
    DESCRIPTION
        "Parameter 'connection-id' in event NOE.13"
    ::= { noeEventObjects13 2 }

noeEventObjects14 OBJECT-IDENTITY
    STATUS current
    DESCRIPTION
        "Event NOE.14
        UAUDP KEEPALIVE message sent in connetion-id."
    ::= { noeEventsGroup 14 }

noe14_connection-id OBJECT-TYPE
    SYNTAX Integer32
    MAX-ACCESS accessible-for-notify
    STATUS current
    DESCRIPTION
        "Parameter 'connection-id' in event NOE.14"
    ::= { noeEventObjects14 1 }

noeEventObjects15 OBJECT-IDENTITY
    STATUS current
    DESCRIPTION
        "Event NOE.15
        UAUDP RELEASEACK message sent in connetion-id."
    ::= { noeEventsGroup 15 }

noe15_connection-id OBJECT-TYPE
    SYNTAX Integer32
    MAX-ACCESS accessible-for-notify
    STATUS current
    DESCRIPTION
        "Parameter 'connection-id' in event NOE.15"
    ::= { noeEventObjects15 1 }

noeEventObjects16 OBJECT-IDENTITY
    STATUS current
    DESCRIPTION
        "Event NOE.16
        UAUDP message with size forwarded in connetion-id with contents. 
        Direction In (towards CS) or Out (towards terminal)"
    ::= { noeEventsGroup 16 }

noe16_direction OBJECT-TYPE
    SYNTAX DisplayString
    MAX-ACCESS accessible-for-notify
    STATUS current
    DESCRIPTION
        "Parameter 'direction' in event NOE.16"
    ::= { noeEventObjects16 1 }

noe16_size OBJECT-TYPE
    SYNTAX Integer32
    MAX-ACCESS accessible-for-notify
    STATUS current
    DESCRIPTION
        "Parameter 'size' in event NOE.16"
    ::= { noeEventObjects16 2 }

noe16_connection-id OBJECT-TYPE
    SYNTAX Integer32
    MAX-ACCESS accessible-for-notify
    STATUS current
    DESCRIPTION
        "Parameter 'connection-id' in event NOE.16"
    ::= { noeEventObjects16 3 }

noe16_contents OBJECT-TYPE
    SYNTAX DisplayString
    MAX-ACCESS accessible-for-notify
    STATUS current
    DESCRIPTION
        "Parameter 'contents' in event NOE.16"
    ::= { noeEventObjects16 4 }

noeEventObjects17 OBJECT-IDENTITY
    STATUS current
    DESCRIPTION
        "Event NOE.17
        UAUDP message from Call Server dropped in connetion-id."
    ::= { noeEventsGroup 17 }

noe17_connection-id OBJECT-TYPE
    SYNTAX Integer32
    MAX-ACCESS accessible-for-notify
    STATUS current
    DESCRIPTION
        "Parameter 'connection-id' in event NOE.17"
    ::= { noeEventObjects17 1 }

noeEventObjects18 OBJECT-IDENTITY
    STATUS current
    DESCRIPTION
        "Event NOE.18
        New event in noe terminal"
    ::= { noeEventsGroup 18 }

noe18_event OBJECT-TYPE
    SYNTAX DisplayString
    MAX-ACCESS accessible-for-notify
    STATUS current
    DESCRIPTION
        "Parameter 'event' in event NOE.18"
    ::= { noeEventObjects18 1 }

noe18_old_state OBJECT-TYPE
    SYNTAX DisplayString
    MAX-ACCESS accessible-for-notify
    STATUS current
    DESCRIPTION
        "Parameter 'old_state' in event NOE.18"
    ::= { noeEventObjects18 2 }

noe18_new_state OBJECT-TYPE
    SYNTAX DisplayString
    MAX-ACCESS accessible-for-notify
    STATUS current
    DESCRIPTION
        "Parameter 'new_state' in event NOE.18"
    ::= { noeEventObjects18 3 }

noe18_cdr OBJECT-TYPE
    SYNTAX Integer32
    MAX-ACCESS accessible-for-notify
    STATUS current
    DESCRIPTION
        "Parameter 'cdr' in event NOE.18"
    ::= { noeEventObjects18 4 }

noe18_connection-id OBJECT-TYPE
    SYNTAX Integer32
    MAX-ACCESS accessible-for-notify
    STATUS current
    DESCRIPTION
        "Parameter 'connection-id' in event NOE.18"
    ::= { noeEventObjects18 5 }

noeEventObjects19 OBJECT-IDENTITY
    STATUS current
    DESCRIPTION
        "Event NOE.19
        UAUDP RELEASE message sent in connetion-id."
    ::= { noeEventsGroup 19 }

noe19_connection-id OBJECT-TYPE
    SYNTAX Integer32
    MAX-ACCESS accessible-for-notify
    STATUS current
    DESCRIPTION
        "Parameter 'connection-id' in event NOE.19"
    ::= { noeEventObjects19 1 }

noeEventObjects20 OBJECT-IDENTITY
    STATUS current
    DESCRIPTION
        "Event NOE.20
        NOE Application trace."
    ::= { noeEventsGroup 20 }

noe20_trace OBJECT-TYPE
    SYNTAX DisplayString
    MAX-ACCESS accessible-for-notify
    STATUS current
    DESCRIPTION
        "Parameter 'trace' in event NOE.20"
    ::= { noeEventObjects20 1 }

noe20_connetion-id OBJECT-TYPE
    SYNTAX Integer32
    MAX-ACCESS accessible-for-notify
    STATUS current
    DESCRIPTION
        "Parameter 'connetion-id' in event NOE.20"
    ::= { noeEventObjects20 2 }

noeEventObjects21 OBJECT-IDENTITY
    STATUS current
    DESCRIPTION
        "Event NOE.21
        UAUDP CONNECT message received in connetion-id."
    ::= { noeEventsGroup 21 }

noe21_size OBJECT-TYPE
    SYNTAX Integer32
    MAX-ACCESS accessible-for-notify
    STATUS current
    DESCRIPTION
        "Parameter 'size' in event NOE.21"
    ::= { noeEventObjects21 1 }

noe21_connection-id OBJECT-TYPE
    SYNTAX Integer32
    MAX-ACCESS accessible-for-notify
    STATUS current
    DESCRIPTION
        "Parameter 'connection-id' in event NOE.21"
    ::= { noeEventObjects21 2 }

noe21_contents OBJECT-TYPE
    SYNTAX DisplayString
    MAX-ACCESS accessible-for-notify
    STATUS current
    DESCRIPTION
        "Parameter 'contents' in event NOE.21"
    ::= { noeEventObjects21 3 }

noeEventObjects22 OBJECT-IDENTITY
    STATUS current
    DESCRIPTION
        "Event NOE.22
        UAUDP CONNECTACK message received in connetion-id."
    ::= { noeEventsGroup 22 }

noe22_connection-id OBJECT-TYPE
    SYNTAX Integer32
    MAX-ACCESS accessible-for-notify
    STATUS current
    DESCRIPTION
        "Parameter 'connection-id' in event NOE.22"
    ::= { noeEventObjects22 1 }

noeEventObjects23 OBJECT-IDENTITY
    STATUS current
    DESCRIPTION
        "Event NOE.23
        UAUDP CONNECT message sent in connetion-id."
    ::= { noeEventsGroup 23 }

noe23_size OBJECT-TYPE
    SYNTAX Integer32
    MAX-ACCESS accessible-for-notify
    STATUS current
    DESCRIPTION
        "Parameter 'size' in event NOE.23"
    ::= { noeEventObjects23 1 }

noe23_connection-id OBJECT-TYPE
    SYNTAX Integer32
    MAX-ACCESS accessible-for-notify
    STATUS current
    DESCRIPTION
        "Parameter 'connection-id' in event NOE.23"
    ::= { noeEventObjects23 2 }

noe23_contents OBJECT-TYPE
    SYNTAX DisplayString
    MAX-ACCESS accessible-for-notify
    STATUS current
    DESCRIPTION
        "Parameter 'contents' in event NOE.23"
    ::= { noeEventObjects23 3 }

noeEventObjects24 OBJECT-IDENTITY
    STATUS current
    DESCRIPTION
        "Event NOE.24
        UAUDP CONNECTACK message sent in connetion-id."
    ::= { noeEventsGroup 24 }

noe24_connection-id OBJECT-TYPE
    SYNTAX Integer32
    MAX-ACCESS accessible-for-notify
    STATUS current
    DESCRIPTION
        "Parameter 'connection-id' in event NOE.24"
    ::= { noeEventObjects24 1 }


noeNotification1 NOTIFICATION-TYPE
    OBJECTS { 
              noe1_error, 
              noe1_connetion-id 
            }
    STATUS current
    DESCRIPTION
        "Notification of Event NOE.1

        Message: 'Noe App error: $1. Id $2'

        Parameters list:
              $1: noe1_error
              $2: noe1_connetion-id

        NOE Application error."
    ::= { noeNotificationsPrefix 1 }

noeNotification2 NOTIFICATION-TYPE
    OBJECTS { 
              noe2_info, 
              noe2_connetion-id 
            }
    STATUS current
    DESCRIPTION
        "Notification of Event NOE.2

        Message: 'Noe App info: $1. Id $2'

        Parameters list:
              $1: noe2_info
              $2: noe2_connetion-id

        NOE Application information."
    ::= { noeNotificationsPrefix 2 }

noeNotification3 NOTIFICATION-TYPE
    OBJECTS { 
              noe3_warning, 
              noe3_connetion-id 
            }
    STATUS current
    DESCRIPTION
        "Notification of Event NOE.3

        Message: 'Noe App warning: $1. Id $2'

        Parameters list:
              $1: noe3_warning
              $2: noe3_connetion-id

        NOE Application warning."
    ::= { noeNotificationsPrefix 3 }

noeNotification4 NOTIFICATION-TYPE
    OBJECTS { 
              noe4_event, 
              noe4_description,
              noe4_connetion-id 
            }
    STATUS current
    DESCRIPTION
        "Notification of Event NOE.4

        Message: 'Terminal: $1 $2. Id $3'

        Parameters list:
              $1: noe4_event
              $2: noe4_description
              $3: noe4_connetion-id

        Terminal connection event."
    ::= { noeNotificationsPrefix 4 }

noeNotification5 NOTIFICATION-TYPE
    OBJECTS { 
              noe5_state 
            }
    STATUS current
    DESCRIPTION
        "Notification of Event NOE.5

        Message: 'Noe App state: $1'

        Parameters list:
              $1: noe5_state

        Event related with application state."
    ::= { noeNotificationsPrefix 5 }

noeNotification6 NOTIFICATION-TYPE
    OBJECTS { 
              noe6_expected-seq, 
              noe6_sent-seq,
              noe6_size,
              noe6_connection-id,
              noe6_contents 
            }
    STATUS current
    DESCRIPTION
        "Notification of Event NOE.6

        Message: 'Rx DATA, exp $1, sent $2, size $3, Id $4: $5'

        Parameters list:
              $1: noe6_expected-seq
              $2: noe6_sent-seq
              $3: noe6_size
              $4: noe6_connection-id
              $5: noe6_contents

        UAUDP data message received with sequences <expected-seq> and <sent-seq>
        content size <size> in connection <connection-id>"
    ::= { noeNotificationsPrefix 6 }

noeNotification7 NOTIFICATION-TYPE
    OBJECTS { 
              noe7_expected-seq, 
              noe7_connection-id 
            }
    STATUS current
    DESCRIPTION
        "Notification of Event NOE.7

        Message: 'Rx NACK, exp $1, Id $2'

        Parameters list:
              $1: noe7_expected-seq
              $2: noe7_connection-id

        UAUDP NACK message received with expected sequence <expected-seq> in 
        connection <connection-id>"
    ::= { noeNotificationsPrefix 7 }

noeNotification8 NOTIFICATION-TYPE
    OBJECTS { 
              noe8_connection-id 
            }
    STATUS current
    DESCRIPTION
        "Notification of Event NOE.8

        Message: 'Rx KEEPALIVEACK, Id $1'

        Parameters list:
              $1: noe8_connection-id

        UAUDP KEEPALIVEACK message received in connetion-id."
    ::= { noeNotificationsPrefix 8 }

noeNotification9 NOTIFICATION-TYPE
    OBJECTS { 
              noe9_connection-id 
            }
    STATUS current
    DESCRIPTION
        "Notification of Event NOE.9

        Message: 'Rx RELEASE, Id $1'

        Parameters list:
              $1: noe9_connection-id

        UAUDP RELEASE message received in connetion-id."
    ::= { noeNotificationsPrefix 9 }

noeNotification10 NOTIFICATION-TYPE
    OBJECTS { 
              noe10_connection-id 
            }
    STATUS current
    DESCRIPTION
        "Notification of Event NOE.10

        Message: 'Rx RELEASEACK, Id $1'

        Parameters list:
              $1: noe10_connection-id

        UAUDP RELEASE message received in connetion-id."
    ::= { noeNotificationsPrefix 10 }

noeNotification11 NOTIFICATION-TYPE
    OBJECTS { 
              noe11_size, 
              noe11_connection-id,
              noe11_contents 
            }
    STATUS current
    DESCRIPTION
        "Notification of Event NOE.11

        Message: 'Rx UNKNOWN, size $1, Id $2: $3'

        Parameters list:
              $1: noe11_size
              $2: noe11_connection-id
              $3: noe11_contents

        UAUDP UNKNOWN message with size received in connetion-id."
    ::= { noeNotificationsPrefix 11 }

noeNotification12 NOTIFICATION-TYPE
    OBJECTS { 
              noe12_expected-seq, 
              noe12_sent-seq,
              noe12_size,
              noe12_connection-id,
              noe12_contents 
            }
    STATUS current
    DESCRIPTION
        "Notification of Event NOE.12

        Message: 'Tx DATA, exp $1, sent $2, size $3, Id $4: $5'

        Parameters list:
              $1: noe12_expected-seq
              $2: noe12_sent-seq
              $3: noe12_size
              $4: noe12_connection-id
              $5: noe12_contents

        UAUDP data message sent with sequences <expected-seq> and <sent-seq>
        content size <size> in connection <connection-id>"
    ::= { noeNotificationsPrefix 12 }

noeNotification13 NOTIFICATION-TYPE
    OBJECTS { 
              noe13_expected-seq, 
              noe13_connection-id 
            }
    STATUS current
    DESCRIPTION
        "Notification of Event NOE.13

        Message: 'Tx NACK, exp $1, Id $2'

        Parameters list:
              $1: noe13_expected-seq
              $2: noe13_connection-id

        UAUDP NACK message sent with expected sequence <expected-seq> in 
        connection <connection-id>"
    ::= { noeNotificationsPrefix 13 }

noeNotification14 NOTIFICATION-TYPE
    OBJECTS { 
              noe14_connection-id 
            }
    STATUS current
    DESCRIPTION
        "Notification of Event NOE.14

        Message: 'Tx KEEPALIVE, Id $1'

        Parameters list:
              $1: noe14_connection-id

        UAUDP KEEPALIVE message sent in connetion-id."
    ::= { noeNotificationsPrefix 14 }

noeNotification15 NOTIFICATION-TYPE
    OBJECTS { 
              noe15_connection-id 
            }
    STATUS current
    DESCRIPTION
        "Notification of Event NOE.15

        Message: 'Tx RELEASEACK, Id $1'

        Parameters list:
              $1: noe15_connection-id

        UAUDP RELEASEACK message sent in connetion-id."
    ::= { noeNotificationsPrefix 15 }

noeNotification16 NOTIFICATION-TYPE
    OBJECTS { 
              noe16_direction, 
              noe16_size,
              noe16_connection-id,
              noe16_contents 
            }
    STATUS current
    DESCRIPTION
        "Notification of Event NOE.16

        Message: 'Packet forwarded, Dir: $1, size $2, Id $3: $4'

        Parameters list:
              $1: noe16_direction
              $2: noe16_size
              $3: noe16_connection-id
              $4: noe16_contents

        UAUDP message with size forwarded in connetion-id with contents. 
        Direction In (towards CS) or Out (towards terminal)"
    ::= { noeNotificationsPrefix 16 }

noeNotification17 NOTIFICATION-TYPE
    OBJECTS { 
              noe17_connection-id 
            }
    STATUS current
    DESCRIPTION
        "Notification of Event NOE.17

        Message: 'Packet from CS dropped, Id $1'

        Parameters list:
              $1: noe17_connection-id

        UAUDP message from Call Server dropped in connetion-id."
    ::= { noeNotificationsPrefix 17 }

noeNotification18 NOTIFICATION-TYPE
    OBJECTS { 
              noe18_event, 
              noe18_old_state,
              noe18_new_state,
              noe18_cdr,
              noe18_connection-id 
            }
    STATUS current
    DESCRIPTION
        "Notification of Event NOE.18

        Message: 'New event $1 old state $2 new state $3, cdr $4, Id $5'

        Parameters list:
              $1: noe18_event
              $2: noe18_old_state
              $3: noe18_new_state
              $4: noe18_cdr
              $5: noe18_connection-id

        New event in noe terminal"
    ::= { noeNotificationsPrefix 18 }

noeNotification19 NOTIFICATION-TYPE
    OBJECTS { 
              noe19_connection-id 
            }
    STATUS current
    DESCRIPTION
        "Notification of Event NOE.19

        Message: 'Tx RELEASE, Id $1'

        Parameters list:
              $1: noe19_connection-id

        UAUDP RELEASE message sent in connetion-id."
    ::= { noeNotificationsPrefix 19 }

noeNotification20 NOTIFICATION-TYPE
    OBJECTS { 
              noe20_trace, 
              noe20_connetion-id 
            }
    STATUS current
    DESCRIPTION
        "Notification of Event NOE.20

        Message: 'Noe App trace: $1. Id $2'

        Parameters list:
              $1: noe20_trace
              $2: noe20_connetion-id

        NOE Application trace."
    ::= { noeNotificationsPrefix 20 }

noeNotification21 NOTIFICATION-TYPE
    OBJECTS { 
              noe21_size, 
              noe21_connection-id,
              noe21_contents 
            }
    STATUS current
    DESCRIPTION
        "Notification of Event NOE.21

        Message: 'Rx CONNECT, size $1, Id $2: $3'

        Parameters list:
              $1: noe21_size
              $2: noe21_connection-id
              $3: noe21_contents

        UAUDP CONNECT message received in connetion-id."
    ::= { noeNotificationsPrefix 21 }

noeNotification22 NOTIFICATION-TYPE
    OBJECTS { 
              noe22_connection-id 
            }
    STATUS current
    DESCRIPTION
        "Notification of Event NOE.22

        Message: 'Rx CONNECTACK, Id $1'

        Parameters list:
              $1: noe22_connection-id

        UAUDP CONNECTACK message received in connetion-id."
    ::= { noeNotificationsPrefix 22 }

noeNotification23 NOTIFICATION-TYPE
    OBJECTS { 
              noe23_size, 
              noe23_connection-id,
              noe23_contents 
            }
    STATUS current
    DESCRIPTION
        "Notification of Event NOE.23

        Message: 'Tx CONNECT, size $1, Id $2: $3'

        Parameters list:
              $1: noe23_size
              $2: noe23_connection-id
              $3: noe23_contents

        UAUDP CONNECT message sent in connetion-id."
    ::= { noeNotificationsPrefix 23 }

noeNotification24 NOTIFICATION-TYPE
    OBJECTS { 
              noe24_connection-id 
            }
    STATUS current
    DESCRIPTION
        "Notification of Event NOE.24

        Message: 'Tx CONNECTACK, Id $1'

        Parameters list:
              $1: noe24_connection-id

        UAUDP CONNECTACK message sent in connetion-id."
    ::= { noeNotificationsPrefix 24 }


END
