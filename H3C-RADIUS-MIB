-- =================================================================
-- Copyright (C) 2002-2004 by H3C Technologies. All rights reserved.
--
-- Description:
--
--A configuration management and statistical MIB, includes configuration of
--RADIUS Server, and statistics about Accounting Server which complements
--the IETF standard MIB as described in RFC2620.  In addition, there are two
--traps supported to notify client the RADIUS Server's down state.
--
-- Reference: RFC2866, RADIUS-AUTH-CLIENT-MIB, RADIUS-ACC-CLIENT-MIB
-- Version: V1.5
-- History:
--  V1.0 Initial version 2004-07-13
--  V1.1 2004-10-12 updated by gaolong
--       Set size of DisplayString from 0 to 255.
--  V1.2 2005-03-10 updated by xulei
--       Modified description of this MIB
--       Modified MAX-ACCESS of nodes in h3cRdInfoTable
--       Modified description of nodes in h3cRdInfoTable
--       Added nodes of h3cRdInfoTable
--       Added h3cRdAccInfoTable
--       Added h3cRadiusAccServerTable
--       Added Traps
--  V1.3 2005-05-08 updated by xulei
--       Modified MAX-ACCESS of h3cRdPrimAccState and h3cRdSecAccState
--  V1.4 2005-06-03 updated by xulei
--       Modified SYNTAX and DESCRIPTION of h3cRdAccPacketUnit
--  V1.5 2008-05-19 updated by yangxu
--       Added nodes of h3cRdAccInfoTable
--       Added node of h3cRdAcctOnEnable
--       Added node of h3cRdAcctOnSendTimes
--       Added node of h3cRdAcctOnSendInterval
-- =================================================================
H3C-RADIUS-MIB DEFINITIONS ::= BEGIN
    IMPORTS
        h3cCommon
            FROM HUAWEI-3COM-OID-MIB
        OBJECT-GROUP, MODULE-COMPLIANCE
            FROM SNMPv2-CONF
        IpAddress, Integer32, Counter32, OBJECT-TYPE, MODULE-IDENTITY, NOTIFICATION-TYPE
            FROM SNMPv2-SMI
        RowStatus, TruthValue
            FROM SNMPv2-TC
        InetAddressType, InetAddress
            FROM INET-ADDRESS-MIB
        radiusAuthServerIndex, radiusAuthServerAddress, radiusAuthClientServerPortNumber
            FROM RADIUS-AUTH-CLIENT-MIB
        radiusAccServerIndex, radiusAccServerAddress, radiusAccClientServerPortNumber
            FROM RADIUS-ACC-CLIENT-MIB;

    h3cRadius MODULE-IDENTITY
    LAST-UPDATED "200807170000Z"            -- July 17, 2008 at 00:00 GMT
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "The H3C-RADIUS-MIB contains objects to
        Manage configuration and Monitor running state
        for RADIUS feature."
    ::= { h3cCommon 13 }


    DisplayString ::=
    OCTET STRING
    -- This data type   is used to model textual information taken
    -- from the NVT ASCII character set.  By convention, objects
    -- with this syntax are declared as having
    --
    (SIZE (0..255))

    h3cRdObjects OBJECT IDENTIFIER ::= { h3cRadius 1 }

    h3cRdInfoTable  OBJECT-TYPE
        SYNTAX SEQUENCE OF H3cRdInfoEntry
        MAX-ACCESS not-accessible
        STATUS current
        DESCRIPTION
        "The (conceptual) table listing RADIUS authentication servers."
    ::= { h3cRdObjects 1 }

    h3cRdInfoEntry OBJECT-TYPE
        SYNTAX H3cRdInfoEntry
        MAX-ACCESS not-accessible
        STATUS current
        DESCRIPTION
        "An entry (conceptual row) representing a RADIUS authentication server."
        INDEX { h3cRdGroupName }
    ::= { h3cRdInfoTable 1 }

    H3cRdInfoEntry ::= SEQUENCE {
        h3cRdGroupName          DisplayString,
        h3cRdPrimAuthIp         IpAddress,
        h3cRdPrimUdpPort        Integer32,
        h3cRdPrimState          INTEGER,
        h3cRdSecAuthIp          IpAddress,
        h3cRdSecUdpPort         Integer32,
        h3cRdSecState           INTEGER,
        h3cRdKey                DisplayString,
        h3cRdRetry              Integer32,
        h3cRdTimeout            Integer32,
        h3cRdPrimAuthIpAddrType InetAddressType,
        h3cRdPrimAuthIpAddr     InetAddress,
        h3cRdSecAuthIpAddrType  InetAddressType,
        h3cRdSecAuthIpAddr      InetAddress,
        h3cRdServerType         INTEGER,
        h3cRdQuietTime          INTEGER,
        h3cRdUserNameFormat     INTEGER,
        h3cRdRowStatus          RowStatus
        }

    h3cRdGroupName OBJECT-TYPE
        SYNTAX DisplayString
        MAX-ACCESS not-accessible
        STATUS current
        DESCRIPTION
        "The name of the RADIUS authentication group referred to in this table entry."
    ::= { h3cRdInfoEntry 1 }


    h3cRdPrimAuthIp OBJECT-TYPE
        SYNTAX IpAddress
        MAX-ACCESS read-create
        STATUS deprecated
        DESCRIPTION
        "The IP address of primary RADIUS authentication server."
    ::= { h3cRdInfoEntry 2 }

    h3cRdPrimUdpPort OBJECT-TYPE
        SYNTAX Integer32
        MAX-ACCESS read-create
        STATUS current
        DESCRIPTION
        "The UDP port the client is using to send requests to
        primary RADIUS authentication server. Default value is 1812."
    ::= { h3cRdInfoEntry 3 }

    h3cRdPrimState OBJECT-TYPE
        SYNTAX INTEGER
        {
            active(1),
            block(2)
        }
        MAX-ACCESS read-create
        STATUS current
        DESCRIPTION
        "The state of the primary RADIUS authentication server.
        1 (active) The primary authentication server is in active state.
        2 (block)  The primary authentication server is in block state."
    ::= { h3cRdInfoEntry 4 }

    h3cRdSecAuthIp OBJECT-TYPE
        SYNTAX IpAddress
        MAX-ACCESS read-create
        STATUS deprecated
        DESCRIPTION
        "The IP address of secondary RADIUS authentication server."
    ::= { h3cRdInfoEntry 5 }

    h3cRdSecUdpPort OBJECT-TYPE
        SYNTAX Integer32
        MAX-ACCESS read-create
        STATUS current
        DESCRIPTION
        "The UDP port the client is using to send requests to
        secondary RADIUS authentication server. Default value is 1812."
    ::= { h3cRdInfoEntry 6 }

    h3cRdSecState OBJECT-TYPE
        SYNTAX INTEGER
        {
            active(1),
            block(2)
        }
        MAX-ACCESS read-create
        STATUS current
        DESCRIPTION
        "The state of the secondary RADIUS authentication server.
        1 (active) The secondary authentication server is in active state.
        2 (block)  The secondary authentication server is in block state."
    ::= { h3cRdInfoEntry 7 }

    h3cRdKey OBJECT-TYPE
        SYNTAX DisplayString
        MAX-ACCESS read-create
        STATUS current
        DESCRIPTION
        "The secret shared between the RADIUS client and RADIUS
        authentication server used in encoding and decoding
        sensitive data.   Length is 1 - 16 characters."
    ::= { h3cRdInfoEntry 8 }

    h3cRdRetry OBJECT-TYPE
        SYNTAX Integer32
        MAX-ACCESS read-create
        STATUS current
        DESCRIPTION
        "The number of attempts the client will make when trying to send
        requests to a server before it will consider the attempt failed.
        Default value is 3."
    ::= { h3cRdInfoEntry 9 }

    h3cRdTimeout OBJECT-TYPE
        SYNTAX Integer32
        MAX-ACCESS read-create
        STATUS current
        DESCRIPTION
        "The timeout value the client will use when sending requests to a server.
        The unit is second.  Default value is 3."
    ::= { h3cRdInfoEntry 10 }

    h3cRdPrimAuthIpAddrType OBJECT-TYPE
        SYNTAX InetAddressType
        MAX-ACCESS read-create
        STATUS current
        DESCRIPTION
        "The IP addresses type (IPv4 or IPv6) of primary RADIUS authentication server."
    ::= { h3cRdInfoEntry 11 }

    h3cRdPrimAuthIpAddr OBJECT-TYPE
        SYNTAX InetAddress
        MAX-ACCESS read-create
        STATUS current
        DESCRIPTION
        "The IP address of primary RADIUS authentication server."
    ::= { h3cRdInfoEntry 12 }

    h3cRdSecAuthIpAddrType OBJECT-TYPE
        SYNTAX InetAddressType
        MAX-ACCESS read-create
        STATUS current
        DESCRIPTION
        "The IP addresses type (IPv4 or IPv6) of secondary RADIUS authentication server."
    ::= { h3cRdInfoEntry 13 }

    h3cRdSecAuthIpAddr OBJECT-TYPE
        SYNTAX InetAddress
        MAX-ACCESS read-create
        STATUS current
        DESCRIPTION
        "The IP address of secondary RADIUS authentication server."
    ::= { h3cRdInfoEntry 14 }

    h3cRdServerType OBJECT-TYPE
        SYNTAX INTEGER
        {
            standard(1),
            iphotel(2),
            portal(3),
            extended(4)
        }
        MAX-ACCESS read-create
        STATUS current
        DESCRIPTION
        "Specify the type of RADIUS server.
        1 (standard) - Server based on RFC protocol(s).
        2 (iphotel) - Server for IP-Hotel or 201+ system.
        3 (portal) - Server for iTellin Portal system.
        4 (extended) - Server based on RADIUS extensions.
        Default type is standard."
    ::= { h3cRdInfoEntry 15 }

    h3cRdQuietTime OBJECT-TYPE
        SYNTAX INTEGER (1..255)
        MAX-ACCESS read-create
        STATUS current
        DESCRIPTION
        "The time for primary server returning active.  The unit is minute.
        Default value is 5."
    ::= { h3cRdInfoEntry 16 }

    h3cRdUserNameFormat OBJECT-TYPE
        SYNTAX INTEGER
        {
            withoutdomain(1),
            withdomain(2)
        }
        MAX-ACCESS read-create
        STATUS current
        DESCRIPTION
        "Specify the user-name format that is sent to RADIUS server.
        1 (withoutdomain) - send the user-name without domain.
        2 (withdomain) - send the user-name with domain.
        Default format is withdomain."
    ::= { h3cRdInfoEntry 17 }


    h3cRdRowStatus   OBJECT-TYPE
        SYNTAX   RowStatus
        MAX-ACCESS  read-create
        STATUS   current
        DESCRIPTION
        "This object is responsible for managing the creation, deletion and
        modification of rows, which support active status and CreateAndGo,
        Destroy operation.  To create a new row, h3cRdGroupName must be specified.
        To destroy an existent row, the h3cRdGroupName MUST NOT be referred by
        h3cDomainTable in h3cDomainRadiusGroupName column."
    ::= { h3cRdInfoEntry 18 }



    -- ***************************************************************************
    --
    --  Accounting Server Table
    --
    -- ***************************************************************************
    h3cRdAccInfoTable  OBJECT-TYPE
        SYNTAX SEQUENCE OF H3cRdAccInfoEntry
        MAX-ACCESS not-accessible
        STATUS current
        DESCRIPTION
        "The (conceptual) table listing RADIUS accounting servers."
    ::= { h3cRdObjects 2 }

    h3cRdAccInfoEntry OBJECT-TYPE
        SYNTAX H3cRdAccInfoEntry
        MAX-ACCESS not-accessible
        STATUS current
        DESCRIPTION
        "An entry (conceptual row) representing a RADIUS accounting server."
        INDEX { h3cRdAccGroupName }
    ::= { h3cRdAccInfoTable 1 }


    H3cRdAccInfoEntry ::= SEQUENCE {
        h3cRdAccGroupName           DisplayString,
        h3cRdPrimAccIpAddrType      InetAddressType,
        h3cRdPrimAccIpAddr          InetAddress,
        h3cRdPrimAccUdpPort         Integer32,
        h3cRdPrimAccState           INTEGER,
        h3cRdSecAccIpAddrType       InetAddressType,
        h3cRdSecAccIpAddr           InetAddress,
        h3cRdSecAccUdpPort          Integer32,
        h3cRdSecAccState            INTEGER,
        h3cRdAccKey                 DisplayString,
        h3cRdAccRetry               Integer32,
        h3cRdAccTimeout             Integer32,
        h3cRdAccServerType          INTEGER,
        h3cRdAccQuietTime           INTEGER,
        h3cRdAccFailureAction       INTEGER,
        h3cRdAccRealTime            INTEGER,
        h3cRdAccRealTimeRetry       INTEGER,
        h3cRdAccSaveStopPktEnable   TruthValue,
        h3cRdAccStopRetry           INTEGER,
        h3cRdAccDataFlowUnit        INTEGER,
        h3cRdAccPacketUnit          INTEGER,
        h3cRdAccRowStatus           RowStatus,
        h3cRdAcctOnEnable           TruthValue,
        h3cRdAcctOnSendTimes        Integer32,
        h3cRdAcctOnSendInterval     Integer32
        }

    h3cRdAccGroupName OBJECT-TYPE
        SYNTAX DisplayString
        MAX-ACCESS not-accessible
        STATUS current
        DESCRIPTION
        "The name of the RADIUS group referred to in this table entry."
    ::= { h3cRdAccInfoEntry 1 }

    h3cRdPrimAccIpAddrType OBJECT-TYPE
        SYNTAX      InetAddressType
        MAX-ACCESS  read-create
        STATUS      current
        DESCRIPTION
        "The IP addresses type (IPv4 or IPv6) of primary RADIUS accounting server."
    ::= { h3cRdAccInfoEntry 2 }

    h3cRdPrimAccIpAddr OBJECT-TYPE
        SYNTAX      InetAddress
        MAX-ACCESS  read-create
        STATUS      current
        DESCRIPTION
        "The IP address of primary RADIUS accounting server."
    ::= { h3cRdAccInfoEntry 3 }

    h3cRdPrimAccUdpPort OBJECT-TYPE
        SYNTAX      Integer32
        MAX-ACCESS  read-create
        STATUS      current
        DESCRIPTION
        "The UDP port the client is using to send requests to primary
        RADIUS accounting server. Default value is 1813."
    ::= { h3cRdAccInfoEntry 4 }

    h3cRdPrimAccState OBJECT-TYPE
        SYNTAX INTEGER
        {
            active(1),
            block(2)
        }
        MAX-ACCESS  read-create
        STATUS      current
        DESCRIPTION
        "The state of the primary RADIUS accounting server.
        1 (active) The primary accounting server is in active state.
        2 (block)  The primary accounting server is in block state."
    ::= { h3cRdAccInfoEntry 5 }

    h3cRdSecAccIpAddrType OBJECT-TYPE
        SYNTAX      InetAddressType
        MAX-ACCESS  read-create
        STATUS      current
        DESCRIPTION
        "The IP addresses type (IPv4 or IPv6) of secondary RADIUS accounting server."
    ::= { h3cRdAccInfoEntry 6 }

    h3cRdSecAccIpAddr OBJECT-TYPE
        SYNTAX      InetAddress
        MAX-ACCESS  read-create
        STATUS      current
        DESCRIPTION
        "The IP address of secondary RADIUS accounting server."
    ::= { h3cRdAccInfoEntry 7 }

    h3cRdSecAccUdpPort OBJECT-TYPE
        SYNTAX      Integer32
        MAX-ACCESS  read-create
        STATUS      current
        DESCRIPTION
        "The UDP port the client is using to send requests to secondary
        RADIUS accounting server. Default value is 1813."
    ::= { h3cRdAccInfoEntry 8 }

    h3cRdSecAccState OBJECT-TYPE
        SYNTAX INTEGER
        {
            active(1),
            block(2)
        }
        MAX-ACCESS  read-create
        STATUS      current
        DESCRIPTION
        "The state of the secondary RADIUS accounting server.
        1 (active) The secondary accounting server is in active state.
        2 (block)  The secondary accounting server is in block state."
    ::= { h3cRdAccInfoEntry 9 }

    h3cRdAccKey OBJECT-TYPE
        SYNTAX DisplayString
        MAX-ACCESS read-create
        STATUS current
        DESCRIPTION
        "The secret shared between the RADIUS client and RADIUS
        accounting server used in encoding and decoding sensitive data.
        Length is 1 - 16 characters."
    ::= { h3cRdAccInfoEntry 10 }


    h3cRdAccRetry OBJECT-TYPE
        SYNTAX Integer32
        MAX-ACCESS read-create
        STATUS current
        DESCRIPTION
        "The number of attempt the client will make when trying to send
        requests to a server before it will consider the attempt failed.
        Default value is 3."
    ::= { h3cRdAccInfoEntry 11 }

    h3cRdAccTimeout OBJECT-TYPE
        SYNTAX Integer32
        MAX-ACCESS read-create
        STATUS current
        DESCRIPTION
        "The timeout value the client will use when sending requests to a server.
        The unit is second.  Default value is 3."
    ::= { h3cRdAccInfoEntry 12 }

    h3cRdAccServerType OBJECT-TYPE
        SYNTAX INTEGER
        {
            standard(1),
            iphotel(2),
            portal(3),
            extended(4)
        }
        MAX-ACCESS read-create
        STATUS current
        DESCRIPTION
        "Specify the type of RADIUS server.
        1 (standard) - Server based on RFC protocol(s).
        2 (iphotel) - Server for IP-Hotel or 201+ system.
        3 (portal) - Server for iTellin Portal system.
        4 (extended) - Server based on RADIUS extensions.
        Default type is standard."
    ::= { h3cRdAccInfoEntry 13 }

    h3cRdAccQuietTime OBJECT-TYPE
        SYNTAX INTEGER (1..255)
        MAX-ACCESS read-create
        STATUS current
        DESCRIPTION
        "The time for primary server returning active.  The unit is minute.
        Default value is 5."
    ::= { h3cRdAccInfoEntry 14 }

    h3cRdAccFailureAction OBJECT-TYPE
        SYNTAX INTEGER
        {
            ignore(1),
            reject(2)
        }
        MAX-ACCESS read-create
        STATUS current
        DESCRIPTION
        "Defines the action that authentication should take if
        authentication succeeds but the associated accounting start
        fails.
        1 (ignore) - treat as authentication success; ignore
            accounting start failure.
        2 (reject) - treat as authentication failed if
            corresponding accounting start fails.
        Default value is 1(reject)."
    ::= { h3cRdAccInfoEntry 15 }

    h3cRdAccRealTime OBJECT-TYPE
        SYNTAX INTEGER (3..60)
        MAX-ACCESS read-create
        STATUS current
        DESCRIPTION
        "Interval of realtime-accounting packets.  The unit is minute.
        The time must be a multiple of 3.  Default value is 12."
    ::= { h3cRdAccInfoEntry 16 }

    h3cRdAccRealTimeRetry OBJECT-TYPE
        SYNTAX INTEGER (1..255)
        MAX-ACCESS read-create
        STATUS current
        DESCRIPTION
        "The number of attempt the client will make when trying to send
        realtime-accounting packet to accounting server before it will
        consider the attempt failed.  Default value is 5."
    ::= { h3cRdAccInfoEntry 17 }

    h3cRdAccSaveStopPktEnable OBJECT-TYPE
        SYNTAX TruthValue
        MAX-ACCESS read-create
        STATUS current
        DESCRIPTION
        "The control of whether save stop-accounting packet in local buffer
        and resend later when the accounting server doesn't respond.  When
        SaveStopPktEnable is set to false, the value of AccStopRetry will be
        ignored.  Default value is true."
    ::= { h3cRdAccInfoEntry 18 }

    h3cRdAccStopRetry OBJECT-TYPE
        SYNTAX INTEGER (10..65535)
        MAX-ACCESS read-create
        STATUS current
        DESCRIPTION
        "The number of attempt the client will make when trying to send
        stop-accounting packet to accounting server.  Default value is 500."
    ::= { h3cRdAccInfoEntry 19 }

    h3cRdAccDataFlowUnit OBJECT-TYPE
        SYNTAX INTEGER
        {
            byte(1),
            kiloByte(2),
            megaByte(3),
            gigaByte(4)
        }
        MAX-ACCESS read-create
        STATUS current
        DESCRIPTION
        "Specify data flow format that is sent to RADIUS server.  The value
        SHOULD be set the same as the value of corresponding server.
        1 (byte) -  Specify 'byte' as the unit of data flow.
        2 (kiloByte) - Specify 'kilo-byte' as the unit of data flow.
        3 (megaByte) - Specify 'mega-byte' as the unit of data flow.
        4 (gigaByte) - Specify 'giga-byte' as the unit of data flow.
        Default value is 1."
    ::= { h3cRdAccInfoEntry 20 }

    h3cRdAccPacketUnit OBJECT-TYPE
        SYNTAX INTEGER
        {
            onePacket(1),
            kiloPacket(2),
            megaPacket(3),
            gigaPacket(4)
        }
        MAX-ACCESS read-create
        STATUS current
        DESCRIPTION
        "Specify packet format that is sent to RADIUS server.  The value
        SHOULD be set the same as the value of corresponding server.
        1 (onePacket)  - Specify 'one-packet' as the unit of packet.
        2 (kiloPacket) - Specify 'kilo-packet' as the unit of packet.
        3 (megaPacket) - Specify 'mega-packet' as the unit of packet.
        4 (gigaPacket) - Specify 'giga-packet' as the unit of packet.
        Default value is 1."
    ::= { h3cRdAccInfoEntry 21 }

    h3cRdAccRowStatus   OBJECT-TYPE
        SYNTAX   RowStatus
        MAX-ACCESS  read-create
        STATUS   current
        DESCRIPTION
        "This object is responsible for managing the creation, deletion and
        modification of rows, which support active status and CreateAndGo,
        Destroy operation.  To create a new row, h3cRdAccGroupName must be specified.
        To destroy an existent row, the h3cRdAccGroupName MUST NOT be referred by
        h3cDomainTable in h3cDomainRadiusGroupName column."
    ::= { h3cRdAccInfoEntry 22 }

    h3cRdAcctOnEnable OBJECT-TYPE
        SYNTAX TruthValue
        MAX-ACCESS read-create
        STATUS current
        DESCRIPTION
        "The control of Accounting-On function.  The Accounting-On function is
        used by the client to mark the start of accounting (for example, upon
        booting) by sending Accounting-On packets and to mark the end of
        accounting (for example, just before a scheduled reboot) by sending
        Accounting-Off packets.  Default value is false."
    ::= { h3cRdAccInfoEntry 23 }

    h3cRdAcctOnSendTimes OBJECT-TYPE
        SYNTAX Integer32
        MAX-ACCESS read-create
        STATUS current
        DESCRIPTION
        "The number of Accounting-On packets the client will send before it
        considers the accounting server failed.  Default value is 15."
        DEFVAL { 15 }
    ::= { h3cRdAccInfoEntry 24 }

    h3cRdAcctOnSendInterval OBJECT-TYPE
        SYNTAX Integer32
        MAX-ACCESS read-create
        STATUS current
        DESCRIPTION
        "Interval of Accounting-On packets.  The unit is second.
        Default value is 3."
        DEFVAL { 3 }
    ::= { h3cRdAccInfoEntry 25 }


    -- ***************************************************************************
    --
    --  Supplement to RFC2620 RADIUS-ACC-CLIENT-MIB
    --
    -- ***************************************************************************

    h3cRadiusAccounting OBJECT IDENTIFIER ::= { h3cRadius 2 }

    h3cRadiusAccClient OBJECT IDENTIFIER ::= { h3cRadiusAccounting 1 }

    h3cRadiusAccServerTable OBJECT-TYPE
        SYNTAX  SEQUENCE OF H3cRadiusAccServerEntry
        MAX-ACCESS  not-accessible
        STATUS  current
        DESCRIPTION
        "The (conceptual) table listing the RADIUS accounting
        servers with which the client shares a secret."
    ::= { h3cRadiusAccClient 1 }

    h3cRadiusAccServerEntry OBJECT-TYPE
        SYNTAX  H3cRadiusAccServerEntry
        MAX-ACCESS  not-accessible
        STATUS  current
        DESCRIPTION
        "An entry (conceptual row) representing a RADIUS accounting
        server with which a client shares a secret."
        INDEX { radiusAccServerIndex }
    ::= { h3cRadiusAccServerTable 1 }

    H3cRadiusAccServerEntry ::= SEQUENCE {
        h3cRadiusAccClientStartRequests         Counter32,
        h3cRadiusAccClientStartResponses        Counter32,
        h3cRadiusAccClientInterimRequests       Counter32,
        h3cRadiusAccClientInterimResponses      Counter32,
        h3cRadiusAccClientStopRequests          Counter32,
        h3cRadiusAccClientStopResponses         Counter32 }

    h3cRadiusAccClientStartRequests   OBJECT-TYPE
        SYNTAX  Counter32
        MAX-ACCESS  read-only
        STATUS  current
        DESCRIPTION
        "The number of RADIUS accounting start request sent to this
        server."
    ::= { h3cRadiusAccServerEntry  1 }

    h3cRadiusAccClientStartResponses   OBJECT-TYPE
        SYNTAX  Counter32
        MAX-ACCESS  read-only
        STATUS  current
        DESCRIPTION
        "The number of RADIUS accounting start response received
        from this server."
    ::= { h3cRadiusAccServerEntry  2 }

    h3cRadiusAccClientInterimRequests   OBJECT-TYPE
        SYNTAX  Counter32
        MAX-ACCESS  read-only
        STATUS  current
        DESCRIPTION
        "The number of RADIUS interim accounting request sent to
        this server."
    ::= { h3cRadiusAccServerEntry  3 }

    h3cRadiusAccClientInterimResponses   OBJECT-TYPE
        SYNTAX  Counter32
        MAX-ACCESS  read-only
        STATUS  current
        DESCRIPTION
        "The number of RADIUS interim accounting response received
        from this server."
    ::= { h3cRadiusAccServerEntry  4 }

    h3cRadiusAccClientStopRequests   OBJECT-TYPE
        SYNTAX  Counter32
        MAX-ACCESS  read-only
        STATUS  current
        DESCRIPTION
        "The number of RADIUS stop accounting request sent to
        this RADIUS server."
    ::= { h3cRadiusAccServerEntry  5 }

    h3cRadiusAccClientStopResponses   OBJECT-TYPE
        SYNTAX  Counter32
        MAX-ACCESS  read-only
        STATUS  current
        DESCRIPTION
        "The number of RADIUS stop accounting response received
        from this server."
    ::= { h3cRadiusAccServerEntry  6 }

    --------------------------------------------------------------
    -- Traps
    --------------------------------------------------------------

    -- All trap definitions should be placed under this object.
    h3cRadiusServerTrap OBJECT IDENTIFIER ::= { h3cRadius 3 }

    h3cRadiusAuthServerDownTrap NOTIFICATION-TYPE
        OBJECTS     { radiusAuthServerAddress,
                     radiusAuthClientServerPortNumber }
        STATUS      current
        DESCRIPTION
        "This trap is generated when the Authentication Radius server
        doesn't respond client's requests for specified times."
    ::= { h3cRadiusServerTrap 1 }

    h3cRadiusAccServerDownTrap NOTIFICATION-TYPE
        OBJECTS     { radiusAccServerAddress,
                     radiusAccClientServerPortNumber }
        STATUS      current
        DESCRIPTION
        "This trap is generated when the Accounting Radius server
        doesn't respond client's requests for specified times."
    ::= { h3cRadiusServerTrap 2 }

END
