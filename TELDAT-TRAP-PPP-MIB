-- file automatically created


TELDAT-TRAP-PPP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


pppTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the PPP event subsystem."
    REVISION "201401200930Z"
    DESCRIPTION "Initial implementation"
        ::= { telEventTraps 95 }


pppEventsGroup	OBJECT IDENTIFIER	::= { pppTrapsMIB 1 }

pppNotifications	OBJECT IDENTIFIER	::= { pppTrapsMIB 2 }
pppNotificationsPrefix	OBJECT IDENTIFIER	::= { pppNotifications 0 }

pppEventObjects1 OBJECT-IDENTITY
    STATUS current
    DESCRIPTION
        "Event PPP.1
        Selftest successfully completed."
    ::= { pppEventsGroup 1 }

ppp1_interface OBJECT-TYPE
    SYNTAX DisplayString
    MAX-ACCESS accessible-for-notify
    STATUS current
    DESCRIPTION
        "Parameter 'interface' in event PPP.1"
    ::= { pppEventObjects1 1 }

pppEventObjects2 OBJECT-IDENTITY
    STATUS current
    DESCRIPTION
        "Event PPP.2
        The selftest indicates that the base interfaces are all down."
    ::= { pppEventsGroup 2 }

ppp2_interface OBJECT-TYPE
    SYNTAX DisplayString
    MAX-ACCESS accessible-for-notify
    STATUS current
    DESCRIPTION
        "Parameter 'interface' in event PPP.2"
    ::= { pppEventObjects2 1 }

pppEventObjects3 OBJECT-IDENTITY
    STATUS current
    DESCRIPTION
        "Event PPP.3
        The MRU has been exceeded in an incoming packet in the indicated link."
    ::= { pppEventsGroup 3 }

ppp3_linkPPP OBJECT-TYPE
    SYNTAX DisplayString
    MAX-ACCESS accessible-for-notify
    STATUS current
    DESCRIPTION
        "Parameter 'linkPPP' in event PPP.3"
    ::= { pppEventObjects3 1 }

ppp3_size OBJECT-TYPE
    SYNTAX Integer32
    MAX-ACCESS accessible-for-notify
    STATUS current
    DESCRIPTION
        "Parameter 'size' in event PPP.3"
    ::= { pppEventObjects3 2 }

ppp3_MRU OBJECT-TYPE
    SYNTAX Integer32
    MAX-ACCESS accessible-for-notify
    STATUS current
    DESCRIPTION
        "Parameter 'MRU' in event PPP.3"
    ::= { pppEventObjects3 3 }

pppEventObjects4 OBJECT-IDENTITY
    STATUS current
    DESCRIPTION
        "Event PPP.4
        A multilink PPP fragment has been received out-of-order. Queue is flushed
        or link reordered."
    ::= { pppEventsGroup 4 }

ppp4_linkPPP OBJECT-TYPE
    SYNTAX DisplayString
    MAX-ACCESS accessible-for-notify
    STATUS current
    DESCRIPTION
        "Parameter 'linkPPP' in event PPP.4"
    ::= { pppEventObjects4 1 }

ppp4_action OBJECT-TYPE
    SYNTAX DisplayString
    MAX-ACCESS accessible-for-notify
    STATUS current
    DESCRIPTION
        "Parameter 'action' in event PPP.4"
    ::= { pppEventObjects4 2 }

pppEventObjects5 OBJECT-IDENTITY
    STATUS current
    DESCRIPTION
        "Event PPP.5
        Multilink Header Format option description."
    ::= { pppEventsGroup 5 }

ppp5_link_name OBJECT-TYPE
    SYNTAX DisplayString
    MAX-ACCESS accessible-for-notify
    STATUS current
    DESCRIPTION
        "Parameter 'link name' in event PPP.5"
    ::= { pppEventObjects5 1 }

ppp5_sequence OBJECT-TYPE
    SYNTAX DisplayString
    MAX-ACCESS accessible-for-notify
    STATUS current
    DESCRIPTION
        "Parameter 'sequence' in event PPP.5"
    ::= { pppEventObjects5 2 }

ppp5_classes OBJECT-TYPE
    SYNTAX Integer32
    MAX-ACCESS accessible-for-notify
    STATUS current
    DESCRIPTION
        "Parameter 'classes' in event PPP.5"
    ::= { pppEventObjects5 3 }

ppp5_dump OBJECT-TYPE
    SYNTAX DisplayString
    MAX-ACCESS accessible-for-notify
    STATUS current
    DESCRIPTION
        "Parameter 'dump' in event PPP.5"
    ::= { pppEventObjects5 4 }

pppEventObjects6 OBJECT-IDENTITY
    STATUS current
    DESCRIPTION
        "Event PPP.6
        Multiclass Multilink negotiated in the MP bundle."
    ::= { pppEventsGroup 6 }

ppp6_linkPPP OBJECT-TYPE
    SYNTAX DisplayString
    MAX-ACCESS accessible-for-notify
    STATUS current
    DESCRIPTION
        "Parameter 'linkPPP' in event PPP.6"
    ::= { pppEventObjects6 1 }

pppEventObjects7 OBJECT-IDENTITY
    STATUS current
    DESCRIPTION
        "Event PPP.7
        MP Real Time Frame."
    ::= { pppEventsGroup 7 }

ppp7_linkPPP OBJECT-TYPE
    SYNTAX DisplayString
    MAX-ACCESS accessible-for-notify
    STATUS current
    DESCRIPTION
        "Parameter 'linkPPP' in event PPP.7"
    ::= { pppEventObjects7 1 }

pppEventObjects11 OBJECT-IDENTITY
    STATUS current
    DESCRIPTION
        "Event PPP.11
        Received/sent frame from the protocol specified by a PPP interface."
    ::= { pppEventsGroup 11 }

ppp11_linkPPP OBJECT-TYPE
    SYNTAX DisplayString
    MAX-ACCESS accessible-for-notify
    STATUS current
    DESCRIPTION
        "Parameter 'linkPPP' in event PPP.11"
    ::= { pppEventObjects11 1 }

ppp11_receivedIn_or_sentOut OBJECT-TYPE
    SYNTAX DisplayString
    MAX-ACCESS accessible-for-notify
    STATUS current
    DESCRIPTION
        "Parameter 'received(In) or sent(Out)' in event PPP.11"
    ::= { pppEventObjects11 2 }

ppp11_protocol OBJECT-TYPE
    SYNTAX Integer32
    MAX-ACCESS accessible-for-notify
    STATUS current
    DESCRIPTION
        "Parameter 'protocol' in event PPP.11"
    ::= { pppEventObjects11 3 }

ppp11_size OBJECT-TYPE
    SYNTAX Integer32
    MAX-ACCESS accessible-for-notify
    STATUS current
    DESCRIPTION
        "Parameter 'size' in event PPP.11"
    ::= { pppEventObjects11 4 }

pppEventObjects12 OBJECT-IDENTITY
    STATUS current
    DESCRIPTION
        "Event PPP.12
        Frame received with Protocol Field Compression (PFC)."
    ::= { pppEventsGroup 12 }

ppp12_linkPPP OBJECT-TYPE
    SYNTAX DisplayString
    MAX-ACCESS accessible-for-notify
    STATUS current
    DESCRIPTION
        "Parameter 'linkPPP' in event PPP.12"
    ::= { pppEventObjects12 1 }

ppp12_receivedIn_or_sentOut OBJECT-TYPE
    SYNTAX DisplayString
    MAX-ACCESS accessible-for-notify
    STATUS current
    DESCRIPTION
        "Parameter 'received(In) or sent(Out)' in event PPP.12"
    ::= { pppEventObjects12 2 }

ppp12_protocol OBJECT-TYPE
    SYNTAX Integer32
    MAX-ACCESS accessible-for-notify
    STATUS current
    DESCRIPTION
        "Parameter 'protocol' in event PPP.12"
    ::= { pppEventObjects12 3 }

ppp12_result OBJECT-TYPE
    SYNTAX DisplayString
    MAX-ACCESS accessible-for-notify
    STATUS current
    DESCRIPTION
        "Parameter 'result' in event PPP.12"
    ::= { pppEventObjects12 4 }

pppEventObjects13 OBJECT-IDENTITY
    STATUS current
    DESCRIPTION
        "Event PPP.13
        A Van Jacobson frame has been compressed/decompressed (indicating
        the result of the operation)."
    ::= { pppEventsGroup 13 }

ppp13_linkPPP OBJECT-TYPE
    SYNTAX DisplayString
    MAX-ACCESS accessible-for-notify
    STATUS current
    DESCRIPTION
        "Parameter 'linkPPP' in event PPP.13"
    ::= { pppEventObjects13 1 }

ppp13_compressedIn_or_uncompressedOut OBJECT-TYPE
    SYNTAX DisplayString
    MAX-ACCESS accessible-for-notify
    STATUS current
    DESCRIPTION
        "Parameter 'compressed(In) or uncompressed(Out)' in event PPP.13"
    ::= { pppEventObjects13 2 }

ppp13_action OBJECT-TYPE
    SYNTAX DisplayString
    MAX-ACCESS accessible-for-notify
    STATUS current
    DESCRIPTION
        "Parameter 'action' in event PPP.13"
    ::= { pppEventObjects13 3 }

ppp13_protocol OBJECT-TYPE
    SYNTAX Integer32
    MAX-ACCESS accessible-for-notify
    STATUS current
    DESCRIPTION
        "Parameter 'protocol' in event PPP.13"
    ::= { pppEventObjects13 4 }

ppp13_result OBJECT-TYPE
    SYNTAX DisplayString
    MAX-ACCESS accessible-for-notify
    STATUS current
    DESCRIPTION
        "Parameter 'result' in event PPP.13"
    ::= { pppEventObjects13 5 }

pppEventObjects14 OBJECT-IDENTITY
    STATUS current
    DESCRIPTION
        "Event PPP.14
        An IPHC frame has been compressed/decompressed (indicating the result
        of the operation)."
    ::= { pppEventsGroup 14 }

ppp14_linkPPP OBJECT-TYPE
    SYNTAX DisplayString
    MAX-ACCESS accessible-for-notify
    STATUS current
    DESCRIPTION
        "Parameter 'linkPPP' in event PPP.14"
    ::= { pppEventObjects14 1 }

ppp14_compressedIn_or_uncompressedOut OBJECT-TYPE
    SYNTAX DisplayString
    MAX-ACCESS accessible-for-notify
    STATUS current
    DESCRIPTION
        "Parameter 'compressed(In) or uncompressed(Out)' in event PPP.14"
    ::= { pppEventObjects14 2 }

ppp14_action OBJECT-TYPE
    SYNTAX DisplayString
    MAX-ACCESS accessible-for-notify
    STATUS current
    DESCRIPTION
        "Parameter 'action' in event PPP.14"
    ::= { pppEventObjects14 3 }

ppp14_protocol OBJECT-TYPE
    SYNTAX Integer32
    MAX-ACCESS accessible-for-notify
    STATUS current
    DESCRIPTION
        "Parameter 'protocol' in event PPP.14"
    ::= { pppEventObjects14 4 }

ppp14_result OBJECT-TYPE
    SYNTAX DisplayString
    MAX-ACCESS accessible-for-notify
    STATUS current
    DESCRIPTION
        "Parameter 'result' in event PPP.14"
    ::= { pppEventObjects14 5 }

pppEventObjects15 OBJECT-IDENTITY
    STATUS current
    DESCRIPTION
        "Event PPP.15
        A CCP frame has been compressed/decompressed (indicating the result
        of the operation)."
    ::= { pppEventsGroup 15 }

ppp15_linkPPP OBJECT-TYPE
    SYNTAX DisplayString
    MAX-ACCESS accessible-for-notify
    STATUS current
    DESCRIPTION
        "Parameter 'linkPPP' in event PPP.15"
    ::= { pppEventObjects15 1 }

ppp15_compressedIn_or_uncompressedOut OBJECT-TYPE
    SYNTAX DisplayString
    MAX-ACCESS accessible-for-notify
    STATUS current
    DESCRIPTION
        "Parameter 'compressed(In) or uncompressed(Out)' in event PPP.15"
    ::= { pppEventObjects15 2 }

ppp15_action OBJECT-TYPE
    SYNTAX DisplayString
    MAX-ACCESS accessible-for-notify
    STATUS current
    DESCRIPTION
        "Parameter 'action' in event PPP.15"
    ::= { pppEventObjects15 3 }

ppp15_protocol OBJECT-TYPE
    SYNTAX Integer32
    MAX-ACCESS accessible-for-notify
    STATUS current
    DESCRIPTION
        "Parameter 'protocol' in event PPP.15"
    ::= { pppEventObjects15 4 }

ppp15_result OBJECT-TYPE
    SYNTAX DisplayString
    MAX-ACCESS accessible-for-notify
    STATUS current
    DESCRIPTION
        "Parameter 'result' in event PPP.15"
    ::= { pppEventObjects15 5 }

pppEventObjects16 OBJECT-IDENTITY
    STATUS current
    DESCRIPTION
        "Event PPP.16
        Se ha enviado/recibido un CCP Reset Request/Ack."
    ::= { pppEventsGroup 16 }

ppp16_linkPPP OBJECT-TYPE
    SYNTAX DisplayString
    MAX-ACCESS accessible-for-notify
    STATUS current
    DESCRIPTION
        "Parameter 'linkPPP' in event PPP.16"
    ::= { pppEventObjects16 1 }

ppp16_receivedIn_or_sentOut OBJECT-TYPE
    SYNTAX DisplayString
    MAX-ACCESS accessible-for-notify
    STATUS current
    DESCRIPTION
        "Parameter 'received(In) or sent(Out)' in event PPP.16"
    ::= { pppEventObjects16 2 }

ppp16_request_ack OBJECT-TYPE
    SYNTAX DisplayString
    MAX-ACCESS accessible-for-notify
    STATUS current
    DESCRIPTION
        "Parameter 'request_ack' in event PPP.16"
    ::= { pppEventObjects16 3 }

pppEventObjects17 OBJECT-IDENTITY
    STATUS current
    DESCRIPTION
        "Event PPP.17
        An MP bundle has been created or eliminated."
    ::= { pppEventsGroup 17 }

ppp17_linkPPP OBJECT-TYPE
    SYNTAX DisplayString
    MAX-ACCESS accessible-for-notify
    STATUS current
    DESCRIPTION
        "Parameter 'linkPPP' in event PPP.17"
    ::= { pppEventObjects17 1 }

ppp17_created_or_deleted OBJECT-TYPE
    SYNTAX DisplayString
    MAX-ACCESS accessible-for-notify
    STATUS current
    DESCRIPTION
        "Parameter 'created or deleted' in event PPP.17"
    ::= { pppEventObjects17 2 }

pppEventObjects18 OBJECT-IDENTITY
    STATUS current
    DESCRIPTION
        "Event PPP.18
        MRRU negotiated in the MP bundle."
    ::= { pppEventsGroup 18 }

ppp18_linkPPP OBJECT-TYPE
    SYNTAX DisplayString
    MAX-ACCESS accessible-for-notify
    STATUS current
    DESCRIPTION
        "Parameter 'linkPPP' in event PPP.18"
    ::= { pppEventObjects18 1 }

ppp18_local_or_remote OBJECT-TYPE
    SYNTAX DisplayString
    MAX-ACCESS accessible-for-notify
    STATUS current
    DESCRIPTION
        "Parameter 'local or remote' in event PPP.18"
    ::= { pppEventObjects18 2 }

ppp18_MRRU OBJECT-TYPE
    SYNTAX Integer32
    MAX-ACCESS accessible-for-notify
    STATUS current
    DESCRIPTION
        "Parameter 'MRRU' in event PPP.18"
    ::= { pppEventObjects18 3 }

pppEventObjects19 OBJECT-IDENTITY
    STATUS current
    DESCRIPTION
        "Event PPP.19
        SSN format (Short Sequence Number) negotiated in the MP bundle."
    ::= { pppEventsGroup 19 }

ppp19_linkPPP OBJECT-TYPE
    SYNTAX DisplayString
    MAX-ACCESS accessible-for-notify
    STATUS current
    DESCRIPTION
        "Parameter 'linkPPP' in event PPP.19"
    ::= { pppEventObjects19 1 }

ppp19_local_or_remote OBJECT-TYPE
    SYNTAX DisplayString
    MAX-ACCESS accessible-for-notify
    STATUS current
    DESCRIPTION
        "Parameter 'local or remote' in event PPP.19"
    ::= { pppEventObjects19 2 }

pppEventObjects20 OBJECT-IDENTITY
    STATUS current
    DESCRIPTION
        "Event PPP.20
        Endpoint Discriminator used in the MP bundle."
    ::= { pppEventsGroup 20 }

ppp20_linkPPP OBJECT-TYPE
    SYNTAX DisplayString
    MAX-ACCESS accessible-for-notify
    STATUS current
    DESCRIPTION
        "Parameter 'linkPPP' in event PPP.20"
    ::= { pppEventObjects20 1 }

ppp20_local_or_remote OBJECT-TYPE
    SYNTAX DisplayString
    MAX-ACCESS accessible-for-notify
    STATUS current
    DESCRIPTION
        "Parameter 'local or remote' in event PPP.20"
    ::= { pppEventObjects20 2 }

ppp20_Endpoint_class OBJECT-TYPE
    SYNTAX Integer32
    MAX-ACCESS accessible-for-notify
    STATUS current
    DESCRIPTION
        "Parameter 'Endpoint class' in event PPP.20"
    ::= { pppEventObjects20 3 }

ppp20_Endpoint_value OBJECT-TYPE
    SYNTAX DisplayString
    MAX-ACCESS accessible-for-notify
    STATUS current
    DESCRIPTION
        "Parameter 'Endpoint value' in event PPP.20"
    ::= { pppEventObjects20 4 }

pppEventObjects21 OBJECT-IDENTITY
    STATUS current
    DESCRIPTION
        "Event PPP.21
        A PPP link has been added to or removed from an MP bundle."
    ::= { pppEventsGroup 21 }

ppp21_linkPPP OBJECT-TYPE
    SYNTAX DisplayString
    MAX-ACCESS accessible-for-notify
    STATUS current
    DESCRIPTION
        "Parameter 'linkPPP' in event PPP.21"
    ::= { pppEventObjects21 1 }

ppp21_added_or_removed OBJECT-TYPE
    SYNTAX DisplayString
    MAX-ACCESS accessible-for-notify
    STATUS current
    DESCRIPTION
        "Parameter 'added or removed' in event PPP.21"
    ::= { pppEventObjects21 2 }

pppEventObjects22 OBJECT-IDENTITY
    STATUS current
    DESCRIPTION
        "Event PPP.22
        A multilink PPP frame has been received with a determined sequence
        number (the expected sequence number is displayed and the corresponding
        action: accept, discard or queue). Includes the flags and
        the frame size."
    ::= { pppEventsGroup 22 }

ppp22_linkPPP OBJECT-TYPE
    SYNTAX DisplayString
    MAX-ACCESS accessible-for-notify
    STATUS current
    DESCRIPTION
        "Parameter 'linkPPP' in event PPP.22"
    ::= { pppEventObjects22 1 }

ppp22_flags OBJECT-TYPE
    SYNTAX Integer32
    MAX-ACCESS accessible-for-notify
    STATUS current
    DESCRIPTION
        "Parameter 'flags' in event PPP.22"
    ::= { pppEventObjects22 2 }

ppp22_received_sequence OBJECT-TYPE
    SYNTAX Integer32
    MAX-ACCESS accessible-for-notify
    STATUS current
    DESCRIPTION
        "Parameter 'received sequence' in event PPP.22"
    ::= { pppEventObjects22 3 }

ppp22_expected_sequence OBJECT-TYPE
    SYNTAX Integer32
    MAX-ACCESS accessible-for-notify
    STATUS current
    DESCRIPTION
        "Parameter 'expected sequence' in event PPP.22"
    ::= { pppEventObjects22 4 }

ppp22_action OBJECT-TYPE
    SYNTAX DisplayString
    MAX-ACCESS accessible-for-notify
    STATUS current
    DESCRIPTION
        "Parameter 'action' in event PPP.22"
    ::= { pppEventObjects22 5 }

ppp22_size OBJECT-TYPE
    SYNTAX Integer32
    MAX-ACCESS accessible-for-notify
    STATUS current
    DESCRIPTION
        "Parameter 'size' in event PPP.22"
    ::= { pppEventObjects22 6 }

pppEventObjects23 OBJECT-IDENTITY
    STATUS current
    DESCRIPTION
        "Event PPP.23
        A multilink PPP frame has been transmitted (the transmission sequence
        number, the flags and the frame size is displayed)."
    ::= { pppEventsGroup 23 }

ppp23_linkPPP OBJECT-TYPE
    SYNTAX DisplayString
    MAX-ACCESS accessible-for-notify
    STATUS current
    DESCRIPTION
        "Parameter 'linkPPP' in event PPP.23"
    ::= { pppEventObjects23 1 }

ppp23_flags OBJECT-TYPE
    SYNTAX Integer32
    MAX-ACCESS accessible-for-notify
    STATUS current
    DESCRIPTION
        "Parameter 'flags' in event PPP.23"
    ::= { pppEventObjects23 2 }

ppp23_transmission_sequence OBJECT-TYPE
    SYNTAX Integer32
    MAX-ACCESS accessible-for-notify
    STATUS current
    DESCRIPTION
        "Parameter 'transmission sequence' in event PPP.23"
    ::= { pppEventObjects23 3 }

ppp23_size OBJECT-TYPE
    SYNTAX Integer32
    MAX-ACCESS accessible-for-notify
    STATUS current
    DESCRIPTION
        "Parameter 'size' in event PPP.23"
    ::= { pppEventObjects23 4 }

pppEventObjects24 OBJECT-IDENTITY
    STATUS current
    DESCRIPTION
        "Event PPP.24
        The maximum number of queued multilink PPP fragments has been exceeded."
    ::= { pppEventsGroup 24 }

ppp24_linkPPP OBJECT-TYPE
    SYNTAX DisplayString
    MAX-ACCESS accessible-for-notify
    STATUS current
    DESCRIPTION
        "Parameter 'linkPPP' in event PPP.24"
    ::= { pppEventObjects24 1 }

pppEventObjects25 OBJECT-IDENTITY
    STATUS current
    DESCRIPTION
        "Event PPP.25
        A fragment with the MP frame end flag has been found (END) however
        the beginning part of the frame is not available."
    ::= { pppEventsGroup 25 }

ppp25_linkPPP OBJECT-TYPE
    SYNTAX DisplayString
    MAX-ACCESS accessible-for-notify
    STATUS current
    DESCRIPTION
        "Parameter 'linkPPP' in event PPP.25"
    ::= { pppEventObjects25 1 }

ppp25_sequence OBJECT-TYPE
    SYNTAX Integer32
    MAX-ACCESS accessible-for-notify
    STATUS current
    DESCRIPTION
        "Parameter 'sequence' in event PPP.25"
    ::= { pppEventObjects25 2 }

pppEventObjects26 OBJECT-IDENTITY
    STATUS current
    DESCRIPTION
        "Event PPP.26
        An error has been produced compressing/decompressing
        a Van Jacobson frame."
    ::= { pppEventsGroup 26 }

ppp26_linkPPP OBJECT-TYPE
    SYNTAX DisplayString
    MAX-ACCESS accessible-for-notify
    STATUS current
    DESCRIPTION
        "Parameter 'linkPPP' in event PPP.26"
    ::= { pppEventObjects26 1 }

ppp26_compressedIn_or_uncompressedOut OBJECT-TYPE
    SYNTAX DisplayString
    MAX-ACCESS accessible-for-notify
    STATUS current
    DESCRIPTION
        "Parameter 'compressed(In) or uncompressed(Out)' in event PPP.26"
    ::= { pppEventObjects26 2 }

ppp26_action OBJECT-TYPE
    SYNTAX DisplayString
    MAX-ACCESS accessible-for-notify
    STATUS current
    DESCRIPTION
        "Parameter 'action' in event PPP.26"
    ::= { pppEventObjects26 3 }

ppp26_protocol OBJECT-TYPE
    SYNTAX Integer32
    MAX-ACCESS accessible-for-notify
    STATUS current
    DESCRIPTION
        "Parameter 'protocol' in event PPP.26"
    ::= { pppEventObjects26 4 }

ppp26_result OBJECT-TYPE
    SYNTAX DisplayString
    MAX-ACCESS accessible-for-notify
    STATUS current
    DESCRIPTION
        "Parameter 'result' in event PPP.26"
    ::= { pppEventObjects26 5 }

pppEventObjects27 OBJECT-IDENTITY
    STATUS current
    DESCRIPTION
        "Event PPP.27
        An error has been produced compressing/decompressing a IPHC frame."
    ::= { pppEventsGroup 27 }

ppp27_linkPPP OBJECT-TYPE
    SYNTAX DisplayString
    MAX-ACCESS accessible-for-notify
    STATUS current
    DESCRIPTION
        "Parameter 'linkPPP' in event PPP.27"
    ::= { pppEventObjects27 1 }

ppp27_compressedIn_or_uncompressedOut OBJECT-TYPE
    SYNTAX DisplayString
    MAX-ACCESS accessible-for-notify
    STATUS current
    DESCRIPTION
        "Parameter 'compressed(In) or uncompressed(Out)' in event PPP.27"
    ::= { pppEventObjects27 2 }

ppp27_action OBJECT-TYPE
    SYNTAX DisplayString
    MAX-ACCESS accessible-for-notify
    STATUS current
    DESCRIPTION
        "Parameter 'action' in event PPP.27"
    ::= { pppEventObjects27 3 }

ppp27_protocol OBJECT-TYPE
    SYNTAX Integer32
    MAX-ACCESS accessible-for-notify
    STATUS current
    DESCRIPTION
        "Parameter 'protocol' in event PPP.27"
    ::= { pppEventObjects27 4 }

ppp27_result OBJECT-TYPE
    SYNTAX DisplayString
    MAX-ACCESS accessible-for-notify
    STATUS current
    DESCRIPTION
        "Parameter 'result' in event PPP.27"
    ::= { pppEventObjects27 5 }

pppEventObjects28 OBJECT-IDENTITY
    STATUS current
    DESCRIPTION
        "Event PPP.28
        An error has been produced compressing/decompressing a CCP frame."
    ::= { pppEventsGroup 28 }

ppp28_linkPPP OBJECT-TYPE
    SYNTAX DisplayString
    MAX-ACCESS accessible-for-notify
    STATUS current
    DESCRIPTION
        "Parameter 'linkPPP' in event PPP.28"
    ::= { pppEventObjects28 1 }

ppp28_compressedIn_or_uncompressedOut OBJECT-TYPE
    SYNTAX DisplayString
    MAX-ACCESS accessible-for-notify
    STATUS current
    DESCRIPTION
        "Parameter 'compressed(In) or uncompressed(Out)' in event PPP.28"
    ::= { pppEventObjects28 2 }

ppp28_action OBJECT-TYPE
    SYNTAX DisplayString
    MAX-ACCESS accessible-for-notify
    STATUS current
    DESCRIPTION
        "Parameter 'action' in event PPP.28"
    ::= { pppEventObjects28 3 }

ppp28_protocol OBJECT-TYPE
    SYNTAX Integer32
    MAX-ACCESS accessible-for-notify
    STATUS current
    DESCRIPTION
        "Parameter 'protocol' in event PPP.28"
    ::= { pppEventObjects28 4 }

ppp28_result OBJECT-TYPE
    SYNTAX DisplayString
    MAX-ACCESS accessible-for-notify
    STATUS current
    DESCRIPTION
        "Parameter 'result' in event PPP.28"
    ::= { pppEventObjects28 5 }

pppEventObjects29 OBJECT-IDENTITY
    STATUS current
    DESCRIPTION
        "Event PPP.29
        Indicates a request/establishment of an L2TP session."
    ::= { pppEventsGroup 29 }

ppp29_link_name OBJECT-TYPE
    SYNTAX DisplayString
    MAX-ACCESS accessible-for-notify
    STATUS current
    DESCRIPTION
        "Parameter 'link name' in event PPP.29"
    ::= { pppEventObjects29 1 }

ppp29_user OBJECT-TYPE
    SYNTAX DisplayString
    MAX-ACCESS accessible-for-notify
    STATUS current
    DESCRIPTION
        "Parameter 'user' in event PPP.29"
    ::= { pppEventObjects29 2 }

ppp29_action OBJECT-TYPE
    SYNTAX DisplayString
    MAX-ACCESS accessible-for-notify
    STATUS current
    DESCRIPTION
        "Parameter 'action' in event PPP.29"
    ::= { pppEventObjects29 3 }

pppEventObjects30 OBJECT-IDENTITY
    STATUS current
    DESCRIPTION
        "Event PPP.30
        Indicates an unusual situation in Multilink PPP."
    ::= { pppEventsGroup 30 }

ppp30_linkPPP OBJECT-TYPE
    SYNTAX DisplayString
    MAX-ACCESS accessible-for-notify
    STATUS current
    DESCRIPTION
        "Parameter 'linkPPP' in event PPP.30"
    ::= { pppEventObjects30 1 }

ppp30_information_message OBJECT-TYPE
    SYNTAX DisplayString
    MAX-ACCESS accessible-for-notify
    STATUS current
    DESCRIPTION
        "Parameter 'information message' in event PPP.30"
    ::= { pppEventObjects30 2 }

pppEventObjects31 OBJECT-IDENTITY
    STATUS current
    DESCRIPTION
        "Event PPP.31
        BCP packet description."
    ::= { pppEventsGroup 31 }

ppp31_link_name OBJECT-TYPE
    SYNTAX DisplayString
    MAX-ACCESS accessible-for-notify
    STATUS current
    DESCRIPTION
        "Parameter 'link name' in event PPP.31"
    ::= { pppEventObjects31 1 }

ppp31_direction OBJECT-TYPE
    SYNTAX DisplayString
    MAX-ACCESS accessible-for-notify
    STATUS current
    DESCRIPTION
        "Parameter 'direction' in event PPP.31"
    ::= { pppEventObjects31 2 }

ppp31_code OBJECT-TYPE
    SYNTAX DisplayString
    MAX-ACCESS accessible-for-notify
    STATUS current
    DESCRIPTION
        "Parameter 'code' in event PPP.31"
    ::= { pppEventObjects31 3 }

ppp31_BCP_state OBJECT-TYPE
    SYNTAX DisplayString
    MAX-ACCESS accessible-for-notify
    STATUS current
    DESCRIPTION
        "Parameter 'BCP state' in event PPP.31"
    ::= { pppEventObjects31 4 }

ppp31_identifier OBJECT-TYPE
    SYNTAX Integer32
    MAX-ACCESS accessible-for-notify
    STATUS current
    DESCRIPTION
        "Parameter 'identifier' in event PPP.31"
    ::= { pppEventObjects31 5 }

ppp31_length OBJECT-TYPE
    SYNTAX Integer32
    MAX-ACCESS accessible-for-notify
    STATUS current
    DESCRIPTION
        "Parameter 'length' in event PPP.31"
    ::= { pppEventObjects31 6 }

pppEventObjects32 OBJECT-IDENTITY
    STATUS current
    DESCRIPTION
        "Event PPP.32
        BCP Bridge ID option"
    ::= { pppEventsGroup 32 }

ppp32_link_name OBJECT-TYPE
    SYNTAX DisplayString
    MAX-ACCESS accessible-for-notify
    STATUS current
    DESCRIPTION
        "Parameter 'link name' in event PPP.32"
    ::= { pppEventObjects32 1 }

ppp32_id OBJECT-TYPE
    SYNTAX Integer32
    MAX-ACCESS accessible-for-notify
    STATUS current
    DESCRIPTION
        "Parameter 'id' in event PPP.32"
    ::= { pppEventObjects32 2 }

ppp32_dump OBJECT-TYPE
    SYNTAX DisplayString
    MAX-ACCESS accessible-for-notify
    STATUS current
    DESCRIPTION
        "Parameter 'dump' in event PPP.32"
    ::= { pppEventObjects32 3 }

pppEventObjects33 OBJECT-IDENTITY
    STATUS current
    DESCRIPTION
        "Event PPP.33
        BCP Line ID option."
    ::= { pppEventsGroup 33 }

ppp33_link_name OBJECT-TYPE
    SYNTAX DisplayString
    MAX-ACCESS accessible-for-notify
    STATUS current
    DESCRIPTION
        "Parameter 'link name' in event PPP.33"
    ::= { pppEventObjects33 1 }

ppp33_id OBJECT-TYPE
    SYNTAX Integer32
    MAX-ACCESS accessible-for-notify
    STATUS current
    DESCRIPTION
        "Parameter 'id' in event PPP.33"
    ::= { pppEventObjects33 2 }

ppp33_dump OBJECT-TYPE
    SYNTAX DisplayString
    MAX-ACCESS accessible-for-notify
    STATUS current
    DESCRIPTION
        "Parameter 'dump' in event PPP.33"
    ::= { pppEventObjects33 3 }

pppEventObjects34 OBJECT-IDENTITY
    STATUS current
    DESCRIPTION
        "Event PPP.34
        BCP MAC Support option."
    ::= { pppEventsGroup 34 }

ppp34_link_name OBJECT-TYPE
    SYNTAX DisplayString
    MAX-ACCESS accessible-for-notify
    STATUS current
    DESCRIPTION
        "Parameter 'link name' in event PPP.34"
    ::= { pppEventObjects34 1 }

ppp34_maccode OBJECT-TYPE
    SYNTAX Integer32
    MAX-ACCESS accessible-for-notify
    STATUS current
    DESCRIPTION
        "Parameter 'maccode' in event PPP.34"
    ::= { pppEventObjects34 2 }

ppp34_macname OBJECT-TYPE
    SYNTAX DisplayString
    MAX-ACCESS accessible-for-notify
    STATUS current
    DESCRIPTION
        "Parameter 'macname' in event PPP.34"
    ::= { pppEventObjects34 3 }

ppp34_dump OBJECT-TYPE
    SYNTAX DisplayString
    MAX-ACCESS accessible-for-notify
    STATUS current
    DESCRIPTION
        "Parameter 'dump' in event PPP.34"
    ::= { pppEventObjects34 4 }

pppEventObjects35 OBJECT-IDENTITY
    STATUS current
    DESCRIPTION
        "Event PPP.35
        BCP Tinygram compression option."
    ::= { pppEventsGroup 35 }

ppp35_link_name OBJECT-TYPE
    SYNTAX DisplayString
    MAX-ACCESS accessible-for-notify
    STATUS current
    DESCRIPTION
        "Parameter 'link name' in event PPP.35"
    ::= { pppEventObjects35 1 }

ppp35_comp OBJECT-TYPE
    SYNTAX DisplayString
    MAX-ACCESS accessible-for-notify
    STATUS current
    DESCRIPTION
        "Parameter 'comp' in event PPP.35"
    ::= { pppEventObjects35 2 }

ppp35_dump OBJECT-TYPE
    SYNTAX DisplayString
    MAX-ACCESS accessible-for-notify
    STATUS current
    DESCRIPTION
        "Parameter 'dump' in event PPP.35"
    ::= { pppEventObjects35 3 }

pppEventObjects36 OBJECT-IDENTITY
    STATUS current
    DESCRIPTION
        "Event PPP.36
        BCP LAN Identification option."
    ::= { pppEventsGroup 36 }

ppp36_link_name OBJECT-TYPE
    SYNTAX DisplayString
    MAX-ACCESS accessible-for-notify
    STATUS current
    DESCRIPTION
        "Parameter 'link name' in event PPP.36"
    ::= { pppEventObjects36 1 }

ppp36_lanid OBJECT-TYPE
    SYNTAX DisplayString
    MAX-ACCESS accessible-for-notify
    STATUS current
    DESCRIPTION
        "Parameter 'lanid' in event PPP.36"
    ::= { pppEventObjects36 2 }

ppp36_dump OBJECT-TYPE
    SYNTAX DisplayString
    MAX-ACCESS accessible-for-notify
    STATUS current
    DESCRIPTION
        "Parameter 'dump' in event PPP.36"
    ::= { pppEventObjects36 3 }

pppEventObjects37 OBJECT-IDENTITY
    STATUS current
    DESCRIPTION
        "Event PPP.37
        BCP MAC Address option."
    ::= { pppEventsGroup 37 }

ppp37_link_name OBJECT-TYPE
    SYNTAX DisplayString
    MAX-ACCESS accessible-for-notify
    STATUS current
    DESCRIPTION
        "Parameter 'link name' in event PPP.37"
    ::= { pppEventObjects37 1 }

ppp37_macaddr OBJECT-TYPE
    SYNTAX DisplayString
    MAX-ACCESS accessible-for-notify
    STATUS current
    DESCRIPTION
        "Parameter 'macaddr' in event PPP.37"
    ::= { pppEventObjects37 2 }

ppp37_dump OBJECT-TYPE
    SYNTAX DisplayString
    MAX-ACCESS accessible-for-notify
    STATUS current
    DESCRIPTION
        "Parameter 'dump' in event PPP.37"
    ::= { pppEventObjects37 3 }

pppEventObjects38 OBJECT-IDENTITY
    STATUS current
    DESCRIPTION
        "Event PPP.38
        BCP Old Spanning Tree Protocol option."
    ::= { pppEventsGroup 38 }

ppp38_link_name OBJECT-TYPE
    SYNTAX DisplayString
    MAX-ACCESS accessible-for-notify
    STATUS current
    DESCRIPTION
        "Parameter 'link name' in event PPP.38"
    ::= { pppEventObjects38 1 }

ppp38_oldstp OBJECT-TYPE
    SYNTAX DisplayString
    MAX-ACCESS accessible-for-notify
    STATUS current
    DESCRIPTION
        "Parameter 'oldstp' in event PPP.38"
    ::= { pppEventObjects38 2 }

ppp38_dump OBJECT-TYPE
    SYNTAX DisplayString
    MAX-ACCESS accessible-for-notify
    STATUS current
    DESCRIPTION
        "Parameter 'dump' in event PPP.38"
    ::= { pppEventObjects38 3 }

pppEventObjects39 OBJECT-IDENTITY
    STATUS current
    DESCRIPTION
        "Event PPP.39
        BCP Tagged Frame option."
    ::= { pppEventsGroup 39 }

ppp39_link_name OBJECT-TYPE
    SYNTAX DisplayString
    MAX-ACCESS accessible-for-notify
    STATUS current
    DESCRIPTION
        "Parameter 'link name' in event PPP.39"
    ::= { pppEventObjects39 1 }

ppp39_tagged OBJECT-TYPE
    SYNTAX DisplayString
    MAX-ACCESS accessible-for-notify
    STATUS current
    DESCRIPTION
        "Parameter 'tagged' in event PPP.39"
    ::= { pppEventObjects39 2 }

ppp39_dump OBJECT-TYPE
    SYNTAX DisplayString
    MAX-ACCESS accessible-for-notify
    STATUS current
    DESCRIPTION
        "Parameter 'dump' in event PPP.39"
    ::= { pppEventObjects39 3 }

pppEventObjects40 OBJECT-IDENTITY
    STATUS current
    DESCRIPTION
        "Event PPP.40
        BCP Management Inline support option."
    ::= { pppEventsGroup 40 }

ppp40_link_name OBJECT-TYPE
    SYNTAX DisplayString
    MAX-ACCESS accessible-for-notify
    STATUS current
    DESCRIPTION
        "Parameter 'link name' in event PPP.40"
    ::= { pppEventObjects40 1 }

ppp40_dump OBJECT-TYPE
    SYNTAX DisplayString
    MAX-ACCESS accessible-for-notify
    STATUS current
    DESCRIPTION
        "Parameter 'dump' in event PPP.40"
    ::= { pppEventObjects40 2 }

pppEventObjects41 OBJECT-IDENTITY
    STATUS current
    DESCRIPTION
        "Event PPP.41
        BCP unknown option."
    ::= { pppEventsGroup 41 }

ppp41_link_name OBJECT-TYPE
    SYNTAX DisplayString
    MAX-ACCESS accessible-for-notify
    STATUS current
    DESCRIPTION
        "Parameter 'link name' in event PPP.41"
    ::= { pppEventObjects41 1 }

ppp41_dump OBJECT-TYPE
    SYNTAX DisplayString
    MAX-ACCESS accessible-for-notify
    STATUS current
    DESCRIPTION
        "Parameter 'dump' in event PPP.41"
    ::= { pppEventObjects41 2 }

pppEventObjects42 OBJECT-IDENTITY
    STATUS current
    DESCRIPTION
        "Event PPP.42
        BCP information trace."
    ::= { pppEventsGroup 42 }

ppp42_link_name OBJECT-TYPE
    SYNTAX DisplayString
    MAX-ACCESS accessible-for-notify
    STATUS current
    DESCRIPTION
        "Parameter 'link name' in event PPP.42"
    ::= { pppEventObjects42 1 }

ppp42_information OBJECT-TYPE
    SYNTAX DisplayString
    MAX-ACCESS accessible-for-notify
    STATUS current
    DESCRIPTION
        "Parameter 'information' in event PPP.42"
    ::= { pppEventObjects42 2 }

pppEventObjects43 OBJECT-IDENTITY
    STATUS current
    DESCRIPTION
        "Event PPP.43
        A frame was received of a bridge type defined in RFC 2878.
        However, since bridging has not been enabled on this circuit, frame
        is being discarded."
    ::= { pppEventsGroup 43 }

ppp43_link_name OBJECT-TYPE
    SYNTAX DisplayString
    MAX-ACCESS accessible-for-notify
    STATUS current
    DESCRIPTION
        "Parameter 'link name' in event PPP.43"
    ::= { pppEventObjects43 1 }

pppEventObjects44 OBJECT-IDENTITY
    STATUS current
    DESCRIPTION
        "Event PPP.44
        A bridge frame is being discarded as a bridge port is not in
        forwarding state."
    ::= { pppEventsGroup 44 }

ppp44_link_name OBJECT-TYPE
    SYNTAX DisplayString
    MAX-ACCESS accessible-for-notify
    STATUS current
    DESCRIPTION
        "Parameter 'link name' in event PPP.44"
    ::= { pppEventObjects44 1 }

pppEventObjects45 OBJECT-IDENTITY
    STATUS current
    DESCRIPTION
        "Event PPP.45
        A bridged frame has been received and is being discarded due to mismatch
        in the frame type versus the bridge port behavior."
    ::= { pppEventsGroup 45 }

ppp45_link_name OBJECT-TYPE
    SYNTAX DisplayString
    MAX-ACCESS accessible-for-notify
    STATUS current
    DESCRIPTION
        "Parameter 'link name' in event PPP.45"
    ::= { pppEventObjects45 1 }

ppp45_source_mac OBJECT-TYPE
    SYNTAX DisplayString
    MAX-ACCESS accessible-for-notify
    STATUS current
    DESCRIPTION
        "Parameter 'source_mac' in event PPP.45"
    ::= { pppEventObjects45 2 }

ppp45_dest_mac OBJECT-TYPE
    SYNTAX DisplayString
    MAX-ACCESS accessible-for-notify
    STATUS current
    DESCRIPTION
        "Parameter 'dest_mac' in event PPP.45"
    ::= { pppEventObjects45 3 }

pppEventObjects46 OBJECT-IDENTITY
    STATUS current
    DESCRIPTION
        "Event PPP.46
        An unsupported bridge frame type has been encountered."
    ::= { pppEventsGroup 46 }

ppp46_link_name OBJECT-TYPE
    SYNTAX DisplayString
    MAX-ACCESS accessible-for-notify
    STATUS current
    DESCRIPTION
        "Parameter 'link name' in event PPP.46"
    ::= { pppEventObjects46 1 }

ppp46_type OBJECT-TYPE
    SYNTAX Integer32
    MAX-ACCESS accessible-for-notify
    STATUS current
    DESCRIPTION
        "Parameter 'type' in event PPP.46"
    ::= { pppEventObjects46 2 }

pppEventObjects49 OBJECT-IDENTITY
    STATUS current
    DESCRIPTION
        "Event PPP.49
        Unsupported LCP option description."
    ::= { pppEventsGroup 49 }

ppp49_link_name OBJECT-TYPE
    SYNTAX DisplayString
    MAX-ACCESS accessible-for-notify
    STATUS current
    DESCRIPTION
        "Parameter 'link name' in event PPP.49"
    ::= { pppEventObjects49 1 }

ppp49_option OBJECT-TYPE
    SYNTAX DisplayString
    MAX-ACCESS accessible-for-notify
    STATUS current
    DESCRIPTION
        "Parameter 'option' in event PPP.49"
    ::= { pppEventObjects49 2 }

ppp49_dump OBJECT-TYPE
    SYNTAX DisplayString
    MAX-ACCESS accessible-for-notify
    STATUS current
    DESCRIPTION
        "Parameter 'dump' in event PPP.49"
    ::= { pppEventObjects49 3 }

pppEventObjects50 OBJECT-IDENTITY
    STATUS current
    DESCRIPTION
        "Event PPP.50
        LCP packet data."
    ::= { pppEventsGroup 50 }

ppp50_link_name OBJECT-TYPE
    SYNTAX DisplayString
    MAX-ACCESS accessible-for-notify
    STATUS current
    DESCRIPTION
        "Parameter 'link name' in event PPP.50"
    ::= { pppEventObjects50 1 }

ppp50_dump OBJECT-TYPE
    SYNTAX DisplayString
    MAX-ACCESS accessible-for-notify
    STATUS current
    DESCRIPTION
        "Parameter 'dump' in event PPP.50"
    ::= { pppEventObjects50 2 }

pppEventObjects51 OBJECT-IDENTITY
    STATUS current
    DESCRIPTION
        "Event PPP.51
        LCP packet description."
    ::= { pppEventsGroup 51 }

ppp51_link_name OBJECT-TYPE
    SYNTAX DisplayString
    MAX-ACCESS accessible-for-notify
    STATUS current
    DESCRIPTION
        "Parameter 'link name' in event PPP.51"
    ::= { pppEventObjects51 1 }

ppp51_direction OBJECT-TYPE
    SYNTAX DisplayString
    MAX-ACCESS accessible-for-notify
    STATUS current
    DESCRIPTION
        "Parameter 'direction' in event PPP.51"
    ::= { pppEventObjects51 2 }

ppp51_code OBJECT-TYPE
    SYNTAX DisplayString
    MAX-ACCESS accessible-for-notify
    STATUS current
    DESCRIPTION
        "Parameter 'code' in event PPP.51"
    ::= { pppEventObjects51 3 }

ppp51_LCP_state OBJECT-TYPE
    SYNTAX DisplayString
    MAX-ACCESS accessible-for-notify
    STATUS current
    DESCRIPTION
        "Parameter 'LCP state' in event PPP.51"
    ::= { pppEventObjects51 4 }

ppp51_identifier OBJECT-TYPE
    SYNTAX Integer32
    MAX-ACCESS accessible-for-notify
    STATUS current
    DESCRIPTION
        "Parameter 'identifier' in event PPP.51"
    ::= { pppEventObjects51 5 }

ppp51_length OBJECT-TYPE
    SYNTAX Integer32
    MAX-ACCESS accessible-for-notify
    STATUS current
    DESCRIPTION
        "Parameter 'length' in event PPP.51"
    ::= { pppEventObjects51 6 }

pppEventObjects52 OBJECT-IDENTITY
    STATUS current
    DESCRIPTION
        "Event PPP.52
        MRU option description."
    ::= { pppEventsGroup 52 }

ppp52_link_name OBJECT-TYPE
    SYNTAX DisplayString
    MAX-ACCESS accessible-for-notify
    STATUS current
    DESCRIPTION
        "Parameter 'link name' in event PPP.52"
    ::= { pppEventObjects52 1 }

ppp52_mru OBJECT-TYPE
    SYNTAX Integer32
    MAX-ACCESS accessible-for-notify
    STATUS current
    DESCRIPTION
        "Parameter 'mru' in event PPP.52"
    ::= { pppEventObjects52 2 }

ppp52_dump OBJECT-TYPE
    SYNTAX DisplayString
    MAX-ACCESS accessible-for-notify
    STATUS current
    DESCRIPTION
        "Parameter 'dump' in event PPP.52"
    ::= { pppEventObjects52 3 }

pppEventObjects53 OBJECT-IDENTITY
    STATUS current
    DESCRIPTION
        "Event PPP.53
        Asynchronous Control Character Map (ACCM) option description."
    ::= { pppEventsGroup 53 }

ppp53_link_name OBJECT-TYPE
    SYNTAX DisplayString
    MAX-ACCESS accessible-for-notify
    STATUS current
    DESCRIPTION
        "Parameter 'link name' in event PPP.53"
    ::= { pppEventObjects53 1 }

ppp53_async_map OBJECT-TYPE
    SYNTAX Integer32
    MAX-ACCESS accessible-for-notify
    STATUS current
    DESCRIPTION
        "Parameter 'async. map' in event PPP.53"
    ::= { pppEventObjects53 2 }

ppp53_dump OBJECT-TYPE
    SYNTAX DisplayString
    MAX-ACCESS accessible-for-notify
    STATUS current
    DESCRIPTION
        "Parameter 'dump' in event PPP.53"
    ::= { pppEventObjects53 3 }

pppEventObjects54 OBJECT-IDENTITY
    STATUS current
    DESCRIPTION
        "Event PPP.54
        Authentication option description."
    ::= { pppEventsGroup 54 }

ppp54_link_name OBJECT-TYPE
    SYNTAX DisplayString
    MAX-ACCESS accessible-for-notify
    STATUS current
    DESCRIPTION
        "Parameter 'link name' in event PPP.54"
    ::= { pppEventObjects54 1 }

ppp54_auth_protocol OBJECT-TYPE
    SYNTAX DisplayString
    MAX-ACCESS accessible-for-notify
    STATUS current
    DESCRIPTION
        "Parameter 'auth. protocol' in event PPP.54"
    ::= { pppEventObjects54 2 }

ppp54_dump OBJECT-TYPE
    SYNTAX DisplayString
    MAX-ACCESS accessible-for-notify
    STATUS current
    DESCRIPTION
        "Parameter 'dump' in event PPP.54"
    ::= { pppEventObjects54 3 }

pppEventObjects55 OBJECT-IDENTITY
    STATUS current
    DESCRIPTION
        "Event PPP.55
        Magic Number option description."
    ::= { pppEventsGroup 55 }

ppp55_link_name OBJECT-TYPE
    SYNTAX DisplayString
    MAX-ACCESS accessible-for-notify
    STATUS current
    DESCRIPTION
        "Parameter 'link name' in event PPP.55"
    ::= { pppEventObjects55 1 }

ppp55_magic_number OBJECT-TYPE
    SYNTAX Integer32
    MAX-ACCESS accessible-for-notify
    STATUS current
    DESCRIPTION
        "Parameter 'magic number' in event PPP.55"
    ::= { pppEventObjects55 2 }

ppp55_dump OBJECT-TYPE
    SYNTAX DisplayString
    MAX-ACCESS accessible-for-notify
    STATUS current
    DESCRIPTION
        "Parameter 'dump' in event PPP.55"
    ::= { pppEventObjects55 3 }

pppEventObjects56 OBJECT-IDENTITY
    STATUS current
    DESCRIPTION
        "Event PPP.56
        Protocol Field Compression option description."
    ::= { pppEventsGroup 56 }

ppp56_link_name OBJECT-TYPE
    SYNTAX DisplayString
    MAX-ACCESS accessible-for-notify
    STATUS current
    DESCRIPTION
        "Parameter 'link name' in event PPP.56"
    ::= { pppEventObjects56 1 }

ppp56_dump OBJECT-TYPE
    SYNTAX DisplayString
    MAX-ACCESS accessible-for-notify
    STATUS current
    DESCRIPTION
        "Parameter 'dump' in event PPP.56"
    ::= { pppEventObjects56 2 }

pppEventObjects57 OBJECT-IDENTITY
    STATUS current
    DESCRIPTION
        "Event PPP.57
        Address/Control Fields Compression option description."
    ::= { pppEventsGroup 57 }

ppp57_link_name OBJECT-TYPE
    SYNTAX DisplayString
    MAX-ACCESS accessible-for-notify
    STATUS current
    DESCRIPTION
        "Parameter 'link name' in event PPP.57"
    ::= { pppEventObjects57 1 }

ppp57_dump OBJECT-TYPE
    SYNTAX DisplayString
    MAX-ACCESS accessible-for-notify
    STATUS current
    DESCRIPTION
        "Parameter 'dump' in event PPP.57"
    ::= { pppEventObjects57 2 }

pppEventObjects58 OBJECT-IDENTITY
    STATUS current
    DESCRIPTION
        "Event PPP.58
        MRRU option description."
    ::= { pppEventsGroup 58 }

ppp58_link_name OBJECT-TYPE
    SYNTAX DisplayString
    MAX-ACCESS accessible-for-notify
    STATUS current
    DESCRIPTION
        "Parameter 'link name' in event PPP.58"
    ::= { pppEventObjects58 1 }

ppp58_mrru OBJECT-TYPE
    SYNTAX Integer32
    MAX-ACCESS accessible-for-notify
    STATUS current
    DESCRIPTION
        "Parameter 'mrru' in event PPP.58"
    ::= { pppEventObjects58 2 }

ppp58_dump OBJECT-TYPE
    SYNTAX DisplayString
    MAX-ACCESS accessible-for-notify
    STATUS current
    DESCRIPTION
        "Parameter 'dump' in event PPP.58"
    ::= { pppEventObjects58 3 }

pppEventObjects59 OBJECT-IDENTITY
    STATUS current
    DESCRIPTION
        "Event PPP.59
        Short Sequence Number header format option description."
    ::= { pppEventsGroup 59 }

ppp59_link_name OBJECT-TYPE
    SYNTAX DisplayString
    MAX-ACCESS accessible-for-notify
    STATUS current
    DESCRIPTION
        "Parameter 'link name' in event PPP.59"
    ::= { pppEventObjects59 1 }

ppp59_dump OBJECT-TYPE
    SYNTAX DisplayString
    MAX-ACCESS accessible-for-notify
    STATUS current
    DESCRIPTION
        "Parameter 'dump' in event PPP.59"
    ::= { pppEventObjects59 2 }

pppEventObjects60 OBJECT-IDENTITY
    STATUS current
    DESCRIPTION
        "Event PPP.60
        End-Point Discriminator option description."
    ::= { pppEventsGroup 60 }

ppp60_link_name OBJECT-TYPE
    SYNTAX DisplayString
    MAX-ACCESS accessible-for-notify
    STATUS current
    DESCRIPTION
        "Parameter 'link name' in event PPP.60"
    ::= { pppEventObjects60 1 }

ppp60_class OBJECT-TYPE
    SYNTAX Integer32
    MAX-ACCESS accessible-for-notify
    STATUS current
    DESCRIPTION
        "Parameter 'class' in event PPP.60"
    ::= { pppEventObjects60 2 }

ppp60_dump OBJECT-TYPE
    SYNTAX DisplayString
    MAX-ACCESS accessible-for-notify
    STATUS current
    DESCRIPTION
        "Parameter 'dump' in event PPP.60"
    ::= { pppEventObjects60 3 }

pppEventObjects61 OBJECT-IDENTITY
    STATUS current
    DESCRIPTION
        "Event PPP.61
        Unknown option description."
    ::= { pppEventsGroup 61 }

ppp61_link_name OBJECT-TYPE
    SYNTAX DisplayString
    MAX-ACCESS accessible-for-notify
    STATUS current
    DESCRIPTION
        "Parameter 'link name' in event PPP.61"
    ::= { pppEventObjects61 1 }

ppp61_dump OBJECT-TYPE
    SYNTAX DisplayString
    MAX-ACCESS accessible-for-notify
    STATUS current
    DESCRIPTION
        "Parameter 'dump' in event PPP.61"
    ::= { pppEventObjects61 2 }

pppEventObjects62 OBJECT-IDENTITY
    STATUS current
    DESCRIPTION
        "Event PPP.62
        Bad format option description."
    ::= { pppEventsGroup 62 }

ppp62_link_name OBJECT-TYPE
    SYNTAX DisplayString
    MAX-ACCESS accessible-for-notify
    STATUS current
    DESCRIPTION
        "Parameter 'link name' in event PPP.62"
    ::= { pppEventObjects62 1 }

ppp62_dump OBJECT-TYPE
    SYNTAX DisplayString
    MAX-ACCESS accessible-for-notify
    STATUS current
    DESCRIPTION
        "Parameter 'dump' in event PPP.62"
    ::= { pppEventObjects62 2 }

pppEventObjects63 OBJECT-IDENTITY
    STATUS current
    DESCRIPTION
        "Event PPP.63
        PAP packet description."
    ::= { pppEventsGroup 63 }

ppp63_link_name OBJECT-TYPE
    SYNTAX DisplayString
    MAX-ACCESS accessible-for-notify
    STATUS current
    DESCRIPTION
        "Parameter 'link name' in event PPP.63"
    ::= { pppEventObjects63 1 }

ppp63_direction OBJECT-TYPE
    SYNTAX DisplayString
    MAX-ACCESS accessible-for-notify
    STATUS current
    DESCRIPTION
        "Parameter 'direction' in event PPP.63"
    ::= { pppEventObjects63 2 }

ppp63_code OBJECT-TYPE
    SYNTAX DisplayString
    MAX-ACCESS accessible-for-notify
    STATUS current
    DESCRIPTION
        "Parameter 'code' in event PPP.63"
    ::= { pppEventObjects63 3 }

ppp63_PAP_state OBJECT-TYPE
    SYNTAX DisplayString
    MAX-ACCESS accessible-for-notify
    STATUS current
    DESCRIPTION
        "Parameter 'PAP state' in event PPP.63"
    ::= { pppEventObjects63 4 }

ppp63_identifier OBJECT-TYPE
    SYNTAX Integer32
    MAX-ACCESS accessible-for-notify
    STATUS current
    DESCRIPTION
        "Parameter 'identifier' in event PPP.63"
    ::= { pppEventObjects63 5 }

ppp63_length OBJECT-TYPE
    SYNTAX Integer32
    MAX-ACCESS accessible-for-notify
    STATUS current
    DESCRIPTION
        "Parameter 'length' in event PPP.63"
    ::= { pppEventObjects63 6 }

pppEventObjects64 OBJECT-IDENTITY
    STATUS current
    DESCRIPTION
        "Event PPP.64
        PAP request peer-id."
    ::= { pppEventsGroup 64 }

ppp64_link_name OBJECT-TYPE
    SYNTAX DisplayString
    MAX-ACCESS accessible-for-notify
    STATUS current
    DESCRIPTION
        "Parameter 'link name' in event PPP.64"
    ::= { pppEventObjects64 1 }

ppp64_peer-id OBJECT-TYPE
    SYNTAX DisplayString
    MAX-ACCESS accessible-for-notify
    STATUS current
    DESCRIPTION
        "Parameter 'peer-id' in event PPP.64"
    ::= { pppEventObjects64 2 }

pppEventObjects65 OBJECT-IDENTITY
    STATUS current
    DESCRIPTION
        "Event PPP.65
        PAP request password."
    ::= { pppEventsGroup 65 }

ppp65_link_name OBJECT-TYPE
    SYNTAX DisplayString
    MAX-ACCESS accessible-for-notify
    STATUS current
    DESCRIPTION
        "Parameter 'link name' in event PPP.65"
    ::= { pppEventObjects65 1 }

ppp65_password OBJECT-TYPE
    SYNTAX DisplayString
    MAX-ACCESS accessible-for-notify
    STATUS current
    DESCRIPTION
        "Parameter 'password' in event PPP.65"
    ::= { pppEventObjects65 2 }

pppEventObjects66 OBJECT-IDENTITY
    STATUS current
    DESCRIPTION
        "Event PPP.66
        PAP reply message."
    ::= { pppEventsGroup 66 }

ppp66_link__name OBJECT-TYPE
    SYNTAX DisplayString
    MAX-ACCESS accessible-for-notify
    STATUS current
    DESCRIPTION
        "Parameter 'link  name' in event PPP.66"
    ::= { pppEventObjects66 1 }

ppp66_message OBJECT-TYPE
    SYNTAX DisplayString
    MAX-ACCESS accessible-for-notify
    STATUS current
    DESCRIPTION
        "Parameter 'message' in event PPP.66"
    ::= { pppEventObjects66 2 }

pppEventObjects67 OBJECT-IDENTITY
    STATUS current
    DESCRIPTION
        "Event PPP.67
        CHAP packet description."
    ::= { pppEventsGroup 67 }

ppp67_link_name OBJECT-TYPE
    SYNTAX DisplayString
    MAX-ACCESS accessible-for-notify
    STATUS current
    DESCRIPTION
        "Parameter 'link name' in event PPP.67"
    ::= { pppEventObjects67 1 }

ppp67_direction OBJECT-TYPE
    SYNTAX DisplayString
    MAX-ACCESS accessible-for-notify
    STATUS current
    DESCRIPTION
        "Parameter 'direction' in event PPP.67"
    ::= { pppEventObjects67 2 }

ppp67_code OBJECT-TYPE
    SYNTAX DisplayString
    MAX-ACCESS accessible-for-notify
    STATUS current
    DESCRIPTION
        "Parameter 'code' in event PPP.67"
    ::= { pppEventObjects67 3 }

ppp67_CHAP_state OBJECT-TYPE
    SYNTAX DisplayString
    MAX-ACCESS accessible-for-notify
    STATUS current
    DESCRIPTION
        "Parameter 'CHAP state' in event PPP.67"
    ::= { pppEventObjects67 4 }

ppp67_identifier OBJECT-TYPE
    SYNTAX Integer32
    MAX-ACCESS accessible-for-notify
    STATUS current
    DESCRIPTION
        "Parameter 'identifier' in event PPP.67"
    ::= { pppEventObjects67 5 }

ppp67_length OBJECT-TYPE
    SYNTAX Integer32
    MAX-ACCESS accessible-for-notify
    STATUS current
    DESCRIPTION
        "Parameter 'length' in event PPP.67"
    ::= { pppEventObjects67 6 }

pppEventObjects68 OBJECT-IDENTITY
    STATUS current
    DESCRIPTION
        "Event PPP.68
        CHAP peer name."
    ::= { pppEventsGroup 68 }

ppp68_link_name OBJECT-TYPE
    SYNTAX DisplayString
    MAX-ACCESS accessible-for-notify
    STATUS current
    DESCRIPTION
        "Parameter 'link name' in event PPP.68"
    ::= { pppEventObjects68 1 }

ppp68_peer_name OBJECT-TYPE
    SYNTAX DisplayString
    MAX-ACCESS accessible-for-notify
    STATUS current
    DESCRIPTION
        "Parameter 'peer name' in event PPP.68"
    ::= { pppEventObjects68 2 }

pppEventObjects69 OBJECT-IDENTITY
    STATUS current
    DESCRIPTION
        "Event PPP.69
        CHAP peer message."
    ::= { pppEventsGroup 69 }

ppp69_link_name OBJECT-TYPE
    SYNTAX DisplayString
    MAX-ACCESS accessible-for-notify
    STATUS current
    DESCRIPTION
        "Parameter 'link name' in event PPP.69"
    ::= { pppEventObjects69 1 }

ppp69_peer_message OBJECT-TYPE
    SYNTAX DisplayString
    MAX-ACCESS accessible-for-notify
    STATUS current
    DESCRIPTION
        "Parameter 'peer message' in event PPP.69"
    ::= { pppEventObjects69 2 }

pppEventObjects70 OBJECT-IDENTITY
    STATUS current
    DESCRIPTION
        "Event PPP.70
        CHAP challenge value."
    ::= { pppEventsGroup 70 }

ppp70_link_name OBJECT-TYPE
    SYNTAX DisplayString
    MAX-ACCESS accessible-for-notify
    STATUS current
    DESCRIPTION
        "Parameter 'link name' in event PPP.70"
    ::= { pppEventObjects70 1 }

ppp70_challenge OBJECT-TYPE
    SYNTAX DisplayString
    MAX-ACCESS accessible-for-notify
    STATUS current
    DESCRIPTION
        "Parameter 'challenge' in event PPP.70"
    ::= { pppEventObjects70 2 }

pppEventObjects71 OBJECT-IDENTITY
    STATUS current
    DESCRIPTION
        "Event PPP.71
        CHAP MD5 value."
    ::= { pppEventsGroup 71 }

ppp71_link_name OBJECT-TYPE
    SYNTAX DisplayString
    MAX-ACCESS accessible-for-notify
    STATUS current
    DESCRIPTION
        "Parameter 'link name' in event PPP.71"
    ::= { pppEventObjects71 1 }

ppp71_md5 OBJECT-TYPE
    SYNTAX DisplayString
    MAX-ACCESS accessible-for-notify
    STATUS current
    DESCRIPTION
        "Parameter 'md5' in event PPP.71"
    ::= { pppEventObjects71 2 }

pppEventObjects72 OBJECT-IDENTITY
    STATUS current
    DESCRIPTION
        "Event PPP.72
        IPCP packet description."
    ::= { pppEventsGroup 72 }

ppp72_link_name OBJECT-TYPE
    SYNTAX DisplayString
    MAX-ACCESS accessible-for-notify
    STATUS current
    DESCRIPTION
        "Parameter 'link name' in event PPP.72"
    ::= { pppEventObjects72 1 }

ppp72_direction OBJECT-TYPE
    SYNTAX DisplayString
    MAX-ACCESS accessible-for-notify
    STATUS current
    DESCRIPTION
        "Parameter 'direction' in event PPP.72"
    ::= { pppEventObjects72 2 }

ppp72_code OBJECT-TYPE
    SYNTAX DisplayString
    MAX-ACCESS accessible-for-notify
    STATUS current
    DESCRIPTION
        "Parameter 'code' in event PPP.72"
    ::= { pppEventObjects72 3 }

ppp72_IPCP_state OBJECT-TYPE
    SYNTAX DisplayString
    MAX-ACCESS accessible-for-notify
    STATUS current
    DESCRIPTION
        "Parameter 'IPCP state' in event PPP.72"
    ::= { pppEventObjects72 4 }

ppp72_identifier OBJECT-TYPE
    SYNTAX Integer32
    MAX-ACCESS accessible-for-notify
    STATUS current
    DESCRIPTION
        "Parameter 'identifier' in event PPP.72"
    ::= { pppEventObjects72 5 }

ppp72_length OBJECT-TYPE
    SYNTAX Integer32
    MAX-ACCESS accessible-for-notify
    STATUS current
    DESCRIPTION
        "Parameter 'length' in event PPP.72"
    ::= { pppEventObjects72 6 }

pppEventObjects73 OBJECT-IDENTITY
    STATUS current
    DESCRIPTION
        "Event PPP.73
        IPCP address option."
    ::= { pppEventsGroup 73 }

ppp73_link_name OBJECT-TYPE
    SYNTAX DisplayString
    MAX-ACCESS accessible-for-notify
    STATUS current
    DESCRIPTION
        "Parameter 'link name' in event PPP.73"
    ::= { pppEventObjects73 1 }

ppp73_address OBJECT-TYPE
    SYNTAX IpAddress
    MAX-ACCESS accessible-for-notify
    STATUS current
    DESCRIPTION
        "Parameter 'address' in event PPP.73"
    ::= { pppEventObjects73 2 }

ppp73_dump OBJECT-TYPE
    SYNTAX DisplayString
    MAX-ACCESS accessible-for-notify
    STATUS current
    DESCRIPTION
        "Parameter 'dump' in event PPP.73"
    ::= { pppEventObjects73 3 }

pppEventObjects74 OBJECT-IDENTITY
    STATUS current
    DESCRIPTION
        "Event PPP.74
        IPCP Van-Jacobson compression protocol."
    ::= { pppEventsGroup 74 }

ppp74_link_name OBJECT-TYPE
    SYNTAX DisplayString
    MAX-ACCESS accessible-for-notify
    STATUS current
    DESCRIPTION
        "Parameter 'link name' in event PPP.74"
    ::= { pppEventObjects74 1 }

ppp74_slots OBJECT-TYPE
    SYNTAX Integer32
    MAX-ACCESS accessible-for-notify
    STATUS current
    DESCRIPTION
        "Parameter 'slots' in event PPP.74"
    ::= { pppEventObjects74 2 }

ppp74_compression_flag OBJECT-TYPE
    SYNTAX DisplayString
    MAX-ACCESS accessible-for-notify
    STATUS current
    DESCRIPTION
        "Parameter 'compression flag' in event PPP.74"
    ::= { pppEventObjects74 3 }

ppp74_dump OBJECT-TYPE
    SYNTAX DisplayString
    MAX-ACCESS accessible-for-notify
    STATUS current
    DESCRIPTION
        "Parameter 'dump' in event PPP.74"
    ::= { pppEventObjects74 4 }

pppEventObjects75 OBJECT-IDENTITY
    STATUS current
    DESCRIPTION
        "Event PPP.75
        IPCP unknown compression protocol."
    ::= { pppEventsGroup 75 }

ppp75_link_name OBJECT-TYPE
    SYNTAX DisplayString
    MAX-ACCESS accessible-for-notify
    STATUS current
    DESCRIPTION
        "Parameter 'link name' in event PPP.75"
    ::= { pppEventObjects75 1 }

ppp75_dump OBJECT-TYPE
    SYNTAX DisplayString
    MAX-ACCESS accessible-for-notify
    STATUS current
    DESCRIPTION
        "Parameter 'dump' in event PPP.75"
    ::= { pppEventObjects75 2 }

pppEventObjects76 OBJECT-IDENTITY
    STATUS current
    DESCRIPTION
        "Event PPP.76
        IPCP unknown option."
    ::= { pppEventsGroup 76 }

ppp76_link_name OBJECT-TYPE
    SYNTAX DisplayString
    MAX-ACCESS accessible-for-notify
    STATUS current
    DESCRIPTION
        "Parameter 'link name' in event PPP.76"
    ::= { pppEventObjects76 1 }

ppp76_dump OBJECT-TYPE
    SYNTAX DisplayString
    MAX-ACCESS accessible-for-notify
    STATUS current
    DESCRIPTION
        "Parameter 'dump' in event PPP.76"
    ::= { pppEventObjects76 2 }

pppEventObjects77 OBJECT-IDENTITY
    STATUS current
    DESCRIPTION
        "Event PPP.77
        CCP packet description."
    ::= { pppEventsGroup 77 }

ppp77_link_name OBJECT-TYPE
    SYNTAX DisplayString
    MAX-ACCESS accessible-for-notify
    STATUS current
    DESCRIPTION
        "Parameter 'link name' in event PPP.77"
    ::= { pppEventObjects77 1 }

ppp77_direction OBJECT-TYPE
    SYNTAX DisplayString
    MAX-ACCESS accessible-for-notify
    STATUS current
    DESCRIPTION
        "Parameter 'direction' in event PPP.77"
    ::= { pppEventObjects77 2 }

ppp77_code OBJECT-TYPE
    SYNTAX DisplayString
    MAX-ACCESS accessible-for-notify
    STATUS current
    DESCRIPTION
        "Parameter 'code' in event PPP.77"
    ::= { pppEventObjects77 3 }

ppp77_CCP_state OBJECT-TYPE
    SYNTAX DisplayString
    MAX-ACCESS accessible-for-notify
    STATUS current
    DESCRIPTION
        "Parameter 'CCP state' in event PPP.77"
    ::= { pppEventObjects77 4 }

ppp77_identifier OBJECT-TYPE
    SYNTAX Integer32
    MAX-ACCESS accessible-for-notify
    STATUS current
    DESCRIPTION
        "Parameter 'identifier' in event PPP.77"
    ::= { pppEventObjects77 5 }

ppp77_length OBJECT-TYPE
    SYNTAX Integer32
    MAX-ACCESS accessible-for-notify
    STATUS current
    DESCRIPTION
        "Parameter 'length' in event PPP.77"
    ::= { pppEventObjects77 6 }

pppEventObjects78 OBJECT-IDENTITY
    STATUS current
    DESCRIPTION
        "Event PPP.78
        LZS-DCP compression option."
    ::= { pppEventsGroup 78 }

ppp78_link_name OBJECT-TYPE
    SYNTAX DisplayString
    MAX-ACCESS accessible-for-notify
    STATUS current
    DESCRIPTION
        "Parameter 'link name' in event PPP.78"
    ::= { pppEventObjects78 1 }

ppp78_dump OBJECT-TYPE
    SYNTAX DisplayString
    MAX-ACCESS accessible-for-notify
    STATUS current
    DESCRIPTION
        "Parameter 'dump' in event PPP.78"
    ::= { pppEventObjects78 2 }

pppEventObjects79 OBJECT-IDENTITY
    STATUS current
    DESCRIPTION
        "Event PPP.79
        Stac LZS compression option."
    ::= { pppEventsGroup 79 }

ppp79_link_name OBJECT-TYPE
    SYNTAX DisplayString
    MAX-ACCESS accessible-for-notify
    STATUS current
    DESCRIPTION
        "Parameter 'link name' in event PPP.79"
    ::= { pppEventObjects79 1 }

ppp79_dump OBJECT-TYPE
    SYNTAX DisplayString
    MAX-ACCESS accessible-for-notify
    STATUS current
    DESCRIPTION
        "Parameter 'dump' in event PPP.79"
    ::= { pppEventObjects79 2 }

pppEventObjects80 OBJECT-IDENTITY
    STATUS current
    DESCRIPTION
        "Event PPP.80
        History number parameter."
    ::= { pppEventsGroup 80 }

ppp80_link_name OBJECT-TYPE
    SYNTAX DisplayString
    MAX-ACCESS accessible-for-notify
    STATUS current
    DESCRIPTION
        "Parameter 'link name' in event PPP.80"
    ::= { pppEventObjects80 1 }

ppp80_histories OBJECT-TYPE
    SYNTAX Integer32
    MAX-ACCESS accessible-for-notify
    STATUS current
    DESCRIPTION
        "Parameter 'histories' in event PPP.80"
    ::= { pppEventObjects80 2 }

pppEventObjects81 OBJECT-IDENTITY
    STATUS current
    DESCRIPTION
        "Event PPP.81
        Check mode parameter."
    ::= { pppEventsGroup 81 }

ppp81_link_name OBJECT-TYPE
    SYNTAX DisplayString
    MAX-ACCESS accessible-for-notify
    STATUS current
    DESCRIPTION
        "Parameter 'link name' in event PPP.81"
    ::= { pppEventObjects81 1 }

ppp81_check_mode OBJECT-TYPE
    SYNTAX DisplayString
    MAX-ACCESS accessible-for-notify
    STATUS current
    DESCRIPTION
        "Parameter 'check mode' in event PPP.81"
    ::= { pppEventObjects81 2 }

pppEventObjects82 OBJECT-IDENTITY
    STATUS current
    DESCRIPTION
        "Event PPP.82
        Process mode parameter."
    ::= { pppEventsGroup 82 }

ppp82_link_name OBJECT-TYPE
    SYNTAX DisplayString
    MAX-ACCESS accessible-for-notify
    STATUS current
    DESCRIPTION
        "Parameter 'link name' in event PPP.82"
    ::= { pppEventObjects82 1 }

ppp82_process_mode OBJECT-TYPE
    SYNTAX DisplayString
    MAX-ACCESS accessible-for-notify
    STATUS current
    DESCRIPTION
        "Parameter 'process mode' in event PPP.82"
    ::= { pppEventObjects82 2 }

pppEventObjects83 OBJECT-IDENTITY
    STATUS current
    DESCRIPTION
        "Event PPP.83
        Unknown compression type."
    ::= { pppEventsGroup 83 }

ppp83_link_name OBJECT-TYPE
    SYNTAX DisplayString
    MAX-ACCESS accessible-for-notify
    STATUS current
    DESCRIPTION
        "Parameter 'link name' in event PPP.83"
    ::= { pppEventObjects83 1 }

ppp83_compression_type OBJECT-TYPE
    SYNTAX Integer32
    MAX-ACCESS accessible-for-notify
    STATUS current
    DESCRIPTION
        "Parameter 'compression type' in event PPP.83"
    ::= { pppEventObjects83 2 }

ppp83_dump OBJECT-TYPE
    SYNTAX DisplayString
    MAX-ACCESS accessible-for-notify
    STATUS current
    DESCRIPTION
        "Parameter 'dump' in event PPP.83"
    ::= { pppEventObjects83 3 }

pppEventObjects84 OBJECT-IDENTITY
    STATUS current
    DESCRIPTION
        "Event PPP.84
        PAP mode description."
    ::= { pppEventsGroup 84 }

ppp84_link_name OBJECT-TYPE
    SYNTAX DisplayString
    MAX-ACCESS accessible-for-notify
    STATUS current
    DESCRIPTION
        "Parameter 'link name' in event PPP.84"
    ::= { pppEventObjects84 1 }

ppp84_mode OBJECT-TYPE
    SYNTAX DisplayString
    MAX-ACCESS accessible-for-notify
    STATUS current
    DESCRIPTION
        "Parameter 'mode' in event PPP.84"
    ::= { pppEventObjects84 2 }

pppEventObjects85 OBJECT-IDENTITY
    STATUS current
    DESCRIPTION
        "Event PPP.85
        CHAP mode description."
    ::= { pppEventsGroup 85 }

ppp85_link_name OBJECT-TYPE
    SYNTAX DisplayString
    MAX-ACCESS accessible-for-notify
    STATUS current
    DESCRIPTION
        "Parameter 'link name' in event PPP.85"
    ::= { pppEventObjects85 1 }

ppp85_mode OBJECT-TYPE
    SYNTAX DisplayString
    MAX-ACCESS accessible-for-notify
    STATUS current
    DESCRIPTION
        "Parameter 'mode' in event PPP.85"
    ::= { pppEventObjects85 2 }

pppEventObjects86 OBJECT-IDENTITY
    STATUS current
    DESCRIPTION
        "Event PPP.86
        LCP bad packet description."
    ::= { pppEventsGroup 86 }

ppp86_link_name OBJECT-TYPE
    SYNTAX DisplayString
    MAX-ACCESS accessible-for-notify
    STATUS current
    DESCRIPTION
        "Parameter 'link name' in event PPP.86"
    ::= { pppEventObjects86 1 }

ppp86_cause OBJECT-TYPE
    SYNTAX DisplayString
    MAX-ACCESS accessible-for-notify
    STATUS current
    DESCRIPTION
        "Parameter 'cause' in event PPP.86"
    ::= { pppEventObjects86 2 }

pppEventObjects87 OBJECT-IDENTITY
    STATUS current
    DESCRIPTION
        "Event PPP.87
        LCP information trace."
    ::= { pppEventsGroup 87 }

ppp87_link_name OBJECT-TYPE
    SYNTAX DisplayString
    MAX-ACCESS accessible-for-notify
    STATUS current
    DESCRIPTION
        "Parameter 'link name' in event PPP.87"
    ::= { pppEventObjects87 1 }

ppp87_information OBJECT-TYPE
    SYNTAX DisplayString
    MAX-ACCESS accessible-for-notify
    STATUS current
    DESCRIPTION
        "Parameter 'information' in event PPP.87"
    ::= { pppEventObjects87 2 }

pppEventObjects88 OBJECT-IDENTITY
    STATUS current
    DESCRIPTION
        "Event PPP.88
        IPCP information trace."
    ::= { pppEventsGroup 88 }

ppp88_link_name OBJECT-TYPE
    SYNTAX DisplayString
    MAX-ACCESS accessible-for-notify
    STATUS current
    DESCRIPTION
        "Parameter 'link name' in event PPP.88"
    ::= { pppEventObjects88 1 }

ppp88_information OBJECT-TYPE
    SYNTAX DisplayString
    MAX-ACCESS accessible-for-notify
    STATUS current
    DESCRIPTION
        "Parameter 'information' in event PPP.88"
    ::= { pppEventObjects88 2 }

pppEventObjects89 OBJECT-IDENTITY
    STATUS current
    DESCRIPTION
        "Event PPP.89
        CCP information trace."
    ::= { pppEventsGroup 89 }

ppp89_link_name OBJECT-TYPE
    SYNTAX DisplayString
    MAX-ACCESS accessible-for-notify
    STATUS current
    DESCRIPTION
        "Parameter 'link name' in event PPP.89"
    ::= { pppEventObjects89 1 }

ppp89_information OBJECT-TYPE
    SYNTAX DisplayString
    MAX-ACCESS accessible-for-notify
    STATUS current
    DESCRIPTION
        "Parameter 'information' in event PPP.89"
    ::= { pppEventObjects89 2 }

pppEventObjects90 OBJECT-IDENTITY
    STATUS current
    DESCRIPTION
        "Event PPP.90
        PPP connection established with the specified negotiation times."
    ::= { pppEventsGroup 90 }

ppp90_serial_number OBJECT-TYPE
    SYNTAX DisplayString
    MAX-ACCESS accessible-for-notify
    STATUS current
    DESCRIPTION
        "Parameter 'serial_number' in event PPP.90"
    ::= { pppEventObjects90 1 }

ppp90_hostname OBJECT-TYPE
    SYNTAX DisplayString
    MAX-ACCESS accessible-for-notify
    STATUS current
    DESCRIPTION
        "Parameter 'hostname' in event PPP.90"
    ::= { pppEventObjects90 2 }

ppp90_network OBJECT-TYPE
    SYNTAX Integer32
    MAX-ACCESS accessible-for-notify
    STATUS current
    DESCRIPTION
        "Parameter 'network' in event PPP.90"
    ::= { pppEventObjects90 3 }

ppp90_local_address OBJECT-TYPE
    SYNTAX IpAddress
    MAX-ACCESS accessible-for-notify
    STATUS current
    DESCRIPTION
        "Parameter 'local_address' in event PPP.90"
    ::= { pppEventObjects90 4 }

ppp90_pppoe_disc_time OBJECT-TYPE
    SYNTAX Integer32
    MAX-ACCESS accessible-for-notify
    STATUS current
    DESCRIPTION
        "Parameter 'pppoe_disc_time' in event PPP.90"
    ::= { pppEventObjects90 5 }

ppp90_lcp_time OBJECT-TYPE
    SYNTAX Integer32
    MAX-ACCESS accessible-for-notify
    STATUS current
    DESCRIPTION
        "Parameter 'lcp_time' in event PPP.90"
    ::= { pppEventObjects90 6 }

ppp90_ipcp_time OBJECT-TYPE
    SYNTAX Integer32
    MAX-ACCESS accessible-for-notify
    STATUS current
    DESCRIPTION
        "Parameter 'ipcp_time' in event PPP.90"
    ::= { pppEventObjects90 7 }

ppp90_authentication_time OBJECT-TYPE
    SYNTAX Integer32
    MAX-ACCESS accessible-for-notify
    STATUS current
    DESCRIPTION
        "Parameter 'authentication_time' in event PPP.90"
    ::= { pppEventObjects90 8 }

ppp90_compression_time OBJECT-TYPE
    SYNTAX Integer32
    MAX-ACCESS accessible-for-notify
    STATUS current
    DESCRIPTION
        "Parameter 'compression_time' in event PPP.90"
    ::= { pppEventObjects90 9 }

ppp90_device_status OBJECT-TYPE
    SYNTAX Integer32
    MAX-ACCESS accessible-for-notify
    STATUS current
    DESCRIPTION
        "Parameter 'device_status' in event PPP.90"
    ::= { pppEventObjects90 10 }

pppEventObjects91 OBJECT-IDENTITY
    STATUS current
    DESCRIPTION
        "Event PPP.91
        An error occurred negotiating the PPP connection."
    ::= { pppEventsGroup 91 }

ppp91_serial_number OBJECT-TYPE
    SYNTAX DisplayString
    MAX-ACCESS accessible-for-notify
    STATUS current
    DESCRIPTION
        "Parameter 'serial_number' in event PPP.91"
    ::= { pppEventObjects91 1 }

ppp91_hostname OBJECT-TYPE
    SYNTAX DisplayString
    MAX-ACCESS accessible-for-notify
    STATUS current
    DESCRIPTION
        "Parameter 'hostname' in event PPP.91"
    ::= { pppEventObjects91 2 }

ppp91_network OBJECT-TYPE
    SYNTAX Integer32
    MAX-ACCESS accessible-for-notify
    STATUS current
    DESCRIPTION
        "Parameter 'network' in event PPP.91"
    ::= { pppEventObjects91 3 }

ppp91_error_identifier OBJECT-TYPE
    SYNTAX Integer32
    MAX-ACCESS accessible-for-notify
    STATUS current
    DESCRIPTION
        "Parameter 'error_identifier' in event PPP.91"
    ::= { pppEventObjects91 4 }

ppp91_date OBJECT-TYPE
    SYNTAX DisplayString
    MAX-ACCESS accessible-for-notify
    STATUS current
    DESCRIPTION
        "Parameter 'date' in event PPP.91"
    ::= { pppEventObjects91 5 }

ppp91_error_code OBJECT-TYPE
    SYNTAX Integer32
    MAX-ACCESS accessible-for-notify
    STATUS current
    DESCRIPTION
        "Parameter 'error_code' in event PPP.91"
    ::= { pppEventObjects91 6 }

pppEventObjects92 OBJECT-IDENTITY
    STATUS current
    DESCRIPTION
        "Event PPP.92
        This messages specifies the protocol which was rejected in
        LCP Protocol Reject frame."
    ::= { pppEventsGroup 92 }

ppp92_link_name OBJECT-TYPE
    SYNTAX DisplayString
    MAX-ACCESS accessible-for-notify
    STATUS current
    DESCRIPTION
        "Parameter 'link name' in event PPP.92"
    ::= { pppEventObjects92 1 }

ppp92_protocol OBJECT-TYPE
    SYNTAX Integer32
    MAX-ACCESS accessible-for-notify
    STATUS current
    DESCRIPTION
        "Parameter 'protocol' in event PPP.92"
    ::= { pppEventObjects92 2 }

ppp92_dump OBJECT-TYPE
    SYNTAX DisplayString
    MAX-ACCESS accessible-for-notify
    STATUS current
    DESCRIPTION
        "Parameter 'dump' in event PPP.92"
    ::= { pppEventObjects92 3 }

pppEventObjects93 OBJECT-IDENTITY
    STATUS current
    DESCRIPTION
        "Event PPP.93
        IPCP generic option."
    ::= { pppEventsGroup 93 }

ppp93_link_name OBJECT-TYPE
    SYNTAX DisplayString
    MAX-ACCESS accessible-for-notify
    STATUS current
    DESCRIPTION
        "Parameter 'link name' in event PPP.93"
    ::= { pppEventObjects93 1 }

ppp93_IPCP_option OBJECT-TYPE
    SYNTAX DisplayString
    MAX-ACCESS accessible-for-notify
    STATUS current
    DESCRIPTION
        "Parameter 'IPCP option' in event PPP.93"
    ::= { pppEventObjects93 2 }

ppp93_dump OBJECT-TYPE
    SYNTAX DisplayString
    MAX-ACCESS accessible-for-notify
    STATUS current
    DESCRIPTION
        "Parameter 'dump' in event PPP.93"
    ::= { pppEventObjects93 3 }

pppEventObjects94 OBJECT-IDENTITY
    STATUS current
    DESCRIPTION
        "Event PPP.94
        IPCP generic parameter (associated to an option)."
    ::= { pppEventsGroup 94 }

ppp94_link_name OBJECT-TYPE
    SYNTAX DisplayString
    MAX-ACCESS accessible-for-notify
    STATUS current
    DESCRIPTION
        "Parameter 'link name' in event PPP.94"
    ::= { pppEventObjects94 1 }

ppp94_IPCP_option_parameter OBJECT-TYPE
    SYNTAX DisplayString
    MAX-ACCESS accessible-for-notify
    STATUS current
    DESCRIPTION
        "Parameter 'IPCP option parameter' in event PPP.94"
    ::= { pppEventObjects94 2 }

pppEventObjects95 OBJECT-IDENTITY
    STATUS current
    DESCRIPTION
        "Event PPP.95
        Generic LLC information trace."
    ::= { pppEventsGroup 95 }

ppp95_link_name OBJECT-TYPE
    SYNTAX DisplayString
    MAX-ACCESS accessible-for-notify
    STATUS current
    DESCRIPTION
        "Parameter 'link name' in event PPP.95"
    ::= { pppEventObjects95 1 }

ppp95_information OBJECT-TYPE
    SYNTAX DisplayString
    MAX-ACCESS accessible-for-notify
    STATUS current
    DESCRIPTION
        "Parameter 'information' in event PPP.95"
    ::= { pppEventObjects95 2 }

pppEventObjects100 OBJECT-IDENTITY
    STATUS current
    DESCRIPTION
        "Event PPP.100
        PPP POS, UDP message control management."
    ::= { pppEventsGroup 100 }

ppp100_message OBJECT-TYPE
    SYNTAX DisplayString
    MAX-ACCESS accessible-for-notify
    STATUS current
    DESCRIPTION
        "Parameter 'message' in event PPP.100"
    ::= { pppEventObjects100 1 }


pppNotification1 NOTIFICATION-TYPE
    OBJECTS { 
              ppp1_interface 
            }
    STATUS current
    DESCRIPTION
        "Notification of Event PPP.1

        Message: 'Interface $1 ready'

        Parameters list:
              $1: ppp1_interface

        Selftest successfully completed."
    ::= { pppNotificationsPrefix 1 }

pppNotification2 NOTIFICATION-TYPE
    OBJECTS { 
              ppp2_interface 
            }
    STATUS current
    DESCRIPTION
        "Notification of Event PPP.2

        Message: 'Interface $1 down'

        Parameters list:
              $1: ppp2_interface

        The selftest indicates that the base interfaces are all down."
    ::= { pppNotificationsPrefix 2 }

pppNotification3 NOTIFICATION-TYPE
    OBJECTS { 
              ppp3_linkPPP, 
              ppp3_size,
              ppp3_MRU 
            }
    STATUS current
    DESCRIPTION
        "Notification of Event PPP.3

        Message: '$1 In frame, MRU exceeded. Size $2, MRU $3'

        Parameters list:
              $1: ppp3_linkPPP
              $2: ppp3_size
              $3: ppp3_MRU

        The MRU has been exceeded in an incoming packet in the indicated link."
    ::= { pppNotificationsPrefix 3 }

pppNotification4 NOTIFICATION-TYPE
    OBJECTS { 
              ppp4_linkPPP, 
              ppp4_action 
            }
    STATUS current
    DESCRIPTION
        "Notification of Event PPP.4

        Message: '$1 MP fragment received out-of-order inside a link [$2]'

        Parameters list:
              $1: ppp4_linkPPP
              $2: ppp4_action

        A multilink PPP fragment has been received out-of-order. Queue is flushed
        or link reordered."
    ::= { pppNotificationsPrefix 4 }

pppNotification5 NOTIFICATION-TYPE
    OBJECTS { 
              ppp5_link_name, 
              ppp5_sequence,
              ppp5_classes,
              ppp5_dump 
            }
    STATUS current
    DESCRIPTION
        "Notification of Event PPP.5

        Message: '$1 LCP   Multilink Header Format: seq $2 classes $3 (0x$4)'

        Parameters list:
              $1: ppp5_link_name
              $2: ppp5_sequence
              $3: ppp5_classes
              $4: ppp5_dump

        Multilink Header Format option description."
    ::= { pppNotificationsPrefix 5 }

pppNotification6 NOTIFICATION-TYPE
    OBJECTS { 
              ppp6_linkPPP 
            }
    STATUS current
    DESCRIPTION
        "Notification of Event PPP.6

        Message: '$1 MP Multiclass Multilink negotiated'

        Parameters list:
              $1: ppp6_linkPPP

        Multiclass Multilink negotiated in the MP bundle."
    ::= { pppNotificationsPrefix 6 }

pppNotification7 NOTIFICATION-TYPE
    OBJECTS { 
              ppp7_linkPPP 
            }
    STATUS current
    DESCRIPTION
        "Notification of Event PPP.7

        Message: '$1 MP Real Time Frame'

        Parameters list:
              $1: ppp7_linkPPP

        MP Real Time Frame."
    ::= { pppNotificationsPrefix 7 }

pppNotification8 NOTIFICATION-TYPE
    STATUS current
    DESCRIPTION
        "Notification of Event PPP.8

        Message: '---'

        Reserved for possible future use."
    ::= { pppNotificationsPrefix 8 }

pppNotification9 NOTIFICATION-TYPE
    STATUS current
    DESCRIPTION
        "Notification of Event PPP.9

        Message: '---'

        Reserved for possible future use."
    ::= { pppNotificationsPrefix 9 }

pppNotification10 NOTIFICATION-TYPE
    STATUS current
    DESCRIPTION
        "Notification of Event PPP.10

        Message: '---'

        Reserved for possible future use."
    ::= { pppNotificationsPrefix 10 }

pppNotification11 NOTIFICATION-TYPE
    OBJECTS { 
              ppp11_linkPPP, 
              ppp11_receivedIn_or_sentOut,
              ppp11_protocol,
              ppp11_size 
            }
    STATUS current
    DESCRIPTION
        "Notification of Event PPP.11

        Message: '$1 $2 frame, protocol type 0x$3, size $4'

        Parameters list:
              $1: ppp11_linkPPP
              $2: ppp11_receivedIn_or_sentOut
              $3: ppp11_protocol
              $4: ppp11_size

        Received/sent frame from the protocol specified by a PPP interface."
    ::= { pppNotificationsPrefix 11 }

pppNotification12 NOTIFICATION-TYPE
    OBJECTS { 
              ppp12_linkPPP, 
              ppp12_receivedIn_or_sentOut,
              ppp12_protocol,
              ppp12_result 
            }
    STATUS current
    DESCRIPTION
        "Notification of Event PPP.12

        Message: '$1 $2 PFC frame, type 0x$3 [result: $4]'

        Parameters list:
              $1: ppp12_linkPPP
              $2: ppp12_receivedIn_or_sentOut
              $3: ppp12_protocol
              $4: ppp12_result

        Frame received with Protocol Field Compression (PFC)."
    ::= { pppNotificationsPrefix 12 }

pppNotification13 NOTIFICATION-TYPE
    OBJECTS { 
              ppp13_linkPPP, 
              ppp13_compressedIn_or_uncompressedOut,
              ppp13_action,
              ppp13_protocol,
              ppp13_result 
            }
    STATUS current
    DESCRIPTION
        "Notification of Event PPP.13

        Message: '$1 $2 $3 VJ frame, type 0x$4 [result: $5]'

        Parameters list:
              $1: ppp13_linkPPP
              $2: ppp13_compressedIn_or_uncompressedOut
              $3: ppp13_action
              $4: ppp13_protocol
              $5: ppp13_result

        A Van Jacobson frame has been compressed/decompressed (indicating
        the result of the operation)."
    ::= { pppNotificationsPrefix 13 }

pppNotification14 NOTIFICATION-TYPE
    OBJECTS { 
              ppp14_linkPPP, 
              ppp14_compressedIn_or_uncompressedOut,
              ppp14_action,
              ppp14_protocol,
              ppp14_result 
            }
    STATUS current
    DESCRIPTION
        "Notification of Event PPP.14

        Message: '$1 $2 $3 IPHC frame, type 0x$4 [result: $5]'

        Parameters list:
              $1: ppp14_linkPPP
              $2: ppp14_compressedIn_or_uncompressedOut
              $3: ppp14_action
              $4: ppp14_protocol
              $5: ppp14_result

        An IPHC frame has been compressed/decompressed (indicating the result
        of the operation)."
    ::= { pppNotificationsPrefix 14 }

pppNotification15 NOTIFICATION-TYPE
    OBJECTS { 
              ppp15_linkPPP, 
              ppp15_compressedIn_or_uncompressedOut,
              ppp15_action,
              ppp15_protocol,
              ppp15_result 
            }
    STATUS current
    DESCRIPTION
        "Notification of Event PPP.15

        Message: '$1 $2 $3 CCP frame, type 0x$4 [result: $5]'

        Parameters list:
              $1: ppp15_linkPPP
              $2: ppp15_compressedIn_or_uncompressedOut
              $3: ppp15_action
              $4: ppp15_protocol
              $5: ppp15_result

        A CCP frame has been compressed/decompressed (indicating the result
        of the operation)."
    ::= { pppNotificationsPrefix 15 }

pppNotification16 NOTIFICATION-TYPE
    OBJECTS { 
              ppp16_linkPPP, 
              ppp16_receivedIn_or_sentOut,
              ppp16_request_ack 
            }
    STATUS current
    DESCRIPTION
        "Notification of Event PPP.16

        Message: '$1 $2 CCP Reset $3'

        Parameters list:
              $1: ppp16_linkPPP
              $2: ppp16_receivedIn_or_sentOut
              $3: ppp16_request_ack

        Se ha enviado/recibido un CCP Reset Request/Ack."
    ::= { pppNotificationsPrefix 16 }

pppNotification17 NOTIFICATION-TYPE
    OBJECTS { 
              ppp17_linkPPP, 
              ppp17_created_or_deleted 
            }
    STATUS current
    DESCRIPTION
        "Notification of Event PPP.17

        Message: '$1 MP $2 bundle'

        Parameters list:
              $1: ppp17_linkPPP
              $2: ppp17_created_or_deleted

        An MP bundle has been created or eliminated."
    ::= { pppNotificationsPrefix 17 }

pppNotification18 NOTIFICATION-TYPE
    OBJECTS { 
              ppp18_linkPPP, 
              ppp18_local_or_remote,
              ppp18_MRRU 
            }
    STATUS current
    DESCRIPTION
        "Notification of Event PPP.18

        Message: '$1 MP $2 MRRU: $3'

        Parameters list:
              $1: ppp18_linkPPP
              $2: ppp18_local_or_remote
              $3: ppp18_MRRU

        MRRU negotiated in the MP bundle."
    ::= { pppNotificationsPrefix 18 }

pppNotification19 NOTIFICATION-TYPE
    OBJECTS { 
              ppp19_linkPPP, 
              ppp19_local_or_remote 
            }
    STATUS current
    DESCRIPTION
        "Notification of Event PPP.19

        Message: '$1 MP $2 SSN header'

        Parameters list:
              $1: ppp19_linkPPP
              $2: ppp19_local_or_remote

        SSN format (Short Sequence Number) negotiated in the MP bundle."
    ::= { pppNotificationsPrefix 19 }

pppNotification20 NOTIFICATION-TYPE
    OBJECTS { 
              ppp20_linkPPP, 
              ppp20_local_or_remote,
              ppp20_Endpoint_class,
              ppp20_Endpoint_value 
            }
    STATUS current
    DESCRIPTION
        "Notification of Event PPP.20

        Message: '$1 MP $2 EndPoint: class $3, value $4'

        Parameters list:
              $1: ppp20_linkPPP
              $2: ppp20_local_or_remote
              $3: ppp20_Endpoint_class
              $4: ppp20_Endpoint_value

        Endpoint Discriminator used in the MP bundle."
    ::= { pppNotificationsPrefix 20 }

pppNotification21 NOTIFICATION-TYPE
    OBJECTS { 
              ppp21_linkPPP, 
              ppp21_added_or_removed 
            }
    STATUS current
    DESCRIPTION
        "Notification of Event PPP.21

        Message: '$1 MP link $2 bundle'

        Parameters list:
              $1: ppp21_linkPPP
              $2: ppp21_added_or_removed

        A PPP link has been added to or removed from an MP bundle."
    ::= { pppNotificationsPrefix 21 }

pppNotification22 NOTIFICATION-TYPE
    OBJECTS { 
              ppp22_linkPPP, 
              ppp22_flags,
              ppp22_received_sequence,
              ppp22_expected_sequence,
              ppp22_action,
              ppp22_size 
            }
    STATUS current
    DESCRIPTION
        "Notification of Event PPP.22

        Message: '$1 In MP frame, flags 0x$2, seq 0x$3 (exp 0x$4)[$5], size $6'

        Parameters list:
              $1: ppp22_linkPPP
              $2: ppp22_flags
              $3: ppp22_received_sequence
              $4: ppp22_expected_sequence
              $5: ppp22_action
              $6: ppp22_size

        A multilink PPP frame has been received with a determined sequence
        number (the expected sequence number is displayed and the corresponding
        action: accept, discard or queue). Includes the flags and
        the frame size."
    ::= { pppNotificationsPrefix 22 }

pppNotification23 NOTIFICATION-TYPE
    OBJECTS { 
              ppp23_linkPPP, 
              ppp23_flags,
              ppp23_transmission_sequence,
              ppp23_size 
            }
    STATUS current
    DESCRIPTION
        "Notification of Event PPP.23

        Message: '$1 Out MP frame, flags 0x$2, seq 0x$3, size $4'

        Parameters list:
              $1: ppp23_linkPPP
              $2: ppp23_flags
              $3: ppp23_transmission_sequence
              $4: ppp23_size

        A multilink PPP frame has been transmitted (the transmission sequence
        number, the flags and the frame size is displayed)."
    ::= { pppNotificationsPrefix 23 }

pppNotification24 NOTIFICATION-TYPE
    OBJECTS { 
              ppp24_linkPPP 
            }
    STATUS current
    DESCRIPTION
        "Notification of Event PPP.24

        Message: '$1 MP Queue exceeds MAX Items'

        Parameters list:
              $1: ppp24_linkPPP

        The maximum number of queued multilink PPP fragments has been exceeded."
    ::= { pppNotificationsPrefix 24 }

pppNotification25 NOTIFICATION-TYPE
    OBJECTS { 
              ppp25_linkPPP, 
              ppp25_sequence 
            }
    STATUS current
    DESCRIPTION
        "Notification of Event PPP.25

        Message: '$1 MP found END fragment: 0x$2'

        Parameters list:
              $1: ppp25_linkPPP
              $2: ppp25_sequence

        A fragment with the MP frame end flag has been found (END) however
        the beginning part of the frame is not available."
    ::= { pppNotificationsPrefix 25 }

pppNotification26 NOTIFICATION-TYPE
    OBJECTS { 
              ppp26_linkPPP, 
              ppp26_compressedIn_or_uncompressedOut,
              ppp26_action,
              ppp26_protocol,
              ppp26_result 
            }
    STATUS current
    DESCRIPTION
        "Notification of Event PPP.26

        Message: '$1 $2 $3 VJ frame, type 0x$4 [result: $5]'

        Parameters list:
              $1: ppp26_linkPPP
              $2: ppp26_compressedIn_or_uncompressedOut
              $3: ppp26_action
              $4: ppp26_protocol
              $5: ppp26_result

        An error has been produced compressing/decompressing
        a Van Jacobson frame."
    ::= { pppNotificationsPrefix 26 }

pppNotification27 NOTIFICATION-TYPE
    OBJECTS { 
              ppp27_linkPPP, 
              ppp27_compressedIn_or_uncompressedOut,
              ppp27_action,
              ppp27_protocol,
              ppp27_result 
            }
    STATUS current
    DESCRIPTION
        "Notification of Event PPP.27

        Message: '$1 $2 $3 IPHC frame, type 0x$4 [result: $5]'

        Parameters list:
              $1: ppp27_linkPPP
              $2: ppp27_compressedIn_or_uncompressedOut
              $3: ppp27_action
              $4: ppp27_protocol
              $5: ppp27_result

        An error has been produced compressing/decompressing a IPHC frame."
    ::= { pppNotificationsPrefix 27 }

pppNotification28 NOTIFICATION-TYPE
    OBJECTS { 
              ppp28_linkPPP, 
              ppp28_compressedIn_or_uncompressedOut,
              ppp28_action,
              ppp28_protocol,
              ppp28_result 
            }
    STATUS current
    DESCRIPTION
        "Notification of Event PPP.28

        Message: '$1 $2 $3 CCP frame, type 0x$4 [result: $5]'

        Parameters list:
              $1: ppp28_linkPPP
              $2: ppp28_compressedIn_or_uncompressedOut
              $3: ppp28_action
              $4: ppp28_protocol
              $5: ppp28_result

        An error has been produced compressing/decompressing a CCP frame."
    ::= { pppNotificationsPrefix 28 }

pppNotification29 NOTIFICATION-TYPE
    OBJECTS { 
              ppp29_link_name, 
              ppp29_user,
              ppp29_action 
            }
    STATUS current
    DESCRIPTION
        "Notification of Event PPP.29

        Message: '$1 L2TP session ($2) $3'

        Parameters list:
              $1: ppp29_link_name
              $2: ppp29_user
              $3: ppp29_action

        Indicates a request/establishment of an L2TP session."
    ::= { pppNotificationsPrefix 29 }

pppNotification30 NOTIFICATION-TYPE
    OBJECTS { 
              ppp30_linkPPP, 
              ppp30_information_message 
            }
    STATUS current
    DESCRIPTION
        "Notification of Event PPP.30

        Message: '$1 MP $2'

        Parameters list:
              $1: ppp30_linkPPP
              $2: ppp30_information_message

        Indicates an unusual situation in Multilink PPP."
    ::= { pppNotificationsPrefix 30 }

pppNotification31 NOTIFICATION-TYPE
    OBJECTS { 
              ppp31_link_name, 
              ppp31_direction,
              ppp31_code,
              ppp31_BCP_state,
              ppp31_identifier,
              ppp31_length 
            }
    STATUS current
    DESCRIPTION
        "Notification of Event PPP.31

        Message: '$1 BCP $2 $3 [$4] id $5 len $6'

        Parameters list:
              $1: ppp31_link_name
              $2: ppp31_direction
              $3: ppp31_code
              $4: ppp31_BCP_state
              $5: ppp31_identifier
              $6: ppp31_length

        BCP packet description."
    ::= { pppNotificationsPrefix 31 }

pppNotification32 NOTIFICATION-TYPE
    OBJECTS { 
              ppp32_link_name, 
              ppp32_id,
              ppp32_dump 
            }
    STATUS current
    DESCRIPTION
        "Notification of Event PPP.32

        Message: '$1 BCP   Bridge ID $2, (0x$3)'

        Parameters list:
              $1: ppp32_link_name
              $2: ppp32_id
              $3: ppp32_dump

        BCP Bridge ID option"
    ::= { pppNotificationsPrefix 32 }

pppNotification33 NOTIFICATION-TYPE
    OBJECTS { 
              ppp33_link_name, 
              ppp33_id,
              ppp33_dump 
            }
    STATUS current
    DESCRIPTION
        "Notification of Event PPP.33

        Message: '$1 BCP   Line ID $2, (0x$3)'

        Parameters list:
              $1: ppp33_link_name
              $2: ppp33_id
              $3: ppp33_dump

        BCP Line ID option."
    ::= { pppNotificationsPrefix 33 }

pppNotification34 NOTIFICATION-TYPE
    OBJECTS { 
              ppp34_link_name, 
              ppp34_maccode,
              ppp34_macname,
              ppp34_dump 
            }
    STATUS current
    DESCRIPTION
        "Notification of Event PPP.34

        Message: '$1 BCP   MAC Support $2 $3, (0x$4)'

        Parameters list:
              $1: ppp34_link_name
              $2: ppp34_maccode
              $3: ppp34_macname
              $4: ppp34_dump

        BCP MAC Support option."
    ::= { pppNotificationsPrefix 34 }

pppNotification35 NOTIFICATION-TYPE
    OBJECTS { 
              ppp35_link_name, 
              ppp35_comp,
              ppp35_dump 
            }
    STATUS current
    DESCRIPTION
        "Notification of Event PPP.35

        Message: '$1 BCP   Tinygram Compression $2, (0x$3)'

        Parameters list:
              $1: ppp35_link_name
              $2: ppp35_comp
              $3: ppp35_dump

        BCP Tinygram compression option."
    ::= { pppNotificationsPrefix 35 }

pppNotification36 NOTIFICATION-TYPE
    OBJECTS { 
              ppp36_link_name, 
              ppp36_lanid,
              ppp36_dump 
            }
    STATUS current
    DESCRIPTION
        "Notification of Event PPP.36

        Message: '$1 BCP   LAN Identification $2, (0x$3)'

        Parameters list:
              $1: ppp36_link_name
              $2: ppp36_lanid
              $3: ppp36_dump

        BCP LAN Identification option."
    ::= { pppNotificationsPrefix 36 }

pppNotification37 NOTIFICATION-TYPE
    OBJECTS { 
              ppp37_link_name, 
              ppp37_macaddr,
              ppp37_dump 
            }
    STATUS current
    DESCRIPTION
        "Notification of Event PPP.37

        Message: '$1 BCP   MAC Address $2, (0x$3)'

        Parameters list:
              $1: ppp37_link_name
              $2: ppp37_macaddr
              $3: ppp37_dump

        BCP MAC Address option."
    ::= { pppNotificationsPrefix 37 }

pppNotification38 NOTIFICATION-TYPE
    OBJECTS { 
              ppp38_link_name, 
              ppp38_oldstp,
              ppp38_dump 
            }
    STATUS current
    DESCRIPTION
        "Notification of Event PPP.38

        Message: '$1 BCP   Old Spanning Tree Protocol $2, (0x$3)'

        Parameters list:
              $1: ppp38_link_name
              $2: ppp38_oldstp
              $3: ppp38_dump

        BCP Old Spanning Tree Protocol option."
    ::= { pppNotificationsPrefix 38 }

pppNotification39 NOTIFICATION-TYPE
    OBJECTS { 
              ppp39_link_name, 
              ppp39_tagged,
              ppp39_dump 
            }
    STATUS current
    DESCRIPTION
        "Notification of Event PPP.39

        Message: '$1 BCP   Tagged Frame $2, (0x$3)'

        Parameters list:
              $1: ppp39_link_name
              $2: ppp39_tagged
              $3: ppp39_dump

        BCP Tagged Frame option."
    ::= { pppNotificationsPrefix 39 }

pppNotification40 NOTIFICATION-TYPE
    OBJECTS { 
              ppp40_link_name, 
              ppp40_dump 
            }
    STATUS current
    DESCRIPTION
        "Notification of Event PPP.40

        Message: '$1 BCP   Management Inline supported, (0x$2)'

        Parameters list:
              $1: ppp40_link_name
              $2: ppp40_dump

        BCP Management Inline support option."
    ::= { pppNotificationsPrefix 40 }

pppNotification41 NOTIFICATION-TYPE
    OBJECTS { 
              ppp41_link_name, 
              ppp41_dump 
            }
    STATUS current
    DESCRIPTION
        "Notification of Event PPP.41

        Message: '$1 BCP   Unknown option (0x$2)'

        Parameters list:
              $1: ppp41_link_name
              $2: ppp41_dump

        BCP unknown option."
    ::= { pppNotificationsPrefix 41 }

pppNotification42 NOTIFICATION-TYPE
    OBJECTS { 
              ppp42_link_name, 
              ppp42_information 
            }
    STATUS current
    DESCRIPTION
        "Notification of Event PPP.42

        Message: '$1 BCP $2'

        Parameters list:
              $1: ppp42_link_name
              $2: ppp42_information

        BCP information trace."
    ::= { pppNotificationsPrefix 42 }

pppNotification43 NOTIFICATION-TYPE
    OBJECTS { 
              ppp43_link_name 
            }
    STATUS current
    DESCRIPTION
        "Notification of Event PPP.43

        Message: '$1 DROP: Bridging not enabled on this interface'

        Parameters list:
              $1: ppp43_link_name

        A frame was received of a bridge type defined in RFC 2878.
        However, since bridging has not been enabled on this circuit, frame
        is being discarded."
    ::= { pppNotificationsPrefix 43 }

pppNotification44 NOTIFICATION-TYPE
    OBJECTS { 
              ppp44_link_name 
            }
    STATUS current
    DESCRIPTION
        "Notification of Event PPP.44

        Message: '$1 DROP: Bridge port not forwarding on this interface'

        Parameters list:
              $1: ppp44_link_name

        A bridge frame is being discarded as a bridge port is not in
        forwarding state."
    ::= { pppNotificationsPrefix 44 }

pppNotification45 NOTIFICATION-TYPE
    OBJECTS { 
              ppp45_link_name, 
              ppp45_source_mac,
              ppp45_dest_mac 
            }
    STATUS current
    DESCRIPTION
        "Notification of Event PPP.45

        Message: '$1 DROP: $2->$3, Frame to bridge port behavior mismatch on this interface'

        Parameters list:
              $1: ppp45_link_name
              $2: ppp45_source_mac
              $3: ppp45_dest_mac

        A bridged frame has been received and is being discarded due to mismatch
        in the frame type versus the bridge port behavior."
    ::= { pppNotificationsPrefix 45 }

pppNotification46 NOTIFICATION-TYPE
    OBJECTS { 
              ppp46_link_name, 
              ppp46_type 
            }
    STATUS current
    DESCRIPTION
        "Notification of Event PPP.46

        Message: '$1 DROP: Unsupported bridge frame type = $2 on this interface'

        Parameters list:
              $1: ppp46_link_name
              $2: ppp46_type

        An unsupported bridge frame type has been encountered."
    ::= { pppNotificationsPrefix 46 }

pppNotification47 NOTIFICATION-TYPE
    STATUS current
    DESCRIPTION
        "Notification of Event PPP.47

        Message: '---'

        Reserved for possible future use."
    ::= { pppNotificationsPrefix 47 }

pppNotification48 NOTIFICATION-TYPE
    STATUS current
    DESCRIPTION
        "Notification of Event PPP.48

        Message: '---'

        Reserved for possible future use."
    ::= { pppNotificationsPrefix 48 }

pppNotification49 NOTIFICATION-TYPE
    OBJECTS { 
              ppp49_link_name, 
              ppp49_option,
              ppp49_dump 
            }
    STATUS current
    DESCRIPTION
        "Notification of Event PPP.49

        Message: '$1 LCP   $2 (0x$3)'

        Parameters list:
              $1: ppp49_link_name
              $2: ppp49_option
              $3: ppp49_dump

        Unsupported LCP option description."
    ::= { pppNotificationsPrefix 49 }

pppNotification50 NOTIFICATION-TYPE
    OBJECTS { 
              ppp50_link_name, 
              ppp50_dump 
            }
    STATUS current
    DESCRIPTION
        "Notification of Event PPP.50

        Message: '$1 LCP   (0x$2)'

        Parameters list:
              $1: ppp50_link_name
              $2: ppp50_dump

        LCP packet data."
    ::= { pppNotificationsPrefix 50 }

pppNotification51 NOTIFICATION-TYPE
    OBJECTS { 
              ppp51_link_name, 
              ppp51_direction,
              ppp51_code,
              ppp51_LCP_state,
              ppp51_identifier,
              ppp51_length 
            }
    STATUS current
    DESCRIPTION
        "Notification of Event PPP.51

        Message: '$1 LCP $2 $3 [$4] id $5 len $6'

        Parameters list:
              $1: ppp51_link_name
              $2: ppp51_direction
              $3: ppp51_code
              $4: ppp51_LCP_state
              $5: ppp51_identifier
              $6: ppp51_length

        LCP packet description."
    ::= { pppNotificationsPrefix 51 }

pppNotification52 NOTIFICATION-TYPE
    OBJECTS { 
              ppp52_link_name, 
              ppp52_mru,
              ppp52_dump 
            }
    STATUS current
    DESCRIPTION
        "Notification of Event PPP.52

        Message: '$1 LCP   MRU $2 (0x$3)'

        Parameters list:
              $1: ppp52_link_name
              $2: ppp52_mru
              $3: ppp52_dump

        MRU option description."
    ::= { pppNotificationsPrefix 52 }

pppNotification53 NOTIFICATION-TYPE
    OBJECTS { 
              ppp53_link_name, 
              ppp53_async_map,
              ppp53_dump 
            }
    STATUS current
    DESCRIPTION
        "Notification of Event PPP.53

        Message: '$1 LCP   AsyncMap $2 (0x$3)'

        Parameters list:
              $1: ppp53_link_name
              $2: ppp53_async_map
              $3: ppp53_dump

        Asynchronous Control Character Map (ACCM) option description."
    ::= { pppNotificationsPrefix 53 }

pppNotification54 NOTIFICATION-TYPE
    OBJECTS { 
              ppp54_link_name, 
              ppp54_auth_protocol,
              ppp54_dump 
            }
    STATUS current
    DESCRIPTION
        "Notification of Event PPP.54

        Message: '$1 LCP   AuthProt $2 (0x$3)'

        Parameters list:
              $1: ppp54_link_name
              $2: ppp54_auth_protocol
              $3: ppp54_dump

        Authentication option description."
    ::= { pppNotificationsPrefix 54 }

pppNotification55 NOTIFICATION-TYPE
    OBJECTS { 
              ppp55_link_name, 
              ppp55_magic_number,
              ppp55_dump 
            }
    STATUS current
    DESCRIPTION
        "Notification of Event PPP.55

        Message: '$1 LCP   MagicNumber $2 (0x$3)'

        Parameters list:
              $1: ppp55_link_name
              $2: ppp55_magic_number
              $3: ppp55_dump

        Magic Number option description."
    ::= { pppNotificationsPrefix 55 }

pppNotification56 NOTIFICATION-TYPE
    OBJECTS { 
              ppp56_link_name, 
              ppp56_dump 
            }
    STATUS current
    DESCRIPTION
        "Notification of Event PPP.56

        Message: '$1 LCP   ProtComp available (0x$2)'

        Parameters list:
              $1: ppp56_link_name
              $2: ppp56_dump

        Protocol Field Compression option description."
    ::= { pppNotificationsPrefix 56 }

pppNotification57 NOTIFICATION-TYPE
    OBJECTS { 
              ppp57_link_name, 
              ppp57_dump 
            }
    STATUS current
    DESCRIPTION
        "Notification of Event PPP.57

        Message: '$1 LCP   AddrCtrlComp available (0x$2)'

        Parameters list:
              $1: ppp57_link_name
              $2: ppp57_dump

        Address/Control Fields Compression option description."
    ::= { pppNotificationsPrefix 57 }

pppNotification58 NOTIFICATION-TYPE
    OBJECTS { 
              ppp58_link_name, 
              ppp58_mrru,
              ppp58_dump 
            }
    STATUS current
    DESCRIPTION
        "Notification of Event PPP.58

        Message: '$1 LCP   MRRU $2 (0x$3)'

        Parameters list:
              $1: ppp58_link_name
              $2: ppp58_mrru
              $3: ppp58_dump

        MRRU option description."
    ::= { pppNotificationsPrefix 58 }

pppNotification59 NOTIFICATION-TYPE
    OBJECTS { 
              ppp59_link_name, 
              ppp59_dump 
            }
    STATUS current
    DESCRIPTION
        "Notification of Event PPP.59

        Message: '$1 LCP   ShortHeader available (0x$2)'

        Parameters list:
              $1: ppp59_link_name
              $2: ppp59_dump

        Short Sequence Number header format option description."
    ::= { pppNotificationsPrefix 59 }

pppNotification60 NOTIFICATION-TYPE
    OBJECTS { 
              ppp60_link_name, 
              ppp60_class,
              ppp60_dump 
            }
    STATUS current
    DESCRIPTION
        "Notification of Event PPP.60

        Message: '$1 LCP   EndPoint class $2 (0x$3)'

        Parameters list:
              $1: ppp60_link_name
              $2: ppp60_class
              $3: ppp60_dump

        End-Point Discriminator option description."
    ::= { pppNotificationsPrefix 60 }

pppNotification61 NOTIFICATION-TYPE
    OBJECTS { 
              ppp61_link_name, 
              ppp61_dump 
            }
    STATUS current
    DESCRIPTION
        "Notification of Event PPP.61

        Message: '$1 LCP   Unknown option (0x$2)'

        Parameters list:
              $1: ppp61_link_name
              $2: ppp61_dump

        Unknown option description."
    ::= { pppNotificationsPrefix 61 }

pppNotification62 NOTIFICATION-TYPE
    OBJECTS { 
              ppp62_link_name, 
              ppp62_dump 
            }
    STATUS current
    DESCRIPTION
        "Notification of Event PPP.62

        Message: '$1 LCP   Bad option (0x$2)'

        Parameters list:
              $1: ppp62_link_name
              $2: ppp62_dump

        Bad format option description."
    ::= { pppNotificationsPrefix 62 }

pppNotification63 NOTIFICATION-TYPE
    OBJECTS { 
              ppp63_link_name, 
              ppp63_direction,
              ppp63_code,
              ppp63_PAP_state,
              ppp63_identifier,
              ppp63_length 
            }
    STATUS current
    DESCRIPTION
        "Notification of Event PPP.63

        Message: '$1 PAP $2 $3 [$4] id $5 len $6'

        Parameters list:
              $1: ppp63_link_name
              $2: ppp63_direction
              $3: ppp63_code
              $4: ppp63_PAP_state
              $5: ppp63_identifier
              $6: ppp63_length

        PAP packet description."
    ::= { pppNotificationsPrefix 63 }

pppNotification64 NOTIFICATION-TYPE
    OBJECTS { 
              ppp64_link_name, 
              ppp64_peer-id 
            }
    STATUS current
    DESCRIPTION
        "Notification of Event PPP.64

        Message: '$1 PAP   Peer-Id $2'

        Parameters list:
              $1: ppp64_link_name
              $2: ppp64_peer-id

        PAP request peer-id."
    ::= { pppNotificationsPrefix 64 }

pppNotification65 NOTIFICATION-TYPE
    OBJECTS { 
              ppp65_link_name, 
              ppp65_password 
            }
    STATUS current
    DESCRIPTION
        "Notification of Event PPP.65

        Message: '$1 PAP   Password $2'

        Parameters list:
              $1: ppp65_link_name
              $2: ppp65_password

        PAP request password."
    ::= { pppNotificationsPrefix 65 }

pppNotification66 NOTIFICATION-TYPE
    OBJECTS { 
              ppp66_link__name, 
              ppp66_message 
            }
    STATUS current
    DESCRIPTION
        "Notification of Event PPP.66

        Message: '$1 PAP   Message: $2'

        Parameters list:
              $1: ppp66_link__name
              $2: ppp66_message

        PAP reply message."
    ::= { pppNotificationsPrefix 66 }

pppNotification67 NOTIFICATION-TYPE
    OBJECTS { 
              ppp67_link_name, 
              ppp67_direction,
              ppp67_code,
              ppp67_CHAP_state,
              ppp67_identifier,
              ppp67_length 
            }
    STATUS current
    DESCRIPTION
        "Notification of Event PPP.67

        Message: '$1 CHAP $2 $3 [$4] id $5 len $6'

        Parameters list:
              $1: ppp67_link_name
              $2: ppp67_direction
              $3: ppp67_code
              $4: ppp67_CHAP_state
              $5: ppp67_identifier
              $6: ppp67_length

        CHAP packet description."
    ::= { pppNotificationsPrefix 67 }

pppNotification68 NOTIFICATION-TYPE
    OBJECTS { 
              ppp68_link_name, 
              ppp68_peer_name 
            }
    STATUS current
    DESCRIPTION
        "Notification of Event PPP.68

        Message: '$1 CHAP   Peer-Name $2'

        Parameters list:
              $1: ppp68_link_name
              $2: ppp68_peer_name

        CHAP peer name."
    ::= { pppNotificationsPrefix 68 }

pppNotification69 NOTIFICATION-TYPE
    OBJECTS { 
              ppp69_link_name, 
              ppp69_peer_message 
            }
    STATUS current
    DESCRIPTION
        "Notification of Event PPP.69

        Message: '$1 CHAP   Message: $2'

        Parameters list:
              $1: ppp69_link_name
              $2: ppp69_peer_message

        CHAP peer message."
    ::= { pppNotificationsPrefix 69 }

pppNotification70 NOTIFICATION-TYPE
    OBJECTS { 
              ppp70_link_name, 
              ppp70_challenge 
            }
    STATUS current
    DESCRIPTION
        "Notification of Event PPP.70

        Message: '$1 CHAP   Challenge $2'

        Parameters list:
              $1: ppp70_link_name
              $2: ppp70_challenge

        CHAP challenge value."
    ::= { pppNotificationsPrefix 70 }

pppNotification71 NOTIFICATION-TYPE
    OBJECTS { 
              ppp71_link_name, 
              ppp71_md5 
            }
    STATUS current
    DESCRIPTION
        "Notification of Event PPP.71

        Message: '$1 CHAP   MD5 $2'

        Parameters list:
              $1: ppp71_link_name
              $2: ppp71_md5

        CHAP MD5 value."
    ::= { pppNotificationsPrefix 71 }

pppNotification72 NOTIFICATION-TYPE
    OBJECTS { 
              ppp72_link_name, 
              ppp72_direction,
              ppp72_code,
              ppp72_IPCP_state,
              ppp72_identifier,
              ppp72_length 
            }
    STATUS current
    DESCRIPTION
        "Notification of Event PPP.72

        Message: '$1 IPCP $2 $3 [$4] id $5 len $6'

        Parameters list:
              $1: ppp72_link_name
              $2: ppp72_direction
              $3: ppp72_code
              $4: ppp72_IPCP_state
              $5: ppp72_identifier
              $6: ppp72_length

        IPCP packet description."
    ::= { pppNotificationsPrefix 72 }

pppNotification73 NOTIFICATION-TYPE
    OBJECTS { 
              ppp73_link_name, 
              ppp73_address,
              ppp73_dump 
            }
    STATUS current
    DESCRIPTION
        "Notification of Event PPP.73

        Message: '$1 IPCP   Address $2 (0x$3)'

        Parameters list:
              $1: ppp73_link_name
              $2: ppp73_address
              $3: ppp73_dump

        IPCP address option."
    ::= { pppNotificationsPrefix 73 }

pppNotification74 NOTIFICATION-TYPE
    OBJECTS { 
              ppp74_link_name, 
              ppp74_slots,
              ppp74_compression_flag,
              ppp74_dump 
            }
    STATUS current
    DESCRIPTION
        "Notification of Event PPP.74

        Message: '$1 IPCP   CompressProt VJ, $2 slots, comp $3 (0x$4)'

        Parameters list:
              $1: ppp74_link_name
              $2: ppp74_slots
              $3: ppp74_compression_flag
              $4: ppp74_dump

        IPCP Van-Jacobson compression protocol."
    ::= { pppNotificationsPrefix 74 }

pppNotification75 NOTIFICATION-TYPE
    OBJECTS { 
              ppp75_link_name, 
              ppp75_dump 
            }
    STATUS current
    DESCRIPTION
        "Notification of Event PPP.75

        Message: '$1 IPCP   Unknown CompressProt (0x$2)'

        Parameters list:
              $1: ppp75_link_name
              $2: ppp75_dump

        IPCP unknown compression protocol."
    ::= { pppNotificationsPrefix 75 }

pppNotification76 NOTIFICATION-TYPE
    OBJECTS { 
              ppp76_link_name, 
              ppp76_dump 
            }
    STATUS current
    DESCRIPTION
        "Notification of Event PPP.76

        Message: '$1 IPCP   Unknown option (0x$2)'

        Parameters list:
              $1: ppp76_link_name
              $2: ppp76_dump

        IPCP unknown option."
    ::= { pppNotificationsPrefix 76 }

pppNotification77 NOTIFICATION-TYPE
    OBJECTS { 
              ppp77_link_name, 
              ppp77_direction,
              ppp77_code,
              ppp77_CCP_state,
              ppp77_identifier,
              ppp77_length 
            }
    STATUS current
    DESCRIPTION
        "Notification of Event PPP.77

        Message: '$1 CCP $2 $3 [$4] id $5 len $6'

        Parameters list:
              $1: ppp77_link_name
              $2: ppp77_direction
              $3: ppp77_code
              $4: ppp77_CCP_state
              $5: ppp77_identifier
              $6: ppp77_length

        CCP packet description."
    ::= { pppNotificationsPrefix 77 }

pppNotification78 NOTIFICATION-TYPE
    OBJECTS { 
              ppp78_link_name, 
              ppp78_dump 
            }
    STATUS current
    DESCRIPTION
        "Notification of Event PPP.78

        Message: '$1 CCP   LZS-DCP Compression (0x$2)'

        Parameters list:
              $1: ppp78_link_name
              $2: ppp78_dump

        LZS-DCP compression option."
    ::= { pppNotificationsPrefix 78 }

pppNotification79 NOTIFICATION-TYPE
    OBJECTS { 
              ppp79_link_name, 
              ppp79_dump 
            }
    STATUS current
    DESCRIPTION
        "Notification of Event PPP.79

        Message: '$1 CCP   Stac LZS Compression (0x$2)'

        Parameters list:
              $1: ppp79_link_name
              $2: ppp79_dump

        Stac LZS compression option."
    ::= { pppNotificationsPrefix 79 }

pppNotification80 NOTIFICATION-TYPE
    OBJECTS { 
              ppp80_link_name, 
              ppp80_histories 
            }
    STATUS current
    DESCRIPTION
        "Notification of Event PPP.80

        Message: '$1 CCP      History number: $2'

        Parameters list:
              $1: ppp80_link_name
              $2: ppp80_histories

        History number parameter."
    ::= { pppNotificationsPrefix 80 }

pppNotification81 NOTIFICATION-TYPE
    OBJECTS { 
              ppp81_link_name, 
              ppp81_check_mode 
            }
    STATUS current
    DESCRIPTION
        "Notification of Event PPP.81

        Message: '$1 CCP      Check mode: $2'

        Parameters list:
              $1: ppp81_link_name
              $2: ppp81_check_mode

        Check mode parameter."
    ::= { pppNotificationsPrefix 81 }

pppNotification82 NOTIFICATION-TYPE
    OBJECTS { 
              ppp82_link_name, 
              ppp82_process_mode 
            }
    STATUS current
    DESCRIPTION
        "Notification of Event PPP.82

        Message: '$1 CCP      Process mode: $2'

        Parameters list:
              $1: ppp82_link_name
              $2: ppp82_process_mode

        Process mode parameter."
    ::= { pppNotificationsPrefix 82 }

pppNotification83 NOTIFICATION-TYPE
    OBJECTS { 
              ppp83_link_name, 
              ppp83_compression_type,
              ppp83_dump 
            }
    STATUS current
    DESCRIPTION
        "Notification of Event PPP.83

        Message: '$1 CCP   Unknown compression type $2 (0x$3)'

        Parameters list:
              $1: ppp83_link_name
              $2: ppp83_compression_type
              $3: ppp83_dump

        Unknown compression type."
    ::= { pppNotificationsPrefix 83 }

pppNotification84 NOTIFICATION-TYPE
    OBJECTS { 
              ppp84_link_name, 
              ppp84_mode 
            }
    STATUS current
    DESCRIPTION
        "Notification of Event PPP.84

        Message: '$1 PAP required by $2'

        Parameters list:
              $1: ppp84_link_name
              $2: ppp84_mode

        PAP mode description."
    ::= { pppNotificationsPrefix 84 }

pppNotification85 NOTIFICATION-TYPE
    OBJECTS { 
              ppp85_link_name, 
              ppp85_mode 
            }
    STATUS current
    DESCRIPTION
        "Notification of Event PPP.85

        Message: '$1 CHAP required by $2'

        Parameters list:
              $1: ppp85_link_name
              $2: ppp85_mode

        CHAP mode description."
    ::= { pppNotificationsPrefix 85 }

pppNotification86 NOTIFICATION-TYPE
    OBJECTS { 
              ppp86_link_name, 
              ppp86_cause 
            }
    STATUS current
    DESCRIPTION
        "Notification of Event PPP.86

        Message: '$1 LCP Invalid packet ($2)'

        Parameters list:
              $1: ppp86_link_name
              $2: ppp86_cause

        LCP bad packet description."
    ::= { pppNotificationsPrefix 86 }

pppNotification87 NOTIFICATION-TYPE
    OBJECTS { 
              ppp87_link_name, 
              ppp87_information 
            }
    STATUS current
    DESCRIPTION
        "Notification of Event PPP.87

        Message: '$1 LCP $2'

        Parameters list:
              $1: ppp87_link_name
              $2: ppp87_information

        LCP information trace."
    ::= { pppNotificationsPrefix 87 }

pppNotification88 NOTIFICATION-TYPE
    OBJECTS { 
              ppp88_link_name, 
              ppp88_information 
            }
    STATUS current
    DESCRIPTION
        "Notification of Event PPP.88

        Message: '$1 IPCP $2'

        Parameters list:
              $1: ppp88_link_name
              $2: ppp88_information

        IPCP information trace."
    ::= { pppNotificationsPrefix 88 }

pppNotification89 NOTIFICATION-TYPE
    OBJECTS { 
              ppp89_link_name, 
              ppp89_information 
            }
    STATUS current
    DESCRIPTION
        "Notification of Event PPP.89

        Message: '$1 CCP $2'

        Parameters list:
              $1: ppp89_link_name
              $2: ppp89_information

        CCP information trace."
    ::= { pppNotificationsPrefix 89 }

pppNotification90 NOTIFICATION-TYPE
    OBJECTS { 
              ppp90_serial_number, 
              ppp90_hostname,
              ppp90_network,
              ppp90_local_address,
              ppp90_pppoe_disc_time,
              ppp90_lcp_time,
              ppp90_ipcp_time,
              ppp90_authentication_time,
              ppp90_compression_time,
              ppp90_device_status 
            }
    STATUS current
    DESCRIPTION
        "Notification of Event PPP.90

        Message: 'est $1 $2 nt $3, local addr: $4, time PPPoED $5 ms, lcp $6 ms, ipcp $7 ms, auth $8 ms, comp $9 ms dev_st=$10'

        Parameters list:
              $1: ppp90_serial_number
              $2: ppp90_hostname
              $3: ppp90_network
              $4: ppp90_local_address
              $5: ppp90_pppoe_disc_time
              $6: ppp90_lcp_time
              $7: ppp90_ipcp_time
              $8: ppp90_authentication_time
              $9: ppp90_compression_time
              $10: ppp90_device_status

        PPP connection established with the specified negotiation times."
    ::= { pppNotificationsPrefix 90 }

pppNotification91 NOTIFICATION-TYPE
    OBJECTS { 
              ppp91_serial_number, 
              ppp91_hostname,
              ppp91_network,
              ppp91_error_identifier,
              ppp91_date,
              ppp91_error_code 
            }
    STATUS current
    DESCRIPTION
        "Notification of Event PPP.91

        Message: 'conn err $1 $2 nt $3 err-id $4 $5 err $6'

        Parameters list:
              $1: ppp91_serial_number
              $2: ppp91_hostname
              $3: ppp91_network
              $4: ppp91_error_identifier
              $5: ppp91_date
              $6: ppp91_error_code

        An error occurred negotiating the PPP connection."
    ::= { pppNotificationsPrefix 91 }

pppNotification92 NOTIFICATION-TYPE
    OBJECTS { 
              ppp92_link_name, 
              ppp92_protocol,
              ppp92_dump 
            }
    STATUS current
    DESCRIPTION
        "Notification of Event PPP.92

        Message: '$1 LCP   Protocol 0x$2 (0x$3)'

        Parameters list:
              $1: ppp92_link_name
              $2: ppp92_protocol
              $3: ppp92_dump

        This messages specifies the protocol which was rejected in
        LCP Protocol Reject frame."
    ::= { pppNotificationsPrefix 92 }

pppNotification93 NOTIFICATION-TYPE
    OBJECTS { 
              ppp93_link_name, 
              ppp93_IPCP_option,
              ppp93_dump 
            }
    STATUS current
    DESCRIPTION
        "Notification of Event PPP.93

        Message: '$1 IPCP   $2 (0x$3)'

        Parameters list:
              $1: ppp93_link_name
              $2: ppp93_IPCP_option
              $3: ppp93_dump

        IPCP generic option."
    ::= { pppNotificationsPrefix 93 }

pppNotification94 NOTIFICATION-TYPE
    OBJECTS { 
              ppp94_link_name, 
              ppp94_IPCP_option_parameter 
            }
    STATUS current
    DESCRIPTION
        "Notification of Event PPP.94

        Message: '$1 IPCP   $2'

        Parameters list:
              $1: ppp94_link_name
              $2: ppp94_IPCP_option_parameter

        IPCP generic parameter (associated to an option)."
    ::= { pppNotificationsPrefix 94 }

pppNotification95 NOTIFICATION-TYPE
    OBJECTS { 
              ppp95_link_name, 
              ppp95_information 
            }
    STATUS current
    DESCRIPTION
        "Notification of Event PPP.95

        Message: '$1 LLC $2'

        Parameters list:
              $1: ppp95_link_name
              $2: ppp95_information

        Generic LLC information trace."
    ::= { pppNotificationsPrefix 95 }

pppNotification96 NOTIFICATION-TYPE
    STATUS current
    DESCRIPTION
        "Notification of Event PPP.96

        Message: '---'

        Reserved for possible future use."
    ::= { pppNotificationsPrefix 96 }

pppNotification97 NOTIFICATION-TYPE
    STATUS current
    DESCRIPTION
        "Notification of Event PPP.97

        Message: '---'

        Reserved for possible future use."
    ::= { pppNotificationsPrefix 97 }

pppNotification98 NOTIFICATION-TYPE
    STATUS current
    DESCRIPTION
        "Notification of Event PPP.98

        Message: '---'

        Reserved for possible future use."
    ::= { pppNotificationsPrefix 98 }

pppNotification99 NOTIFICATION-TYPE
    STATUS current
    DESCRIPTION
        "Notification of Event PPP.99

        Message: '---'

        Reserved for possible future use."
    ::= { pppNotificationsPrefix 99 }

pppNotification100 NOTIFICATION-TYPE
    OBJECTS { 
              ppp100_message 
            }
    STATUS current
    DESCRIPTION
        "Notification of Event PPP.100

        Message: 'POS message: $1'

        Parameters list:
              $1: ppp100_message

        PPP POS, UDP message control management."
    ::= { pppNotificationsPrefix 100 }


END
