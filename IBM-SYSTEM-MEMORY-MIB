IBM-SYSTEM-MEMORY-MIB DEFINITIONS ::= BEGIN

IMPORTS
   OBJECT-TYPE
        FROM RFC-1212

   TRAP-TYPE
        FROM RFC-1215

   ibmSystemMemory,
   Boolean, Uint8, Sint8, Uint16, Sint16, Uint32,
   Sint32, Uint64, Sint64, Real32, Real64, String, Datetime
      FROM IBM-SYSTEM-MIB;
      

--
-- Primitive types
--
Boolean  ::= INTEGER (0..1)
Uint8    ::= INTEGER (0..255)
Sint8    ::= INTEGER (-128..127)
Uint16   ::= INTEGER (0..65535)
Sint16   ::= INTEGER (-32767..32766)
Uint32   ::= INTEGER (0..4294967295)
Sint32   ::= INTEGER (-2147483647..2147483646)
Uint64   ::= OCTET STRING
Sint64   ::= OCTET STRING
Real32   ::= INTEGER (-1..1)
Real64   ::= INTEGER (-1..1)
String   ::= OCTET STRING
Datetime ::= OCTET STRING

ibmSystemPhysicalMemoryTable OBJECT-TYPE
   SYNTAX         SEQUENCE OF IbmSystemPhysicalMemoryEntry
   ACCESS         not-accessible
   STATUS         mandatory
   DESCRIPTION    "The IBMPSG_PhysicalMemory class represents an IBM managed Memory Array."
   REFERENCE      "IBMPSG_PhysicalMemory"
::= { ibmSystemMemory 1 }

ibmSystemPhysicalMemoryEntry OBJECT-TYPE
   SYNTAX         IbmSystemPhysicalMemoryEntry
   ACCESS         not-accessible
   STATUS         mandatory
   DESCRIPTION    "This class defines an entry for each IBMPSG_PhysicalMemory
                    instance. Each instance of the IBMPSG_PhysicalMemory class 
                    contains status and descriptive information for each memory 
                    bank recognized by the operating system."
   INDEX          { ibmSystemPhysicalMemoryKeyIndex }
::= { ibmSystemPhysicalMemoryTable 1 }

IbmSystemPhysicalMemoryEntry ::= SEQUENCE
{
   ibmSystemPhysicalMemoryKeyIndex String,   
   ibmSystemPhysicalMemoryIsActive Boolean,
   ibmSystemPhysicalMemoryHasError Boolean,
   ibmSystemPhysicalMemoryPoweredOn Boolean,
   ibmSystemPhysicalMemoryTotalWidth Uint16,
   ibmSystemPhysicalMemoryDataWidth Uint16,
   ibmSystemPhysicalMemoryFormFactor Uint16,
   ibmSystemPhysicalMemoryMemoryType Uint16,
   ibmSystemPhysicalMemoryTypeDetail Uint16,
   ibmSystemPhysicalMemorySpeed Uint32,
   ibmSystemPhysicalMemoryCapacity Uint64,
   ibmSystemPhysicalMemoryBankLabel String,
   ibmSystemPhysicalMemoryDeviceLocator String,
   ibmSystemPhysicalMemoryManufacturer String,
   ibmSystemPhysicalMemoryPartNumber String,
   ibmSystemPhysicalMemorySerialNumber String,
   ibmSystemPhysicalMemoryStatus String
}

ibmSystemPhysicalMemoryKeyIndex OBJECT-TYPE
   SYNTAX         String
   ACCESS         read-write
   STATUS         mandatory
   DESCRIPTION    ""
   REFERENCE      "IBMPSG_PhysicalMemory.KeyIndex"
::= { ibmSystemPhysicalMemoryEntry 1 }

ibmSystemPhysicalMemoryIsActive OBJECT-TYPE
   SYNTAX         Boolean
   ACCESS         read-write
   STATUS         mandatory
   DESCRIPTION    ""
   REFERENCE      "IBMPSG_PhysicalMemory.IsActive"
::= { ibmSystemPhysicalMemoryEntry 2 }

ibmSystemPhysicalMemoryHasError OBJECT-TYPE
   SYNTAX         Boolean
   ACCESS         read-write
   STATUS         mandatory
   DESCRIPTION    ""
   REFERENCE      "IBMPSG_PhysicalMemory.NominalReading"
::= { ibmSystemPhysicalMemoryEntry 3 }

ibmSystemPhysicalMemoryPoweredOn OBJECT-TYPE
   SYNTAX         Boolean
   ACCESS         read-write
   STATUS         mandatory
   DESCRIPTION    ""
   REFERENCE      "IBMPSG_PhysicalMemory.PoweredOn"
::= { ibmSystemPhysicalMemoryEntry 4 }

ibmSystemPhysicalMemoryTotalWidth OBJECT-TYPE
   SYNTAX         Uint16
   ACCESS         read-write
   STATUS         mandatory
   DESCRIPTION    "Total width, in bits, of the PhysicalMemory, including check or error correction bits. If there are no error correction bits, the value in this property should match that specified for DataWidth."
   REFERENCE      "IBMPSG_PhysicalMemory.TotalWidth"
::= { ibmSystemPhysicalMemoryEntry 5 }

ibmSystemPhysicalMemoryDataWidth OBJECT-TYPE
   SYNTAX         Uint16
   ACCESS         read-write
   STATUS         mandatory
   DESCRIPTION    "Data width of the PhysicalMemory, in bits. A data width of 0 and a TotalWidth of 8 would indicate that the Memory is solely used to provide error correction bits."
   REFERENCE      "IBMPSG_PhysicalMemory.DataWidth"
::= { ibmSystemPhysicalMemoryEntry 6 }

ibmSystemPhysicalMemoryFormFactor OBJECT-TYPE
   SYNTAX         Uint16
   ACCESS         read-write
   STATUS         mandatory
   DESCRIPTION    ""
   REFERENCE      "IBMPSG_PhysicalMemory.FormFactor"
::= { ibmSystemPhysicalMemoryEntry 7 }

ibmSystemPhysicalMemoryMemoryType OBJECT-TYPE
   SYNTAX         Uint16
   ACCESS         read-write
   STATUS         mandatory
   DESCRIPTION    "The type of PhysicalMemory."
   REFERENCE      "IBMPSG_PhysicalMemory.MemoryType"
::= { ibmSystemPhysicalMemoryEntry 8 }

ibmSystemPhysicalMemoryTypeDetail OBJECT-TYPE
   SYNTAX         Uint16
   ACCESS         read-write
   STATUS         mandatory
   DESCRIPTION    ""
   REFERENCE      "IBMPSG_PhysicalMemory.TypeDetail"
::= { ibmSystemPhysicalMemoryEntry 9 }

ibmSystemPhysicalMemorySpeed OBJECT-TYPE
   SYNTAX         Uint32
   ACCESS         read-write
   STATUS         mandatory
   DESCRIPTION    "The speed of the PhysicalMemory, in nanoseconds."
   REFERENCE      "IBMPSG_PhysicalMemory.Speed"
::= { ibmSystemPhysicalMemoryEntry 10 }

ibmSystemPhysicalMemoryCapacity OBJECT-TYPE
   SYNTAX         Uint64
   ACCESS         read-write
   STATUS         mandatory
   DESCRIPTION    "The total capacity of this PhysicalMemory, in bytes."
   REFERENCE      "IBMPSG_PhysicalMemory.Capacity"
::= { ibmSystemPhysicalMemoryEntry 11 }

ibmSystemPhysicalMemoryBankLabel OBJECT-TYPE
   SYNTAX         String
   ACCESS         read-write
   STATUS         mandatory
   DESCRIPTION    "A string identifying the physically labeled bank where the Memory is located - for example, 'Bank 0' or 'Bank A'."
   REFERENCE      "IBMPSG_PhysicalMemory.BankLabel"
::= { ibmSystemPhysicalMemoryEntry 12 }

ibmSystemPhysicalMemoryDeviceLocator OBJECT-TYPE
   SYNTAX         String
   ACCESS         read-write
   STATUS         mandatory
   DESCRIPTION    ""
   REFERENCE      "IBMPSG_PhysicalMemory.DeviceLocator"
::= { ibmSystemPhysicalMemoryEntry 13 }

ibmSystemPhysicalMemoryManufacturer OBJECT-TYPE
   SYNTAX         String
   ACCESS         read-write
   STATUS         mandatory
   DESCRIPTION    "The name of the organization responsible for producing this Memory."
   REFERENCE      "IBMPSG_PhysicalMemory.Manufacturer"
::= { ibmSystemPhysicalMemoryEntry 14 }

ibmSystemPhysicalMemoryPartNumber OBJECT-TYPE
   SYNTAX         String
   ACCESS         read-write
   STATUS         mandatory
   DESCRIPTION    ""
   REFERENCE      "IBMPSG_PhysicalMemory.PartNumber"
::= { ibmSystemPhysicalMemoryEntry 15 }

ibmSystemPhysicalMemorySerialNumber OBJECT-TYPE
   SYNTAX         String
   ACCESS         read-write
   STATUS         mandatory
   DESCRIPTION    "A manufacturer-allocated number used to identify the Memory."
   REFERENCE      "IBMPSG_PhysicalMemory.SerialNumber"
::= { ibmSystemPhysicalMemoryEntry 16 }

ibmSystemPhysicalMemoryStatus OBJECT-TYPE
   SYNTAX         String
   ACCESS         read-write
   STATUS         mandatory
   DESCRIPTION    "The current Status of the Memory."
   REFERENCE      "IBMPSG_PhysicalMemory.Status"
::= { ibmSystemPhysicalMemoryEntry 17 }

END
