-- file automatically created


TELDAT-TRAP-X28-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


x28TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the X28 event subsystem."
    REVISION "201401200930Z"
    DESCRIPTION "Initial implementation"
        ::= { telEventTraps 200 }


x28EventsGroup	OBJECT IDENTIFIER	::= { x28TrapsMIB 1 }

x28Notifications	OBJECT IDENTIFIER	::= { x28TrapsMIB 2 }
x28NotificationsPrefix	OBJECT IDENTIFIER	::= { x28Notifications 0 }

x28EventObjects1 OBJECT-IDENTITY
    STATUS current
    DESCRIPTION
        "Event X28.1
        Detailed Data send to serial interface."
    ::= { x28EventsGroup 1 }

x281_interface OBJECT-TYPE
    SYNTAX DisplayString
    MAX-ACCESS accessible-for-notify
    STATUS current
    DESCRIPTION
        "Parameter 'interface' in event X28.1"
    ::= { x28EventObjects1 1 }

x281_lenght OBJECT-TYPE
    SYNTAX Integer32
    MAX-ACCESS accessible-for-notify
    STATUS current
    DESCRIPTION
        "Parameter 'lenght' in event X28.1"
    ::= { x28EventObjects1 2 }

x281_state OBJECT-TYPE
    SYNTAX Integer32
    MAX-ACCESS accessible-for-notify
    STATUS current
    DESCRIPTION
        "Parameter 'state' in event X28.1"
    ::= { x28EventObjects1 3 }

x281_hex_data OBJECT-TYPE
    SYNTAX DisplayString
    MAX-ACCESS accessible-for-notify
    STATUS current
    DESCRIPTION
        "Parameter 'hex_data' in event X28.1"
    ::= { x28EventObjects1 4 }

x28EventObjects2 OBJECT-IDENTITY
    STATUS current
    DESCRIPTION
        "Event X28.2
        Detailed Data received from serial interface."
    ::= { x28EventsGroup 2 }

x282_interface OBJECT-TYPE
    SYNTAX DisplayString
    MAX-ACCESS accessible-for-notify
    STATUS current
    DESCRIPTION
        "Parameter 'interface' in event X28.2"
    ::= { x28EventObjects2 1 }

x282_lenght OBJECT-TYPE
    SYNTAX Integer32
    MAX-ACCESS accessible-for-notify
    STATUS current
    DESCRIPTION
        "Parameter 'lenght' in event X28.2"
    ::= { x28EventObjects2 2 }

x282_state OBJECT-TYPE
    SYNTAX Integer32
    MAX-ACCESS accessible-for-notify
    STATUS current
    DESCRIPTION
        "Parameter 'state' in event X28.2"
    ::= { x28EventObjects2 3 }

x282_hex_data OBJECT-TYPE
    SYNTAX DisplayString
    MAX-ACCESS accessible-for-notify
    STATUS current
    DESCRIPTION
        "Parameter 'hex_data' in event X28.2"
    ::= { x28EventObjects2 4 }

x28EventObjects3 OBJECT-IDENTITY
    STATUS current
    DESCRIPTION
        "Event X28.3
        A change ON/OFF has been detected in Serial Control Signal Input."
    ::= { x28EventsGroup 3 }

x283_message_type OBJECT-TYPE
    SYNTAX DisplayString
    MAX-ACCESS accessible-for-notify
    STATUS current
    DESCRIPTION
        "Parameter 'message_type' in event X28.3"
    ::= { x28EventObjects3 1 }

x283_interface OBJECT-TYPE
    SYNTAX DisplayString
    MAX-ACCESS accessible-for-notify
    STATUS current
    DESCRIPTION
        "Parameter 'interface' in event X28.3"
    ::= { x28EventObjects3 2 }

x283_state OBJECT-TYPE
    SYNTAX Integer32
    MAX-ACCESS accessible-for-notify
    STATUS current
    DESCRIPTION
        "Parameter 'state' in event X28.3"
    ::= { x28EventObjects3 3 }

x28EventObjects4 OBJECT-IDENTITY
    STATUS current
    DESCRIPTION
        "Event X28.4
        BREAK signal has been received from serial interface."
    ::= { x28EventsGroup 4 }

x284_interface OBJECT-TYPE
    SYNTAX DisplayString
    MAX-ACCESS accessible-for-notify
    STATUS current
    DESCRIPTION
        "Parameter 'interface' in event X28.4"
    ::= { x28EventObjects4 1 }

x284_state OBJECT-TYPE
    SYNTAX Integer32
    MAX-ACCESS accessible-for-notify
    STATUS current
    DESCRIPTION
        "Parameter 'state' in event X28.4"
    ::= { x28EventObjects4 2 }

x28EventObjects5 OBJECT-IDENTITY
    STATUS current
    DESCRIPTION
        "Event X28.5
        Session not found, when data has been received from serial interface."
    ::= { x28EventsGroup 5 }

x285_interface OBJECT-TYPE
    SYNTAX DisplayString
    MAX-ACCESS accessible-for-notify
    STATUS current
    DESCRIPTION
        "Parameter 'interface' in event X28.5"
    ::= { x28EventObjects5 1 }

x28EventObjects6 OBJECT-IDENTITY
    STATUS current
    DESCRIPTION
        "Event X28.6
        X28 command has been received from serial interface."
    ::= { x28EventsGroup 6 }

x286_rx_cmd OBJECT-TYPE
    SYNTAX DisplayString
    MAX-ACCESS accessible-for-notify
    STATUS current
    DESCRIPTION
        "Parameter 'rx_cmd' in event X28.6"
    ::= { x28EventObjects6 1 }

x286_interface OBJECT-TYPE
    SYNTAX DisplayString
    MAX-ACCESS accessible-for-notify
    STATUS current
    DESCRIPTION
        "Parameter 'interface' in event X28.6"
    ::= { x28EventObjects6 2 }

x286_state OBJECT-TYPE
    SYNTAX Integer32
    MAX-ACCESS accessible-for-notify
    STATUS current
    DESCRIPTION
        "Parameter 'state' in event X28.6"
    ::= { x28EventObjects6 3 }


x28Notification1 NOTIFICATION-TYPE
    OBJECTS { 
              x281_interface, 
              x281_lenght,
              x281_state,
              x281_hex_data 
            }
    STATUS current
    DESCRIPTION
        "Notification of Event X28.1

        Message: 'Data transmitted to serial interface $1 ($2 bytes, st $3):$4'

        Parameters list:
              $1: x281_interface
              $2: x281_lenght
              $3: x281_state
              $4: x281_hex_data

        Detailed Data send to serial interface."
    ::= { x28NotificationsPrefix 1 }

x28Notification2 NOTIFICATION-TYPE
    OBJECTS { 
              x282_interface, 
              x282_lenght,
              x282_state,
              x282_hex_data 
            }
    STATUS current
    DESCRIPTION
        "Notification of Event X28.2

        Message: 'Data received from serial interface $1 ($2 bytes, st $3):$4'

        Parameters list:
              $1: x282_interface
              $2: x282_lenght
              $3: x282_state
              $4: x282_hex_data

        Detailed Data received from serial interface."
    ::= { x28NotificationsPrefix 2 }

x28Notification3 NOTIFICATION-TYPE
    OBJECTS { 
              x283_message_type, 
              x283_interface,
              x283_state 
            }
    STATUS current
    DESCRIPTION
        "Notification of Event X28.3

        Message: 'Serial Control Signal Input change to $1, interface $2 state $3'

        Parameters list:
              $1: x283_message_type
              $2: x283_interface
              $3: x283_state

        A change ON/OFF has been detected in Serial Control Signal Input."
    ::= { x28NotificationsPrefix 3 }

x28Notification4 NOTIFICATION-TYPE
    OBJECTS { 
              x284_interface, 
              x284_state 
            }
    STATUS current
    DESCRIPTION
        "Notification of Event X28.4

        Message: 'Received BREAK signal from ifc $1, state $2'

        Parameters list:
              $1: x284_interface
              $2: x284_state

        BREAK signal has been received from serial interface."
    ::= { x28NotificationsPrefix 4 }

x28Notification5 NOTIFICATION-TYPE
    OBJECTS { 
              x285_interface 
            }
    STATUS current
    DESCRIPTION
        "Notification of Event X28.5

        Message: 'In-Data serial data, session not found ifc $1'

        Parameters list:
              $1: x285_interface

        Session not found, when data has been received from serial interface."
    ::= { x28NotificationsPrefix 5 }

x28Notification6 NOTIFICATION-TYPE
    OBJECTS { 
              x286_rx_cmd, 
              x286_interface,
              x286_state 
            }
    STATUS current
    DESCRIPTION
        "Notification of Event X28.6

        Message: 'Received command $1 from interface $2 state $3'

        Parameters list:
              $1: x286_rx_cmd
              $2: x286_interface
              $3: x286_state

        X28 command has been received from serial interface."
    ::= { x28NotificationsPrefix 6 }


END
