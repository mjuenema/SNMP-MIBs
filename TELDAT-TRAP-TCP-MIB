-- file automatically created


TELDAT-TRAP-TCP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tcpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TCP event subsystem."
    REVISION "201401200930Z"
    DESCRIPTION "Initial implementation"
        ::= { telEventTraps 12 }


tcpEventsGroup	OBJECT IDENTIFIER	::= { tcpTrapsMIB 1 }

tcpNotifications	OBJECT IDENTIFIER	::= { tcpTrapsMIB 2 }
tcpNotificationsPrefix	OBJECT IDENTIFIER	::= { tcpNotifications 0 }

tcpEventObjects1 OBJECT-IDENTITY
    STATUS current
    DESCRIPTION
        "Event TCP.1
        Checksum failed because received packet checksum is not equal to
        the calculated checksum."
    ::= { tcpEventsGroup 1 }

tcp1_tcp_checksum OBJECT-TYPE
    SYNTAX Integer32
    MAX-ACCESS accessible-for-notify
    STATUS current
    DESCRIPTION
        "Parameter 'tcp_checksum' in event TCP.1"
    ::= { tcpEventObjects1 1 }

tcpEventObjects2 OBJECT-IDENTITY
    STATUS current
    DESCRIPTION
        "Event TCP.2
        TCP has received a packet with an invalid tcp port number."
    ::= { tcpEventsGroup 2 }

tcp2_source_ip_address OBJECT-TYPE
    SYNTAX IpAddress
    MAX-ACCESS accessible-for-notify
    STATUS current
    DESCRIPTION
        "Parameter 'source_ip_address' in event TCP.2"
    ::= { tcpEventObjects2 1 }

tcp2_source_tcp_port OBJECT-TYPE
    SYNTAX Integer32
    MAX-ACCESS accessible-for-notify
    STATUS current
    DESCRIPTION
        "Parameter 'source_tcp_port' in event TCP.2"
    ::= { tcpEventObjects2 2 }

tcp2_destination_ip_address OBJECT-TYPE
    SYNTAX IpAddress
    MAX-ACCESS accessible-for-notify
    STATUS current
    DESCRIPTION
        "Parameter 'destination_ip_address' in event TCP.2"
    ::= { tcpEventObjects2 3 }

tcp2_destination_tcp_port OBJECT-TYPE
    SYNTAX Integer32
    MAX-ACCESS accessible-for-notify
    STATUS current
    DESCRIPTION
        "Parameter 'destination_tcp_port' in event TCP.2"
    ::= { tcpEventObjects2 4 }

tcpEventObjects3 OBJECT-IDENTITY
    STATUS current
    DESCRIPTION
        "Event TCP.3
        Active open was successful and we are notifying application of the open."
    ::= { tcpEventsGroup 3 }

tcp3_local_ip_address OBJECT-TYPE
    SYNTAX IpAddress
    MAX-ACCESS accessible-for-notify
    STATUS current
    DESCRIPTION
        "Parameter 'local_ip_address' in event TCP.3"
    ::= { tcpEventObjects3 1 }

tcp3_local_tcp_port OBJECT-TYPE
    SYNTAX Integer32
    MAX-ACCESS accessible-for-notify
    STATUS current
    DESCRIPTION
        "Parameter 'local_tcp_port' in event TCP.3"
    ::= { tcpEventObjects3 2 }

tcp3_remote_ip_address OBJECT-TYPE
    SYNTAX IpAddress
    MAX-ACCESS accessible-for-notify
    STATUS current
    DESCRIPTION
        "Parameter 'remote_ip_address' in event TCP.3"
    ::= { tcpEventObjects3 3 }

tcp3_remote_tcp_port OBJECT-TYPE
    SYNTAX Integer32
    MAX-ACCESS accessible-for-notify
    STATUS current
    DESCRIPTION
        "Parameter 'remote_tcp_port' in event TCP.3"
    ::= { tcpEventObjects3 4 }

tcpEventObjects4 OBJECT-IDENTITY
    STATUS current
    DESCRIPTION
        "Event TCP.4
        TCP has received an illegal SYN packet, so kill the connection."
    ::= { tcpEventsGroup 4 }

tcp4_source_ip_address OBJECT-TYPE
    SYNTAX IpAddress
    MAX-ACCESS accessible-for-notify
    STATUS current
    DESCRIPTION
        "Parameter 'source_ip_address' in event TCP.4"
    ::= { tcpEventObjects4 1 }

tcp4_source_tcp_port OBJECT-TYPE
    SYNTAX Integer32
    MAX-ACCESS accessible-for-notify
    STATUS current
    DESCRIPTION
        "Parameter 'source_tcp_port' in event TCP.4"
    ::= { tcpEventObjects4 2 }

tcp4_destination_ip_address OBJECT-TYPE
    SYNTAX IpAddress
    MAX-ACCESS accessible-for-notify
    STATUS current
    DESCRIPTION
        "Parameter 'destination_ip_address' in event TCP.4"
    ::= { tcpEventObjects4 3 }

tcp4_destination_tcp_port OBJECT-TYPE
    SYNTAX Integer32
    MAX-ACCESS accessible-for-notify
    STATUS current
    DESCRIPTION
        "Parameter 'destination_tcp_port' in event TCP.4"
    ::= { tcpEventObjects4 4 }

tcpEventObjects5 OBJECT-IDENTITY
    STATUS current
    DESCRIPTION
        "Event TCP.5
        Debug string."
    ::= { tcpEventsGroup 5 }

tcp5_debug_string OBJECT-TYPE
    SYNTAX DisplayString
    MAX-ACCESS accessible-for-notify
    STATUS current
    DESCRIPTION
        "Parameter 'debug_string' in event TCP.5"
    ::= { tcpEventObjects5 1 }

tcpEventObjects6 OBJECT-IDENTITY
    STATUS current
    DESCRIPTION
        "Event TCP.6
        TCP has received an invalid packet when MD5 authentication is active, so drop packet."
    ::= { tcpEventsGroup 6 }

tcp6_source_ip_address OBJECT-TYPE
    SYNTAX IpAddress
    MAX-ACCESS accessible-for-notify
    STATUS current
    DESCRIPTION
        "Parameter 'source_ip_address' in event TCP.6"
    ::= { tcpEventObjects6 1 }

tcp6_source_tcp_port OBJECT-TYPE
    SYNTAX Integer32
    MAX-ACCESS accessible-for-notify
    STATUS current
    DESCRIPTION
        "Parameter 'source_tcp_port' in event TCP.6"
    ::= { tcpEventObjects6 2 }

tcp6_destination_ip_address OBJECT-TYPE
    SYNTAX IpAddress
    MAX-ACCESS accessible-for-notify
    STATUS current
    DESCRIPTION
        "Parameter 'destination_ip_address' in event TCP.6"
    ::= { tcpEventObjects6 3 }

tcp6_destination_tcp_port OBJECT-TYPE
    SYNTAX Integer32
    MAX-ACCESS accessible-for-notify
    STATUS current
    DESCRIPTION
        "Parameter 'destination_tcp_port' in event TCP.6"
    ::= { tcpEventObjects6 4 }

tcp6_reason OBJECT-TYPE
    SYNTAX DisplayString
    MAX-ACCESS accessible-for-notify
    STATUS current
    DESCRIPTION
        "Parameter 'reason' in event TCP.6"
    ::= { tcpEventObjects6 5 }

tcpEventObjects7 OBJECT-IDENTITY
    STATUS current
    DESCRIPTION
        "Event TCP.7
        TCP has rejected a segment. Reject codes are as follows:
        Reject codes:
        1 - Seg len = 0, Rcv win > 0, seqnum < tcb_ack or seqnum >= winend
        2 - Seg len = 0, Rcv win = 0, seqnum != tcb_ack
        3 - Seg len > 0, Rcv win > 0, inend < tcb_ack or seqnum >= winend
        4 - Seg len > 0, Rcv win = 0.
        Note: we only ACK if the segment received was a non RST segment."
    ::= { tcpEventsGroup 7 }

tcp7_source_ip_address OBJECT-TYPE
    SYNTAX IpAddress
    MAX-ACCESS accessible-for-notify
    STATUS current
    DESCRIPTION
        "Parameter 'source_ip_address' in event TCP.7"
    ::= { tcpEventObjects7 1 }

tcp7_source_port OBJECT-TYPE
    SYNTAX Integer32
    MAX-ACCESS accessible-for-notify
    STATUS current
    DESCRIPTION
        "Parameter 'source_port' in event TCP.7"
    ::= { tcpEventObjects7 2 }

tcp7_destination_ip_address OBJECT-TYPE
    SYNTAX IpAddress
    MAX-ACCESS accessible-for-notify
    STATUS current
    DESCRIPTION
        "Parameter 'destination_ip_address' in event TCP.7"
    ::= { tcpEventObjects7 3 }

tcp7_destination_port OBJECT-TYPE
    SYNTAX Integer32
    MAX-ACCESS accessible-for-notify
    STATUS current
    DESCRIPTION
        "Parameter 'destination_port' in event TCP.7"
    ::= { tcpEventObjects7 4 }

tcp7_reject_code OBJECT-TYPE
    SYNTAX Integer32
    MAX-ACCESS accessible-for-notify
    STATUS current
    DESCRIPTION
        "Parameter 'reject_code' in event TCP.7"
    ::= { tcpEventObjects7 5 }

tcpEventObjects8 OBJECT-IDENTITY
    STATUS current
    DESCRIPTION
        "Event TCP.8
        TCP has received an old segment that has already been consumed by the
        application, so send ACK in response."
    ::= { tcpEventsGroup 8 }

tcp8_source_ip_address OBJECT-TYPE
    SYNTAX IpAddress
    MAX-ACCESS accessible-for-notify
    STATUS current
    DESCRIPTION
        "Parameter 'source_ip_address' in event TCP.8"
    ::= { tcpEventObjects8 1 }

tcp8_source_tcp_port OBJECT-TYPE
    SYNTAX Integer32
    MAX-ACCESS accessible-for-notify
    STATUS current
    DESCRIPTION
        "Parameter 'source_tcp_port' in event TCP.8"
    ::= { tcpEventObjects8 2 }

tcp8_destination_ip_address OBJECT-TYPE
    SYNTAX IpAddress
    MAX-ACCESS accessible-for-notify
    STATUS current
    DESCRIPTION
        "Parameter 'destination_ip_address' in event TCP.8"
    ::= { tcpEventObjects8 3 }

tcp8_destination_tcp_port OBJECT-TYPE
    SYNTAX Integer32
    MAX-ACCESS accessible-for-notify
    STATUS current
    DESCRIPTION
        "Parameter 'destination_tcp_port' in event TCP.8"
    ::= { tcpEventObjects8 4 }

tcp8_seq_num OBJECT-TYPE
    SYNTAX Integer32
    MAX-ACCESS accessible-for-notify
    STATUS current
    DESCRIPTION
        "Parameter 'seq_num' in event TCP.8"
    ::= { tcpEventObjects8 5 }

tcpEventObjects9 OBJECT-IDENTITY
    STATUS current
    DESCRIPTION
        "Event TCP.9
        TCP has received a RST while in LISTEN state; just ignore packet."
    ::= { tcpEventsGroup 9 }

tcp9_source_ip_address OBJECT-TYPE
    SYNTAX IpAddress
    MAX-ACCESS accessible-for-notify
    STATUS current
    DESCRIPTION
        "Parameter 'source_ip_address' in event TCP.9"
    ::= { tcpEventObjects9 1 }

tcp9_source_tcp_port OBJECT-TYPE
    SYNTAX Integer32
    MAX-ACCESS accessible-for-notify
    STATUS current
    DESCRIPTION
        "Parameter 'source_tcp_port' in event TCP.9"
    ::= { tcpEventObjects9 2 }

tcp9_destination_ip_address OBJECT-TYPE
    SYNTAX IpAddress
    MAX-ACCESS accessible-for-notify
    STATUS current
    DESCRIPTION
        "Parameter 'destination_ip_address' in event TCP.9"
    ::= { tcpEventObjects9 3 }

tcp9_destination_tcp_port OBJECT-TYPE
    SYNTAX Integer32
    MAX-ACCESS accessible-for-notify
    STATUS current
    DESCRIPTION
        "Parameter 'destination_tcp_port' in event TCP.9"
    ::= { tcpEventObjects9 4 }

tcp9_seq_num OBJECT-TYPE
    SYNTAX Integer32
    MAX-ACCESS accessible-for-notify
    STATUS current
    DESCRIPTION
        "Parameter 'seq_num' in event TCP.9"
    ::= { tcpEventObjects9 5 }

tcpEventObjects10 OBJECT-IDENTITY
    STATUS current
    DESCRIPTION
        "Event TCP.10
        TCP has received a RST while in SYN_RECEIVED or SYN_SENT states;
        drop packet and return to LISTEN state."
    ::= { tcpEventsGroup 10 }

tcp10_source_ip_address OBJECT-TYPE
    SYNTAX IpAddress
    MAX-ACCESS accessible-for-notify
    STATUS current
    DESCRIPTION
        "Parameter 'source_ip_address' in event TCP.10"
    ::= { tcpEventObjects10 1 }

tcp10_source_tcp_port OBJECT-TYPE
    SYNTAX Integer32
    MAX-ACCESS accessible-for-notify
    STATUS current
    DESCRIPTION
        "Parameter 'source_tcp_port' in event TCP.10"
    ::= { tcpEventObjects10 2 }

tcp10_destination_ip_address OBJECT-TYPE
    SYNTAX IpAddress
    MAX-ACCESS accessible-for-notify
    STATUS current
    DESCRIPTION
        "Parameter 'destination_ip_address' in event TCP.10"
    ::= { tcpEventObjects10 3 }

tcp10_destination_tcp_port OBJECT-TYPE
    SYNTAX Integer32
    MAX-ACCESS accessible-for-notify
    STATUS current
    DESCRIPTION
        "Parameter 'destination_tcp_port' in event TCP.10"
    ::= { tcpEventObjects10 4 }

tcp10_seq_num OBJECT-TYPE
    SYNTAX Integer32
    MAX-ACCESS accessible-for-notify
    STATUS current
    DESCRIPTION
        "Parameter 'seq_num' in event TCP.10"
    ::= { tcpEventObjects10 5 }

tcpEventObjects11 OBJECT-IDENTITY
    STATUS current
    DESCRIPTION
        "Event TCP.11
        TCP has received a RST; abort connection."
    ::= { tcpEventsGroup 11 }

tcp11_source_ip_address OBJECT-TYPE
    SYNTAX IpAddress
    MAX-ACCESS accessible-for-notify
    STATUS current
    DESCRIPTION
        "Parameter 'source_ip_address' in event TCP.11"
    ::= { tcpEventObjects11 1 }

tcp11_source_tcp_port OBJECT-TYPE
    SYNTAX Integer32
    MAX-ACCESS accessible-for-notify
    STATUS current
    DESCRIPTION
        "Parameter 'source_tcp_port' in event TCP.11"
    ::= { tcpEventObjects11 2 }

tcp11_destination_ip_address OBJECT-TYPE
    SYNTAX IpAddress
    MAX-ACCESS accessible-for-notify
    STATUS current
    DESCRIPTION
        "Parameter 'destination_ip_address' in event TCP.11"
    ::= { tcpEventObjects11 3 }

tcp11_destination_tcp_port OBJECT-TYPE
    SYNTAX Integer32
    MAX-ACCESS accessible-for-notify
    STATUS current
    DESCRIPTION
        "Parameter 'destination_tcp_port' in event TCP.11"
    ::= { tcpEventObjects11 4 }

tcp11_seq_num OBJECT-TYPE
    SYNTAX Integer32
    MAX-ACCESS accessible-for-notify
    STATUS current
    DESCRIPTION
        "Parameter 'seq_num' in event TCP.11"
    ::= { tcpEventObjects11 5 }

tcpEventObjects12 OBJECT-IDENTITY
    STATUS current
    DESCRIPTION
        "Event TCP.12
        TCP has stopped processing the packet because there is no ACK present
        in the packet."
    ::= { tcpEventsGroup 12 }

tcp12_source_ip_address OBJECT-TYPE
    SYNTAX IpAddress
    MAX-ACCESS accessible-for-notify
    STATUS current
    DESCRIPTION
        "Parameter 'source_ip_address' in event TCP.12"
    ::= { tcpEventObjects12 1 }

tcp12_source_tcp_port OBJECT-TYPE
    SYNTAX Integer32
    MAX-ACCESS accessible-for-notify
    STATUS current
    DESCRIPTION
        "Parameter 'source_tcp_port' in event TCP.12"
    ::= { tcpEventObjects12 2 }

tcp12_destination_ip_address OBJECT-TYPE
    SYNTAX IpAddress
    MAX-ACCESS accessible-for-notify
    STATUS current
    DESCRIPTION
        "Parameter 'destination_ip_address' in event TCP.12"
    ::= { tcpEventObjects12 3 }

tcp12_destination_tcp_port OBJECT-TYPE
    SYNTAX Integer32
    MAX-ACCESS accessible-for-notify
    STATUS current
    DESCRIPTION
        "Parameter 'destination_tcp_port' in event TCP.12"
    ::= { tcpEventObjects12 4 }

tcp12_seq_num OBJECT-TYPE
    SYNTAX Integer32
    MAX-ACCESS accessible-for-notify
    STATUS current
    DESCRIPTION
        "Parameter 'seq_num' in event TCP.12"
    ::= { tcpEventObjects12 5 }

tcpEventObjects13 OBJECT-IDENTITY
    STATUS current
    DESCRIPTION
        "Event TCP.13
        Stop processing the segment because it contains acknowledgement for
        data not yet sent."
    ::= { tcpEventsGroup 13 }

tcp13_source_ip_address OBJECT-TYPE
    SYNTAX IpAddress
    MAX-ACCESS accessible-for-notify
    STATUS current
    DESCRIPTION
        "Parameter 'source_ip_address' in event TCP.13"
    ::= { tcpEventObjects13 1 }

tcp13_source_tcp_port OBJECT-TYPE
    SYNTAX Integer32
    MAX-ACCESS accessible-for-notify
    STATUS current
    DESCRIPTION
        "Parameter 'source_tcp_port' in event TCP.13"
    ::= { tcpEventObjects13 2 }

tcp13_destination_ip_address OBJECT-TYPE
    SYNTAX IpAddress
    MAX-ACCESS accessible-for-notify
    STATUS current
    DESCRIPTION
        "Parameter 'destination_ip_address' in event TCP.13"
    ::= { tcpEventObjects13 3 }

tcp13_destination_tcp_port OBJECT-TYPE
    SYNTAX Integer32
    MAX-ACCESS accessible-for-notify
    STATUS current
    DESCRIPTION
        "Parameter 'destination_tcp_port' in event TCP.13"
    ::= { tcpEventObjects13 4 }

tcp13_seq_num OBJECT-TYPE
    SYNTAX Integer32
    MAX-ACCESS accessible-for-notify
    STATUS current
    DESCRIPTION
        "Parameter 'seq_num' in event TCP.13"
    ::= { tcpEventObjects13 5 }

tcp13_ack_num OBJECT-TYPE
    SYNTAX Integer32
    MAX-ACCESS accessible-for-notify
    STATUS current
    DESCRIPTION
        "Parameter 'ack_num' in event TCP.13"
    ::= { tcpEventObjects13 6 }

tcpEventObjects14 OBJECT-IDENTITY
    STATUS current
    DESCRIPTION
        "Event TCP.14
        TCP has received a FIN while in ESTABLISHED state; when all data
        has been received, send FIN|ACK."
    ::= { tcpEventsGroup 14 }

tcp14_source_ip_address OBJECT-TYPE
    SYNTAX IpAddress
    MAX-ACCESS accessible-for-notify
    STATUS current
    DESCRIPTION
        "Parameter 'source_ip_address' in event TCP.14"
    ::= { tcpEventObjects14 1 }

tcp14_source_tcp_port OBJECT-TYPE
    SYNTAX Integer32
    MAX-ACCESS accessible-for-notify
    STATUS current
    DESCRIPTION
        "Parameter 'source_tcp_port' in event TCP.14"
    ::= { tcpEventObjects14 2 }

tcp14_destination_ip_address OBJECT-TYPE
    SYNTAX IpAddress
    MAX-ACCESS accessible-for-notify
    STATUS current
    DESCRIPTION
        "Parameter 'destination_ip_address' in event TCP.14"
    ::= { tcpEventObjects14 3 }

tcp14_destination_tcp_port OBJECT-TYPE
    SYNTAX Integer32
    MAX-ACCESS accessible-for-notify
    STATUS current
    DESCRIPTION
        "Parameter 'destination_tcp_port' in event TCP.14"
    ::= { tcpEventObjects14 4 }

tcp14_seq_num OBJECT-TYPE
    SYNTAX Integer32
    MAX-ACCESS accessible-for-notify
    STATUS current
    DESCRIPTION
        "Parameter 'seq_num' in event TCP.14"
    ::= { tcpEventObjects14 5 }

tcpEventObjects15 OBJECT-IDENTITY
    STATUS current
    DESCRIPTION
        "Event TCP.15
        TCP has received a segment with PSH bit set."
    ::= { tcpEventsGroup 15 }

tcp15_source_ip_address OBJECT-TYPE
    SYNTAX IpAddress
    MAX-ACCESS accessible-for-notify
    STATUS current
    DESCRIPTION
        "Parameter 'source_ip_address' in event TCP.15"
    ::= { tcpEventObjects15 1 }

tcp15_source_tcp_port OBJECT-TYPE
    SYNTAX Integer32
    MAX-ACCESS accessible-for-notify
    STATUS current
    DESCRIPTION
        "Parameter 'source_tcp_port' in event TCP.15"
    ::= { tcpEventObjects15 2 }

tcp15_destination_ip_address OBJECT-TYPE
    SYNTAX IpAddress
    MAX-ACCESS accessible-for-notify
    STATUS current
    DESCRIPTION
        "Parameter 'destination_ip_address' in event TCP.15"
    ::= { tcpEventObjects15 3 }

tcp15_destination_tcp_port OBJECT-TYPE
    SYNTAX Integer32
    MAX-ACCESS accessible-for-notify
    STATUS current
    DESCRIPTION
        "Parameter 'destination_tcp_port' in event TCP.15"
    ::= { tcpEventObjects15 4 }

tcp15_seq_num OBJECT-TYPE
    SYNTAX Integer32
    MAX-ACCESS accessible-for-notify
    STATUS current
    DESCRIPTION
        "Parameter 'seq_num' in event TCP.15"
    ::= { tcpEventObjects15 5 }

tcpEventObjects16 OBJECT-IDENTITY
    STATUS current
    DESCRIPTION
        "Event TCP.16
        TCP has received a valid segment while in SYNRCVD state; enter
        ESTABLISHED state and notify application of the open."
    ::= { tcpEventsGroup 16 }

tcp16_source_ip_address OBJECT-TYPE
    SYNTAX IpAddress
    MAX-ACCESS accessible-for-notify
    STATUS current
    DESCRIPTION
        "Parameter 'source_ip_address' in event TCP.16"
    ::= { tcpEventObjects16 1 }

tcp16_source_tcp_port OBJECT-TYPE
    SYNTAX Integer32
    MAX-ACCESS accessible-for-notify
    STATUS current
    DESCRIPTION
        "Parameter 'source_tcp_port' in event TCP.16"
    ::= { tcpEventObjects16 2 }

tcp16_destination_ip_address OBJECT-TYPE
    SYNTAX IpAddress
    MAX-ACCESS accessible-for-notify
    STATUS current
    DESCRIPTION
        "Parameter 'destination_ip_address' in event TCP.16"
    ::= { tcpEventObjects16 3 }

tcp16_destination_tcp_port OBJECT-TYPE
    SYNTAX Integer32
    MAX-ACCESS accessible-for-notify
    STATUS current
    DESCRIPTION
        "Parameter 'destination_tcp_port' in event TCP.16"
    ::= { tcpEventObjects16 4 }

tcp16_seq_num OBJECT-TYPE
    SYNTAX Integer32
    MAX-ACCESS accessible-for-notify
    STATUS current
    DESCRIPTION
        "Parameter 'seq_num' in event TCP.16"
    ::= { tcpEventObjects16 5 }

tcpEventObjects17 OBJECT-IDENTITY
    STATUS current
    DESCRIPTION
        "Event TCP.17
        TCP has received a FIN while in the LISTEN state, so we send RST to
        the other side."
    ::= { tcpEventsGroup 17 }

tcp17_source_ip_address OBJECT-TYPE
    SYNTAX IpAddress
    MAX-ACCESS accessible-for-notify
    STATUS current
    DESCRIPTION
        "Parameter 'source_ip_address' in event TCP.17"
    ::= { tcpEventObjects17 1 }

tcp17_source_tcp_port OBJECT-TYPE
    SYNTAX Integer32
    MAX-ACCESS accessible-for-notify
    STATUS current
    DESCRIPTION
        "Parameter 'source_tcp_port' in event TCP.17"
    ::= { tcpEventObjects17 2 }

tcp17_destination_ip_address OBJECT-TYPE
    SYNTAX IpAddress
    MAX-ACCESS accessible-for-notify
    STATUS current
    DESCRIPTION
        "Parameter 'destination_ip_address' in event TCP.17"
    ::= { tcpEventObjects17 3 }

tcp17_destination_tcp_port OBJECT-TYPE
    SYNTAX Integer32
    MAX-ACCESS accessible-for-notify
    STATUS current
    DESCRIPTION
        "Parameter 'destination_tcp_port' in event TCP.17"
    ::= { tcpEventObjects17 4 }

tcp17_seq_num OBJECT-TYPE
    SYNTAX Integer32
    MAX-ACCESS accessible-for-notify
    STATUS current
    DESCRIPTION
        "Parameter 'seq_num' in event TCP.17"
    ::= { tcpEventObjects17 5 }

tcpEventObjects18 OBJECT-IDENTITY
    STATUS current
    DESCRIPTION
        "Event TCP.18
        TCP has received an out of order packet; this creates a hole in
        the receive buffer."
    ::= { tcpEventsGroup 18 }

tcp18_source_ip_address OBJECT-TYPE
    SYNTAX IpAddress
    MAX-ACCESS accessible-for-notify
    STATUS current
    DESCRIPTION
        "Parameter 'source_ip_address' in event TCP.18"
    ::= { tcpEventObjects18 1 }

tcp18_source_tcp_port OBJECT-TYPE
    SYNTAX Integer32
    MAX-ACCESS accessible-for-notify
    STATUS current
    DESCRIPTION
        "Parameter 'source_tcp_port' in event TCP.18"
    ::= { tcpEventObjects18 2 }

tcp18_destination_ip_address OBJECT-TYPE
    SYNTAX IpAddress
    MAX-ACCESS accessible-for-notify
    STATUS current
    DESCRIPTION
        "Parameter 'destination_ip_address' in event TCP.18"
    ::= { tcpEventObjects18 3 }

tcp18_destination_tcp_port OBJECT-TYPE
    SYNTAX Integer32
    MAX-ACCESS accessible-for-notify
    STATUS current
    DESCRIPTION
        "Parameter 'destination_tcp_port' in event TCP.18"
    ::= { tcpEventObjects18 4 }

tcp18_seq_num OBJECT-TYPE
    SYNTAX Integer32
    MAX-ACCESS accessible-for-notify
    STATUS current
    DESCRIPTION
        "Parameter 'seq_num' in event TCP.18"
    ::= { tcpEventObjects18 5 }

tcpEventObjects19 OBJECT-IDENTITY
    STATUS current
    DESCRIPTION
        "Event TCP.19
        TCP has received an out of order packet; this creates a hole in
        the receive buffer."
    ::= { tcpEventsGroup 19 }

tcp19_source_ip_address OBJECT-TYPE
    SYNTAX IpAddress
    MAX-ACCESS accessible-for-notify
    STATUS current
    DESCRIPTION
        "Parameter 'source_ip_address' in event TCP.19"
    ::= { tcpEventObjects19 1 }

tcp19_source_tcp_port OBJECT-TYPE
    SYNTAX Integer32
    MAX-ACCESS accessible-for-notify
    STATUS current
    DESCRIPTION
        "Parameter 'source_tcp_port' in event TCP.19"
    ::= { tcpEventObjects19 2 }

tcp19_destination_ip_address OBJECT-TYPE
    SYNTAX IpAddress
    MAX-ACCESS accessible-for-notify
    STATUS current
    DESCRIPTION
        "Parameter 'destination_ip_address' in event TCP.19"
    ::= { tcpEventObjects19 3 }

tcp19_destination_tcp_port OBJECT-TYPE
    SYNTAX Integer32
    MAX-ACCESS accessible-for-notify
    STATUS current
    DESCRIPTION
        "Parameter 'destination_tcp_port' in event TCP.19"
    ::= { tcpEventObjects19 4 }

tcp19_seq_num OBJECT-TYPE
    SYNTAX Integer32
    MAX-ACCESS accessible-for-notify
    STATUS current
    DESCRIPTION
        "Parameter 'seq_num' in event TCP.19"
    ::= { tcpEventObjects19 5 }

tcpEventObjects20 OBJECT-IDENTITY
    STATUS current
    DESCRIPTION
        "Event TCP.20
        TCP has received a packet that partially fills the beginning of a hole."
    ::= { tcpEventsGroup 20 }

tcp20_source_ip_address OBJECT-TYPE
    SYNTAX IpAddress
    MAX-ACCESS accessible-for-notify
    STATUS current
    DESCRIPTION
        "Parameter 'source_ip_address' in event TCP.20"
    ::= { tcpEventObjects20 1 }

tcp20_source_tcp_port OBJECT-TYPE
    SYNTAX Integer32
    MAX-ACCESS accessible-for-notify
    STATUS current
    DESCRIPTION
        "Parameter 'source_tcp_port' in event TCP.20"
    ::= { tcpEventObjects20 2 }

tcp20_destination_ip_address OBJECT-TYPE
    SYNTAX IpAddress
    MAX-ACCESS accessible-for-notify
    STATUS current
    DESCRIPTION
        "Parameter 'destination_ip_address' in event TCP.20"
    ::= { tcpEventObjects20 3 }

tcp20_destination_tcp_port OBJECT-TYPE
    SYNTAX Integer32
    MAX-ACCESS accessible-for-notify
    STATUS current
    DESCRIPTION
        "Parameter 'destination_tcp_port' in event TCP.20"
    ::= { tcpEventObjects20 4 }

tcp20_seq_num OBJECT-TYPE
    SYNTAX Integer32
    MAX-ACCESS accessible-for-notify
    STATUS current
    DESCRIPTION
        "Parameter 'seq_num' in event TCP.20"
    ::= { tcpEventObjects20 5 }

tcpEventObjects21 OBJECT-IDENTITY
    STATUS current
    DESCRIPTION
        "Event TCP.21
        TCP has received a packet that partially fills the end of a hole."
    ::= { tcpEventsGroup 21 }

tcp21_source_ip_address OBJECT-TYPE
    SYNTAX IpAddress
    MAX-ACCESS accessible-for-notify
    STATUS current
    DESCRIPTION
        "Parameter 'source_ip_address' in event TCP.21"
    ::= { tcpEventObjects21 1 }

tcp21_source_tcp_port OBJECT-TYPE
    SYNTAX Integer32
    MAX-ACCESS accessible-for-notify
    STATUS current
    DESCRIPTION
        "Parameter 'source_tcp_port' in event TCP.21"
    ::= { tcpEventObjects21 2 }

tcp21_destination_ip_address OBJECT-TYPE
    SYNTAX IpAddress
    MAX-ACCESS accessible-for-notify
    STATUS current
    DESCRIPTION
        "Parameter 'destination_ip_address' in event TCP.21"
    ::= { tcpEventObjects21 3 }

tcp21_destination_tcp_port OBJECT-TYPE
    SYNTAX Integer32
    MAX-ACCESS accessible-for-notify
    STATUS current
    DESCRIPTION
        "Parameter 'destination_tcp_port' in event TCP.21"
    ::= { tcpEventObjects21 4 }

tcp21_seq_num OBJECT-TYPE
    SYNTAX Integer32
    MAX-ACCESS accessible-for-notify
    STATUS current
    DESCRIPTION
        "Parameter 'seq_num' in event TCP.21"
    ::= { tcpEventObjects21 5 }

tcpEventObjects22 OBJECT-IDENTITY
    STATUS current
    DESCRIPTION
        "Event TCP.22
        TCP has received a packet that completely fills a hole."
    ::= { tcpEventsGroup 22 }

tcp22_source_ip_address OBJECT-TYPE
    SYNTAX IpAddress
    MAX-ACCESS accessible-for-notify
    STATUS current
    DESCRIPTION
        "Parameter 'source_ip_address' in event TCP.22"
    ::= { tcpEventObjects22 1 }

tcp22_source_tcp_port OBJECT-TYPE
    SYNTAX Integer32
    MAX-ACCESS accessible-for-notify
    STATUS current
    DESCRIPTION
        "Parameter 'source_tcp_port' in event TCP.22"
    ::= { tcpEventObjects22 2 }

tcp22_destination_ip_address OBJECT-TYPE
    SYNTAX IpAddress
    MAX-ACCESS accessible-for-notify
    STATUS current
    DESCRIPTION
        "Parameter 'destination_ip_address' in event TCP.22"
    ::= { tcpEventObjects22 3 }

tcp22_destination_tcp_port OBJECT-TYPE
    SYNTAX Integer32
    MAX-ACCESS accessible-for-notify
    STATUS current
    DESCRIPTION
        "Parameter 'destination_tcp_port' in event TCP.22"
    ::= { tcpEventObjects22 4 }

tcp22_seq_num OBJECT-TYPE
    SYNTAX Integer32
    MAX-ACCESS accessible-for-notify
    STATUS current
    DESCRIPTION
        "Parameter 'seq_num' in event TCP.22"
    ::= { tcpEventObjects22 5 }

tcpEventObjects23 OBJECT-IDENTITY
    STATUS current
    DESCRIPTION
        "Event TCP.23
        TCP has received a packet that is too big to fit into the remaining
        space in the receive buffer."
    ::= { tcpEventsGroup 23 }

tcp23_source_ip_address OBJECT-TYPE
    SYNTAX IpAddress
    MAX-ACCESS accessible-for-notify
    STATUS current
    DESCRIPTION
        "Parameter 'source_ip_address' in event TCP.23"
    ::= { tcpEventObjects23 1 }

tcp23_source_tcp_port OBJECT-TYPE
    SYNTAX Integer32
    MAX-ACCESS accessible-for-notify
    STATUS current
    DESCRIPTION
        "Parameter 'source_tcp_port' in event TCP.23"
    ::= { tcpEventObjects23 2 }

tcp23_destination_ip_address OBJECT-TYPE
    SYNTAX IpAddress
    MAX-ACCESS accessible-for-notify
    STATUS current
    DESCRIPTION
        "Parameter 'destination_ip_address' in event TCP.23"
    ::= { tcpEventObjects23 3 }

tcp23_destination_tcp_port OBJECT-TYPE
    SYNTAX Integer32
    MAX-ACCESS accessible-for-notify
    STATUS current
    DESCRIPTION
        "Parameter 'destination_tcp_port' in event TCP.23"
    ::= { tcpEventObjects23 4 }

tcp23_seq_num OBJECT-TYPE
    SYNTAX Integer32
    MAX-ACCESS accessible-for-notify
    STATUS current
    DESCRIPTION
        "Parameter 'seq_num' in event TCP.23"
    ::= { tcpEventObjects23 5 }

tcpEventObjects24 OBJECT-IDENTITY
    STATUS current
    DESCRIPTION
        "Event TCP.24
        TCP processing FIN while not in SYNRCVD|ESTAB state."
    ::= { tcpEventsGroup 24 }

tcp24_source_ip_address OBJECT-TYPE
    SYNTAX IpAddress
    MAX-ACCESS accessible-for-notify
    STATUS current
    DESCRIPTION
        "Parameter 'source_ip_address' in event TCP.24"
    ::= { tcpEventObjects24 1 }

tcp24_source_tcp_port OBJECT-TYPE
    SYNTAX Integer32
    MAX-ACCESS accessible-for-notify
    STATUS current
    DESCRIPTION
        "Parameter 'source_tcp_port' in event TCP.24"
    ::= { tcpEventObjects24 2 }

tcp24_destination_ip_address OBJECT-TYPE
    SYNTAX IpAddress
    MAX-ACCESS accessible-for-notify
    STATUS current
    DESCRIPTION
        "Parameter 'destination_ip_address' in event TCP.24"
    ::= { tcpEventObjects24 3 }

tcp24_destination_tcp_port OBJECT-TYPE
    SYNTAX Integer32
    MAX-ACCESS accessible-for-notify
    STATUS current
    DESCRIPTION
        "Parameter 'destination_tcp_port' in event TCP.24"
    ::= { tcpEventObjects24 4 }

tcp24_state OBJECT-TYPE
    SYNTAX Integer32
    MAX-ACCESS accessible-for-notify
    STATUS current
    DESCRIPTION
        "Parameter 'state' in event TCP.24"
    ::= { tcpEventObjects24 5 }

tcpEventObjects25 OBJECT-IDENTITY
    STATUS current
    DESCRIPTION
        "Event TCP.25
        TCP processing FIN while in SYNRCVD|ESTAB state."
    ::= { tcpEventsGroup 25 }

tcp25_source_ip_address OBJECT-TYPE
    SYNTAX IpAddress
    MAX-ACCESS accessible-for-notify
    STATUS current
    DESCRIPTION
        "Parameter 'source_ip_address' in event TCP.25"
    ::= { tcpEventObjects25 1 }

tcp25_source_tcp_port OBJECT-TYPE
    SYNTAX Integer32
    MAX-ACCESS accessible-for-notify
    STATUS current
    DESCRIPTION
        "Parameter 'source_tcp_port' in event TCP.25"
    ::= { tcpEventObjects25 2 }

tcp25_destination_ip_address OBJECT-TYPE
    SYNTAX IpAddress
    MAX-ACCESS accessible-for-notify
    STATUS current
    DESCRIPTION
        "Parameter 'destination_ip_address' in event TCP.25"
    ::= { tcpEventObjects25 3 }

tcp25_destination_tcp_port OBJECT-TYPE
    SYNTAX Integer32
    MAX-ACCESS accessible-for-notify
    STATUS current
    DESCRIPTION
        "Parameter 'destination_tcp_port' in event TCP.25"
    ::= { tcpEventObjects25 4 }

tcpEventObjects26 OBJECT-IDENTITY
    STATUS current
    DESCRIPTION
        "Event TCP.26
        Application posts a read specifying a timeout value. If not all the
        requested data has been received within a timeout period, a timer fires,
        and whatever is in the receive buffer is given to the application."
    ::= { tcpEventsGroup 26 }

tcp26_source_ip_address OBJECT-TYPE
    SYNTAX IpAddress
    MAX-ACCESS accessible-for-notify
    STATUS current
    DESCRIPTION
        "Parameter 'source_ip_address' in event TCP.26"
    ::= { tcpEventObjects26 1 }

tcp26_source_tcp_port OBJECT-TYPE
    SYNTAX Integer32
    MAX-ACCESS accessible-for-notify
    STATUS current
    DESCRIPTION
        "Parameter 'source_tcp_port' in event TCP.26"
    ::= { tcpEventObjects26 2 }

tcp26_destination_ip_address OBJECT-TYPE
    SYNTAX IpAddress
    MAX-ACCESS accessible-for-notify
    STATUS current
    DESCRIPTION
        "Parameter 'destination_ip_address' in event TCP.26"
    ::= { tcpEventObjects26 3 }

tcp26_destination_tcp_port OBJECT-TYPE
    SYNTAX Integer32
    MAX-ACCESS accessible-for-notify
    STATUS current
    DESCRIPTION
        "Parameter 'destination_tcp_port' in event TCP.26"
    ::= { tcpEventObjects26 4 }

tcpEventObjects27 OBJECT-IDENTITY
    STATUS current
    DESCRIPTION
        "Event TCP.27
        The other side has been deaf and mute, and the the foreign window
        seems to have been closed illegally; send a RST."
    ::= { tcpEventsGroup 27 }

tcp27_source_ip_address OBJECT-TYPE
    SYNTAX IpAddress
    MAX-ACCESS accessible-for-notify
    STATUS current
    DESCRIPTION
        "Parameter 'source_ip_address' in event TCP.27"
    ::= { tcpEventObjects27 1 }

tcp27_source_tcp_port OBJECT-TYPE
    SYNTAX Integer32
    MAX-ACCESS accessible-for-notify
    STATUS current
    DESCRIPTION
        "Parameter 'source_tcp_port' in event TCP.27"
    ::= { tcpEventObjects27 2 }

tcp27_destination_ip_address OBJECT-TYPE
    SYNTAX IpAddress
    MAX-ACCESS accessible-for-notify
    STATUS current
    DESCRIPTION
        "Parameter 'destination_ip_address' in event TCP.27"
    ::= { tcpEventObjects27 3 }

tcp27_destination_tcp_port OBJECT-TYPE
    SYNTAX Integer32
    MAX-ACCESS accessible-for-notify
    STATUS current
    DESCRIPTION
        "Parameter 'destination_tcp_port' in event TCP.27"
    ::= { tcpEventObjects27 4 }

tcpEventObjects28 OBJECT-IDENTITY
    STATUS current
    DESCRIPTION
        "Event TCP.28
        State of the connection has transitioned to SYN-RECEIVED state
        as a result of either an active open or a passive open."
    ::= { tcpEventsGroup 28 }

tcp28_source_ip_address OBJECT-TYPE
    SYNTAX IpAddress
    MAX-ACCESS accessible-for-notify
    STATUS current
    DESCRIPTION
        "Parameter 'source_ip_address' in event TCP.28"
    ::= { tcpEventObjects28 1 }

tcp28_source_tcp_port OBJECT-TYPE
    SYNTAX Integer32
    MAX-ACCESS accessible-for-notify
    STATUS current
    DESCRIPTION
        "Parameter 'source_tcp_port' in event TCP.28"
    ::= { tcpEventObjects28 2 }

tcp28_destination_ip_address OBJECT-TYPE
    SYNTAX IpAddress
    MAX-ACCESS accessible-for-notify
    STATUS current
    DESCRIPTION
        "Parameter 'destination_ip_address' in event TCP.28"
    ::= { tcpEventObjects28 3 }

tcp28_destination_tcp_port OBJECT-TYPE
    SYNTAX Integer32
    MAX-ACCESS accessible-for-notify
    STATUS current
    DESCRIPTION
        "Parameter 'destination_tcp_port' in event TCP.28"
    ::= { tcpEventObjects28 4 }

tcpEventObjects29 OBJECT-IDENTITY
    STATUS current
    DESCRIPTION
        "Event TCP.29
        State of the connection has transitioned to ESTABLISHED state
        as a result of either an active open or a passive open."
    ::= { tcpEventsGroup 29 }

tcp29_source_ip_address OBJECT-TYPE
    SYNTAX IpAddress
    MAX-ACCESS accessible-for-notify
    STATUS current
    DESCRIPTION
        "Parameter 'source_ip_address' in event TCP.29"
    ::= { tcpEventObjects29 1 }

tcp29_source_tcp_port OBJECT-TYPE
    SYNTAX Integer32
    MAX-ACCESS accessible-for-notify
    STATUS current
    DESCRIPTION
        "Parameter 'source_tcp_port' in event TCP.29"
    ::= { tcpEventObjects29 2 }

tcp29_destination_ip_address OBJECT-TYPE
    SYNTAX IpAddress
    MAX-ACCESS accessible-for-notify
    STATUS current
    DESCRIPTION
        "Parameter 'destination_ip_address' in event TCP.29"
    ::= { tcpEventObjects29 3 }

tcp29_destination_tcp_port OBJECT-TYPE
    SYNTAX Integer32
    MAX-ACCESS accessible-for-notify
    STATUS current
    DESCRIPTION
        "Parameter 'destination_tcp_port' in event TCP.29"
    ::= { tcpEventObjects29 4 }

tcpEventObjects30 OBJECT-IDENTITY
    STATUS current
    DESCRIPTION
        "Event TCP.30
        TCP has received a packet."
    ::= { tcpEventsGroup 30 }

tcp30_source_ip_address OBJECT-TYPE
    SYNTAX IpAddress
    MAX-ACCESS accessible-for-notify
    STATUS current
    DESCRIPTION
        "Parameter 'source_ip_address' in event TCP.30"
    ::= { tcpEventObjects30 1 }

tcp30_source_tcp_port OBJECT-TYPE
    SYNTAX Integer32
    MAX-ACCESS accessible-for-notify
    STATUS current
    DESCRIPTION
        "Parameter 'source_tcp_port' in event TCP.30"
    ::= { tcpEventObjects30 2 }

tcp30_destination_ip_address OBJECT-TYPE
    SYNTAX IpAddress
    MAX-ACCESS accessible-for-notify
    STATUS current
    DESCRIPTION
        "Parameter 'destination_ip_address' in event TCP.30"
    ::= { tcpEventObjects30 3 }

tcp30_destination_tcp_port OBJECT-TYPE
    SYNTAX Integer32
    MAX-ACCESS accessible-for-notify
    STATUS current
    DESCRIPTION
        "Parameter 'destination_tcp_port' in event TCP.30"
    ::= { tcpEventObjects30 4 }

tcp30_flags OBJECT-TYPE
    SYNTAX DisplayString
    MAX-ACCESS accessible-for-notify
    STATUS current
    DESCRIPTION
        "Parameter 'flags' in event TCP.30"
    ::= { tcpEventObjects30 5 }

tcp30_sequence OBJECT-TYPE
    SYNTAX Integer32
    MAX-ACCESS accessible-for-notify
    STATUS current
    DESCRIPTION
        "Parameter 'sequence' in event TCP.30"
    ::= { tcpEventObjects30 6 }

tcp30_acknowledge OBJECT-TYPE
    SYNTAX Integer32
    MAX-ACCESS accessible-for-notify
    STATUS current
    DESCRIPTION
        "Parameter 'acknowledge' in event TCP.30"
    ::= { tcpEventObjects30 7 }

tcp30_window OBJECT-TYPE
    SYNTAX Integer32
    MAX-ACCESS accessible-for-notify
    STATUS current
    DESCRIPTION
        "Parameter 'window' in event TCP.30"
    ::= { tcpEventObjects30 8 }

tcp30_length OBJECT-TYPE
    SYNTAX Integer32
    MAX-ACCESS accessible-for-notify
    STATUS current
    DESCRIPTION
        "Parameter 'length' in event TCP.30"
    ::= { tcpEventObjects30 9 }

tcpEventObjects31 OBJECT-IDENTITY
    STATUS current
    DESCRIPTION
        "Event TCP.31
        Valid data in receive buffer has been handed to the application for
        further processing."
    ::= { tcpEventsGroup 31 }

tcp31_source_ip_address OBJECT-TYPE
    SYNTAX IpAddress
    MAX-ACCESS accessible-for-notify
    STATUS current
    DESCRIPTION
        "Parameter 'source_ip_address' in event TCP.31"
    ::= { tcpEventObjects31 1 }

tcp31_source_tcp_port OBJECT-TYPE
    SYNTAX Integer32
    MAX-ACCESS accessible-for-notify
    STATUS current
    DESCRIPTION
        "Parameter 'source_tcp_port' in event TCP.31"
    ::= { tcpEventObjects31 2 }

tcp31_destination_ip_address OBJECT-TYPE
    SYNTAX IpAddress
    MAX-ACCESS accessible-for-notify
    STATUS current
    DESCRIPTION
        "Parameter 'destination_ip_address' in event TCP.31"
    ::= { tcpEventObjects31 3 }

tcp31_destination_tcp_port OBJECT-TYPE
    SYNTAX Integer32
    MAX-ACCESS accessible-for-notify
    STATUS current
    DESCRIPTION
        "Parameter 'destination_tcp_port' in event TCP.31"
    ::= { tcpEventObjects31 4 }

tcp31_seq_num OBJECT-TYPE
    SYNTAX Integer32
    MAX-ACCESS accessible-for-notify
    STATUS current
    DESCRIPTION
        "Parameter 'seq_num' in event TCP.31"
    ::= { tcpEventObjects31 5 }

tcp31_length OBJECT-TYPE
    SYNTAX Integer32
    MAX-ACCESS accessible-for-notify
    STATUS current
    DESCRIPTION
        "Parameter 'length' in event TCP.31"
    ::= { tcpEventObjects31 6 }

tcpEventObjects32 OBJECT-IDENTITY
    STATUS current
    DESCRIPTION
        "Event TCP.32
        We have retransmitted a frame an excessive number of times.
        If the application has closed the connection already, just abort. Else,
        notify the application that there is a problem."
    ::= { tcpEventsGroup 32 }

tcp32_source_ip_address OBJECT-TYPE
    SYNTAX IpAddress
    MAX-ACCESS accessible-for-notify
    STATUS current
    DESCRIPTION
        "Parameter 'source_ip_address' in event TCP.32"
    ::= { tcpEventObjects32 1 }

tcp32_source_tcp_port OBJECT-TYPE
    SYNTAX Integer32
    MAX-ACCESS accessible-for-notify
    STATUS current
    DESCRIPTION
        "Parameter 'source_tcp_port' in event TCP.32"
    ::= { tcpEventObjects32 2 }

tcp32_destination_ip_address OBJECT-TYPE
    SYNTAX IpAddress
    MAX-ACCESS accessible-for-notify
    STATUS current
    DESCRIPTION
        "Parameter 'destination_ip_address' in event TCP.32"
    ::= { tcpEventObjects32 3 }

tcp32_destination_tcp_port OBJECT-TYPE
    SYNTAX Integer32
    MAX-ACCESS accessible-for-notify
    STATUS current
    DESCRIPTION
        "Parameter 'destination_tcp_port' in event TCP.32"
    ::= { tcpEventObjects32 4 }

tcpEventObjects33 OBJECT-IDENTITY
    STATUS current
    DESCRIPTION
        "Event TCP.33
        Send a control segment to either ack a segment or send special control
        segments like FIN or RST."
    ::= { tcpEventsGroup 33 }

tcp33_source_ip_address OBJECT-TYPE
    SYNTAX IpAddress
    MAX-ACCESS accessible-for-notify
    STATUS current
    DESCRIPTION
        "Parameter 'source_ip_address' in event TCP.33"
    ::= { tcpEventObjects33 1 }

tcp33_source_tcp_port OBJECT-TYPE
    SYNTAX Integer32
    MAX-ACCESS accessible-for-notify
    STATUS current
    DESCRIPTION
        "Parameter 'source_tcp_port' in event TCP.33"
    ::= { tcpEventObjects33 2 }

tcp33_destination_ip_address OBJECT-TYPE
    SYNTAX IpAddress
    MAX-ACCESS accessible-for-notify
    STATUS current
    DESCRIPTION
        "Parameter 'destination_ip_address' in event TCP.33"
    ::= { tcpEventObjects33 3 }

tcp33_destination_tcp_port OBJECT-TYPE
    SYNTAX Integer32
    MAX-ACCESS accessible-for-notify
    STATUS current
    DESCRIPTION
        "Parameter 'destination_tcp_port' in event TCP.33"
    ::= { tcpEventObjects33 4 }

tcp33_flags OBJECT-TYPE
    SYNTAX DisplayString
    MAX-ACCESS accessible-for-notify
    STATUS current
    DESCRIPTION
        "Parameter 'flags' in event TCP.33"
    ::= { tcpEventObjects33 5 }

tcp33_seq_num OBJECT-TYPE
    SYNTAX Integer32
    MAX-ACCESS accessible-for-notify
    STATUS current
    DESCRIPTION
        "Parameter 'seq_num' in event TCP.33"
    ::= { tcpEventObjects33 6 }

tcp33_ack_num OBJECT-TYPE
    SYNTAX Integer32
    MAX-ACCESS accessible-for-notify
    STATUS current
    DESCRIPTION
        "Parameter 'ack_num' in event TCP.33"
    ::= { tcpEventObjects33 7 }

tcp33_window OBJECT-TYPE
    SYNTAX Integer32
    MAX-ACCESS accessible-for-notify
    STATUS current
    DESCRIPTION
        "Parameter 'window' in event TCP.33"
    ::= { tcpEventObjects33 8 }

tcpEventObjects34 OBJECT-IDENTITY
    STATUS current
    DESCRIPTION
        "Event TCP.34
        We have failed to receive a valid ACK for transmitted data,
        so retransmit the data."
    ::= { tcpEventsGroup 34 }

tcp34_source_ip_address OBJECT-TYPE
    SYNTAX IpAddress
    MAX-ACCESS accessible-for-notify
    STATUS current
    DESCRIPTION
        "Parameter 'source_ip_address' in event TCP.34"
    ::= { tcpEventObjects34 1 }

tcp34_source_tcp_port OBJECT-TYPE
    SYNTAX Integer32
    MAX-ACCESS accessible-for-notify
    STATUS current
    DESCRIPTION
        "Parameter 'source_tcp_port' in event TCP.34"
    ::= { tcpEventObjects34 2 }

tcp34_destination_ip_address OBJECT-TYPE
    SYNTAX IpAddress
    MAX-ACCESS accessible-for-notify
    STATUS current
    DESCRIPTION
        "Parameter 'destination_ip_address' in event TCP.34"
    ::= { tcpEventObjects34 3 }

tcp34_destination_tcp_port OBJECT-TYPE
    SYNTAX Integer32
    MAX-ACCESS accessible-for-notify
    STATUS current
    DESCRIPTION
        "Parameter 'destination_tcp_port' in event TCP.34"
    ::= { tcpEventObjects34 4 }

tcp34_flags OBJECT-TYPE
    SYNTAX DisplayString
    MAX-ACCESS accessible-for-notify
    STATUS current
    DESCRIPTION
        "Parameter 'flags' in event TCP.34"
    ::= { tcpEventObjects34 5 }

tcp34_seq_num OBJECT-TYPE
    SYNTAX Integer32
    MAX-ACCESS accessible-for-notify
    STATUS current
    DESCRIPTION
        "Parameter 'seq_num' in event TCP.34"
    ::= { tcpEventObjects34 6 }

tcp34_ack_num OBJECT-TYPE
    SYNTAX Integer32
    MAX-ACCESS accessible-for-notify
    STATUS current
    DESCRIPTION
        "Parameter 'ack_num' in event TCP.34"
    ::= { tcpEventObjects34 7 }

tcp34_window OBJECT-TYPE
    SYNTAX Integer32
    MAX-ACCESS accessible-for-notify
    STATUS current
    DESCRIPTION
        "Parameter 'window' in event TCP.34"
    ::= { tcpEventObjects34 8 }

tcp34_length OBJECT-TYPE
    SYNTAX Integer32
    MAX-ACCESS accessible-for-notify
    STATUS current
    DESCRIPTION
        "Parameter 'length' in event TCP.34"
    ::= { tcpEventObjects34 9 }

tcpEventObjects35 OBJECT-IDENTITY
    STATUS current
    DESCRIPTION
        "Event TCP.35
        Transmit data."
    ::= { tcpEventsGroup 35 }

tcp35_source_ip_address OBJECT-TYPE
    SYNTAX IpAddress
    MAX-ACCESS accessible-for-notify
    STATUS current
    DESCRIPTION
        "Parameter 'source_ip_address' in event TCP.35"
    ::= { tcpEventObjects35 1 }

tcp35_source_tcp_port OBJECT-TYPE
    SYNTAX Integer32
    MAX-ACCESS accessible-for-notify
    STATUS current
    DESCRIPTION
        "Parameter 'source_tcp_port' in event TCP.35"
    ::= { tcpEventObjects35 2 }

tcp35_destination_ip_address OBJECT-TYPE
    SYNTAX IpAddress
    MAX-ACCESS accessible-for-notify
    STATUS current
    DESCRIPTION
        "Parameter 'destination_ip_address' in event TCP.35"
    ::= { tcpEventObjects35 3 }

tcp35_destination_tcp_port OBJECT-TYPE
    SYNTAX Integer32
    MAX-ACCESS accessible-for-notify
    STATUS current
    DESCRIPTION
        "Parameter 'destination_tcp_port' in event TCP.35"
    ::= { tcpEventObjects35 4 }

tcp35_flags OBJECT-TYPE
    SYNTAX DisplayString
    MAX-ACCESS accessible-for-notify
    STATUS current
    DESCRIPTION
        "Parameter 'flags' in event TCP.35"
    ::= { tcpEventObjects35 5 }

tcp35_seq_num OBJECT-TYPE
    SYNTAX Integer32
    MAX-ACCESS accessible-for-notify
    STATUS current
    DESCRIPTION
        "Parameter 'seq_num' in event TCP.35"
    ::= { tcpEventObjects35 6 }

tcp35_ack_num OBJECT-TYPE
    SYNTAX Integer32
    MAX-ACCESS accessible-for-notify
    STATUS current
    DESCRIPTION
        "Parameter 'ack_num' in event TCP.35"
    ::= { tcpEventObjects35 7 }

tcp35_window OBJECT-TYPE
    SYNTAX Integer32
    MAX-ACCESS accessible-for-notify
    STATUS current
    DESCRIPTION
        "Parameter 'window' in event TCP.35"
    ::= { tcpEventObjects35 8 }

tcp35_length OBJECT-TYPE
    SYNTAX Integer32
    MAX-ACCESS accessible-for-notify
    STATUS current
    DESCRIPTION
        "Parameter 'length' in event TCP.35"
    ::= { tcpEventObjects35 9 }

tcpEventObjects36 OBJECT-IDENTITY
    STATUS current
    DESCRIPTION
        "Event TCP.36
        An unsupported option is present in the options field of a SYN packet."
    ::= { tcpEventsGroup 36 }

tcp36_source_ip_address OBJECT-TYPE
    SYNTAX IpAddress
    MAX-ACCESS accessible-for-notify
    STATUS current
    DESCRIPTION
        "Parameter 'source_ip_address' in event TCP.36"
    ::= { tcpEventObjects36 1 }

tcp36_source_tcp_port OBJECT-TYPE
    SYNTAX Integer32
    MAX-ACCESS accessible-for-notify
    STATUS current
    DESCRIPTION
        "Parameter 'source_tcp_port' in event TCP.36"
    ::= { tcpEventObjects36 2 }

tcp36_destination_ip_address OBJECT-TYPE
    SYNTAX IpAddress
    MAX-ACCESS accessible-for-notify
    STATUS current
    DESCRIPTION
        "Parameter 'destination_ip_address' in event TCP.36"
    ::= { tcpEventObjects36 3 }

tcp36_destination_tcp_port OBJECT-TYPE
    SYNTAX Integer32
    MAX-ACCESS accessible-for-notify
    STATUS current
    DESCRIPTION
        "Parameter 'destination_tcp_port' in event TCP.36"
    ::= { tcpEventObjects36 4 }

tcp36_option OBJECT-TYPE
    SYNTAX Integer32
    MAX-ACCESS accessible-for-notify
    STATUS current
    DESCRIPTION
        "Parameter 'option' in event TCP.36"
    ::= { tcpEventObjects36 5 }

tcpEventObjects38 OBJECT-IDENTITY
    STATUS current
    DESCRIPTION
        "Event TCP.38
        Reject the segment, and send a RST to the other side for receiving
        a segment with the incorrect acknowledgement while in the
        SYNRCVD state. Until a correct acknowledgement is received, we cannot
        progress into the ESTABLISHED state."
    ::= { tcpEventsGroup 38 }

tcp38_source_ip_address OBJECT-TYPE
    SYNTAX IpAddress
    MAX-ACCESS accessible-for-notify
    STATUS current
    DESCRIPTION
        "Parameter 'source_ip_address' in event TCP.38"
    ::= { tcpEventObjects38 1 }

tcp38_source_tcp_port OBJECT-TYPE
    SYNTAX Integer32
    MAX-ACCESS accessible-for-notify
    STATUS current
    DESCRIPTION
        "Parameter 'source_tcp_port' in event TCP.38"
    ::= { tcpEventObjects38 2 }

tcp38_destination_ip_address OBJECT-TYPE
    SYNTAX IpAddress
    MAX-ACCESS accessible-for-notify
    STATUS current
    DESCRIPTION
        "Parameter 'destination_ip_address' in event TCP.38"
    ::= { tcpEventObjects38 3 }

tcp38_destination_tcp_port OBJECT-TYPE
    SYNTAX Integer32
    MAX-ACCESS accessible-for-notify
    STATUS current
    DESCRIPTION
        "Parameter 'destination_tcp_port' in event TCP.38"
    ::= { tcpEventObjects38 4 }

tcp38_seq_num OBJECT-TYPE
    SYNTAX Integer32
    MAX-ACCESS accessible-for-notify
    STATUS current
    DESCRIPTION
        "Parameter 'seq_num' in event TCP.38"
    ::= { tcpEventObjects38 5 }

tcpEventObjects39 OBJECT-IDENTITY
    STATUS current
    DESCRIPTION
        "Event TCP.39
        TCP has received an ACK while in the LISTEN state; this does not make
        any sense because we have not yet sent any data, so nothing should
        be ACKed. As a result, we send a RST."
    ::= { tcpEventsGroup 39 }

tcp39_source_ip_address OBJECT-TYPE
    SYNTAX IpAddress
    MAX-ACCESS accessible-for-notify
    STATUS current
    DESCRIPTION
        "Parameter 'source_ip_address' in event TCP.39"
    ::= { tcpEventObjects39 1 }

tcp39_source_tcp_port OBJECT-TYPE
    SYNTAX Integer32
    MAX-ACCESS accessible-for-notify
    STATUS current
    DESCRIPTION
        "Parameter 'source_tcp_port' in event TCP.39"
    ::= { tcpEventObjects39 2 }

tcp39_destination_ip_address OBJECT-TYPE
    SYNTAX IpAddress
    MAX-ACCESS accessible-for-notify
    STATUS current
    DESCRIPTION
        "Parameter 'destination_ip_address' in event TCP.39"
    ::= { tcpEventObjects39 3 }

tcp39_destination_tcp_port OBJECT-TYPE
    SYNTAX Integer32
    MAX-ACCESS accessible-for-notify
    STATUS current
    DESCRIPTION
        "Parameter 'destination_tcp_port' in event TCP.39"
    ::= { tcpEventObjects39 4 }

tcp39_seq_num OBJECT-TYPE
    SYNTAX Integer32
    MAX-ACCESS accessible-for-notify
    STATUS current
    DESCRIPTION
        "Parameter 'seq_num' in event TCP.39"
    ::= { tcpEventObjects39 5 }

tcpEventObjects40 OBJECT-IDENTITY
    STATUS current
    DESCRIPTION
        "Event TCP.40
        TCP is sending a RESET segment to the other side."
    ::= { tcpEventsGroup 40 }

tcp40_source_ip_address OBJECT-TYPE
    SYNTAX IpAddress
    MAX-ACCESS accessible-for-notify
    STATUS current
    DESCRIPTION
        "Parameter 'source_ip_address' in event TCP.40"
    ::= { tcpEventObjects40 1 }

tcp40_source_tcp_port OBJECT-TYPE
    SYNTAX Integer32
    MAX-ACCESS accessible-for-notify
    STATUS current
    DESCRIPTION
        "Parameter 'source_tcp_port' in event TCP.40"
    ::= { tcpEventObjects40 2 }

tcp40_destination_ip_address OBJECT-TYPE
    SYNTAX IpAddress
    MAX-ACCESS accessible-for-notify
    STATUS current
    DESCRIPTION
        "Parameter 'destination_ip_address' in event TCP.40"
    ::= { tcpEventObjects40 3 }

tcp40_destination_tcp_port OBJECT-TYPE
    SYNTAX Integer32
    MAX-ACCESS accessible-for-notify
    STATUS current
    DESCRIPTION
        "Parameter 'destination_tcp_port' in event TCP.40"
    ::= { tcpEventObjects40 4 }

tcp40_flags OBJECT-TYPE
    SYNTAX DisplayString
    MAX-ACCESS accessible-for-notify
    STATUS current
    DESCRIPTION
        "Parameter 'flags' in event TCP.40"
    ::= { tcpEventObjects40 5 }

tcp40_seq_num OBJECT-TYPE
    SYNTAX Integer32
    MAX-ACCESS accessible-for-notify
    STATUS current
    DESCRIPTION
        "Parameter 'seq_num' in event TCP.40"
    ::= { tcpEventObjects40 6 }

tcp40_ack_num OBJECT-TYPE
    SYNTAX Integer32
    MAX-ACCESS accessible-for-notify
    STATUS current
    DESCRIPTION
        "Parameter 'ack_num' in event TCP.40"
    ::= { tcpEventObjects40 7 }

tcpEventObjects41 OBJECT-IDENTITY
    STATUS current
    DESCRIPTION
        "Event TCP.41
        TCP connection is closed - notifying the application."
    ::= { tcpEventsGroup 41 }

tcp41_source_ip_address OBJECT-TYPE
    SYNTAX IpAddress
    MAX-ACCESS accessible-for-notify
    STATUS current
    DESCRIPTION
        "Parameter 'source_ip_address' in event TCP.41"
    ::= { tcpEventObjects41 1 }

tcp41_source_tcp_port OBJECT-TYPE
    SYNTAX Integer32
    MAX-ACCESS accessible-for-notify
    STATUS current
    DESCRIPTION
        "Parameter 'source_tcp_port' in event TCP.41"
    ::= { tcpEventObjects41 2 }

tcp41_destination_ip_address OBJECT-TYPE
    SYNTAX IpAddress
    MAX-ACCESS accessible-for-notify
    STATUS current
    DESCRIPTION
        "Parameter 'destination_ip_address' in event TCP.41"
    ::= { tcpEventObjects41 3 }

tcp41_destination_tcp_port OBJECT-TYPE
    SYNTAX Integer32
    MAX-ACCESS accessible-for-notify
    STATUS current
    DESCRIPTION
        "Parameter 'destination_tcp_port' in event TCP.41"
    ::= { tcpEventObjects41 4 }

tcpEventObjects42 OBJECT-IDENTITY
    STATUS current
    DESCRIPTION
        "Event TCP.42
        Freeing the TCB block associated with the TCP connection
        that has closed."
    ::= { tcpEventsGroup 42 }

tcp42_source_ip_address OBJECT-TYPE
    SYNTAX IpAddress
    MAX-ACCESS accessible-for-notify
    STATUS current
    DESCRIPTION
        "Parameter 'source_ip_address' in event TCP.42"
    ::= { tcpEventObjects42 1 }

tcp42_source_tcp_port OBJECT-TYPE
    SYNTAX Integer32
    MAX-ACCESS accessible-for-notify
    STATUS current
    DESCRIPTION
        "Parameter 'source_tcp_port' in event TCP.42"
    ::= { tcpEventObjects42 2 }

tcp42_destination_ip_address OBJECT-TYPE
    SYNTAX IpAddress
    MAX-ACCESS accessible-for-notify
    STATUS current
    DESCRIPTION
        "Parameter 'destination_ip_address' in event TCP.42"
    ::= { tcpEventObjects42 3 }

tcp42_destination_tcp_port OBJECT-TYPE
    SYNTAX Integer32
    MAX-ACCESS accessible-for-notify
    STATUS current
    DESCRIPTION
        "Parameter 'destination_tcp_port' in event TCP.42"
    ::= { tcpEventObjects42 4 }

tcpEventObjects43 OBJECT-IDENTITY
    STATUS current
    DESCRIPTION
        "Event TCP.43
        TCP has received a segment with data that has already been consumed
        by the application."
    ::= { tcpEventsGroup 43 }

tcp43_source_ip_address OBJECT-TYPE
    SYNTAX IpAddress
    MAX-ACCESS accessible-for-notify
    STATUS current
    DESCRIPTION
        "Parameter 'source_ip_address' in event TCP.43"
    ::= { tcpEventObjects43 1 }

tcp43_source_tcp_port OBJECT-TYPE
    SYNTAX Integer32
    MAX-ACCESS accessible-for-notify
    STATUS current
    DESCRIPTION
        "Parameter 'source_tcp_port' in event TCP.43"
    ::= { tcpEventObjects43 2 }

tcp43_destination_ip_address OBJECT-TYPE
    SYNTAX IpAddress
    MAX-ACCESS accessible-for-notify
    STATUS current
    DESCRIPTION
        "Parameter 'destination_ip_address' in event TCP.43"
    ::= { tcpEventObjects43 3 }

tcp43_destination_tcp_port OBJECT-TYPE
    SYNTAX Integer32
    MAX-ACCESS accessible-for-notify
    STATUS current
    DESCRIPTION
        "Parameter 'destination_tcp_port' in event TCP.43"
    ::= { tcpEventObjects43 4 }

tcp43_seq_num OBJECT-TYPE
    SYNTAX Integer32
    MAX-ACCESS accessible-for-notify
    STATUS current
    DESCRIPTION
        "Parameter 'seq_num' in event TCP.43"
    ::= { tcpEventObjects43 5 }

tcpEventObjects44 OBJECT-IDENTITY
    STATUS current
    DESCRIPTION
        "Event TCP.44
        Idle timer fires for TCP connection."
    ::= { tcpEventsGroup 44 }

tcp44_source_ip_address OBJECT-TYPE
    SYNTAX IpAddress
    MAX-ACCESS accessible-for-notify
    STATUS current
    DESCRIPTION
        "Parameter 'source_ip_address' in event TCP.44"
    ::= { tcpEventObjects44 1 }

tcp44_source_tcp_port OBJECT-TYPE
    SYNTAX Integer32
    MAX-ACCESS accessible-for-notify
    STATUS current
    DESCRIPTION
        "Parameter 'source_tcp_port' in event TCP.44"
    ::= { tcpEventObjects44 2 }

tcp44_destination_ip_address OBJECT-TYPE
    SYNTAX IpAddress
    MAX-ACCESS accessible-for-notify
    STATUS current
    DESCRIPTION
        "Parameter 'destination_ip_address' in event TCP.44"
    ::= { tcpEventObjects44 3 }

tcp44_destination_tcp_port OBJECT-TYPE
    SYNTAX Integer32
    MAX-ACCESS accessible-for-notify
    STATUS current
    DESCRIPTION
        "Parameter 'destination_tcp_port' in event TCP.44"
    ::= { tcpEventObjects44 4 }

tcpEventObjects45 OBJECT-IDENTITY
    STATUS current
    DESCRIPTION
        "Event TCP.45
        Retransmit timer fires for TCP connection."
    ::= { tcpEventsGroup 45 }

tcp45_source_ip_address OBJECT-TYPE
    SYNTAX IpAddress
    MAX-ACCESS accessible-for-notify
    STATUS current
    DESCRIPTION
        "Parameter 'source_ip_address' in event TCP.45"
    ::= { tcpEventObjects45 1 }

tcp45_source_tcp_port OBJECT-TYPE
    SYNTAX Integer32
    MAX-ACCESS accessible-for-notify
    STATUS current
    DESCRIPTION
        "Parameter 'source_tcp_port' in event TCP.45"
    ::= { tcpEventObjects45 2 }

tcp45_destination_ip_address OBJECT-TYPE
    SYNTAX IpAddress
    MAX-ACCESS accessible-for-notify
    STATUS current
    DESCRIPTION
        "Parameter 'destination_ip_address' in event TCP.45"
    ::= { tcpEventObjects45 3 }

tcp45_destination_tcp_port OBJECT-TYPE
    SYNTAX Integer32
    MAX-ACCESS accessible-for-notify
    STATUS current
    DESCRIPTION
        "Parameter 'destination_tcp_port' in event TCP.45"
    ::= { tcpEventObjects45 4 }

tcpEventObjects46 OBJECT-IDENTITY
    STATUS current
    DESCRIPTION
        "Event TCP.46
        State of tcp connection has transitioned from ESTABLISHED to
        FINWAIT - send FIN, and now waiting for FIN-ACK to arrive."
    ::= { tcpEventsGroup 46 }

tcp46_source_ip_address OBJECT-TYPE
    SYNTAX IpAddress
    MAX-ACCESS accessible-for-notify
    STATUS current
    DESCRIPTION
        "Parameter 'source_ip_address' in event TCP.46"
    ::= { tcpEventObjects46 1 }

tcp46_source_tcp_port OBJECT-TYPE
    SYNTAX Integer32
    MAX-ACCESS accessible-for-notify
    STATUS current
    DESCRIPTION
        "Parameter 'source_tcp_port' in event TCP.46"
    ::= { tcpEventObjects46 2 }

tcp46_destination_ip_address OBJECT-TYPE
    SYNTAX IpAddress
    MAX-ACCESS accessible-for-notify
    STATUS current
    DESCRIPTION
        "Parameter 'destination_ip_address' in event TCP.46"
    ::= { tcpEventObjects46 3 }

tcp46_destination_tcp_port OBJECT-TYPE
    SYNTAX Integer32
    MAX-ACCESS accessible-for-notify
    STATUS current
    DESCRIPTION
        "Parameter 'destination_tcp_port' in event TCP.46"
    ::= { tcpEventObjects46 4 }

tcpEventObjects47 OBJECT-IDENTITY
    STATUS current
    DESCRIPTION
        "Event TCP.47
        State of tcp connection has transitioned to CLOSED."
    ::= { tcpEventsGroup 47 }

tcp47_source_ip_address OBJECT-TYPE
    SYNTAX IpAddress
    MAX-ACCESS accessible-for-notify
    STATUS current
    DESCRIPTION
        "Parameter 'source_ip_address' in event TCP.47"
    ::= { tcpEventObjects47 1 }

tcp47_source_tcp_port OBJECT-TYPE
    SYNTAX Integer32
    MAX-ACCESS accessible-for-notify
    STATUS current
    DESCRIPTION
        "Parameter 'source_tcp_port' in event TCP.47"
    ::= { tcpEventObjects47 2 }

tcp47_destination_ip_address OBJECT-TYPE
    SYNTAX IpAddress
    MAX-ACCESS accessible-for-notify
    STATUS current
    DESCRIPTION
        "Parameter 'destination_ip_address' in event TCP.47"
    ::= { tcpEventObjects47 3 }

tcp47_destination_tcp_port OBJECT-TYPE
    SYNTAX Integer32
    MAX-ACCESS accessible-for-notify
    STATUS current
    DESCRIPTION
        "Parameter 'destination_tcp_port' in event TCP.47"
    ::= { tcpEventObjects47 4 }

tcpEventObjects48 OBJECT-IDENTITY
    STATUS current
    DESCRIPTION
        "Event TCP.48
        TCP connection is CLOSING due to application requesting a CLOSE.
        After the window shrinks to zero, discard any packets received.
        This is based on the half-duplex TCP close sequence."
    ::= { tcpEventsGroup 48 }

tcp48_source_ip_address OBJECT-TYPE
    SYNTAX IpAddress
    MAX-ACCESS accessible-for-notify
    STATUS current
    DESCRIPTION
        "Parameter 'source_ip_address' in event TCP.48"
    ::= { tcpEventObjects48 1 }

tcp48_source_tcp_port OBJECT-TYPE
    SYNTAX Integer32
    MAX-ACCESS accessible-for-notify
    STATUS current
    DESCRIPTION
        "Parameter 'source_tcp_port' in event TCP.48"
    ::= { tcpEventObjects48 2 }

tcp48_destination_ip_address OBJECT-TYPE
    SYNTAX IpAddress
    MAX-ACCESS accessible-for-notify
    STATUS current
    DESCRIPTION
        "Parameter 'destination_ip_address' in event TCP.48"
    ::= { tcpEventObjects48 3 }

tcp48_destination_tcp_port OBJECT-TYPE
    SYNTAX Integer32
    MAX-ACCESS accessible-for-notify
    STATUS current
    DESCRIPTION
        "Parameter 'destination_tcp_port' in event TCP.48"
    ::= { tcpEventObjects48 4 }

tcpEventObjects49 OBJECT-IDENTITY
    STATUS current
    DESCRIPTION
        "Event TCP.49
        The other side has send an old ACK with zero data length - we treat
        this as a NACK."
    ::= { tcpEventsGroup 49 }

tcp49_source_ip_address OBJECT-TYPE
    SYNTAX IpAddress
    MAX-ACCESS accessible-for-notify
    STATUS current
    DESCRIPTION
        "Parameter 'source_ip_address' in event TCP.49"
    ::= { tcpEventObjects49 1 }

tcp49_destination_ip_address OBJECT-TYPE
    SYNTAX Integer32
    MAX-ACCESS accessible-for-notify
    STATUS current
    DESCRIPTION
        "Parameter 'destination_ip_address' in event TCP.49"
    ::= { tcpEventObjects49 2 }

tcp49_tcp_src_port OBJECT-TYPE
    SYNTAX IpAddress
    MAX-ACCESS accessible-for-notify
    STATUS current
    DESCRIPTION
        "Parameter 'tcp_src_port' in event TCP.49"
    ::= { tcpEventObjects49 3 }

tcp49_tcp_dst_port OBJECT-TYPE
    SYNTAX Integer32
    MAX-ACCESS accessible-for-notify
    STATUS current
    DESCRIPTION
        "Parameter 'tcp_dst_port' in event TCP.49"
    ::= { tcpEventObjects49 4 }

tcpEventObjects50 OBJECT-IDENTITY
    STATUS current
    DESCRIPTION
        "Event TCP.50
        The other side has acknowledged the keep alive packet. The keep alive
        packet is sent if keep alive is enabled on this TCP connection, and
        the connection has been idle."
    ::= { tcpEventsGroup 50 }

tcp50_source_ip_address OBJECT-TYPE
    SYNTAX IpAddress
    MAX-ACCESS accessible-for-notify
    STATUS current
    DESCRIPTION
        "Parameter 'source_ip_address' in event TCP.50"
    ::= { tcpEventObjects50 1 }

tcp50_destination_ip_address OBJECT-TYPE
    SYNTAX Integer32
    MAX-ACCESS accessible-for-notify
    STATUS current
    DESCRIPTION
        "Parameter 'destination_ip_address' in event TCP.50"
    ::= { tcpEventObjects50 2 }

tcp50_tcp_src_port OBJECT-TYPE
    SYNTAX IpAddress
    MAX-ACCESS accessible-for-notify
    STATUS current
    DESCRIPTION
        "Parameter 'tcp_src_port' in event TCP.50"
    ::= { tcpEventObjects50 3 }

tcp50_tcp_dst_port OBJECT-TYPE
    SYNTAX Integer32
    MAX-ACCESS accessible-for-notify
    STATUS current
    DESCRIPTION
        "Parameter 'tcp_dst_port' in event TCP.50"
    ::= { tcpEventObjects50 4 }

tcpEventObjects51 OBJECT-IDENTITY
    STATUS current
    DESCRIPTION
        "Event TCP.51
        The local window advertised is zero. The application is not draining
        the TCP receive buffer fast enough."
    ::= { tcpEventsGroup 51 }

tcp51_source_ip_address OBJECT-TYPE
    SYNTAX IpAddress
    MAX-ACCESS accessible-for-notify
    STATUS current
    DESCRIPTION
        "Parameter 'source_ip_address' in event TCP.51"
    ::= { tcpEventObjects51 1 }

tcp51_destination_ip_address OBJECT-TYPE
    SYNTAX Integer32
    MAX-ACCESS accessible-for-notify
    STATUS current
    DESCRIPTION
        "Parameter 'destination_ip_address' in event TCP.51"
    ::= { tcpEventObjects51 2 }

tcp51_tcp_src_port OBJECT-TYPE
    SYNTAX IpAddress
    MAX-ACCESS accessible-for-notify
    STATUS current
    DESCRIPTION
        "Parameter 'tcp_src_port' in event TCP.51"
    ::= { tcpEventObjects51 3 }

tcp51_tcp_dst_port OBJECT-TYPE
    SYNTAX Integer32
    MAX-ACCESS accessible-for-notify
    STATUS current
    DESCRIPTION
        "Parameter 'tcp_dst_port' in event TCP.51"
    ::= { tcpEventObjects51 4 }

tcpEventObjects52 OBJECT-IDENTITY
    STATUS current
    DESCRIPTION
        "Event TCP.52
        The TCP connection is closing, and we sent a FIN."
    ::= { tcpEventsGroup 52 }

tcp52_source_ip_address OBJECT-TYPE
    SYNTAX IpAddress
    MAX-ACCESS accessible-for-notify
    STATUS current
    DESCRIPTION
        "Parameter 'source_ip_address' in event TCP.52"
    ::= { tcpEventObjects52 1 }

tcp52_destination_ip_address OBJECT-TYPE
    SYNTAX Integer32
    MAX-ACCESS accessible-for-notify
    STATUS current
    DESCRIPTION
        "Parameter 'destination_ip_address' in event TCP.52"
    ::= { tcpEventObjects52 2 }

tcp52_tcp_src_port OBJECT-TYPE
    SYNTAX IpAddress
    MAX-ACCESS accessible-for-notify
    STATUS current
    DESCRIPTION
        "Parameter 'tcp_src_port' in event TCP.52"
    ::= { tcpEventObjects52 3 }

tcp52_tcp_dst_port OBJECT-TYPE
    SYNTAX Integer32
    MAX-ACCESS accessible-for-notify
    STATUS current
    DESCRIPTION
        "Parameter 'tcp_dst_port' in event TCP.52"
    ::= { tcpEventObjects52 4 }

tcp52_seq_num OBJECT-TYPE
    SYNTAX Integer32
    MAX-ACCESS accessible-for-notify
    STATUS current
    DESCRIPTION
        "Parameter 'seq_num' in event TCP.52"
    ::= { tcpEventObjects52 5 }

tcp52_ack_num OBJECT-TYPE
    SYNTAX Integer32
    MAX-ACCESS accessible-for-notify
    STATUS current
    DESCRIPTION
        "Parameter 'ack_num' in event TCP.52"
    ::= { tcpEventObjects52 6 }

tcpEventObjects54 OBJECT-IDENTITY
    STATUS current
    DESCRIPTION
        "Event TCP.54
        The transmit buffer size requested for a TCP connection is too large
        to be allocated by the system. TCP has selected in its place
        the largest chunk size available in the system."
    ::= { tcpEventsGroup 54 }

tcp54_requested_amount OBJECT-TYPE
    SYNTAX Integer32
    MAX-ACCESS accessible-for-notify
    STATUS current
    DESCRIPTION
        "Parameter 'requested_amount' in event TCP.54"
    ::= { tcpEventObjects54 1 }

tcp54_clipped_amount OBJECT-TYPE
    SYNTAX Integer32
    MAX-ACCESS accessible-for-notify
    STATUS current
    DESCRIPTION
        "Parameter 'clipped_amount' in event TCP.54"
    ::= { tcpEventObjects54 2 }

tcpEventObjects55 OBJECT-IDENTITY
    STATUS current
    DESCRIPTION
        "Event TCP.55
        The receive buffer size requested for a TCP connection is too large
        to be allocated by the system. TCP has selected in its place
        the largest chunk size available in the system."
    ::= { tcpEventsGroup 55 }

tcp55_requested_amount OBJECT-TYPE
    SYNTAX Integer32
    MAX-ACCESS accessible-for-notify
    STATUS current
    DESCRIPTION
        "Parameter 'requested_amount' in event TCP.55"
    ::= { tcpEventObjects55 1 }

tcp55_clipped_amount OBJECT-TYPE
    SYNTAX Integer32
    MAX-ACCESS accessible-for-notify
    STATUS current
    DESCRIPTION
        "Parameter 'clipped_amount' in event TCP.55"
    ::= { tcpEventObjects55 2 }


tcpNotification1 NOTIFICATION-TYPE
    OBJECTS { 
              tcp1_tcp_checksum, 
              tcp1_tcp_checksum 
            }
    STATUS current
    DESCRIPTION
        "Notification of Event TCP.1

        Message: 'packet checksum failed received packet checksum is $1 and calculated checksum is $2'

        Parameters list:
              $1: tcp1_tcp_checksum
              $2: tcp1_tcp_checksum

        Checksum failed because received packet checksum is not equal to
        the calculated checksum."
    ::= { tcpNotificationsPrefix 1 }

tcpNotification2 NOTIFICATION-TYPE
    OBJECTS { 
              tcp2_source_ip_address, 
              tcp2_source_tcp_port,
              tcp2_destination_ip_address,
              tcp2_destination_tcp_port 
            }
    STATUS current
    DESCRIPTION
        "Notification of Event TCP.2

        Message: '$1:$2 -> $3:$4 received packet with no tcp connection'

        Parameters list:
              $1: tcp2_source_ip_address
              $2: tcp2_source_tcp_port
              $3: tcp2_destination_ip_address
              $4: tcp2_destination_tcp_port

        TCP has received a packet with an invalid tcp port number."
    ::= { tcpNotificationsPrefix 2 }

tcpNotification3 NOTIFICATION-TYPE
    OBJECTS { 
              tcp3_local_ip_address, 
              tcp3_local_tcp_port,
              tcp3_remote_ip_address,
              tcp3_remote_tcp_port 
            }
    STATUS current
    DESCRIPTION
        "Notification of Event TCP.3

        Message: '$1:$2 -- $3:$4 TCP active open successful'

        Parameters list:
              $1: tcp3_local_ip_address
              $2: tcp3_local_tcp_port
              $3: tcp3_remote_ip_address
              $4: tcp3_remote_tcp_port

        Active open was successful and we are notifying application of the open."
    ::= { tcpNotificationsPrefix 3 }

tcpNotification4 NOTIFICATION-TYPE
    OBJECTS { 
              tcp4_source_ip_address, 
              tcp4_source_tcp_port,
              tcp4_destination_ip_address,
              tcp4_destination_tcp_port 
            }
    STATUS current
    DESCRIPTION
        "Notification of Event TCP.4

        Message: '$1:$2 -> $3:$4 received invalid SYN packet, kill connection'

        Parameters list:
              $1: tcp4_source_ip_address
              $2: tcp4_source_tcp_port
              $3: tcp4_destination_ip_address
              $4: tcp4_destination_tcp_port

        TCP has received an illegal SYN packet, so kill the connection."
    ::= { tcpNotificationsPrefix 4 }

tcpNotification5 NOTIFICATION-TYPE
    OBJECTS { 
              tcp5_debug_string 
            }
    STATUS current
    DESCRIPTION
        "Notification of Event TCP.5

        Message: '$1'

        Parameters list:
              $1: tcp5_debug_string

        Debug string."
    ::= { tcpNotificationsPrefix 5 }

tcpNotification6 NOTIFICATION-TYPE
    OBJECTS { 
              tcp6_source_ip_address, 
              tcp6_source_tcp_port,
              tcp6_destination_ip_address,
              tcp6_destination_tcp_port,
              tcp6_reason 
            }
    STATUS current
    DESCRIPTION
        "Notification of Event TCP.6

        Message: '$1:$2 -> $3:$4 MD5 authentication failed, reason: $5'

        Parameters list:
              $1: tcp6_source_ip_address
              $2: tcp6_source_tcp_port
              $3: tcp6_destination_ip_address
              $4: tcp6_destination_tcp_port
              $5: tcp6_reason

        TCP has received an invalid packet when MD5 authentication is active, so drop packet."
    ::= { tcpNotificationsPrefix 6 }

tcpNotification7 NOTIFICATION-TYPE
    OBJECTS { 
              tcp7_source_ip_address, 
              tcp7_source_port,
              tcp7_destination_ip_address,
              tcp7_destination_port,
              tcp7_reject_code 
            }
    STATUS current
    DESCRIPTION
        "Notification of Event TCP.7

        Message: '$1:$2 -> $3:$4 dropped segment, reason $5, send a valid ACK in response'

        Parameters list:
              $1: tcp7_source_ip_address
              $2: tcp7_source_port
              $3: tcp7_destination_ip_address
              $4: tcp7_destination_port
              $5: tcp7_reject_code

        TCP has rejected a segment. Reject codes are as follows:
        Reject codes:
        1 - Seg len = 0, Rcv win > 0, seqnum < tcb_ack or seqnum >= winend
        2 - Seg len = 0, Rcv win = 0, seqnum != tcb_ack
        3 - Seg len > 0, Rcv win > 0, inend < tcb_ack or seqnum >= winend
        4 - Seg len > 0, Rcv win = 0.
        Note: we only ACK if the segment received was a non RST segment."
    ::= { tcpNotificationsPrefix 7 }

tcpNotification8 NOTIFICATION-TYPE
    OBJECTS { 
              tcp8_source_ip_address, 
              tcp8_source_tcp_port,
              tcp8_destination_ip_address,
              tcp8_destination_tcp_port,
              tcp8_seq_num 
            }
    STATUS current
    DESCRIPTION
        "Notification of Event TCP.8

        Message: '$1:$2 -> $3:$4 received old duplicate packet, sequence number $5, send ACK in response'

        Parameters list:
              $1: tcp8_source_ip_address
              $2: tcp8_source_tcp_port
              $3: tcp8_destination_ip_address
              $4: tcp8_destination_tcp_port
              $5: tcp8_seq_num

        TCP has received an old segment that has already been consumed by the
        application, so send ACK in response."
    ::= { tcpNotificationsPrefix 8 }

tcpNotification9 NOTIFICATION-TYPE
    OBJECTS { 
              tcp9_source_ip_address, 
              tcp9_source_tcp_port,
              tcp9_destination_ip_address,
              tcp9_destination_tcp_port,
              tcp9_seq_num 
            }
    STATUS current
    DESCRIPTION
        "Notification of Event TCP.9

        Message: '$1:$2 -> $3:$4 received RST, sequence number $5; LISTEN state, drop segment'

        Parameters list:
              $1: tcp9_source_ip_address
              $2: tcp9_source_tcp_port
              $3: tcp9_destination_ip_address
              $4: tcp9_destination_tcp_port
              $5: tcp9_seq_num

        TCP has received a RST while in LISTEN state; just ignore packet."
    ::= { tcpNotificationsPrefix 9 }

tcpNotification10 NOTIFICATION-TYPE
    OBJECTS { 
              tcp10_source_ip_address, 
              tcp10_source_tcp_port,
              tcp10_destination_ip_address,
              tcp10_destination_tcp_port,
              tcp10_seq_num 
            }
    STATUS current
    DESCRIPTION
        "Notification of Event TCP.10

        Message: '$1:$2 -> $3:$4 received RST, sequence number $5; SYN_RECEIVED or SYN_SENT states, drop segment and return to LISTEN state'

        Parameters list:
              $1: tcp10_source_ip_address
              $2: tcp10_source_tcp_port
              $3: tcp10_destination_ip_address
              $4: tcp10_destination_tcp_port
              $5: tcp10_seq_num

        TCP has received a RST while in SYN_RECEIVED or SYN_SENT states;
        drop packet and return to LISTEN state."
    ::= { tcpNotificationsPrefix 10 }

tcpNotification11 NOTIFICATION-TYPE
    OBJECTS { 
              tcp11_source_ip_address, 
              tcp11_source_tcp_port,
              tcp11_destination_ip_address,
              tcp11_destination_tcp_port,
              tcp11_seq_num 
            }
    STATUS current
    DESCRIPTION
        "Notification of Event TCP.11

        Message: '$1:$2 -> $3:$4 received RST, sequence number $5; drop segment and abort connection'

        Parameters list:
              $1: tcp11_source_ip_address
              $2: tcp11_source_tcp_port
              $3: tcp11_destination_ip_address
              $4: tcp11_destination_tcp_port
              $5: tcp11_seq_num

        TCP has received a RST; abort connection."
    ::= { tcpNotificationsPrefix 11 }

tcpNotification12 NOTIFICATION-TYPE
    OBJECTS { 
              tcp12_source_ip_address, 
              tcp12_source_tcp_port,
              tcp12_destination_ip_address,
              tcp12_destination_tcp_port,
              tcp12_seq_num 
            }
    STATUS current
    DESCRIPTION
        "Notification of Event TCP.12

        Message: '$1:$2 -> $3:$4 drop segment, sequence number $5; NO ACK is present'

        Parameters list:
              $1: tcp12_source_ip_address
              $2: tcp12_source_tcp_port
              $3: tcp12_destination_ip_address
              $4: tcp12_destination_tcp_port
              $5: tcp12_seq_num

        TCP has stopped processing the packet because there is no ACK present
        in the packet."
    ::= { tcpNotificationsPrefix 12 }

tcpNotification13 NOTIFICATION-TYPE
    OBJECTS { 
              tcp13_source_ip_address, 
              tcp13_source_tcp_port,
              tcp13_destination_ip_address,
              tcp13_destination_tcp_port,
              tcp13_seq_num,
              tcp13_ack_num 
            }
    STATUS current
    DESCRIPTION
        "Notification of Event TCP.13

        Message: '$1:$2 -> $3:$4 drop segment, sequence number $5, acknowledge number $6, received invalid ACK'

        Parameters list:
              $1: tcp13_source_ip_address
              $2: tcp13_source_tcp_port
              $3: tcp13_destination_ip_address
              $4: tcp13_destination_tcp_port
              $5: tcp13_seq_num
              $6: tcp13_ack_num

        Stop processing the segment because it contains acknowledgement for
        data not yet sent."
    ::= { tcpNotificationsPrefix 13 }

tcpNotification14 NOTIFICATION-TYPE
    OBJECTS { 
              tcp14_source_ip_address, 
              tcp14_source_tcp_port,
              tcp14_destination_ip_address,
              tcp14_destination_tcp_port,
              tcp14_seq_num 
            }
    STATUS current
    DESCRIPTION
        "Notification of Event TCP.14

        Message: '$1:$2 -> $3:$4 received FIN, sequence number $5; ESTABLISHED state,'

        Parameters list:
              $1: tcp14_source_ip_address
              $2: tcp14_source_tcp_port
              $3: tcp14_destination_ip_address
              $4: tcp14_destination_tcp_port
              $5: tcp14_seq_num

        TCP has received a FIN while in ESTABLISHED state; when all data
        has been received, send FIN|ACK."
    ::= { tcpNotificationsPrefix 14 }

tcpNotification15 NOTIFICATION-TYPE
    OBJECTS { 
              tcp15_source_ip_address, 
              tcp15_source_tcp_port,
              tcp15_destination_ip_address,
              tcp15_destination_tcp_port,
              tcp15_seq_num 
            }
    STATUS current
    DESCRIPTION
        "Notification of Event TCP.15

        Message: '$1:$2 -> $3:$4 received segment with PSH bit set, sequence number $5'

        Parameters list:
              $1: tcp15_source_ip_address
              $2: tcp15_source_tcp_port
              $3: tcp15_destination_ip_address
              $4: tcp15_destination_tcp_port
              $5: tcp15_seq_num

        TCP has received a segment with PSH bit set."
    ::= { tcpNotificationsPrefix 15 }

tcpNotification16 NOTIFICATION-TYPE
    OBJECTS { 
              tcp16_source_ip_address, 
              tcp16_source_tcp_port,
              tcp16_destination_ip_address,
              tcp16_destination_tcp_port,
              tcp16_seq_num 
            }
    STATUS current
    DESCRIPTION
        "Notification of Event TCP.16

        Message: '$1:$2 -> $3:$4 received valid segment, sequence number $5; SYNRCVD state, enter ESTABLISHED state'

        Parameters list:
              $1: tcp16_source_ip_address
              $2: tcp16_source_tcp_port
              $3: tcp16_destination_ip_address
              $4: tcp16_destination_tcp_port
              $5: tcp16_seq_num

        TCP has received a valid segment while in SYNRCVD state; enter
        ESTABLISHED state and notify application of the open."
    ::= { tcpNotificationsPrefix 16 }

tcpNotification17 NOTIFICATION-TYPE
    OBJECTS { 
              tcp17_source_ip_address, 
              tcp17_source_tcp_port,
              tcp17_destination_ip_address,
              tcp17_destination_tcp_port,
              tcp17_seq_num 
            }
    STATUS current
    DESCRIPTION
        "Notification of Event TCP.17

        Message: '$1:$2 -> $3:$4 received FIN, sequence number $5; LISTEN state, send RST'

        Parameters list:
              $1: tcp17_source_ip_address
              $2: tcp17_source_tcp_port
              $3: tcp17_destination_ip_address
              $4: tcp17_destination_tcp_port
              $5: tcp17_seq_num

        TCP has received a FIN while in the LISTEN state, so we send RST to
        the other side."
    ::= { tcpNotificationsPrefix 17 }

tcpNotification18 NOTIFICATION-TYPE
    OBJECTS { 
              tcp18_source_ip_address, 
              tcp18_source_tcp_port,
              tcp18_destination_ip_address,
              tcp18_destination_tcp_port,
              tcp18_seq_num,
              tcp18_seq_num,
              tcp18_seq_num 
            }
    STATUS current
    DESCRIPTION
        "Notification of Event TCP.18

        Message: '$1:$2 -> $3:$4 received an out of order segment, sequence number $5; hole created at end of receive buffer seq num $6 to $7'

        Parameters list:
              $1: tcp18_source_ip_address
              $2: tcp18_source_tcp_port
              $3: tcp18_destination_ip_address
              $4: tcp18_destination_tcp_port
              $5: tcp18_seq_num
              $6: tcp18_seq_num
              $7: tcp18_seq_num

        TCP has received an out of order packet; this creates a hole in
        the receive buffer."
    ::= { tcpNotificationsPrefix 18 }

tcpNotification19 NOTIFICATION-TYPE
    OBJECTS { 
              tcp19_source_ip_address, 
              tcp19_source_tcp_port,
              tcp19_destination_ip_address,
              tcp19_destination_tcp_port,
              tcp19_seq_num,
              tcp19_seq_num,
              tcp19_seq_num 
            }
    STATUS current
    DESCRIPTION
        "Notification of Event TCP.19

        Message: '$1:$2 -> $3:$4 received an out of order segment, sequence number $5; hole created at end of receive buffer seq num $6 to $7'

        Parameters list:
              $1: tcp19_source_ip_address
              $2: tcp19_source_tcp_port
              $3: tcp19_destination_ip_address
              $4: tcp19_destination_tcp_port
              $5: tcp19_seq_num
              $6: tcp19_seq_num
              $7: tcp19_seq_num

        TCP has received an out of order packet; this creates a hole in
        the receive buffer."
    ::= { tcpNotificationsPrefix 19 }

tcpNotification20 NOTIFICATION-TYPE
    OBJECTS { 
              tcp20_source_ip_address, 
              tcp20_source_tcp_port,
              tcp20_destination_ip_address,
              tcp20_destination_tcp_port,
              tcp20_seq_num,
              tcp20_seq_num,
              tcp20_seq_num 
            }
    STATUS current
    DESCRIPTION
        "Notification of Event TCP.20

        Message: '$1:$2 -> $3:$4 received segment, sequence number $5; partially fills the beginning of a hole $6 to $7'

        Parameters list:
              $1: tcp20_source_ip_address
              $2: tcp20_source_tcp_port
              $3: tcp20_destination_ip_address
              $4: tcp20_destination_tcp_port
              $5: tcp20_seq_num
              $6: tcp20_seq_num
              $7: tcp20_seq_num

        TCP has received a packet that partially fills the beginning of a hole."
    ::= { tcpNotificationsPrefix 20 }

tcpNotification21 NOTIFICATION-TYPE
    OBJECTS { 
              tcp21_source_ip_address, 
              tcp21_source_tcp_port,
              tcp21_destination_ip_address,
              tcp21_destination_tcp_port,
              tcp21_seq_num,
              tcp21_seq_num,
              tcp21_seq_num 
            }
    STATUS current
    DESCRIPTION
        "Notification of Event TCP.21

        Message: '$1:$2 -> $3:$4 received segment, sequence number $5; partially fills the end of a hole $6 to $7'

        Parameters list:
              $1: tcp21_source_ip_address
              $2: tcp21_source_tcp_port
              $3: tcp21_destination_ip_address
              $4: tcp21_destination_tcp_port
              $5: tcp21_seq_num
              $6: tcp21_seq_num
              $7: tcp21_seq_num

        TCP has received a packet that partially fills the end of a hole."
    ::= { tcpNotificationsPrefix 21 }

tcpNotification22 NOTIFICATION-TYPE
    OBJECTS { 
              tcp22_source_ip_address, 
              tcp22_source_tcp_port,
              tcp22_destination_ip_address,
              tcp22_destination_tcp_port,
              tcp22_seq_num,
              tcp22_seq_num,
              tcp22_seq_num 
            }
    STATUS current
    DESCRIPTION
        "Notification of Event TCP.22

        Message: '$1:$2 -> $3:$4 received segment, sequence number $5; completely fills a hole, removing hole $6 to $7'

        Parameters list:
              $1: tcp22_source_ip_address
              $2: tcp22_source_tcp_port
              $3: tcp22_destination_ip_address
              $4: tcp22_destination_tcp_port
              $5: tcp22_seq_num
              $6: tcp22_seq_num
              $7: tcp22_seq_num

        TCP has received a packet that completely fills a hole."
    ::= { tcpNotificationsPrefix 22 }

tcpNotification23 NOTIFICATION-TYPE
    OBJECTS { 
              tcp23_source_ip_address, 
              tcp23_source_tcp_port,
              tcp23_destination_ip_address,
              tcp23_destination_tcp_port,
              tcp23_seq_num 
            }
    STATUS current
    DESCRIPTION
        "Notification of Event TCP.23

        Message: '$1:$2 -> $3:$4 drop segment, sequence number $5; segment too big for receive buffer'

        Parameters list:
              $1: tcp23_source_ip_address
              $2: tcp23_source_tcp_port
              $3: tcp23_destination_ip_address
              $4: tcp23_destination_tcp_port
              $5: tcp23_seq_num

        TCP has received a packet that is too big to fit into the remaining
        space in the receive buffer."
    ::= { tcpNotificationsPrefix 23 }

tcpNotification24 NOTIFICATION-TYPE
    OBJECTS { 
              tcp24_source_ip_address, 
              tcp24_source_tcp_port,
              tcp24_destination_ip_address,
              tcp24_destination_tcp_port,
              tcp24_state 
            }
    STATUS current
    DESCRIPTION
        "Notification of Event TCP.24

        Message: '$1:$2 -- $3:$4 process a received FIN; current state $5 is not SYNRCVD|ESTAB, so do nothing'

        Parameters list:
              $1: tcp24_source_ip_address
              $2: tcp24_source_tcp_port
              $3: tcp24_destination_ip_address
              $4: tcp24_destination_tcp_port
              $5: tcp24_state

        TCP processing FIN while not in SYNRCVD|ESTAB state."
    ::= { tcpNotificationsPrefix 24 }

tcpNotification25 NOTIFICATION-TYPE
    OBJECTS { 
              tcp25_source_ip_address, 
              tcp25_source_tcp_port,
              tcp25_destination_ip_address,
              tcp25_destination_tcp_port 
            }
    STATUS current
    DESCRIPTION
        "Notification of Event TCP.25

        Message: '$1:$2 -- $3:$4 process a received FIN; current state is SYNRCVD|ESTAB'

        Parameters list:
              $1: tcp25_source_ip_address
              $2: tcp25_source_tcp_port
              $3: tcp25_destination_ip_address
              $4: tcp25_destination_tcp_port

        TCP processing FIN while in SYNRCVD|ESTAB state."
    ::= { tcpNotificationsPrefix 25 }

tcpNotification26 NOTIFICATION-TYPE
    OBJECTS { 
              tcp26_source_ip_address, 
              tcp26_source_tcp_port,
              tcp26_destination_ip_address,
              tcp26_destination_tcp_port 
            }
    STATUS current
    DESCRIPTION
        "Notification of Event TCP.26

        Message: '$1:$2 -- $3:$4 application posted receive timeout has fired'

        Parameters list:
              $1: tcp26_source_ip_address
              $2: tcp26_source_tcp_port
              $3: tcp26_destination_ip_address
              $4: tcp26_destination_tcp_port

        Application posts a read specifying a timeout value. If not all the
        requested data has been received within a timeout period, a timer fires,
        and whatever is in the receive buffer is given to the application."
    ::= { tcpNotificationsPrefix 26 }

tcpNotification27 NOTIFICATION-TYPE
    OBJECTS { 
              tcp27_source_ip_address, 
              tcp27_source_tcp_port,
              tcp27_destination_ip_address,
              tcp27_destination_tcp_port 
            }
    STATUS current
    DESCRIPTION
        "Notification of Event TCP.27

        Message: '$1:$2 -- $3:$4 foreign port closed the advertised window illegally'

        Parameters list:
              $1: tcp27_source_ip_address
              $2: tcp27_source_tcp_port
              $3: tcp27_destination_ip_address
              $4: tcp27_destination_tcp_port

        The other side has been deaf and mute, and the the foreign window
        seems to have been closed illegally; send a RST."
    ::= { tcpNotificationsPrefix 27 }

tcpNotification28 NOTIFICATION-TYPE
    OBJECTS { 
              tcp28_source_ip_address, 
              tcp28_source_tcp_port,
              tcp28_destination_ip_address,
              tcp28_destination_tcp_port 
            }
    STATUS current
    DESCRIPTION
        "Notification of Event TCP.28

        Message: '$1:$2 -- $3:$4 state of TCP connection transitioned to SYN-RECEIVED state'

        Parameters list:
              $1: tcp28_source_ip_address
              $2: tcp28_source_tcp_port
              $3: tcp28_destination_ip_address
              $4: tcp28_destination_tcp_port

        State of the connection has transitioned to SYN-RECEIVED state
        as a result of either an active open or a passive open."
    ::= { tcpNotificationsPrefix 28 }

tcpNotification29 NOTIFICATION-TYPE
    OBJECTS { 
              tcp29_source_ip_address, 
              tcp29_source_tcp_port,
              tcp29_destination_ip_address,
              tcp29_destination_tcp_port 
            }
    STATUS current
    DESCRIPTION
        "Notification of Event TCP.29

        Message: '$1:$2 -- $3:$4 state of TCP connection transitioned to ESTABLISHED state'

        Parameters list:
              $1: tcp29_source_ip_address
              $2: tcp29_source_tcp_port
              $3: tcp29_destination_ip_address
              $4: tcp29_destination_tcp_port

        State of the connection has transitioned to ESTABLISHED state
        as a result of either an active open or a passive open."
    ::= { tcpNotificationsPrefix 29 }

tcpNotification30 NOTIFICATION-TYPE
    OBJECTS { 
              tcp30_source_ip_address, 
              tcp30_source_tcp_port,
              tcp30_destination_ip_address,
              tcp30_destination_tcp_port,
              tcp30_flags,
              tcp30_sequence,
              tcp30_acknowledge,
              tcp30_window,
              tcp30_length 
            }
    STATUS current
    DESCRIPTION
        "Notification of Event TCP.30

        Message: '$1:$2 -> $3:$4 received TCP packet with flags [$5] sequence $6 acknowledge $7 window $8 length $9'

        Parameters list:
              $1: tcp30_source_ip_address
              $2: tcp30_source_tcp_port
              $3: tcp30_destination_ip_address
              $4: tcp30_destination_tcp_port
              $5: tcp30_flags
              $6: tcp30_sequence
              $7: tcp30_acknowledge
              $8: tcp30_window
              $9: tcp30_length

        TCP has received a packet."
    ::= { tcpNotificationsPrefix 30 }

tcpNotification31 NOTIFICATION-TYPE
    OBJECTS { 
              tcp31_source_ip_address, 
              tcp31_source_tcp_port,
              tcp31_destination_ip_address,
              tcp31_destination_tcp_port,
              tcp31_seq_num,
              tcp31_length 
            }
    STATUS current
    DESCRIPTION
        "Notification of Event TCP.31

        Message: '$1:$2 -> $3:$4 data with sequence number $5 length $6 given to application'

        Parameters list:
              $1: tcp31_source_ip_address
              $2: tcp31_source_tcp_port
              $3: tcp31_destination_ip_address
              $4: tcp31_destination_tcp_port
              $5: tcp31_seq_num
              $6: tcp31_length

        Valid data in receive buffer has been handed to the application for
        further processing."
    ::= { tcpNotificationsPrefix 31 }

tcpNotification32 NOTIFICATION-TYPE
    OBJECTS { 
              tcp32_source_ip_address, 
              tcp32_source_tcp_port,
              tcp32_destination_ip_address,
              tcp32_destination_tcp_port 
            }
    STATUS current
    DESCRIPTION
        "Notification of Event TCP.32

        Message: '$1:$2 -> $3:$4 excessive number of retries has occurred'

        Parameters list:
              $1: tcp32_source_ip_address
              $2: tcp32_source_tcp_port
              $3: tcp32_destination_ip_address
              $4: tcp32_destination_tcp_port

        We have retransmitted a frame an excessive number of times.
        If the application has closed the connection already, just abort. Else,
        notify the application that there is a problem."
    ::= { tcpNotificationsPrefix 32 }

tcpNotification33 NOTIFICATION-TYPE
    OBJECTS { 
              tcp33_source_ip_address, 
              tcp33_source_tcp_port,
              tcp33_destination_ip_address,
              tcp33_destination_tcp_port,
              tcp33_flags,
              tcp33_seq_num,
              tcp33_ack_num,
              tcp33_window 
            }
    STATUS current
    DESCRIPTION
        "Notification of Event TCP.33

        Message: '$1:$2 -> $3:$4 send control segment with flags [$5] sequence number $6, acknowledge number $7 and window $8'

        Parameters list:
              $1: tcp33_source_ip_address
              $2: tcp33_source_tcp_port
              $3: tcp33_destination_ip_address
              $4: tcp33_destination_tcp_port
              $5: tcp33_flags
              $6: tcp33_seq_num
              $7: tcp33_ack_num
              $8: tcp33_window

        Send a control segment to either ack a segment or send special control
        segments like FIN or RST."
    ::= { tcpNotificationsPrefix 33 }

tcpNotification34 NOTIFICATION-TYPE
    OBJECTS { 
              tcp34_source_ip_address, 
              tcp34_source_tcp_port,
              tcp34_destination_ip_address,
              tcp34_destination_tcp_port,
              tcp34_flags,
              tcp34_seq_num,
              tcp34_ack_num,
              tcp34_window,
              tcp34_length 
            }
    STATUS current
    DESCRIPTION
        "Notification of Event TCP.34

        Message: '$1:$2 -> $3:$4 retransmit data with flags [$5] sequence number $6 ack number $7 window $8 and length $9'

        Parameters list:
              $1: tcp34_source_ip_address
              $2: tcp34_source_tcp_port
              $3: tcp34_destination_ip_address
              $4: tcp34_destination_tcp_port
              $5: tcp34_flags
              $6: tcp34_seq_num
              $7: tcp34_ack_num
              $8: tcp34_window
              $9: tcp34_length

        We have failed to receive a valid ACK for transmitted data,
        so retransmit the data."
    ::= { tcpNotificationsPrefix 34 }

tcpNotification35 NOTIFICATION-TYPE
    OBJECTS { 
              tcp35_source_ip_address, 
              tcp35_source_tcp_port,
              tcp35_destination_ip_address,
              tcp35_destination_tcp_port,
              tcp35_flags,
              tcp35_seq_num,
              tcp35_ack_num,
              tcp35_window,
              tcp35_length 
            }
    STATUS current
    DESCRIPTION
        "Notification of Event TCP.35

        Message: '$1:$2 -> $3:$4 transmit data with flags [$5] sequence number $6 ack number $7 window $8 and length $9'

        Parameters list:
              $1: tcp35_source_ip_address
              $2: tcp35_source_tcp_port
              $3: tcp35_destination_ip_address
              $4: tcp35_destination_tcp_port
              $5: tcp35_flags
              $6: tcp35_seq_num
              $7: tcp35_ack_num
              $8: tcp35_window
              $9: tcp35_length

        Transmit data."
    ::= { tcpNotificationsPrefix 35 }

tcpNotification36 NOTIFICATION-TYPE
    OBJECTS { 
              tcp36_source_ip_address, 
              tcp36_source_tcp_port,
              tcp36_destination_ip_address,
              tcp36_destination_tcp_port,
              tcp36_option 
            }
    STATUS current
    DESCRIPTION
        "Notification of Event TCP.36

        Message: '$1:$2 -> $3:$4 illegal option $5 received in SYN segment'

        Parameters list:
              $1: tcp36_source_ip_address
              $2: tcp36_source_tcp_port
              $3: tcp36_destination_ip_address
              $4: tcp36_destination_tcp_port
              $5: tcp36_option

        An unsupported option is present in the options field of a SYN packet."
    ::= { tcpNotificationsPrefix 36 }

tcpNotification37 NOTIFICATION-TYPE
    STATUS current
    DESCRIPTION
        "Notification of Event TCP.37

        Message: '---'

        Reserved for possible future use."
    ::= { tcpNotificationsPrefix 37 }

tcpNotification38 NOTIFICATION-TYPE
    OBJECTS { 
              tcp38_source_ip_address, 
              tcp38_source_tcp_port,
              tcp38_destination_ip_address,
              tcp38_destination_tcp_port,
              tcp38_seq_num 
            }
    STATUS current
    DESCRIPTION
        "Notification of Event TCP.38

        Message: '$1:$2 -> $3:$4 reject segment with sequence number $5; bad ACK in segment while in SYNRCVD state, send RST'

        Parameters list:
              $1: tcp38_source_ip_address
              $2: tcp38_source_tcp_port
              $3: tcp38_destination_ip_address
              $4: tcp38_destination_tcp_port
              $5: tcp38_seq_num

        Reject the segment, and send a RST to the other side for receiving
        a segment with the incorrect acknowledgement while in the
        SYNRCVD state. Until a correct acknowledgement is received, we cannot
        progress into the ESTABLISHED state."
    ::= { tcpNotificationsPrefix 38 }

tcpNotification39 NOTIFICATION-TYPE
    OBJECTS { 
              tcp39_source_ip_address, 
              tcp39_source_tcp_port,
              tcp39_destination_ip_address,
              tcp39_destination_tcp_port,
              tcp39_seq_num 
            }
    STATUS current
    DESCRIPTION
        "Notification of Event TCP.39

        Message: '$1:$2 -> $3:$4 received ACK segment, sequence number $5; while in LISTEN state, send RST'

        Parameters list:
              $1: tcp39_source_ip_address
              $2: tcp39_source_tcp_port
              $3: tcp39_destination_ip_address
              $4: tcp39_destination_tcp_port
              $5: tcp39_seq_num

        TCP has received an ACK while in the LISTEN state; this does not make
        any sense because we have not yet sent any data, so nothing should
        be ACKed. As a result, we send a RST."
    ::= { tcpNotificationsPrefix 39 }

tcpNotification40 NOTIFICATION-TYPE
    OBJECTS { 
              tcp40_source_ip_address, 
              tcp40_source_tcp_port,
              tcp40_destination_ip_address,
              tcp40_destination_tcp_port,
              tcp40_flags,
              tcp40_seq_num,
              tcp40_ack_num 
            }
    STATUS current
    DESCRIPTION
        "Notification of Event TCP.40

        Message: '$1:$2 -> $3:$4 sending TCP RESET with flags [$5] sequence number $6 acknowledge $7'

        Parameters list:
              $1: tcp40_source_ip_address
              $2: tcp40_source_tcp_port
              $3: tcp40_destination_ip_address
              $4: tcp40_destination_tcp_port
              $5: tcp40_flags
              $6: tcp40_seq_num
              $7: tcp40_ack_num

        TCP is sending a RESET segment to the other side."
    ::= { tcpNotificationsPrefix 40 }

tcpNotification41 NOTIFICATION-TYPE
    OBJECTS { 
              tcp41_source_ip_address, 
              tcp41_source_tcp_port,
              tcp41_destination_ip_address,
              tcp41_destination_tcp_port 
            }
    STATUS current
    DESCRIPTION
        "Notification of Event TCP.41

        Message: '$1:$2 -- $3:$4 TCP connection closed'

        Parameters list:
              $1: tcp41_source_ip_address
              $2: tcp41_source_tcp_port
              $3: tcp41_destination_ip_address
              $4: tcp41_destination_tcp_port

        TCP connection is closed - notifying the application."
    ::= { tcpNotificationsPrefix 41 }

tcpNotification42 NOTIFICATION-TYPE
    OBJECTS { 
              tcp42_source_ip_address, 
              tcp42_source_tcp_port,
              tcp42_destination_ip_address,
              tcp42_destination_tcp_port 
            }
    STATUS current
    DESCRIPTION
        "Notification of Event TCP.42

        Message: '$1:$2 -- $3:$4 freeing tcb block'

        Parameters list:
              $1: tcp42_source_ip_address
              $2: tcp42_source_tcp_port
              $3: tcp42_destination_ip_address
              $4: tcp42_destination_tcp_port

        Freeing the TCB block associated with the TCP connection
        that has closed."
    ::= { tcpNotificationsPrefix 42 }

tcpNotification43 NOTIFICATION-TYPE
    OBJECTS { 
              tcp43_source_ip_address, 
              tcp43_source_tcp_port,
              tcp43_destination_ip_address,
              tcp43_destination_tcp_port,
              tcp43_seq_num 
            }
    STATUS current
    DESCRIPTION
        "Notification of Event TCP.43

        Message: '$1:$2 -> $3:$4 overlap allowed in packet with sequence number $5'

        Parameters list:
              $1: tcp43_source_ip_address
              $2: tcp43_source_tcp_port
              $3: tcp43_destination_ip_address
              $4: tcp43_destination_tcp_port
              $5: tcp43_seq_num

        TCP has received a segment with data that has already been consumed
        by the application."
    ::= { tcpNotificationsPrefix 43 }

tcpNotification44 NOTIFICATION-TYPE
    OBJECTS { 
              tcp44_source_ip_address, 
              tcp44_source_tcp_port,
              tcp44_destination_ip_address,
              tcp44_destination_tcp_port 
            }
    STATUS current
    DESCRIPTION
        "Notification of Event TCP.44

        Message: '$1:$2 -> $3:$4 Idle timer fires for connection'

        Parameters list:
              $1: tcp44_source_ip_address
              $2: tcp44_source_tcp_port
              $3: tcp44_destination_ip_address
              $4: tcp44_destination_tcp_port

        Idle timer fires for TCP connection."
    ::= { tcpNotificationsPrefix 44 }

tcpNotification45 NOTIFICATION-TYPE
    OBJECTS { 
              tcp45_source_ip_address, 
              tcp45_source_tcp_port,
              tcp45_destination_ip_address,
              tcp45_destination_tcp_port 
            }
    STATUS current
    DESCRIPTION
        "Notification of Event TCP.45

        Message: '$1:$2 -> $3:$4 Retransmit timer fires for connection'

        Parameters list:
              $1: tcp45_source_ip_address
              $2: tcp45_source_tcp_port
              $3: tcp45_destination_ip_address
              $4: tcp45_destination_tcp_port

        Retransmit timer fires for TCP connection."
    ::= { tcpNotificationsPrefix 45 }

tcpNotification46 NOTIFICATION-TYPE
    OBJECTS { 
              tcp46_source_ip_address, 
              tcp46_source_tcp_port,
              tcp46_destination_ip_address,
              tcp46_destination_tcp_port 
            }
    STATUS current
    DESCRIPTION
        "Notification of Event TCP.46

        Message: '$1:$2 -- $3:$4 State transitioned from ESTABLISHED to FINWAIT'

        Parameters list:
              $1: tcp46_source_ip_address
              $2: tcp46_source_tcp_port
              $3: tcp46_destination_ip_address
              $4: tcp46_destination_tcp_port

        State of tcp connection has transitioned from ESTABLISHED to
        FINWAIT - send FIN, and now waiting for FIN-ACK to arrive."
    ::= { tcpNotificationsPrefix 46 }

tcpNotification47 NOTIFICATION-TYPE
    OBJECTS { 
              tcp47_source_ip_address, 
              tcp47_source_tcp_port,
              tcp47_destination_ip_address,
              tcp47_destination_tcp_port 
            }
    STATUS current
    DESCRIPTION
        "Notification of Event TCP.47

        Message: '$1:$2 -- $3:$4 State transitioned to CLOSED'

        Parameters list:
              $1: tcp47_source_ip_address
              $2: tcp47_source_tcp_port
              $3: tcp47_destination_ip_address
              $4: tcp47_destination_tcp_port

        State of tcp connection has transitioned to CLOSED."
    ::= { tcpNotificationsPrefix 47 }

tcpNotification48 NOTIFICATION-TYPE
    OBJECTS { 
              tcp48_source_ip_address, 
              tcp48_source_tcp_port,
              tcp48_destination_ip_address,
              tcp48_destination_tcp_port 
            }
    STATUS current
    DESCRIPTION
        "Notification of Event TCP.48

        Message: '$1:$2 -> $3:$4 Received data after CLOSE was issued, and window is zero, send RST'

        Parameters list:
              $1: tcp48_source_ip_address
              $2: tcp48_source_tcp_port
              $3: tcp48_destination_ip_address
              $4: tcp48_destination_tcp_port

        TCP connection is CLOSING due to application requesting a CLOSE.
        After the window shrinks to zero, discard any packets received.
        This is based on the half-duplex TCP close sequence."
    ::= { tcpNotificationsPrefix 48 }

tcpNotification49 NOTIFICATION-TYPE
    OBJECTS { 
              tcp49_source_ip_address, 
              tcp49_destination_ip_address,
              tcp49_tcp_src_port,
              tcp49_tcp_dst_port 
            }
    STATUS current
    DESCRIPTION
        "Notification of Event TCP.49

        Message: '$1:$2 -> $3:$4 Received NACK'

        Parameters list:
              $1: tcp49_source_ip_address
              $2: tcp49_destination_ip_address
              $3: tcp49_tcp_src_port
              $4: tcp49_tcp_dst_port

        The other side has send an old ACK with zero data length - we treat
        this as a NACK."
    ::= { tcpNotificationsPrefix 49 }

tcpNotification50 NOTIFICATION-TYPE
    OBJECTS { 
              tcp50_source_ip_address, 
              tcp50_destination_ip_address,
              tcp50_tcp_src_port,
              tcp50_tcp_dst_port 
            }
    STATUS current
    DESCRIPTION
        "Notification of Event TCP.50

        Message: '$1:$2 -> $3:$4 Received Acknowledge for the keep alive packet sent'

        Parameters list:
              $1: tcp50_source_ip_address
              $2: tcp50_destination_ip_address
              $3: tcp50_tcp_src_port
              $4: tcp50_tcp_dst_port

        The other side has acknowledged the keep alive packet. The keep alive
        packet is sent if keep alive is enabled on this TCP connection, and
        the connection has been idle."
    ::= { tcpNotificationsPrefix 50 }

tcpNotification51 NOTIFICATION-TYPE
    OBJECTS { 
              tcp51_source_ip_address, 
              tcp51_destination_ip_address,
              tcp51_tcp_src_port,
              tcp51_tcp_dst_port 
            }
    STATUS current
    DESCRIPTION
        "Notification of Event TCP.51

        Message: '$1:$2 -> $3:$4 Local window zero'

        Parameters list:
              $1: tcp51_source_ip_address
              $2: tcp51_destination_ip_address
              $3: tcp51_tcp_src_port
              $4: tcp51_tcp_dst_port

        The local window advertised is zero. The application is not draining
        the TCP receive buffer fast enough."
    ::= { tcpNotificationsPrefix 51 }

tcpNotification52 NOTIFICATION-TYPE
    OBJECTS { 
              tcp52_source_ip_address, 
              tcp52_destination_ip_address,
              tcp52_tcp_src_port,
              tcp52_tcp_dst_port,
              tcp52_seq_num,
              tcp52_ack_num 
            }
    STATUS current
    DESCRIPTION
        "Notification of Event TCP.52

        Message: '$1:$2 -> $3:$4 send FIN sequence number $5, acknowledge number $6'

        Parameters list:
              $1: tcp52_source_ip_address
              $2: tcp52_destination_ip_address
              $3: tcp52_tcp_src_port
              $4: tcp52_tcp_dst_port
              $5: tcp52_seq_num
              $6: tcp52_ack_num

        The TCP connection is closing, and we sent a FIN."
    ::= { tcpNotificationsPrefix 52 }

tcpNotification53 NOTIFICATION-TYPE
    STATUS current
    DESCRIPTION
        "Notification of Event TCP.53

        Message: 'get buf failed - cannot send packet'

        The router is running out of iorbs, getbuf failed, so we cannot
        send a packet."
    ::= { tcpNotificationsPrefix 53 }

tcpNotification54 NOTIFICATION-TYPE
    OBJECTS { 
              tcp54_requested_amount, 
              tcp54_clipped_amount 
            }
    STATUS current
    DESCRIPTION
        "Notification of Event TCP.54

        Message: 'transmit buffer too large for listen/open ($1), clipped to ($2)'

        Parameters list:
              $1: tcp54_requested_amount
              $2: tcp54_clipped_amount

        The transmit buffer size requested for a TCP connection is too large
        to be allocated by the system. TCP has selected in its place
        the largest chunk size available in the system."
    ::= { tcpNotificationsPrefix 54 }

tcpNotification55 NOTIFICATION-TYPE
    OBJECTS { 
              tcp55_requested_amount, 
              tcp55_clipped_amount 
            }
    STATUS current
    DESCRIPTION
        "Notification of Event TCP.55

        Message: 'receive buffer too large for listen/open ($1), clipped to ($2)'

        Parameters list:
              $1: tcp55_requested_amount
              $2: tcp55_clipped_amount

        The receive buffer size requested for a TCP connection is too large
        to be allocated by the system. TCP has selected in its place
        the largest chunk size available in the system."
    ::= { tcpNotificationsPrefix 55 }


END
