-- file automatically created


TELDAT-TRAP-RAD-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


radTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the RAD event subsystem."
    REVISION "201401200930Z"
    DESCRIPTION "Initial implementation"
        ::= { telEventTraps 130 }


radEventsGroup	OBJECT IDENTIFIER	::= { radTrapsMIB 1 }

radNotifications	OBJECT IDENTIFIER	::= { radTrapsMIB 2 }
radNotificationsPrefix	OBJECT IDENTIFIER	::= { radNotifications 0 }

radEventObjects1 OBJECT-IDENTITY
    STATUS current
    DESCRIPTION
        "Event RAD.1
        This message is generated when an ACCESS REQUEST packet is sent to
        RADIUS server, if a new PAP or CHAP authentication arrives."
    ::= { radEventsGroup 1 }

rad1_addr_rad_serv OBJECT-TYPE
    SYNTAX IpAddress
    MAX-ACCESS accessible-for-notify
    STATUS current
    DESCRIPTION
        "Parameter 'addr_rad_serv' in event RAD.1"
    ::= { radEventObjects1 1 }

rad1_id OBJECT-TYPE
    SYNTAX Integer32
    MAX-ACCESS accessible-for-notify
    STATUS current
    DESCRIPTION
        "Parameter 'id' in event RAD.1"
    ::= { radEventObjects1 2 }

rad1_servc OBJECT-TYPE
    SYNTAX DisplayString
    MAX-ACCESS accessible-for-notify
    STATUS current
    DESCRIPTION
        "Parameter 'servc' in event RAD.1"
    ::= { radEventObjects1 3 }

rad1_interface OBJECT-TYPE
    SYNTAX DisplayString
    MAX-ACCESS accessible-for-notify
    STATUS current
    DESCRIPTION
        "Parameter 'interface' in event RAD.1"
    ::= { radEventObjects1 4 }

radEventObjects2 OBJECT-IDENTITY
    STATUS current
    DESCRIPTION
        "Event RAD.2
        This message is generated when an ACCESS ACCEPT packet is received,
        which is sent by the RADIUS server if the RADIUS request
        is authenticated (PAP or CHAP)."
    ::= { radEventsGroup 2 }

rad2_addr_rad_serv OBJECT-TYPE
    SYNTAX IpAddress
    MAX-ACCESS accessible-for-notify
    STATUS current
    DESCRIPTION
        "Parameter 'addr_rad_serv' in event RAD.2"
    ::= { radEventObjects2 1 }

rad2_id OBJECT-TYPE
    SYNTAX Integer32
    MAX-ACCESS accessible-for-notify
    STATUS current
    DESCRIPTION
        "Parameter 'id' in event RAD.2"
    ::= { radEventObjects2 2 }

rad2_servc OBJECT-TYPE
    SYNTAX DisplayString
    MAX-ACCESS accessible-for-notify
    STATUS current
    DESCRIPTION
        "Parameter 'servc' in event RAD.2"
    ::= { radEventObjects2 3 }

rad2_interface OBJECT-TYPE
    SYNTAX DisplayString
    MAX-ACCESS accessible-for-notify
    STATUS current
    DESCRIPTION
        "Parameter 'interface' in event RAD.2"
    ::= { radEventObjects2 4 }

radEventObjects3 OBJECT-IDENTITY
    STATUS current
    DESCRIPTION
        "Event RAD.3
        This message is generated when an ACCESS REJECT packet is received,
        which is sent by the RADIUS server if the RADIUS request is rejected
        (PAP or CHAP)."
    ::= { radEventsGroup 3 }

rad3_addr_rad_serv OBJECT-TYPE
    SYNTAX IpAddress
    MAX-ACCESS accessible-for-notify
    STATUS current
    DESCRIPTION
        "Parameter 'addr_rad_serv' in event RAD.3"
    ::= { radEventObjects3 1 }

rad3_id OBJECT-TYPE
    SYNTAX Integer32
    MAX-ACCESS accessible-for-notify
    STATUS current
    DESCRIPTION
        "Parameter 'id' in event RAD.3"
    ::= { radEventObjects3 2 }

rad3_servc OBJECT-TYPE
    SYNTAX DisplayString
    MAX-ACCESS accessible-for-notify
    STATUS current
    DESCRIPTION
        "Parameter 'servc' in event RAD.3"
    ::= { radEventObjects3 3 }

rad3_interface OBJECT-TYPE
    SYNTAX DisplayString
    MAX-ACCESS accessible-for-notify
    STATUS current
    DESCRIPTION
        "Parameter 'interface' in event RAD.3"
    ::= { radEventObjects3 4 }

radEventObjects4 OBJECT-IDENTITY
    STATUS current
    DESCRIPTION
        "Event RAD.4
        This message is generated when an ACCESS CHALLENGE packet is received,
        which is sent by the RADIUS server to ask for a new
        ACCESS REQUEST packet (PAP or CHAP)."
    ::= { radEventsGroup 4 }

rad4_addr_rad_serv OBJECT-TYPE
    SYNTAX IpAddress
    MAX-ACCESS accessible-for-notify
    STATUS current
    DESCRIPTION
        "Parameter 'addr_rad_serv' in event RAD.4"
    ::= { radEventObjects4 1 }

rad4_id OBJECT-TYPE
    SYNTAX Integer32
    MAX-ACCESS accessible-for-notify
    STATUS current
    DESCRIPTION
        "Parameter 'id' in event RAD.4"
    ::= { radEventObjects4 2 }

rad4_servc OBJECT-TYPE
    SYNTAX DisplayString
    MAX-ACCESS accessible-for-notify
    STATUS current
    DESCRIPTION
        "Parameter 'servc' in event RAD.4"
    ::= { radEventObjects4 3 }

rad4_interface OBJECT-TYPE
    SYNTAX DisplayString
    MAX-ACCESS accessible-for-notify
    STATUS current
    DESCRIPTION
        "Parameter 'interface' in event RAD.4"
    ::= { radEventObjects4 4 }

radEventObjects5 OBJECT-IDENTITY
    STATUS current
    DESCRIPTION
        "Event RAD.5
        This message is generated when an ACCESS REQUEST packet is retransmitted
        by the client if the RADIUS server response is not received
        in the expected time (PAP or CHAP)."
    ::= { radEventsGroup 5 }

rad5_addr_rad_serv OBJECT-TYPE
    SYNTAX IpAddress
    MAX-ACCESS accessible-for-notify
    STATUS current
    DESCRIPTION
        "Parameter 'addr_rad_serv' in event RAD.5"
    ::= { radEventObjects5 1 }

rad5_id OBJECT-TYPE
    SYNTAX Integer32
    MAX-ACCESS accessible-for-notify
    STATUS current
    DESCRIPTION
        "Parameter 'id' in event RAD.5"
    ::= { radEventObjects5 2 }

rad5_servc OBJECT-TYPE
    SYNTAX DisplayString
    MAX-ACCESS accessible-for-notify
    STATUS current
    DESCRIPTION
        "Parameter 'servc' in event RAD.5"
    ::= { radEventObjects5 3 }

rad5_interface OBJECT-TYPE
    SYNTAX DisplayString
    MAX-ACCESS accessible-for-notify
    STATUS current
    DESCRIPTION
        "Parameter 'interface' in event RAD.5"
    ::= { radEventObjects5 4 }

radEventObjects6 OBJECT-IDENTITY
    STATUS current
    DESCRIPTION
        "Event RAD.6
        This message is generated when an authentication request is rejected
        if a RADIUS server response is not received or nets to RADIUS servers
        are down and the number of possible attempts is over (PAP or CHAP)."
    ::= { radEventsGroup 6 }

rad6_servc OBJECT-TYPE
    SYNTAX DisplayString
    MAX-ACCESS accessible-for-notify
    STATUS current
    DESCRIPTION
        "Parameter 'servc' in event RAD.6"
    ::= { radEventObjects6 1 }

rad6_interface OBJECT-TYPE
    SYNTAX DisplayString
    MAX-ACCESS accessible-for-notify
    STATUS current
    DESCRIPTION
        "Parameter 'interface' in event RAD.6"
    ::= { radEventObjects6 2 }

radEventObjects7 OBJECT-IDENTITY
    STATUS current
    DESCRIPTION
        "Event RAD.7
        This message is generated when it is tried to send a packet to
        a RADIUS server and outgoing net is no UP (PAP or CHAP)."
    ::= { radEventsGroup 7 }

rad7_addr_rad_serv OBJECT-TYPE
    SYNTAX IpAddress
    MAX-ACCESS accessible-for-notify
    STATUS current
    DESCRIPTION
        "Parameter 'addr_rad_serv' in event RAD.7"
    ::= { radEventObjects7 1 }

rad7_servc OBJECT-TYPE
    SYNTAX DisplayString
    MAX-ACCESS accessible-for-notify
    STATUS current
    DESCRIPTION
        "Parameter 'servc' in event RAD.7"
    ::= { radEventObjects7 2 }

rad7_interface OBJECT-TYPE
    SYNTAX DisplayString
    MAX-ACCESS accessible-for-notify
    STATUS current
    DESCRIPTION
        "Parameter 'interface' in event RAD.7"
    ::= { radEventObjects7 3 }

radEventObjects8 OBJECT-IDENTITY
    STATUS current
    DESCRIPTION
        "Event RAD.8
        This message is generated when an ACCESS ACCEPT packet is received
        with an attribute with invalid length from the RADIUS Server
        (PAP or CHAP)."
    ::= { radEventsGroup 8 }

rad8_addr_rad_serv OBJECT-TYPE
    SYNTAX IpAddress
    MAX-ACCESS accessible-for-notify
    STATUS current
    DESCRIPTION
        "Parameter 'addr_rad_serv' in event RAD.8"
    ::= { radEventObjects8 1 }

rad8_id OBJECT-TYPE
    SYNTAX Integer32
    MAX-ACCESS accessible-for-notify
    STATUS current
    DESCRIPTION
        "Parameter 'id' in event RAD.8"
    ::= { radEventObjects8 2 }

rad8_typ OBJECT-TYPE
    SYNTAX Integer32
    MAX-ACCESS accessible-for-notify
    STATUS current
    DESCRIPTION
        "Parameter 'typ' in event RAD.8"
    ::= { radEventObjects8 3 }

rad8_servc OBJECT-TYPE
    SYNTAX DisplayString
    MAX-ACCESS accessible-for-notify
    STATUS current
    DESCRIPTION
        "Parameter 'servc' in event RAD.8"
    ::= { radEventObjects8 4 }

rad8_interface OBJECT-TYPE
    SYNTAX DisplayString
    MAX-ACCESS accessible-for-notify
    STATUS current
    DESCRIPTION
        "Parameter 'interface' in event RAD.8"
    ::= { radEventObjects8 5 }

radEventObjects9 OBJECT-IDENTITY
    STATUS current
    DESCRIPTION
        "Event RAD.9
        This message is generated when an ACCESS ACCEPT packet is received
        with an attribute with an invalid content from the RADIUS Server
        (PAP or CHAP)."
    ::= { radEventsGroup 9 }

rad9_addr_rad_serv OBJECT-TYPE
    SYNTAX IpAddress
    MAX-ACCESS accessible-for-notify
    STATUS current
    DESCRIPTION
        "Parameter 'addr_rad_serv' in event RAD.9"
    ::= { radEventObjects9 1 }

rad9_id OBJECT-TYPE
    SYNTAX Integer32
    MAX-ACCESS accessible-for-notify
    STATUS current
    DESCRIPTION
        "Parameter 'id' in event RAD.9"
    ::= { radEventObjects9 2 }

rad9_typ OBJECT-TYPE
    SYNTAX Integer32
    MAX-ACCESS accessible-for-notify
    STATUS current
    DESCRIPTION
        "Parameter 'typ' in event RAD.9"
    ::= { radEventObjects9 3 }

rad9_servc OBJECT-TYPE
    SYNTAX DisplayString
    MAX-ACCESS accessible-for-notify
    STATUS current
    DESCRIPTION
        "Parameter 'servc' in event RAD.9"
    ::= { radEventObjects9 4 }

rad9_interface OBJECT-TYPE
    SYNTAX DisplayString
    MAX-ACCESS accessible-for-notify
    STATUS current
    DESCRIPTION
        "Parameter 'interface' in event RAD.9"
    ::= { radEventObjects9 5 }

radEventObjects10 OBJECT-IDENTITY
    STATUS current
    DESCRIPTION
        "Event RAD.10
        This message is generated when an ACCESS ACCEPT packet is received
        with an excessive number of attributes with the same type from
        the RADIUS Server (PAP or CHAP)."
    ::= { radEventsGroup 10 }

rad10_addr_rad_serv OBJECT-TYPE
    SYNTAX IpAddress
    MAX-ACCESS accessible-for-notify
    STATUS current
    DESCRIPTION
        "Parameter 'addr_rad_serv' in event RAD.10"
    ::= { radEventObjects10 1 }

rad10_id OBJECT-TYPE
    SYNTAX Integer32
    MAX-ACCESS accessible-for-notify
    STATUS current
    DESCRIPTION
        "Parameter 'id' in event RAD.10"
    ::= { radEventObjects10 2 }

rad10_typ OBJECT-TYPE
    SYNTAX Integer32
    MAX-ACCESS accessible-for-notify
    STATUS current
    DESCRIPTION
        "Parameter 'typ' in event RAD.10"
    ::= { radEventObjects10 3 }

rad10_servc OBJECT-TYPE
    SYNTAX DisplayString
    MAX-ACCESS accessible-for-notify
    STATUS current
    DESCRIPTION
        "Parameter 'servc' in event RAD.10"
    ::= { radEventObjects10 4 }

rad10_interface OBJECT-TYPE
    SYNTAX DisplayString
    MAX-ACCESS accessible-for-notify
    STATUS current
    DESCRIPTION
        "Parameter 'interface' in event RAD.10"
    ::= { radEventObjects10 5 }

radEventObjects11 OBJECT-IDENTITY
    STATUS current
    DESCRIPTION
        "Event RAD.11
        This message is generated when an ACCESS ACCEPT packet is received
        with an invalid attribute for the offered service from the RADIUS
        Server (PAP or CHAP)."
    ::= { radEventsGroup 11 }

rad11_addr_rad_serv OBJECT-TYPE
    SYNTAX IpAddress
    MAX-ACCESS accessible-for-notify
    STATUS current
    DESCRIPTION
        "Parameter 'addr_rad_serv' in event RAD.11"
    ::= { radEventObjects11 1 }

rad11_id OBJECT-TYPE
    SYNTAX Integer32
    MAX-ACCESS accessible-for-notify
    STATUS current
    DESCRIPTION
        "Parameter 'id' in event RAD.11"
    ::= { radEventObjects11 2 }

rad11_typ OBJECT-TYPE
    SYNTAX Integer32
    MAX-ACCESS accessible-for-notify
    STATUS current
    DESCRIPTION
        "Parameter 'typ' in event RAD.11"
    ::= { radEventObjects11 3 }

rad11_servc OBJECT-TYPE
    SYNTAX DisplayString
    MAX-ACCESS accessible-for-notify
    STATUS current
    DESCRIPTION
        "Parameter 'servc' in event RAD.11"
    ::= { radEventObjects11 4 }

rad11_interface OBJECT-TYPE
    SYNTAX DisplayString
    MAX-ACCESS accessible-for-notify
    STATUS current
    DESCRIPTION
        "Parameter 'interface' in event RAD.11"
    ::= { radEventObjects11 5 }

radEventObjects12 OBJECT-IDENTITY
    STATUS current
    DESCRIPTION
        "Event RAD.12
        This message is generated when a RADIUS server response is received
        with an invalid length (PAP or CHAP)."
    ::= { radEventsGroup 12 }

rad12_addr_rad_serv OBJECT-TYPE
    SYNTAX IpAddress
    MAX-ACCESS accessible-for-notify
    STATUS current
    DESCRIPTION
        "Parameter 'addr_rad_serv' in event RAD.12"
    ::= { radEventObjects12 1 }

rad12_id OBJECT-TYPE
    SYNTAX Integer32
    MAX-ACCESS accessible-for-notify
    STATUS current
    DESCRIPTION
        "Parameter 'id' in event RAD.12"
    ::= { radEventObjects12 2 }

rad12_servc OBJECT-TYPE
    SYNTAX DisplayString
    MAX-ACCESS accessible-for-notify
    STATUS current
    DESCRIPTION
        "Parameter 'servc' in event RAD.12"
    ::= { radEventObjects12 3 }

rad12_interface OBJECT-TYPE
    SYNTAX DisplayString
    MAX-ACCESS accessible-for-notify
    STATUS current
    DESCRIPTION
        "Parameter 'interface' in event RAD.12"
    ::= { radEventObjects12 4 }

radEventObjects13 OBJECT-IDENTITY
    STATUS current
    DESCRIPTION
        "Event RAD.13
        This message is generated when an ACCESS REQUEST packet is sent to
        RADIUS server, if a new CONSOLE authentication arrives."
    ::= { radEventsGroup 13 }

rad13_addr_rad_serv OBJECT-TYPE
    SYNTAX IpAddress
    MAX-ACCESS accessible-for-notify
    STATUS current
    DESCRIPTION
        "Parameter 'addr_rad_serv' in event RAD.13"
    ::= { radEventObjects13 1 }

rad13_id OBJECT-TYPE
    SYNTAX Integer32
    MAX-ACCESS accessible-for-notify
    STATUS current
    DESCRIPTION
        "Parameter 'id' in event RAD.13"
    ::= { radEventObjects13 2 }

radEventObjects14 OBJECT-IDENTITY
    STATUS current
    DESCRIPTION
        "Event RAD.14
        This message is generated when an ACCESS ACCEPT packet is received,
        which is sent by the RADIUS server if the RADIUS request is
        authenticated (CONSOLE)."
    ::= { radEventsGroup 14 }

rad14_addr_rad_serv OBJECT-TYPE
    SYNTAX IpAddress
    MAX-ACCESS accessible-for-notify
    STATUS current
    DESCRIPTION
        "Parameter 'addr_rad_serv' in event RAD.14"
    ::= { radEventObjects14 1 }

rad14_id OBJECT-TYPE
    SYNTAX Integer32
    MAX-ACCESS accessible-for-notify
    STATUS current
    DESCRIPTION
        "Parameter 'id' in event RAD.14"
    ::= { radEventObjects14 2 }

radEventObjects15 OBJECT-IDENTITY
    STATUS current
    DESCRIPTION
        "Event RAD.15
        This message is generated when an ACCESS REJECT packet is received,
        which is sent by the RADIUS server if the RADIUS request is rejected
        (CONSOLE)."
    ::= { radEventsGroup 15 }

rad15_addr_rad_serv OBJECT-TYPE
    SYNTAX IpAddress
    MAX-ACCESS accessible-for-notify
    STATUS current
    DESCRIPTION
        "Parameter 'addr_rad_serv' in event RAD.15"
    ::= { radEventObjects15 1 }

rad15_id OBJECT-TYPE
    SYNTAX Integer32
    MAX-ACCESS accessible-for-notify
    STATUS current
    DESCRIPTION
        "Parameter 'id' in event RAD.15"
    ::= { radEventObjects15 2 }

radEventObjects16 OBJECT-IDENTITY
    STATUS current
    DESCRIPTION
        "Event RAD.16
        This message is generated when an ACCESS CHALLENGE packet is received,
        which is sent by the RADIUS server to ask for a new ACCESS REQUEST
        packet (CONSOLE)."
    ::= { radEventsGroup 16 }

rad16_addr_rad_serv OBJECT-TYPE
    SYNTAX IpAddress
    MAX-ACCESS accessible-for-notify
    STATUS current
    DESCRIPTION
        "Parameter 'addr_rad_serv' in event RAD.16"
    ::= { radEventObjects16 1 }

rad16_id OBJECT-TYPE
    SYNTAX Integer32
    MAX-ACCESS accessible-for-notify
    STATUS current
    DESCRIPTION
        "Parameter 'id' in event RAD.16"
    ::= { radEventObjects16 2 }

radEventObjects17 OBJECT-IDENTITY
    STATUS current
    DESCRIPTION
        "Event RAD.17
        This message is generated when an ACCESS REQUEST packet is retransmitted
        by the client if the RADIUS server response is not received
        in the expected time (CONSOLE)."
    ::= { radEventsGroup 17 }

rad17_addr_rad_serv OBJECT-TYPE
    SYNTAX IpAddress
    MAX-ACCESS accessible-for-notify
    STATUS current
    DESCRIPTION
        "Parameter 'addr_rad_serv' in event RAD.17"
    ::= { radEventObjects17 1 }

rad17_id OBJECT-TYPE
    SYNTAX Integer32
    MAX-ACCESS accessible-for-notify
    STATUS current
    DESCRIPTION
        "Parameter 'id' in event RAD.17"
    ::= { radEventObjects17 2 }

radEventObjects19 OBJECT-IDENTITY
    STATUS current
    DESCRIPTION
        "Event RAD.19
        This message is generated when it is tried to send a packet to a
        RADIUS server and outgoing net is not UP (CONSOLE)."
    ::= { radEventsGroup 19 }

rad19_addr_rad_serv OBJECT-TYPE
    SYNTAX IpAddress
    MAX-ACCESS accessible-for-notify
    STATUS current
    DESCRIPTION
        "Parameter 'addr_rad_serv' in event RAD.19"
    ::= { radEventObjects19 1 }

radEventObjects20 OBJECT-IDENTITY
    STATUS current
    DESCRIPTION
        "Event RAD.20
        This message is generated when an ACCESS ACCEPT packet is received
        with an attribute with invalid length from the RADIUS Server (CONSOLE)."
    ::= { radEventsGroup 20 }

rad20_addr_rad_serv OBJECT-TYPE
    SYNTAX IpAddress
    MAX-ACCESS accessible-for-notify
    STATUS current
    DESCRIPTION
        "Parameter 'addr_rad_serv' in event RAD.20"
    ::= { radEventObjects20 1 }

rad20_id OBJECT-TYPE
    SYNTAX Integer32
    MAX-ACCESS accessible-for-notify
    STATUS current
    DESCRIPTION
        "Parameter 'id' in event RAD.20"
    ::= { radEventObjects20 2 }

rad20_typ OBJECT-TYPE
    SYNTAX Integer32
    MAX-ACCESS accessible-for-notify
    STATUS current
    DESCRIPTION
        "Parameter 'typ' in event RAD.20"
    ::= { radEventObjects20 3 }

radEventObjects21 OBJECT-IDENTITY
    STATUS current
    DESCRIPTION
        "Event RAD.21
        This message is generated when an ACCESS ACCEPT packet is received
        with an attribute with an invalid content from the RADIUS Server
        (CONSOLE)."
    ::= { radEventsGroup 21 }

rad21_addr_rad_serv OBJECT-TYPE
    SYNTAX IpAddress
    MAX-ACCESS accessible-for-notify
    STATUS current
    DESCRIPTION
        "Parameter 'addr_rad_serv' in event RAD.21"
    ::= { radEventObjects21 1 }

rad21_id OBJECT-TYPE
    SYNTAX Integer32
    MAX-ACCESS accessible-for-notify
    STATUS current
    DESCRIPTION
        "Parameter 'id' in event RAD.21"
    ::= { radEventObjects21 2 }

rad21_typ OBJECT-TYPE
    SYNTAX Integer32
    MAX-ACCESS accessible-for-notify
    STATUS current
    DESCRIPTION
        "Parameter 'typ' in event RAD.21"
    ::= { radEventObjects21 3 }

radEventObjects22 OBJECT-IDENTITY
    STATUS current
    DESCRIPTION
        "Event RAD.22
        This message is generated when an ACCESS ACCEPT packet is received
        with a excessive number of attributes with the same type
        from the RADIUS Server (CONSOLE)."
    ::= { radEventsGroup 22 }

rad22_addr_rad_serv OBJECT-TYPE
    SYNTAX IpAddress
    MAX-ACCESS accessible-for-notify
    STATUS current
    DESCRIPTION
        "Parameter 'addr_rad_serv' in event RAD.22"
    ::= { radEventObjects22 1 }

rad22_id OBJECT-TYPE
    SYNTAX Integer32
    MAX-ACCESS accessible-for-notify
    STATUS current
    DESCRIPTION
        "Parameter 'id' in event RAD.22"
    ::= { radEventObjects22 2 }

rad22_typ OBJECT-TYPE
    SYNTAX Integer32
    MAX-ACCESS accessible-for-notify
    STATUS current
    DESCRIPTION
        "Parameter 'typ' in event RAD.22"
    ::= { radEventObjects22 3 }

radEventObjects23 OBJECT-IDENTITY
    STATUS current
    DESCRIPTION
        "Event RAD.23
        This message is generated when an ACCESS ACCEPT packet is received
        with an invalid attribute for the offered service from the RADIUS
        Server (CONSOLE)."
    ::= { radEventsGroup 23 }

rad23_addr_rad_serv OBJECT-TYPE
    SYNTAX IpAddress
    MAX-ACCESS accessible-for-notify
    STATUS current
    DESCRIPTION
        "Parameter 'addr_rad_serv' in event RAD.23"
    ::= { radEventObjects23 1 }

rad23_id OBJECT-TYPE
    SYNTAX Integer32
    MAX-ACCESS accessible-for-notify
    STATUS current
    DESCRIPTION
        "Parameter 'id' in event RAD.23"
    ::= { radEventObjects23 2 }

rad23_typ OBJECT-TYPE
    SYNTAX Integer32
    MAX-ACCESS accessible-for-notify
    STATUS current
    DESCRIPTION
        "Parameter 'typ' in event RAD.23"
    ::= { radEventObjects23 3 }

radEventObjects24 OBJECT-IDENTITY
    STATUS current
    DESCRIPTION
        "Event RAD.24
        This message is generated when a RADIUS server response is received
        with an invalid length (CONSOLE)."
    ::= { radEventsGroup 24 }

rad24_addr_rad_serv OBJECT-TYPE
    SYNTAX IpAddress
    MAX-ACCESS accessible-for-notify
    STATUS current
    DESCRIPTION
        "Parameter 'addr_rad_serv' in event RAD.24"
    ::= { radEventObjects24 1 }

rad24_id OBJECT-TYPE
    SYNTAX Integer32
    MAX-ACCESS accessible-for-notify
    STATUS current
    DESCRIPTION
        "Parameter 'id' in event RAD.24"
    ::= { radEventObjects24 2 }

radEventObjects25 OBJECT-IDENTITY
    STATUS current
    DESCRIPTION
        "Event RAD.25
        This message is generated when an ACCESS REQUEST packet is sent to the
        RADIUS server, if a new TELNET or FTP authentication arrives."
    ::= { radEventsGroup 25 }

rad25_addr_rad_serv OBJECT-TYPE
    SYNTAX IpAddress
    MAX-ACCESS accessible-for-notify
    STATUS current
    DESCRIPTION
        "Parameter 'addr_rad_serv' in event RAD.25"
    ::= { radEventObjects25 1 }

rad25_id OBJECT-TYPE
    SYNTAX Integer32
    MAX-ACCESS accessible-for-notify
    STATUS current
    DESCRIPTION
        "Parameter 'id' in event RAD.25"
    ::= { radEventObjects25 2 }

rad25_servc OBJECT-TYPE
    SYNTAX DisplayString
    MAX-ACCESS accessible-for-notify
    STATUS current
    DESCRIPTION
        "Parameter 'servc' in event RAD.25"
    ::= { radEventObjects25 3 }

rad25_lcl_addr OBJECT-TYPE
    SYNTAX IpAddress
    MAX-ACCESS accessible-for-notify
    STATUS current
    DESCRIPTION
        "Parameter 'lcl_addr' in event RAD.25"
    ::= { radEventObjects25 4 }

rad25_lcl_prt OBJECT-TYPE
    SYNTAX Integer32
    MAX-ACCESS accessible-for-notify
    STATUS current
    DESCRIPTION
        "Parameter 'lcl_prt' in event RAD.25"
    ::= { radEventObjects25 5 }

rad25_rmt_addr OBJECT-TYPE
    SYNTAX IpAddress
    MAX-ACCESS accessible-for-notify
    STATUS current
    DESCRIPTION
        "Parameter 'rmt_addr' in event RAD.25"
    ::= { radEventObjects25 6 }

rad25_rmt_prt OBJECT-TYPE
    SYNTAX Integer32
    MAX-ACCESS accessible-for-notify
    STATUS current
    DESCRIPTION
        "Parameter 'rmt_prt' in event RAD.25"
    ::= { radEventObjects25 7 }

radEventObjects26 OBJECT-IDENTITY
    STATUS current
    DESCRIPTION
        "Event RAD.26
        This message is generated when an ACCESS ACCEPT packet is received,
        which is sent by the RADIUS server if the RADIUS request is
        authenticated (TELNET or FTP)."
    ::= { radEventsGroup 26 }

rad26_addr_rad_serv OBJECT-TYPE
    SYNTAX IpAddress
    MAX-ACCESS accessible-for-notify
    STATUS current
    DESCRIPTION
        "Parameter 'addr_rad_serv' in event RAD.26"
    ::= { radEventObjects26 1 }

rad26_id OBJECT-TYPE
    SYNTAX Integer32
    MAX-ACCESS accessible-for-notify
    STATUS current
    DESCRIPTION
        "Parameter 'id' in event RAD.26"
    ::= { radEventObjects26 2 }

rad26_servc OBJECT-TYPE
    SYNTAX DisplayString
    MAX-ACCESS accessible-for-notify
    STATUS current
    DESCRIPTION
        "Parameter 'servc' in event RAD.26"
    ::= { radEventObjects26 3 }

rad26_lcl_addr OBJECT-TYPE
    SYNTAX IpAddress
    MAX-ACCESS accessible-for-notify
    STATUS current
    DESCRIPTION
        "Parameter 'lcl_addr' in event RAD.26"
    ::= { radEventObjects26 4 }

rad26_lcl_prt OBJECT-TYPE
    SYNTAX Integer32
    MAX-ACCESS accessible-for-notify
    STATUS current
    DESCRIPTION
        "Parameter 'lcl_prt' in event RAD.26"
    ::= { radEventObjects26 5 }

rad26_rmt_addr OBJECT-TYPE
    SYNTAX IpAddress
    MAX-ACCESS accessible-for-notify
    STATUS current
    DESCRIPTION
        "Parameter 'rmt_addr' in event RAD.26"
    ::= { radEventObjects26 6 }

rad26_rmt_prt OBJECT-TYPE
    SYNTAX Integer32
    MAX-ACCESS accessible-for-notify
    STATUS current
    DESCRIPTION
        "Parameter 'rmt_prt' in event RAD.26"
    ::= { radEventObjects26 7 }

radEventObjects27 OBJECT-IDENTITY
    STATUS current
    DESCRIPTION
        "Event RAD.27
        This message is generated when an ACCESS REJECT packet is received,
        which is sent by the RADIUS server if the RADIUS request is rejected
        (TELNET or FTP)."
    ::= { radEventsGroup 27 }

rad27_addr_rad_serv OBJECT-TYPE
    SYNTAX IpAddress
    MAX-ACCESS accessible-for-notify
    STATUS current
    DESCRIPTION
        "Parameter 'addr_rad_serv' in event RAD.27"
    ::= { radEventObjects27 1 }

rad27_id OBJECT-TYPE
    SYNTAX Integer32
    MAX-ACCESS accessible-for-notify
    STATUS current
    DESCRIPTION
        "Parameter 'id' in event RAD.27"
    ::= { radEventObjects27 2 }

rad27_servc OBJECT-TYPE
    SYNTAX DisplayString
    MAX-ACCESS accessible-for-notify
    STATUS current
    DESCRIPTION
        "Parameter 'servc' in event RAD.27"
    ::= { radEventObjects27 3 }

rad27_lcl_addr OBJECT-TYPE
    SYNTAX IpAddress
    MAX-ACCESS accessible-for-notify
    STATUS current
    DESCRIPTION
        "Parameter 'lcl_addr' in event RAD.27"
    ::= { radEventObjects27 4 }

rad27_lcl_prt OBJECT-TYPE
    SYNTAX Integer32
    MAX-ACCESS accessible-for-notify
    STATUS current
    DESCRIPTION
        "Parameter 'lcl_prt' in event RAD.27"
    ::= { radEventObjects27 5 }

rad27_rmt_addr OBJECT-TYPE
    SYNTAX IpAddress
    MAX-ACCESS accessible-for-notify
    STATUS current
    DESCRIPTION
        "Parameter 'rmt_addr' in event RAD.27"
    ::= { radEventObjects27 6 }

rad27_rmt_prt OBJECT-TYPE
    SYNTAX Integer32
    MAX-ACCESS accessible-for-notify
    STATUS current
    DESCRIPTION
        "Parameter 'rmt_prt' in event RAD.27"
    ::= { radEventObjects27 7 }

radEventObjects28 OBJECT-IDENTITY
    STATUS current
    DESCRIPTION
        "Event RAD.28
        This message is generated when an ACCESS CHALLENGE packet is received,
        which is sent by the RADIUS server to ask for a new ACCESS REQUEST
        packet (TELNET or FTP)."
    ::= { radEventsGroup 28 }

rad28_addr_rad_serv OBJECT-TYPE
    SYNTAX IpAddress
    MAX-ACCESS accessible-for-notify
    STATUS current
    DESCRIPTION
        "Parameter 'addr_rad_serv' in event RAD.28"
    ::= { radEventObjects28 1 }

rad28_id OBJECT-TYPE
    SYNTAX Integer32
    MAX-ACCESS accessible-for-notify
    STATUS current
    DESCRIPTION
        "Parameter 'id' in event RAD.28"
    ::= { radEventObjects28 2 }

rad28_servc OBJECT-TYPE
    SYNTAX DisplayString
    MAX-ACCESS accessible-for-notify
    STATUS current
    DESCRIPTION
        "Parameter 'servc' in event RAD.28"
    ::= { radEventObjects28 3 }

rad28_lcl_addr OBJECT-TYPE
    SYNTAX IpAddress
    MAX-ACCESS accessible-for-notify
    STATUS current
    DESCRIPTION
        "Parameter 'lcl_addr' in event RAD.28"
    ::= { radEventObjects28 4 }

rad28_lcl_prt OBJECT-TYPE
    SYNTAX Integer32
    MAX-ACCESS accessible-for-notify
    STATUS current
    DESCRIPTION
        "Parameter 'lcl_prt' in event RAD.28"
    ::= { radEventObjects28 5 }

rad28_rmt_addr OBJECT-TYPE
    SYNTAX IpAddress
    MAX-ACCESS accessible-for-notify
    STATUS current
    DESCRIPTION
        "Parameter 'rmt_addr' in event RAD.28"
    ::= { radEventObjects28 6 }

rad28_rmt_prt OBJECT-TYPE
    SYNTAX Integer32
    MAX-ACCESS accessible-for-notify
    STATUS current
    DESCRIPTION
        "Parameter 'rmt_prt' in event RAD.28"
    ::= { radEventObjects28 7 }

radEventObjects29 OBJECT-IDENTITY
    STATUS current
    DESCRIPTION
        "Event RAD.29
        This message is generated when an ACCESS REQUEST packet is retransmitted
        by the client if the RADIUS server response is not received
        in the expected time (TELNET or FTP)."
    ::= { radEventsGroup 29 }

rad29_addr_rad_serv OBJECT-TYPE
    SYNTAX IpAddress
    MAX-ACCESS accessible-for-notify
    STATUS current
    DESCRIPTION
        "Parameter 'addr_rad_serv' in event RAD.29"
    ::= { radEventObjects29 1 }

rad29_id OBJECT-TYPE
    SYNTAX Integer32
    MAX-ACCESS accessible-for-notify
    STATUS current
    DESCRIPTION
        "Parameter 'id' in event RAD.29"
    ::= { radEventObjects29 2 }

rad29_servc OBJECT-TYPE
    SYNTAX DisplayString
    MAX-ACCESS accessible-for-notify
    STATUS current
    DESCRIPTION
        "Parameter 'servc' in event RAD.29"
    ::= { radEventObjects29 3 }

rad29_lcl_addr OBJECT-TYPE
    SYNTAX IpAddress
    MAX-ACCESS accessible-for-notify
    STATUS current
    DESCRIPTION
        "Parameter 'lcl_addr' in event RAD.29"
    ::= { radEventObjects29 4 }

rad29_lcl_prt OBJECT-TYPE
    SYNTAX Integer32
    MAX-ACCESS accessible-for-notify
    STATUS current
    DESCRIPTION
        "Parameter 'lcl_prt' in event RAD.29"
    ::= { radEventObjects29 5 }

rad29_rmt_addr OBJECT-TYPE
    SYNTAX IpAddress
    MAX-ACCESS accessible-for-notify
    STATUS current
    DESCRIPTION
        "Parameter 'rmt_addr' in event RAD.29"
    ::= { radEventObjects29 6 }

rad29_rmt_prt OBJECT-TYPE
    SYNTAX Integer32
    MAX-ACCESS accessible-for-notify
    STATUS current
    DESCRIPTION
        "Parameter 'rmt_prt' in event RAD.29"
    ::= { radEventObjects29 7 }

radEventObjects30 OBJECT-IDENTITY
    STATUS current
    DESCRIPTION
        "Event RAD.30
        This message is generated when an authentication request is rejected
        if a RADIUS server response is not received or nets to RADIUS servers
        are down and the number of possible attempts is over (TELNET or FTP)."
    ::= { radEventsGroup 30 }

rad30_servc OBJECT-TYPE
    SYNTAX DisplayString
    MAX-ACCESS accessible-for-notify
    STATUS current
    DESCRIPTION
        "Parameter 'servc' in event RAD.30"
    ::= { radEventObjects30 1 }

rad30_lcl_addr OBJECT-TYPE
    SYNTAX IpAddress
    MAX-ACCESS accessible-for-notify
    STATUS current
    DESCRIPTION
        "Parameter 'lcl_addr' in event RAD.30"
    ::= { radEventObjects30 2 }

rad30_lcl_prt OBJECT-TYPE
    SYNTAX Integer32
    MAX-ACCESS accessible-for-notify
    STATUS current
    DESCRIPTION
        "Parameter 'lcl_prt' in event RAD.30"
    ::= { radEventObjects30 3 }

rad30_rmt_addr OBJECT-TYPE
    SYNTAX IpAddress
    MAX-ACCESS accessible-for-notify
    STATUS current
    DESCRIPTION
        "Parameter 'rmt_addr' in event RAD.30"
    ::= { radEventObjects30 4 }

rad30_rmt_prt OBJECT-TYPE
    SYNTAX Integer32
    MAX-ACCESS accessible-for-notify
    STATUS current
    DESCRIPTION
        "Parameter 'rmt_prt' in event RAD.30"
    ::= { radEventObjects30 5 }

radEventObjects31 OBJECT-IDENTITY
    STATUS current
    DESCRIPTION
        "Event RAD.31
        This message is generated when it is tried to send a packet to
        a RADIUS server and outgoing net is not UP (TELNET or FTP)."
    ::= { radEventsGroup 31 }

rad31_addr_rad_serv OBJECT-TYPE
    SYNTAX IpAddress
    MAX-ACCESS accessible-for-notify
    STATUS current
    DESCRIPTION
        "Parameter 'addr_rad_serv' in event RAD.31"
    ::= { radEventObjects31 1 }

rad31_servc OBJECT-TYPE
    SYNTAX DisplayString
    MAX-ACCESS accessible-for-notify
    STATUS current
    DESCRIPTION
        "Parameter 'servc' in event RAD.31"
    ::= { radEventObjects31 2 }

rad31_lcl_addr OBJECT-TYPE
    SYNTAX IpAddress
    MAX-ACCESS accessible-for-notify
    STATUS current
    DESCRIPTION
        "Parameter 'lcl_addr' in event RAD.31"
    ::= { radEventObjects31 3 }

rad31_lcl_prt OBJECT-TYPE
    SYNTAX Integer32
    MAX-ACCESS accessible-for-notify
    STATUS current
    DESCRIPTION
        "Parameter 'lcl_prt' in event RAD.31"
    ::= { radEventObjects31 4 }

rad31_rmt_addr OBJECT-TYPE
    SYNTAX IpAddress
    MAX-ACCESS accessible-for-notify
    STATUS current
    DESCRIPTION
        "Parameter 'rmt_addr' in event RAD.31"
    ::= { radEventObjects31 5 }

rad31_rmt_prt OBJECT-TYPE
    SYNTAX Integer32
    MAX-ACCESS accessible-for-notify
    STATUS current
    DESCRIPTION
        "Parameter 'rmt_prt' in event RAD.31"
    ::= { radEventObjects31 6 }

radEventObjects32 OBJECT-IDENTITY
    STATUS current
    DESCRIPTION
        "Event RAD.32
        This message is generated when an ACCESS ACCEPT packet is received
        with an attribute with invalid length from the RADIUS Server
        (TELNET or FTP)."
    ::= { radEventsGroup 32 }

rad32_addr_rad_serv OBJECT-TYPE
    SYNTAX IpAddress
    MAX-ACCESS accessible-for-notify
    STATUS current
    DESCRIPTION
        "Parameter 'addr_rad_serv' in event RAD.32"
    ::= { radEventObjects32 1 }

rad32_id OBJECT-TYPE
    SYNTAX Integer32
    MAX-ACCESS accessible-for-notify
    STATUS current
    DESCRIPTION
        "Parameter 'id' in event RAD.32"
    ::= { radEventObjects32 2 }

rad32_typ OBJECT-TYPE
    SYNTAX Integer32
    MAX-ACCESS accessible-for-notify
    STATUS current
    DESCRIPTION
        "Parameter 'typ' in event RAD.32"
    ::= { radEventObjects32 3 }

rad32_servc OBJECT-TYPE
    SYNTAX DisplayString
    MAX-ACCESS accessible-for-notify
    STATUS current
    DESCRIPTION
        "Parameter 'servc' in event RAD.32"
    ::= { radEventObjects32 4 }

rad32_lcl_addr OBJECT-TYPE
    SYNTAX IpAddress
    MAX-ACCESS accessible-for-notify
    STATUS current
    DESCRIPTION
        "Parameter 'lcl_addr' in event RAD.32"
    ::= { radEventObjects32 5 }

rad32_lcl_prt OBJECT-TYPE
    SYNTAX Integer32
    MAX-ACCESS accessible-for-notify
    STATUS current
    DESCRIPTION
        "Parameter 'lcl_prt' in event RAD.32"
    ::= { radEventObjects32 6 }

rad32_rmt_addr OBJECT-TYPE
    SYNTAX IpAddress
    MAX-ACCESS accessible-for-notify
    STATUS current
    DESCRIPTION
        "Parameter 'rmt_addr' in event RAD.32"
    ::= { radEventObjects32 7 }

rad32_rmt_prt OBJECT-TYPE
    SYNTAX Integer32
    MAX-ACCESS accessible-for-notify
    STATUS current
    DESCRIPTION
        "Parameter 'rmt_prt' in event RAD.32"
    ::= { radEventObjects32 8 }

radEventObjects33 OBJECT-IDENTITY
    STATUS current
    DESCRIPTION
        "Event RAD.33
        This message is generated when an ACCESS ACCEPT packet is received
        with an attribute with an invalid content from the RADIUS Server
        (TELNET or FTP)."
    ::= { radEventsGroup 33 }

rad33_addr_rad_serv OBJECT-TYPE
    SYNTAX IpAddress
    MAX-ACCESS accessible-for-notify
    STATUS current
    DESCRIPTION
        "Parameter 'addr_rad_serv' in event RAD.33"
    ::= { radEventObjects33 1 }

rad33_id OBJECT-TYPE
    SYNTAX Integer32
    MAX-ACCESS accessible-for-notify
    STATUS current
    DESCRIPTION
        "Parameter 'id' in event RAD.33"
    ::= { radEventObjects33 2 }

rad33_typ OBJECT-TYPE
    SYNTAX Integer32
    MAX-ACCESS accessible-for-notify
    STATUS current
    DESCRIPTION
        "Parameter 'typ' in event RAD.33"
    ::= { radEventObjects33 3 }

rad33_servc OBJECT-TYPE
    SYNTAX DisplayString
    MAX-ACCESS accessible-for-notify
    STATUS current
    DESCRIPTION
        "Parameter 'servc' in event RAD.33"
    ::= { radEventObjects33 4 }

rad33_lcl_addr OBJECT-TYPE
    SYNTAX IpAddress
    MAX-ACCESS accessible-for-notify
    STATUS current
    DESCRIPTION
        "Parameter 'lcl_addr' in event RAD.33"
    ::= { radEventObjects33 5 }

rad33_lcl_prt OBJECT-TYPE
    SYNTAX Integer32
    MAX-ACCESS accessible-for-notify
    STATUS current
    DESCRIPTION
        "Parameter 'lcl_prt' in event RAD.33"
    ::= { radEventObjects33 6 }

rad33_rmt_addr OBJECT-TYPE
    SYNTAX IpAddress
    MAX-ACCESS accessible-for-notify
    STATUS current
    DESCRIPTION
        "Parameter 'rmt_addr' in event RAD.33"
    ::= { radEventObjects33 7 }

rad33_rmt_prt OBJECT-TYPE
    SYNTAX Integer32
    MAX-ACCESS accessible-for-notify
    STATUS current
    DESCRIPTION
        "Parameter 'rmt_prt' in event RAD.33"
    ::= { radEventObjects33 8 }

radEventObjects34 OBJECT-IDENTITY
    STATUS current
    DESCRIPTION
        "Event RAD.34
        This message is generated when an ACCESS ACCEPT packet is received
        with an excessive number of attributes with the same type from
        the RADIUS Server (TELNET or FTP)."
    ::= { radEventsGroup 34 }

rad34_addr_rad_serv OBJECT-TYPE
    SYNTAX IpAddress
    MAX-ACCESS accessible-for-notify
    STATUS current
    DESCRIPTION
        "Parameter 'addr_rad_serv' in event RAD.34"
    ::= { radEventObjects34 1 }

rad34_id OBJECT-TYPE
    SYNTAX Integer32
    MAX-ACCESS accessible-for-notify
    STATUS current
    DESCRIPTION
        "Parameter 'id' in event RAD.34"
    ::= { radEventObjects34 2 }

rad34_typ OBJECT-TYPE
    SYNTAX Integer32
    MAX-ACCESS accessible-for-notify
    STATUS current
    DESCRIPTION
        "Parameter 'typ' in event RAD.34"
    ::= { radEventObjects34 3 }

rad34_servc OBJECT-TYPE
    SYNTAX DisplayString
    MAX-ACCESS accessible-for-notify
    STATUS current
    DESCRIPTION
        "Parameter 'servc' in event RAD.34"
    ::= { radEventObjects34 4 }

rad34_lcl_addr OBJECT-TYPE
    SYNTAX IpAddress
    MAX-ACCESS accessible-for-notify
    STATUS current
    DESCRIPTION
        "Parameter 'lcl_addr' in event RAD.34"
    ::= { radEventObjects34 5 }

rad34_lcl_prt OBJECT-TYPE
    SYNTAX Integer32
    MAX-ACCESS accessible-for-notify
    STATUS current
    DESCRIPTION
        "Parameter 'lcl_prt' in event RAD.34"
    ::= { radEventObjects34 6 }

rad34_rmt_addr OBJECT-TYPE
    SYNTAX IpAddress
    MAX-ACCESS accessible-for-notify
    STATUS current
    DESCRIPTION
        "Parameter 'rmt_addr' in event RAD.34"
    ::= { radEventObjects34 7 }

rad34_rmt_prt OBJECT-TYPE
    SYNTAX Integer32
    MAX-ACCESS accessible-for-notify
    STATUS current
    DESCRIPTION
        "Parameter 'rmt_prt' in event RAD.34"
    ::= { radEventObjects34 8 }

radEventObjects35 OBJECT-IDENTITY
    STATUS current
    DESCRIPTION
        "Event RAD.35
        This message is generated when an ACCESS ACCEPT packet is received
        with an invalid attribute for the offered service from the RADIUS
        Server (TELNET or FTP)."
    ::= { radEventsGroup 35 }

rad35_addr_rad_serv OBJECT-TYPE
    SYNTAX IpAddress
    MAX-ACCESS accessible-for-notify
    STATUS current
    DESCRIPTION
        "Parameter 'addr_rad_serv' in event RAD.35"
    ::= { radEventObjects35 1 }

rad35_id OBJECT-TYPE
    SYNTAX Integer32
    MAX-ACCESS accessible-for-notify
    STATUS current
    DESCRIPTION
        "Parameter 'id' in event RAD.35"
    ::= { radEventObjects35 2 }

rad35_typ OBJECT-TYPE
    SYNTAX Integer32
    MAX-ACCESS accessible-for-notify
    STATUS current
    DESCRIPTION
        "Parameter 'typ' in event RAD.35"
    ::= { radEventObjects35 3 }

rad35_servc OBJECT-TYPE
    SYNTAX DisplayString
    MAX-ACCESS accessible-for-notify
    STATUS current
    DESCRIPTION
        "Parameter 'servc' in event RAD.35"
    ::= { radEventObjects35 4 }

rad35_lcl_addr OBJECT-TYPE
    SYNTAX IpAddress
    MAX-ACCESS accessible-for-notify
    STATUS current
    DESCRIPTION
        "Parameter 'lcl_addr' in event RAD.35"
    ::= { radEventObjects35 5 }

rad35_lcl_prt OBJECT-TYPE
    SYNTAX Integer32
    MAX-ACCESS accessible-for-notify
    STATUS current
    DESCRIPTION
        "Parameter 'lcl_prt' in event RAD.35"
    ::= { radEventObjects35 6 }

rad35_rmt_addr OBJECT-TYPE
    SYNTAX IpAddress
    MAX-ACCESS accessible-for-notify
    STATUS current
    DESCRIPTION
        "Parameter 'rmt_addr' in event RAD.35"
    ::= { radEventObjects35 7 }

rad35_rmt_prt OBJECT-TYPE
    SYNTAX Integer32
    MAX-ACCESS accessible-for-notify
    STATUS current
    DESCRIPTION
        "Parameter 'rmt_prt' in event RAD.35"
    ::= { radEventObjects35 8 }

radEventObjects36 OBJECT-IDENTITY
    STATUS current
    DESCRIPTION
        "Event RAD.36
        This message is generated when a RADIUS server response is received
        with an invalid length (TELNET or FTP)."
    ::= { radEventsGroup 36 }

rad36_addr_rad_serv OBJECT-TYPE
    SYNTAX IpAddress
    MAX-ACCESS accessible-for-notify
    STATUS current
    DESCRIPTION
        "Parameter 'addr_rad_serv' in event RAD.36"
    ::= { radEventObjects36 1 }

rad36_id OBJECT-TYPE
    SYNTAX Integer32
    MAX-ACCESS accessible-for-notify
    STATUS current
    DESCRIPTION
        "Parameter 'id' in event RAD.36"
    ::= { radEventObjects36 2 }

rad36_servc OBJECT-TYPE
    SYNTAX DisplayString
    MAX-ACCESS accessible-for-notify
    STATUS current
    DESCRIPTION
        "Parameter 'servc' in event RAD.36"
    ::= { radEventObjects36 3 }

rad36_lcl_addr OBJECT-TYPE
    SYNTAX IpAddress
    MAX-ACCESS accessible-for-notify
    STATUS current
    DESCRIPTION
        "Parameter 'lcl_addr' in event RAD.36"
    ::= { radEventObjects36 4 }

rad36_lcl_prt OBJECT-TYPE
    SYNTAX Integer32
    MAX-ACCESS accessible-for-notify
    STATUS current
    DESCRIPTION
        "Parameter 'lcl_prt' in event RAD.36"
    ::= { radEventObjects36 5 }

rad36_rmt_addr OBJECT-TYPE
    SYNTAX IpAddress
    MAX-ACCESS accessible-for-notify
    STATUS current
    DESCRIPTION
        "Parameter 'rmt_addr' in event RAD.36"
    ::= { radEventObjects36 6 }

rad36_rmt_prt OBJECT-TYPE
    SYNTAX Integer32
    MAX-ACCESS accessible-for-notify
    STATUS current
    DESCRIPTION
        "Parameter 'rmt_prt' in event RAD.36"
    ::= { radEventObjects36 7 }

radEventObjects37 OBJECT-IDENTITY
    STATUS current
    DESCRIPTION
        "Event RAD.37
        This message is generated when a RADIUS server response is received and
        there is not any pending request corresponding to that packet or rhe
        packet contains errors."
    ::= { radEventsGroup 37 }

rad37_addr_rad_serv OBJECT-TYPE
    SYNTAX IpAddress
    MAX-ACCESS accessible-for-notify
    STATUS current
    DESCRIPTION
        "Parameter 'addr_rad_serv' in event RAD.37"
    ::= { radEventObjects37 1 }

rad37_id OBJECT-TYPE
    SYNTAX Integer32
    MAX-ACCESS accessible-for-notify
    STATUS current
    DESCRIPTION
        "Parameter 'id' in event RAD.37"
    ::= { radEventObjects37 2 }

radEventObjects38 OBJECT-IDENTITY
    STATUS current
    DESCRIPTION
        "Event RAD.38
        This message is generated when a response is received from an unknown
        RADIUS server."
    ::= { radEventsGroup 38 }

rad38_addr_rad_serv OBJECT-TYPE
    SYNTAX IpAddress
    MAX-ACCESS accessible-for-notify
    STATUS current
    DESCRIPTION
        "Parameter 'addr_rad_serv' in event RAD.38"
    ::= { radEventObjects38 1 }

rad38_id OBJECT-TYPE
    SYNTAX Integer32
    MAX-ACCESS accessible-for-notify
    STATUS current
    DESCRIPTION
        "Parameter 'id' in event RAD.38"
    ::= { radEventObjects38 2 }

rad38_src_prt OBJECT-TYPE
    SYNTAX Integer32
    MAX-ACCESS accessible-for-notify
    STATUS current
    DESCRIPTION
        "Parameter 'src_prt' in event RAD.38"
    ::= { radEventObjects38 3 }

rad38_dst_prt OBJECT-TYPE
    SYNTAX Integer32
    MAX-ACCESS accessible-for-notify
    STATUS current
    DESCRIPTION
        "Parameter 'dst_prt' in event RAD.38"
    ::= { radEventObjects38 4 }

radEventObjects39 OBJECT-IDENTITY
    STATUS current
    DESCRIPTION
        "Event RAD.39
        This message is generated when a RADIUS packet is received
        with an unknown type."
    ::= { radEventsGroup 39 }

rad39_addr_rad_serv OBJECT-TYPE
    SYNTAX IpAddress
    MAX-ACCESS accessible-for-notify
    STATUS current
    DESCRIPTION
        "Parameter 'addr_rad_serv' in event RAD.39"
    ::= { radEventObjects39 1 }

rad39_id OBJECT-TYPE
    SYNTAX Integer32
    MAX-ACCESS accessible-for-notify
    STATUS current
    DESCRIPTION
        "Parameter 'id' in event RAD.39"
    ::= { radEventObjects39 2 }

rad39_typ OBJECT-TYPE
    SYNTAX Integer32
    MAX-ACCESS accessible-for-notify
    STATUS current
    DESCRIPTION
        "Parameter 'typ' in event RAD.39"
    ::= { radEventObjects39 3 }

radEventObjects40 OBJECT-IDENTITY
    STATUS current
    DESCRIPTION
        "Event RAD.40
        This message is generated when a RADIUS server response is received
        with an invalid length."
    ::= { radEventsGroup 40 }

rad40_addr_rad_serv OBJECT-TYPE
    SYNTAX IpAddress
    MAX-ACCESS accessible-for-notify
    STATUS current
    DESCRIPTION
        "Parameter 'addr_rad_serv' in event RAD.40"
    ::= { radEventObjects40 1 }

rad40_id OBJECT-TYPE
    SYNTAX Integer32
    MAX-ACCESS accessible-for-notify
    STATUS current
    DESCRIPTION
        "Parameter 'id' in event RAD.40"
    ::= { radEventObjects40 2 }

radEventObjects41 OBJECT-IDENTITY
    STATUS current
    DESCRIPTION
        "Event RAD.41
        Generic internal error event."
    ::= { radEventsGroup 41 }

rad41_error_string OBJECT-TYPE
    SYNTAX DisplayString
    MAX-ACCESS accessible-for-notify
    STATUS current
    DESCRIPTION
        "Parameter 'error_string' in event RAD.41"
    ::= { radEventObjects41 1 }

radEventObjects42 OBJECT-IDENTITY
    STATUS current
    DESCRIPTION
        "Event RAD.42
        Attribute sent in a Radius request."
    ::= { radEventsGroup 42 }

rad42_name OBJECT-TYPE
    SYNTAX DisplayString
    MAX-ACCESS accessible-for-notify
    STATUS current
    DESCRIPTION
        "Parameter 'name' in event RAD.42"
    ::= { radEventObjects42 1 }

rad42_length OBJECT-TYPE
    SYNTAX Integer32
    MAX-ACCESS accessible-for-notify
    STATUS current
    DESCRIPTION
        "Parameter 'length' in event RAD.42"
    ::= { radEventObjects42 2 }

rad42_value OBJECT-TYPE
    SYNTAX DisplayString
    MAX-ACCESS accessible-for-notify
    STATUS current
    DESCRIPTION
        "Parameter 'value' in event RAD.42"
    ::= { radEventObjects42 3 }

radEventObjects43 OBJECT-IDENTITY
    STATUS current
    DESCRIPTION
        "Event RAD.43
        Attribute received in a Radius response."
    ::= { radEventsGroup 43 }

rad43_name OBJECT-TYPE
    SYNTAX DisplayString
    MAX-ACCESS accessible-for-notify
    STATUS current
    DESCRIPTION
        "Parameter 'name' in event RAD.43"
    ::= { radEventObjects43 1 }

rad43_length OBJECT-TYPE
    SYNTAX Integer32
    MAX-ACCESS accessible-for-notify
    STATUS current
    DESCRIPTION
        "Parameter 'length' in event RAD.43"
    ::= { radEventObjects43 2 }

rad43_value OBJECT-TYPE
    SYNTAX DisplayString
    MAX-ACCESS accessible-for-notify
    STATUS current
    DESCRIPTION
        "Parameter 'value' in event RAD.43"
    ::= { radEventObjects43 3 }

radEventObjects44 OBJECT-IDENTITY
    STATUS current
    DESCRIPTION
        "Event RAD.44
        This message is generated when a packet is sent to a RADIUS server."
    ::= { radEventsGroup 44 }

rad44_packet_type OBJECT-TYPE
    SYNTAX DisplayString
    MAX-ACCESS accessible-for-notify
    STATUS current
    DESCRIPTION
        "Parameter 'packet_type' in event RAD.44"
    ::= { radEventObjects44 1 }

rad44_length OBJECT-TYPE
    SYNTAX Integer32
    MAX-ACCESS accessible-for-notify
    STATUS current
    DESCRIPTION
        "Parameter 'length' in event RAD.44"
    ::= { radEventObjects44 2 }

rad44_server_address OBJECT-TYPE
    SYNTAX IpAddress
    MAX-ACCESS accessible-for-notify
    STATUS current
    DESCRIPTION
        "Parameter 'server_address' in event RAD.44"
    ::= { radEventObjects44 3 }

rad44_server_port OBJECT-TYPE
    SYNTAX Integer32
    MAX-ACCESS accessible-for-notify
    STATUS current
    DESCRIPTION
        "Parameter 'server_port' in event RAD.44"
    ::= { radEventObjects44 4 }

rad44_identifier OBJECT-TYPE
    SYNTAX Integer32
    MAX-ACCESS accessible-for-notify
    STATUS current
    DESCRIPTION
        "Parameter 'identifier' in event RAD.44"
    ::= { radEventObjects44 5 }

rad44_service OBJECT-TYPE
    SYNTAX DisplayString
    MAX-ACCESS accessible-for-notify
    STATUS current
    DESCRIPTION
        "Parameter 'service' in event RAD.44"
    ::= { radEventObjects44 6 }

radEventObjects45 OBJECT-IDENTITY
    STATUS current
    DESCRIPTION
        "Event RAD.45
        This message is generated when a packet is sent to a RADIUS server."
    ::= { radEventsGroup 45 }

rad45_packet_type OBJECT-TYPE
    SYNTAX DisplayString
    MAX-ACCESS accessible-for-notify
    STATUS current
    DESCRIPTION
        "Parameter 'packet_type' in event RAD.45"
    ::= { radEventObjects45 1 }

rad45_length OBJECT-TYPE
    SYNTAX Integer32
    MAX-ACCESS accessible-for-notify
    STATUS current
    DESCRIPTION
        "Parameter 'length' in event RAD.45"
    ::= { radEventObjects45 2 }

rad45_server_address OBJECT-TYPE
    SYNTAX IpAddress
    MAX-ACCESS accessible-for-notify
    STATUS current
    DESCRIPTION
        "Parameter 'server_address' in event RAD.45"
    ::= { radEventObjects45 3 }

rad45_server_port OBJECT-TYPE
    SYNTAX Integer32
    MAX-ACCESS accessible-for-notify
    STATUS current
    DESCRIPTION
        "Parameter 'server_port' in event RAD.45"
    ::= { radEventObjects45 4 }

rad45_identifier OBJECT-TYPE
    SYNTAX Integer32
    MAX-ACCESS accessible-for-notify
    STATUS current
    DESCRIPTION
        "Parameter 'identifier' in event RAD.45"
    ::= { radEventObjects45 5 }

rad45_service OBJECT-TYPE
    SYNTAX DisplayString
    MAX-ACCESS accessible-for-notify
    STATUS current
    DESCRIPTION
        "Parameter 'service' in event RAD.45"
    ::= { radEventObjects45 6 }

radEventObjects46 OBJECT-IDENTITY
    STATUS current
    DESCRIPTION
        "Event RAD.46
        This message is generated when a packet is retransmitted to a RADIUS server."
    ::= { radEventsGroup 46 }

rad46_packet_type OBJECT-TYPE
    SYNTAX DisplayString
    MAX-ACCESS accessible-for-notify
    STATUS current
    DESCRIPTION
        "Parameter 'packet_type' in event RAD.46"
    ::= { radEventObjects46 1 }

rad46_length OBJECT-TYPE
    SYNTAX Integer32
    MAX-ACCESS accessible-for-notify
    STATUS current
    DESCRIPTION
        "Parameter 'length' in event RAD.46"
    ::= { radEventObjects46 2 }

rad46_server_address OBJECT-TYPE
    SYNTAX IpAddress
    MAX-ACCESS accessible-for-notify
    STATUS current
    DESCRIPTION
        "Parameter 'server_address' in event RAD.46"
    ::= { radEventObjects46 3 }

rad46_server_port OBJECT-TYPE
    SYNTAX Integer32
    MAX-ACCESS accessible-for-notify
    STATUS current
    DESCRIPTION
        "Parameter 'server_port' in event RAD.46"
    ::= { radEventObjects46 4 }

rad46_identifier OBJECT-TYPE
    SYNTAX Integer32
    MAX-ACCESS accessible-for-notify
    STATUS current
    DESCRIPTION
        "Parameter 'identifier' in event RAD.46"
    ::= { radEventObjects46 5 }

rad46_service OBJECT-TYPE
    SYNTAX DisplayString
    MAX-ACCESS accessible-for-notify
    STATUS current
    DESCRIPTION
        "Parameter 'service' in event RAD.46"
    ::= { radEventObjects46 6 }

radEventObjects47 OBJECT-IDENTITY
    STATUS current
    DESCRIPTION
        "Event RAD.47
        Generic comment on usual information message."
    ::= { radEventsGroup 47 }

rad47_info_string OBJECT-TYPE
    SYNTAX DisplayString
    MAX-ACCESS accessible-for-notify
    STATUS current
    DESCRIPTION
        "Parameter 'info_string' in event RAD.47"
    ::= { radEventObjects47 1 }

radEventObjects48 OBJECT-IDENTITY
    STATUS current
    DESCRIPTION
        "Event RAD.48
        This message is generated when an authentication request is rejected
        if a RADIUS server response is not received or nets to RADIUS servers
        are down and the number of possible attempts is over."
    ::= { radEventsGroup 48 }

rad48_service OBJECT-TYPE
    SYNTAX DisplayString
    MAX-ACCESS accessible-for-notify
    STATUS current
    DESCRIPTION
        "Parameter 'service' in event RAD.48"
    ::= { radEventObjects48 1 }

radEventObjects49 OBJECT-IDENTITY
    STATUS current
    DESCRIPTION
        "Event RAD.49
        This message is generated when it is tried to send a packet to a
        RADIUS server and outgoing net is not UP."
    ::= { radEventsGroup 49 }

rad49_addr_rad_serv OBJECT-TYPE
    SYNTAX IpAddress
    MAX-ACCESS accessible-for-notify
    STATUS current
    DESCRIPTION
        "Parameter 'addr_rad_serv' in event RAD.49"
    ::= { radEventObjects49 1 }

rad49_service OBJECT-TYPE
    SYNTAX DisplayString
    MAX-ACCESS accessible-for-notify
    STATUS current
    DESCRIPTION
        "Parameter 'service' in event RAD.49"
    ::= { radEventObjects49 2 }

radEventObjects50 OBJECT-IDENTITY
    STATUS current
    DESCRIPTION
        "Event RAD.50
        This message is generated when an ACCESS REQUEST packet is sent to
        RADIUS server, if a new authentication arrives."
    ::= { radEventsGroup 50 }

rad50_addr_rad_serv OBJECT-TYPE
    SYNTAX IpAddress
    MAX-ACCESS accessible-for-notify
    STATUS current
    DESCRIPTION
        "Parameter 'addr_rad_serv' in event RAD.50"
    ::= { radEventObjects50 1 }

rad50_id OBJECT-TYPE
    SYNTAX Integer32
    MAX-ACCESS accessible-for-notify
    STATUS current
    DESCRIPTION
        "Parameter 'id' in event RAD.50"
    ::= { radEventObjects50 2 }

rad50_service OBJECT-TYPE
    SYNTAX DisplayString
    MAX-ACCESS accessible-for-notify
    STATUS current
    DESCRIPTION
        "Parameter 'service' in event RAD.50"
    ::= { radEventObjects50 3 }

radEventObjects51 OBJECT-IDENTITY
    STATUS current
    DESCRIPTION
        "Event RAD.51
        This message is generated when an ACCESS REQUEST packet is retransmitted
        by the client if the RADIUS server response is not received
        in the expected time."
    ::= { radEventsGroup 51 }

rad51_addr_rad_serv OBJECT-TYPE
    SYNTAX IpAddress
    MAX-ACCESS accessible-for-notify
    STATUS current
    DESCRIPTION
        "Parameter 'addr_rad_serv' in event RAD.51"
    ::= { radEventObjects51 1 }

rad51_id OBJECT-TYPE
    SYNTAX Integer32
    MAX-ACCESS accessible-for-notify
    STATUS current
    DESCRIPTION
        "Parameter 'id' in event RAD.51"
    ::= { radEventObjects51 2 }

rad51_service OBJECT-TYPE
    SYNTAX DisplayString
    MAX-ACCESS accessible-for-notify
    STATUS current
    DESCRIPTION
        "Parameter 'service' in event RAD.51"
    ::= { radEventObjects51 3 }

radEventObjects52 OBJECT-IDENTITY
    STATUS current
    DESCRIPTION
        "Event RAD.52
        This message is generated when an ACCESS ACCEPT packet is received,
        which is sent by the RADIUS server if the RADIUS request is
        authenticated."
    ::= { radEventsGroup 52 }

rad52_addr_rad_serv OBJECT-TYPE
    SYNTAX IpAddress
    MAX-ACCESS accessible-for-notify
    STATUS current
    DESCRIPTION
        "Parameter 'addr_rad_serv' in event RAD.52"
    ::= { radEventObjects52 1 }

rad52_id OBJECT-TYPE
    SYNTAX Integer32
    MAX-ACCESS accessible-for-notify
    STATUS current
    DESCRIPTION
        "Parameter 'id' in event RAD.52"
    ::= { radEventObjects52 2 }

rad52_service OBJECT-TYPE
    SYNTAX DisplayString
    MAX-ACCESS accessible-for-notify
    STATUS current
    DESCRIPTION
        "Parameter 'service' in event RAD.52"
    ::= { radEventObjects52 3 }

radEventObjects53 OBJECT-IDENTITY
    STATUS current
    DESCRIPTION
        "Event RAD.53
        This message is generated when an ACCESS REJECT packet is received,
        which is sent by the RADIUS server if the RADIUS request is rejected."
    ::= { radEventsGroup 53 }

rad53_addr_rad_serv OBJECT-TYPE
    SYNTAX IpAddress
    MAX-ACCESS accessible-for-notify
    STATUS current
    DESCRIPTION
        "Parameter 'addr_rad_serv' in event RAD.53"
    ::= { radEventObjects53 1 }

rad53_id OBJECT-TYPE
    SYNTAX Integer32
    MAX-ACCESS accessible-for-notify
    STATUS current
    DESCRIPTION
        "Parameter 'id' in event RAD.53"
    ::= { radEventObjects53 2 }

rad53_service OBJECT-TYPE
    SYNTAX DisplayString
    MAX-ACCESS accessible-for-notify
    STATUS current
    DESCRIPTION
        "Parameter 'service' in event RAD.53"
    ::= { radEventObjects53 3 }

radEventObjects54 OBJECT-IDENTITY
    STATUS current
    DESCRIPTION
        "Event RAD.54
        This message is generated when an ACCESS CHALLENGE packet is received,
        which is sent by the RADIUS server to ask for a new ACCESS REQUEST
        packet."
    ::= { radEventsGroup 54 }

rad54_addr_rad_serv OBJECT-TYPE
    SYNTAX IpAddress
    MAX-ACCESS accessible-for-notify
    STATUS current
    DESCRIPTION
        "Parameter 'addr_rad_serv' in event RAD.54"
    ::= { radEventObjects54 1 }

rad54_id OBJECT-TYPE
    SYNTAX Integer32
    MAX-ACCESS accessible-for-notify
    STATUS current
    DESCRIPTION
        "Parameter 'id' in event RAD.54"
    ::= { radEventObjects54 2 }

rad54_service OBJECT-TYPE
    SYNTAX DisplayString
    MAX-ACCESS accessible-for-notify
    STATUS current
    DESCRIPTION
        "Parameter 'service' in event RAD.54"
    ::= { radEventObjects54 3 }

radEventObjects55 OBJECT-IDENTITY
    STATUS current
    DESCRIPTION
        "Event RAD.55
        This message is generated when an ACCESS ACCEPT packet is received
        with an attribute with invalid length from the RADIUS Server."
    ::= { radEventsGroup 55 }

rad55_addr_rad_serv OBJECT-TYPE
    SYNTAX IpAddress
    MAX-ACCESS accessible-for-notify
    STATUS current
    DESCRIPTION
        "Parameter 'addr_rad_serv' in event RAD.55"
    ::= { radEventObjects55 1 }

rad55_id OBJECT-TYPE
    SYNTAX Integer32
    MAX-ACCESS accessible-for-notify
    STATUS current
    DESCRIPTION
        "Parameter 'id' in event RAD.55"
    ::= { radEventObjects55 2 }

rad55_typ OBJECT-TYPE
    SYNTAX Integer32
    MAX-ACCESS accessible-for-notify
    STATUS current
    DESCRIPTION
        "Parameter 'typ' in event RAD.55"
    ::= { radEventObjects55 3 }

rad55_service OBJECT-TYPE
    SYNTAX DisplayString
    MAX-ACCESS accessible-for-notify
    STATUS current
    DESCRIPTION
        "Parameter 'service' in event RAD.55"
    ::= { radEventObjects55 4 }

radEventObjects56 OBJECT-IDENTITY
    STATUS current
    DESCRIPTION
        "Event RAD.56
        This message is generated when an ACCESS ACCEPT packet is received
        with an attribute with an invalid content from the RADIUS Server."
    ::= { radEventsGroup 56 }

rad56_addr_rad_serv OBJECT-TYPE
    SYNTAX IpAddress
    MAX-ACCESS accessible-for-notify
    STATUS current
    DESCRIPTION
        "Parameter 'addr_rad_serv' in event RAD.56"
    ::= { radEventObjects56 1 }

rad56_id OBJECT-TYPE
    SYNTAX Integer32
    MAX-ACCESS accessible-for-notify
    STATUS current
    DESCRIPTION
        "Parameter 'id' in event RAD.56"
    ::= { radEventObjects56 2 }

rad56_typ OBJECT-TYPE
    SYNTAX Integer32
    MAX-ACCESS accessible-for-notify
    STATUS current
    DESCRIPTION
        "Parameter 'typ' in event RAD.56"
    ::= { radEventObjects56 3 }

rad56_service OBJECT-TYPE
    SYNTAX DisplayString
    MAX-ACCESS accessible-for-notify
    STATUS current
    DESCRIPTION
        "Parameter 'service' in event RAD.56"
    ::= { radEventObjects56 4 }

radEventObjects57 OBJECT-IDENTITY
    STATUS current
    DESCRIPTION
        "Event RAD.57
        This message is generated when an ACCESS ACCEPT packet is received
        with a excessive number of attributes with the same type
        from the RADIUS Server."
    ::= { radEventsGroup 57 }

rad57_addr_rad_serv OBJECT-TYPE
    SYNTAX IpAddress
    MAX-ACCESS accessible-for-notify
    STATUS current
    DESCRIPTION
        "Parameter 'addr_rad_serv' in event RAD.57"
    ::= { radEventObjects57 1 }

rad57_id OBJECT-TYPE
    SYNTAX Integer32
    MAX-ACCESS accessible-for-notify
    STATUS current
    DESCRIPTION
        "Parameter 'id' in event RAD.57"
    ::= { radEventObjects57 2 }

rad57_typ OBJECT-TYPE
    SYNTAX Integer32
    MAX-ACCESS accessible-for-notify
    STATUS current
    DESCRIPTION
        "Parameter 'typ' in event RAD.57"
    ::= { radEventObjects57 3 }

rad57_service OBJECT-TYPE
    SYNTAX DisplayString
    MAX-ACCESS accessible-for-notify
    STATUS current
    DESCRIPTION
        "Parameter 'service' in event RAD.57"
    ::= { radEventObjects57 4 }

radEventObjects58 OBJECT-IDENTITY
    STATUS current
    DESCRIPTION
        "Event RAD.58
        This message is generated when an ACCESS ACCEPT packet is received
        with an invalid attribute for the offered service from the RADIUS
        Server."
    ::= { radEventsGroup 58 }

rad58_addr_rad_serv OBJECT-TYPE
    SYNTAX IpAddress
    MAX-ACCESS accessible-for-notify
    STATUS current
    DESCRIPTION
        "Parameter 'addr_rad_serv' in event RAD.58"
    ::= { radEventObjects58 1 }

rad58_id OBJECT-TYPE
    SYNTAX Integer32
    MAX-ACCESS accessible-for-notify
    STATUS current
    DESCRIPTION
        "Parameter 'id' in event RAD.58"
    ::= { radEventObjects58 2 }

rad58_typ OBJECT-TYPE
    SYNTAX Integer32
    MAX-ACCESS accessible-for-notify
    STATUS current
    DESCRIPTION
        "Parameter 'typ' in event RAD.58"
    ::= { radEventObjects58 3 }

rad58_service OBJECT-TYPE
    SYNTAX DisplayString
    MAX-ACCESS accessible-for-notify
    STATUS current
    DESCRIPTION
        "Parameter 'service' in event RAD.58"
    ::= { radEventObjects58 4 }

radEventObjects59 OBJECT-IDENTITY
    STATUS current
    DESCRIPTION
        "Event RAD.59
        This message is generated when a RADIUS server response is received
        with an invalid length."
    ::= { radEventsGroup 59 }

rad59_addr_rad_serv OBJECT-TYPE
    SYNTAX IpAddress
    MAX-ACCESS accessible-for-notify
    STATUS current
    DESCRIPTION
        "Parameter 'addr_rad_serv' in event RAD.59"
    ::= { radEventObjects59 1 }

rad59_id OBJECT-TYPE
    SYNTAX Integer32
    MAX-ACCESS accessible-for-notify
    STATUS current
    DESCRIPTION
        "Parameter 'id' in event RAD.59"
    ::= { radEventObjects59 2 }

rad59_service OBJECT-TYPE
    SYNTAX DisplayString
    MAX-ACCESS accessible-for-notify
    STATUS current
    DESCRIPTION
        "Parameter 'service' in event RAD.59"
    ::= { radEventObjects59 3 }


radNotification1 NOTIFICATION-TYPE
    OBJECTS { 
              rad1_addr_rad_serv, 
              rad1_id,
              rad1_servc,
              rad1_interface 
            }
    STATUS current
    DESCRIPTION
        "Notification of Event RAD.1

        Message: 'send an ACCESS REQUEST packet to RADIUS server $1, identifier $2, for service $3 on interface $4'

        Parameters list:
              $1: rad1_addr_rad_serv
              $2: rad1_id
              $3: rad1_servc
              $4: rad1_interface

        This message is generated when an ACCESS REQUEST packet is sent to
        RADIUS server, if a new PAP or CHAP authentication arrives."
    ::= { radNotificationsPrefix 1 }

radNotification2 NOTIFICATION-TYPE
    OBJECTS { 
              rad2_addr_rad_serv, 
              rad2_id,
              rad2_servc,
              rad2_interface 
            }
    STATUS current
    DESCRIPTION
        "Notification of Event RAD.2

        Message: 'receive an ACCESS ACCEPT packet from RADIUS server $1, identifier $2, for service $3 on interface $4'

        Parameters list:
              $1: rad2_addr_rad_serv
              $2: rad2_id
              $3: rad2_servc
              $4: rad2_interface

        This message is generated when an ACCESS ACCEPT packet is received,
        which is sent by the RADIUS server if the RADIUS request
        is authenticated (PAP or CHAP)."
    ::= { radNotificationsPrefix 2 }

radNotification3 NOTIFICATION-TYPE
    OBJECTS { 
              rad3_addr_rad_serv, 
              rad3_id,
              rad3_servc,
              rad3_interface 
            }
    STATUS current
    DESCRIPTION
        "Notification of Event RAD.3

        Message: 'receive an ACCESS REJECT packet from RADIUS server $1, identifier $2, for service $3 on interface $4'

        Parameters list:
              $1: rad3_addr_rad_serv
              $2: rad3_id
              $3: rad3_servc
              $4: rad3_interface

        This message is generated when an ACCESS REJECT packet is received,
        which is sent by the RADIUS server if the RADIUS request is rejected
        (PAP or CHAP)."
    ::= { radNotificationsPrefix 3 }

radNotification4 NOTIFICATION-TYPE
    OBJECTS { 
              rad4_addr_rad_serv, 
              rad4_id,
              rad4_servc,
              rad4_interface 
            }
    STATUS current
    DESCRIPTION
        "Notification of Event RAD.4

        Message: 'receive an ACCESS CHALLENGE packet from RADIUS server $1, identifier $2, for service $3 on interface $4'

        Parameters list:
              $1: rad4_addr_rad_serv
              $2: rad4_id
              $3: rad4_servc
              $4: rad4_interface

        This message is generated when an ACCESS CHALLENGE packet is received,
        which is sent by the RADIUS server to ask for a new
        ACCESS REQUEST packet (PAP or CHAP)."
    ::= { radNotificationsPrefix 4 }

radNotification5 NOTIFICATION-TYPE
    OBJECTS { 
              rad5_addr_rad_serv, 
              rad5_id,
              rad5_servc,
              rad5_interface 
            }
    STATUS current
    DESCRIPTION
        "Notification of Event RAD.5

        Message: 'retransmit ACCESS REQUEST packet to RADIUS server $1, identifier $2, for service $3 on interface $4'

        Parameters list:
              $1: rad5_addr_rad_serv
              $2: rad5_id
              $3: rad5_servc
              $4: rad5_interface

        This message is generated when an ACCESS REQUEST packet is retransmitted
        by the client if the RADIUS server response is not received
        in the expected time (PAP or CHAP)."
    ::= { radNotificationsPrefix 5 }

radNotification6 NOTIFICATION-TYPE
    OBJECTS { 
              rad6_servc, 
              rad6_interface 
            }
    STATUS current
    DESCRIPTION
        "Notification of Event RAD.6

        Message: 'fail authentication due to no communication with RADIUS servers, for service $1 on interface $2'

        Parameters list:
              $1: rad6_servc
              $2: rad6_interface

        This message is generated when an authentication request is rejected
        if a RADIUS server response is not received or nets to RADIUS servers
        are down and the number of possible attempts is over (PAP or CHAP)."
    ::= { radNotificationsPrefix 6 }

radNotification7 NOTIFICATION-TYPE
    OBJECTS { 
              rad7_addr_rad_serv, 
              rad7_servc,
              rad7_interface 
            }
    STATUS current
    DESCRIPTION
        "Notification of Event RAD.7

        Message: 'net to servidor RADIUS $1 is not UP, for service $2 on interface $3'

        Parameters list:
              $1: rad7_addr_rad_serv
              $2: rad7_servc
              $3: rad7_interface

        This message is generated when it is tried to send a packet to
        a RADIUS server and outgoing net is no UP (PAP or CHAP)."
    ::= { radNotificationsPrefix 7 }

radNotification8 NOTIFICATION-TYPE
    OBJECTS { 
              rad8_addr_rad_serv, 
              rad8_id,
              rad8_typ,
              rad8_servc,
              rad8_interface 
            }
    STATUS current
    DESCRIPTION
        "Notification of Event RAD.8

        Message: 'receive an ACCESS ACCEPT packet from RADIUS server $1, identifier $2, with attribute type $3 with invalid length, for service $4 on interface $5'

        Parameters list:
              $1: rad8_addr_rad_serv
              $2: rad8_id
              $3: rad8_typ
              $4: rad8_servc
              $5: rad8_interface

        This message is generated when an ACCESS ACCEPT packet is received
        with an attribute with invalid length from the RADIUS Server
        (PAP or CHAP)."
    ::= { radNotificationsPrefix 8 }

radNotification9 NOTIFICATION-TYPE
    OBJECTS { 
              rad9_addr_rad_serv, 
              rad9_id,
              rad9_typ,
              rad9_servc,
              rad9_interface 
            }
    STATUS current
    DESCRIPTION
        "Notification of Event RAD.9

        Message: 'receive an ACCESS ACCEPT packet from RADIUS server $1, identifier $2, with attribute type $3 with invalid content, for service $4 on interface $5'

        Parameters list:
              $1: rad9_addr_rad_serv
              $2: rad9_id
              $3: rad9_typ
              $4: rad9_servc
              $5: rad9_interface

        This message is generated when an ACCESS ACCEPT packet is received
        with an attribute with an invalid content from the RADIUS Server
        (PAP or CHAP)."
    ::= { radNotificationsPrefix 9 }

radNotification10 NOTIFICATION-TYPE
    OBJECTS { 
              rad10_addr_rad_serv, 
              rad10_id,
              rad10_typ,
              rad10_servc,
              rad10_interface 
            }
    STATUS current
    DESCRIPTION
        "Notification of Event RAD.10

        Message: 'receive an ACCESS ACCEPT packet from RADIUS server $1, identifier $2, with extra attribute type $3, for service $4 on interface $5'

        Parameters list:
              $1: rad10_addr_rad_serv
              $2: rad10_id
              $3: rad10_typ
              $4: rad10_servc
              $5: rad10_interface

        This message is generated when an ACCESS ACCEPT packet is received
        with an excessive number of attributes with the same type from
        the RADIUS Server (PAP or CHAP)."
    ::= { radNotificationsPrefix 10 }

radNotification11 NOTIFICATION-TYPE
    OBJECTS { 
              rad11_addr_rad_serv, 
              rad11_id,
              rad11_typ,
              rad11_servc,
              rad11_interface 
            }
    STATUS current
    DESCRIPTION
        "Notification of Event RAD.11

        Message: 'receive an ACCESS ACCEPT packet from RADIUS server $1, identifier $2, with invalid attribute type $3, for service $4 on interface $5'

        Parameters list:
              $1: rad11_addr_rad_serv
              $2: rad11_id
              $3: rad11_typ
              $4: rad11_servc
              $5: rad11_interface

        This message is generated when an ACCESS ACCEPT packet is received
        with an invalid attribute for the offered service from the RADIUS
        Server (PAP or CHAP)."
    ::= { radNotificationsPrefix 11 }

radNotification12 NOTIFICATION-TYPE
    OBJECTS { 
              rad12_addr_rad_serv, 
              rad12_id,
              rad12_servc,
              rad12_interface 
            }
    STATUS current
    DESCRIPTION
        "Notification of Event RAD.12

        Message: 'receive an ACCESS RESPONSE packet from RADIUS server $1, identifier $2, with invalid length, for service $3 on interface $4'

        Parameters list:
              $1: rad12_addr_rad_serv
              $2: rad12_id
              $3: rad12_servc
              $4: rad12_interface

        This message is generated when a RADIUS server response is received
        with an invalid length (PAP or CHAP)."
    ::= { radNotificationsPrefix 12 }

radNotification13 NOTIFICATION-TYPE
    OBJECTS { 
              rad13_addr_rad_serv, 
              rad13_id 
            }
    STATUS current
    DESCRIPTION
        "Notification of Event RAD.13

        Message: 'send an ACCESS REQUEST packet to RADIUS server $1, identifier $2, for service CONSOLE'

        Parameters list:
              $1: rad13_addr_rad_serv
              $2: rad13_id

        This message is generated when an ACCESS REQUEST packet is sent to
        RADIUS server, if a new CONSOLE authentication arrives."
    ::= { radNotificationsPrefix 13 }

radNotification14 NOTIFICATION-TYPE
    OBJECTS { 
              rad14_addr_rad_serv, 
              rad14_id 
            }
    STATUS current
    DESCRIPTION
        "Notification of Event RAD.14

        Message: 'receive an ACCESS ACCEPT packet from RADIUS server $1, identifier $2, for service CONSOLE'

        Parameters list:
              $1: rad14_addr_rad_serv
              $2: rad14_id

        This message is generated when an ACCESS ACCEPT packet is received,
        which is sent by the RADIUS server if the RADIUS request is
        authenticated (CONSOLE)."
    ::= { radNotificationsPrefix 14 }

radNotification15 NOTIFICATION-TYPE
    OBJECTS { 
              rad15_addr_rad_serv, 
              rad15_id 
            }
    STATUS current
    DESCRIPTION
        "Notification of Event RAD.15

        Message: 'receive an ACCESS REJECT packet from RADIUS server $1, identifier $2, for service CONSOLE'

        Parameters list:
              $1: rad15_addr_rad_serv
              $2: rad15_id

        This message is generated when an ACCESS REJECT packet is received,
        which is sent by the RADIUS server if the RADIUS request is rejected
        (CONSOLE)."
    ::= { radNotificationsPrefix 15 }

radNotification16 NOTIFICATION-TYPE
    OBJECTS { 
              rad16_addr_rad_serv, 
              rad16_id 
            }
    STATUS current
    DESCRIPTION
        "Notification of Event RAD.16

        Message: 'receive an ACCESS CHALLENGE packet from RADIUS server $1, identifier $2, for service CONSOLE'

        Parameters list:
              $1: rad16_addr_rad_serv
              $2: rad16_id

        This message is generated when an ACCESS CHALLENGE packet is received,
        which is sent by the RADIUS server to ask for a new ACCESS REQUEST
        packet (CONSOLE)."
    ::= { radNotificationsPrefix 16 }

radNotification17 NOTIFICATION-TYPE
    OBJECTS { 
              rad17_addr_rad_serv, 
              rad17_id 
            }
    STATUS current
    DESCRIPTION
        "Notification of Event RAD.17

        Message: 'retransmit ACCESS REQUEST packet to RADIUS server $1, identifier $2, for service CONSOLE'

        Parameters list:
              $1: rad17_addr_rad_serv
              $2: rad17_id

        This message is generated when an ACCESS REQUEST packet is retransmitted
        by the client if the RADIUS server response is not received
        in the expected time (CONSOLE)."
    ::= { radNotificationsPrefix 17 }

radNotification18 NOTIFICATION-TYPE
    STATUS current
    DESCRIPTION
        "Notification of Event RAD.18

        Message: 'fail authentication due to no communication with RADIUS servers, for service CONSOLE'

        This message is generated when an authentication request is rejected
        if a RADIUS server response is not received or nets to RADIUS servers
        are down and the number of possible attempts is over (CONSOLE)."
    ::= { radNotificationsPrefix 18 }

radNotification19 NOTIFICATION-TYPE
    OBJECTS { 
              rad19_addr_rad_serv 
            }
    STATUS current
    DESCRIPTION
        "Notification of Event RAD.19

        Message: 'net to servidor RADIUS $1 is not UP, for service CONSOLE'

        Parameters list:
              $1: rad19_addr_rad_serv

        This message is generated when it is tried to send a packet to a
        RADIUS server and outgoing net is not UP (CONSOLE)."
    ::= { radNotificationsPrefix 19 }

radNotification20 NOTIFICATION-TYPE
    OBJECTS { 
              rad20_addr_rad_serv, 
              rad20_id,
              rad20_typ 
            }
    STATUS current
    DESCRIPTION
        "Notification of Event RAD.20

        Message: 'receive an ACCESS ACCEPT packet from RADIUS server $1, identifier $2, with attribute type $3 with invalid length, for service CONSOLE'

        Parameters list:
              $1: rad20_addr_rad_serv
              $2: rad20_id
              $3: rad20_typ

        This message is generated when an ACCESS ACCEPT packet is received
        with an attribute with invalid length from the RADIUS Server (CONSOLE)."
    ::= { radNotificationsPrefix 20 }

radNotification21 NOTIFICATION-TYPE
    OBJECTS { 
              rad21_addr_rad_serv, 
              rad21_id,
              rad21_typ 
            }
    STATUS current
    DESCRIPTION
        "Notification of Event RAD.21

        Message: 'receive an ACCESS ACCEPT packet from RADIUS server $1, identifier $2, with attribute type $3 with invalid content, for service CONSOLE'

        Parameters list:
              $1: rad21_addr_rad_serv
              $2: rad21_id
              $3: rad21_typ

        This message is generated when an ACCESS ACCEPT packet is received
        with an attribute with an invalid content from the RADIUS Server
        (CONSOLE)."
    ::= { radNotificationsPrefix 21 }

radNotification22 NOTIFICATION-TYPE
    OBJECTS { 
              rad22_addr_rad_serv, 
              rad22_id,
              rad22_typ 
            }
    STATUS current
    DESCRIPTION
        "Notification of Event RAD.22

        Message: 'receive an ACCESS ACCEPT packet from RADIUS server $1, identifier $2, with extra attribute type $3, for service CONSOLE'

        Parameters list:
              $1: rad22_addr_rad_serv
              $2: rad22_id
              $3: rad22_typ

        This message is generated when an ACCESS ACCEPT packet is received
        with a excessive number of attributes with the same type
        from the RADIUS Server (CONSOLE)."
    ::= { radNotificationsPrefix 22 }

radNotification23 NOTIFICATION-TYPE
    OBJECTS { 
              rad23_addr_rad_serv, 
              rad23_id,
              rad23_typ 
            }
    STATUS current
    DESCRIPTION
        "Notification of Event RAD.23

        Message: 'receive an ACCESS ACCEPT packet from RADIUS server $1, identifier $2, with invalid attribute type $3, for service CONSOLE'

        Parameters list:
              $1: rad23_addr_rad_serv
              $2: rad23_id
              $3: rad23_typ

        This message is generated when an ACCESS ACCEPT packet is received
        with an invalid attribute for the offered service from the RADIUS
        Server (CONSOLE)."
    ::= { radNotificationsPrefix 23 }

radNotification24 NOTIFICATION-TYPE
    OBJECTS { 
              rad24_addr_rad_serv, 
              rad24_id 
            }
    STATUS current
    DESCRIPTION
        "Notification of Event RAD.24

        Message: 'receive an ACCESS RESPONSE packet from RADIUS server $1, identifier $2, with invalid length, for service CONSOLE'

        Parameters list:
              $1: rad24_addr_rad_serv
              $2: rad24_id

        This message is generated when a RADIUS server response is received
        with an invalid length (CONSOLE)."
    ::= { radNotificationsPrefix 24 }

radNotification25 NOTIFICATION-TYPE
    OBJECTS { 
              rad25_addr_rad_serv, 
              rad25_id,
              rad25_servc,
              rad25_lcl_addr,
              rad25_lcl_prt,
              rad25_rmt_addr,
              rad25_rmt_prt 
            }
    STATUS current
    DESCRIPTION
        "Notification of Event RAD.25

        Message: 'send an ACCESS REQUEST packet to RADIUS server $1, identifier $2, for service $3, local address $4, local port $5, remote address $6, remote port $7'

        Parameters list:
              $1: rad25_addr_rad_serv
              $2: rad25_id
              $3: rad25_servc
              $4: rad25_lcl_addr
              $5: rad25_lcl_prt
              $6: rad25_rmt_addr
              $7: rad25_rmt_prt

        This message is generated when an ACCESS REQUEST packet is sent to the
        RADIUS server, if a new TELNET or FTP authentication arrives."
    ::= { radNotificationsPrefix 25 }

radNotification26 NOTIFICATION-TYPE
    OBJECTS { 
              rad26_addr_rad_serv, 
              rad26_id,
              rad26_servc,
              rad26_lcl_addr,
              rad26_lcl_prt,
              rad26_rmt_addr,
              rad26_rmt_prt 
            }
    STATUS current
    DESCRIPTION
        "Notification of Event RAD.26

        Message: 'receive an ACCESS ACCEPT packet from RADIUS server $1, identifier $2, for service $3, local address $4, local port $5, remote address $6, remote port $7'

        Parameters list:
              $1: rad26_addr_rad_serv
              $2: rad26_id
              $3: rad26_servc
              $4: rad26_lcl_addr
              $5: rad26_lcl_prt
              $6: rad26_rmt_addr
              $7: rad26_rmt_prt

        This message is generated when an ACCESS ACCEPT packet is received,
        which is sent by the RADIUS server if the RADIUS request is
        authenticated (TELNET or FTP)."
    ::= { radNotificationsPrefix 26 }

radNotification27 NOTIFICATION-TYPE
    OBJECTS { 
              rad27_addr_rad_serv, 
              rad27_id,
              rad27_servc,
              rad27_lcl_addr,
              rad27_lcl_prt,
              rad27_rmt_addr,
              rad27_rmt_prt 
            }
    STATUS current
    DESCRIPTION
        "Notification of Event RAD.27

        Message: 'receive an ACCESS REJECT packet from RADIUS server $1, identifier $2, for service $3, local address $4, local port $5, remote address $6, remote port $7'

        Parameters list:
              $1: rad27_addr_rad_serv
              $2: rad27_id
              $3: rad27_servc
              $4: rad27_lcl_addr
              $5: rad27_lcl_prt
              $6: rad27_rmt_addr
              $7: rad27_rmt_prt

        This message is generated when an ACCESS REJECT packet is received,
        which is sent by the RADIUS server if the RADIUS request is rejected
        (TELNET or FTP)."
    ::= { radNotificationsPrefix 27 }

radNotification28 NOTIFICATION-TYPE
    OBJECTS { 
              rad28_addr_rad_serv, 
              rad28_id,
              rad28_servc,
              rad28_lcl_addr,
              rad28_lcl_prt,
              rad28_rmt_addr,
              rad28_rmt_prt 
            }
    STATUS current
    DESCRIPTION
        "Notification of Event RAD.28

        Message: 'receive an ACCESS CHALLENGE packet from RADIUS server $1, identifier $2, for service $3, local address $4, local port $5, remote address $6, remote port $7'

        Parameters list:
              $1: rad28_addr_rad_serv
              $2: rad28_id
              $3: rad28_servc
              $4: rad28_lcl_addr
              $5: rad28_lcl_prt
              $6: rad28_rmt_addr
              $7: rad28_rmt_prt

        This message is generated when an ACCESS CHALLENGE packet is received,
        which is sent by the RADIUS server to ask for a new ACCESS REQUEST
        packet (TELNET or FTP)."
    ::= { radNotificationsPrefix 28 }

radNotification29 NOTIFICATION-TYPE
    OBJECTS { 
              rad29_addr_rad_serv, 
              rad29_id,
              rad29_servc,
              rad29_lcl_addr,
              rad29_lcl_prt,
              rad29_rmt_addr,
              rad29_rmt_prt 
            }
    STATUS current
    DESCRIPTION
        "Notification of Event RAD.29

        Message: 'retransmit ACCESS REQUEST packet to RADIUS server $1, identifier $2, for service $3, local address $4, local port $5, remote address $6, remote port $7'

        Parameters list:
              $1: rad29_addr_rad_serv
              $2: rad29_id
              $3: rad29_servc
              $4: rad29_lcl_addr
              $5: rad29_lcl_prt
              $6: rad29_rmt_addr
              $7: rad29_rmt_prt

        This message is generated when an ACCESS REQUEST packet is retransmitted
        by the client if the RADIUS server response is not received
        in the expected time (TELNET or FTP)."
    ::= { radNotificationsPrefix 29 }

radNotification30 NOTIFICATION-TYPE
    OBJECTS { 
              rad30_servc, 
              rad30_lcl_addr,
              rad30_lcl_prt,
              rad30_rmt_addr,
              rad30_rmt_prt 
            }
    STATUS current
    DESCRIPTION
        "Notification of Event RAD.30

        Message: 'fail authentication due to no communication with RADIUS servers, for service $1, local address $2, local port $3, remote address $4, remote port $5'

        Parameters list:
              $1: rad30_servc
              $2: rad30_lcl_addr
              $3: rad30_lcl_prt
              $4: rad30_rmt_addr
              $5: rad30_rmt_prt

        This message is generated when an authentication request is rejected
        if a RADIUS server response is not received or nets to RADIUS servers
        are down and the number of possible attempts is over (TELNET or FTP)."
    ::= { radNotificationsPrefix 30 }

radNotification31 NOTIFICATION-TYPE
    OBJECTS { 
              rad31_addr_rad_serv, 
              rad31_servc,
              rad31_lcl_addr,
              rad31_lcl_prt,
              rad31_rmt_addr,
              rad31_rmt_prt 
            }
    STATUS current
    DESCRIPTION
        "Notification of Event RAD.31

        Message: 'net to servidor RADIUS $1 is not UP, for service $2, local address $3, local port $4, remote address $5, remote port $6'

        Parameters list:
              $1: rad31_addr_rad_serv
              $2: rad31_servc
              $3: rad31_lcl_addr
              $4: rad31_lcl_prt
              $5: rad31_rmt_addr
              $6: rad31_rmt_prt

        This message is generated when it is tried to send a packet to
        a RADIUS server and outgoing net is not UP (TELNET or FTP)."
    ::= { radNotificationsPrefix 31 }

radNotification32 NOTIFICATION-TYPE
    OBJECTS { 
              rad32_addr_rad_serv, 
              rad32_id,
              rad32_typ,
              rad32_servc,
              rad32_lcl_addr,
              rad32_lcl_prt,
              rad32_rmt_addr,
              rad32_rmt_prt 
            }
    STATUS current
    DESCRIPTION
        "Notification of Event RAD.32

        Message: 'receive an ACCESS ACCEPT packet from RADIUS server $1, identifier $2, with attribute type $3 with invalid length, for service $4, local address $5, local port $6, remote address $7, remote port $8'

        Parameters list:
              $1: rad32_addr_rad_serv
              $2: rad32_id
              $3: rad32_typ
              $4: rad32_servc
              $5: rad32_lcl_addr
              $6: rad32_lcl_prt
              $7: rad32_rmt_addr
              $8: rad32_rmt_prt

        This message is generated when an ACCESS ACCEPT packet is received
        with an attribute with invalid length from the RADIUS Server
        (TELNET or FTP)."
    ::= { radNotificationsPrefix 32 }

radNotification33 NOTIFICATION-TYPE
    OBJECTS { 
              rad33_addr_rad_serv, 
              rad33_id,
              rad33_typ,
              rad33_servc,
              rad33_lcl_addr,
              rad33_lcl_prt,
              rad33_rmt_addr,
              rad33_rmt_prt 
            }
    STATUS current
    DESCRIPTION
        "Notification of Event RAD.33

        Message: 'receive an ACCESS ACCEPT packet from RADIUS server $1, identifier $2, with attribute type $3 with invalid content, for service $4, local address $5, local port $6, remote address $7, remote port $8'

        Parameters list:
              $1: rad33_addr_rad_serv
              $2: rad33_id
              $3: rad33_typ
              $4: rad33_servc
              $5: rad33_lcl_addr
              $6: rad33_lcl_prt
              $7: rad33_rmt_addr
              $8: rad33_rmt_prt

        This message is generated when an ACCESS ACCEPT packet is received
        with an attribute with an invalid content from the RADIUS Server
        (TELNET or FTP)."
    ::= { radNotificationsPrefix 33 }

radNotification34 NOTIFICATION-TYPE
    OBJECTS { 
              rad34_addr_rad_serv, 
              rad34_id,
              rad34_typ,
              rad34_servc,
              rad34_lcl_addr,
              rad34_lcl_prt,
              rad34_rmt_addr,
              rad34_rmt_prt 
            }
    STATUS current
    DESCRIPTION
        "Notification of Event RAD.34

        Message: 'receive an ACCESS ACCEPT packet from RADIUS server $1, identifier $2, with extra attribute type $3, for service $4, local address $5, local port $6, remote address $7, remote port $8'

        Parameters list:
              $1: rad34_addr_rad_serv
              $2: rad34_id
              $3: rad34_typ
              $4: rad34_servc
              $5: rad34_lcl_addr
              $6: rad34_lcl_prt
              $7: rad34_rmt_addr
              $8: rad34_rmt_prt

        This message is generated when an ACCESS ACCEPT packet is received
        with an excessive number of attributes with the same type from
        the RADIUS Server (TELNET or FTP)."
    ::= { radNotificationsPrefix 34 }

radNotification35 NOTIFICATION-TYPE
    OBJECTS { 
              rad35_addr_rad_serv, 
              rad35_id,
              rad35_typ,
              rad35_servc,
              rad35_lcl_addr,
              rad35_lcl_prt,
              rad35_rmt_addr,
              rad35_rmt_prt 
            }
    STATUS current
    DESCRIPTION
        "Notification of Event RAD.35

        Message: 'receive an ACCESS ACCEPT packet from RADIUS server $1, identifier $2, with invalid attribute type $3, for service $4, local address $5, local port $6, remote address $7, remote port $8'

        Parameters list:
              $1: rad35_addr_rad_serv
              $2: rad35_id
              $3: rad35_typ
              $4: rad35_servc
              $5: rad35_lcl_addr
              $6: rad35_lcl_prt
              $7: rad35_rmt_addr
              $8: rad35_rmt_prt

        This message is generated when an ACCESS ACCEPT packet is received
        with an invalid attribute for the offered service from the RADIUS
        Server (TELNET or FTP)."
    ::= { radNotificationsPrefix 35 }

radNotification36 NOTIFICATION-TYPE
    OBJECTS { 
              rad36_addr_rad_serv, 
              rad36_id,
              rad36_servc,
              rad36_lcl_addr,
              rad36_lcl_prt,
              rad36_rmt_addr,
              rad36_rmt_prt 
            }
    STATUS current
    DESCRIPTION
        "Notification of Event RAD.36

        Message: 'receive an ACCESS RESPONSE packet from RADIUS server $1, identifier $2, with invalid length, for service $3, local address $4, local port $5, remote address $6, remote port $7'

        Parameters list:
              $1: rad36_addr_rad_serv
              $2: rad36_id
              $3: rad36_servc
              $4: rad36_lcl_addr
              $5: rad36_lcl_prt
              $6: rad36_rmt_addr
              $7: rad36_rmt_prt

        This message is generated when a RADIUS server response is received
        with an invalid length (TELNET or FTP)."
    ::= { radNotificationsPrefix 36 }

radNotification37 NOTIFICATION-TYPE
    OBJECTS { 
              rad37_addr_rad_serv, 
              rad37_id 
            }
    STATUS current
    DESCRIPTION
        "Notification of Event RAD.37

        Message: 'discard packet from RADIUS server $1, identifier $2'

        Parameters list:
              $1: rad37_addr_rad_serv
              $2: rad37_id

        This message is generated when a RADIUS server response is received and
        there is not any pending request corresponding to that packet or rhe
        packet contains errors."
    ::= { radNotificationsPrefix 37 }

radNotification38 NOTIFICATION-TYPE
    OBJECTS { 
              rad38_addr_rad_serv, 
              rad38_id,
              rad38_src_prt,
              rad38_dst_prt 
            }
    STATUS current
    DESCRIPTION
        "Notification of Event RAD.38

        Message: 'receive an ACCESS RESPONSE packet from unknown RADIUS server $1, identifier $2, source port $3, destination port $4'

        Parameters list:
              $1: rad38_addr_rad_serv
              $2: rad38_id
              $3: rad38_src_prt
              $4: rad38_dst_prt

        This message is generated when a response is received from an unknown
        RADIUS server."
    ::= { radNotificationsPrefix 38 }

radNotification39 NOTIFICATION-TYPE
    OBJECTS { 
              rad39_addr_rad_serv, 
              rad39_id,
              rad39_typ 
            }
    STATUS current
    DESCRIPTION
        "Notification of Event RAD.39

        Message: 'received a RADIUS packet from RADIUS server $1, identifier $2, with unknown type $3'

        Parameters list:
              $1: rad39_addr_rad_serv
              $2: rad39_id
              $3: rad39_typ

        This message is generated when a RADIUS packet is received
        with an unknown type."
    ::= { radNotificationsPrefix 39 }

radNotification40 NOTIFICATION-TYPE
    OBJECTS { 
              rad40_addr_rad_serv, 
              rad40_id 
            }
    STATUS current
    DESCRIPTION
        "Notification of Event RAD.40

        Message: 'receive an ACCESS RESPONSE packet from RADIUS server $1, identifier $2, with invalid length'

        Parameters list:
              $1: rad40_addr_rad_serv
              $2: rad40_id

        This message is generated when a RADIUS server response is received
        with an invalid length."
    ::= { radNotificationsPrefix 40 }

radNotification41 NOTIFICATION-TYPE
    OBJECTS { 
              rad41_error_string 
            }
    STATUS current
    DESCRIPTION
        "Notification of Event RAD.41

        Message: '$1'

        Parameters list:
              $1: rad41_error_string

        Generic internal error event."
    ::= { radNotificationsPrefix 41 }

radNotification42 NOTIFICATION-TYPE
    OBJECTS { 
              rad42_name, 
              rad42_length,
              rad42_value 
            }
    STATUS current
    DESCRIPTION
        "Notification of Event RAD.42

        Message: 'send attribute $1, length $2: $3'

        Parameters list:
              $1: rad42_name
              $2: rad42_length
              $3: rad42_value

        Attribute sent in a Radius request."
    ::= { radNotificationsPrefix 42 }

radNotification43 NOTIFICATION-TYPE
    OBJECTS { 
              rad43_name, 
              rad43_length,
              rad43_value 
            }
    STATUS current
    DESCRIPTION
        "Notification of Event RAD.43

        Message: 'receive attribute $1, length $2: $3'

        Parameters list:
              $1: rad43_name
              $2: rad43_length
              $3: rad43_value

        Attribute received in a Radius response."
    ::= { radNotificationsPrefix 43 }

radNotification44 NOTIFICATION-TYPE
    OBJECTS { 
              rad44_packet_type, 
              rad44_length,
              rad44_server_address,
              rad44_server_port,
              rad44_identifier,
              rad44_service 
            }
    STATUS current
    DESCRIPTION
        "Notification of Event RAD.44

        Message: 'send $1 packet length $2, to RADIUS server $3:$4, identifier $5, for service $6'

        Parameters list:
              $1: rad44_packet_type
              $2: rad44_length
              $3: rad44_server_address
              $4: rad44_server_port
              $5: rad44_identifier
              $6: rad44_service

        This message is generated when a packet is sent to a RADIUS server."
    ::= { radNotificationsPrefix 44 }

radNotification45 NOTIFICATION-TYPE
    OBJECTS { 
              rad45_packet_type, 
              rad45_length,
              rad45_server_address,
              rad45_server_port,
              rad45_identifier,
              rad45_service 
            }
    STATUS current
    DESCRIPTION
        "Notification of Event RAD.45

        Message: 'receive $1 packet length $2, from RADIUS server $3:$4, identifier $5, for service $6'

        Parameters list:
              $1: rad45_packet_type
              $2: rad45_length
              $3: rad45_server_address
              $4: rad45_server_port
              $5: rad45_identifier
              $6: rad45_service

        This message is generated when a packet is sent to a RADIUS server."
    ::= { radNotificationsPrefix 45 }

radNotification46 NOTIFICATION-TYPE
    OBJECTS { 
              rad46_packet_type, 
              rad46_length,
              rad46_server_address,
              rad46_server_port,
              rad46_identifier,
              rad46_service 
            }
    STATUS current
    DESCRIPTION
        "Notification of Event RAD.46

        Message: 'retransmit $1 packet length $2, to RADIUS server $3:$4, identifier $5, for service $6'

        Parameters list:
              $1: rad46_packet_type
              $2: rad46_length
              $3: rad46_server_address
              $4: rad46_server_port
              $5: rad46_identifier
              $6: rad46_service

        This message is generated when a packet is retransmitted to a RADIUS server."
    ::= { radNotificationsPrefix 46 }

radNotification47 NOTIFICATION-TYPE
    OBJECTS { 
              rad47_info_string 
            }
    STATUS current
    DESCRIPTION
        "Notification of Event RAD.47

        Message: '$1'

        Parameters list:
              $1: rad47_info_string

        Generic comment on usual information message."
    ::= { radNotificationsPrefix 47 }

radNotification48 NOTIFICATION-TYPE
    OBJECTS { 
              rad48_service 
            }
    STATUS current
    DESCRIPTION
        "Notification of Event RAD.48

        Message: 'fail authentication due to no communication with RADIUS servers, for service $1'

        Parameters list:
              $1: rad48_service

        This message is generated when an authentication request is rejected
        if a RADIUS server response is not received or nets to RADIUS servers
        are down and the number of possible attempts is over."
    ::= { radNotificationsPrefix 48 }

radNotification49 NOTIFICATION-TYPE
    OBJECTS { 
              rad49_addr_rad_serv, 
              rad49_service 
            }
    STATUS current
    DESCRIPTION
        "Notification of Event RAD.49

        Message: 'net to servidor RADIUS $1 is not UP, for service $2'

        Parameters list:
              $1: rad49_addr_rad_serv
              $2: rad49_service

        This message is generated when it is tried to send a packet to a
        RADIUS server and outgoing net is not UP."
    ::= { radNotificationsPrefix 49 }

radNotification50 NOTIFICATION-TYPE
    OBJECTS { 
              rad50_addr_rad_serv, 
              rad50_id,
              rad50_service 
            }
    STATUS current
    DESCRIPTION
        "Notification of Event RAD.50

        Message: 'send an ACCESS REQUEST packet to RADIUS server $1, identifier $2, for service $3'

        Parameters list:
              $1: rad50_addr_rad_serv
              $2: rad50_id
              $3: rad50_service

        This message is generated when an ACCESS REQUEST packet is sent to
        RADIUS server, if a new authentication arrives."
    ::= { radNotificationsPrefix 50 }

radNotification51 NOTIFICATION-TYPE
    OBJECTS { 
              rad51_addr_rad_serv, 
              rad51_id,
              rad51_service 
            }
    STATUS current
    DESCRIPTION
        "Notification of Event RAD.51

        Message: 'retransmit ACCESS REQUEST packet to RADIUS server $1, identifier $2, for service $3'

        Parameters list:
              $1: rad51_addr_rad_serv
              $2: rad51_id
              $3: rad51_service

        This message is generated when an ACCESS REQUEST packet is retransmitted
        by the client if the RADIUS server response is not received
        in the expected time."
    ::= { radNotificationsPrefix 51 }

radNotification52 NOTIFICATION-TYPE
    OBJECTS { 
              rad52_addr_rad_serv, 
              rad52_id,
              rad52_service 
            }
    STATUS current
    DESCRIPTION
        "Notification of Event RAD.52

        Message: 'receive an ACCESS ACCEPT packet from RADIUS server $1, identifier $2, for service $3'

        Parameters list:
              $1: rad52_addr_rad_serv
              $2: rad52_id
              $3: rad52_service

        This message is generated when an ACCESS ACCEPT packet is received,
        which is sent by the RADIUS server if the RADIUS request is
        authenticated."
    ::= { radNotificationsPrefix 52 }

radNotification53 NOTIFICATION-TYPE
    OBJECTS { 
              rad53_addr_rad_serv, 
              rad53_id,
              rad53_service 
            }
    STATUS current
    DESCRIPTION
        "Notification of Event RAD.53

        Message: 'receive an ACCESS REJECT packet from RADIUS server $1, identifier $2, for service $3'

        Parameters list:
              $1: rad53_addr_rad_serv
              $2: rad53_id
              $3: rad53_service

        This message is generated when an ACCESS REJECT packet is received,
        which is sent by the RADIUS server if the RADIUS request is rejected."
    ::= { radNotificationsPrefix 53 }

radNotification54 NOTIFICATION-TYPE
    OBJECTS { 
              rad54_addr_rad_serv, 
              rad54_id,
              rad54_service 
            }
    STATUS current
    DESCRIPTION
        "Notification of Event RAD.54

        Message: 'receive an ACCESS CHALLENGE packet from RADIUS server $1, identifier $2, for service $3'

        Parameters list:
              $1: rad54_addr_rad_serv
              $2: rad54_id
              $3: rad54_service

        This message is generated when an ACCESS CHALLENGE packet is received,
        which is sent by the RADIUS server to ask for a new ACCESS REQUEST
        packet."
    ::= { radNotificationsPrefix 54 }

radNotification55 NOTIFICATION-TYPE
    OBJECTS { 
              rad55_addr_rad_serv, 
              rad55_id,
              rad55_typ,
              rad55_service 
            }
    STATUS current
    DESCRIPTION
        "Notification of Event RAD.55

        Message: 'receive an ACCESS ACCEPT packet from RADIUS server $1, identifier $2, with attribute type $3 with invalid length, for service $4'

        Parameters list:
              $1: rad55_addr_rad_serv
              $2: rad55_id
              $3: rad55_typ
              $4: rad55_service

        This message is generated when an ACCESS ACCEPT packet is received
        with an attribute with invalid length from the RADIUS Server."
    ::= { radNotificationsPrefix 55 }

radNotification56 NOTIFICATION-TYPE
    OBJECTS { 
              rad56_addr_rad_serv, 
              rad56_id,
              rad56_typ,
              rad56_service 
            }
    STATUS current
    DESCRIPTION
        "Notification of Event RAD.56

        Message: 'receive an ACCESS ACCEPT packet from RADIUS server $1, identifier $2, with attribute type $3 with invalid content, for service $4'

        Parameters list:
              $1: rad56_addr_rad_serv
              $2: rad56_id
              $3: rad56_typ
              $4: rad56_service

        This message is generated when an ACCESS ACCEPT packet is received
        with an attribute with an invalid content from the RADIUS Server."
    ::= { radNotificationsPrefix 56 }

radNotification57 NOTIFICATION-TYPE
    OBJECTS { 
              rad57_addr_rad_serv, 
              rad57_id,
              rad57_typ,
              rad57_service 
            }
    STATUS current
    DESCRIPTION
        "Notification of Event RAD.57

        Message: 'receive an ACCESS ACCEPT packet from RADIUS server $1, identifier $2, with extra attribute type $3, for service $4'

        Parameters list:
              $1: rad57_addr_rad_serv
              $2: rad57_id
              $3: rad57_typ
              $4: rad57_service

        This message is generated when an ACCESS ACCEPT packet is received
        with a excessive number of attributes with the same type
        from the RADIUS Server."
    ::= { radNotificationsPrefix 57 }

radNotification58 NOTIFICATION-TYPE
    OBJECTS { 
              rad58_addr_rad_serv, 
              rad58_id,
              rad58_typ,
              rad58_service 
            }
    STATUS current
    DESCRIPTION
        "Notification of Event RAD.58

        Message: 'receive an ACCESS ACCEPT packet from RADIUS server $1, identifier $2, with invalid attribute type $3, for service $4'

        Parameters list:
              $1: rad58_addr_rad_serv
              $2: rad58_id
              $3: rad58_typ
              $4: rad58_service

        This message is generated when an ACCESS ACCEPT packet is received
        with an invalid attribute for the offered service from the RADIUS
        Server."
    ::= { radNotificationsPrefix 58 }

radNotification59 NOTIFICATION-TYPE
    OBJECTS { 
              rad59_addr_rad_serv, 
              rad59_id,
              rad59_service 
            }
    STATUS current
    DESCRIPTION
        "Notification of Event RAD.59

        Message: 'receive an ACCESS RESPONSE packet from RADIUS server $1, identifier $2, with invalid length, for service $3'

        Parameters list:
              $1: rad59_addr_rad_serv
              $2: rad59_id
              $3: rad59_service

        This message is generated when a RADIUS server response is received
        with an invalid length."
    ::= { radNotificationsPrefix 59 }


END
