-- This	Extension Agent	implements the CLARiiON	Agent.	It's
-- definition follows here:
--
-- Extensions for Fibre Cat made by Reinhard Kockmann, Fujitsu Siemens Computers
--
	CLARIION1-MIB DEFINITIONS ::= BEGIN


IMPORTS
	OBJECT-TYPE                            FROM RFC-1212
	mib-2                                  FROM RFC1213-MIB
	DisplayString                          FROM RFC1213-MIB
	PhysAddress                            FROM RFC1213-MIB
	Counter, Gauge, IpAddress, enterprises FROM RFC1155-SMI;

--
-- The Windows NT MIB compiler doesn't support IMPORTS.
-- So, include these definitions here. NT defines "DisplayString" as
-- OCTET STRING (SIZE(0..255)), in RFC1213 it has no explicit size.
--
-- DisplayString ::= OCTET STRING
-- PhysAddress   ::= OCTET STRING
-- enterprises     OBJECT IDENTIFIER ::= { iso org(3) dod(6) internet(1) private(4) 1 }
--
	 dataGeneral	 OBJECT	IDENTIFIER ::= { enterprises 1981 }
	 dgHardware	 OBJECT	IDENTIFIER ::= { dataGeneral 1 }
	 cLARiiON	 OBJECT	IDENTIFIER ::= { dgHardware 4 }
	 clarAgent	 OBJECT	IDENTIFIER ::= { cLARiiON 1 }
	 clarAgentTbl	 OBJECT	IDENTIFIER ::= { cLARiiON 2 }
 

	

-- Changes for FibreCat                                                                                                             
     clarHostName   OBJECT-TYPE
		SYNTAX	DisplayString
		ACCESS	read-only
		STATUS	mandatory
		DESCRIPTION
			"Host name for CLARiiON FibreCat"
		::= { cLARiiON 3 }
 
     clarEventCode  OBJECT-TYPE
		SYNTAX	DisplayString
		ACCESS	read-only
		STATUS	mandatory
		DESCRIPTION
			"Event Code for CLARiiON FibreCat"
		::= { cLARiiON 4 } 

     clarErrorCode  OBJECT-TYPE
		SYNTAX	INTEGER 
		ACCESS	read-only
		STATUS	mandatory
		DESCRIPTION
			"Error code for CLARiiON FibreCat"
		::= { cLARiiON 5 } 
 
     clarErrorDescript  OBJECT-TYPE
		SYNTAX	DisplayString
		ACCESS	read-only
		STATUS	mandatory
		DESCRIPTION
			"Error description for CLARiiON FibreCat"
		::= { cLARiiON 6 }                                                                            

     clarSerialNo   OBJECT-TYPE
		SYNTAX	DisplayString
		ACCESS	read-only
		STATUS	mandatory
		DESCRIPTION
			"Serial no. of CLARiiON FibreCat"
		::= { cLARiiON 7 }    

-- trap description from Alfred Boehme

 clarTrap	TRAP-TYPE
	ENTERPRISE      dataGeneral
	VARIABLES       { clarHostName, clarEventCode, clarErrorCode, clarErrorDescript, clarSerialNo  }
	DESCRIPTION
		"Clariion FibreCat Trap"
    --#TYPE      "Clariion FibreCat Trap"
    --#SUMMARY   "FibreCat error: %s on host: %s, error number: %d, "
    --#SUMMARY   "event code: %d, serial number: %s"
    --#ARGUMENTS { 3, 0, 2, 1, 4 }
    --#SEVERITY  INFORMATIONAL
    --#TIMEINDEX 1
    --#STATE     OPERATIONAL
	::= 2                                                                       

END
