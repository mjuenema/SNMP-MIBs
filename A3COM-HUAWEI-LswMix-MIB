-- ------------------------------------------------------------------
--
-- Description: HuaWei Lan Switch Dual Main Control MIB
--
-- Version: V1.2
-- History:
-- Revise History: 1) 2003-03-27 Fuzhenyu created
-- V1.1 2004-10-12 updated by gaolong
--      Import NOTIFICATION-TYPE.
--      MAX-ACCESS clause value from write-only to read-write.
--      Substitute hwsMixTrapMib MODULE-IDENTITY with hwsMixTrapMib OBJECT IDENTIFIER.
-- V1.2 2005-11-14
--      updated by Chen Xi
--      Modify description of all objects except hwLswXSlotTable and hwLswXSlotEntry.
--      updated by Yu Lan
--      Add process(3) value for hwLswMainCardBoardStatus.
--      Add hwLswCrossBarStatus.
-- ------------------------------------------------------------------
--
-- ------------------------------------------------------------------
--
-- Variable imported
--
-- ------------------------------------------------------------------
A3COM-HUAWEI-LswMix-MIB DEFINITIONS ::= BEGIN

IMPORTS

	MODULE-IDENTITY, OBJECT-TYPE, NOTIFICATION-TYPE
		FROM SNMPv2-SMI
	hwLswFrameIndex,hwLswSlotIndex
		FROM A3COM-HUAWEI-DEVICE-MIB
	lswCommon
		FROM A3COM-HUAWEI-OID-MIB;

--  the document include the private data about device
-- ******************************beginning  ******************************
--
-- ------------------------------------------------------------------
	hwLswMix MODULE-IDENTITY
			LAST-UPDATED "200106290000Z"
			ORGANIZATION ""
			CONTACT-INFO
			""
			DESCRIPTION
			""
			REVISION "200106290000Z"
			DESCRIPTION
			""
			::= { lswCommon  17 }


--  the document include the private data about device mix

hwLswLastSwitchDate OBJECT-TYPE
	SYNTAX INTEGER
	MAX-ACCESS  read-only
	STATUS  current
	DESCRIPTION
	"This object indicates the date of the most recent change
	to the mpu(Main Processing Unit). "
	::= { hwLswMix 1 }

hwLswLastSwitchTime OBJECT-TYPE
	SYNTAX INTEGER
	MAX-ACCESS  read-only
	STATUS  current
	DESCRIPTION
	"This object indicates the time of the most recent change
	to the mpu. "
	::= { hwLswMix 2 }

hwLswMpuSwitchsNum OBJECT-TYPE
	SYNTAX INTEGER
	MAX-ACCESS  read-only
	STATUS  current
	DESCRIPTION
	"This object indicates the total times of the mpu switched
	since the system start up. "
	::= { hwLswMix 3 }

hwLswMpuSwitch OBJECT-TYPE
	SYNTAX INTEGER{
		switch(1)
	}
	MAX-ACCESS  read-write
	STATUS  current
	DESCRIPTION
	"Setting this object will immediately switch the standby mpu
	to master mpu. Read is not supported. "
	::= { hwLswMix 4 }

--  the document include the private data about main card
hwLswXSlotTable OBJECT-TYPE
	SYNTAX  SEQUENCE OF HwLswXSlotEntry
	MAX-ACCESS  not-accessible
	STATUS  current
	DESCRIPTION
	"The source main table."
	 ::= { hwLswMix 5 }

hwLswXSlotEntry OBJECT-TYPE
	SYNTAX  HwLswXSlotEntry
	MAX-ACCESS  not-accessible
	STATUS  current
	DESCRIPTION
	"An entry in the source main table."
	INDEX   { hwLswFrameIndex, hwLswSlotIndex }
	 ::= { hwLswXSlotTable 1 }

HwLswXSlotEntry ::=
	SEQUENCE {
		hwLswMainCardBoardStatus        INTEGER,
		hwLswCrossBarStatus            INTEGER
	}

hwLswMainCardBoardStatus OBJECT-TYPE
	SYNTAX  INTEGER{
	  master(1),
	  standby(2),
	  process(3)
	}
	MAX-ACCESS  read-only
	STATUS  current
	DESCRIPTION
	   "The value describes whether the board is master, standby or process.
	   master and standby are the possible states for the mpu, while process
	   indicates the state of lpu(Line Processing Unit)"
	 ::= { hwLswXSlotEntry 1 }

hwLswCrossBarStatus OBJECT-TYPE
	SYNTAX INTEGER{
	   master(1),
	   standby(2)
	   }
	MAX-ACCESS read-only
	STATUS current
	DESCRIPTION
	   "The value describes whether the crossbar is master or standby. It is
	   master when it's in the master mpu board, standby when in the standby mpu.
	   But both crossbars in mpus are master when the device in load-balance mode."
	::= { hwLswXSlotEntry 2 }

   hwsMixTrapMib OBJECT IDENTIFIER        ::= { hwLswMix  10 }

   hwSlaveSwitchOver NOTIFICATION-TYPE
	  STATUS  current
	  DESCRIPTION
	  "An hwSlaveSwitchOver trap signifies that the action of standby Main Processing Unit (MPU) switching to master has completed. "
	  ::= { hwsMixTrapMib 1 }

END
