-- file automatically created


TELDAT-TRAP-FR-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


frTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the FR event subsystem."
    REVISION "201401200930Z"
    DESCRIPTION "Initial implementation"
        ::= { telEventTraps 92 }


frEventsGroup	OBJECT IDENTIFIER	::= { frTrapsMIB 1 }

frNotifications	OBJECT IDENTIFIER	::= { frTrapsMIB 2 }
frNotificationsPrefix	OBJECT IDENTIFIER	::= { frNotifications 0 }

frEventObjects1 OBJECT-IDENTITY
    STATUS current
    DESCRIPTION
        "Event FR.1
        A frame had been received on the FR interface."
    ::= { frEventsGroup 1 }

fr1_circuit OBJECT-TYPE
    SYNTAX Integer32
    MAX-ACCESS accessible-for-notify
    STATUS current
    DESCRIPTION
        "Parameter 'circuit' in event FR.1"
    ::= { frEventObjects1 1 }

fr1_protocol OBJECT-TYPE
    SYNTAX DisplayString
    MAX-ACCESS accessible-for-notify
    STATUS current
    DESCRIPTION
        "Parameter 'protocol' in event FR.1"
    ::= { frEventObjects1 2 }

fr1_size OBJECT-TYPE
    SYNTAX Integer32
    MAX-ACCESS accessible-for-notify
    STATUS current
    DESCRIPTION
        "Parameter 'size' in event FR.1"
    ::= { frEventObjects1 3 }

fr1_ifcname OBJECT-TYPE
    SYNTAX DisplayString
    MAX-ACCESS accessible-for-notify
    STATUS current
    DESCRIPTION
        "Parameter 'ifcname' in event FR.1"
    ::= { frEventObjects1 4 }

fr1_buffer OBJECT-TYPE
    SYNTAX DisplayString
    MAX-ACCESS accessible-for-notify
    STATUS current
    DESCRIPTION
        "Parameter 'buffer' in event FR.1"
    ::= { frEventObjects1 5 }

frEventObjects2 OBJECT-IDENTITY
    STATUS current
    DESCRIPTION
        "Event FR.2
        A frame had been transmitted on the FR interface."
    ::= { frEventsGroup 2 }

fr2_circuit OBJECT-TYPE
    SYNTAX Integer32
    MAX-ACCESS accessible-for-notify
    STATUS current
    DESCRIPTION
        "Parameter 'circuit' in event FR.2"
    ::= { frEventObjects2 1 }

fr2_protocol OBJECT-TYPE
    SYNTAX DisplayString
    MAX-ACCESS accessible-for-notify
    STATUS current
    DESCRIPTION
        "Parameter 'protocol' in event FR.2"
    ::= { frEventObjects2 2 }

fr2_size OBJECT-TYPE
    SYNTAX Integer32
    MAX-ACCESS accessible-for-notify
    STATUS current
    DESCRIPTION
        "Parameter 'size' in event FR.2"
    ::= { frEventObjects2 3 }

fr2_ifcname OBJECT-TYPE
    SYNTAX DisplayString
    MAX-ACCESS accessible-for-notify
    STATUS current
    DESCRIPTION
        "Parameter 'ifcname' in event FR.2"
    ::= { frEventObjects2 4 }

fr2_buffer OBJECT-TYPE
    SYNTAX DisplayString
    MAX-ACCESS accessible-for-notify
    STATUS current
    DESCRIPTION
        "Parameter 'buffer' in event FR.2"
    ::= { frEventObjects2 5 }

frEventObjects3 OBJECT-IDENTITY
    STATUS current
    DESCRIPTION
        "Event FR.3
        A protocol frame had been discarded due to the PVC congested condition."
    ::= { frEventsGroup 3 }

fr3_circuit OBJECT-TYPE
    SYNTAX Integer32
    MAX-ACCESS accessible-for-notify
    STATUS current
    DESCRIPTION
        "Parameter 'circuit' in event FR.3"
    ::= { frEventObjects3 1 }

fr3_protocol OBJECT-TYPE
    SYNTAX DisplayString
    MAX-ACCESS accessible-for-notify
    STATUS current
    DESCRIPTION
        "Parameter 'protocol' in event FR.3"
    ::= { frEventObjects3 2 }

fr3_ifcname OBJECT-TYPE
    SYNTAX DisplayString
    MAX-ACCESS accessible-for-notify
    STATUS current
    DESCRIPTION
        "Parameter 'ifcname' in event FR.3"
    ::= { frEventObjects3 3 }

frEventObjects4 OBJECT-IDENTITY
    STATUS current
    DESCRIPTION
        "Event FR.4
        The circuit is now experiencing congestion in the outbound direction."
    ::= { frEventsGroup 4 }

fr4_circuit OBJECT-TYPE
    SYNTAX Integer32
    MAX-ACCESS accessible-for-notify
    STATUS current
    DESCRIPTION
        "Parameter 'circuit' in event FR.4"
    ::= { frEventObjects4 1 }

fr4_ifcname OBJECT-TYPE
    SYNTAX DisplayString
    MAX-ACCESS accessible-for-notify
    STATUS current
    DESCRIPTION
        "Parameter 'ifcname' in event FR.4"
    ::= { frEventObjects4 2 }

frEventObjects5 OBJECT-IDENTITY
    STATUS current
    DESCRIPTION
        "Event FR.5
        The circuit is now not experiencing congestion in the outbound
        direction."
    ::= { frEventsGroup 5 }

fr5_circuit OBJECT-TYPE
    SYNTAX Integer32
    MAX-ACCESS accessible-for-notify
    STATUS current
    DESCRIPTION
        "Parameter 'circuit' in event FR.5"
    ::= { frEventObjects5 1 }

fr5_ifcname OBJECT-TYPE
    SYNTAX DisplayString
    MAX-ACCESS accessible-for-notify
    STATUS current
    DESCRIPTION
        "Parameter 'ifcname' in event FR.5"
    ::= { frEventObjects5 2 }

frEventObjects6 OBJECT-IDENTITY
    STATUS current
    DESCRIPTION
        "Event FR.6
        The circuit enters the active state."
    ::= { frEventsGroup 6 }

fr6_circuit OBJECT-TYPE
    SYNTAX Integer32
    MAX-ACCESS accessible-for-notify
    STATUS current
    DESCRIPTION
        "Parameter 'circuit' in event FR.6"
    ::= { frEventObjects6 1 }

fr6_ifcname OBJECT-TYPE
    SYNTAX DisplayString
    MAX-ACCESS accessible-for-notify
    STATUS current
    DESCRIPTION
        "Parameter 'ifcname' in event FR.6"
    ::= { frEventObjects6 2 }

frEventObjects7 OBJECT-IDENTITY
    STATUS current
    DESCRIPTION
        "Event FR.7
        The LMI signalled present and active a circuit which had not been
        statically configured."
    ::= { frEventsGroup 7 }

fr7_circuit OBJECT-TYPE
    SYNTAX Integer32
    MAX-ACCESS accessible-for-notify
    STATUS current
    DESCRIPTION
        "Parameter 'circuit' in event FR.7"
    ::= { frEventObjects7 1 }

fr7_ifcname OBJECT-TYPE
    SYNTAX DisplayString
    MAX-ACCESS accessible-for-notify
    STATUS current
    DESCRIPTION
        "Parameter 'ifcname' in event FR.7"
    ::= { frEventObjects7 2 }

frEventObjects8 OBJECT-IDENTITY
    STATUS current
    DESCRIPTION
        "Event FR.8
        The circuit enters the inactive state."
    ::= { frEventsGroup 8 }

fr8_circuit OBJECT-TYPE
    SYNTAX Integer32
    MAX-ACCESS accessible-for-notify
    STATUS current
    DESCRIPTION
        "Parameter 'circuit' in event FR.8"
    ::= { frEventObjects8 1 }

fr8_ifcname OBJECT-TYPE
    SYNTAX DisplayString
    MAX-ACCESS accessible-for-notify
    STATUS current
    DESCRIPTION
        "Parameter 'ifcname' in event FR.8"
    ::= { frEventObjects8 2 }

frEventObjects9 OBJECT-IDENTITY
    STATUS current
    DESCRIPTION
        "Event FR.9
        The circuit is no longer available on the network."
    ::= { frEventsGroup 9 }

fr9_circuit OBJECT-TYPE
    SYNTAX Integer32
    MAX-ACCESS accessible-for-notify
    STATUS current
    DESCRIPTION
        "Parameter 'circuit' in event FR.9"
    ::= { frEventObjects9 1 }

fr9_ifcname OBJECT-TYPE
    SYNTAX DisplayString
    MAX-ACCESS accessible-for-notify
    STATUS current
    DESCRIPTION
        "Parameter 'ifcname' in event FR.9"
    ::= { frEventObjects9 2 }

frEventObjects10 OBJECT-IDENTITY
    STATUS current
    DESCRIPTION
        "Event FR.10
        The circuit is now available on the network."
    ::= { frEventsGroup 10 }

fr10_circuit OBJECT-TYPE
    SYNTAX Integer32
    MAX-ACCESS accessible-for-notify
    STATUS current
    DESCRIPTION
        "Parameter 'circuit' in event FR.10"
    ::= { frEventObjects10 1 }

fr10_ifcname OBJECT-TYPE
    SYNTAX DisplayString
    MAX-ACCESS accessible-for-notify
    STATUS current
    DESCRIPTION
        "Parameter 'ifcname' in event FR.10"
    ::= { frEventObjects10 2 }

frEventObjects11 OBJECT-IDENTITY
    STATUS current
    DESCRIPTION
        "Event FR.11
        A LMI sequence number exchange has been requested."
    ::= { frEventsGroup 11 }

fr11_rcvseq OBJECT-TYPE
    SYNTAX Integer32
    MAX-ACCESS accessible-for-notify
    STATUS current
    DESCRIPTION
        "Parameter 'rcvseq' in event FR.11"
    ::= { frEventObjects11 1 }

fr11_xmtseq OBJECT-TYPE
    SYNTAX Integer32
    MAX-ACCESS accessible-for-notify
    STATUS current
    DESCRIPTION
        "Parameter 'xmtseq' in event FR.11"
    ::= { frEventObjects11 2 }

fr11_ifcname OBJECT-TYPE
    SYNTAX DisplayString
    MAX-ACCESS accessible-for-notify
    STATUS current
    DESCRIPTION
        "Parameter 'ifcname' in event FR.11"
    ::= { frEventObjects11 3 }

frEventObjects12 OBJECT-IDENTITY
    STATUS current
    DESCRIPTION
        "Event FR.12
        A LMI full Status Enquiry has been requested."
    ::= { frEventsGroup 12 }

fr12_ifcname OBJECT-TYPE
    SYNTAX DisplayString
    MAX-ACCESS accessible-for-notify
    STATUS current
    DESCRIPTION
        "Parameter 'ifcname' in event FR.12"
    ::= { frEventObjects12 1 }

frEventObjects13 OBJECT-IDENTITY
    STATUS current
    DESCRIPTION
        "Event FR.13
        A solicited LMI Status Enquiry response has been received."
    ::= { frEventsGroup 13 }

fr13_ifcname OBJECT-TYPE
    SYNTAX DisplayString
    MAX-ACCESS accessible-for-notify
    STATUS current
    DESCRIPTION
        "Parameter 'ifcname' in event FR.13"
    ::= { frEventObjects13 1 }

frEventObjects14 OBJECT-IDENTITY
    STATUS current
    DESCRIPTION
        "Event FR.14
        A LMI full Status Enquiry response has been received."
    ::= { frEventsGroup 14 }

fr14_ifcname OBJECT-TYPE
    SYNTAX DisplayString
    MAX-ACCESS accessible-for-notify
    STATUS current
    DESCRIPTION
        "Parameter 'ifcname' in event FR.14"
    ::= { frEventObjects14 1 }

frEventObjects15 OBJECT-IDENTITY
    STATUS current
    DESCRIPTION
        "Event FR.15
        A modem status change has occurred. The present state is described."
    ::= { frEventsGroup 15 }

fr15_dcd OBJECT-TYPE
    SYNTAX DisplayString
    MAX-ACCESS accessible-for-notify
    STATUS current
    DESCRIPTION
        "Parameter 'dcd' in event FR.15"
    ::= { frEventObjects15 1 }

fr15_cts OBJECT-TYPE
    SYNTAX DisplayString
    MAX-ACCESS accessible-for-notify
    STATUS current
    DESCRIPTION
        "Parameter 'cts' in event FR.15"
    ::= { frEventObjects15 2 }

fr15_ifcname OBJECT-TYPE
    SYNTAX DisplayString
    MAX-ACCESS accessible-for-notify
    STATUS current
    DESCRIPTION
        "Parameter 'ifcname' in event FR.15"
    ::= { frEventObjects15 3 }

frEventObjects16 OBJECT-IDENTITY
    STATUS current
    DESCRIPTION
        "Event FR.16
        A multicast frame had been transmitted on the FR interface."
    ::= { frEventsGroup 16 }

fr16_circuit OBJECT-TYPE
    SYNTAX Integer32
    MAX-ACCESS accessible-for-notify
    STATUS current
    DESCRIPTION
        "Parameter 'circuit' in event FR.16"
    ::= { frEventObjects16 1 }

fr16_protocol OBJECT-TYPE
    SYNTAX DisplayString
    MAX-ACCESS accessible-for-notify
    STATUS current
    DESCRIPTION
        "Parameter 'protocol' in event FR.16"
    ::= { frEventObjects16 2 }

fr16_ifcname OBJECT-TYPE
    SYNTAX DisplayString
    MAX-ACCESS accessible-for-notify
    STATUS current
    DESCRIPTION
        "Parameter 'ifcname' in event FR.16"
    ::= { frEventObjects16 3 }

frEventObjects17 OBJECT-IDENTITY
    STATUS current
    DESCRIPTION
        "Event FR.17
        The circuit is remaining in the outbound congested state toward
        the network."
    ::= { frEventsGroup 17 }

fr17_circuit OBJECT-TYPE
    SYNTAX Integer32
    MAX-ACCESS accessible-for-notify
    STATUS current
    DESCRIPTION
        "Parameter 'circuit' in event FR.17"
    ::= { frEventObjects17 1 }

fr17_ifcname OBJECT-TYPE
    SYNTAX DisplayString
    MAX-ACCESS accessible-for-notify
    STATUS current
    DESCRIPTION
        "Parameter 'ifcname' in event FR.17"
    ::= { frEventObjects17 2 }

frEventObjects18 OBJECT-IDENTITY
    STATUS current
    DESCRIPTION
        "Event FR.18
        A protocol frame had been discarded due to the PVC exceeding the CIR on
        the circuit."
    ::= { frEventsGroup 18 }

fr18_circuit OBJECT-TYPE
    SYNTAX Integer32
    MAX-ACCESS accessible-for-notify
    STATUS current
    DESCRIPTION
        "Parameter 'circuit' in event FR.18"
    ::= { frEventObjects18 1 }

fr18_protocol OBJECT-TYPE
    SYNTAX DisplayString
    MAX-ACCESS accessible-for-notify
    STATUS current
    DESCRIPTION
        "Parameter 'protocol' in event FR.18"
    ::= { frEventObjects18 2 }

fr18_ifcname OBJECT-TYPE
    SYNTAX DisplayString
    MAX-ACCESS accessible-for-notify
    STATUS current
    DESCRIPTION
        "Parameter 'ifcname' in event FR.18"
    ::= { frEventObjects18 3 }

frEventObjects19 OBJECT-IDENTITY
    STATUS current
    DESCRIPTION
        "Event FR.19
        The LMI signalled present and active a circuit which had not been
        statically configured or allowed."
    ::= { frEventsGroup 19 }

fr19_circuit OBJECT-TYPE
    SYNTAX Integer32
    MAX-ACCESS accessible-for-notify
    STATUS current
    DESCRIPTION
        "Parameter 'circuit' in event FR.19"
    ::= { frEventObjects19 1 }

fr19_ifcname OBJECT-TYPE
    SYNTAX DisplayString
    MAX-ACCESS accessible-for-notify
    STATUS current
    DESCRIPTION
        "Parameter 'ifcname' in event FR.19"
    ::= { frEventObjects19 2 }

frEventObjects20 OBJECT-IDENTITY
    STATUS current
    DESCRIPTION
        "Event FR.20
        The LMI signalled present and active a circuit which cannot join
        the interface, maximum circuits have been exceeded."
    ::= { frEventsGroup 20 }

fr20_circuit OBJECT-TYPE
    SYNTAX Integer32
    MAX-ACCESS accessible-for-notify
    STATUS current
    DESCRIPTION
        "Parameter 'circuit' in event FR.20"
    ::= { frEventObjects20 1 }

fr20_ifcname OBJECT-TYPE
    SYNTAX DisplayString
    MAX-ACCESS accessible-for-notify
    STATUS current
    DESCRIPTION
        "Parameter 'ifcname' in event FR.20"
    ::= { frEventObjects20 2 }

frEventObjects21 OBJECT-IDENTITY
    STATUS current
    DESCRIPTION
        "Event FR.21
        The LMI signalled present and active a circuit which cannot join
        the interface, memory is unavailable."
    ::= { frEventsGroup 21 }

fr21_circuit OBJECT-TYPE
    SYNTAX Integer32
    MAX-ACCESS accessible-for-notify
    STATUS current
    DESCRIPTION
        "Parameter 'circuit' in event FR.21"
    ::= { frEventObjects21 1 }

fr21_ifcname OBJECT-TYPE
    SYNTAX DisplayString
    MAX-ACCESS accessible-for-notify
    STATUS current
    DESCRIPTION
        "Parameter 'ifcname' in event FR.21"
    ::= { frEventObjects21 2 }

frEventObjects22 OBJECT-IDENTITY
    STATUS current
    DESCRIPTION
        "Event FR.22
        An unsupported management information element has been encountered."
    ::= { frEventsGroup 22 }

fr22_type OBJECT-TYPE
    SYNTAX Integer32
    MAX-ACCESS accessible-for-notify
    STATUS current
    DESCRIPTION
        "Parameter 'type' in event FR.22"
    ::= { frEventObjects22 1 }

fr22_ifcname OBJECT-TYPE
    SYNTAX DisplayString
    MAX-ACCESS accessible-for-notify
    STATUS current
    DESCRIPTION
        "Parameter 'ifcname' in event FR.22"
    ::= { frEventObjects22 2 }

frEventObjects23 OBJECT-IDENTITY
    STATUS current
    DESCRIPTION
        "Event FR.23
        An unsupported management message has been encountered."
    ::= { frEventsGroup 23 }

fr23_type OBJECT-TYPE
    SYNTAX Integer32
    MAX-ACCESS accessible-for-notify
    STATUS current
    DESCRIPTION
        "Parameter 'type' in event FR.23"
    ::= { frEventObjects23 1 }

fr23_ifcname OBJECT-TYPE
    SYNTAX DisplayString
    MAX-ACCESS accessible-for-notify
    STATUS current
    DESCRIPTION
        "Parameter 'ifcname' in event FR.23"
    ::= { frEventObjects23 2 }

frEventObjects24 OBJECT-IDENTITY
    STATUS current
    DESCRIPTION
        "Event FR.24
        The LMI signalled present and active a multicast circuit."
    ::= { frEventsGroup 24 }

fr24_circuit OBJECT-TYPE
    SYNTAX Integer32
    MAX-ACCESS accessible-for-notify
    STATUS current
    DESCRIPTION
        "Parameter 'circuit' in event FR.24"
    ::= { frEventObjects24 1 }

fr24_group OBJECT-TYPE
    SYNTAX Integer32
    MAX-ACCESS accessible-for-notify
    STATUS current
    DESCRIPTION
        "Parameter 'group' in event FR.24"
    ::= { frEventObjects24 2 }

fr24_ifcname OBJECT-TYPE
    SYNTAX DisplayString
    MAX-ACCESS accessible-for-notify
    STATUS current
    DESCRIPTION
        "Parameter 'ifcname' in event FR.24"
    ::= { frEventObjects24 3 }

frEventObjects25 OBJECT-IDENTITY
    STATUS current
    DESCRIPTION
        "Event FR.25
        The LMI signalled present and active a multicast circuit."
    ::= { frEventsGroup 25 }

fr25_circuit OBJECT-TYPE
    SYNTAX Integer32
    MAX-ACCESS accessible-for-notify
    STATUS current
    DESCRIPTION
        "Parameter 'circuit' in event FR.25"
    ::= { frEventObjects25 1 }

fr25_group OBJECT-TYPE
    SYNTAX Integer32
    MAX-ACCESS accessible-for-notify
    STATUS current
    DESCRIPTION
        "Parameter 'group' in event FR.25"
    ::= { frEventObjects25 2 }

fr25_ifcname OBJECT-TYPE
    SYNTAX DisplayString
    MAX-ACCESS accessible-for-notify
    STATUS current
    DESCRIPTION
        "Parameter 'ifcname' in event FR.25"
    ::= { frEventObjects25 3 }

frEventObjects26 OBJECT-IDENTITY
    STATUS current
    DESCRIPTION
        "Event FR.26
        An unsupported network layer protocol NLPID has been encountered."
    ::= { frEventsGroup 26 }

fr26_type OBJECT-TYPE
    SYNTAX Integer32
    MAX-ACCESS accessible-for-notify
    STATUS current
    DESCRIPTION
        "Parameter 'type' in event FR.26"
    ::= { frEventObjects26 1 }

fr26_circuit OBJECT-TYPE
    SYNTAX Integer32
    MAX-ACCESS accessible-for-notify
    STATUS current
    DESCRIPTION
        "Parameter 'circuit' in event FR.26"
    ::= { frEventObjects26 2 }

fr26_size OBJECT-TYPE
    SYNTAX Integer32
    MAX-ACCESS accessible-for-notify
    STATUS current
    DESCRIPTION
        "Parameter 'size' in event FR.26"
    ::= { frEventObjects26 3 }

fr26_ifcname OBJECT-TYPE
    SYNTAX DisplayString
    MAX-ACCESS accessible-for-notify
    STATUS current
    DESCRIPTION
        "Parameter 'ifcname' in event FR.26"
    ::= { frEventObjects26 4 }

frEventObjects27 OBJECT-IDENTITY
    STATUS current
    DESCRIPTION
        "Event FR.27
        An unsupported Ethernet type has been encountered."
    ::= { frEventsGroup 27 }

fr27_type OBJECT-TYPE
    SYNTAX Integer32
    MAX-ACCESS accessible-for-notify
    STATUS current
    DESCRIPTION
        "Parameter 'type' in event FR.27"
    ::= { frEventObjects27 1 }

fr27_circuit OBJECT-TYPE
    SYNTAX Integer32
    MAX-ACCESS accessible-for-notify
    STATUS current
    DESCRIPTION
        "Parameter 'circuit' in event FR.27"
    ::= { frEventObjects27 2 }

fr27_size OBJECT-TYPE
    SYNTAX Integer32
    MAX-ACCESS accessible-for-notify
    STATUS current
    DESCRIPTION
        "Parameter 'size' in event FR.27"
    ::= { frEventObjects27 3 }

fr27_ifcname OBJECT-TYPE
    SYNTAX DisplayString
    MAX-ACCESS accessible-for-notify
    STATUS current
    DESCRIPTION
        "Parameter 'ifcname' in event FR.27"
    ::= { frEventObjects27 4 }

frEventObjects28 OBJECT-IDENTITY
    STATUS current
    DESCRIPTION
        "Event FR.28
        The LMI signalled present and active a multicast circuit that is not
        supported on the interface."
    ::= { frEventsGroup 28 }

fr28_circuit OBJECT-TYPE
    SYNTAX Integer32
    MAX-ACCESS accessible-for-notify
    STATUS current
    DESCRIPTION
        "Parameter 'circuit' in event FR.28"
    ::= { frEventObjects28 1 }

fr28_group OBJECT-TYPE
    SYNTAX Integer32
    MAX-ACCESS accessible-for-notify
    STATUS current
    DESCRIPTION
        "Parameter 'group' in event FR.28"
    ::= { frEventObjects28 2 }

fr28_ifcname OBJECT-TYPE
    SYNTAX DisplayString
    MAX-ACCESS accessible-for-notify
    STATUS current
    DESCRIPTION
        "Parameter 'ifcname' in event FR.28"
    ::= { frEventObjects28 3 }

frEventObjects29 OBJECT-IDENTITY
    STATUS current
    DESCRIPTION
        "Event FR.29
        Data has been received on a circuit not configured or learned
        dynamically but not yet active on network."
    ::= { frEventsGroup 29 }

fr29_circuit OBJECT-TYPE
    SYNTAX Integer32
    MAX-ACCESS accessible-for-notify
    STATUS current
    DESCRIPTION
        "Parameter 'circuit' in event FR.29"
    ::= { frEventObjects29 1 }

fr29_ifcname OBJECT-TYPE
    SYNTAX DisplayString
    MAX-ACCESS accessible-for-notify
    STATUS current
    DESCRIPTION
        "Parameter 'ifcname' in event FR.29"
    ::= { frEventObjects29 2 }

frEventObjects30 OBJECT-IDENTITY
    STATUS current
    DESCRIPTION
        "Event FR.30
        A LMI sequence number exchange has been received."
    ::= { frEventsGroup 30 }

fr30_rcvseq OBJECT-TYPE
    SYNTAX Integer32
    MAX-ACCESS accessible-for-notify
    STATUS current
    DESCRIPTION
        "Parameter 'rcvseq' in event FR.30"
    ::= { frEventObjects30 1 }

fr30_xmtseq OBJECT-TYPE
    SYNTAX Integer32
    MAX-ACCESS accessible-for-notify
    STATUS current
    DESCRIPTION
        "Parameter 'xmtseq' in event FR.30"
    ::= { frEventObjects30 2 }

fr30_ifcname OBJECT-TYPE
    SYNTAX DisplayString
    MAX-ACCESS accessible-for-notify
    STATUS current
    DESCRIPTION
        "Parameter 'ifcname' in event FR.30"
    ::= { frEventObjects30 3 }

frEventObjects31 OBJECT-IDENTITY
    STATUS current
    DESCRIPTION
        "Event FR.31
        An LMI unsolicited single status update message has been received."
    ::= { frEventsGroup 31 }

fr31_ifcname OBJECT-TYPE
    SYNTAX DisplayString
    MAX-ACCESS accessible-for-notify
    STATUS current
    DESCRIPTION
        "Parameter 'ifcname' in event FR.31"
    ::= { frEventObjects31 1 }

frEventObjects32 OBJECT-IDENTITY
    STATUS current
    DESCRIPTION
        "Event FR.32
        A frame containing less than the 2 octet minimum address length
        had been encountered."
    ::= { frEventsGroup 32 }

fr32_ifcname OBJECT-TYPE
    SYNTAX DisplayString
    MAX-ACCESS accessible-for-notify
    STATUS current
    DESCRIPTION
        "Parameter 'ifcname' in event FR.32"
    ::= { frEventObjects32 1 }

frEventObjects33 OBJECT-IDENTITY
    STATUS current
    DESCRIPTION
        "Event FR.33
        A frame containing greater than the 2 octet maximum address length
        supported had been encountered.
        Currently, only 2 octet addressing is supported."
    ::= { frEventsGroup 33 }

fr33_ifcname OBJECT-TYPE
    SYNTAX DisplayString
    MAX-ACCESS accessible-for-notify
    STATUS current
    DESCRIPTION
        "Parameter 'ifcname' in event FR.33"
    ::= { frEventObjects33 1 }

frEventObjects34 OBJECT-IDENTITY
    STATUS current
    DESCRIPTION
        "Event FR.34
        The LMI status message contained a reserved management channel address."
    ::= { frEventsGroup 34 }

fr34_circuit OBJECT-TYPE
    SYNTAX Integer32
    MAX-ACCESS accessible-for-notify
    STATUS current
    DESCRIPTION
        "Parameter 'circuit' in event FR.34"
    ::= { frEventObjects34 1 }

fr34_ifcname OBJECT-TYPE
    SYNTAX DisplayString
    MAX-ACCESS accessible-for-notify
    STATUS current
    DESCRIPTION
        "Parameter 'ifcname' in event FR.34"
    ::= { frEventObjects34 2 }

frEventObjects35 OBJECT-IDENTITY
    STATUS current
    DESCRIPTION
        "Event FR.35
        An unsupported link layer control frame encountered."
    ::= { frEventsGroup 35 }

fr35_type OBJECT-TYPE
    SYNTAX Integer32
    MAX-ACCESS accessible-for-notify
    STATUS current
    DESCRIPTION
        "Parameter 'type' in event FR.35"
    ::= { frEventObjects35 1 }

fr35_circuit OBJECT-TYPE
    SYNTAX Integer32
    MAX-ACCESS accessible-for-notify
    STATUS current
    DESCRIPTION
        "Parameter 'circuit' in event FR.35"
    ::= { frEventObjects35 2 }

fr35_ifcname OBJECT-TYPE
    SYNTAX DisplayString
    MAX-ACCESS accessible-for-notify
    STATUS current
    DESCRIPTION
        "Parameter 'ifcname' in event FR.35"
    ::= { frEventObjects35 3 }

frEventObjects36 OBJECT-IDENTITY
    STATUS current
    DESCRIPTION
        "Event FR.36
        An unsupported network layer protocol descriptor has been encountered."
    ::= { frEventsGroup 36 }

fr36_type OBJECT-TYPE
    SYNTAX Integer32
    MAX-ACCESS accessible-for-notify
    STATUS current
    DESCRIPTION
        "Parameter 'type' in event FR.36"
    ::= { frEventObjects36 1 }

fr36_ifcname OBJECT-TYPE
    SYNTAX DisplayString
    MAX-ACCESS accessible-for-notify
    STATUS current
    DESCRIPTION
        "Parameter 'ifcname' in event FR.36"
    ::= { frEventObjects36 2 }

frEventObjects37 OBJECT-IDENTITY
    STATUS current
    DESCRIPTION
        "Event FR.37
        An unsupported network layer call reference field has been encountered."
    ::= { frEventsGroup 37 }

fr37_ifcname OBJECT-TYPE
    SYNTAX DisplayString
    MAX-ACCESS accessible-for-notify
    STATUS current
    DESCRIPTION
        "Parameter 'ifcname' in event FR.37"
    ::= { frEventObjects37 1 }

frEventObjects38 OBJECT-IDENTITY
    STATUS current
    DESCRIPTION
        "Event FR.38
        The received ANSI management frame did not include required
        locking shift information element."
    ::= { frEventsGroup 38 }

fr38_ifcname OBJECT-TYPE
    SYNTAX DisplayString
    MAX-ACCESS accessible-for-notify
    STATUS current
    DESCRIPTION
        "Parameter 'ifcname' in event FR.38"
    ::= { frEventObjects38 1 }

frEventObjects39 OBJECT-IDENTITY
    STATUS current
    DESCRIPTION
        "Event FR.39
        The received management frame information element was incorrectly
        formated."
    ::= { frEventsGroup 39 }

fr39_ifcname OBJECT-TYPE
    SYNTAX DisplayString
    MAX-ACCESS accessible-for-notify
    STATUS current
    DESCRIPTION
        "Parameter 'ifcname' in event FR.39"
    ::= { frEventObjects39 1 }

frEventObjects40 OBJECT-IDENTITY
    STATUS current
    DESCRIPTION
        "Event FR.40
        An incorrect LMI receive sequence number has been received."
    ::= { frEventsGroup 40 }

fr40_rcvseq OBJECT-TYPE
    SYNTAX Integer32
    MAX-ACCESS accessible-for-notify
    STATUS current
    DESCRIPTION
        "Parameter 'rcvseq' in event FR.40"
    ::= { frEventObjects40 1 }

fr40_xmtseq OBJECT-TYPE
    SYNTAX Integer32
    MAX-ACCESS accessible-for-notify
    STATUS current
    DESCRIPTION
        "Parameter 'xmtseq' in event FR.40"
    ::= { frEventObjects40 2 }

fr40_ifcname OBJECT-TYPE
    SYNTAX DisplayString
    MAX-ACCESS accessible-for-notify
    STATUS current
    DESCRIPTION
        "Parameter 'ifcname' in event FR.40"
    ::= { frEventObjects40 3 }

frEventObjects41 OBJECT-IDENTITY
    STATUS current
    DESCRIPTION
        "Event FR.41
        The LMI failed to signal the mentioned circuit is last network status
        update message.
        Circuit assumed removed from network."
    ::= { frEventsGroup 41 }

fr41_circuit OBJECT-TYPE
    SYNTAX Integer32
    MAX-ACCESS accessible-for-notify
    STATUS current
    DESCRIPTION
        "Parameter 'circuit' in event FR.41"
    ::= { frEventObjects41 1 }

fr41_ifcname OBJECT-TYPE
    SYNTAX DisplayString
    MAX-ACCESS accessible-for-notify
    STATUS current
    DESCRIPTION
        "Parameter 'ifcname' in event FR.41"
    ::= { frEventObjects41 2 }

frEventObjects42 OBJECT-IDENTITY
    STATUS current
    DESCRIPTION
        "Event FR.42
        The circuit is now experiencing congestion in the inbound direction."
    ::= { frEventsGroup 42 }

fr42_circuit OBJECT-TYPE
    SYNTAX Integer32
    MAX-ACCESS accessible-for-notify
    STATUS current
    DESCRIPTION
        "Parameter 'circuit' in event FR.42"
    ::= { frEventObjects42 1 }

fr42_ifcname OBJECT-TYPE
    SYNTAX DisplayString
    MAX-ACCESS accessible-for-notify
    STATUS current
    DESCRIPTION
        "Parameter 'ifcname' in event FR.42"
    ::= { frEventObjects42 2 }

frEventObjects43 OBJECT-IDENTITY
    STATUS current
    DESCRIPTION
        "Event FR.43
        The address header on received management frame had BECN, FECN,
        DE or CR bits set."
    ::= { frEventsGroup 43 }

fr43_ifcname OBJECT-TYPE
    SYNTAX DisplayString
    MAX-ACCESS accessible-for-notify
    STATUS current
    DESCRIPTION
        "Parameter 'ifcname' in event FR.43"
    ::= { frEventObjects43 1 }

frEventObjects44 OBJECT-IDENTITY
    STATUS current
    DESCRIPTION
        "Event FR.44
        LMI Link Integrity Verification message was received from the network
        without the router polling for it."
    ::= { frEventsGroup 44 }

fr44_ifcname OBJECT-TYPE
    SYNTAX DisplayString
    MAX-ACCESS accessible-for-notify
    STATUS current
    DESCRIPTION
        "Parameter 'ifcname' in event FR.44"
    ::= { frEventObjects44 1 }

frEventObjects45 OBJECT-IDENTITY
    STATUS current
    DESCRIPTION
        "Event FR.45
        LMI Full Status message was received from the network without the
        router polling for it."
    ::= { frEventsGroup 45 }

fr45_ifcname OBJECT-TYPE
    SYNTAX DisplayString
    MAX-ACCESS accessible-for-notify
    STATUS current
    DESCRIPTION
        "Parameter 'ifcname' in event FR.45"
    ::= { frEventObjects45 1 }

frEventObjects46 OBJECT-IDENTITY
    STATUS current
    DESCRIPTION
        "Event FR.46
        A frame was received of a bridge type defined in RFC 1490.
        However, since bridging has not been enabled on this circuit, frame
        is being discarded."
    ::= { frEventsGroup 46 }

fr46_circuit OBJECT-TYPE
    SYNTAX Integer32
    MAX-ACCESS accessible-for-notify
    STATUS current
    DESCRIPTION
        "Parameter 'circuit' in event FR.46"
    ::= { frEventObjects46 1 }

fr46_ifcname OBJECT-TYPE
    SYNTAX DisplayString
    MAX-ACCESS accessible-for-notify
    STATUS current
    DESCRIPTION
        "Parameter 'ifcname' in event FR.46"
    ::= { frEventObjects46 2 }

frEventObjects47 OBJECT-IDENTITY
    STATUS current
    DESCRIPTION
        "Event FR.47
        A bridge frame is being discarded as a bridge port is not in
        forwarding state."
    ::= { frEventsGroup 47 }

fr47_circuit OBJECT-TYPE
    SYNTAX Integer32
    MAX-ACCESS accessible-for-notify
    STATUS current
    DESCRIPTION
        "Parameter 'circuit' in event FR.47"
    ::= { frEventObjects47 1 }

fr47_ifcname OBJECT-TYPE
    SYNTAX DisplayString
    MAX-ACCESS accessible-for-notify
    STATUS current
    DESCRIPTION
        "Parameter 'ifcname' in event FR.47"
    ::= { frEventObjects47 2 }

frEventObjects48 OBJECT-IDENTITY
    STATUS current
    DESCRIPTION
        "Event FR.48
        A bridged frame has been received and is being discarded due to mismatch
        in the frame type versus the bridge port behavior."
    ::= { frEventsGroup 48 }

fr48_source_mac OBJECT-TYPE
    SYNTAX DisplayString
    MAX-ACCESS accessible-for-notify
    STATUS current
    DESCRIPTION
        "Parameter 'source_mac' in event FR.48"
    ::= { frEventObjects48 1 }

fr48_dest_mac OBJECT-TYPE
    SYNTAX DisplayString
    MAX-ACCESS accessible-for-notify
    STATUS current
    DESCRIPTION
        "Parameter 'dest_mac' in event FR.48"
    ::= { frEventObjects48 2 }

fr48_circuit OBJECT-TYPE
    SYNTAX Integer32
    MAX-ACCESS accessible-for-notify
    STATUS current
    DESCRIPTION
        "Parameter 'circuit' in event FR.48"
    ::= { frEventObjects48 3 }

fr48_ifcname OBJECT-TYPE
    SYNTAX DisplayString
    MAX-ACCESS accessible-for-notify
    STATUS current
    DESCRIPTION
        "Parameter 'ifcname' in event FR.48"
    ::= { frEventObjects48 4 }

frEventObjects49 OBJECT-IDENTITY
    STATUS current
    DESCRIPTION
        "Event FR.49
        An unsupported bridge frame type has been encountered."
    ::= { frEventsGroup 49 }

fr49_type OBJECT-TYPE
    SYNTAX Integer32
    MAX-ACCESS accessible-for-notify
    STATUS current
    DESCRIPTION
        "Parameter 'type' in event FR.49"
    ::= { frEventObjects49 1 }

fr49_circuit OBJECT-TYPE
    SYNTAX Integer32
    MAX-ACCESS accessible-for-notify
    STATUS current
    DESCRIPTION
        "Parameter 'circuit' in event FR.49"
    ::= { frEventObjects49 2 }

fr49_ifcname OBJECT-TYPE
    SYNTAX DisplayString
    MAX-ACCESS accessible-for-notify
    STATUS current
    DESCRIPTION
        "Parameter 'ifcname' in event FR.49"
    ::= { frEventObjects49 3 }

frEventObjects50 OBJECT-IDENTITY
    STATUS current
    DESCRIPTION
        "Event FR.50
        An unrecognized outgoing bridge frame type. Bridge has asked the
        Frame Relay interface to send out a frame whose type cannot be
        translated into encapsulation defined in RFC 1490."
    ::= { frEventsGroup 50 }

fr50_type OBJECT-TYPE
    SYNTAX Integer32
    MAX-ACCESS accessible-for-notify
    STATUS current
    DESCRIPTION
        "Parameter 'type' in event FR.50"
    ::= { frEventObjects50 1 }

fr50_circuit OBJECT-TYPE
    SYNTAX Integer32
    MAX-ACCESS accessible-for-notify
    STATUS current
    DESCRIPTION
        "Parameter 'circuit' in event FR.50"
    ::= { frEventObjects50 2 }

fr50_ifcname OBJECT-TYPE
    SYNTAX DisplayString
    MAX-ACCESS accessible-for-notify
    STATUS current
    DESCRIPTION
        "Parameter 'ifcname' in event FR.50"
    ::= { frEventObjects50 3 }

frEventObjects51 OBJECT-IDENTITY
    STATUS current
    DESCRIPTION
        "Event FR.51
        A protocol frame has been discarded because it could not be queued
        for transmission."
    ::= { frEventsGroup 51 }

fr51_circuit OBJECT-TYPE
    SYNTAX Integer32
    MAX-ACCESS accessible-for-notify
    STATUS current
    DESCRIPTION
        "Parameter 'circuit' in event FR.51"
    ::= { frEventObjects51 1 }

fr51_protocol OBJECT-TYPE
    SYNTAX DisplayString
    MAX-ACCESS accessible-for-notify
    STATUS current
    DESCRIPTION
        "Parameter 'protocol' in event FR.51"
    ::= { frEventObjects51 2 }

fr51_ifcname OBJECT-TYPE
    SYNTAX DisplayString
    MAX-ACCESS accessible-for-notify
    STATUS current
    DESCRIPTION
        "Parameter 'ifcname' in event FR.51"
    ::= { frEventObjects51 3 }

frEventObjects52 OBJECT-IDENTITY
    STATUS current
    DESCRIPTION
        "Event FR.52
        An LMI send sequence number of 0 has been received."
    ::= { frEventsGroup 52 }

fr52_sndseq OBJECT-TYPE
    SYNTAX Integer32
    MAX-ACCESS accessible-for-notify
    STATUS current
    DESCRIPTION
        "Parameter 'sndseq' in event FR.52"
    ::= { frEventObjects52 1 }

fr52_ifcname OBJECT-TYPE
    SYNTAX DisplayString
    MAX-ACCESS accessible-for-notify
    STATUS current
    DESCRIPTION
        "Parameter 'ifcname' in event FR.52"
    ::= { frEventObjects52 2 }

frEventObjects53 OBJECT-IDENTITY
    STATUS current
    DESCRIPTION
        "Event FR.53
        A FRF.12 fragment is processed and a event is reported."
    ::= { frEventsGroup 53 }

fr53_message OBJECT-TYPE
    SYNTAX DisplayString
    MAX-ACCESS accessible-for-notify
    STATUS current
    DESCRIPTION
        "Parameter 'message' in event FR.53"
    ::= { frEventObjects53 1 }

fr53_header OBJECT-TYPE
    SYNTAX Integer32
    MAX-ACCESS accessible-for-notify
    STATUS current
    DESCRIPTION
        "Parameter 'header' in event FR.53"
    ::= { frEventObjects53 2 }

fr53_circuit OBJECT-TYPE
    SYNTAX Integer32
    MAX-ACCESS accessible-for-notify
    STATUS current
    DESCRIPTION
        "Parameter 'circuit' in event FR.53"
    ::= { frEventObjects53 3 }

fr53_size OBJECT-TYPE
    SYNTAX Integer32
    MAX-ACCESS accessible-for-notify
    STATUS current
    DESCRIPTION
        "Parameter 'size' in event FR.53"
    ::= { frEventObjects53 4 }

fr53_ifcname OBJECT-TYPE
    SYNTAX DisplayString
    MAX-ACCESS accessible-for-notify
    STATUS current
    DESCRIPTION
        "Parameter 'ifcname' in event FR.53"
    ::= { frEventObjects53 5 }


frNotification1 NOTIFICATION-TYPE
    OBJECTS { 
              fr1_circuit, 
              fr1_protocol,
              fr1_size,
              fr1_ifcname,
              fr1_buffer 
            }
    STATUS current
    DESCRIPTION
        "Notification of Event FR.1

        Message: 'Frame received, PVC = $1 protocol type = $2 size $3 bytes, on interface $4HexadecimalData: $5'

        Parameters list:
              $1: fr1_circuit
              $2: fr1_protocol
              $3: fr1_size
              $4: fr1_ifcname
              $5: fr1_buffer

        A frame had been received on the FR interface."
    ::= { frNotificationsPrefix 1 }

frNotification2 NOTIFICATION-TYPE
    OBJECTS { 
              fr2_circuit, 
              fr2_protocol,
              fr2_size,
              fr2_ifcname,
              fr2_buffer 
            }
    STATUS current
    DESCRIPTION
        "Notification of Event FR.2

        Message: 'Frame transmitted PVC = $1 protocol type = $2 size $3 bytes, on interface $4HexadecimalData: $5'

        Parameters list:
              $1: fr2_circuit
              $2: fr2_protocol
              $3: fr2_size
              $4: fr2_ifcname
              $5: fr2_buffer

        A frame had been transmitted on the FR interface."
    ::= { frNotificationsPrefix 2 }

frNotification3 NOTIFICATION-TYPE
    OBJECTS { 
              fr3_circuit, 
              fr3_protocol,
              fr3_ifcname 
            }
    STATUS current
    DESCRIPTION
        "Notification of Event FR.3

        Message: 'Transmit frame discarded PVC = $1 protocol type = $2, on interface $3'

        Parameters list:
              $1: fr3_circuit
              $2: fr3_protocol
              $3: fr3_ifcname

        A protocol frame had been discarded due to the PVC congested condition."
    ::= { frNotificationsPrefix 3 }

frNotification4 NOTIFICATION-TYPE
    OBJECTS { 
              fr4_circuit, 
              fr4_ifcname 
            }
    STATUS current
    DESCRIPTION
        "Notification of Event FR.4

        Message: 'Circuit outbound congestion PVC = $1, on interface $2'

        Parameters list:
              $1: fr4_circuit
              $2: fr4_ifcname

        The circuit is now experiencing congestion in the outbound direction."
    ::= { frNotificationsPrefix 4 }

frNotification5 NOTIFICATION-TYPE
    OBJECTS { 
              fr5_circuit, 
              fr5_ifcname 
            }
    STATUS current
    DESCRIPTION
        "Notification of Event FR.5

        Message: 'Circuit outbound uncongested PVC = $1, on interface $2'

        Parameters list:
              $1: fr5_circuit
              $2: fr5_ifcname

        The circuit is now not experiencing congestion in the outbound
        direction."
    ::= { frNotificationsPrefix 5 }

frNotification6 NOTIFICATION-TYPE
    OBJECTS { 
              fr6_circuit, 
              fr6_ifcname 
            }
    STATUS current
    DESCRIPTION
        "Notification of Event FR.6

        Message: 'Circuit enters active state PVC = $1, on interface $2'

        Parameters list:
              $1: fr6_circuit
              $2: fr6_ifcname

        The circuit enters the active state."
    ::= { frNotificationsPrefix 6 }

frNotification7 NOTIFICATION-TYPE
    OBJECTS { 
              fr7_circuit, 
              fr7_ifcname 
            }
    STATUS current
    DESCRIPTION
        "Notification of Event FR.7

        Message: 'An orphan circuit not statically configured has joined the network PVC = $1, on interface $2'

        Parameters list:
              $1: fr7_circuit
              $2: fr7_ifcname

        The LMI signalled present and active a circuit which had not been
        statically configured."
    ::= { frNotificationsPrefix 7 }

frNotification8 NOTIFICATION-TYPE
    OBJECTS { 
              fr8_circuit, 
              fr8_ifcname 
            }
    STATUS current
    DESCRIPTION
        "Notification of Event FR.8

        Message: 'Circuit enters inactive state PVC = $1, on interface $2'

        Parameters list:
              $1: fr8_circuit
              $2: fr8_ifcname

        The circuit enters the inactive state."
    ::= { frNotificationsPrefix 8 }

frNotification9 NOTIFICATION-TYPE
    OBJECTS { 
              fr9_circuit, 
              fr9_ifcname 
            }
    STATUS current
    DESCRIPTION
        "Notification of Event FR.9

        Message: 'Circuit is unavailable PVC = $1, on interface $2'

        Parameters list:
              $1: fr9_circuit
              $2: fr9_ifcname

        The circuit is no longer available on the network."
    ::= { frNotificationsPrefix 9 }

frNotification10 NOTIFICATION-TYPE
    OBJECTS { 
              fr10_circuit, 
              fr10_ifcname 
            }
    STATUS current
    DESCRIPTION
        "Notification of Event FR.10

        Message: 'Circuit is available PVC = $1, on interface $2'

        Parameters list:
              $1: fr10_circuit
              $2: fr10_ifcname

        The circuit is now available on the network."
    ::= { frNotificationsPrefix 10 }

frNotification11 NOTIFICATION-TYPE
    OBJECTS { 
              fr11_rcvseq, 
              fr11_xmtseq,
              fr11_ifcname 
            }
    STATUS current
    DESCRIPTION
        "Notification of Event FR.11

        Message: 'LMI sequence number exchange requested, last received sequence = $1, current transmit sequence = $2, on interface $3'

        Parameters list:
              $1: fr11_rcvseq
              $2: fr11_xmtseq
              $3: fr11_ifcname

        A LMI sequence number exchange has been requested."
    ::= { frNotificationsPrefix 11 }

frNotification12 NOTIFICATION-TYPE
    OBJECTS { 
              fr12_ifcname 
            }
    STATUS current
    DESCRIPTION
        "Notification of Event FR.12

        Message: 'LMI Status Enquiry requested on interface $1'

        Parameters list:
              $1: fr12_ifcname

        A LMI full Status Enquiry has been requested."
    ::= { frNotificationsPrefix 12 }

frNotification13 NOTIFICATION-TYPE
    OBJECTS { 
              fr13_ifcname 
            }
    STATUS current
    DESCRIPTION
        "Notification of Event FR.13

        Message: 'LMI solicited Status Enquiry response had been received on interface $1'

        Parameters list:
              $1: fr13_ifcname

        A solicited LMI Status Enquiry response has been received."
    ::= { frNotificationsPrefix 13 }

frNotification14 NOTIFICATION-TYPE
    OBJECTS { 
              fr14_ifcname 
            }
    STATUS current
    DESCRIPTION
        "Notification of Event FR.14

        Message: 'LMI Full Status Enquiry response had been received on interface $1'

        Parameters list:
              $1: fr14_ifcname

        A LMI full Status Enquiry response has been received."
    ::= { frNotificationsPrefix 14 }

frNotification15 NOTIFICATION-TYPE
    OBJECTS { 
              fr15_dcd, 
              fr15_cts,
              fr15_ifcname 
            }
    STATUS current
    DESCRIPTION
        "Notification of Event FR.15

        Message: 'Modem status changed DCD = $1 CTS = $2 on interface $3'

        Parameters list:
              $1: fr15_dcd
              $2: fr15_cts
              $3: fr15_ifcname

        A modem status change has occurred. The present state is described."
    ::= { frNotificationsPrefix 15 }

frNotification16 NOTIFICATION-TYPE
    OBJECTS { 
              fr16_circuit, 
              fr16_protocol,
              fr16_ifcname 
            }
    STATUS current
    DESCRIPTION
        "Notification of Event FR.16

        Message: 'Multicast frame transmitted PVC = $1 protocol type = $2, on interface $3'

        Parameters list:
              $1: fr16_circuit
              $2: fr16_protocol
              $3: fr16_ifcname

        A multicast frame had been transmitted on the FR interface."
    ::= { frNotificationsPrefix 16 }

frNotification17 NOTIFICATION-TYPE
    OBJECTS { 
              fr17_circuit, 
              fr17_ifcname 
            }
    STATUS current
    DESCRIPTION
        "Notification of Event FR.17

        Message: 'Circuit remains congested in the outbound direction PVC = $1, on interface $2'

        Parameters list:
              $1: fr17_circuit
              $2: fr17_ifcname

        The circuit is remaining in the outbound congested state toward
        the network."
    ::= { frNotificationsPrefix 17 }

frNotification18 NOTIFICATION-TYPE
    OBJECTS { 
              fr18_circuit, 
              fr18_protocol,
              fr18_ifcname 
            }
    STATUS current
    DESCRIPTION
        "Notification of Event FR.18

        Message: 'CIR exceeded, transmit frame discarded PVC = $1 protocol type = $2, on interface $3'

        Parameters list:
              $1: fr18_circuit
              $2: fr18_protocol
              $3: fr18_ifcname

        A protocol frame had been discarded due to the PVC exceeding the CIR on
        the circuit."
    ::= { frNotificationsPrefix 18 }

frNotification19 NOTIFICATION-TYPE
    OBJECTS { 
              fr19_circuit, 
              fr19_ifcname 
            }
    STATUS current
    DESCRIPTION
        "Notification of Event FR.19

        Message: 'A disallowed orphan circuit not statically configured has been ignored PVC = $1, on interface $2'

        Parameters list:
              $1: fr19_circuit
              $2: fr19_ifcname

        The LMI signalled present and active a circuit which had not been
        statically configured or allowed."
    ::= { frNotificationsPrefix 19 }

frNotification20 NOTIFICATION-TYPE
    OBJECTS { 
              fr20_circuit, 
              fr20_ifcname 
            }
    STATUS current
    DESCRIPTION
        "Notification of Event FR.20

        Message: 'The total circuits allowed has been exceeded, an orphan circuit has been ignored PVC = $1, on interface $2'

        Parameters list:
              $1: fr20_circuit
              $2: fr20_ifcname

        The LMI signalled present and active a circuit which cannot join
        the interface, maximum circuits have been exceeded."
    ::= { frNotificationsPrefix 20 }

frNotification21 NOTIFICATION-TYPE
    OBJECTS { 
              fr21_circuit, 
              fr21_ifcname 
            }
    STATUS current
    DESCRIPTION
        "Notification of Event FR.21

        Message: 'No available memory for orphan circuit, the circuit has been ignored PVC = $1, on interface $2'

        Parameters list:
              $1: fr21_circuit
              $2: fr21_ifcname

        The LMI signalled present and active a circuit which cannot join
        the interface, memory is unavailable."
    ::= { frNotificationsPrefix 21 }

frNotification22 NOTIFICATION-TYPE
    OBJECTS { 
              fr22_type, 
              fr22_ifcname 
            }
    STATUS current
    DESCRIPTION
        "Notification of Event FR.22

        Message: 'Unsupported LMI information element, type = $1 on interface $2'

        Parameters list:
              $1: fr22_type
              $2: fr22_ifcname

        An unsupported management information element has been encountered."
    ::= { frNotificationsPrefix 22 }

frNotification23 NOTIFICATION-TYPE
    OBJECTS { 
              fr23_type, 
              fr23_ifcname 
            }
    STATUS current
    DESCRIPTION
        "Notification of Event FR.23

        Message: 'Unsupported LMI message type, type encountered = $1, on interface $2'

        Parameters list:
              $1: fr23_type
              $2: fr23_ifcname

        An unsupported management message has been encountered."
    ::= { frNotificationsPrefix 23 }

frNotification24 NOTIFICATION-TYPE
    OBJECTS { 
              fr24_circuit, 
              fr24_group,
              fr24_ifcname 
            }
    STATUS current
    DESCRIPTION
        "Notification of Event FR.24

        Message: 'A multicast circuit has joined the network PVC = $1, in multicast group = $2 on interface $3'

        Parameters list:
              $1: fr24_circuit
              $2: fr24_group
              $3: fr24_ifcname

        The LMI signalled present and active a multicast circuit."
    ::= { frNotificationsPrefix 24 }

frNotification25 NOTIFICATION-TYPE
    OBJECTS { 
              fr25_circuit, 
              fr25_group,
              fr25_ifcname 
            }
    STATUS current
    DESCRIPTION
        "Notification of Event FR.25

        Message: 'An multicast circuit has left the network PVC = $1, from multicast group = $2 on interface $3'

        Parameters list:
              $1: fr25_circuit
              $2: fr25_group
              $3: fr25_ifcname

        The LMI signalled present and active a multicast circuit."
    ::= { frNotificationsPrefix 25 }

frNotification26 NOTIFICATION-TYPE
    OBJECTS { 
              fr26_type, 
              fr26_circuit,
              fr26_size,
              fr26_ifcname 
            }
    STATUS current
    DESCRIPTION
        "Notification of Event FR.26

        Message: 'Unsupported Network Layer Protocol ID, type = $1 from PVC = $2 size $3 bytes on interface $4'

        Parameters list:
              $1: fr26_type
              $2: fr26_circuit
              $3: fr26_size
              $4: fr26_ifcname

        An unsupported network layer protocol NLPID has been encountered."
    ::= { frNotificationsPrefix 26 }

frNotification27 NOTIFICATION-TYPE
    OBJECTS { 
              fr27_type, 
              fr27_circuit,
              fr27_size,
              fr27_ifcname 
            }
    STATUS current
    DESCRIPTION
        "Notification of Event FR.27

        Message: 'Unsupported ethernet type, type = $1 from PVC = $2 size $3 bytes on interface $4'

        Parameters list:
              $1: fr27_type
              $2: fr27_circuit
              $3: fr27_size
              $4: fr27_ifcname

        An unsupported Ethernet type has been encountered."
    ::= { frNotificationsPrefix 27 }

frNotification28 NOTIFICATION-TYPE
    OBJECTS { 
              fr28_circuit, 
              fr28_group,
              fr28_ifcname 
            }
    STATUS current
    DESCRIPTION
        "Notification of Event FR.28

        Message: 'An unsupported multicast circuit has been ignored, PVC = $1, in multicast group = $2 on interface $3'

        Parameters list:
              $1: fr28_circuit
              $2: fr28_group
              $3: fr28_ifcname

        The LMI signalled present and active a multicast circuit that is not
        supported on the interface."
    ::= { frNotificationsPrefix 28 }

frNotification29 NOTIFICATION-TYPE
    OBJECTS { 
              fr29_circuit, 
              fr29_ifcname 
            }
    STATUS current
    DESCRIPTION
        "Notification of Event FR.29

        Message: 'Data received on invalid or nonconfigured circuit, PVC = $1 on interface $2'

        Parameters list:
              $1: fr29_circuit
              $2: fr29_ifcname

        Data has been received on a circuit not configured or learned
        dynamically but not yet active on network."
    ::= { frNotificationsPrefix 29 }

frNotification30 NOTIFICATION-TYPE
    OBJECTS { 
              fr30_rcvseq, 
              fr30_xmtseq,
              fr30_ifcname 
            }
    STATUS current
    DESCRIPTION
        "Notification of Event FR.30

        Message: 'LMI sequence number exchange received, last received sequence = $1 current transmit sequence = $2, on interface $3'

        Parameters list:
              $1: fr30_rcvseq
              $2: fr30_xmtseq
              $3: fr30_ifcname

        A LMI sequence number exchange has been received."
    ::= { frNotificationsPrefix 30 }

frNotification31 NOTIFICATION-TYPE
    OBJECTS { 
              fr31_ifcname 
            }
    STATUS current
    DESCRIPTION
        "Notification of Event FR.31

        Message: 'LMI unsolicited single Status Update had been received on interface $1'

        Parameters list:
              $1: fr31_ifcname

        An LMI unsolicited single status update message has been received."
    ::= { frNotificationsPrefix 31 }

frNotification32 NOTIFICATION-TYPE
    OBJECTS { 
              fr32_ifcname 
            }
    STATUS current
    DESCRIPTION
        "Notification of Event FR.32

        Message: 'Circuit address length less than the 2 octet minimum received on interface $1'

        Parameters list:
              $1: fr32_ifcname

        A frame containing less than the 2 octet minimum address length
        had been encountered."
    ::= { frNotificationsPrefix 32 }

frNotification33 NOTIFICATION-TYPE
    OBJECTS { 
              fr33_ifcname 
            }
    STATUS current
    DESCRIPTION
        "Notification of Event FR.33

        Message: 'Circuit address length greater than the 2 octet maximum received on interface $1'

        Parameters list:
              $1: fr33_ifcname

        A frame containing greater than the 2 octet maximum address length
        supported had been encountered.
        Currently, only 2 octet addressing is supported."
    ::= { frNotificationsPrefix 33 }

frNotification34 NOTIFICATION-TYPE
    OBJECTS { 
              fr34_circuit, 
              fr34_ifcname 
            }
    STATUS current
    DESCRIPTION
        "Notification of Event FR.34

        Message: 'Circuit status update message contained a reserved management channel address, PVC = $1, on interface $2'

        Parameters list:
              $1: fr34_circuit
              $2: fr34_ifcname

        The LMI status message contained a reserved management channel address."
    ::= { frNotificationsPrefix 34 }

frNotification35 NOTIFICATION-TYPE
    OBJECTS { 
              fr35_type, 
              fr35_circuit,
              fr35_ifcname 
            }
    STATUS current
    DESCRIPTION
        "Notification of Event FR.35

        Message: 'Unsupported Link Layer Control frame encountered, type = $1 from PVC = $2 on interface $3'

        Parameters list:
              $1: fr35_type
              $2: fr35_circuit
              $3: fr35_ifcname

        An unsupported link layer control frame encountered."
    ::= { frNotificationsPrefix 35 }

frNotification36 NOTIFICATION-TYPE
    OBJECTS { 
              fr36_type, 
              fr36_ifcname 
            }
    STATUS current
    DESCRIPTION
        "Notification of Event FR.36

        Message: 'Unsupported layer management protocol descriptor encountered, type = $1 on interface $2'

        Parameters list:
              $1: fr36_type
              $2: fr36_ifcname

        An unsupported network layer protocol descriptor has been encountered."
    ::= { frNotificationsPrefix 36 }

frNotification37 NOTIFICATION-TYPE
    OBJECTS { 
              fr37_ifcname 
            }
    STATUS current
    DESCRIPTION
        "Notification of Event FR.37

        Message: 'Unsupported layer management call reference encountered on interface $1'

        Parameters list:
              $1: fr37_ifcname

        An unsupported network layer call reference field has been encountered."
    ::= { frNotificationsPrefix 37 }

frNotification38 NOTIFICATION-TYPE
    OBJECTS { 
              fr38_ifcname 
            }
    STATUS current
    DESCRIPTION
        "Notification of Event FR.38

        Message: 'No lock shift encountered in received ANSI LMI message on interface $1'

        Parameters list:
              $1: fr38_ifcname

        The received ANSI management frame did not include required
        locking shift information element."
    ::= { frNotificationsPrefix 38 }

frNotification39 NOTIFICATION-TYPE
    OBJECTS { 
              fr39_ifcname 
            }
    STATUS current
    DESCRIPTION
        "Notification of Event FR.39

        Message: 'Incorrect formated information element encountered on interface $1'

        Parameters list:
              $1: fr39_ifcname

        The received management frame information element was incorrectly
        formated."
    ::= { frNotificationsPrefix 39 }

frNotification40 NOTIFICATION-TYPE
    OBJECTS { 
              fr40_rcvseq, 
              fr40_xmtseq,
              fr40_ifcname 
            }
    STATUS current
    DESCRIPTION
        "Notification of Event FR.40

        Message: 'LMI receive sequence number in error, receive sequence = $1 expected sequence = $2, on interface $3'

        Parameters list:
              $1: fr40_rcvseq
              $2: fr40_xmtseq
              $3: fr40_ifcname

        An incorrect LMI receive sequence number has been received."
    ::= { frNotificationsPrefix 40 }

frNotification41 NOTIFICATION-TYPE
    OBJECTS { 
              fr41_circuit, 
              fr41_ifcname 
            }
    STATUS current
    DESCRIPTION
        "Notification of Event FR.41

        Message: 'An circuit has been removed from the network PVC = $1, on interface $2'

        Parameters list:
              $1: fr41_circuit
              $2: fr41_ifcname

        The LMI failed to signal the mentioned circuit is last network status
        update message.
        Circuit assumed removed from network."
    ::= { frNotificationsPrefix 41 }

frNotification42 NOTIFICATION-TYPE
    OBJECTS { 
              fr42_circuit, 
              fr42_ifcname 
            }
    STATUS current
    DESCRIPTION
        "Notification of Event FR.42

        Message: 'Circuit inbound congestion PVC = $1, on interface $2'

        Parameters list:
              $1: fr42_circuit
              $2: fr42_ifcname

        The circuit is now experiencing congestion in the inbound direction."
    ::= { frNotificationsPrefix 42 }

frNotification43 NOTIFICATION-TYPE
    OBJECTS { 
              fr43_ifcname 
            }
    STATUS current
    DESCRIPTION
        "Notification of Event FR.43

        Message: 'Incorrect formatted address header for LMI packet encountered on interface $1'

        Parameters list:
              $1: fr43_ifcname

        The address header on received management frame had BECN, FECN,
        DE or CR bits set."
    ::= { frNotificationsPrefix 43 }

frNotification44 NOTIFICATION-TYPE
    OBJECTS { 
              fr44_ifcname 
            }
    STATUS current
    DESCRIPTION
        "Notification of Event FR.44

        Message: 'Unsolicited LMI Link Integrity Verification received on interface $1'

        Parameters list:
              $1: fr44_ifcname

        LMI Link Integrity Verification message was received from the network
        without the router polling for it."
    ::= { frNotificationsPrefix 44 }

frNotification45 NOTIFICATION-TYPE
    OBJECTS { 
              fr45_ifcname 
            }
    STATUS current
    DESCRIPTION
        "Notification of Event FR.45

        Message: 'Unsolicited LMI FULL STATUS response received on interface $1'

        Parameters list:
              $1: fr45_ifcname

        LMI Full Status message was received from the network without the
        router polling for it."
    ::= { frNotificationsPrefix 45 }

frNotification46 NOTIFICATION-TYPE
    OBJECTS { 
              fr46_circuit, 
              fr46_ifcname 
            }
    STATUS current
    DESCRIPTION
        "Notification of Event FR.46

        Message: 'DROP: Bridging not enabled on PVC=$1, on interface $2'

        Parameters list:
              $1: fr46_circuit
              $2: fr46_ifcname

        A frame was received of a bridge type defined in RFC 1490.
        However, since bridging has not been enabled on this circuit, frame
        is being discarded."
    ::= { frNotificationsPrefix 46 }

frNotification47 NOTIFICATION-TYPE
    OBJECTS { 
              fr47_circuit, 
              fr47_ifcname 
            }
    STATUS current
    DESCRIPTION
        "Notification of Event FR.47

        Message: 'DROP: Bridge port not forwarding on PVC=$1, on interface $2'

        Parameters list:
              $1: fr47_circuit
              $2: fr47_ifcname

        A bridge frame is being discarded as a bridge port is not in
        forwarding state."
    ::= { frNotificationsPrefix 47 }

frNotification48 NOTIFICATION-TYPE
    OBJECTS { 
              fr48_source_mac, 
              fr48_dest_mac,
              fr48_circuit,
              fr48_ifcname 
            }
    STATUS current
    DESCRIPTION
        "Notification of Event FR.48

        Message: 'DROP: $1->$2, Frame to bridge port behavior mismatch on PVC=$3, on interface $4'

        Parameters list:
              $1: fr48_source_mac
              $2: fr48_dest_mac
              $3: fr48_circuit
              $4: fr48_ifcname

        A bridged frame has been received and is being discarded due to mismatch
        in the frame type versus the bridge port behavior."
    ::= { frNotificationsPrefix 48 }

frNotification49 NOTIFICATION-TYPE
    OBJECTS { 
              fr49_type, 
              fr49_circuit,
              fr49_ifcname 
            }
    STATUS current
    DESCRIPTION
        "Notification of Event FR.49

        Message: 'Unsupported bridge frame type = $1 from PVC = $2 on interface $3'

        Parameters list:
              $1: fr49_type
              $2: fr49_circuit
              $3: fr49_ifcname

        An unsupported bridge frame type has been encountered."
    ::= { frNotificationsPrefix 49 }

frNotification50 NOTIFICATION-TYPE
    OBJECTS { 
              fr50_type, 
              fr50_circuit,
              fr50_ifcname 
            }
    STATUS current
    DESCRIPTION
        "Notification of Event FR.50

        Message: 'Unrecognized outgoing bridge frame type = $1 on PVC = $2 on interface $3'

        Parameters list:
              $1: fr50_type
              $2: fr50_circuit
              $3: fr50_ifcname

        An unrecognized outgoing bridge frame type. Bridge has asked the
        Frame Relay interface to send out a frame whose type cannot be
        translated into encapsulation defined in RFC 1490."
    ::= { frNotificationsPrefix 50 }

frNotification51 NOTIFICATION-TYPE
    OBJECTS { 
              fr51_circuit, 
              fr51_protocol,
              fr51_ifcname 
            }
    STATUS current
    DESCRIPTION
        "Notification of Event FR.51

        Message: 'Transmit frame discarded PVC = $1 protocol type = $2, on interface $3'

        Parameters list:
              $1: fr51_circuit
              $2: fr51_protocol
              $3: fr51_ifcname

        A protocol frame has been discarded because it could not be queued
        for transmission."
    ::= { frNotificationsPrefix 51 }

frNotification52 NOTIFICATION-TYPE
    OBJECTS { 
              fr52_sndseq, 
              fr52_ifcname 
            }
    STATUS current
    DESCRIPTION
        "Notification of Event FR.52

        Message: 'LMI send sequence number in error, sequence = $1, on interface $2'

        Parameters list:
              $1: fr52_sndseq
              $2: fr52_ifcname

        An LMI send sequence number of 0 has been received."
    ::= { frNotificationsPrefix 52 }

frNotification53 NOTIFICATION-TYPE
    OBJECTS { 
              fr53_message, 
              fr53_header,
              fr53_circuit,
              fr53_size,
              fr53_ifcname 
            }
    STATUS current
    DESCRIPTION
        "Notification of Event FR.53

        Message: 'FRF.12 $1 header $2 on PVC = $3 size $4 bytes, on interface $5'

        Parameters list:
              $1: fr53_message
              $2: fr53_header
              $3: fr53_circuit
              $4: fr53_size
              $5: fr53_ifcname

        A FRF.12 fragment is processed and a event is reported."
    ::= { frNotificationsPrefix 53 }


END
