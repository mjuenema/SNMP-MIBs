-- file automatically created


TELDAT-TRAP-AT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


atTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the AT event subsystem."
    REVISION "201401200930Z"
    DESCRIPTION "Initial implementation"
        ::= { telEventTraps 149 }


atEventsGroup	OBJECT IDENTIFIER	::= { atTrapsMIB 1 }

atNotifications	OBJECT IDENTIFIER	::= { atTrapsMIB 2 }
atNotificationsPrefix	OBJECT IDENTIFIER	::= { atNotifications 0 }

atEventObjects1 OBJECT-IDENTITY
    STATUS current
    DESCRIPTION
        "Event AT.1
        Selftest completed successfully when modem is detected and initialized."
    ::= { atEventsGroup 1 }

at1_ifcname OBJECT-TYPE
    SYNTAX DisplayString
    MAX-ACCESS accessible-for-notify
    STATUS current
    DESCRIPTION
        "Parameter 'ifcname' in event AT.1"
    ::= { atEventObjects1 1 }

atEventObjects2 OBJECT-IDENTITY
    STATUS current
    DESCRIPTION
        "Event AT.2
        Maintenance failure. Modem not detected."
    ::= { atEventsGroup 2 }

at2_ifcname OBJECT-TYPE
    SYNTAX DisplayString
    MAX-ACCESS accessible-for-notify
    STATUS current
    DESCRIPTION
        "Parameter 'ifcname' in event AT.2"
    ::= { atEventObjects2 1 }

atEventObjects3 OBJECT-IDENTITY
    STATUS current
    DESCRIPTION
        "Event AT.3
        An IP packet has been received with a CRC error."
    ::= { atEventsGroup 3 }

at3_frame_size OBJECT-TYPE
    SYNTAX Integer32
    MAX-ACCESS accessible-for-notify
    STATUS current
    DESCRIPTION
        "Parameter 'frame_size' in event AT.3"
    ::= { atEventObjects3 1 }

at3_ifcname OBJECT-TYPE
    SYNTAX DisplayString
    MAX-ACCESS accessible-for-notify
    STATUS current
    DESCRIPTION
        "Parameter 'ifcname' in event AT.3"
    ::= { atEventObjects3 2 }

atEventObjects4 OBJECT-IDENTITY
    STATUS current
    DESCRIPTION
        "Event AT.4
        End flag is not found on received frame."
    ::= { atEventsGroup 4 }

at4_frame_size OBJECT-TYPE
    SYNTAX Integer32
    MAX-ACCESS accessible-for-notify
    STATUS current
    DESCRIPTION
        "Parameter 'frame_size' in event AT.4"
    ::= { atEventObjects4 1 }

at4_ifcname OBJECT-TYPE
    SYNTAX DisplayString
    MAX-ACCESS accessible-for-notify
    STATUS current
    DESCRIPTION
        "Parameter 'ifcname' in event AT.4"
    ::= { atEventObjects4 2 }

atEventObjects5 OBJECT-IDENTITY
    STATUS current
    DESCRIPTION
        "Event AT.5
        Incorrect packet format: last character of frame is escape character."
    ::= { atEventsGroup 5 }

at5_frame_size OBJECT-TYPE
    SYNTAX Integer32
    MAX-ACCESS accessible-for-notify
    STATUS current
    DESCRIPTION
        "Parameter 'frame_size' in event AT.5"
    ::= { atEventObjects5 1 }

at5_ifcname OBJECT-TYPE
    SYNTAX DisplayString
    MAX-ACCESS accessible-for-notify
    STATUS current
    DESCRIPTION
        "Parameter 'ifcname' in event AT.5"
    ::= { atEventObjects5 2 }

atEventObjects6 OBJECT-IDENTITY
    STATUS current
    DESCRIPTION
        "Event AT.6
        A call to the indicated destination address has been initiated."
    ::= { atEventsGroup 6 }

at6_call_address OBJECT-TYPE
    SYNTAX DisplayString
    MAX-ACCESS accessible-for-notify
    STATUS current
    DESCRIPTION
        "Parameter 'call_address' in event AT.6"
    ::= { atEventObjects6 1 }

at6_ifcname OBJECT-TYPE
    SYNTAX DisplayString
    MAX-ACCESS accessible-for-notify
    STATUS current
    DESCRIPTION
        "Parameter 'ifcname' in event AT.6"
    ::= { atEventObjects6 2 }

atEventObjects7 OBJECT-IDENTITY
    STATUS current
    DESCRIPTION
        "Event AT.7
        The call to the indicated destination address has been completed
        successfully. The call is established."
    ::= { atEventsGroup 7 }

at7_destination_address OBJECT-TYPE
    SYNTAX DisplayString
    MAX-ACCESS accessible-for-notify
    STATUS current
    DESCRIPTION
        "Parameter 'destination_address' in event AT.7"
    ::= { atEventObjects7 1 }

at7_ifcname OBJECT-TYPE
    SYNTAX DisplayString
    MAX-ACCESS accessible-for-notify
    STATUS current
    DESCRIPTION
        "Parameter 'ifcname' in event AT.7"
    ::= { atEventObjects7 2 }

atEventObjects8 OBJECT-IDENTITY
    STATUS current
    DESCRIPTION
        "Event AT.8
        The call to the indicated destination address could not be completed
        successfully because there is no answer from the remote end. The call
        is not established."
    ::= { atEventsGroup 8 }

at8_destination_address OBJECT-TYPE
    SYNTAX DisplayString
    MAX-ACCESS accessible-for-notify
    STATUS current
    DESCRIPTION
        "Parameter 'destination_address' in event AT.8"
    ::= { atEventObjects8 1 }

at8_ifcname OBJECT-TYPE
    SYNTAX DisplayString
    MAX-ACCESS accessible-for-notify
    STATUS current
    DESCRIPTION
        "Parameter 'ifcname' in event AT.8"
    ::= { atEventObjects8 2 }

atEventObjects9 OBJECT-IDENTITY
    STATUS current
    DESCRIPTION
        "Event AT.9
        The call to the indicated destination address is released."
    ::= { atEventsGroup 9 }

at9_destination_address OBJECT-TYPE
    SYNTAX DisplayString
    MAX-ACCESS accessible-for-notify
    STATUS current
    DESCRIPTION
        "Parameter 'destination_address' in event AT.9"
    ::= { atEventObjects9 1 }

at9_ifcname OBJECT-TYPE
    SYNTAX DisplayString
    MAX-ACCESS accessible-for-notify
    STATUS current
    DESCRIPTION
        "Parameter 'ifcname' in event AT.9"
    ::= { atEventObjects9 2 }

atEventObjects10 OBJECT-IDENTITY
    STATUS current
    DESCRIPTION
        "Event AT.10
        Incoming call established successfully."
    ::= { atEventsGroup 10 }

at10_ifcname OBJECT-TYPE
    SYNTAX DisplayString
    MAX-ACCESS accessible-for-notify
    STATUS current
    DESCRIPTION
        "Parameter 'ifcname' in event AT.10"
    ::= { atEventObjects10 1 }

atEventObjects11 OBJECT-IDENTITY
    STATUS current
    DESCRIPTION
        "Event AT.11
        The indicated AT command is not recognized by the modem
        (it returns ERROR)."
    ::= { atEventsGroup 11 }

at11_command OBJECT-TYPE
    SYNTAX DisplayString
    MAX-ACCESS accessible-for-notify
    STATUS current
    DESCRIPTION
        "Parameter 'command' in event AT.11"
    ::= { atEventObjects11 1 }

at11_ifcname OBJECT-TYPE
    SYNTAX DisplayString
    MAX-ACCESS accessible-for-notify
    STATUS current
    DESCRIPTION
        "Parameter 'ifcname' in event AT.11"
    ::= { atEventObjects11 2 }

atEventObjects12 OBJECT-IDENTITY
    STATUS current
    DESCRIPTION
        "Event AT.12
        The modem has given an unknown answer to the indicated AT command."
    ::= { atEventsGroup 12 }

at12_command OBJECT-TYPE
    SYNTAX DisplayString
    MAX-ACCESS accessible-for-notify
    STATUS current
    DESCRIPTION
        "Parameter 'command' in event AT.12"
    ::= { atEventObjects12 1 }

at12_ifcname OBJECT-TYPE
    SYNTAX DisplayString
    MAX-ACCESS accessible-for-notify
    STATUS current
    DESCRIPTION
        "Parameter 'ifcname' in event AT.12"
    ::= { atEventObjects12 2 }

atEventObjects13 OBJECT-IDENTITY
    STATUS current
    DESCRIPTION
        "Event AT.13
        The modem has not answered to the indicated AT command."
    ::= { atEventsGroup 13 }

at13_command OBJECT-TYPE
    SYNTAX DisplayString
    MAX-ACCESS accessible-for-notify
    STATUS current
    DESCRIPTION
        "Parameter 'command' in event AT.13"
    ::= { atEventObjects13 1 }

at13_ifcname OBJECT-TYPE
    SYNTAX DisplayString
    MAX-ACCESS accessible-for-notify
    STATUS current
    DESCRIPTION
        "Parameter 'ifcname' in event AT.13"
    ::= { atEventObjects13 2 }

atEventObjects14 OBJECT-IDENTITY
    STATUS current
    DESCRIPTION
        "Event AT.14
        The modem has not answered to the indicated AT command. Initialization
        process is retried."
    ::= { atEventsGroup 14 }

at14_ifcname OBJECT-TYPE
    SYNTAX DisplayString
    MAX-ACCESS accessible-for-notify
    STATUS current
    DESCRIPTION
        "Parameter 'ifcname' in event AT.14"
    ::= { atEventObjects14 1 }

atEventObjects15 OBJECT-IDENTITY
    STATUS current
    DESCRIPTION
        "Event AT.15
        Modem autodetection on indicated interface is being tried."
    ::= { atEventsGroup 15 }

at15_ifcname OBJECT-TYPE
    SYNTAX DisplayString
    MAX-ACCESS accessible-for-notify
    STATUS current
    DESCRIPTION
        "Parameter 'ifcname' in event AT.15"
    ::= { atEventObjects15 1 }

atEventObjects16 OBJECT-IDENTITY
    STATUS current
    DESCRIPTION
        "Event AT.16
        Modem autodetection has been completed successfully. Initialization
        string for the detected modem or standard initialization string if
        the modem is unknown is going to be used next."
    ::= { atEventsGroup 16 }

at16_modem_type OBJECT-TYPE
    SYNTAX DisplayString
    MAX-ACCESS accessible-for-notify
    STATUS current
    DESCRIPTION
        "Parameter 'modem_type' in event AT.16"
    ::= { atEventObjects16 1 }

at16_ifcname OBJECT-TYPE
    SYNTAX DisplayString
    MAX-ACCESS accessible-for-notify
    STATUS current
    DESCRIPTION
        "Parameter 'ifcname' in event AT.16"
    ::= { atEventObjects16 2 }

atEventObjects17 OBJECT-IDENTITY
    STATUS current
    DESCRIPTION
        "Event AT.17
        Modem signals were lost during initialization. Modem must have switched
        off or must have been disconnected of serial line.
        Selftest is restarted from the beginning."
    ::= { atEventsGroup 17 }

at17_ifcname OBJECT-TYPE
    SYNTAX DisplayString
    MAX-ACCESS accessible-for-notify
    STATUS current
    DESCRIPTION
        "Parameter 'ifcname' in event AT.17"
    ::= { atEventObjects17 1 }

atEventObjects18 OBJECT-IDENTITY
    STATUS current
    DESCRIPTION
        "Event AT.18
        The modem returned an error making call because the line is busy or
        not connected."
    ::= { atEventsGroup 18 }

at18_ifcname OBJECT-TYPE
    SYNTAX DisplayString
    MAX-ACCESS accessible-for-notify
    STATUS current
    DESCRIPTION
        "Parameter 'ifcname' in event AT.18"
    ::= { atEventObjects18 1 }

atEventObjects19 OBJECT-IDENTITY
    STATUS current
    DESCRIPTION
        "Event AT.19
        The modem returned an error making call because the remote end is busy
        (it is already making a call)."
    ::= { atEventsGroup 19 }

at19_ifcname OBJECT-TYPE
    SYNTAX DisplayString
    MAX-ACCESS accessible-for-notify
    STATUS current
    DESCRIPTION
        "Parameter 'ifcname' in event AT.19"
    ::= { atEventObjects19 1 }

atEventObjects20 OBJECT-IDENTITY
    STATUS current
    DESCRIPTION
        "Event AT.20
        Generic event. Used for ring pattern detection."
    ::= { atEventsGroup 20 }

at20_string OBJECT-TYPE
    SYNTAX DisplayString
    MAX-ACCESS accessible-for-notify
    STATUS current
    DESCRIPTION
        "Parameter 'string' in event AT.20"
    ::= { atEventObjects20 1 }

at20_ifcname OBJECT-TYPE
    SYNTAX DisplayString
    MAX-ACCESS accessible-for-notify
    STATUS current
    DESCRIPTION
        "Parameter 'ifcname' in event AT.20"
    ::= { atEventObjects20 2 }


atNotification1 NOTIFICATION-TYPE
    OBJECTS { 
              at1_ifcname 
            }
    STATUS current
    DESCRIPTION
        "Notification of Event AT.1

        Message: 'Modem initialized sucessfully on interface $1'

        Parameters list:
              $1: at1_ifcname

        Selftest completed successfully when modem is detected and initialized."
    ::= { atNotificationsPrefix 1 }

atNotification2 NOTIFICATION-TYPE
    OBJECTS { 
              at2_ifcname 
            }
    STATUS current
    DESCRIPTION
        "Notification of Event AT.2

        Message: 'Maintenance failure on interface $1'

        Parameters list:
              $1: at2_ifcname

        Maintenance failure. Modem not detected."
    ::= { atNotificationsPrefix 2 }

atNotification3 NOTIFICATION-TYPE
    OBJECTS { 
              at3_frame_size, 
              at3_ifcname 
            }
    STATUS current
    DESCRIPTION
        "Notification of Event AT.3

        Message: 'Received packed with bad crc, frame size $1, on interface $2'

        Parameters list:
              $1: at3_frame_size
              $2: at3_ifcname

        An IP packet has been received with a CRC error."
    ::= { atNotificationsPrefix 3 }

atNotification4 NOTIFICATION-TYPE
    OBJECTS { 
              at4_frame_size, 
              at4_ifcname 
            }
    STATUS current
    DESCRIPTION
        "Notification of Event AT.4

        Message: 'Not received end flag on frame with size $1, on interface $2'

        Parameters list:
              $1: at4_frame_size
              $2: at4_ifcname

        End flag is not found on received frame."
    ::= { atNotificationsPrefix 4 }

atNotification5 NOTIFICATION-TYPE
    OBJECTS { 
              at5_frame_size, 
              at5_ifcname 
            }
    STATUS current
    DESCRIPTION
        "Notification of Event AT.5

        Message: 'Frame ended with escape character with size $1, on interface $2'

        Parameters list:
              $1: at5_frame_size
              $2: at5_ifcname

        Incorrect packet format: last character of frame is escape character."
    ::= { atNotificationsPrefix 5 }

atNotification6 NOTIFICATION-TYPE
    OBJECTS { 
              at6_call_address, 
              at6_ifcname 
            }
    STATUS current
    DESCRIPTION
        "Notification of Event AT.6

        Message: 'Dial Request Call, Destination address = $1, on interface $2'

        Parameters list:
              $1: at6_call_address
              $2: at6_ifcname

        A call to the indicated destination address has been initiated."
    ::= { atNotificationsPrefix 6 }

atNotification7 NOTIFICATION-TYPE
    OBJECTS { 
              at7_destination_address, 
              at7_ifcname 
            }
    STATUS current
    DESCRIPTION
        "Notification of Event AT.7

        Message: 'Out Call established to $1, on interface $2'

        Parameters list:
              $1: at7_destination_address
              $2: at7_ifcname

        The call to the indicated destination address has been completed
        successfully. The call is established."
    ::= { atNotificationsPrefix 7 }

atNotification8 NOTIFICATION-TYPE
    OBJECTS { 
              at8_destination_address, 
              at8_ifcname 
            }
    STATUS current
    DESCRIPTION
        "Notification of Event AT.8

        Message: 'Call not established to $1, no answer, on interface $2'

        Parameters list:
              $1: at8_destination_address
              $2: at8_ifcname

        The call to the indicated destination address could not be completed
        successfully because there is no answer from the remote end. The call
        is not established."
    ::= { atNotificationsPrefix 8 }

atNotification9 NOTIFICATION-TYPE
    OBJECTS { 
              at9_destination_address, 
              at9_ifcname 
            }
    STATUS current
    DESCRIPTION
        "Notification of Event AT.9

        Message: 'Out Call released to $1, on interface $2'

        Parameters list:
              $1: at9_destination_address
              $2: at9_ifcname

        The call to the indicated destination address is released."
    ::= { atNotificationsPrefix 9 }

atNotification10 NOTIFICATION-TYPE
    OBJECTS { 
              at10_ifcname 
            }
    STATUS current
    DESCRIPTION
        "Notification of Event AT.10

        Message: 'Input Call established on interface $1'

        Parameters list:
              $1: at10_ifcname

        Incoming call established successfully."
    ::= { atNotificationsPrefix 10 }

atNotification11 NOTIFICATION-TYPE
    OBJECTS { 
              at11_command, 
              at11_ifcname 
            }
    STATUS current
    DESCRIPTION
        "Notification of Event AT.11

        Message: 'Error in AT command $1 interface $2'

        Parameters list:
              $1: at11_command
              $2: at11_ifcname

        The indicated AT command is not recognized by the modem
        (it returns ERROR)."
    ::= { atNotificationsPrefix 11 }

atNotification12 NOTIFICATION-TYPE
    OBJECTS { 
              at12_command, 
              at12_ifcname 
            }
    STATUS current
    DESCRIPTION
        "Notification of Event AT.12

        Message: 'Unknown answer to AT command $1 interface $2'

        Parameters list:
              $1: at12_command
              $2: at12_ifcname

        The modem has given an unknown answer to the indicated AT command."
    ::= { atNotificationsPrefix 12 }

atNotification13 NOTIFICATION-TYPE
    OBJECTS { 
              at13_command, 
              at13_ifcname 
            }
    STATUS current
    DESCRIPTION
        "Notification of Event AT.13

        Message: 'No answer to AT command $1 interface $2'

        Parameters list:
              $1: at13_command
              $2: at13_ifcname

        The modem has not answered to the indicated AT command."
    ::= { atNotificationsPrefix 13 }

atNotification14 NOTIFICATION-TYPE
    OBJECTS { 
              at14_ifcname 
            }
    STATUS current
    DESCRIPTION
        "Notification of Event AT.14

        Message: 'No response to AT commands. Retrying... intf $1'

        Parameters list:
              $1: at14_ifcname

        The modem has not answered to the indicated AT command. Initialization
        process is retried."
    ::= { atNotificationsPrefix 14 }

atNotification15 NOTIFICATION-TYPE
    OBJECTS { 
              at15_ifcname 
            }
    STATUS current
    DESCRIPTION
        "Notification of Event AT.15

        Message: 'Trying modem autodetection on intf $1'

        Parameters list:
              $1: at15_ifcname

        Modem autodetection on indicated interface is being tried."
    ::= { atNotificationsPrefix 15 }

atNotification16 NOTIFICATION-TYPE
    OBJECTS { 
              at16_modem_type, 
              at16_ifcname 
            }
    STATUS current
    DESCRIPTION
        "Notification of Event AT.16

        Message: 'Autodetection completed. $1 modem intf $2'

        Parameters list:
              $1: at16_modem_type
              $2: at16_ifcname

        Modem autodetection has been completed successfully. Initialization
        string for the detected modem or standard initialization string if
        the modem is unknown is going to be used next."
    ::= { atNotificationsPrefix 16 }

atNotification17 NOTIFICATION-TYPE
    OBJECTS { 
              at17_ifcname 
            }
    STATUS current
    DESCRIPTION
        "Notification of Event AT.17

        Message: 'Modem signals lost. Modem off or disconnected intf $1'

        Parameters list:
              $1: at17_ifcname

        Modem signals were lost during initialization. Modem must have switched
        off or must have been disconnected of serial line.
        Selftest is restarted from the beginning."
    ::= { atNotificationsPrefix 17 }

atNotification18 NOTIFICATION-TYPE
    OBJECTS { 
              at18_ifcname 
            }
    STATUS current
    DESCRIPTION
        "Notification of Event AT.18

        Message: 'Error making call. Line busy (NO DIALTONE) intf $1'

        Parameters list:
              $1: at18_ifcname

        The modem returned an error making call because the line is busy or
        not connected."
    ::= { atNotificationsPrefix 18 }

atNotification19 NOTIFICATION-TYPE
    OBJECTS { 
              at19_ifcname 
            }
    STATUS current
    DESCRIPTION
        "Notification of Event AT.19

        Message: 'Error making call. Remote end busy (BUSY) intf $1'

        Parameters list:
              $1: at19_ifcname

        The modem returned an error making call because the remote end is busy
        (it is already making a call)."
    ::= { atNotificationsPrefix 19 }

atNotification20 NOTIFICATION-TYPE
    OBJECTS { 
              at20_string, 
              at20_ifcname 
            }
    STATUS current
    DESCRIPTION
        "Notification of Event AT.20

        Message: '$1 intf $2'

        Parameters list:
              $1: at20_string
              $2: at20_ifcname

        Generic event. Used for ring pattern detection."
    ::= { atNotificationsPrefix 20 }


END
