CAMEDIATIONMANAGER-ENTERPRISES-HUAWEI-MIB DEFINITIONS ::= BEGIN
 
--
-- Huawei infrastructure of the CA MEDIATION MANAGER enterprise MIB tree
--
 
IMPORTS
    MODULE-IDENTITY, caMMEnterprises FROM CAMEDIATIONMANAGER-ENTERPRISES-MIB;
 
caMMHuawei MODULE-IDENTITY
    LAST-UPDATED "201201300000Z"
    ORGANIZATION "www.CA.com"
    CONTACT-INFO   
                 "postal:   One CA Plaza
                        Islandia, NY 11749
                        USA
          email:    support@ca.com"
    DESCRIPTION
                "Hauwei infrastructure of the CA Mediation Manager enterprise MIB tree"
    REVISION     "201201300000Z"
    DESCRIPTION
                "First draft"
    ::= { caMMEnterprises 2011}

-- caMMHuaweiPTN OBJECT IDENTIFIER ::= { caMMHauwei 1 }
-- caMMHuaweiSingleCloud OBJECT IDENTIFIER ::= { caMMHauwei 2 }


 
--
 
END
