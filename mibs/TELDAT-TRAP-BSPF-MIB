-- file automatically created


TELDAT-TRAP-BSPF-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


bspfTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the BSPF event subsystem."
    REVISION "201401200930Z"
    DESCRIPTION "Initial implementation"
        ::= { telEventTraps 194 }


bspfEventsGroup	OBJECT IDENTIFIER	::= { bspfTrapsMIB 1 }

bspfNotifications	OBJECT IDENTIFIER	::= { bspfTrapsMIB 2 }
bspfNotificationsPrefix	OBJECT IDENTIFIER	::= { bspfNotifications 0 }

bspfEventObjects1 OBJECT-IDENTITY
    STATUS current
    DESCRIPTION
        "Event BSPF.1
        Bridge has detected an incoming packet whose destination matches a
        spoofed MAC address."
    ::= { bspfEventsGroup 1 }

bspf1_src_mac OBJECT-TYPE
    SYNTAX DisplayString
    MAX-ACCESS accessible-for-notify
    STATUS current
    DESCRIPTION
        "Parameter 'src_mac' in event BSPF.1"
    ::= { bspfEventObjects1 1 }

bspf1_src_port OBJECT-TYPE
    SYNTAX Integer32
    MAX-ACCESS accessible-for-notify
    STATUS current
    DESCRIPTION
        "Parameter 'src_port' in event BSPF.1"
    ::= { bspfEventObjects1 2 }

bspf1_dst_mac OBJECT-TYPE
    SYNTAX DisplayString
    MAX-ACCESS accessible-for-notify
    STATUS current
    DESCRIPTION
        "Parameter 'dst_mac' in event BSPF.1"
    ::= { bspfEventObjects1 3 }

bspf1_dst_port OBJECT-TYPE
    SYNTAX Integer32
    MAX-ACCESS accessible-for-notify
    STATUS current
    DESCRIPTION
        "Parameter 'dst_port' in event BSPF.1"
    ::= { bspfEventObjects1 4 }

bspf1_protocol OBJECT-TYPE
    SYNTAX Integer32
    MAX-ACCESS accessible-for-notify
    STATUS current
    DESCRIPTION
        "Parameter 'protocol' in event BSPF.1"
    ::= { bspfEventObjects1 5 }

bspf1_interface OBJECT-TYPE
    SYNTAX DisplayString
    MAX-ACCESS accessible-for-notify
    STATUS current
    DESCRIPTION
        "Parameter 'interface' in event BSPF.1"
    ::= { bspfEventObjects1 6 }

bspfEventObjects2 OBJECT-IDENTITY
    STATUS current
    DESCRIPTION
        "Event BSPF.2
        Bridge has intercepted an incoming packet destined for a spoofed MAC.
        If its protocol is IP, the destination ip address does not match the
        one	spoofed. If it is ARP, the operation code must be request."
    ::= { bspfEventsGroup 2 }

bspf2_spoof_addr OBJECT-TYPE
    SYNTAX IpAddress
    MAX-ACCESS accessible-for-notify
    STATUS current
    DESCRIPTION
        "Parameter 'spoof_addr' in event BSPF.2"
    ::= { bspfEventObjects2 1 }

bspf2_protocol OBJECT-TYPE
    SYNTAX Integer32
    MAX-ACCESS accessible-for-notify
    STATUS current
    DESCRIPTION
        "Parameter 'protocol' in event BSPF.2"
    ::= { bspfEventObjects2 2 }

bspf2_interface OBJECT-TYPE
    SYNTAX DisplayString
    MAX-ACCESS accessible-for-notify
    STATUS current
    DESCRIPTION
        "Parameter 'interface' in event BSPF.2"
    ::= { bspfEventObjects2 3 }

bspfEventObjects3 OBJECT-IDENTITY
    STATUS current
    DESCRIPTION
        "Event BSPF.3
        The MAC address associated with a spoofed address has been updated."
    ::= { bspfEventsGroup 3 }

bspf3_mac_addr OBJECT-TYPE
    SYNTAX DisplayString
    MAX-ACCESS accessible-for-notify
    STATUS current
    DESCRIPTION
        "Parameter 'mac_addr' in event BSPF.3"
    ::= { bspfEventObjects3 1 }

bspf3_spoof_addr OBJECT-TYPE
    SYNTAX IpAddress
    MAX-ACCESS accessible-for-notify
    STATUS current
    DESCRIPTION
        "Parameter 'spoof_addr' in event BSPF.3"
    ::= { bspfEventObjects3 2 }

bspf3_interface OBJECT-TYPE
    SYNTAX DisplayString
    MAX-ACCESS accessible-for-notify
    STATUS current
    DESCRIPTION
        "Parameter 'interface' in event BSPF.3"
    ::= { bspfEventObjects3 3 }

bspfEventObjects4 OBJECT-IDENTITY
    STATUS current
    DESCRIPTION
        "Event BSPF.4
        The port associated with a spoofed address has been updated."
    ::= { bspfEventsGroup 4 }

bspf4_port OBJECT-TYPE
    SYNTAX Integer32
    MAX-ACCESS accessible-for-notify
    STATUS current
    DESCRIPTION
        "Parameter 'port' in event BSPF.4"
    ::= { bspfEventObjects4 1 }

bspf4_spoof_addr OBJECT-TYPE
    SYNTAX IpAddress
    MAX-ACCESS accessible-for-notify
    STATUS current
    DESCRIPTION
        "Parameter 'spoof_addr' in event BSPF.4"
    ::= { bspfEventObjects4 2 }

bspf4_interface OBJECT-TYPE
    SYNTAX DisplayString
    MAX-ACCESS accessible-for-notify
    STATUS current
    DESCRIPTION
        "Parameter 'interface' in event BSPF.4"
    ::= { bspfEventObjects4 3 }

bspfEventObjects5 OBJECT-IDENTITY
    STATUS current
    DESCRIPTION
        "Event BSPF.5
        Bridge-spoofing sends an ARP packet periodically requesting the MAC
        address associated with every spoofed address configured."
    ::= { bspfEventsGroup 5 }

bspf5_spoof_addr OBJECT-TYPE
    SYNTAX IpAddress
    MAX-ACCESS accessible-for-notify
    STATUS current
    DESCRIPTION
        "Parameter 'spoof_addr' in event BSPF.5"
    ::= { bspfEventObjects5 1 }

bspf5_interface OBJECT-TYPE
    SYNTAX DisplayString
    MAX-ACCESS accessible-for-notify
    STATUS current
    DESCRIPTION
        "Parameter 'interface' in event BSPF.5"
    ::= { bspfEventObjects5 2 }

bspfEventObjects6 OBJECT-IDENTITY
    STATUS current
    DESCRIPTION
        "Event BSPF.6
        Bridge-spoofing broadcasts an ARP gratuitous packet after changing
        the MAC address associated with a configured spoofed address."
    ::= { bspfEventsGroup 6 }

bspf6_mac_addr OBJECT-TYPE
    SYNTAX DisplayString
    MAX-ACCESS accessible-for-notify
    STATUS current
    DESCRIPTION
        "Parameter 'mac_addr' in event BSPF.6"
    ::= { bspfEventObjects6 1 }

bspf6_spoof_addr OBJECT-TYPE
    SYNTAX IpAddress
    MAX-ACCESS accessible-for-notify
    STATUS current
    DESCRIPTION
        "Parameter 'spoof_addr' in event BSPF.6"
    ::= { bspfEventObjects6 2 }

bspf6_interface OBJECT-TYPE
    SYNTAX DisplayString
    MAX-ACCESS accessible-for-notify
    STATUS current
    DESCRIPTION
        "Parameter 'interface' in event BSPF.6"
    ::= { bspfEventObjects6 3 }

bspfEventObjects7 OBJECT-IDENTITY
    STATUS current
    DESCRIPTION
        "Event BSPF.7
        Received an ARP request packet asking for a spoofed configured address."
    ::= { bspfEventsGroup 7 }

bspf7_mac_addr OBJECT-TYPE
    SYNTAX DisplayString
    MAX-ACCESS accessible-for-notify
    STATUS current
    DESCRIPTION
        "Parameter 'mac_addr' in event BSPF.7"
    ::= { bspfEventObjects7 1 }

bspf7_spoof_addr OBJECT-TYPE
    SYNTAX IpAddress
    MAX-ACCESS accessible-for-notify
    STATUS current
    DESCRIPTION
        "Parameter 'spoof_addr' in event BSPF.7"
    ::= { bspfEventObjects7 2 }

bspf7_interface OBJECT-TYPE
    SYNTAX DisplayString
    MAX-ACCESS accessible-for-notify
    STATUS current
    DESCRIPTION
        "Parameter 'interface' in event BSPF.7"
    ::= { bspfEventObjects7 3 }

bspfEventObjects8 OBJECT-IDENTITY
    STATUS current
    DESCRIPTION
        "Event BSPF.8
        Sent a reply to an ARP request asking for a spoofed configured address."
    ::= { bspfEventsGroup 8 }

bspf8_spoof_addr OBJECT-TYPE
    SYNTAX IpAddress
    MAX-ACCESS accessible-for-notify
    STATUS current
    DESCRIPTION
        "Parameter 'spoof_addr' in event BSPF.8"
    ::= { bspfEventObjects8 1 }

bspf8_src_mac OBJECT-TYPE
    SYNTAX DisplayString
    MAX-ACCESS accessible-for-notify
    STATUS current
    DESCRIPTION
        "Parameter 'src_mac' in event BSPF.8"
    ::= { bspfEventObjects8 2 }

bspf8_dst_mac OBJECT-TYPE
    SYNTAX DisplayString
    MAX-ACCESS accessible-for-notify
    STATUS current
    DESCRIPTION
        "Parameter 'dst_mac' in event BSPF.8"
    ::= { bspfEventObjects8 3 }

bspf8_interface OBJECT-TYPE
    SYNTAX DisplayString
    MAX-ACCESS accessible-for-notify
    STATUS current
    DESCRIPTION
        "Parameter 'interface' in event BSPF.8"
    ::= { bspfEventObjects8 4 }

bspfEventObjects9 OBJECT-IDENTITY
    STATUS current
    DESCRIPTION
        "Event BSPF.9
        A bridge must be defined before a spoofing ip address can be
        configured."
    ::= { bspfEventsGroup 9 }

bspf9_spoof_addr OBJECT-TYPE
    SYNTAX IpAddress
    MAX-ACCESS accessible-for-notify
    STATUS current
    DESCRIPTION
        "Parameter 'spoof_addr' in event BSPF.9"
    ::= { bspfEventObjects9 1 }

bspf9_interface OBJECT-TYPE
    SYNTAX DisplayString
    MAX-ACCESS accessible-for-notify
    STATUS current
    DESCRIPTION
        "Parameter 'interface' in event BSPF.9"
    ::= { bspfEventObjects9 2 }

bspfEventObjects10 OBJECT-IDENTITY
    STATUS current
    DESCRIPTION
        "Event BSPF.10
        There is no enough free memory to configure a new spoofing ip address."
    ::= { bspfEventsGroup 10 }

bspf10_spoof_addr OBJECT-TYPE
    SYNTAX IpAddress
    MAX-ACCESS accessible-for-notify
    STATUS current
    DESCRIPTION
        "Parameter 'spoof_addr' in event BSPF.10"
    ::= { bspfEventObjects10 1 }

bspf10_interface OBJECT-TYPE
    SYNTAX DisplayString
    MAX-ACCESS accessible-for-notify
    STATUS current
    DESCRIPTION
        "Parameter 'interface' in event BSPF.10"
    ::= { bspfEventObjects10 2 }


bspfNotification1 NOTIFICATION-TYPE
    OBJECTS { 
              bspf1_src_mac, 
              bspf1_src_port,
              bspf1_dst_mac,
              bspf1_dst_port,
              bspf1_protocol,
              bspf1_interface 
            }
    STATUS current
    DESCRIPTION
        "Notification of Event BSPF.1

        Message: 'Packet from $1 port $2 to $3 port $4 protocol 0x$5, interface $6'

        Parameters list:
              $1: bspf1_src_mac
              $2: bspf1_src_port
              $3: bspf1_dst_mac
              $4: bspf1_dst_port
              $5: bspf1_protocol
              $6: bspf1_interface

        Bridge has detected an incoming packet whose destination matches a
        spoofed MAC address."
    ::= { bspfNotificationsPrefix 1 }

bspfNotification2 NOTIFICATION-TYPE
    OBJECTS { 
              bspf2_spoof_addr, 
              bspf2_protocol,
              bspf2_interface 
            }
    STATUS current
    DESCRIPTION
        "Notification of Event BSPF.2

        Message: 'Packet intercepted, spoofed address $1 protocol 0x$2, interface $3'

        Parameters list:
              $1: bspf2_spoof_addr
              $2: bspf2_protocol
              $3: bspf2_interface

        Bridge has intercepted an incoming packet destined for a spoofed MAC.
        If its protocol is IP, the destination ip address does not match the
        one	spoofed. If it is ARP, the operation code must be request."
    ::= { bspfNotificationsPrefix 2 }

bspfNotification3 NOTIFICATION-TYPE
    OBJECTS { 
              bspf3_mac_addr, 
              bspf3_spoof_addr,
              bspf3_interface 
            }
    STATUS current
    DESCRIPTION
        "Notification of Event BSPF.3

        Message: 'New MAC $1 learned, spoofed address $2, interface $3'

        Parameters list:
              $1: bspf3_mac_addr
              $2: bspf3_spoof_addr
              $3: bspf3_interface

        The MAC address associated with a spoofed address has been updated."
    ::= { bspfNotificationsPrefix 3 }

bspfNotification4 NOTIFICATION-TYPE
    OBJECTS { 
              bspf4_port, 
              bspf4_spoof_addr,
              bspf4_interface 
            }
    STATUS current
    DESCRIPTION
        "Notification of Event BSPF.4

        Message: 'New port $1 learned, spoofed address $2, interface $3'

        Parameters list:
              $1: bspf4_port
              $2: bspf4_spoof_addr
              $3: bspf4_interface

        The port associated with a spoofed address has been updated."
    ::= { bspfNotificationsPrefix 4 }

bspfNotification5 NOTIFICATION-TYPE
    OBJECTS { 
              bspf5_spoof_addr, 
              bspf5_interface 
            }
    STATUS current
    DESCRIPTION
        "Notification of Event BSPF.5

        Message: 'Discovering MAC and port associated with spoofed address $1, interface $2'

        Parameters list:
              $1: bspf5_spoof_addr
              $2: bspf5_interface

        Bridge-spoofing sends an ARP packet periodically requesting the MAC
        address associated with every spoofed address configured."
    ::= { bspfNotificationsPrefix 5 }

bspfNotification6 NOTIFICATION-TYPE
    OBJECTS { 
              bspf6_mac_addr, 
              bspf6_spoof_addr,
              bspf6_interface 
            }
    STATUS current
    DESCRIPTION
        "Notification of Event BSPF.6

        Message: 'Broadcasting new MAC $1 associated with spoofed address $2, interface $3'

        Parameters list:
              $1: bspf6_mac_addr
              $2: bspf6_spoof_addr
              $3: bspf6_interface

        Bridge-spoofing broadcasts an ARP gratuitous packet after changing
        the MAC address associated with a configured spoofed address."
    ::= { bspfNotificationsPrefix 6 }

bspfNotification7 NOTIFICATION-TYPE
    OBJECTS { 
              bspf7_mac_addr, 
              bspf7_spoof_addr,
              bspf7_interface 
            }
    STATUS current
    DESCRIPTION
        "Notification of Event BSPF.7

        Message: 'ARP request from MAC $1 for spoofed address $2, interface $3'

        Parameters list:
              $1: bspf7_mac_addr
              $2: bspf7_spoof_addr
              $3: bspf7_interface

        Received an ARP request packet asking for a spoofed configured address."
    ::= { bspfNotificationsPrefix 7 }

bspfNotification8 NOTIFICATION-TYPE
    OBJECTS { 
              bspf8_spoof_addr, 
              bspf8_src_mac,
              bspf8_dst_mac,
              bspf8_interface 
            }
    STATUS current
    DESCRIPTION
        "Notification of Event BSPF.8

        Message: 'ARP reply for address $1 is MAC $2, destination MAC $3, interface $4'

        Parameters list:
              $1: bspf8_spoof_addr
              $2: bspf8_src_mac
              $3: bspf8_dst_mac
              $4: bspf8_interface

        Sent a reply to an ARP request asking for a spoofed configured address."
    ::= { bspfNotificationsPrefix 8 }

bspfNotification9 NOTIFICATION-TYPE
    OBJECTS { 
              bspf9_spoof_addr, 
              bspf9_interface 
            }
    STATUS current
    DESCRIPTION
        "Notification of Event BSPF.9

        Message: 'Error adding address $1, bridge must be enabled, interface $2'

        Parameters list:
              $1: bspf9_spoof_addr
              $2: bspf9_interface

        A bridge must be defined before a spoofing ip address can be
        configured."
    ::= { bspfNotificationsPrefix 9 }

bspfNotification10 NOTIFICATION-TYPE
    OBJECTS { 
              bspf10_spoof_addr, 
              bspf10_interface 
            }
    STATUS current
    DESCRIPTION
        "Notification of Event BSPF.10

        Message: 'Error adding address $1, out of memory, interface $2'

        Parameters list:
              $1: bspf10_spoof_addr
              $2: bspf10_interface

        There is no enough free memory to configure a new spoofing ip address."
    ::= { bspfNotificationsPrefix 10 }


END
