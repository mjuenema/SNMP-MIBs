-- =============================================================================
-- Copyright (c) 2004-2013 Hangzhou H3C Tech. Co., Ltd. All rights reserved.
--
-- Description: The MIB for VSI (Virtual Switch Instance).
-- Reference:
-- Version: V1.1
-- History:
--   V1.0 2009-08-08 Initial version Created by Zhonghua Gao
--   V1.1 2012-11-21 Modified by yanneng, add hh3cVsiSpbIsid,
--               Value 'default(0)' is added for data type 'hh3cVsiMode'
-- =============================================================================
HH3C-VSI-MIB DEFINITIONS ::= BEGIN
IMPORTS
        RowStatus
    FROM SNMPv2-TC
        MODULE-IDENTITY,
        OBJECT-TYPE,
        Integer32,
        Unsigned32
    FROM SNMPv2-SMI
        hh3cCommon
    FROM HH3C-OID-MIB;

-- =============================================================================
-- module identity part
-- =============================================================================
hh3cVsi MODULE-IDENTITY
    LAST-UPDATED
        "200908081000Z"        -- Aug 08, 2009 at 10:00 GMT
    ORGANIZATION
        "Hangzhou H3C Technologies Co., Ltd."
    CONTACT-INFO
        "Platform Team Hangzhou H3C Technologies Co., Ltd.
         Hai-Dian District Beijing P.R. China
         http://www.h3c.com
         Zip:100085"
    DESCRIPTION
        "The MIB for VSI (Virtual Switch Instance)."
    REVISION
        "200908081000Z"   -- Aug 08, 2009 at 10:00 GMT
    DESCRIPTION
        "Initial version."
    ::= { hh3cCommon 105 }

-- =============================================================================
-- object definition begin
-- =============================================================================

hh3cVsiObjects      OBJECT IDENTIFIER ::= { hh3cVsi 1 }

hh3cVsiScalarGroup OBJECT IDENTIFIER ::= { hh3cVsiObjects 1 }

hh3cVsiNextAvailableVsiIndex    OBJECT-TYPE
    SYNTAX      Unsigned32
    MAX-ACCESS  read-only
    STATUS      current
    DESCRIPTION
        "Next available VSI entry index for creating VSI. Its value ranges
        from 0x1 to 0xFFFFFFFF.The invalid value 0xFFFFFFFF indicates that
        no VSI entry can be created."
    ::= { hh3cVsiScalarGroup 1 }

-- =============================================================================
-- hh3cVsiTable Definition
-- =============================================================================
hh3cVsiTable  OBJECT-TYPE
    SYNTAX      SEQUENCE OF Hh3cVsiEntry
    MAX-ACCESS  not-accessible
    STATUS      current
    DESCRIPTION
        "A table for configuring VSI parameters."
    ::= { hh3cVsiObjects 2 }

hh3cVsiEntry  OBJECT-TYPE
    SYNTAX      Hh3cVsiEntry
    MAX-ACCESS  not-accessible
    STATUS      current
    DESCRIPTION
        "An entry for configuring VSI parameters."
    INDEX
    {
        hh3cVsiIndex
    }
    ::= { hh3cVsiTable 1 }

Hh3cVsiEntry ::=
    SEQUENCE
    {
        hh3cVsiIndex             Unsigned32,
        hh3cVsiName              OCTET STRING,
        hh3cVsiMode              INTEGER,
        hh3cMinmIsid             Integer32,
        hh3cVsiId                Unsigned32,
        hh3cVsiTransMode         INTEGER,
        hh3cVsiEnableHubSpoke    INTEGER,
        hh3cVsiAdminState        INTEGER,
        hh3cVsiRowStatus         RowStatus,
        hh3cVsiSpbIsid           Integer32
    }

hh3cVsiIndex    OBJECT-TYPE
    SYNTAX      Unsigned32
    MAX-ACCESS  not-accessible
    STATUS      current
    DESCRIPTION
        "Index of VSI. Its value ranges from 0x1 to 0xFFFFFFFE."
    ::= { hh3cVsiEntry 1 }

hh3cVsiName    OBJECT-TYPE
    SYNTAX      OCTET STRING(SIZE(1..31))
    MAX-ACCESS  read-create
    STATUS      current
    DESCRIPTION
        "Name of VSI. Max string length of VSI name is 31."
    ::= { hh3cVsiEntry 2 }

hh3cVsiMode    OBJECT-TYPE
    SYNTAX      INTEGER
    {
        default(0),
        martini(1),
        minm(2),
        martiniAndMinm(3),
        kompella(4),
        kompellaAndMinm(5)
    }
    MAX-ACCESS  read-create
    STATUS      current
    DESCRIPTION
        "Mode of VSI. Martini mode indicated this VSI supports VPLS service
         signalled using LDP. Kompella indicated this VSI supports VPLS
         service signalled using BGP. Minm indicated this VSI supports
         MAC-in-MAC service. Default indicated this VSI supports all services."

    ::= { hh3cVsiEntry 3 }

hh3cMinmIsid    OBJECT-TYPE
    SYNTAX      Integer32
    MAX-ACCESS  read-create
    STATUS      current
    DESCRIPTION
        "The PBB I-SID of VSI in minm or martiniAndMinm mode. It
        must be different for every VSI. Its value ranges from 0x1 to
        0xFFFFFF. In other VSI modes, its value is invalid value 0x0."
    ::= { hh3cVsiEntry 4 }

hh3cVsiId    OBJECT-TYPE
    SYNTAX      Unsigned32
    MAX-ACCESS  read-create
    STATUS      current
    DESCRIPTION
        "Identifier of VSI in martini or martiniAndMinm mode, by default,
        it's the PW ID of this VSI. Its value ranges from 1 to 4294967295.
        In other VSI modes, its value is invalid value 0."
    ::= { hh3cVsiEntry 5 }

hh3cVsiTransMode    OBJECT-TYPE
    SYNTAX      INTEGER
    {
        vlan(1),
        ethernet(2)
    }
    MAX-ACCESS  read-create
    STATUS      current
    DESCRIPTION
        "Transit Mode of VSI."
    ::= { hh3cVsiEntry 6 }

hh3cVsiEnableHubSpoke    OBJECT-TYPE
    SYNTAX      INTEGER
    {
        disable(1),
        enable(2)
    }
    MAX-ACCESS  read-create
    STATUS      current
    DESCRIPTION
        "Config HubSpoke property of this VSI."
    ::= { hh3cVsiEntry 7 }

hh3cVsiAdminState   OBJECT-TYPE
    SYNTAX      INTEGER
    {
        adminUp(1),
        adminDown(2)
    }
    MAX-ACCESS  read-create
    STATUS      current
    DESCRIPTION
        "Set VSI admin state as adminUp or adminDown."
    ::= { hh3cVsiEntry 8 }

hh3cVsiRowStatus     OBJECT-TYPE
    SYNTAX      RowStatus
    MAX-ACCESS  read-create
    STATUS      current
    DESCRIPTION
        "Operation status of this table entry."
    ::= { hh3cVsiEntry 9 }

hh3cVsiSpbIsid    OBJECT-TYPE
    SYNTAX      Integer32
    MAX-ACCESS  read-create
    STATUS      current
    DESCRIPTION
        "The SPB I-SID of VSI in minm or martiniAndMinm mode. It
        must be different for every VSI. Its value ranges from 0x100 to
        0xFFFFFF. In other VSI modes, its value is invalid value 0x0."
    ::= { hh3cVsiEntry 10 }
-- =============================================================================
-- End of hh3cVsiTable Definition
-- =============================================================================

-- =============================================================================
-- hh3cVsiXconnectTable Definition
-- =============================================================================
hh3cVsiXconnectTable  OBJECT-TYPE
    SYNTAX      SEQUENCE OF Hh3cVsiXconnectEntry
    MAX-ACCESS  not-accessible
    STATUS      current
    DESCRIPTION
        "A table for configuring xconnect parameters."
    ::= { hh3cVsiObjects 3 }

hh3cVsiXconnectEntry  OBJECT-TYPE
    SYNTAX      Hh3cVsiXconnectEntry
    MAX-ACCESS  not-accessible
    STATUS      current
    DESCRIPTION
        "An entry for configuring xconnect parameters. Each entry means connecting
        a service instance of a interface to a VSI."
    INDEX
    {
        hh3cVsiXconnectIfIndex,
        hh3cVsiXconnectEvcSrvInstId
    }
    ::= { hh3cVsiXconnectTable 1 }

Hh3cVsiXconnectEntry ::=
    SEQUENCE
    {
        hh3cVsiXconnectIfIndex      Unsigned32,
        hh3cVsiXconnectEvcSrvInstId Unsigned32,
        hh3cVsiXconnectVsiName      OCTET STRING,
        hh3cVsiXconnectAccessMode   INTEGER,
        hh3cVsiXconnectHubSpoke     INTEGER,
        hh3cVsiXconnectRowStatus    RowStatus
    }
hh3cVsiXconnectIfIndex    OBJECT-TYPE
    SYNTAX      Unsigned32
    MAX-ACCESS  not-accessible
    STATUS      current
    DESCRIPTION
        "Index of the interface associated with the VSI."
    ::= { hh3cVsiXconnectEntry 1 }

hh3cVsiXconnectEvcSrvInstId    OBJECT-TYPE
    SYNTAX      Unsigned32
    MAX-ACCESS  not-accessible
    STATUS      current
    DESCRIPTION
        "Index of the service instance associated with the VSI."
    ::= { hh3cVsiXconnectEntry 2 }


hh3cVsiXconnectVsiName    OBJECT-TYPE
    SYNTAX      OCTET STRING(SIZE(1..31))
    MAX-ACCESS  read-create
    STATUS      current
    DESCRIPTION
        "Name of VSI. Max string length of VSI name is 31."
    ::= { hh3cVsiXconnectEntry 3 }

hh3cVsiXconnectAccessMode    OBJECT-TYPE
    SYNTAX      INTEGER
    {
        vlan(1),
        ethernet(2)
    }
    MAX-ACCESS  read-create
    STATUS      current
    DESCRIPTION
        "Access mode of this service instance."
    ::= { hh3cVsiXconnectEntry 4 }

hh3cVsiXconnectHubSpoke    OBJECT-TYPE
    SYNTAX      INTEGER
    {
        none(1),
        hub(2),
        spoke(3)
    }
    MAX-ACCESS  read-create
    STATUS      current
    DESCRIPTION
        "Config HubSpoke property of this service instance."
    ::= { hh3cVsiXconnectEntry 5 }

hh3cVsiXconnectRowStatus     OBJECT-TYPE
    SYNTAX      RowStatus
    MAX-ACCESS  read-create
    STATUS      current
    DESCRIPTION
        "Operation status of this table entry."
    ::= { hh3cVsiXconnectEntry 6 }

-- =============================================================================
-- End of hh3cVsiXconnectTable Definition
-- =============================================================================

END
