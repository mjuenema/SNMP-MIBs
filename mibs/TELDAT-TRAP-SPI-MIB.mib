-- file automatically created


TELDAT-TRAP-SPI-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


spiTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SPI event subsystem."
    REVISION "201401200930Z"
    DESCRIPTION "Initial implementation"
        ::= { telEventTraps 223 }


spiEventsGroup	OBJECT IDENTIFIER	::= { spiTrapsMIB 1 }

spiNotifications	OBJECT IDENTIFIER	::= { spiTrapsMIB 2 }
spiNotificationsPrefix	OBJECT IDENTIFIER	::= { spiNotifications 0 }

spiEventObjects1 OBJECT-IDENTITY
    STATUS current
    DESCRIPTION
        "Event SPI.1
        Initialization successfully when a SPI agent is configured."
    ::= { spiEventsGroup 1 }

spi1_agent_name OBJECT-TYPE
    SYNTAX DisplayString
    MAX-ACCESS accessible-for-notify
    STATUS current
    DESCRIPTION
        "Parameter 'agent_name' in event SPI.1"
    ::= { spiEventObjects1 1 }

spiEventObjects2 OBJECT-IDENTITY
    STATUS current
    DESCRIPTION
        "Event SPI.2
        SPI agent message don't send due ICC-ID is not available."
    ::= { spiEventsGroup 2 }

spi2_agent_name OBJECT-TYPE
    SYNTAX DisplayString
    MAX-ACCESS accessible-for-notify
    STATUS current
    DESCRIPTION
        "Parameter 'agent_name' in event SPI.2"
    ::= { spiEventObjects2 1 }

spi2_state OBJECT-TYPE
    SYNTAX Integer32
    MAX-ACCESS accessible-for-notify
    STATUS current
    DESCRIPTION
        "Parameter 'state' in event SPI.2"
    ::= { spiEventObjects2 2 }

spiEventObjects3 OBJECT-IDENTITY
    STATUS current
    DESCRIPTION
        "Event SPI.3
        Received SPI message error due protocol version param."
    ::= { spiEventsGroup 3 }

spi3_prot_ver OBJECT-TYPE
    SYNTAX Integer32
    MAX-ACCESS accessible-for-notify
    STATUS current
    DESCRIPTION
        "Parameter 'prot_ver' in event SPI.3"
    ::= { spiEventObjects3 1 }

spi3_agent_name OBJECT-TYPE
    SYNTAX DisplayString
    MAX-ACCESS accessible-for-notify
    STATUS current
    DESCRIPTION
        "Parameter 'agent_name' in event SPI.3"
    ::= { spiEventObjects3 2 }

spi3_state OBJECT-TYPE
    SYNTAX Integer32
    MAX-ACCESS accessible-for-notify
    STATUS current
    DESCRIPTION
        "Parameter 'state' in event SPI.3"
    ::= { spiEventObjects3 3 }

spiEventObjects4 OBJECT-IDENTITY
    STATUS current
    DESCRIPTION
        "Event SPI.4
        Received SPI message error due MSISDN is not associated to agent."
    ::= { spiEventsGroup 4 }

spi4_msisdn OBJECT-TYPE
    SYNTAX DisplayString
    MAX-ACCESS accessible-for-notify
    STATUS current
    DESCRIPTION
        "Parameter 'msisdn' in event SPI.4"
    ::= { spiEventObjects4 1 }

spi4_agent_name OBJECT-TYPE
    SYNTAX DisplayString
    MAX-ACCESS accessible-for-notify
    STATUS current
    DESCRIPTION
        "Parameter 'agent_name' in event SPI.4"
    ::= { spiEventObjects4 2 }

spi4_state OBJECT-TYPE
    SYNTAX Integer32
    MAX-ACCESS accessible-for-notify
    STATUS current
    DESCRIPTION
        "Parameter 'state' in event SPI.4"
    ::= { spiEventObjects4 3 }

spiEventObjects5 OBJECT-IDENTITY
    STATUS current
    DESCRIPTION
        "Event SPI.5
        Correct KAR message has been received."
    ::= { spiEventsGroup 5 }

spi5_agent_name OBJECT-TYPE
    SYNTAX DisplayString
    MAX-ACCESS accessible-for-notify
    STATUS current
    DESCRIPTION
        "Parameter 'agent_name' in event SPI.5"
    ::= { spiEventObjects5 1 }

spi5_ip_org OBJECT-TYPE
    SYNTAX IpAddress
    MAX-ACCESS accessible-for-notify
    STATUS current
    DESCRIPTION
        "Parameter 'ip_org' in event SPI.5"
    ::= { spiEventObjects5 2 }

spi5_port_org OBJECT-TYPE
    SYNTAX Integer32
    MAX-ACCESS accessible-for-notify
    STATUS current
    DESCRIPTION
        "Parameter 'port_org' in event SPI.5"
    ::= { spiEventObjects5 3 }

spi5_state OBJECT-TYPE
    SYNTAX Integer32
    MAX-ACCESS accessible-for-notify
    STATUS current
    DESCRIPTION
        "Parameter 'state' in event SPI.5"
    ::= { spiEventObjects5 4 }

spiEventObjects6 OBJECT-IDENTITY
    STATUS current
    DESCRIPTION
        "Event SPI.6
        Correct SIM message has been received."
    ::= { spiEventsGroup 6 }

spi6_agent_name OBJECT-TYPE
    SYNTAX DisplayString
    MAX-ACCESS accessible-for-notify
    STATUS current
    DESCRIPTION
        "Parameter 'agent_name' in event SPI.6"
    ::= { spiEventObjects6 1 }

spi6_ip_org OBJECT-TYPE
    SYNTAX IpAddress
    MAX-ACCESS accessible-for-notify
    STATUS current
    DESCRIPTION
        "Parameter 'ip_org' in event SPI.6"
    ::= { spiEventObjects6 2 }

spi6_port_org OBJECT-TYPE
    SYNTAX Integer32
    MAX-ACCESS accessible-for-notify
    STATUS current
    DESCRIPTION
        "Parameter 'port_org' in event SPI.6"
    ::= { spiEventObjects6 3 }

spi6_state OBJECT-TYPE
    SYNTAX Integer32
    MAX-ACCESS accessible-for-notify
    STATUS current
    DESCRIPTION
        "Parameter 'state' in event SPI.6"
    ::= { spiEventObjects6 4 }

spiEventObjects7 OBJECT-IDENTITY
    STATUS current
    DESCRIPTION
        "Event SPI.7
        Correct RKAO message has been received."
    ::= { spiEventsGroup 7 }

spi7_agent_name OBJECT-TYPE
    SYNTAX DisplayString
    MAX-ACCESS accessible-for-notify
    STATUS current
    DESCRIPTION
        "Parameter 'agent_name' in event SPI.7"
    ::= { spiEventObjects7 1 }

spi7_ip_org OBJECT-TYPE
    SYNTAX IpAddress
    MAX-ACCESS accessible-for-notify
    STATUS current
    DESCRIPTION
        "Parameter 'ip_org' in event SPI.7"
    ::= { spiEventObjects7 2 }

spi7_port_org OBJECT-TYPE
    SYNTAX Integer32
    MAX-ACCESS accessible-for-notify
    STATUS current
    DESCRIPTION
        "Parameter 'port_org' in event SPI.7"
    ::= { spiEventObjects7 3 }

spi7_state OBJECT-TYPE
    SYNTAX Integer32
    MAX-ACCESS accessible-for-notify
    STATUS current
    DESCRIPTION
        "Parameter 'state' in event SPI.7"
    ::= { spiEventObjects7 4 }

spiEventObjects8 OBJECT-IDENTITY
    STATUS current
    DESCRIPTION
        "Event SPI.8
        Error, Unknown message type has been received."
    ::= { spiEventsGroup 8 }

spi8_msg_type OBJECT-TYPE
    SYNTAX Integer32
    MAX-ACCESS accessible-for-notify
    STATUS current
    DESCRIPTION
        "Parameter 'msg_type' in event SPI.8"
    ::= { spiEventObjects8 1 }

spi8_agent_name OBJECT-TYPE
    SYNTAX DisplayString
    MAX-ACCESS accessible-for-notify
    STATUS current
    DESCRIPTION
        "Parameter 'agent_name' in event SPI.8"
    ::= { spiEventObjects8 2 }

spi8_ip_org OBJECT-TYPE
    SYNTAX IpAddress
    MAX-ACCESS accessible-for-notify
    STATUS current
    DESCRIPTION
        "Parameter 'ip_org' in event SPI.8"
    ::= { spiEventObjects8 3 }

spi8_port_org OBJECT-TYPE
    SYNTAX Integer32
    MAX-ACCESS accessible-for-notify
    STATUS current
    DESCRIPTION
        "Parameter 'port_org' in event SPI.8"
    ::= { spiEventObjects8 4 }

spi8_state OBJECT-TYPE
    SYNTAX Integer32
    MAX-ACCESS accessible-for-notify
    STATUS current
    DESCRIPTION
        "Parameter 'state' in event SPI.8"
    ::= { spiEventObjects8 5 }

spiEventObjects9 OBJECT-IDENTITY
    STATUS current
    DESCRIPTION
        "Event SPI.9
        Initialization failure when a SPI agent is configured."
    ::= { spiEventsGroup 9 }

spi9_agent_name OBJECT-TYPE
    SYNTAX DisplayString
    MAX-ACCESS accessible-for-notify
    STATUS current
    DESCRIPTION
        "Parameter 'agent_name' in event SPI.9"
    ::= { spiEventObjects9 1 }

spi9_server_ip OBJECT-TYPE
    SYNTAX IpAddress
    MAX-ACCESS accessible-for-notify
    STATUS current
    DESCRIPTION
        "Parameter 'server_ip' in event SPI.9"
    ::= { spiEventObjects9 2 }

spi9_server_udp_port OBJECT-TYPE
    SYNTAX Integer32
    MAX-ACCESS accessible-for-notify
    STATUS current
    DESCRIPTION
        "Parameter 'server_udp_port' in event SPI.9"
    ::= { spiEventObjects9 3 }

spiEventObjects10 OBJECT-IDENTITY
    STATUS current
    DESCRIPTION
        "Event SPI.10
        SPI agent timer has been triggered."
    ::= { spiEventsGroup 10 }

spi10_timer OBJECT-TYPE
    SYNTAX DisplayString
    MAX-ACCESS accessible-for-notify
    STATUS current
    DESCRIPTION
        "Parameter 'timer' in event SPI.10"
    ::= { spiEventObjects10 1 }

spi10_agent_name OBJECT-TYPE
    SYNTAX DisplayString
    MAX-ACCESS accessible-for-notify
    STATUS current
    DESCRIPTION
        "Parameter 'agent_name' in event SPI.10"
    ::= { spiEventObjects10 2 }

spi10_state OBJECT-TYPE
    SYNTAX Integer32
    MAX-ACCESS accessible-for-notify
    STATUS current
    DESCRIPTION
        "Parameter 'state' in event SPI.10"
    ::= { spiEventObjects10 3 }

spiEventObjects11 OBJECT-IDENTITY
    STATUS current
    DESCRIPTION
        "Event SPI.11
        KA message has been send to server."
    ::= { spiEventsGroup 11 }

spi11_agent_name OBJECT-TYPE
    SYNTAX DisplayString
    MAX-ACCESS accessible-for-notify
    STATUS current
    DESCRIPTION
        "Parameter 'agent_name' in event SPI.11"
    ::= { spiEventObjects11 1 }

spi11_ip_org OBJECT-TYPE
    SYNTAX IpAddress
    MAX-ACCESS accessible-for-notify
    STATUS current
    DESCRIPTION
        "Parameter 'ip_org' in event SPI.11"
    ::= { spiEventObjects11 2 }

spi11_port_org OBJECT-TYPE
    SYNTAX Integer32
    MAX-ACCESS accessible-for-notify
    STATUS current
    DESCRIPTION
        "Parameter 'port_org' in event SPI.11"
    ::= { spiEventObjects11 3 }

spi11_state OBJECT-TYPE
    SYNTAX Integer32
    MAX-ACCESS accessible-for-notify
    STATUS current
    DESCRIPTION
        "Parameter 'state' in event SPI.11"
    ::= { spiEventObjects11 4 }

spiEventObjects12 OBJECT-IDENTITY
    STATUS current
    DESCRIPTION
        "Event SPI.12
        KAI message has been send to server."
    ::= { spiEventsGroup 12 }

spi12_agent_name OBJECT-TYPE
    SYNTAX DisplayString
    MAX-ACCESS accessible-for-notify
    STATUS current
    DESCRIPTION
        "Parameter 'agent_name' in event SPI.12"
    ::= { spiEventObjects12 1 }

spi12_ip_org OBJECT-TYPE
    SYNTAX IpAddress
    MAX-ACCESS accessible-for-notify
    STATUS current
    DESCRIPTION
        "Parameter 'ip_org' in event SPI.12"
    ::= { spiEventObjects12 2 }

spi12_port_org OBJECT-TYPE
    SYNTAX Integer32
    MAX-ACCESS accessible-for-notify
    STATUS current
    DESCRIPTION
        "Parameter 'port_org' in event SPI.12"
    ::= { spiEventObjects12 3 }

spi12_state OBJECT-TYPE
    SYNTAX Integer32
    MAX-ACCESS accessible-for-notify
    STATUS current
    DESCRIPTION
        "Parameter 'state' in event SPI.12"
    ::= { spiEventObjects12 4 }

spiEventObjects13 OBJECT-IDENTITY
    STATUS current
    DESCRIPTION
        "Event SPI.13
        KAO message has been send to server."
    ::= { spiEventsGroup 13 }

spi13_agent_name OBJECT-TYPE
    SYNTAX DisplayString
    MAX-ACCESS accessible-for-notify
    STATUS current
    DESCRIPTION
        "Parameter 'agent_name' in event SPI.13"
    ::= { spiEventObjects13 1 }

spi13_ip_org OBJECT-TYPE
    SYNTAX IpAddress
    MAX-ACCESS accessible-for-notify
    STATUS current
    DESCRIPTION
        "Parameter 'ip_org' in event SPI.13"
    ::= { spiEventObjects13 2 }

spi13_port_org OBJECT-TYPE
    SYNTAX Integer32
    MAX-ACCESS accessible-for-notify
    STATUS current
    DESCRIPTION
        "Parameter 'port_org' in event SPI.13"
    ::= { spiEventObjects13 3 }

spi13_state OBJECT-TYPE
    SYNTAX Integer32
    MAX-ACCESS accessible-for-notify
    STATUS current
    DESCRIPTION
        "Parameter 'state' in event SPI.13"
    ::= { spiEventObjects13 4 }

spiEventObjects14 OBJECT-IDENTITY
    STATUS current
    DESCRIPTION
        "Event SPI.14
        Max. number of KAI message retransmisions reached."
    ::= { spiEventsGroup 14 }

spi14_agent_name OBJECT-TYPE
    SYNTAX DisplayString
    MAX-ACCESS accessible-for-notify
    STATUS current
    DESCRIPTION
        "Parameter 'agent_name' in event SPI.14"
    ::= { spiEventObjects14 1 }

spi14_state OBJECT-TYPE
    SYNTAX Integer32
    MAX-ACCESS accessible-for-notify
    STATUS current
    DESCRIPTION
        "Parameter 'state' in event SPI.14"
    ::= { spiEventObjects14 2 }

spiEventObjects15 OBJECT-IDENTITY
    STATUS current
    DESCRIPTION
        "Event SPI.15
        Max. number of KA message retransmisions reached."
    ::= { spiEventsGroup 15 }

spi15_agent_name OBJECT-TYPE
    SYNTAX DisplayString
    MAX-ACCESS accessible-for-notify
    STATUS current
    DESCRIPTION
        "Parameter 'agent_name' in event SPI.15"
    ::= { spiEventObjects15 1 }

spi15_state OBJECT-TYPE
    SYNTAX Integer32
    MAX-ACCESS accessible-for-notify
    STATUS current
    DESCRIPTION
        "Parameter 'state' in event SPI.15"
    ::= { spiEventObjects15 2 }

spiEventObjects16 OBJECT-IDENTITY
    STATUS current
    DESCRIPTION
        "Event SPI.16
        Detailed Data received from SPI server."
    ::= { spiEventsGroup 16 }

spi16_agent_name OBJECT-TYPE
    SYNTAX DisplayString
    MAX-ACCESS accessible-for-notify
    STATUS current
    DESCRIPTION
        "Parameter 'agent_name' in event SPI.16"
    ::= { spiEventObjects16 1 }

spi16_state OBJECT-TYPE
    SYNTAX Integer32
    MAX-ACCESS accessible-for-notify
    STATUS current
    DESCRIPTION
        "Parameter 'state' in event SPI.16"
    ::= { spiEventObjects16 2 }

spi16_ip_org OBJECT-TYPE
    SYNTAX IpAddress
    MAX-ACCESS accessible-for-notify
    STATUS current
    DESCRIPTION
        "Parameter 'ip_org' in event SPI.16"
    ::= { spiEventObjects16 3 }

spi16_leng OBJECT-TYPE
    SYNTAX Integer32
    MAX-ACCESS accessible-for-notify
    STATUS current
    DESCRIPTION
        "Parameter 'leng' in event SPI.16"
    ::= { spiEventObjects16 4 }

spi16_data OBJECT-TYPE
    SYNTAX DisplayString
    MAX-ACCESS accessible-for-notify
    STATUS current
    DESCRIPTION
        "Parameter 'data' in event SPI.16"
    ::= { spiEventObjects16 5 }


spiNotification1 NOTIFICATION-TYPE
    OBJECTS { 
              spi1_agent_name 
            }
    STATUS current
    DESCRIPTION
        "Notification of Event SPI.1

        Message: 'SPI initialized sucessfully for agent:$1'

        Parameters list:
              $1: spi1_agent_name

        Initialization successfully when a SPI agent is configured."
    ::= { spiNotificationsPrefix 1 }

spiNotification2 NOTIFICATION-TYPE
    OBJECTS { 
              spi2_agent_name, 
              spi2_state 
            }
    STATUS current
    DESCRIPTION
        "Notification of Event SPI.2

        Message: 'Tx message error due ICC-ID is not available. agent:$1, state:$2'

        Parameters list:
              $1: spi2_agent_name
              $2: spi2_state

        SPI agent message don't send due ICC-ID is not available."
    ::= { spiNotificationsPrefix 2 }

spiNotification3 NOTIFICATION-TYPE
    OBJECTS { 
              spi3_prot_ver, 
              spi3_agent_name,
              spi3_state 
            }
    STATUS current
    DESCRIPTION
        "Notification of Event SPI.3

        Message: 'Rx message error due protocol version ($1) agent:$2, state:$3'

        Parameters list:
              $1: spi3_prot_ver
              $2: spi3_agent_name
              $3: spi3_state

        Received SPI message error due protocol version param."
    ::= { spiNotificationsPrefix 3 }

spiNotification4 NOTIFICATION-TYPE
    OBJECTS { 
              spi4_msisdn, 
              spi4_agent_name,
              spi4_state 
            }
    STATUS current
    DESCRIPTION
        "Notification of Event SPI.4

        Message: 'Rx message error due MSISDN ($1) agent:$2, state:$3'

        Parameters list:
              $1: spi4_msisdn
              $2: spi4_agent_name
              $3: spi4_state

        Received SPI message error due MSISDN is not associated to agent."
    ::= { spiNotificationsPrefix 4 }

spiNotification5 NOTIFICATION-TYPE
    OBJECTS { 
              spi5_agent_name, 
              spi5_ip_org,
              spi5_port_org,
              spi5_state 
            }
    STATUS current
    DESCRIPTION
        "Notification of Event SPI.5

        Message: 'Rx message KAR for agent:$1, Server IP address:$2, Server UDP port$3, state:$4'

        Parameters list:
              $1: spi5_agent_name
              $2: spi5_ip_org
              $3: spi5_port_org
              $4: spi5_state

        Correct KAR message has been received."
    ::= { spiNotificationsPrefix 5 }

spiNotification6 NOTIFICATION-TYPE
    OBJECTS { 
              spi6_agent_name, 
              spi6_ip_org,
              spi6_port_org,
              spi6_state 
            }
    STATUS current
    DESCRIPTION
        "Notification of Event SPI.6

        Message: 'Rx message SIM for agent:$1, Server IP address:$2, Server UDP port$3, state:$4'

        Parameters list:
              $1: spi6_agent_name
              $2: spi6_ip_org
              $3: spi6_port_org
              $4: spi6_state

        Correct SIM message has been received."
    ::= { spiNotificationsPrefix 6 }

spiNotification7 NOTIFICATION-TYPE
    OBJECTS { 
              spi7_agent_name, 
              spi7_ip_org,
              spi7_port_org,
              spi7_state 
            }
    STATUS current
    DESCRIPTION
        "Notification of Event SPI.7

        Message: 'Rx message RKAO for agent:$1, Server IP address:$2, Server UDP port$3, state:$4'

        Parameters list:
              $1: spi7_agent_name
              $2: spi7_ip_org
              $3: spi7_port_org
              $4: spi7_state

        Correct RKAO message has been received."
    ::= { spiNotificationsPrefix 7 }

spiNotification8 NOTIFICATION-TYPE
    OBJECTS { 
              spi8_msg_type, 
              spi8_agent_name,
              spi8_ip_org,
              spi8_port_org,
              spi8_state 
            }
    STATUS current
    DESCRIPTION
        "Notification of Event SPI.8

        Message: 'Rx message type unknown($1 for agent:$2, Server IP address:$3, Server UDP port$4, state:$5'

        Parameters list:
              $1: spi8_msg_type
              $2: spi8_agent_name
              $3: spi8_ip_org
              $4: spi8_port_org
              $5: spi8_state

        Error, Unknown message type has been received."
    ::= { spiNotificationsPrefix 8 }

spiNotification9 NOTIFICATION-TYPE
    OBJECTS { 
              spi9_agent_name, 
              spi9_server_ip,
              spi9_server_udp_port 
            }
    STATUS current
    DESCRIPTION
        "Notification of Event SPI.9

        Message: 'SPI initialization failure agent $1, Server IP address:$2, Server UDP port$3'

        Parameters list:
              $1: spi9_agent_name
              $2: spi9_server_ip
              $3: spi9_server_udp_port

        Initialization failure when a SPI agent is configured."
    ::= { spiNotificationsPrefix 9 }

spiNotification10 NOTIFICATION-TYPE
    OBJECTS { 
              spi10_timer, 
              spi10_agent_name,
              spi10_state 
            }
    STATUS current
    DESCRIPTION
        "Notification of Event SPI.10

        Message: '$1 timer triggered agent:$2, state:$3'

        Parameters list:
              $1: spi10_timer
              $2: spi10_agent_name
              $3: spi10_state

        SPI agent timer has been triggered."
    ::= { spiNotificationsPrefix 10 }

spiNotification11 NOTIFICATION-TYPE
    OBJECTS { 
              spi11_agent_name, 
              spi11_ip_org,
              spi11_port_org,
              spi11_state 
            }
    STATUS current
    DESCRIPTION
        "Notification of Event SPI.11

        Message: 'Tx KA message agent:$1, Server IP address:$2, Server UDP port$3, state:$4'

        Parameters list:
              $1: spi11_agent_name
              $2: spi11_ip_org
              $3: spi11_port_org
              $4: spi11_state

        KA message has been send to server."
    ::= { spiNotificationsPrefix 11 }

spiNotification12 NOTIFICATION-TYPE
    OBJECTS { 
              spi12_agent_name, 
              spi12_ip_org,
              spi12_port_org,
              spi12_state 
            }
    STATUS current
    DESCRIPTION
        "Notification of Event SPI.12

        Message: 'Tx KAI message agent:$1, Server IP address:$2, Server UDP port$3, state:$4'

        Parameters list:
              $1: spi12_agent_name
              $2: spi12_ip_org
              $3: spi12_port_org
              $4: spi12_state

        KAI message has been send to server."
    ::= { spiNotificationsPrefix 12 }

spiNotification13 NOTIFICATION-TYPE
    OBJECTS { 
              spi13_agent_name, 
              spi13_ip_org,
              spi13_port_org,
              spi13_state 
            }
    STATUS current
    DESCRIPTION
        "Notification of Event SPI.13

        Message: 'Tx KAO message agent:$1, Server IP address:$2, Server UDP port$3, state:$4'

        Parameters list:
              $1: spi13_agent_name
              $2: spi13_ip_org
              $3: spi13_port_org
              $4: spi13_state

        KAO message has been send to server."
    ::= { spiNotificationsPrefix 13 }

spiNotification14 NOTIFICATION-TYPE
    OBJECTS { 
              spi14_agent_name, 
              spi14_state 
            }
    STATUS current
    DESCRIPTION
        "Notification of Event SPI.14

        Message: 'Tx nkair retransmisions reached, agent:$1, state:$2'

        Parameters list:
              $1: spi14_agent_name
              $2: spi14_state

        Max. number of KAI message retransmisions reached."
    ::= { spiNotificationsPrefix 14 }

spiNotification15 NOTIFICATION-TYPE
    OBJECTS { 
              spi15_agent_name, 
              spi15_state 
            }
    STATUS current
    DESCRIPTION
        "Notification of Event SPI.15

        Message: 'Tx nkar retransmisions reached, agent:$1, state:$2'

        Parameters list:
              $1: spi15_agent_name
              $2: spi15_state

        Max. number of KA message retransmisions reached."
    ::= { spiNotificationsPrefix 15 }

spiNotification16 NOTIFICATION-TYPE
    OBJECTS { 
              spi16_agent_name, 
              spi16_state,
              spi16_ip_org,
              spi16_leng,
              spi16_data 
            }
    STATUS current
    DESCRIPTION
        "Notification of Event SPI.16

        Message: 'Data received from Server agent:$1 st:$2 (SvrIP:$3,$4 bytes):$5'

        Parameters list:
              $1: spi16_agent_name
              $2: spi16_state
              $3: spi16_ip_org
              $4: spi16_leng
              $5: spi16_data

        Detailed Data received from SPI server."
    ::= { spiNotificationsPrefix 16 }


END
