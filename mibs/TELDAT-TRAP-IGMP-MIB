-- file automatically created


TELDAT-TRAP-IGMP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


igmpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IGMP event subsystem."
    REVISION "201401200930Z"
    DESCRIPTION "Initial implementation"
        ::= { telEventTraps 166 }


igmpEventsGroup	OBJECT IDENTIFIER	::= { igmpTrapsMIB 1 }

igmpNotifications	OBJECT IDENTIFIER	::= { igmpTrapsMIB 2 }
igmpNotificationsPrefix	OBJECT IDENTIFIER	::= { igmpNotifications 0 }

igmpEventObjects1 OBJECT-IDENTITY
    STATUS current
    DESCRIPTION
        "Event IGMP.1
        router side (downstream) part of igmp protocol has been initialized on
        specified interface."
    ::= { igmpEventsGroup 1 }

igmp1_interface OBJECT-TYPE
    SYNTAX DisplayString
    MAX-ACCESS accessible-for-notify
    STATUS current
    DESCRIPTION
        "Parameter 'interface' in event IGMP.1"
    ::= { igmpEventObjects1 1 }

igmpEventObjects2 OBJECT-IDENTITY
    STATUS current
    DESCRIPTION
        "Event IGMP.2
        host side (upstream) part of igmp protocol has been initialized on
        specified interface."
    ::= { igmpEventsGroup 2 }

igmp2_interface OBJECT-TYPE
    SYNTAX DisplayString
    MAX-ACCESS accessible-for-notify
    STATUS current
    DESCRIPTION
        "Parameter 'interface' in event IGMP.2"
    ::= { igmpEventObjects2 1 }

igmpEventObjects3 OBJECT-IDENTITY
    STATUS current
    DESCRIPTION
        "Event IGMP.3
        Started operating router side (downstream) part of igmp protocol on
        specified interface."
    ::= { igmpEventsGroup 3 }

igmp3_interface OBJECT-TYPE
    SYNTAX DisplayString
    MAX-ACCESS accessible-for-notify
    STATUS current
    DESCRIPTION
        "Parameter 'interface' in event IGMP.3"
    ::= { igmpEventObjects3 1 }

igmpEventObjects4 OBJECT-IDENTITY
    STATUS current
    DESCRIPTION
        "Event IGMP.4
        Started operating host side (upstream) part of igmp protocol on
        specified interface."
    ::= { igmpEventsGroup 4 }

igmp4_interface OBJECT-TYPE
    SYNTAX DisplayString
    MAX-ACCESS accessible-for-notify
    STATUS current
    DESCRIPTION
        "Parameter 'interface' in event IGMP.4"
    ::= { igmpEventObjects4 1 }

igmpEventObjects5 OBJECT-IDENTITY
    STATUS current
    DESCRIPTION
        "Event IGMP.5
        Stopped operating router side (downstream) part of igmp protocol on
        specified interface."
    ::= { igmpEventsGroup 5 }

igmp5_interface OBJECT-TYPE
    SYNTAX DisplayString
    MAX-ACCESS accessible-for-notify
    STATUS current
    DESCRIPTION
        "Parameter 'interface' in event IGMP.5"
    ::= { igmpEventObjects5 1 }

igmpEventObjects6 OBJECT-IDENTITY
    STATUS current
    DESCRIPTION
        "Event IGMP.6
        Stopped operating host side (upstream) part of igmp protocol on
        specified interface."
    ::= { igmpEventsGroup 6 }

igmp6_interface OBJECT-TYPE
    SYNTAX DisplayString
    MAX-ACCESS accessible-for-notify
    STATUS current
    DESCRIPTION
        "Parameter 'interface' in event IGMP.6"
    ::= { igmpEventObjects6 1 }

igmpEventObjects7 OBJECT-IDENTITY
    STATUS current
    DESCRIPTION
        "Event IGMP.7
        Description of previous event."
    ::= { igmpEventsGroup 7 }

igmp7_description OBJECT-TYPE
    SYNTAX DisplayString
    MAX-ACCESS accessible-for-notify
    STATUS current
    DESCRIPTION
        "Parameter 'description' in event IGMP.7"
    ::= { igmpEventObjects7 1 }

igmpEventObjects8 OBJECT-IDENTITY
    STATUS current
    DESCRIPTION
        "Event IGMP.8
        An errored packet was received from specified address on specified
        interface."
    ::= { igmpEventsGroup 8 }

igmp8_srcaddr OBJECT-TYPE
    SYNTAX IpAddress
    MAX-ACCESS accessible-for-notify
    STATUS current
    DESCRIPTION
        "Parameter 'srcaddr' in event IGMP.8"
    ::= { igmpEventObjects8 1 }

igmp8_interface OBJECT-TYPE
    SYNTAX DisplayString
    MAX-ACCESS accessible-for-notify
    STATUS current
    DESCRIPTION
        "Parameter 'interface' in event IGMP.8"
    ::= { igmpEventObjects8 2 }

igmpEventObjects9 OBJECT-IDENTITY
    STATUS current
    DESCRIPTION
        "Event IGMP.9
        A packet received from specified address on specified interface, was
        discarded."
    ::= { igmpEventsGroup 9 }

igmp9_srcaddr OBJECT-TYPE
    SYNTAX IpAddress
    MAX-ACCESS accessible-for-notify
    STATUS current
    DESCRIPTION
        "Parameter 'srcaddr' in event IGMP.9"
    ::= { igmpEventObjects9 1 }

igmp9_interface OBJECT-TYPE
    SYNTAX DisplayString
    MAX-ACCESS accessible-for-notify
    STATUS current
    DESCRIPTION
        "Parameter 'interface' in event IGMP.9"
    ::= { igmpEventObjects9 2 }

igmpEventObjects10 OBJECT-IDENTITY
    STATUS current
    DESCRIPTION
        "Event IGMP.10
        A packet received from specified address on specified interface, was
        discarded by the igmp router part."
    ::= { igmpEventsGroup 10 }

igmp10_srcaddr OBJECT-TYPE
    SYNTAX IpAddress
    MAX-ACCESS accessible-for-notify
    STATUS current
    DESCRIPTION
        "Parameter 'srcaddr' in event IGMP.10"
    ::= { igmpEventObjects10 1 }

igmp10_interface OBJECT-TYPE
    SYNTAX DisplayString
    MAX-ACCESS accessible-for-notify
    STATUS current
    DESCRIPTION
        "Parameter 'interface' in event IGMP.10"
    ::= { igmpEventObjects10 2 }

igmpEventObjects11 OBJECT-IDENTITY
    STATUS current
    DESCRIPTION
        "Event IGMP.11
        A packet received from specified address on specified interface, was
        discarded by the igmp host part."
    ::= { igmpEventsGroup 11 }

igmp11_srcaddr OBJECT-TYPE
    SYNTAX IpAddress
    MAX-ACCESS accessible-for-notify
    STATUS current
    DESCRIPTION
        "Parameter 'srcaddr' in event IGMP.11"
    ::= { igmpEventObjects11 1 }

igmp11_interface OBJECT-TYPE
    SYNTAX DisplayString
    MAX-ACCESS accessible-for-notify
    STATUS current
    DESCRIPTION
        "Parameter 'interface' in event IGMP.11"
    ::= { igmpEventObjects11 2 }

igmpEventObjects12 OBJECT-IDENTITY
    STATUS current
    DESCRIPTION
        "Event IGMP.12
        An igmp query of specified version was received from specified address
        on specified interface."
    ::= { igmpEventsGroup 12 }

igmp12_version OBJECT-TYPE
    SYNTAX Integer32
    MAX-ACCESS accessible-for-notify
    STATUS current
    DESCRIPTION
        "Parameter 'version' in event IGMP.12"
    ::= { igmpEventObjects12 1 }

igmp12_srcaddr OBJECT-TYPE
    SYNTAX IpAddress
    MAX-ACCESS accessible-for-notify
    STATUS current
    DESCRIPTION
        "Parameter 'srcaddr' in event IGMP.12"
    ::= { igmpEventObjects12 2 }

igmp12_interface OBJECT-TYPE
    SYNTAX DisplayString
    MAX-ACCESS accessible-for-notify
    STATUS current
    DESCRIPTION
        "Parameter 'interface' in event IGMP.12"
    ::= { igmpEventObjects12 3 }

igmpEventObjects13 OBJECT-IDENTITY
    STATUS current
    DESCRIPTION
        "Event IGMP.13
        An igmp report of specified version was received from specified address
        on specified interface."
    ::= { igmpEventsGroup 13 }

igmp13_version OBJECT-TYPE
    SYNTAX Integer32
    MAX-ACCESS accessible-for-notify
    STATUS current
    DESCRIPTION
        "Parameter 'version' in event IGMP.13"
    ::= { igmpEventObjects13 1 }

igmp13_srcaddr OBJECT-TYPE
    SYNTAX IpAddress
    MAX-ACCESS accessible-for-notify
    STATUS current
    DESCRIPTION
        "Parameter 'srcaddr' in event IGMP.13"
    ::= { igmpEventObjects13 2 }

igmp13_interface OBJECT-TYPE
    SYNTAX DisplayString
    MAX-ACCESS accessible-for-notify
    STATUS current
    DESCRIPTION
        "Parameter 'interface' in event IGMP.13"
    ::= { igmpEventObjects13 3 }

igmpEventObjects14 OBJECT-IDENTITY
    STATUS current
    DESCRIPTION
        "Event IGMP.14
        An igmp leave group message was received from specified address on
        specified interface."
    ::= { igmpEventsGroup 14 }

igmp14_srcaddr OBJECT-TYPE
    SYNTAX IpAddress
    MAX-ACCESS accessible-for-notify
    STATUS current
    DESCRIPTION
        "Parameter 'srcaddr' in event IGMP.14"
    ::= { igmpEventObjects14 1 }

igmp14_interface OBJECT-TYPE
    SYNTAX DisplayString
    MAX-ACCESS accessible-for-notify
    STATUS current
    DESCRIPTION
        "Parameter 'interface' in event IGMP.14"
    ::= { igmpEventObjects14 2 }

igmpEventObjects15 OBJECT-IDENTITY
    STATUS current
    DESCRIPTION
        "Event IGMP.15
        An igmp query of specified version was sent to specified interface."
    ::= { igmpEventsGroup 15 }

igmp15_version OBJECT-TYPE
    SYNTAX Integer32
    MAX-ACCESS accessible-for-notify
    STATUS current
    DESCRIPTION
        "Parameter 'version' in event IGMP.15"
    ::= { igmpEventObjects15 1 }

igmp15_interface OBJECT-TYPE
    SYNTAX DisplayString
    MAX-ACCESS accessible-for-notify
    STATUS current
    DESCRIPTION
        "Parameter 'interface' in event IGMP.15"
    ::= { igmpEventObjects15 2 }

igmpEventObjects16 OBJECT-IDENTITY
    STATUS current
    DESCRIPTION
        "Event IGMP.16
        An error occurred trying to send an igmp query of specified version to
        specified interface."
    ::= { igmpEventsGroup 16 }

igmp16_version OBJECT-TYPE
    SYNTAX Integer32
    MAX-ACCESS accessible-for-notify
    STATUS current
    DESCRIPTION
        "Parameter 'version' in event IGMP.16"
    ::= { igmpEventObjects16 1 }

igmp16_interface OBJECT-TYPE
    SYNTAX DisplayString
    MAX-ACCESS accessible-for-notify
    STATUS current
    DESCRIPTION
        "Parameter 'interface' in event IGMP.16"
    ::= { igmpEventObjects16 2 }

igmpEventObjects17 OBJECT-IDENTITY
    STATUS current
    DESCRIPTION
        "Event IGMP.17
        An igmp report of specified version and group was sent to specified
        interface."
    ::= { igmpEventsGroup 17 }

igmp17_version OBJECT-TYPE
    SYNTAX Integer32
    MAX-ACCESS accessible-for-notify
    STATUS current
    DESCRIPTION
        "Parameter 'version' in event IGMP.17"
    ::= { igmpEventObjects17 1 }

igmp17_group OBJECT-TYPE
    SYNTAX IpAddress
    MAX-ACCESS accessible-for-notify
    STATUS current
    DESCRIPTION
        "Parameter 'group' in event IGMP.17"
    ::= { igmpEventObjects17 2 }

igmp17_interface OBJECT-TYPE
    SYNTAX DisplayString
    MAX-ACCESS accessible-for-notify
    STATUS current
    DESCRIPTION
        "Parameter 'interface' in event IGMP.17"
    ::= { igmpEventObjects17 3 }

igmpEventObjects18 OBJECT-IDENTITY
    STATUS current
    DESCRIPTION
        "Event IGMP.18
        An error occurred trying to send an igmp report of specified version and
        group to specified interface."
    ::= { igmpEventsGroup 18 }

igmp18_version OBJECT-TYPE
    SYNTAX Integer32
    MAX-ACCESS accessible-for-notify
    STATUS current
    DESCRIPTION
        "Parameter 'version' in event IGMP.18"
    ::= { igmpEventObjects18 1 }

igmp18_group OBJECT-TYPE
    SYNTAX IpAddress
    MAX-ACCESS accessible-for-notify
    STATUS current
    DESCRIPTION
        "Parameter 'group' in event IGMP.18"
    ::= { igmpEventObjects18 2 }

igmp18_interface OBJECT-TYPE
    SYNTAX DisplayString
    MAX-ACCESS accessible-for-notify
    STATUS current
    DESCRIPTION
        "Parameter 'interface' in event IGMP.18"
    ::= { igmpEventObjects18 3 }

igmpEventObjects19 OBJECT-IDENTITY
    STATUS current
    DESCRIPTION
        "Event IGMP.19
        An igmp leave group message was sent to specified interface."
    ::= { igmpEventsGroup 19 }

igmp19_group OBJECT-TYPE
    SYNTAX IpAddress
    MAX-ACCESS accessible-for-notify
    STATUS current
    DESCRIPTION
        "Parameter 'group' in event IGMP.19"
    ::= { igmpEventObjects19 1 }

igmp19_interface OBJECT-TYPE
    SYNTAX DisplayString
    MAX-ACCESS accessible-for-notify
    STATUS current
    DESCRIPTION
        "Parameter 'interface' in event IGMP.19"
    ::= { igmpEventObjects19 2 }

igmpEventObjects20 OBJECT-IDENTITY
    STATUS current
    DESCRIPTION
        "Event IGMP.20
        An error occurred trying to send an igmp leave group message to
        specified interface."
    ::= { igmpEventsGroup 20 }

igmp20_group OBJECT-TYPE
    SYNTAX IpAddress
    MAX-ACCESS accessible-for-notify
    STATUS current
    DESCRIPTION
        "Parameter 'group' in event IGMP.20"
    ::= { igmpEventObjects20 1 }

igmp20_interface OBJECT-TYPE
    SYNTAX DisplayString
    MAX-ACCESS accessible-for-notify
    STATUS current
    DESCRIPTION
        "Parameter 'interface' in event IGMP.20"
    ::= { igmpEventObjects20 2 }

igmpEventObjects21 OBJECT-IDENTITY
    STATUS current
    DESCRIPTION
        "Event IGMP.21
        Description of previous event."
    ::= { igmpEventsGroup 21 }

igmp21_description OBJECT-TYPE
    SYNTAX DisplayString
    MAX-ACCESS accessible-for-notify
    STATUS current
    DESCRIPTION
        "Parameter 'description' in event IGMP.21"
    ::= { igmpEventObjects21 1 }

igmpEventObjects22 OBJECT-IDENTITY
    STATUS current
    DESCRIPTION
        "Event IGMP.22
        igmp router processes received message."
    ::= { igmpEventsGroup 22 }

igmp22_message OBJECT-TYPE
    SYNTAX DisplayString
    MAX-ACCESS accessible-for-notify
    STATUS current
    DESCRIPTION
        "Parameter 'message' in event IGMP.22"
    ::= { igmpEventObjects22 1 }

igmpEventObjects23 OBJECT-IDENTITY
    STATUS current
    DESCRIPTION
        "Event IGMP.23
        igmp host processes received message."
    ::= { igmpEventsGroup 23 }

igmp23_message OBJECT-TYPE
    SYNTAX DisplayString
    MAX-ACCESS accessible-for-notify
    STATUS current
    DESCRIPTION
        "Parameter 'message' in event IGMP.23"
    ::= { igmpEventObjects23 1 }

igmpEventObjects24 OBJECT-IDENTITY
    STATUS current
    DESCRIPTION
        "Event IGMP.24
        igmp router error while processing received message."
    ::= { igmpEventsGroup 24 }

igmp24_message OBJECT-TYPE
    SYNTAX DisplayString
    MAX-ACCESS accessible-for-notify
    STATUS current
    DESCRIPTION
        "Parameter 'message' in event IGMP.24"
    ::= { igmpEventObjects24 1 }

igmpEventObjects25 OBJECT-IDENTITY
    STATUS current
    DESCRIPTION
        "Event IGMP.25
        igmp host error while processing received message."
    ::= { igmpEventsGroup 25 }

igmp25_message OBJECT-TYPE
    SYNTAX DisplayString
    MAX-ACCESS accessible-for-notify
    STATUS current
    DESCRIPTION
        "Parameter 'message' in event IGMP.25"
    ::= { igmpEventObjects25 1 }

igmpEventObjects26 OBJECT-IDENTITY
    STATUS current
    DESCRIPTION
        "Event IGMP.26
        igmp router denies given group based on given access list."
    ::= { igmpEventsGroup 26 }

igmp26_groupaddress OBJECT-TYPE
    SYNTAX DisplayString
    MAX-ACCESS accessible-for-notify
    STATUS current
    DESCRIPTION
        "Parameter 'groupaddress' in event IGMP.26"
    ::= { igmpEventObjects26 1 }

igmp26_accessgroup OBJECT-TYPE
    SYNTAX Integer32
    MAX-ACCESS accessible-for-notify
    STATUS current
    DESCRIPTION
        "Parameter 'accessgroup' in event IGMP.26"
    ::= { igmpEventObjects26 2 }

igmpEventObjects27 OBJECT-IDENTITY
    STATUS current
    DESCRIPTION
        "Event IGMP.27
        igmp router notifies a leaf addition or deletion in PIM for group and 
        source on interface."
    ::= { igmpEventsGroup 27 }

igmp27_action OBJECT-TYPE
    SYNTAX DisplayString
    MAX-ACCESS accessible-for-notify
    STATUS current
    DESCRIPTION
        "Parameter 'action' in event IGMP.27"
    ::= { igmpEventObjects27 1 }

igmp27_groupaddress OBJECT-TYPE
    SYNTAX IpAddress
    MAX-ACCESS accessible-for-notify
    STATUS current
    DESCRIPTION
        "Parameter 'groupaddress' in event IGMP.27"
    ::= { igmpEventObjects27 2 }

igmp27_srcaddress OBJECT-TYPE
    SYNTAX DisplayString
    MAX-ACCESS accessible-for-notify
    STATUS current
    DESCRIPTION
        "Parameter 'srcaddress' in event IGMP.27"
    ::= { igmpEventObjects27 3 }

igmp27_interface OBJECT-TYPE
    SYNTAX DisplayString
    MAX-ACCESS accessible-for-notify
    STATUS current
    DESCRIPTION
        "Parameter 'interface' in event IGMP.27"
    ::= { igmpEventObjects27 4 }

igmpEventObjects28 OBJECT-IDENTITY
    STATUS current
    DESCRIPTION
        "Event IGMP.28
        igmp router notifies an error in leaf addition or deletion in PIM for 
        group and source on interface."
    ::= { igmpEventsGroup 28 }

igmp28_action OBJECT-TYPE
    SYNTAX DisplayString
    MAX-ACCESS accessible-for-notify
    STATUS current
    DESCRIPTION
        "Parameter 'action' in event IGMP.28"
    ::= { igmpEventObjects28 1 }

igmp28_groupaddress OBJECT-TYPE
    SYNTAX IpAddress
    MAX-ACCESS accessible-for-notify
    STATUS current
    DESCRIPTION
        "Parameter 'groupaddress' in event IGMP.28"
    ::= { igmpEventObjects28 2 }

igmp28_srcaddress OBJECT-TYPE
    SYNTAX DisplayString
    MAX-ACCESS accessible-for-notify
    STATUS current
    DESCRIPTION
        "Parameter 'srcaddress' in event IGMP.28"
    ::= { igmpEventObjects28 3 }

igmp28_interface OBJECT-TYPE
    SYNTAX DisplayString
    MAX-ACCESS accessible-for-notify
    STATUS current
    DESCRIPTION
        "Parameter 'interface' in event IGMP.28"
    ::= { igmpEventObjects28 4 }

igmp28_message OBJECT-TYPE
    SYNTAX DisplayString
    MAX-ACCESS accessible-for-notify
    STATUS current
    DESCRIPTION
        "Parameter 'message' in event IGMP.28"
    ::= { igmpEventObjects28 5 }

igmpEventObjects29 OBJECT-IDENTITY
    STATUS current
    DESCRIPTION
        "Event IGMP.29
        igmp router or host notifies an error processing igmp messages."
    ::= { igmpEventsGroup 29 }

igmp29_role OBJECT-TYPE
    SYNTAX DisplayString
    MAX-ACCESS accessible-for-notify
    STATUS current
    DESCRIPTION
        "Parameter 'role' in event IGMP.29"
    ::= { igmpEventObjects29 1 }

igmp29_message OBJECT-TYPE
    SYNTAX DisplayString
    MAX-ACCESS accessible-for-notify
    STATUS current
    DESCRIPTION
        "Parameter 'message' in event IGMP.29"
    ::= { igmpEventObjects29 2 }


igmpNotification1 NOTIFICATION-TYPE
    OBJECTS { 
              igmp1_interface 
            }
    STATUS current
    DESCRIPTION
        "Notification of Event IGMP.1

        Message: 'router side igmp protocol initialized on interface $1'

        Parameters list:
              $1: igmp1_interface

        router side (downstream) part of igmp protocol has been initialized on
        specified interface."
    ::= { igmpNotificationsPrefix 1 }

igmpNotification2 NOTIFICATION-TYPE
    OBJECTS { 
              igmp2_interface 
            }
    STATUS current
    DESCRIPTION
        "Notification of Event IGMP.2

        Message: 'host side igmp protocol initialized on interface $1'

        Parameters list:
              $1: igmp2_interface

        host side (upstream) part of igmp protocol has been initialized on
        specified interface."
    ::= { igmpNotificationsPrefix 2 }

igmpNotification3 NOTIFICATION-TYPE
    OBJECTS { 
              igmp3_interface 
            }
    STATUS current
    DESCRIPTION
        "Notification of Event IGMP.3

        Message: 'start router igmp protocol on interface $1'

        Parameters list:
              $1: igmp3_interface

        Started operating router side (downstream) part of igmp protocol on
        specified interface."
    ::= { igmpNotificationsPrefix 3 }

igmpNotification4 NOTIFICATION-TYPE
    OBJECTS { 
              igmp4_interface 
            }
    STATUS current
    DESCRIPTION
        "Notification of Event IGMP.4

        Message: 'start host igmp protocol on interface $1'

        Parameters list:
              $1: igmp4_interface

        Started operating host side (upstream) part of igmp protocol on
        specified interface."
    ::= { igmpNotificationsPrefix 4 }

igmpNotification5 NOTIFICATION-TYPE
    OBJECTS { 
              igmp5_interface 
            }
    STATUS current
    DESCRIPTION
        "Notification of Event IGMP.5

        Message: 'stop router igmp protocol on interface $1'

        Parameters list:
              $1: igmp5_interface

        Stopped operating router side (downstream) part of igmp protocol on
        specified interface."
    ::= { igmpNotificationsPrefix 5 }

igmpNotification6 NOTIFICATION-TYPE
    OBJECTS { 
              igmp6_interface 
            }
    STATUS current
    DESCRIPTION
        "Notification of Event IGMP.6

        Message: 'stop host igmp protocol on interface $1'

        Parameters list:
              $1: igmp6_interface

        Stopped operating host side (upstream) part of igmp protocol on
        specified interface."
    ::= { igmpNotificationsPrefix 6 }

igmpNotification7 NOTIFICATION-TYPE
    OBJECTS { 
              igmp7_description 
            }
    STATUS current
    DESCRIPTION
        "Notification of Event IGMP.7

        Message: '$1'

        Parameters list:
              $1: igmp7_description

        Description of previous event."
    ::= { igmpNotificationsPrefix 7 }

igmpNotification8 NOTIFICATION-TYPE
    OBJECTS { 
              igmp8_srcaddr, 
              igmp8_interface 
            }
    STATUS current
    DESCRIPTION
        "Notification of Event IGMP.8

        Message: 'received errored packet from $1 on interface $2'

        Parameters list:
              $1: igmp8_srcaddr
              $2: igmp8_interface

        An errored packet was received from specified address on specified
        interface."
    ::= { igmpNotificationsPrefix 8 }

igmpNotification9 NOTIFICATION-TYPE
    OBJECTS { 
              igmp9_srcaddr, 
              igmp9_interface 
            }
    STATUS current
    DESCRIPTION
        "Notification of Event IGMP.9

        Message: 'discarded packet from $1 on interface $2'

        Parameters list:
              $1: igmp9_srcaddr
              $2: igmp9_interface

        A packet received from specified address on specified interface, was
        discarded."
    ::= { igmpNotificationsPrefix 9 }

igmpNotification10 NOTIFICATION-TYPE
    OBJECTS { 
              igmp10_srcaddr, 
              igmp10_interface 
            }
    STATUS current
    DESCRIPTION
        "Notification of Event IGMP.10

        Message: 'router discarded packet from $1 on interface $2'

        Parameters list:
              $1: igmp10_srcaddr
              $2: igmp10_interface

        A packet received from specified address on specified interface, was
        discarded by the igmp router part."
    ::= { igmpNotificationsPrefix 10 }

igmpNotification11 NOTIFICATION-TYPE
    OBJECTS { 
              igmp11_srcaddr, 
              igmp11_interface 
            }
    STATUS current
    DESCRIPTION
        "Notification of Event IGMP.11

        Message: 'host discarded packet from $1 on interface $2'

        Parameters list:
              $1: igmp11_srcaddr
              $2: igmp11_interface

        A packet received from specified address on specified interface, was
        discarded by the igmp host part."
    ::= { igmpNotificationsPrefix 11 }

igmpNotification12 NOTIFICATION-TYPE
    OBJECTS { 
              igmp12_version, 
              igmp12_srcaddr,
              igmp12_interface 
            }
    STATUS current
    DESCRIPTION
        "Notification of Event IGMP.12

        Message: 'received igmpv$1 query from $2 on interface $3'

        Parameters list:
              $1: igmp12_version
              $2: igmp12_srcaddr
              $3: igmp12_interface

        An igmp query of specified version was received from specified address
        on specified interface."
    ::= { igmpNotificationsPrefix 12 }

igmpNotification13 NOTIFICATION-TYPE
    OBJECTS { 
              igmp13_version, 
              igmp13_srcaddr,
              igmp13_interface 
            }
    STATUS current
    DESCRIPTION
        "Notification of Event IGMP.13

        Message: 'received igmpv$1 report from $2 on interface $3'

        Parameters list:
              $1: igmp13_version
              $2: igmp13_srcaddr
              $3: igmp13_interface

        An igmp report of specified version was received from specified address
        on specified interface."
    ::= { igmpNotificationsPrefix 13 }

igmpNotification14 NOTIFICATION-TYPE
    OBJECTS { 
              igmp14_srcaddr, 
              igmp14_interface 
            }
    STATUS current
    DESCRIPTION
        "Notification of Event IGMP.14

        Message: 'received igmpv2 leave group from $1 on interface $2'

        Parameters list:
              $1: igmp14_srcaddr
              $2: igmp14_interface

        An igmp leave group message was received from specified address on
        specified interface."
    ::= { igmpNotificationsPrefix 14 }

igmpNotification15 NOTIFICATION-TYPE
    OBJECTS { 
              igmp15_version, 
              igmp15_interface 
            }
    STATUS current
    DESCRIPTION
        "Notification of Event IGMP.15

        Message: 'sent igmpv$1 query to interface $2'

        Parameters list:
              $1: igmp15_version
              $2: igmp15_interface

        An igmp query of specified version was sent to specified interface."
    ::= { igmpNotificationsPrefix 15 }

igmpNotification16 NOTIFICATION-TYPE
    OBJECTS { 
              igmp16_version, 
              igmp16_interface 
            }
    STATUS current
    DESCRIPTION
        "Notification of Event IGMP.16

        Message: 'error sending igmpv$1 query to interface $2'

        Parameters list:
              $1: igmp16_version
              $2: igmp16_interface

        An error occurred trying to send an igmp query of specified version to
        specified interface."
    ::= { igmpNotificationsPrefix 16 }

igmpNotification17 NOTIFICATION-TYPE
    OBJECTS { 
              igmp17_version, 
              igmp17_group,
              igmp17_interface 
            }
    STATUS current
    DESCRIPTION
        "Notification of Event IGMP.17

        Message: 'sent igmpv$1 report of group $2 to interface $3'

        Parameters list:
              $1: igmp17_version
              $2: igmp17_group
              $3: igmp17_interface

        An igmp report of specified version and group was sent to specified
        interface."
    ::= { igmpNotificationsPrefix 17 }

igmpNotification18 NOTIFICATION-TYPE
    OBJECTS { 
              igmp18_version, 
              igmp18_group,
              igmp18_interface 
            }
    STATUS current
    DESCRIPTION
        "Notification of Event IGMP.18

        Message: 'error sending igmpv$1 report of group $2 to interface $3'

        Parameters list:
              $1: igmp18_version
              $2: igmp18_group
              $3: igmp18_interface

        An error occurred trying to send an igmp report of specified version and
        group to specified interface."
    ::= { igmpNotificationsPrefix 18 }

igmpNotification19 NOTIFICATION-TYPE
    OBJECTS { 
              igmp19_group, 
              igmp19_interface 
            }
    STATUS current
    DESCRIPTION
        "Notification of Event IGMP.19

        Message: 'sent igmpv2 leave group $1 to interface $2'

        Parameters list:
              $1: igmp19_group
              $2: igmp19_interface

        An igmp leave group message was sent to specified interface."
    ::= { igmpNotificationsPrefix 19 }

igmpNotification20 NOTIFICATION-TYPE
    OBJECTS { 
              igmp20_group, 
              igmp20_interface 
            }
    STATUS current
    DESCRIPTION
        "Notification of Event IGMP.20

        Message: 'error sending igmpv2 leave group $1 to interface $2'

        Parameters list:
              $1: igmp20_group
              $2: igmp20_interface

        An error occurred trying to send an igmp leave group message to
        specified interface."
    ::= { igmpNotificationsPrefix 20 }

igmpNotification21 NOTIFICATION-TYPE
    OBJECTS { 
              igmp21_description 
            }
    STATUS current
    DESCRIPTION
        "Notification of Event IGMP.21

        Message: '$1'

        Parameters list:
              $1: igmp21_description

        Description of previous event."
    ::= { igmpNotificationsPrefix 21 }

igmpNotification22 NOTIFICATION-TYPE
    OBJECTS { 
              igmp22_message 
            }
    STATUS current
    DESCRIPTION
        "Notification of Event IGMP.22

        Message: 'router process received $1'

        Parameters list:
              $1: igmp22_message

        igmp router processes received message."
    ::= { igmpNotificationsPrefix 22 }

igmpNotification23 NOTIFICATION-TYPE
    OBJECTS { 
              igmp23_message 
            }
    STATUS current
    DESCRIPTION
        "Notification of Event IGMP.23

        Message: 'host process received $1'

        Parameters list:
              $1: igmp23_message

        igmp host processes received message."
    ::= { igmpNotificationsPrefix 23 }

igmpNotification24 NOTIFICATION-TYPE
    OBJECTS { 
              igmp24_message 
            }
    STATUS current
    DESCRIPTION
        "Notification of Event IGMP.24

        Message: 'router process error $1'

        Parameters list:
              $1: igmp24_message

        igmp router error while processing received message."
    ::= { igmpNotificationsPrefix 24 }

igmpNotification25 NOTIFICATION-TYPE
    OBJECTS { 
              igmp25_message 
            }
    STATUS current
    DESCRIPTION
        "Notification of Event IGMP.25

        Message: 'host process error $1'

        Parameters list:
              $1: igmp25_message

        igmp host error while processing received message."
    ::= { igmpNotificationsPrefix 25 }

igmpNotification26 NOTIFICATION-TYPE
    OBJECTS { 
              igmp26_groupaddress, 
              igmp26_accessgroup 
            }
    STATUS current
    DESCRIPTION
        "Notification of Event IGMP.26

        Message: 'router deny group $1 access list $2'

        Parameters list:
              $1: igmp26_groupaddress
              $2: igmp26_accessgroup

        igmp router denies given group based on given access list."
    ::= { igmpNotificationsPrefix 26 }

igmpNotification27 NOTIFICATION-TYPE
    OBJECTS { 
              igmp27_action, 
              igmp27_groupaddress,
              igmp27_srcaddress,
              igmp27_interface 
            }
    STATUS current
    DESCRIPTION
        "Notification of Event IGMP.27

        Message: 'router $1 in PIM for group $2 from source $3 on interface $4'

        Parameters list:
              $1: igmp27_action
              $2: igmp27_groupaddress
              $3: igmp27_srcaddress
              $4: igmp27_interface

        igmp router notifies a leaf addition or deletion in PIM for group and 
        source on interface."
    ::= { igmpNotificationsPrefix 27 }

igmpNotification28 NOTIFICATION-TYPE
    OBJECTS { 
              igmp28_action, 
              igmp28_groupaddress,
              igmp28_srcaddress,
              igmp28_interface,
              igmp28_message 
            }
    STATUS current
    DESCRIPTION
        "Notification of Event IGMP.28

        Message: 'router err $1 in PIM for group $2 from source $3 on interface $4: $5'

        Parameters list:
              $1: igmp28_action
              $2: igmp28_groupaddress
              $3: igmp28_srcaddress
              $4: igmp28_interface
              $5: igmp28_message

        igmp router notifies an error in leaf addition or deletion in PIM for 
        group and source on interface."
    ::= { igmpNotificationsPrefix 28 }

igmpNotification29 NOTIFICATION-TYPE
    OBJECTS { 
              igmp29_role, 
              igmp29_message 
            }
    STATUS current
    DESCRIPTION
        "Notification of Event IGMP.29

        Message: '$1 ssm error: $2'

        Parameters list:
              $1: igmp29_role
              $2: igmp29_message

        igmp router or host notifies an error processing igmp messages."
    ::= { igmpNotificationsPrefix 29 }


END
