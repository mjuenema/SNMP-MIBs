--MibName=rcCfm
-- *****************************************************************
-- RAISECOM-CFM-MIB.mib
--
-- november 2007, chendonghua
--
-- Copyright(c) 2003-2005 by RAISECOM TECH, Ltd. 
-- All rights reserved.                
-- 11,20120704,liyanbao, Adding LB result table
-- 10,20120222,zhangfeng, add y1731-based fault alarm binding variable 
--  rcCfmMepExY1731DefectList    
-- 10,,20120518,zengwenwen,添加mpls-tp LT表，以及增加子网连接的相关mib
-- 09,20120113,zengwenwen,add lb table rcCfmMepExMplstpPingTable 
-- 08,20111231,yangkewei,ROS00008218,advent mib编译检查
-- 07，20111022，huochao,add scaler mibs default values.    
-- 06，20111021,huochao,modify rcCfmMdEntry 's index.
-- 05，20110915,huochao,add multicast lb result table.                                    
-- 04,20110711,zxh, Ros00007590
-- 03,20110530,yanguotao, add nodes for mpls-tp oam
-- 02,20101106,liangyunqing, line 63,add rcCfmMepExLckAdmin,	
--  rcCfmMaExAisSuppressStatus, rcCfmMaExAisTable,rcCfmMaExLckTable 
-- 01,20100714,liweixing,line 570,delete the comma
-- *****************************************************************


RAISECOM-CFM-MIB DEFINITIONS ::= BEGIN      
IMPORTS
    Integer32, Counter64,
    Unsigned32               			FROM SNMPv2-SMI    -- [RFC2578]  
    InterfaceIndexOrZero                FROM IF-MIB        -- [RFC2863]
    Dot1agCfmMDLevelOrNone,
    Dot1agCfmMepId,
    Dot1agCfmMDLevel,
    Dot1agCfmMepDefects,
    Dot1agCfmLowestAlarmPri,  
    Dot1agCfmMDLevel,
	dot1agCfmMdIndex, 
    dot1agCfmMaIndex,
    dot1agCfmMepIdentifier,   
    dot1agCfmMepIfIndex,
    dot1agCfmMaMepListIdentifier, 
    dot1agCfmMepDbRMepIdentifier        FROM IEEE8021-CFM-MIB
    Dot1agCfmMaintAssocNameType         FROM IEEE8021-CFM-MIB 
    Dot1agCfmMaintAssocName             FROM IEEE8021-CFM-MIB 
    Dot1agCfmCcmInterval                FROM IEEE8021-CFM-MIB   
    Dot1agCfmMaintDomainNameType        FROM IEEE8021-CFM-MIB  
    Dot1agCfmMaintDomainName            FROM IEEE8021-CFM-MIB 
    Dot1agCfmMpDirection                FROM IEEE8021-CFM-MIB 
	RowStatus,TruthValue,MacAddress     FROM SNMPv2-TC     -- [RFC2579]
    InterfaceIndex					    FROM IF-MIB        -- [RFC2863]
    EnableVar,ClearVar                  FROM SWITCH-TC
    iscomSwitch                         FROM RAISECOM-BASE-MIB
	VlanIdOrNone, VlanId     			FROM Q-BRIDGE-MIB
	InetAddressType, InetAddress        FROM INET-ADDRESS-MIB  -- [RFC4001]
    ;
rcCfm  MODULE-IDENTITY
    LAST-UPDATED   "200711020000Z"
    ORGANIZATION   "Raisecom, Inc."
    CONTACT-INFO  
                "       Raise Systems
                        
                Postal: Beijing,
                        China

                   Tel: 86-010-82884499

                E-mail: chendonghua@raisecom.com"
    DESCRIPTION
        "This MIB module defines objects to CFM "
        REVISION   "200711020000Z"
        DESCRIPTION
            "The initial revision of this MIB."
        ::={ iscomSwitch 26 } 

rcCfmBridge                   OBJECT IDENTIFIER ::= { rcCfm 1 }

-- MIB Object Definitions 
                                                                                                 
rcCfmBridgeAdminCfm        OBJECT-TYPE
	SYNTAX      EnableVar
    MAX-ACCESS  read-write
    STATUS      current
    DESCRIPTION
            "The administrative value of the bridge. 
            A value of TRUE(1) indicates that bridge should enable CFM. 
            FALSE(2) indicates that bridge should disable CFM" 
    DEFVAL { disable }
    ::= { rcCfmBridge 1 } 
      
rcCfmBridgeCcmDbArchiveHoldtime        OBJECT-TYPE 
	SYNTAX      Unsigned32 (1..65535)
    MAX-ACCESS  read-write
    STATUS      current
    DESCRIPTION
            "The holdtime of fault CCM in CC database."
    DEFVAL { 100 }
    ::= { rcCfmBridge 2 }
    
    
rcCfmBridgeTracerouteCacheEnable        OBJECT-TYPE
	SYNTAX      TruthValue
    MAX-ACCESS  read-write
    STATUS      current
    DESCRIPTION
            "Enable or disable to use traceroute database storing data."
    DEFVAL { false }
    ::= { rcCfmBridge 3 }

rcCfmBridgeTracerouteCacheHoldtime        OBJECT-TYPE 
	SYNTAX      Unsigned32 (1..65535)
    MAX-ACCESS  read-write
    STATUS      current
    DESCRIPTION
            "The holdtime of entries in traceroute database."
    DEFVAL { 100 }
    ::= { rcCfmBridge 4 }

rcCfmBridgeTracerouteCacheSize        OBJECT-TYPE 
	SYNTAX      Unsigned32(1..512)
    MAX-ACCESS  read-write
    STATUS      current
    DESCRIPTION
            "The number of entries in traceroute database."
    DEFVAL { 100 }
    ::= { rcCfmBridge 5 }

rcCfmBridgeTracerouteCacheClear        OBJECT-TYPE
	SYNTAX      ClearVar
    MAX-ACCESS  read-write
    STATUS      current
    DESCRIPTION
            "Clear the entries in traceroute database"
    DEFVAL{clear}
    ::= { rcCfmBridge 6 }    
    
rcCfmBridgeTrapConfig                  OBJECT-TYPE
	SYNTAX      Dot1agCfmLowestAlarmPri
    MAX-ACCESS  read-write
    STATUS      deprecated
    DESCRIPTION
            "An integer value specifying the lowest priority
             defect that is allowed to generate fault alarm. 
             It is similar to dot1agCfmMepLowPrDef, but the 
             difference is that this mib is used for bridge 
             and the latter is used for a mep. When this mib 
             is set, all meps configured in the bridge are 
             configured."
    DEFVAL {noXcon}
    ::= { rcCfmBridge 7 }   
    
rcCfmBridgeRmepAgeTime                  OBJECT-TYPE
	SYNTAX      Unsigned32 (1..65535)
    MAX-ACCESS  read-write         
    STATUS      current
    DESCRIPTION
            "An integer value specifying the age time of remote
             MEP that is dynamic."
    DEFVAL {100}      
    ::= { rcCfmBridge 8 }  
       
rcCfmBridgeMode                  OBJECT-TYPE
	SYNTAX   INTEGER{
                           master(1),
                           slave(2)                    
                    } 
    MAX-ACCESS  read-write         
    STATUS      current
    DESCRIPTION
            "An integer value specifying the mode of the sending of ccm.
             master(1) idendifies the mode of replying unicast CCM by peer device.
             slave(2) idendifies the mode of replying multicast CCM by peer device."
    DEFVAL {slave}
    ::= { rcCfmBridge 9 }    
    

rcCfmLinkVlanList OBJECT-TYPE
    SYNTAX      OCTET STRING (SIZE (512))  
    MAX-ACCESS  read-create
    STATUS      deprecated
    DESCRIPTION
       "The mapping VLANs with which the Maintenance Association is
        associated, or 0 if the MA is not attached to any VID."
    ::= { rcCfmBridge 10 }

rcCfmIccCode OBJECT-TYPE
    SYNTAX      OCTET STRING (SIZE (0..6))  
    MAX-ACCESS  read-write
    STATUS      current
    DESCRIPTION
       "Config ITU-T Carrier Code."
    ::= { rcCfmBridge 11 }

rcCfmIccNodeId OBJECT-TYPE
    SYNTAX      Unsigned32
    MAX-ACCESS  read-write
    STATUS      current
    DESCRIPTION
       "Config ICC nnode id value."
    ::= { rcCfmBridge 12 }

rcCfmMipId OBJECT-TYPE
    SYNTAX      INTEGER(0..8191)  
    MAX-ACCESS  read-write
    STATUS      deprecated
    DESCRIPTION
       "Mip id for per node."  
    DEFVAL {0}
    ::= { rcCfmBridge 13 }

rcCfmBridgeMplstpAdminCfm        OBJECT-TYPE
	SYNTAX      EnableVar
    MAX-ACCESS  read-write
    STATUS      current
    DESCRIPTION
            "The administrative value of the bridge. 
            A value of TRUE(1) indicates that bridge should enable CFM. 
            FALSE(2) indicates that bridge should disable CFM " 
    DEFVAL { disable }
    ::= { rcCfmBridge 14 }

 rcCfmBridgeMplstpCcmDbArchiveHoldtime        OBJECT-TYPE 
	SYNTAX      Unsigned32 (1..65535)
    MAX-ACCESS  read-write
    STATUS      current
    DESCRIPTION
            "The holdtime of fault CCM in CC database.(1-65535)"
    DEFVAL { 100 }
    ::= { rcCfmBridge 15 }

rcCfmBridgeMplstpRmepAgeTime                  OBJECT-TYPE
	SYNTAX      Unsigned32 (1..65535)
    MAX-ACCESS  read-write         
    STATUS      current
    DESCRIPTION
            "An integer value specifying the age time of remote
             MEP that is dynamic."
    DEFVAL {100}      
    ::= { rcCfmBridge 16 }  
 
    rcCfmMplsMdLevelEnable                  OBJECT-TYPE
	SYNTAX      EnableVar
	MAX-ACCESS  read-write         
    STATUS      current
    DESCRIPTION
            "The level valid state of MPLS MD."
    DEFVAL {enable}      
    ::= { rcCfmBridge 17 }  

    rcCfmBridgeMplstpChannelType             OBJECT-TYPE
	SYNTAX      Unsigned32 (1..65535)
	MAX-ACCESS  read-write         
    STATUS      current
    DESCRIPTION
            "The channel type of MPLS-TP OAM."
    DEFVAL {32762}      
    ::= { rcCfmBridge 18 }  
  
    rcCfmBridgeMplstpDynamicLearning             OBJECT-TYPE
	SYNTAX      EnableVar 
	MAX-ACCESS  read-write         
    STATUS      current
    DESCRIPTION
            "The state of MPLS-TP dynamic learning."
    DEFVAL {disable}      
    ::= { rcCfmBridge 19 }  
           
-- CFM Interface Table   

rcCfmIfTable OBJECT-TYPE
    SYNTAX      SEQUENCE OF RcCfmIfEntry
    MAX-ACCESS  not-accessible
    STATUS      current
    DESCRIPTION
        "CFM Interface table"
    ::= { rcCfm 2 }

rcCfmIfEntry   OBJECT-TYPE
    SYNTAX      RcCfmIfEntry
    MAX-ACCESS  not-accessible
    STATUS      current
    DESCRIPTION
        "An entry in the rcCfmIfTable. It contains
        CFM status in each interface port."
	INDEX        { rcCfmIfIndex }    
    ::={ rcCfmIfTable 1 }
    
    RcCfmIfEntry ::= SEQUENCE {
    rcCfmIfIndex					InterfaceIndex,
	rcCfmIfAdminCfm					EnableVar,
	rcCfmIfMipLevel					Dot1agCfmMDLevelOrNone		
}

rcCfmIfIndex        OBJECT-TYPE
	SYNTAX      InterfaceIndex
    MAX-ACCESS  not-accessible
    STATUS      current
    DESCRIPTION
            "This object represents the  Bridge Port or
             aggregated port on which MEPs or MHFs might
             be configured." 
	::= { rcCfmIfEntry 1 }
	
rcCfmIfAdminCfm        OBJECT-TYPE
	SYNTAX      EnableVar
    MAX-ACCESS  read-write
    STATUS      current
    DESCRIPTION
            "The administrative value of the interface.
            A value of enable(1) indicates that interface
            should enable CFM. disable(2) indicates that 
            interface should disable CFM."
    DEFVAL{enable}  
    ::= { rcCfmIfEntry 2 }    
     
rcCfmIfMipLevel        OBJECT-TYPE
	SYNTAX      Dot1agCfmMDLevelOrNone
    MAX-ACCESS  read-write
    STATUS      deprecated
    DESCRIPTION
            "The level on which the mip is configured. 
            The value of -1 indicates that no mip is configured 
            on the port or you must delete the mip configured on the port.
            The other value (0-7) indicates that a mip need to 
            be configured at this level on the port."
    ::= { rcCfmIfEntry 3 }    
    
-- CFM MD TABLE      
rcCfmMdTable OBJECT-TYPE
    SYNTAX      SEQUENCE OF RcCfmMdEntry
    MAX-ACCESS  not-accessible
    STATUS      current
    DESCRIPTION
        "CFM Md Table"  
        
    ::= { rcCfm 3 }

rcCfmMdEntry        OBJECT-TYPE
	SYNTAX      RcCfmMdEntry
    MAX-ACCESS  not-accessible
    STATUS      current
    DESCRIPTION
        "An entry in the rcCfmMdTable. It contains
         clearing remote MEP database operation."
    INDEX	{ dot1agCfmMdIndex }
    ::= { rcCfmMdTable 1 } 
       
    RcCfmMdEntry ::= SEQUENCE {
	rcCfmMdCcmRMpClear					ClearVar,
	rcCfmMdMdType						INTEGER		
}

rcCfmMdCcmRMpClear          OBJECT-TYPE
	SYNTAX      ClearVar
    MAX-ACCESS  read-write
    STATUS      current
    DESCRIPTION
            "Clear Remote MP in CC database"
    DEFVAL{clear}
    ::= { rcCfmMdEntry 1 }    
    
rcCfmMdMdType          OBJECT-TYPE    
     SYNTAX   INTEGER{
                       ethernet(1),
					   mpls-tp(2)
						} 
    MAX-ACCESS  read-write
    STATUS      current
    DESCRIPTION
            "MD type"      
            
    ::= { rcCfmMdEntry 2 }    

    
--CFM Error CCM Table    
rcCfmErrorCcmTable OBJECT-TYPE
    SYNTAX      SEQUENCE OF RcCfmErrorCcmEntry
    MAX-ACCESS  not-accessible
    STATUS      current
    DESCRIPTION
        "CFM Error CCM Table "  
        
    ::= { rcCfm 4 }
    
rcCfmErrorCcmEntry          OBJECT-TYPE
	SYNTAX      RcCfmErrorCcmEntry
    MAX-ACCESS  not-accessible
    STATUS      current
    DESCRIPTION
        "An entry in the rcCfmIfTable. It contains
        error CCM data received. 
        "
    INDEX		{ dot1agCfmMdIndex,
                  dot1agCfmMaIndex,
                  rcCfmErrorCcmRMepId,
                  rcCfmErrorCcmIndex
          }
    ::= { rcCfmErrorCcmTable 1 }  

RcCfmErrorCcmEntry ::= SEQUENCE { 
    rcCfmErrorCcmRMepId                 Dot1agCfmMepId,
	rcCfmErrorCcmIndex					Unsigned32 (0..4294967295),
	rcCfmErrorCcmLevel					Dot1agCfmMDLevel,
	rcCfmErrorCcmVlan					VlanIdOrNone ,
	rcCfmErrorCcmRecvMdName				OCTET STRING (SIZE(1..16)),
	rcCfmErrorCcmMaid					OCTET STRING (SIZE(1..44)),
	rcCfmErrorCcmMacAddress				MacAddress,
	rcCfmErrorCcmErrorType				Dot1agCfmMepDefects,
	rcCfmErrorCcmHoldTime               Unsigned32 (0..4294967295),
	rcCfmErrorCcmClear					ClearVar,
	rcCfmErrorCcmY1731ErrorType         INTEGER
}                  

rcCfmErrorCcmRMepId          		OBJECT-TYPE
	SYNTAX      Dot1agCfmMepId
    MAX-ACCESS  not-accessible
    STATUS      current
    DESCRIPTION
            "The index to the Error CCM table. Maintenance association End Point Identifier field of the 
            received CCM PDU that has some defect."
	::= { rcCfmErrorCcmEntry 1 }

   
rcCfmErrorCcmIndex          		OBJECT-TYPE
	SYNTAX      Unsigned32 (0..4294967295)
    MAX-ACCESS  not-accessible
    STATUS      current
    DESCRIPTION
            "The index to the Error CCM table. The index value
             should keep increasing up to the time that they wrap
             around. This is to facilitate access control based on OID."
	::= { rcCfmErrorCcmEntry 2 }
	
rcCfmErrorCcmLevel          		OBJECT-TYPE
	SYNTAX      Dot1agCfmMDLevel
	MAX-ACCESS  read-only
    STATUS      current
    DESCRIPTION
            "Maintenance Domain Level field of the received CCM PDU
             that has some defect."
	::= { rcCfmErrorCcmEntry 3 }

rcCfmErrorCcmVlan           		OBJECT-TYPE
	SYNTAX      VlanIdOrNone
	MAX-ACCESS  read-only
    STATUS      current
    DESCRIPTION
            "The VLAN ID associated with the MA Name field of the 
            received CCM PDU that has some defect."
	::= { rcCfmErrorCcmEntry 4 }

rcCfmErrorCcmRecvMdName     		OBJECT-TYPE
	SYNTAX      OCTET STRING (SIZE(1..16))
	MAX-ACCESS  read-only
    STATUS      current
    DESCRIPTION
            "The name of the domain in which the error ccm is received"
	::= { rcCfmErrorCcmEntry 5 }

rcCfmErrorCcmMaid           		OBJECT-TYPE
	SYNTAX      OCTET STRING (SIZE(1..44))
	MAX-ACCESS  read-only
    STATUS      current
    DESCRIPTION
            "Maintenance Domain name and Maintenance Association name 
            conveyed in the received CCM PDU that has some defect constitute
             MAID and the domain name and association name using  
             conjunctive character '-', for example, the domain name 
             is 'customer' and the association name is 'vlan100', so the 
             maid which is displayed to users is 'customer-vlan100'."
	::= { rcCfmErrorCcmEntry 6 }

rcCfmErrorCcmMacAddress          	OBJECT-TYPE
	SYNTAX      MacAddress
	MAX-ACCESS  read-only
    STATUS      current
    DESCRIPTION
            "Source MAC address field of the received CCM PDU that has 
            some defect."
	::= { rcCfmErrorCcmEntry 7 }

rcCfmErrorCcmErrorType             	OBJECT-TYPE
	SYNTAX      Dot1agCfmMepDefects
	MAX-ACCESS  read-only
    STATUS      current
    DESCRIPTION
            "Error type of defects in the received CCM PDU."
	::= { rcCfmErrorCcmEntry 8 } 
	   
rcCfmErrorCcmHoldTime        	OBJECT-TYPE
	SYNTAX      Unsigned32 (0..4294967295)
	MAX-ACCESS  read-only
    STATUS      current
    DESCRIPTION
            "Storage time (s) of defects in the ERROR CCM DB."
	::= { rcCfmErrorCcmEntry 9 }  

rcCfmErrorCcmClear                 	OBJECT-TYPE 
	SYNTAX      ClearVar
	MAX-ACCESS  read-write
    STATUS      current
    DESCRIPTION
            "Clear fault CCM in CC database"  
    DEFVAL {clear}
	::= { rcCfmErrorCcmEntry 10 }  
  
rcCfmErrorCcmY1731ErrorType       	OBJECT-TYPE
	SYNTAX      INTEGER{
                       dNONE(0), 
                       dUNL(1), 
                       dMMG(2),
                       dUNP(3),
                       dUNM(4),
                       dUNPr(5),
                       dLOC(6),
                       dRDI(7)
                    } 

	MAX-ACCESS  read-only
    STATUS      current
    DESCRIPTION
            "Error type of defects in the received CCM PDU with mdtype in Y.1731 format."
	::= { rcCfmErrorCcmEntry 11 } 
 
--CFM Ltm Db Table
rcCfmLtmDbTable 					OBJECT-TYPE
    SYNTAX      SEQUENCE OF RcCfmLtmDbEntry
    MAX-ACCESS  not-accessible
    STATUS      current
    DESCRIPTION
        "CFM Ltm Database Table "  
        
    ::= { rcCfm 5 }
    
rcCfmLtmDbEntry          			OBJECT-TYPE
	SYNTAX      RcCfmLtmDbEntry
    MAX-ACCESS  not-accessible
    STATUS      current
    DESCRIPTION
        "An entry in the rcCfmLtmDbTable.  
        "
    INDEX	{ dot1agCfmMdIndex, 
    		  dot1agCfmMaIndex,
    		  dot1agCfmMepIdentifier, 
    		  rcCfmLtmDbTransactionId 
    		}
    ::= { rcCfmLtmDbTable 1 }   
    
RcCfmLtmDbEntry ::= SEQUENCE {
	rcCfmLtmDbTransactionId				Unsigned32 (0..4294967295), 
	rcCfmLtmDbTargetMacAddress			MacAddress
}                    

rcCfmLtmDbTransactionId          	OBJECT-TYPE 
	SYNTAX      Unsigned32 (0..4294967295)
	MAX-ACCESS  not-accessible
    STATUS      current
    DESCRIPTION
            "The index to the Ltm Db table. This is to facilitate access control based on OID."
	::= { rcCfmLtmDbEntry 1 }  
   
rcCfmLtmDbTargetMacAddress          OBJECT-TYPE 
	SYNTAX      MacAddress 
	MAX-ACCESS  read-only
    STATUS      current
    DESCRIPTION
            "Target Mac Address conveyed in the LTM PDU which has been sent."
	::= { rcCfmLtmDbEntry 2 }  
           
--CFM Mep Db Extended Table
rcCfmMepDbExTable 					OBJECT-TYPE
    SYNTAX      SEQUENCE OF RcCfmMepDbExEntry
    MAX-ACCESS  not-accessible
    STATUS      current
    DESCRIPTION
        "CFM MEP Datebase Extended Table "  
        
    ::= { rcCfm 6 }
    
rcCfmMepDbExEntry          			OBJECT-TYPE
	SYNTAX      RcCfmMepDbExEntry
    MAX-ACCESS  not-accessible
    STATUS      current
    DESCRIPTION
        "An entry in the rcCfmMepDbExTable. "
    INDEX	{ dot1agCfmMdIndex, 
    		  dot1agCfmMaIndex,
    		  dot1agCfmMepIdentifier, 
    		  dot1agCfmMepDbRMepIdentifier 
    		}
    ::= { rcCfmMepDbExTable 1 } 
    
    RcCfmMepDbExEntry ::= SEQUENCE 
    {                                             
		rcCfmMepDbExEntryHoldTime				Unsigned32 (0..4294967295)
	} 
	                   
rcCfmMepDbExEntryHoldTime          OBJECT-TYPE 
	SYNTAX      Unsigned32 (0..4294967295) 
	MAX-ACCESS  read-only
    STATUS      current
    DESCRIPTION
            "The time of the remote MEP's information which has been storaged 
            in MEP CCM Database."
	::= { rcCfmMepDbExEntry 1 }      

-- CFM MA CC enabled Table	
rcCfmMaCciEnableTable 					OBJECT-TYPE
    SYNTAX      SEQUENCE OF RcCfmMaCciEnableEntry
    MAX-ACCESS  not-accessible
    STATUS      deprecated
    DESCRIPTION
        "CFM MEP Datebase Extended Table "  
        
    ::= { rcCfm 7 }
    
rcCfmMaCciEnableEntry          			OBJECT-TYPE
	SYNTAX      RcCfmMaCciEnableEntry
    MAX-ACCESS  not-accessible
    STATUS      deprecated
    DESCRIPTION
        "An entry in the rcCfmMepDbExTable. "
    INDEX	{ 
    		     rcCfmMaMdLevel,
    		     rcCfmMaMaVlanId
    		}
    ::= { rcCfmMaCciEnableTable 1 } 
    
    RcCfmMaCciEnableEntry ::= SEQUENCE 
    {                                             
		rcCfmMaMdLevel				Dot1agCfmMDLevel,
		rcCfmMaMaVlanId				VlanIdOrNone,
		rcCfmMaCciEnabled			TruthValue 	} 
	                   
rcCfmMaMdLevel          OBJECT-TYPE 
	SYNTAX      Dot1agCfmMDLevel 
	MAX-ACCESS  not-accessible
    STATUS      deprecated
    DESCRIPTION
            "Level of The Maintenance Domain that the MA belong to"
	::= { rcCfmMaCciEnableEntry 1 }   
	
rcCfmMaMaVlanId          OBJECT-TYPE 
	SYNTAX      VlanIdOrNone 
	MAX-ACCESS  not-accessible
    STATUS      deprecated
    DESCRIPTION
            "The Primary VLAN ID with which the Maintenance Association is associated"
	::= { rcCfmMaCciEnableEntry 2 }   
	
rcCfmMaCciEnabled          OBJECT-TYPE 
	SYNTAX      TruthValue 
	MAX-ACCESS  read-write
    STATUS      deprecated
    DESCRIPTION
            "If set to true, All MEP belong to the MA will generate CCM messages."
	::= { rcCfmMaCciEnableEntry 3 }   

--CFM Mep Extended Table
rcCfmMepExTable 					OBJECT-TYPE
    SYNTAX      SEQUENCE OF RcCfmMepExEntry
    MAX-ACCESS  not-accessible
    STATUS      current
    DESCRIPTION
        "CFM MEP Extended Table "  
        
    ::= { rcCfm 8 }
    
rcCfmMepExEntry          			OBJECT-TYPE
	SYNTAX      RcCfmMepExEntry
    MAX-ACCESS  not-accessible
    STATUS      current
    DESCRIPTION
        "An entry in the rcCfmMepTable. "
    INDEX	{ dot1agCfmMdIndex, 
    		  dot1agCfmMaIndex,
    		  dot1agCfmMepIdentifier 
    		}
    ::= { rcCfmMepExTable 1 } 
    
    RcCfmMepExEntry ::= SEQUENCE 
    {                                             
		rcCfmMepExLbrTimeoutNum				Unsigned32 (0..4294967295),
		rcCfmMepExTransmitLbmDataTlvLen     Unsigned32 (0..1484),  
		rcCfmMepExLckAdmin                  EnableVar,
		rcCfmMaExAisSuppressStatus          INTEGER,
		rcCfmMaExAisSuppressAdmin           EnableVar,
		rcCfmMepY1731HighestPrDefect        INTEGER,
		rcCfmMepExEthPingType               INTEGER,  
		rcCfmMepExEthPingTimeout            Unsigned32 (1..60),  
	        rcCfmMepExEthPingLbmPadType         INTEGER, 
		rcCfmMepExY1731DefectList           BITS,
		rcCfmMepExDot1agDefectList          BITS,
		rcCfmMepExLbResultOk                TruthValue,
        rcCfmMepExLbAbort                   EnableVar,
		rcCfmMepExType                      INTEGER    
	} 
	                   
rcCfmMepExLbrTimeoutNum          OBJECT-TYPE 
	SYNTAX      Unsigned32 (0..4294967295) 
	MAX-ACCESS  read-only
    STATUS      current
    DESCRIPTION
            "The total number of Lbrs revieving timeout. "
    DEFVAL{0}
	::= { rcCfmMepExEntry 1 }      

rcCfmMepExTransmitLbmDataTlvLen          OBJECT-TYPE 
	SYNTAX      Unsigned32 (0..1484) 
	MAX-ACCESS  read-write
    STATUS      current
    DESCRIPTION
            "The length of Lbm data tlv . "
    DEFVAL{0}
	::= { rcCfmMepExEntry 2 }      

rcCfmMepExLckAdmin          OBJECT-TYPE 
	SYNTAX      EnableVar 
	MAX-ACCESS  read-write
    STATUS      current
    DESCRIPTION
            "If set rcCfmMepExLckAdmin_enabled(1),The mep 
             can transmit lck packet when starting the lck 
             functionIf set rcCfmMepExLckAdmin_diabled (2),
             The mep must not transmit lck packet whatever 
             starting or stopping the lck function.
            "
    DEFVAL{disable}
	::= { rcCfmMepExEntry 3 } 
	
rcCfmMaExAisSuppressStatus          OBJECT-TYPE 
	SYNTAX      INTEGER 
	MAX-ACCESS  read-only
    STATUS      current
    DESCRIPTION
            "It is read-only. When receiving the ais or lck packet, 
             the value is rcCfmMaExAisSuppressStatus_WAITING (1). 
             And when the fault is detected, the value is 
             rcCfmMaExAisSuppressStatus_SUPPRESSED (2). 
             If not receiving the ais or lck pakcet within 
             3.5 multiple periods, the value is rcCfmMaExAisSuppressStatus_NONE (3).
             If the status is not rcCfmMaExAisSuppressStatus_NONE (1), 
             will not sending trap even if have any error.
            "
     DEFVAL{3}
	::= { rcCfmMepExEntry 4 } 
	
rcCfmMaExAisSuppressAdmin          OBJECT-TYPE 
	SYNTAX      EnableVar 
	MAX-ACCESS  read-write
    STATUS      current
    DESCRIPTION
            "If set rcCfmMaExAisSuppressAdmin_enabled (1), The mep can suppress alarm trap. 
             If set rcCfmMaExAisSuppressAdmin_diabled (2), The mep must not suppress alarm trap.
            "
    DEFVAL {enable}
	::= { rcCfmMepExEntry 5 } 
	
rcCfmMepY1731HighestPrDefect
OBJECT-TYPE
    SYNTAX   INTEGER{
                       dNONE(0),
                       dMMG(1),
                       dUNL(2),
                       dUNM(3),
                       dUNP(4),
                       dUNPr(5),
                       dLOC(6),
                       dRDI(7)
                    } 

    MAX-ACCESS  read-only
    STATUS      current
    DESCRIPTION
       "The highest priority defect that has been present since the
        MEPs Fault Notification Generator State Machine was last in
        the FNG_RESET state in mpls network.
       "
    REFERENCE
       "802.1ag clause 12.14.7.1.3:n  20.33.9 and Table 21-1" 
      DEFVAL {dNONE} 
    ::= { rcCfmMepExEntry 6 }
    
rcCfmMepExEthPingType          OBJECT-TYPE 
	SYNTAX      INTEGER{
                        cfm_eth_ping_none(0),
                        cfm_eth_ping_mep(1),
                        cfm_eth_ping_mac(2),
                        cfm_eth_ping_multicast(3)
                }
	MAX-ACCESS  read-write
    STATUS      current
    DESCRIPTION
            "The type of the ethernet ping action."   
    DEFVAL {cfm_eth_ping_none} 
	::= { rcCfmMepExEntry 7 }  
	
	rcCfmMepExEthPingTimeout    OBJECT-TYPE 
	SYNTAX      Unsigned32(1..60)
	MAX-ACCESS  read-write
	STATUS      current
    DESCRIPTION
            "The time wait for LBR once sending LBM,when out of time, it indicates 
            that ethernet ping operation has falied." 
    DEFVAL {5}  
	::= { rcCfmMepExEntry 8 }  
	
	rcCfmMepExEthPingLbmPadType    OBJECT-TYPE 
	SYNTAX      INTEGER{
                         cfm_eth_ping_invalid(0),
                         cfm_eth_ping_prbs(1),
                         cfm_eth_ping_prbs_crc(2),  
                         cfm_eth_ping_null(3),
                         cfm_eth_ping_null_crc(4)
                }
	MAX-ACCESS  read-write
	STATUS      current
    DESCRIPTION
            "The tlv type of lbm packet to send.when the value equals to cfm_eth_ping_invalid,
            the tlv type is data tlv"  
    DEFVAL {cfm_eth_ping_invalid}
	::= { rcCfmMepExEntry 9 }
	  	
rcCfmMepExY1731DefectList      OBJECT-TYPE
    SYNTAX     BITS{
                     dUNL(0),
                     dMMG(1),
                     dUNP(2),
                     dUNM(3),
                     dLOC(4),
                     dRDI(5)
                   } 
     MAX-ACCESS  read-only
     STATUS      current
     DESCRIPTION
            "The defect fault list in the type of Y1731."
     ::= { rcCfmMepExEntry 10 }           

rcCfmMepExDot1agDefectList      OBJECT-TYPE
    SYNTAX     BITS{
                     RDI(0),
                     MAC-Status(1),
                     Remote-CCM(2),
                     Error-CCM(3),
                     XCON(4)
                   } 
     MAX-ACCESS  read-only
     STATUS      current
     DESCRIPTION
            "The defect fault list in the type of Dot1ag."
     ::= { rcCfmMepExEntry 11 }    
  
  rcCfmMepExLbResultOk          OBJECT-TYPE 
	SYNTAX      TruthValue
    MAX-ACCESS  read-only
    STATUS      current
    DESCRIPTION
            "The result of lb operation.true indicate LB operation is sucecessful,false
             indicate LB operation is failed;as long as one LBM packect did not recieve 
             the correct response in specific time,the lb operation is considered failed."   
    DEFVAL {true} 
	::= { rcCfmMepExEntry 12 }  
 
rcCfmMepExLbAbort             OBJECT-TYPE                                                                
    SYNTAX      EnableVar 
    MAX-ACCESS  read-write
    STATUS      current
    DESCRIPTION
            "enable is set indicates that loopback operation is aborted."   
    DEFVAL {disable} 
	::= { rcCfmMepExEntry 13 }  

 
rcCfmMepExType             OBJECT-TYPE                                                                
    SYNTAX      INTEGER{  
                        interface(0),                   
                        node(1)
                       }    
    MAX-ACCESS  read-create
    STATUS      current
    DESCRIPTION
            "Indicate the type of MEP."   
    DEFVAL {interface} 
	::= { rcCfmMepExEntry 14 }  
      
	
--CFM Mep List Extended Table
rcCfmMaMepListExTable 					OBJECT-TYPE
    SYNTAX      SEQUENCE OF RcCfmMaMepListExEntry
    MAX-ACCESS  not-accessible
    STATUS      current
    DESCRIPTION
        "CFM Ma MEP List Extended Table "  
        
    ::= { rcCfm 9 }
    
rcCfmMaMepListExEntry          			OBJECT-TYPE
	SYNTAX      RcCfmMaMepListExEntry
    MAX-ACCESS  not-accessible
    STATUS      current
    DESCRIPTION
        "An entry in the rcCfmMepTable. "
    INDEX	{ dot1agCfmMdIndex, 
    		  dot1agCfmMaIndex,
    		  dot1agCfmMaMepListIdentifier 
    		}
    ::= { rcCfmMaMepListExTable 1 } 
    
    RcCfmMaMepListExEntry ::= SEQUENCE 
    {       
		rcCfmMaMepListType                  INTEGER,
		rcCfmMaMepListMacAddress		    MacAddress,      
		rcCfmMaMepListIfIndex		        InterfaceIndex,
	    rcCfmMaMepListMacAddressAdmin	    MacAddress
	} 
	                   
rcCfmMaMepListType          OBJECT-TYPE 
	SYNTAX      INTEGER{
                           local(1),
                           static_remote(2),
                           dynamic_remote(3)
                       } 
	MAX-ACCESS  read-write
    STATUS      deprecated
    DESCRIPTION
            "mep type in the mep list."
	::= { rcCfmMaMepListExEntry 1 }
	 
rcCfmMaMepListMacAddress          OBJECT-TYPE 
	SYNTAX      MacAddress
	MAX-ACCESS  read-only
    STATUS      current
    DESCRIPTION
            "mep mac address in mep list. "
	::= { rcCfmMaMepListExEntry 2 }      

rcCfmMaMepListIfIndex          OBJECT-TYPE 
	SYNTAX      InterfaceIndex
	MAX-ACCESS  read-write
    STATUS      current
    DESCRIPTION
            "interface index for static remote mep in port mode. "
	::= { rcCfmMaMepListExEntry 3 }      

rcCfmMaMepListMacAddressAdmin          OBJECT-TYPE 
	SYNTAX      MacAddress
	MAX-ACCESS  read-write
    STATUS      current
    DESCRIPTION
            "set mep mac address in mep list."
	::= { rcCfmMaMepListExEntry 4 }  
		
--CFM MaNet Extended Table
rcCfmMaNetExTable 					OBJECT-TYPE
    SYNTAX      SEQUENCE OF RcCfmMaNetExEntry
    MAX-ACCESS  not-accessible
    STATUS      current
    DESCRIPTION
        "CFM Ma net Extended Table "  
        
    ::= { rcCfm 10 }
    
rcCfmMaNetExEntry          			OBJECT-TYPE
	SYNTAX      RcCfmMaNetExEntry
    MAX-ACCESS  not-accessible
    STATUS      current
    DESCRIPTION
        "An entry in the rcCfmMaNetExTable. "
    INDEX	{ dot1agCfmMdIndex, 
    		  dot1agCfmMaIndex
    		}
    ::= { rcCfmMaNetExTable 1 } 
    
    RcCfmMaNetExEntry ::= SEQUENCE 
    {       
		rcCfmMaNetRemoteMepLearnEnabled                  TruthValue,
		rcCfmMaNetCostumerVlan                           VlanIdOrNone,
		rcCfmMaNetPduPriority                            Unsigned32 (0..7), 
		rcCfmMaNetRemoteMepLearnActive                   TruthValue,
		rcCfmMaNetCcCheckEnabled                         TruthValue                               
	} 
	                   
rcCfmMaNetRemoteMepLearnEnabled          OBJECT-TYPE 
	SYNTAX      TruthValue
	MAX-ACCESS  read-write
    STATUS      deprecated
    DESCRIPTION
            "status of remote mep learning. the value of true indicates that 
            mep in this ma can recieve unknown remote mep ccm pdu; the value 
            of false indicates that mep in this ma can not recieve unknown 
            remote mep ccm pdu. "
	::= { rcCfmMaNetExEntry 1 }
	
rcCfmMaNetCostumerVlan          OBJECT-TYPE 
	SYNTAX      VlanIdOrNone
	MAX-ACCESS  read-write
    STATUS      current
    DESCRIPTION
            "costumer vlan in oam pdu. the value of 0 indicates oam Pdu transmited 
            without costumer vlan."
    DEFVAL{0}            
	::= { rcCfmMaNetExEntry 2 }
	
rcCfmMaNetPduPriority          OBJECT-TYPE 
	SYNTAX      Unsigned32 (0..7)
	MAX-ACCESS  read-write
    STATUS      current
    DESCRIPTION
            "The pdu Priority. default priority is 6."
    DEFVAL{6} 
	::= { rcCfmMaNetExEntry 3 }
	
rcCfmMaNetRemoteMepLearnActive	 OBJECT-TYPE               
	SYNTAX      TruthValue
	MAX-ACCESS  read-write
    STATUS      current
    DESCRIPTION
            "Remote MEP Learn function is enabled."
    DEFVAL{false} 
	::= { rcCfmMaNetExEntry 4 }
	 
rcCfmMaNetCcCheckEnabled          OBJECT-TYPE 
	SYNTAX      TruthValue
	MAX-ACCESS  read-write
    STATUS      current
    DESCRIPTION
            "check remote mep mpid in CCM."
    DEFVAL{false} 
	::= { rcCfmMaNetExEntry 5 } 
	
--CFM Pm Table
rcCfmPMTable 					OBJECT-TYPE
    SYNTAX      SEQUENCE OF RcCfmPMEntry
    MAX-ACCESS  not-accessible
    STATUS      deprecated
    DESCRIPTION
        "CFM Performance monitor Table "  
        
    ::= { rcCfm 11 }
    
rcCfmPMEntry          			OBJECT-TYPE
	SYNTAX      RcCfmPMEntry
    MAX-ACCESS  not-accessible
    STATUS      deprecated
    DESCRIPTION
        "An entry in the rcCfmPMTable. "
    INDEX	{ 
              dot1agCfmMdIndex, 
    		  dot1agCfmMaIndex,
    		  dot1agCfmMepIdentifier,
    		  dot1agCfmMepDbRMepIdentifier
    		}
    ::= { rcCfmPMTable 1 } 
    
    RcCfmPMEntry ::= SEQUENCE 
    {       
		rcCfmPMEnabled                  TruthValue,
		rcCfmPMDmmTxInterval            INTEGER,
		rcCfmPMDelayObjective           Unsigned32 (0..1000),
		rcCfmPMDVObjective              Unsigned32 (0..1000),
		rcCfmPMFLRRisingThreshold       INTEGER,
		rcCfmPMFLRFallingThreshold      INTEGER,
		rcCfmPMDelayRisingThreshold     INTEGER,
		rcCfmPMDelayFallingThreshold    INTEGER,
		rcCfmPMDVRisingThreshold        INTEGER,
		rcCfmPMDVFallingThreshold       INTEGER,
		rcCfmPMStatiticsClear           INTEGER,
		rcCfmPMTrapSendEnable           TruthValue,
		rcCfmPMThroughputTimeout        Unsigned32(2..30),
		rcCfmPMThroughputObject         Unsigned32 (125..1000000),
		rcCfmPMThroughputPduLength      INTEGER,
		rcCfmPMThroughputEnable         TruthValue,
		rcCfmPMRowStatus                RowStatus
	}
	
rcCfmPMEnabled          OBJECT-TYPE 
	SYNTAX      TruthValue
	MAX-ACCESS  read-write
    STATUS      deprecated
    DESCRIPTION
            "performace monitor function enable "
	::= { rcCfmPMEntry 1 } 
	
rcCfmPMDmmTxInterval          OBJECT-TYPE 
	SYNTAX      INTEGER{
                  intervalInvalid   (0),
                  interval300Hz     (1),
                  interval10ms      (2),
                  interval100ms     (3),
                  interval1s        (4),
                  interval10s       (5),
                  interval1min      (6),
                  interval10min     (7)
	            }
	MAX-ACCESS  read-only
    STATUS      deprecated
    DESCRIPTION
            "DMM pdu transmit period. "
	::= { rcCfmPMEntry 2 }   
	
rcCfmPMDelayObjective          OBJECT-TYPE 
	SYNTAX      Unsigned32 (0..1000)
	MAX-ACCESS  read-write
    STATUS      deprecated
    DESCRIPTION
            "PM delay object."
	::= { rcCfmPMEntry 3 }
	 
rcCfmPMDVObjective          OBJECT-TYPE 
	SYNTAX      Unsigned32 (0..1000)
	MAX-ACCESS  read-write
    STATUS      deprecated
    DESCRIPTION
            "PM delay variation object. "
	::= { rcCfmPMEntry 4 }
                             
rcCfmPMFLRRisingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "frame loss ratio rising threshold, if 15 minutes 
             statistics above this value, a notification will be send. "
	::= { rcCfmPMEntry 5 }
	
rcCfmPMFLRFallingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "frame loss ratio falling threshold, if 15 minutes 
             statistics below this value, a notification will be send."
	::= { rcCfmPMEntry 6 }
	
rcCfmPMDelayRisingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "delay rising threshold, if 15 minutes 
             statistics above this value, a notification will be send."
	::= { rcCfmPMEntry 7 }

rcCfmPMDelayFallingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "delay falling threshold, if 15 minutes 
             statistics below this value, a notification will be send."
	::= { rcCfmPMEntry 8 } 

rcCfmPMDVRisingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "delay variation rising threshold, if 15 minutes 
             statistics above this value, a notification will be send."
	::= { rcCfmPMEntry 9 } 
	
rcCfmPMDVFallingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "delay variation falling threshold, if 15 minutes 
             statistics below this value, a notification will be send. "
	::= { rcCfmPMEntry 10 }
	
rcCfmPMStatiticsClear          OBJECT-TYPE 
	SYNTAX      INTEGER{
	            all              (0),
	            frame-loss-ratio (1),
	            delay            (2),
	            delay-variation  (3)
	            }
	MAX-ACCESS  read-write
    STATUS      deprecated
    DESCRIPTION
            "clear performance monitor statistics in the service. "
	::= { rcCfmPMEntry 11 }

rcCfmPMTrapSendEnable          OBJECT-TYPE 
	SYNTAX      TruthValue
	MAX-ACCESS  read-write
    STATUS      deprecated
    DESCRIPTION
            "performance monitor notification enable status."
	::= { rcCfmPMEntry 12 }

rcCfmPMThroughputTimeout          OBJECT-TYPE 
	SYNTAX      Unsigned32 (2..30)
	MAX-ACCESS  read-write
    STATUS      deprecated
    DESCRIPTION
            "ITU-T Y.1731 throughput(rfc2544) test timeout period, unit second."
	::= { rcCfmPMEntry 13 } 

rcCfmPMThroughputObject          OBJECT-TYPE 
	SYNTAX      Unsigned32 (125..1000000)
	MAX-ACCESS  read-write
    STATUS      deprecated
    DESCRIPTION
            "ITU-T Y.1731 throughput(rfc2544) test expected 
            Object band-wide, unit kbps."
	::= { rcCfmPMEntry 14 } 

rcCfmPMThroughputPduLength          OBJECT-TYPE 
	SYNTAX      INTEGER{
	            length64      (0),
	            length128     (1),
	            length256     (2),
	            length512     (3),
	            length1024    (4),
	            length1280    (5),
	            length1518    (6)
	            }
	MAX-ACCESS  read-write
    STATUS      deprecated
    DESCRIPTION
            "ITU-T Y.1731 throughput(rfc2544) test pdu length."
	::= { rcCfmPMEntry 15 }

rcCfmPMThroughputEnable          OBJECT-TYPE 
	SYNTAX      TruthValue
	MAX-ACCESS  read-write
    STATUS      deprecated
    DESCRIPTION
            "ITU-T Y.1731 throughput(rfc2544) test enable."
	::= { rcCfmPMEntry 16 }

rcCfmPMRowStatus          OBJECT-TYPE 
	SYNTAX      RowStatus
	MAX-ACCESS  read-write
    STATUS      deprecated
    DESCRIPTION
            "the row status of rcCfmPMTable. "
	::= { rcCfmPMEntry 17 }

--CFM Pm frame-loss-ratio total statistic Table
rcCfmPMFLRTotalTable 					OBJECT-TYPE
    SYNTAX      SEQUENCE OF RcCfmPMFLRTotalEntry
    MAX-ACCESS  not-accessible
    STATUS      deprecated
    DESCRIPTION
        "CFM Performance monitor Table "  
        
    ::= { rcCfm 12 }
    
rcCfmPMFLRTotalEntry          		OBJECT-TYPE
	SYNTAX      RcCfmPMFLRTotalEntry
    MAX-ACCESS  not-accessible
    STATUS      deprecated
    DESCRIPTION
        "An entry in the rcCfmPMTable. "
    INDEX	{ 
              dot1agCfmMdIndex, 
    		  dot1agCfmMaIndex,
    		  dot1agCfmMepIdentifier
    		}
    ::= { rcCfmPMFLRTotalTable 1 } 
    
    RcCfmPMFLRTotalEntry ::= SEQUENCE 
    {
        rcCfmPMFLRTotalElapsedTime              Unsigned32,
        rcCfmPMFLRTotalFarEndTxCounter          Unsigned32,
        rcCfmPMFLRTotalFarEndLostCounter        Unsigned32,
        rcCfmPMFLRTotalFarEndLossRatio          Unsigned32(0..1000),
        rcCfmPMFLRTotalFarEndUnaviableSecond    Unsigned32,
        rcCfmPMFLRTotalNearEndTxCounter         Unsigned32,
        rcCfmPMFLRTotalNearEndLostCounter       Unsigned32,
        rcCfmPMFLRTotalNearEndLossRatio         Unsigned32(0..1000),
        rcCfmPMFLRTotalNearEndUnaviableSecond   Unsigned32
    } 
          
rcCfmPMFLRTotalElapsedTime          OBJECT-TYPE 
	SYNTAX      Unsigned32
	MAX-ACCESS  read-only
    STATUS      deprecated
    DESCRIPTION
            "total second passed since performance monitor enabled."
	::= { rcCfmPMFLRTotalEntry 1 } 
	
rcCfmPMFLRTotalFarEndTxCounter          OBJECT-TYPE 
	SYNTAX      Unsigned32
	MAX-ACCESS  read-only
    STATUS      deprecated
    DESCRIPTION
            "total far end frames transmited since performance monitor enabled."
	::= { rcCfmPMFLRTotalEntry 2 }
	
rcCfmPMFLRTotalFarEndLostCounter          OBJECT-TYPE 
	SYNTAX      Unsigned32
	MAX-ACCESS  read-only
    STATUS      deprecated
    DESCRIPTION
            "total far end frames lost since performance monitor enabled."
	::= { rcCfmPMFLRTotalEntry 3 } 
	
rcCfmPMFLRTotalFarEndLossRatio          OBJECT-TYPE 
	SYNTAX      Unsigned32(0..1000)
	MAX-ACCESS  read-only
    STATUS      deprecated
    DESCRIPTION
            "total far end frame lost ratio since performance monitor enabled."
	::= { rcCfmPMFLRTotalEntry 4 }
	 
rcCfmPMFLRTotalFarEndUnaviableSecond          OBJECT-TYPE 
	SYNTAX      Unsigned32
	MAX-ACCESS  read-only
    STATUS      deprecated
    DESCRIPTION
            "total far end unaviable second since performance monitor enabled."
	::= { rcCfmPMFLRTotalEntry 5 }
		
rcCfmPMFLRTotalNearEndTxCounter          OBJECT-TYPE 
	SYNTAX      Unsigned32
	MAX-ACCESS  read-only
    STATUS      deprecated
    DESCRIPTION
            "total near end frames transmited since performance monitor enabled. "
	::= { rcCfmPMFLRTotalEntry 6 }
	
rcCfmPMFLRTotalNearEndLostCounter          OBJECT-TYPE 
	SYNTAX      Unsigned32
	MAX-ACCESS  read-only
    STATUS      deprecated
    DESCRIPTION
            "total near end frames lost since performance monitor enabled."
	::= { rcCfmPMFLRTotalEntry 7 } 
	
rcCfmPMFLRTotalNearEndLossRatio          OBJECT-TYPE 
	SYNTAX      Unsigned32(0..1000)
	MAX-ACCESS  read-only
    STATUS      deprecated
    DESCRIPTION
            "total near end frames lost ratio since performance monitor enabled."
	::= { rcCfmPMFLRTotalEntry 8 }
	 
rcCfmPMFLRTotalNearEndUnaviableSecond          OBJECT-TYPE 
	SYNTAX      Unsigned32
	MAX-ACCESS  read-only
    STATUS      deprecated
    DESCRIPTION
            "total near end unaviable seconds since performance monitor enabled."
	::= { rcCfmPMFLRTotalEntry 9 }
	
-- PM frame-loss-ratio current statistic table    
rcCfmPMFLRCurrentTable 					OBJECT-TYPE
    SYNTAX      SEQUENCE OF RcCfmPMFLRCurrentEntry
    MAX-ACCESS  not-accessible
    STATUS      deprecated
    DESCRIPTION
        "CFM Performance monitor frame loss ratio current table "  
        
    ::= { rcCfm 13 }

rcCfmPMFLRCurrentEntry          		OBJECT-TYPE
	SYNTAX      RcCfmPMFLRCurrentEntry
    MAX-ACCESS  not-accessible
    STATUS      deprecated
    DESCRIPTION
        "An entry in the rcCfmPMFLRCurrentTable. "
    INDEX	{ 
              dot1agCfmMdIndex, 
    		  dot1agCfmMaIndex,
    		  dot1agCfmMepIdentifier,
    		  rcCfmPMFLRCurrentPeriod
    		}
    ::= { rcCfmPMFLRCurrentTable 1 }
 
    RcCfmPMFLRCurrentEntry ::= SEQUENCE 
    {
        rcCfmPMFLRCurrentPeriod                     INTEGER,
        rcCfmPMFLRCurrentElapsedTime                Unsigned32,
        rcCfmPMFLRCurrentFarEndTxFrameCounter       Unsigned32,
        rcCfmPMFLRCurrentFarEndLostFrameCounter     Unsigned32,
        rcCfmPMFLRCurrentFarEndLossRatio            Unsigned32(0..1000),
        rcCfmPMFLRCurrentNearEndTxFrameCounter      Unsigned32,
        rcCfmPMFLRCurrentNearEndLostFrameCounter    Unsigned32,
        rcCfmPMFLRCurrentNearEndLossRatio           Unsigned32(0..1000)
    }
    
rcCfmPMFLRCurrentPeriod          OBJECT-TYPE 
	SYNTAX      INTEGER{
	            rcCfmPMFLRCurrentPeriod15Minutes(1),
	            rcCfmPMFLRCurrentPeriod24Hours  (2)
	            }
	MAX-ACCESS  not-accessible
    STATUS      deprecated
    DESCRIPTION
            "current period type ,15 minutes table or 24 hours table"
	::= { rcCfmPMFLRCurrentEntry 1 }

rcCfmPMFLRCurrentElapsedTime          OBJECT-TYPE 
	SYNTAX      Unsigned32
	MAX-ACCESS  read-only
    STATUS      deprecated
    DESCRIPTION
            "seconds passed in current intervla period."
	::= { rcCfmPMFLRCurrentEntry 2 } 
	
rcCfmPMFLRCurrentFarEndTxFrameCounter          OBJECT-TYPE 
	SYNTAX      Unsigned32
	MAX-ACCESS  read-only
    STATUS      deprecated
    DESCRIPTION
            "far end frames transmited in current interval. "
	::= { rcCfmPMFLRCurrentEntry 3 }
	
rcCfmPMFLRCurrentFarEndLostFrameCounter          OBJECT-TYPE 
	SYNTAX      Unsigned32
	MAX-ACCESS  read-only
    STATUS      deprecated
    DESCRIPTION
            "far end frames lost in current interval."
	::= { rcCfmPMFLRCurrentEntry 4 }
     
rcCfmPMFLRCurrentFarEndLossRatio          OBJECT-TYPE 
	SYNTAX      Unsigned32(0..1000)                                                
	MAX-ACCESS  read-only
    STATUS      deprecated
    DESCRIPTION
            "Far end frame loss ratio in current interval."
	::= { rcCfmPMFLRCurrentEntry 5 }   
	
rcCfmPMFLRCurrentNearEndTxFrameCounter          OBJECT-TYPE 
	SYNTAX      Unsigned32                                                
	MAX-ACCESS  read-only
    STATUS      deprecated
    DESCRIPTION
            "Near end frames transmited in current interval. "
	::= { rcCfmPMFLRCurrentEntry 6 }
	
rcCfmPMFLRCurrentNearEndLostFrameCounter          OBJECT-TYPE 
	SYNTAX      Unsigned32                                                
	MAX-ACCESS  read-only
    STATUS      deprecated
    DESCRIPTION
            "Near end frames lost in current interval."
	::= { rcCfmPMFLRCurrentEntry 7 }     
	
rcCfmPMFLRCurrentNearEndLossRatio          OBJECT-TYPE 
	SYNTAX      Unsigned32(0..1000)                                                
	MAX-ACCESS  read-only
    STATUS      deprecated
    DESCRIPTION
            "PDUs lost ratio from peer mep to local mep in current interval"
	::= { rcCfmPMFLRCurrentEntry 8 }
	
-- PM frame-loss-ratio interval statistic table    
rcCfmPMFLRIntervalTable 					OBJECT-TYPE
    SYNTAX      SEQUENCE OF RcCfmPMFLRIntervalEntry
    MAX-ACCESS  not-accessible
    STATUS      deprecated
    DESCRIPTION
        "CFM Performance monitor frame loss ratio interval Table "  
        
    ::= { rcCfm 14 }

rcCfmPMFLRIntervalEntry          		OBJECT-TYPE
	SYNTAX      RcCfmPMFLRIntervalEntry
    MAX-ACCESS  not-accessible
    STATUS      deprecated
    DESCRIPTION
        "An entry in the rcCfmPMFLRIntervalTable. "
    INDEX	{ 
              dot1agCfmMdIndex, 
    		  dot1agCfmMaIndex,
    		  dot1agCfmMepIdentifier,
      		  rcCfmPMFLRIntervalPeriod,
    		  rcCfmPMFLRIntervalIndex
    		}
    ::= { rcCfmPMFLRIntervalTable 1 }
 
    RcCfmPMFLRIntervalEntry ::= SEQUENCE 
    {
        rcCfmPMFLRIntervalPeriod                     INTEGER,
        rcCfmPMFLRIntervalIndex                      Unsigned32,
        rcCfmPMFLRIntervalPeerMepId                  Dot1agCfmMepId,
        rcCfmPMFLRIntervalBeginTime                  Unsigned32,
        rcCfmPMFLRIntervalFarEndTxFrameCounter       Unsigned32,
        rcCfmPMFLRIntervalFarEndLostFrameCounter     Unsigned32,
        rcCfmPMFLRIntervalFarEndLossRatio            Unsigned32(0..1000),
        rcCfmPMFLRIntervalNearEndTxFrameCounter      Unsigned32,
        rcCfmPMFLRIntervalNearEndLostFrameCounter    Unsigned32,
        rcCfmPMFLRIntervalNearEndLossRatio           Unsigned32(0..1000)
    }
    
rcCfmPMFLRIntervalPeriod          OBJECT-TYPE 
	SYNTAX      INTEGER{
	            rcCfmPMFLRIntervalPeriod15Minutes(1),
	            rcCfmPMFLRIntervalPeriod24Hours  (2)
	            }
	MAX-ACCESS  not-accessible
    STATUS      deprecated
    DESCRIPTION
            "interval period type ,history 15 minutes table or 24 hours table"
	::= { rcCfmPMFLRIntervalEntry 1 } 
	
rcCfmPMFLRIntervalIndex          OBJECT-TYPE 
	SYNTAX      Unsigned32
	MAX-ACCESS  not-accessible
    STATUS      deprecated
    DESCRIPTION
            "interval period index "
	::= { rcCfmPMFLRIntervalEntry 2 }

rcCfmPMFLRIntervalPeerMepId          OBJECT-TYPE 
	SYNTAX      Dot1agCfmMepId
	MAX-ACCESS  read-only
    STATUS      deprecated
    DESCRIPTION
            "peer remote mepid. "
	::= { rcCfmPMFLRIntervalEntry 3 }

	
rcCfmPMFLRIntervalBeginTime          OBJECT-TYPE 
	SYNTAX      Unsigned32
	MAX-ACCESS  read-only
    STATUS      deprecated
    DESCRIPTION
            "begin time in this intervla period, unit second. "
	::= { rcCfmPMFLRIntervalEntry 4 } 
	
rcCfmPMFLRIntervalFarEndTxFrameCounter          OBJECT-TYPE 
	SYNTAX      Unsigned32
	MAX-ACCESS  read-only
    STATUS      deprecated
    DESCRIPTION
            "far end frames transmited in this interval."
	::= { rcCfmPMFLRIntervalEntry 5 }
	
rcCfmPMFLRIntervalFarEndLostFrameCounter          OBJECT-TYPE 
	SYNTAX      Unsigned32
	MAX-ACCESS  read-only
    STATUS      deprecated
    DESCRIPTION
            "far end frames lost in this interval."
	::= { rcCfmPMFLRIntervalEntry 6 }
     
rcCfmPMFLRIntervalFarEndLossRatio          OBJECT-TYPE 
	SYNTAX      Unsigned32(0..1000)                                                
	MAX-ACCESS  read-only
    STATUS      deprecated
    DESCRIPTION
            "far end frame loss ratio in this interval."
	::= { rcCfmPMFLRIntervalEntry 7 }   
	
rcCfmPMFLRIntervalNearEndTxFrameCounter          OBJECT-TYPE 
	SYNTAX      Unsigned32                                                
	MAX-ACCESS  read-only
    STATUS      deprecated
    DESCRIPTION
            "near end frames transmited in this interval."
	::= { rcCfmPMFLRIntervalEntry 8 }
	
rcCfmPMFLRIntervalNearEndLostFrameCounter          OBJECT-TYPE 
	SYNTAX      Unsigned32                                                
	MAX-ACCESS  read-only
    STATUS      deprecated
    DESCRIPTION
            "near end frames lost in this interval."
	::= { rcCfmPMFLRIntervalEntry 9 }     
	
rcCfmPMFLRIntervalNearEndLossRatio          OBJECT-TYPE 
	SYNTAX      Unsigned32(0..1000)                                                
	MAX-ACCESS  read-only
    STATUS      deprecated
    DESCRIPTION
            "near end frame loss ratio in this interval."
	::= { rcCfmPMFLRIntervalEntry 10 }

-- PM delay current statistic table    
rcCfmPMDelayCurrentTable 					OBJECT-TYPE
    SYNTAX      SEQUENCE OF RcCfmPMDelayCurrentEntry
    MAX-ACCESS  not-accessible
    STATUS      deprecated
    DESCRIPTION
        "CFM Performance monitor delay current table "  
        
    ::= { rcCfm 15 }

rcCfmPMDelayCurrentEntry          		OBJECT-TYPE
	SYNTAX      RcCfmPMDelayCurrentEntry
    MAX-ACCESS  not-accessible
    STATUS      deprecated
    DESCRIPTION
        "An entry in the rcCfmPMDelayCurrentTable. "
    INDEX	{ 
              dot1agCfmMdIndex, 
    		  dot1agCfmMaIndex,
    		  dot1agCfmMepIdentifier,
    		  rcCfmPMDelayCurrentPeriod
    		}
    ::= { rcCfmPMDelayCurrentTable 1 }
 
    RcCfmPMDelayCurrentEntry ::= SEQUENCE 
    {
        rcCfmPMDelayCurrentPeriod                               INTEGER,
        rcCfmPMDelayCurrentFarEndAboveObjCounter                Unsigned32,
        rcCfmPMDelayCurrentFarEndBelowObjCounter                Unsigned32,
        rcCfmPMDelayCurrentFarEndMaxDelay                       Unsigned32,
        rcCfmPMDelayCurrentFarEndAvgDelay                       Unsigned32,
        rcCfmPMDelayCurrentFarEndMinDelay                       Unsigned32,
        rcCfmPMDelayCurrentNearEndAboveObjCounter               Unsigned32,
        rcCfmPMDelayCurrentNearEndBelowObjCounter               Unsigned32,
        rcCfmPMDelayCurrentNearEndMaxDelay                      Unsigned32,
        rcCfmPMDelayCurrentNearEndAvgDelay                      Unsigned32,
        rcCfmPMDelayCurrentNearEndMinDelay                      Unsigned32,
        rcCfmPMDelayCurrentRoundTripAboveObjCounter             Unsigned32,
        rcCfmPMDelayCurrentRoundTripBelowObjCounter             Unsigned32,
        rcCfmPMDelayCurrentRoundTripMaxDelay                    Unsigned32,
        rcCfmPMDelayCurrentRoundTripAvgDelay                    Unsigned32,
        rcCfmPMDelayCurrentRoundTripMinDelay                    Unsigned32
    }
    
rcCfmPMDelayCurrentPeriod          OBJECT-TYPE 
	SYNTAX      INTEGER{
	            rcCfmPMDelayCurrentPeriod15Minutes(1),
	            rcCfmPMDelayCurrentPeriod24Hours  (2)
	            }
	MAX-ACCESS  not-accessible
    STATUS      deprecated
    DESCRIPTION
            "current period type ,15 minutes table or 24 hours table."
	::= { rcCfmPMDelayCurrentEntry 1 }

rcCfmPMDelayCurrentFarEndAboveObjCounter          OBJECT-TYPE 
	SYNTAX      Unsigned32
	MAX-ACCESS  read-only
    STATUS      deprecated
    DESCRIPTION
            "numbers of far end delay above object in current interval."
	::= { rcCfmPMDelayCurrentEntry 2 } 
	
rcCfmPMDelayCurrentFarEndBelowObjCounter          OBJECT-TYPE 
	SYNTAX      Unsigned32
	MAX-ACCESS  read-only
    STATUS      deprecated
    DESCRIPTION
            "numbers of far end delay below object in current interval."
	::= { rcCfmPMDelayCurrentEntry 3 }
	
rcCfmPMDelayCurrentFarEndMaxDelay          OBJECT-TYPE 
	SYNTAX      Unsigned32
	MAX-ACCESS  read-only
    STATUS      deprecated
    DESCRIPTION
            "max far end delay in current interval, unit ms"
	::= { rcCfmPMDelayCurrentEntry 4 }
     
rcCfmPMDelayCurrentFarEndAvgDelay          OBJECT-TYPE 
	SYNTAX      Unsigned32                                                
	MAX-ACCESS  read-only
    STATUS      deprecated
    DESCRIPTION
            "average far end delay in current interval, unit ms"
	::= { rcCfmPMDelayCurrentEntry 5 }   
	
rcCfmPMDelayCurrentFarEndMinDelay          OBJECT-TYPE 
	SYNTAX      Unsigned32                                                
	MAX-ACCESS  read-only
    STATUS      deprecated
    DESCRIPTION
            "min far end delay in current interval, unit ms"
	::= { rcCfmPMDelayCurrentEntry 6 }
	
rcCfmPMDelayCurrentNearEndAboveObjCounter          OBJECT-TYPE 
	SYNTAX      Unsigned32                                                
	MAX-ACCESS  read-only
    STATUS      deprecated
    DESCRIPTION
            "numbers of near end delay above object in current interval."
	::= { rcCfmPMDelayCurrentEntry 7 }     
	
rcCfmPMDelayCurrentNearEndBelowObjCounter          OBJECT-TYPE 
	SYNTAX      Unsigned32                                                
	MAX-ACCESS  read-only
    STATUS      deprecated
    DESCRIPTION
            "numbers of near end delay below object in current interval."
	::= { rcCfmPMDelayCurrentEntry 8 }
	
rcCfmPMDelayCurrentNearEndMaxDelay          OBJECT-TYPE 
	SYNTAX      Unsigned32                                                
	MAX-ACCESS  read-only
    STATUS      deprecated
    DESCRIPTION
            "max near end delay in current interval, unit ms"
	::= { rcCfmPMDelayCurrentEntry 9 }

rcCfmPMDelayCurrentNearEndAvgDelay          OBJECT-TYPE 
	SYNTAX      Unsigned32                                                
	MAX-ACCESS  read-only
    STATUS      deprecated
    DESCRIPTION
            "average near end delay in current interval, unit ms"
	::= { rcCfmPMDelayCurrentEntry 10 }
	
rcCfmPMDelayCurrentNearEndMinDelay          OBJECT-TYPE 
	SYNTAX      Unsigned32                                                
	MAX-ACCESS  read-only
    STATUS      deprecated
    DESCRIPTION
            "min near end delay in current interval, unit ms"
	::= { rcCfmPMDelayCurrentEntry 11 }

rcCfmPMDelayCurrentRoundTripAboveObjCounter          OBJECT-TYPE 
	SYNTAX      Unsigned32                                                
	MAX-ACCESS  read-only
    STATUS      deprecated
    DESCRIPTION
            "numbers of round trip delay above object in current interval."
	::= { rcCfmPMDelayCurrentEntry 12 } 
	
rcCfmPMDelayCurrentRoundTripBelowObjCounter          OBJECT-TYPE 
	SYNTAX      Unsigned32                                                
	MAX-ACCESS  read-only
    STATUS      deprecated
    DESCRIPTION
            "numbers of round trip delay below object in current interval."
	::= { rcCfmPMDelayCurrentEntry 13 }
	
rcCfmPMDelayCurrentRoundTripMaxDelay          OBJECT-TYPE 
	SYNTAX      Unsigned32                                                
	MAX-ACCESS  read-only
    STATUS      deprecated
    DESCRIPTION
            "max round trip delay in current interval, unit ms"
	::= { rcCfmPMDelayCurrentEntry 14 }
	
rcCfmPMDelayCurrentRoundTripAvgDelay          OBJECT-TYPE 
	SYNTAX      Unsigned32                                                
	MAX-ACCESS  read-only
    STATUS      deprecated
    DESCRIPTION
            "averge round trip delay in current interval, unit ms"
	::= { rcCfmPMDelayCurrentEntry 15 }
	
rcCfmPMDelayCurrentRoundTripMinDelay          OBJECT-TYPE 
	SYNTAX      Unsigned32                                                
	MAX-ACCESS  read-only
    STATUS      deprecated
    DESCRIPTION
            "min round trip delay in current interval, unit ms"
	::= { rcCfmPMDelayCurrentEntry 16 }
	
-- PM delay interval statistic table    
rcCfmPMDelayIntervalTable 					OBJECT-TYPE
    SYNTAX      SEQUENCE OF RcCfmPMDelayIntervalEntry
    MAX-ACCESS  not-accessible
    STATUS      deprecated
    DESCRIPTION
        "CFM Performance monitor frame loss ratio current table "  
        
    ::= { rcCfm 16 }

rcCfmPMDelayIntervalEntry          		OBJECT-TYPE
	SYNTAX      RcCfmPMDelayIntervalEntry
    MAX-ACCESS  not-accessible
    STATUS      deprecated
    DESCRIPTION
        "An entry in the rcCfmPMDelayIntervalTable. "
    INDEX	{ 
              dot1agCfmMdIndex, 
    		  dot1agCfmMaIndex,
    		  dot1agCfmMepIdentifier,
    		  rcCfmPMDelayIntervalPeriod,
    		  rcCfmPMDelayIntervalIndex
    		}
    ::= { rcCfmPMDelayIntervalTable 1 }
 
    RcCfmPMDelayIntervalEntry ::= SEQUENCE 
    {
        rcCfmPMDelayIntervalPeriod                               INTEGER,
        rcCfmPMDelayIntervalIndex                                Unsigned32, 
        rcCfmPMDelayIntervalBeginTime                            Unsigned32,
        rcCfmPMDelayIntervalPeerMepId                            Dot1agCfmMepId,
        rcCfmPMDelayIntervalFarEndAboveObjCounter                Unsigned32,
        rcCfmPMDelayIntervalFarEndBelowObjCounter                Unsigned32,
        rcCfmPMDelayIntervalFarEndMaxDelay                       Unsigned32,
        rcCfmPMDelayIntervalFarEndAvgDelay                       Unsigned32,
        rcCfmPMDelayIntervalFarEndMinDelay                       Unsigned32,
        rcCfmPMDelayIntervalNearEndAboveObjCounter               Unsigned32,
        rcCfmPMDelayIntervalNearEndBelowObjCounter               Unsigned32,
        rcCfmPMDelayIntervalNearEndMaxDelay                      Unsigned32,
        rcCfmPMDelayIntervalNearEndAvgDelay                      Unsigned32,
        rcCfmPMDelayIntervalNearEndMinDelay                      Unsigned32,
        rcCfmPMDelayIntervalRoundTripAboveObjCounter             Unsigned32,
        rcCfmPMDelayIntervalRoundTripBelowObjCounter             Unsigned32,
        rcCfmPMDelayIntervalRoundTripMaxDelay                    Unsigned32,
        rcCfmPMDelayIntervalRoundTripAvgDelay                    Unsigned32,
        rcCfmPMDelayIntervalRoundTripMinDelay                    Unsigned32
    }
    
rcCfmPMDelayIntervalPeriod          OBJECT-TYPE 
	SYNTAX      INTEGER{
	            rcCfmPMDelayIntervalPeriod15Minutes(1),
	            rcCfmPMDelayIntervalPeriod24Hours  (2)
	            }
	MAX-ACCESS  not-accessible
    STATUS      deprecated
    DESCRIPTION
            "interval period type ,15 minutes table or 24 hours table"
	::= { rcCfmPMDelayIntervalEntry 1 }

rcCfmPMDelayIntervalIndex          OBJECT-TYPE 
	SYNTAX      Unsigned32
	MAX-ACCESS  not-accessible
    STATUS      deprecated
    DESCRIPTION
            "interval index."
	::= { rcCfmPMDelayIntervalEntry 2 }

rcCfmPMDelayIntervalBeginTime          OBJECT-TYPE 
	SYNTAX      Unsigned32
	MAX-ACCESS  read-only
    STATUS      deprecated
    DESCRIPTION
            "begin time in this intervla period, unit second. "
	::= { rcCfmPMDelayIntervalEntry 3 } 

rcCfmPMDelayIntervalPeerMepId          OBJECT-TYPE 
	SYNTAX      Dot1agCfmMepId
	MAX-ACCESS  read-only
    STATUS      deprecated
    DESCRIPTION
            "peer remote mepid. "
	::= { rcCfmPMDelayIntervalEntry 4 }

rcCfmPMDelayIntervalFarEndAboveObjCounter          OBJECT-TYPE 
	SYNTAX      Unsigned32
	MAX-ACCESS  read-only
    STATUS      deprecated
    DESCRIPTION
            "numbers of far end delay above object in this interval."
	::= { rcCfmPMDelayIntervalEntry 5 } 
	
rcCfmPMDelayIntervalFarEndBelowObjCounter          OBJECT-TYPE 
	SYNTAX      Unsigned32
	MAX-ACCESS  read-only
    STATUS      deprecated
    DESCRIPTION
            "numbers of far end delay below object in this interval."
	::= { rcCfmPMDelayIntervalEntry 6 }
	
rcCfmPMDelayIntervalFarEndMaxDelay          OBJECT-TYPE 
	SYNTAX      Unsigned32
	MAX-ACCESS  read-only
    STATUS      deprecated
    DESCRIPTION
            "max far end delay in this interval, unit ms"
	::= { rcCfmPMDelayIntervalEntry 7 }
     
rcCfmPMDelayIntervalFarEndAvgDelay          OBJECT-TYPE 
	SYNTAX      Unsigned32                                                
	MAX-ACCESS  read-only
    STATUS      deprecated
    DESCRIPTION
            "average far end delay in this interval, unit ms"
	::= { rcCfmPMDelayIntervalEntry 8 }   
	
rcCfmPMDelayIntervalFarEndMinDelay          OBJECT-TYPE 
	SYNTAX      Unsigned32                                                
	MAX-ACCESS  read-only
    STATUS      deprecated
    DESCRIPTION
            "min far end delay in this interval, unit ms"
	::= { rcCfmPMDelayIntervalEntry 9 }
	
rcCfmPMDelayIntervalNearEndAboveObjCounter          OBJECT-TYPE 
	SYNTAX      Unsigned32                                                
	MAX-ACCESS  read-only
    STATUS      deprecated
    DESCRIPTION
            "numbers of near end delay above object in this interval."
	::= { rcCfmPMDelayIntervalEntry 10 }     
	
rcCfmPMDelayIntervalNearEndBelowObjCounter          OBJECT-TYPE 
	SYNTAX      Unsigned32                                                
	MAX-ACCESS  read-only
    STATUS      deprecated
    DESCRIPTION
            "numbers of near end delay above object in this interval."
	::= { rcCfmPMDelayIntervalEntry 11 }
	
rcCfmPMDelayIntervalNearEndMaxDelay          OBJECT-TYPE 
	SYNTAX      Unsigned32                                                
	MAX-ACCESS  read-only
    STATUS      current
    DESCRIPTION
            "max near end delay in this interval, unit ms"
	::= { rcCfmPMDelayIntervalEntry 12 }

rcCfmPMDelayIntervalNearEndAvgDelay          OBJECT-TYPE 
	SYNTAX      Unsigned32                                                
	MAX-ACCESS  read-only
    STATUS      deprecated
    DESCRIPTION
            "average near end delay in this interval, unit ms"
	::= { rcCfmPMDelayIntervalEntry 13 }
	
rcCfmPMDelayIntervalNearEndMinDelay          OBJECT-TYPE 
	SYNTAX      Unsigned32                                                
	MAX-ACCESS  read-only
    STATUS      deprecated
    DESCRIPTION
            "min near end delay in this interval, unit ms"
	::= { rcCfmPMDelayIntervalEntry 14 }

rcCfmPMDelayIntervalRoundTripAboveObjCounter          OBJECT-TYPE 
	SYNTAX      Unsigned32                                                
	MAX-ACCESS  read-only
    STATUS      deprecated
    DESCRIPTION
            "numbers of round trip delay above object in this interval."
	::= { rcCfmPMDelayIntervalEntry 15 } 
	
rcCfmPMDelayIntervalRoundTripBelowObjCounter          OBJECT-TYPE 
	SYNTAX      Unsigned32                                                
	MAX-ACCESS  read-only
    STATUS      deprecated
    DESCRIPTION
            "numbers of round trip delay below object in this interval."
	::= { rcCfmPMDelayIntervalEntry 16 }
	
rcCfmPMDelayIntervalRoundTripMaxDelay          OBJECT-TYPE 
	SYNTAX      Unsigned32                                                
	MAX-ACCESS  read-only
    STATUS      deprecated
    DESCRIPTION
            "max round trip delay in this interval, unit ms"
	::= { rcCfmPMDelayIntervalEntry 17 }
	
rcCfmPMDelayIntervalRoundTripAvgDelay          OBJECT-TYPE 
	SYNTAX      Unsigned32                                                
	MAX-ACCESS  read-only
    STATUS      deprecated
    DESCRIPTION
            "average round trip delay in this interval, unit ms"
	::= { rcCfmPMDelayIntervalEntry 18 }
	
rcCfmPMDelayIntervalRoundTripMinDelay          OBJECT-TYPE 
	SYNTAX      Unsigned32                                                
	MAX-ACCESS  read-only
    STATUS      deprecated
    DESCRIPTION
            "min round trip delay in this interval, unit ms"
	::= { rcCfmPMDelayIntervalEntry 19 }
	
-- PM delay variation current statistic table    
rcCfmPMDVCurrentTable 					OBJECT-TYPE
    SYNTAX      SEQUENCE OF RcCfmPMDVCurrentEntry
    MAX-ACCESS  not-accessible
    STATUS      deprecated
    DESCRIPTION
        "CFM Performance monitor delay variation current table "  
        
    ::= { rcCfm 17 }

rcCfmPMDVCurrentEntry          		OBJECT-TYPE
	SYNTAX      RcCfmPMDVCurrentEntry
    MAX-ACCESS  not-accessible
    STATUS      deprecated
    DESCRIPTION
        "An entry in the rcCfmPMFLRCurrentTable. "
    INDEX	{ 
              dot1agCfmMdIndex, 
    		  dot1agCfmMaIndex,
    		  dot1agCfmMepIdentifier,
    		  rcCfmPMDVCurrentPeriod
    		}
    ::= { rcCfmPMDVCurrentTable 1 }
 
    RcCfmPMDVCurrentEntry ::= SEQUENCE 
    {
        rcCfmPMDVCurrentPeriod                               INTEGER,
        rcCfmPMDVCurrentFarEndAboveObjCounter                Unsigned32,
        rcCfmPMDVCurrentFarEndBelowObjCounter                Unsigned32,
        rcCfmPMDVCurrentFarEndMaxDv                          Unsigned32,
        rcCfmPMDVCurrentFarEndAvgDv                          Unsigned32,
        rcCfmPMDVCurrentNearEndAboveObjCounter               Unsigned32,
        rcCfmPMDVCurrentNearEndBelowObjCounter               Unsigned32,
        rcCfmPMDVCurrentNearEndMaxDv                         Unsigned32,
        rcCfmPMDVCurrentNearEndAvgDv                         Unsigned32,
        rcCfmPMDVCurrentRoundTripAboveObjCounter             Unsigned32,
        rcCfmPMDVCurrentRoundTripBelowObjCounter             Unsigned32,
        rcCfmPMDVCurrentRoundTripMaxDv                       Unsigned32,
        rcCfmPMDVCurrentRoundTripAvgDv                       Unsigned32
    }
    
rcCfmPMDVCurrentPeriod          OBJECT-TYPE 
	SYNTAX      INTEGER{
	            rcCfmPMDVCurrentPeriod15Minutes(1),
	            rcCfmPMDVCurrentPeriod24Hours  (2)
	            }
	MAX-ACCESS  not-accessible
    STATUS      deprecated
    DESCRIPTION
            "current period type ,15 minutes table or 24 hours table"
	::= { rcCfmPMDVCurrentEntry 1 }

rcCfmPMDVCurrentFarEndAboveObjCounter          OBJECT-TYPE 
	SYNTAX      Unsigned32
	MAX-ACCESS  read-only
    STATUS      deprecated
    DESCRIPTION
            "numbers of far end delay aviation above object in current interval."
	::= { rcCfmPMDVCurrentEntry 2 } 
	
rcCfmPMDVCurrentFarEndBelowObjCounter          OBJECT-TYPE 
	SYNTAX      Unsigned32
	MAX-ACCESS  read-only
    STATUS      deprecated
    DESCRIPTION
            "numbers of far end delay aviation below object in current interval."
	::= { rcCfmPMDVCurrentEntry 3 }
	
rcCfmPMDVCurrentFarEndMaxDv          OBJECT-TYPE 
	SYNTAX      Unsigned32
	MAX-ACCESS  read-only
    STATUS      deprecated
    DESCRIPTION
            "max far end delay variation in current interval, unit ms"
	::= { rcCfmPMDVCurrentEntry 4 }
     
rcCfmPMDVCurrentFarEndAvgDv          OBJECT-TYPE 
	SYNTAX      Unsigned32                                                
	MAX-ACCESS  read-only
    STATUS      deprecated
    DESCRIPTION
            "average far end delay variation in current interval, unit ms"
	::= { rcCfmPMDVCurrentEntry 5 }   
	
rcCfmPMDVCurrentNearEndAboveObjCounter          OBJECT-TYPE 
	SYNTAX      Unsigned32                                                
	MAX-ACCESS  read-only
    STATUS      deprecated
    DESCRIPTION
            "numbers of near end delay aviation above object in current interval."
	::= { rcCfmPMDVCurrentEntry 6 }     
	
rcCfmPMDVCurrentNearEndBelowObjCounter          OBJECT-TYPE 
	SYNTAX      Unsigned32                                                
	MAX-ACCESS  read-only
    STATUS      deprecated
    DESCRIPTION
            "numbers of near end delay aviation below object in current interval."
	::= { rcCfmPMDVCurrentEntry 7 }
	
rcCfmPMDVCurrentNearEndMaxDv          OBJECT-TYPE 
	SYNTAX      Unsigned32                                                
	MAX-ACCESS  read-only
    STATUS      deprecated
    DESCRIPTION
            "max far end delay variation in current interval, unit ms"
	::= { rcCfmPMDVCurrentEntry 8 }

rcCfmPMDVCurrentNearEndAvgDv          OBJECT-TYPE 
	SYNTAX      Unsigned32                                                
	MAX-ACCESS  read-only
    STATUS      deprecated
    DESCRIPTION
            "average far end delay variation in current interval, unit ms"
	::= { rcCfmPMDVCurrentEntry 9 }

rcCfmPMDVCurrentRoundTripAboveObjCounter          OBJECT-TYPE 
	SYNTAX      Unsigned32                                                
	MAX-ACCESS  read-only
    STATUS      deprecated
    DESCRIPTION
            "numbers of round trip delay aviation above object in current interval."
	::= { rcCfmPMDVCurrentEntry 10 } 
	
rcCfmPMDVCurrentRoundTripBelowObjCounter          OBJECT-TYPE 
	SYNTAX      Unsigned32                                                
	MAX-ACCESS  read-only
    STATUS      deprecated
    DESCRIPTION
            "numbers of round trip delay aviation below object in current interval."
	::= { rcCfmPMDVCurrentEntry 11 }
	
rcCfmPMDVCurrentRoundTripMaxDv          OBJECT-TYPE 
	SYNTAX      Unsigned32                                                
	MAX-ACCESS  read-only
    STATUS      deprecated
    DESCRIPTION
            "max far end delay variation in current interval, unit ms"
	::= { rcCfmPMDVCurrentEntry 12 }
	
rcCfmPMDVCurrentRoundTripAvgDv          OBJECT-TYPE 
	SYNTAX      Unsigned32                                                
	MAX-ACCESS  read-only
    STATUS      deprecated
    DESCRIPTION
            "average far end delay variation in current interval, unit ms"
	::= { rcCfmPMDVCurrentEntry 13 }
	
-- PM delay variation interval statistic table    
rcCfmPMDVIntervalTable 					OBJECT-TYPE
    SYNTAX      SEQUENCE OF RcCfmPMDVIntervalEntry
    MAX-ACCESS  not-accessible
    STATUS      deprecated
    DESCRIPTION
        "CFM Performance monitor delay variation interval table "  
        
    ::= { rcCfm 18 }

rcCfmPMDVIntervalEntry          		OBJECT-TYPE
	SYNTAX      RcCfmPMDVIntervalEntry
    MAX-ACCESS  not-accessible
    STATUS      deprecated
    DESCRIPTION
        "An entry in the rcCfmPMDelayIntervalTable. "
    INDEX	{ 
              dot1agCfmMdIndex, 
    		  dot1agCfmMaIndex,
    		  dot1agCfmMepIdentifier,
    		  rcCfmPMDVIntervalPeriod,
    		  rcCfmPMDVIntervalIndex
    		}
    ::= { rcCfmPMDVIntervalTable 1 }
 
    RcCfmPMDVIntervalEntry ::= SEQUENCE 
    {
        rcCfmPMDVIntervalPeriod                               INTEGER,
        rcCfmPMDVIntervalIndex                                Unsigned32,
        rcCfmPMDVIntervalBeginTime                            Unsigned32,  
        rcCfmPMDVIntervalPeerMepId                           Dot1agCfmMepId,
        rcCfmPMDVIntervalFarEndAboveObjCounter                Unsigned32,
        rcCfmPMDVIntervalFarEndBelowObjCounter                Unsigned32,
        rcCfmPMDVIntervalFarEndMaxDv                          Unsigned32,
        rcCfmPMDVIntervalFarEndAvgDv                          Unsigned32,
        rcCfmPMDVIntervalNearEndAboveObjCounter               Unsigned32,
        rcCfmPMDVIntervalNearEndBelowObjCounter               Unsigned32,
        rcCfmPMDVIntervalNearEndMaxDv                         Unsigned32,
        rcCfmPMDVIntervalNearEndAvgDv                         Unsigned32,
        rcCfmPMDVIntervalRoundTripAboveObjCounter             Unsigned32,
        rcCfmPMDVIntervalRoundTripBelowObjCounter             Unsigned32,
        rcCfmPMDVIntervalRoundTripMaxDv                       Unsigned32,
        rcCfmPMDVIntervalRoundTripAvgDv                       Unsigned32
    }
    
rcCfmPMDVIntervalPeriod          OBJECT-TYPE 
	SYNTAX      INTEGER{
	            rcCfmPMDVIntervalPeriod15Minutes(1),
	            rcCfmPMDVIntervalPeriod24Hours  (2)
	            }
	MAX-ACCESS  not-accessible
    STATUS      deprecated
    DESCRIPTION
            "interval period type ,15 minutes table or 24 hours table"
	::= { rcCfmPMDVIntervalEntry 1 }

rcCfmPMDVIntervalIndex          OBJECT-TYPE 
	SYNTAX      Unsigned32
	MAX-ACCESS  not-accessible
    STATUS      deprecated
    DESCRIPTION
            "interval period index."
	::= { rcCfmPMDVIntervalEntry 2 }

rcCfmPMDVIntervalBeginTime      OBJECT-TYPE 
	SYNTAX      Unsigned32
	MAX-ACCESS  read-only
    STATUS      deprecated
    DESCRIPTION
            "begin time in this intervla period, unit second. "
	::= { rcCfmPMDVIntervalEntry 3 } 


rcCfmPMDVIntervalPeerMepId     OBJECT-TYPE 
	SYNTAX      Dot1agCfmMepId
	MAX-ACCESS  read-only
    STATUS      deprecated
    DESCRIPTION
            "peer remote mepid."
	::= { rcCfmPMDVIntervalEntry 4 }

rcCfmPMDVIntervalFarEndAboveObjCounter          OBJECT-TYPE 
	SYNTAX      Unsigned32
	MAX-ACCESS  read-only
    STATUS      deprecated
    DESCRIPTION
            "numbers of far end delay variation above object in this interval."
	::= { rcCfmPMDVIntervalEntry 5 } 
	
rcCfmPMDVIntervalFarEndBelowObjCounter          OBJECT-TYPE 
	SYNTAX      Unsigned32
	MAX-ACCESS  read-only
    STATUS      deprecated
    DESCRIPTION
            "numbers of far end delay variation above object in this interval."
	::= { rcCfmPMDVIntervalEntry 6 }
	
rcCfmPMDVIntervalFarEndMaxDv          OBJECT-TYPE 
	SYNTAX      Unsigned32
	MAX-ACCESS  read-only
    STATUS      deprecated
    DESCRIPTION
            "max far end delay variation in this interval, unit ms"
	::= { rcCfmPMDVIntervalEntry 7 }
     
rcCfmPMDVIntervalFarEndAvgDv          OBJECT-TYPE 
	SYNTAX      Unsigned32                                                
	MAX-ACCESS  read-only
    STATUS      deprecated
    DESCRIPTION
            "average far end delay variation in this interval, unit ms"
	::= { rcCfmPMDVIntervalEntry 8 }   
	
rcCfmPMDVIntervalNearEndAboveObjCounter          OBJECT-TYPE 
	SYNTAX      Unsigned32                                                
	MAX-ACCESS  read-only
    STATUS      deprecated
    DESCRIPTION
            "numbers of near end delay variation above object in this interval."
	::= { rcCfmPMDVIntervalEntry 9 }     
	
rcCfmPMDVIntervalNearEndBelowObjCounter          OBJECT-TYPE 
	SYNTAX      Unsigned32                                                
	MAX-ACCESS  read-only
    STATUS      deprecated
    DESCRIPTION
            "numbers of near end delay variation below object in this interval."
	::= { rcCfmPMDVIntervalEntry 10 }
	
rcCfmPMDVIntervalNearEndMaxDv          OBJECT-TYPE 
	SYNTAX      Unsigned32                                                
	MAX-ACCESS  read-only
    STATUS      deprecated
    DESCRIPTION
            "max near end delay variation in this interval, unit ms"
	::= { rcCfmPMDVIntervalEntry 11 }

rcCfmPMDVIntervalNearEndAvgDv          OBJECT-TYPE 
	SYNTAX      Unsigned32                                                
	MAX-ACCESS  read-only
    STATUS      deprecated
    DESCRIPTION
            "average near end delay variation in this interval, unit ms"
	::= { rcCfmPMDVIntervalEntry 12 }

rcCfmPMDVIntervalRoundTripAboveObjCounter          OBJECT-TYPE 
	SYNTAX      Unsigned32                                                
	MAX-ACCESS  read-only
    STATUS      deprecated
    DESCRIPTION
            "numbers of round trip delay variation above object in this interval."
	::= { rcCfmPMDVIntervalEntry 13 } 
	
rcCfmPMDVIntervalRoundTripBelowObjCounter          OBJECT-TYPE 
	SYNTAX      Unsigned32                                                
	MAX-ACCESS  read-only
    STATUS      deprecated
    DESCRIPTION
            "numbers of round trip delay variation below object in this interval."
	::= { rcCfmPMDVIntervalEntry 14 }
	
rcCfmPMDVIntervalRoundTripMaxDv          OBJECT-TYPE 
	SYNTAX      Unsigned32                                                
	MAX-ACCESS  read-only
    STATUS      deprecated
    DESCRIPTION
            "max near end delay variation in this interval, unit ms"
	::= { rcCfmPMDVIntervalEntry 15 }
	
rcCfmPMDVIntervalRoundTripAvgDv          OBJECT-TYPE 
	SYNTAX      Unsigned32                                                
	MAX-ACCESS  read-only
    STATUS      deprecated
    DESCRIPTION
            "average near end delay variation in this interval, unit ms"
	::= { rcCfmPMDVIntervalEntry 16 }

-- rfc2544 throughput statistic table
rcCfmPMThroughputTable 					OBJECT-TYPE
    SYNTAX      SEQUENCE OF RcCfmPMThroughputEntry
    MAX-ACCESS  not-accessible
    STATUS      deprecated
    DESCRIPTION
        "ITU-T Y.1731 throughput(according to rfc2544) test statistics table."  
        
    ::= { rcCfm 19 }
    
rcCfmPMThroughputEntry          		OBJECT-TYPE
	SYNTAX      RcCfmPMThroughputEntry
    MAX-ACCESS  not-accessible
    STATUS      deprecated
    DESCRIPTION
        "An entry in the rcCfmPMTable. "
    INDEX	{ 
              dot1agCfmMdIndex, 
    		  dot1agCfmMaIndex,
    		  dot1agCfmMepIdentifier,
    		  dot1agCfmMepDbRMepIdentifier
    		}
    ::= { rcCfmPMThroughputTable 1 } 
    
    RcCfmPMThroughputEntry ::= SEQUENCE 
    {   
        rcCfmPMThroughputTestResult                 INTEGER,
        rcCfmPMThroughputTestState                  INTEGER,
        rcCfmPMThroughputFarEndSendbps              Counter64,
        rcCfmPMThroughputFarEndRecievebps           Counter64,
        rcCfmPMThroughputFarEndSendpps              Counter64,
        rcCfmPMThroughputFarEndRecievepps           Counter64,
        rcCfmPMThroughputNearEndSendbps             Counter64,
        rcCfmPMThroughputNearEndRecievebps          Counter64,
        rcCfmPMThroughputNearEndSendpps             Counter64,
        rcCfmPMThroughputNearEndRecievepps          Counter64
    }

rcCfmPMThroughputTestResult             OBJECT-TYPE 
	SYNTAX      INTEGER{         
	            successed                (0),
	            unknownReasonFailed      (1),
	            localReourceConflict     (2), 
	            remoteResourceConflict   (3),
	            vsxTimeOut               (4)
	            }                                               
	MAX-ACCESS  read-only
    STATUS      deprecated
    DESCRIPTION
            "result of rfc2544 throughput test."
	::= { rcCfmPMThroughputEntry 1 }

rcCfmPMThroughputTestState              OBJECT-TYPE 
	SYNTAX      INTEGER{
	            idle             (0),
	            farEndStart      (1),
	            farEndSend       (2),
	            farEndTest       (3),
	            nearEndStart     (4),
	            nearEndTest      (5),
	            nearEndClose     (6)
	            }                                               
	MAX-ACCESS  read-only
    STATUS      deprecated
    DESCRIPTION
            "state of rfc2544 throughput test."
	::= { rcCfmPMThroughputEntry 2 }

rcCfmPMThroughputFarEndSendbps          OBJECT-TYPE 
	SYNTAX      Counter64                                               
	MAX-ACCESS  read-only
    STATUS      deprecated
    DESCRIPTION
            "far end rfc2544 throughput flow sended statistics, unit bps."
	::= { rcCfmPMThroughputEntry 3 } 
	
rcCfmPMThroughputFarEndRecievebps       OBJECT-TYPE 
	SYNTAX      Counter64                                               
	MAX-ACCESS  read-only
    STATUS      deprecated
    DESCRIPTION
            "far end rfc2544 throughput flow received statistics, unit bps."
	::= { rcCfmPMThroughputEntry 4 }  
	
rcCfmPMThroughputFarEndSendpps          OBJECT-TYPE 
	SYNTAX      Counter64                                               
	MAX-ACCESS  read-only
    STATUS      deprecated
    DESCRIPTION
            "far end rfc2544 throughput flow sended statistics, unit pps."
	::= { rcCfmPMThroughputEntry 5 }
	 
rcCfmPMThroughputFarEndRecievepps       OBJECT-TYPE 
	SYNTAX      Counter64                                               
	MAX-ACCESS  read-only
    STATUS      deprecated
    DESCRIPTION
            "far end rfc2544 throughput flow received statistics, unit pps."
	::= { rcCfmPMThroughputEntry 6 } 
	
rcCfmPMThroughputNearEndSendbps          OBJECT-TYPE 
	SYNTAX      Counter64                                               
	MAX-ACCESS  read-only
    STATUS      deprecated
    DESCRIPTION
            "near end rfc2544 throughput flow sended statistics, unit bps."
	::= { rcCfmPMThroughputEntry 7 }
	 
rcCfmPMThroughputNearEndRecievebps       OBJECT-TYPE 
	SYNTAX      Counter64                                               
	MAX-ACCESS  read-only
    STATUS      deprecated
    DESCRIPTION
            "near end rfc2544 throughput flow received statistics, unit bps."
	::= { rcCfmPMThroughputEntry 8 }   
	
rcCfmPMThroughputNearEndSendpps          OBJECT-TYPE 
	SYNTAX      Counter64                                               
	MAX-ACCESS  read-only
    STATUS      deprecated
    DESCRIPTION
            "near end rfc2544 throughput flow sended statistics, unit pps."
	::= { rcCfmPMThroughputEntry 9 }
	 
rcCfmPMThroughputNearEndRecievepps       OBJECT-TYPE 
	SYNTAX      Counter64                                               
	MAX-ACCESS  read-only
    STATUS      deprecated
    DESCRIPTION
            "near end rfc2544 throughput flow received statistics, unit pps."
	::= { rcCfmPMThroughputEntry 10 }

--CFM Ma Extended Table
rcCfmMaExTable 					OBJECT-TYPE
    SYNTAX      SEQUENCE OF RcCfmMaExEntry
    MAX-ACCESS  not-accessible
    STATUS      current
    DESCRIPTION
        "CFM MA Extended Table "  
        
    ::= { rcCfm 20 }
    
rcCfmMaExEntry          			OBJECT-TYPE
	SYNTAX      RcCfmMaExEntry
    MAX-ACCESS  not-accessible
    STATUS      current
    DESCRIPTION
        "An entry in the rcCfmMaExTable. "
    INDEX	{ dot1agCfmMdIndex, 
    		  dot1agCfmMaIndex
    		}
    ::= { rcCfmMaExTable 1 } 
    
    RcCfmMaExEntry ::= SEQUENCE 
    {
		rcCfmMaExFormat             Dot1agCfmMaintAssocNameType,  
		rcCfmMaExName				Dot1agCfmMaintAssocName,
		rcCfmMaExVlanList           OCTET STRING (SIZE (512))  ,
		rcCfmMaExCcmInterval        Dot1agCfmCcmInterval,
		rcCfmMaExCostumerVlan       VlanIdOrNone,
		rcCfmMaExPduPriority        Unsigned32 (0..7),
        rcCfmMaExRowStatus          RowStatus,
		rcCfmMaExPrimaryVlanId      VlanIdOrNone,
		rcCfmMaExOamType            INTEGER,  
		rcCfmMaExVcid               INTEGER,
		rcCfmMaExIngressLspId       OCTET STRING (SIZE (0..32)),
		rcCfmMaExEgressLspId        OCTET STRING (SIZE (0..32)),
	    rcCfmMaExSection	        TruthValue,
	    rcCfmMaExMipLabel	        INTEGER, 
	    rcCfmMaExSectionMac         MacAddress,
	    rcCfmMaExAisLckSrcClear     ClearVar,                                                               
        rcCfmMaExPwPeerAddrType     InetAddressType,
        rcCfmMaExPwPeerAddr                      InetAddress,
        rcCfmMaExSncTtl                          INTEGER(0..255),
        rcCfmMaExSncLsridAddrType                InetAddressType,
        rcCfmMaExSncLsridAddr                    InetAddress,
        rcCfmMaExTransitForwardPwVcid            INTEGER,
        rcCfmMaExTransitForwardPwPeerAddrType    InetAddressType,
        rcCfmMaExTransitForwardPwPeerAddr        InetAddress,
        rcCfmMaExTransitBackwardPwVcid           INTEGER,
        rcCfmMaExTransitBackwardPwPeerAddrType   InetAddressType,
        rcCfmMaExTransitBackwardPwPeerAddr       InetAddress,
        rcCfmMaExForwardMipIfNum                 Unsigned32,
        rcCfmMaExBackwardMipIfNum                Unsigned32, 
        rcCfmMaExCcmStatisticClear               ClearVar,
        rcCfmMaExAisStatisticClear               ClearVar,
        rcCfmMaExLckStatisticClear               ClearVar,
        rcCfmMaExCsfStatisticClear               ClearVar,
        rcCfmMaExLmResponseEnable                EnableVar,
        rcCfmMaExSectionPort                     InterfaceIndexOrZero
	}
      
rcCfmMaExFormat OBJECT-TYPE
    SYNTAX      Dot1agCfmMaintAssocNameType
    MAX-ACCESS  read-create
    STATUS      current
    DESCRIPTION
       "The type (and thereby format) of the Maintenance Association
        Name.
       "
    REFERENCE
       "802.1ag clauses 21.6.5.4"
    ::= { rcCfmMaExEntry 1 }

rcCfmMaExName OBJECT-TYPE
    SYNTAX      Dot1agCfmMaintAssocName
    MAX-ACCESS  read-create
    STATUS      current
    DESCRIPTION
       "The Short Maintenance Association name. The type/format of
        this object is determined by the value of the
        dot1agCfmMaNetNameType object.  This name must be unique within
        a maintenance domain.
       "
    REFERENCE
       "802.1ag clauses 21.6.5.6, and Table 21-20"
    ::= { rcCfmMaExEntry 2 }  
    
rcCfmMaExVlanList OBJECT-TYPE
    SYNTAX      OCTET STRING (SIZE (512))  
    MAX-ACCESS  read-create
    STATUS      current
    DESCRIPTION
       "The mapping VLANs with which the Maintenance Association is
        associated, or 0 if the MA is not attached to any VID.
        When rcCfmMaExOamType is ether-oam(1) allowed to be configurated."
    ::= { rcCfmMaExEntry 3 }

rcCfmMaExCcmInterval OBJECT-TYPE
    SYNTAX      Dot1agCfmCcmInterval
    MAX-ACCESS  read-create
    STATUS      current
    DESCRIPTION
       "Interval between CCM transmissions to be used by all MEPs
        in the MA.
       "
    REFERENCE
       "802.1ag clause 12.14.6.1.3:e"
    DEFVAL { interval1s }
    ::= { rcCfmMaExEntry 4 }    
    
rcCfmMaExCostumerVlan OBJECT-TYPE
    SYNTAX      VlanIdOrNone
    MAX-ACCESS  read-create
    STATUS      current
    DESCRIPTION
        "costumer vlan in oam pdu. the value of 0 indicates oam Pdu transmited 
            without costumer vlan."
   DEFVAL{0}
	::= { rcCfmMaExEntry 5 }
	
rcCfmMaExPduPriority          OBJECT-TYPE 
	SYNTAX      Unsigned32 (0..7)
	MAX-ACCESS  read-create
    STATUS      current
    DESCRIPTION
            "The pdu Priority. default priority is 6."    
    DEFVAL {6}
	::= { rcCfmMaExEntry 6 }    

rcCfmMaExRowStatus OBJECT-TYPE
    SYNTAX      RowStatus
    MAX-ACCESS  read-create
    STATUS      current
    DESCRIPTION
       "The status of the row.

        The writable columns in a row can not be changed if the row
        is active. All columns must have a valid value before a row
        can be activated.
       "
    ::= {rcCfmMaExEntry 7 }
    	
rcCfmMaExPrimaryVlanId          OBJECT-TYPE 
	SYNTAX      VlanIdOrNone
	MAX-ACCESS  read-create
    STATUS      current
    DESCRIPTION
            "The PrimaryVlanId. default the minimum vlan in the vlanlist.
            When rcCfmMaExOamType is ether-oam(1) allowed to be configurated."    
    DEFVAL { 0 }
	::= { rcCfmMaExEntry 8 } 

rcCfmMaExOamType          OBJECT-TYPE 
	SYNTAX      INTEGER{  
	              mode-none(0),
                  ether-oam(1),
                  pw-oam(2),
                  lsp-oam(3),
                  section-oam(4),
                  transit-lsp-oam(5),
                  transit-pw-oam(6)
                }
	MAX-ACCESS  read-create
    STATUS      current
    DESCRIPTION
            "The OAM Type associated with the ma."    
    DEFVAL {mode-none}
	::= { rcCfmMaExEntry 9 } 
	                
rcCfmMaExVcid              OBJECT-TYPE 
	SYNTAX     INTEGER
	MAX-ACCESS  read-create
    STATUS      current
    DESCRIPTION
            "The VC ID associated with the ma.
            When rcCfmMaExOamType is pw-oam(2) allowed to be configurated."  
     DEFVAL {0}         
	::= { rcCfmMaExEntry 10 }     
	
rcCfmMaExIngressLspId        OBJECT-TYPE 
	SYNTAX     OCTET STRING (SIZE (0..32))
	MAX-ACCESS  read-create
    STATUS      current
    DESCRIPTION
            "The ingress LSP name associated with the ma.
            When rcCfmMaExOamType is lsp-oam(3) allowed to be configurated."    
	::= { rcCfmMaExEntry 11 } 

rcCfmMaExEgressLspId        OBJECT-TYPE 
	SYNTAX     OCTET STRING (SIZE (0..32))
	MAX-ACCESS  read-create
    STATUS      current
    DESCRIPTION
            "The egress LSP name associated with the ma.
            When rcCfmMaExOamType is lsp-oam(3) allowed to be configurated."    
	::= { rcCfmMaExEntry 12 } 
 
 rcCfmMaExSection        OBJECT-TYPE 
	SYNTAX     TruthValue
	MAX-ACCESS  read-create
    STATUS      deprecated
    DESCRIPTION
            "Whether the ma is associated with section oam or not."  
    DEFVAL {false}         
	::= { rcCfmMaExEntry 13 } 

 rcCfmMaExMipLabel        OBJECT-TYPE 
	SYNTAX     INTEGER
	MAX-ACCESS  read-create
	STATUS      deprecated
    DESCRIPTION
            "The pw label for the mip in the ma."  
    DEFVAL {0}  
	::= { rcCfmMaExEntry 14 } 

 rcCfmMaExSectionMac      OBJECT-TYPE
    SYNTAX     MacAddress  
    MAX-ACCESS  read-create
    STATUS      current
    DESCRIPTION
            "Dest mac specified in the layer of section"  
    DEFVAL {0}  
	::= { rcCfmMaExEntry 15 } 
  
 rcCfmMaExAisLckSrcClear      OBJECT-TYPE
    SYNTAX     ClearVar  
    MAX-ACCESS  read-create
    STATUS      current
    DESCRIPTION
            "Clear the statistics of received ais or lck source information."   
    DEFVAL {clear}  
	::= { rcCfmMaExEntry 16 } 
 
rcCfmMaExPwPeerAddrType OBJECT-TYPE
     SYNTAX        InetAddressType
     MAX-ACCESS    read-create
     STATUS        current
     DESCRIPTION
          "Denotes the address type of the peer node.  It should be
           set to 'unknown' if PE/PW maintenance protocol is not used
           and the address is unknown."
     DEFVAL { unknown }
     ::= { rcCfmMaExEntry 17 }

rcCfmMaExPwPeerAddr OBJECT-TYPE
     SYNTAX        InetAddress
     MAX-ACCESS    read-create
     STATUS        current
     DESCRIPTION
          "This object contains the value of the peer node address
           of the PW/PE maintenance protocol entity.  This object
           SHOULD contain a value of all zeroes if not applicable
           (rcCfmMaExPwPeerAddrType is 'unknown')."  
     DEFVAL { 0 }    
     ::= { rcCfmMaExEntry 18 }

rcCfmMaExSncTtl OBJECT-TYPE
     SYNTAX        INTEGER(0..255)
     MAX-ACCESS    read-create
     STATUS        current
     DESCRIPTION
          "The ttl of ma based transit."  
     DEFVAL { 0 }    
     ::= { rcCfmMaExEntry 19 }

rcCfmMaExSncLsridAddrType OBJECT-TYPE
     SYNTAX        InetAddressType
     MAX-ACCESS    read-create
     STATUS        current
     DESCRIPTION
          "Denotes the address type of Lsirid. It should be 
           set to 'unknown' if protocol is not used and the 
           address is unknown." 
     DEFVAL { unknown }
     ::= { rcCfmMaExEntry 20 }

rcCfmMaExSncLsridAddr OBJECT-TYPE
     SYNTAX        InetAddress
     MAX-ACCESS    read-create
     STATUS        current
     DESCRIPTION
          "This object contains the value of the lsrid address
           of the lsp maintenance protocol entity.  This object
           should contain a value of all zeroes if not applicable
           (rcCfmMaExSncLsridAddrType is 'unknown')." 
     DEFVAL { 0 }    
     ::= { rcCfmMaExEntry 21 }

rcCfmMaExTransitForwardPwVcid OBJECT-TYPE
     SYNTAX        INTEGER
     MAX-ACCESS    read-create
     STATUS        current
     DESCRIPTION
          "Transit PW forward VCID, and it is valid when 
           rcCfmMaExOamType is transit-pw-oam."  
     DEFVAL { 0 }    
     ::= { rcCfmMaExEntry 22 }

rcCfmMaExTransitForwardPwPeerAddrType OBJECT-TYPE
     SYNTAX        InetAddressType
     MAX-ACCESS    read-create
     STATUS        current
     DESCRIPTION
          "Transit PW forward peer address type, and it is
           valid when rcCfmMaExOamType is transit-pw-oam." 
     DEFVAL { unknown }
     ::= { rcCfmMaExEntry 23 }

rcCfmMaExTransitForwardPwPeerAddr OBJECT-TYPE
     SYNTAX        InetAddress
     MAX-ACCESS    read-create
     STATUS        current
     DESCRIPTION
          "Transit PW forward peer address, and it is valid
           when rcCfmMaExOamType is transit-pw-oam." 
     DEFVAL { 0 }    
     ::= { rcCfmMaExEntry 24 }

rcCfmMaExTransitBackwardPwVcid OBJECT-TYPE
     SYNTAX        INTEGER
     MAX-ACCESS    read-create
     STATUS        current
     DESCRIPTION
          "Transit PW backward VCID, and it is valid when 
           rcCfmMaExOamType is transit-pw-oam."  
     DEFVAL { 0 }    
     ::= { rcCfmMaExEntry 25 }

rcCfmMaExTransitBackwardPwPeerAddrType OBJECT-TYPE
     SYNTAX        InetAddressType
     MAX-ACCESS    read-create
     STATUS        current
     DESCRIPTION
          "Transit PW backward peer address type, and it is
           valid when rcCfmMaExOamType is transit-pw-oam." 
     DEFVAL { unknown }
     ::= { rcCfmMaExEntry 26 }

rcCfmMaExTransitBackwardPwPeerAddr OBJECT-TYPE
     SYNTAX        InetAddress
     MAX-ACCESS    read-create
     STATUS        current
     DESCRIPTION
          "Transit PW backward peer address, and it is valid
           when rcCfmMaExOamType is transit-pw-oam." 
     DEFVAL { 0 }    
     ::= { rcCfmMaExEntry 27 }

rcCfmMaExForwardMipIfNum OBJECT-TYPE
     SYNTAX        Unsigned32
     MAX-ACCESS    read-only
     STATUS        current
     DESCRIPTION
          "Forward MIP if-num." 
     DEFVAL { 0 }    
     ::= { rcCfmMaExEntry 28 }

rcCfmMaExBackwardMipIfNum OBJECT-TYPE
     SYNTAX        Unsigned32
     MAX-ACCESS    read-only
     STATUS        current
     DESCRIPTION
          "Backward MIP if-num." 
     DEFVAL { 0 }    
     ::= { rcCfmMaExEntry 29 }

rcCfmMaExCcmStatisticClear OBJECT-TYPE
     SYNTAX        ClearVar
     MAX-ACCESS    read-write
     STATUS        current
     DESCRIPTION
          "Clear CCM send statistic." 
     DEFVAL { 0 }    
     ::= { rcCfmMaExEntry 30 }

rcCfmMaExAisStatisticClear OBJECT-TYPE
     SYNTAX        ClearVar
     MAX-ACCESS    read-write
     STATUS        current
     DESCRIPTION
          "Clear AIS send and receive statistic." 
     DEFVAL { 0 }    
     ::= { rcCfmMaExEntry 31 }

rcCfmMaExLckStatisticClear OBJECT-TYPE
     SYNTAX        ClearVar
     MAX-ACCESS    read-write
     STATUS        current
     DESCRIPTION
          "Clear LCK send and receive statistic." 
     DEFVAL { 0 }    
     ::= { rcCfmMaExEntry 32 }
     
rcCfmMaExCsfStatisticClear OBJECT-TYPE
     SYNTAX        ClearVar
     MAX-ACCESS    read-write
     STATUS        current
     DESCRIPTION
          "Clear CSF send and receive statistic." 
     DEFVAL { 0 }    
     ::= { rcCfmMaExEntry 33 }   

rcCfmMaExLmResponseEnable        OBJECT-TYPE
	SYNTAX      EnableVar
    MAX-ACCESS  read-write
    STATUS      current
    DESCRIPTION
            "The administrative value of the pkt loss measurement response. 
            A value of TRUE(1) indicates that the current service should enable lm response. 
            FALSE(2) indicates the current service should disable lm response. " 
    DEFVAL { disable }
    ::= { rcCfmMaExEntry 34 }

rcCfmMaExSectionPort             OBJECT-TYPE
    SYNTAX      InterfaceIndexOrZero
    MAX-ACCESS  read-write
    STATUS      current
    DESCRIPTION
            "Port specified when Ma associates with Section." 
    DEFVAL { 0 }
    ::= { rcCfmMaExEntry 35 }


--Y.1731 Ma Extern AIS table
rcCfmMaExAisTable OBJECT-TYPE
    SYNTAX      SEQUENCE OF RcCfmMaExAisEntry
    MAX-ACCESS  not-accessible
    STATUS      current
    DESCRIPTION
        "Y.1731 MA Extended Ais Table "
    ::= { rcCfm 21 }
    
rcCfmMaExAisEntry OBJECT-TYPE
	SYNTAX      RcCfmMaExAisEntry
    MAX-ACCESS  not-accessible
    STATUS      current
    DESCRIPTION
        "An entry in the rcCfmMaExAisTable. "
    INDEX	{ dot1agCfmMdIndex, 
    		  dot1agCfmMaIndex
    		}
    ::= { rcCfmMaExAisTable 1 } 
    
RcCfmMaExAisEntry ::= SEQUENCE
    {
		rcCfmMaExAisEnable EnableVar,  
		rcCfmMaExAisLevelAdmin Dot1agCfmMDLevelOrNone,
		rcCfmMaExAisLevelOper Dot1agCfmMDLevelOrNone,
		rcCfmMaExAisPeriod INTEGER,
		rcCfmMaExAisStatus INTEGER, 
		rcCfmMaExAisAge Unsigned32,
		rcCfmMaExAisStatisticsTx Unsigned32,
		rcCfmMaExAisStatisticsRx Unsigned32,
		rcCfmMaExAisLspName    OCTET STRING (SIZE (0..32)),
		rcCfmMaExAisVcId       INTEGER,
		rcCfmMaExAisVlan       VlanIdOrNone,
        rcCfmMaExAisPwPeerAddrType   InetAddressType,
        rcCfmMaExAisPwPeerAddr       InetAddress    
	}
 
rcCfmMaExAisEnable OBJECT-TYPE
    SYNTAX      EnableVar
    MAX-ACCESS  read-write
    STATUS      current
    DESCRIPTION
       "Set the enable or disable status of AIS in this MA,then send ais 
        packet when some errors occur."
     DEFVAL{disable}   
    ::= { rcCfmMaExAisEntry 1 }

rcCfmMaExAisLevelAdmin OBJECT-TYPE
    SYNTAX      Dot1agCfmMDLevelOrNone
    MAX-ACCESS  read-write
    STATUS      current
    DESCRIPTION
       "Set the level of AIS in this MA,then send ais packet when 
        some errors occur."
    DEFVAL {-1}
    ::= { rcCfmMaExAisEntry 2 }  
    
rcCfmMaExAisLevelOper OBJECT-TYPE
    SYNTAX      Dot1agCfmMDLevelOrNone  
    MAX-ACCESS  read-only
    STATUS      deprecated
    DESCRIPTION
       "The actually level of sending ais."
    ::= { rcCfmMaExAisEntry 3 }

rcCfmMaExAisPeriod OBJECT-TYPE
    SYNTAX      INTEGER{
                 aisPeriod1s(1),
                 aisPeriod60s(60)
                 }
    MAX-ACCESS  read-write
    STATUS      current
    DESCRIPTION
       "IWhen setting the period of sending AIS in this MA,it’s 
        periodically send ais when the timer arrived because of 
        some errors occur. "
    DEFVAL {aisPeriod1s}
    ::= { rcCfmMaExAisEntry 4 }
	
rcCfmMaExAisStatus          OBJECT-TYPE 
	SYNTAX      INTEGER
                {  active(1),
                   noActive(2)
                } 
	MAX-ACCESS  read-only
    STATUS      current
    DESCRIPTION
            "When receiving ais, it is in active status(rcCfmMaExAisStatus_Active(1));
             When not receiving ais with in 3.5 multiple period,it is in not active 
             status(rcCfmMaExAisStatus_noActive (2)).
            "    
    DEFVAL { noActive }
	::= { rcCfmMaExAisEntry 5 } 
	                
rcCfmMaExAisAge OBJECT-TYPE
    SYNTAX      Unsigned32
    MAX-ACCESS  read-only
    STATUS      current
    DESCRIPTION
       "The storage time (ms) when last receiving ais packet."  
    ::= {rcCfmMaExAisEntry 6 }

rcCfmMaExAisStatisticsTx OBJECT-TYPE
    SYNTAX      Unsigned32
    MAX-ACCESS  read-only
    STATUS      current
    DESCRIPTION
       "The counters of sended ais packets." 
    ::= {rcCfmMaExAisEntry 7 }    
    
rcCfmMaExAisStatisticsRx OBJECT-TYPE
    SYNTAX      Unsigned32
    MAX-ACCESS  read-only
    STATUS      current
    DESCRIPTION
       "The counters of received ais packets."
    ::= {rcCfmMaExAisEntry 8 }   
    
rcCfmMaExAisLspName OBJECT-TYPE
    SYNTAX      OCTET STRING (SIZE (0..32))
    MAX-ACCESS  read-write
    STATUS      deprecated
    DESCRIPTION
       "The LSP name associated with the AIS action."
    ::= {rcCfmMaExAisEntry 9 }  
    
rcCfmMaExAisVcId OBJECT-TYPE
    SYNTAX      INTEGER
    MAX-ACCESS  read-write
    STATUS      deprecated
    DESCRIPTION
       "The VC ID associated with the AIS action."
    ::= {rcCfmMaExAisEntry 10 }  
    
rcCfmMaExAisVlan  OBJECT-TYPE
    SYNTAX      VlanIdOrNone
    MAX-ACCESS  read-write
    STATUS      current
    DESCRIPTION
       "The Vlan Id associated with the PW AIS action."
    ::= {rcCfmMaExAisEntry 11}  

rcCfmMaExAisPwPeerAddrType OBJECT-TYPE
     SYNTAX        InetAddressType
     MAX-ACCESS    read-write
     STATUS        deprecated
     DESCRIPTION
          "Denotes the address type of the peer node.  It should be
           set to 'unknown' if PE/PW maintenance protocol is not used
           and the address is unknown."
     DEFVAL { unknown }
     ::= { rcCfmMaExAisEntry 12 }

rcCfmMaExAisPwPeerAddr OBJECT-TYPE
     SYNTAX        InetAddress
     MAX-ACCESS    read-write
     STATUS        deprecated
     DESCRIPTION
          "This object contains the value of the peer node address
           of the PW/PE maintenance protocol entity.  This object
           SHOULD contain a value of all zeroes if not applicable
           (rcCfmMaExAisPwPeerAddrType is 'unknown')."
     ::= { rcCfmMaExAisEntry 13 }

     
--Y.1731 Ma Extern LCK table
rcCfmMaExLckTable OBJECT-TYPE
    SYNTAX      SEQUENCE OF RcCfmMaExLckEntry
    MAX-ACCESS  not-accessible
    STATUS      current
    DESCRIPTION
        "Y.1731 MA Extended LCK table"
    ::= { rcCfm 22 }
    
rcCfmMaExLckEntry OBJECT-TYPE
	  SYNTAX      RcCfmMaExLckEntry
    MAX-ACCESS  not-accessible
    STATUS      current
    DESCRIPTION
        "An entry in the rcCfmMaExLckTable. "
    INDEX	{ dot1agCfmMdIndex, 
    		  dot1agCfmMaIndex
    		}
    ::= { rcCfmMaExLckTable 1 } 
    
    RcCfmMaExLckEntry ::= SEQUENCE 
    {
		rcCfmMaExLckLevelAdmin Dot1agCfmMDLevelOrNone,  
		rcCfmMaExLckLevelOper Dot1agCfmMDLevelOrNone,
		rcCfmMaExLckPeriod INTEGER,
		rcCfmMaExLckStatus INTEGER,
		rcCfmMaExLckAge Unsigned32,
		rcCfmMaExLckStatisticsTx Unsigned32,
		rcCfmMaExLckStatisticsRx Unsigned32,
		rcCfmMaExLckLspName      OCTET STRING (SIZE (0..32)),  
		rcCfmMaExLckVcid         INTEGER,
		rcCfmMaExLckVlan         VlanIdOrNone,
        rcCfmMaExLckPwPeerAddrType   InetAddressType,
        rcCfmMaExLckPwPeerAddr       InetAddress  
    }
 
rcCfmMaExLckLevelAdmin OBJECT-TYPE
    SYNTAX      Dot1agCfmMDLevelOrNone
    MAX-ACCESS  read-write
    STATUS      current
    DESCRIPTION
       "Set the level of AIS in this MA,then send ais 
       packet when some errors occur."
    DEFVAL{-1}
    ::= { rcCfmMaExLckEntry 1 }

rcCfmMaExLckLevelOper OBJECT-TYPE
    SYNTAX      Dot1agCfmMDLevelOrNone
    MAX-ACCESS  read-only
    STATUS      deprecated
    DESCRIPTION
       "The actually level of sending ais. "
    ::= { rcCfmMaExLckEntry 2 }  
    
rcCfmMaExLckPeriod OBJECT-TYPE
    SYNTAX      INTEGER{
                 lckPeriod1s(1),
                 lckPeriod60s(60)
                 }  
    MAX-ACCESS  read-write
    STATUS      current
    DESCRIPTION
       "When setting the period of sending LCK in this MA,
        it’s periodically send lck when the timer arrived 
        because of some errors occur."
    DEFVAL{lckPeriod1s}
    ::= { rcCfmMaExLckEntry 3 }

rcCfmMaExLckStatus OBJECT-TYPE
    SYNTAX      INTEGER
                {  active(1),
                   noActive(2)
                }       
    MAX-ACCESS  read-only
    STATUS      current
    DESCRIPTION
       "When receiving lck, it is in active status(rcCfmMaExLckStatus _Active(1));
        When not receiving lck with in 3.5 multiple period,
        it is in not active status(rcCfmMaExLckStatus _noActive (2)).
       "
    DEFVAL{noActive}
    ::= { rcCfmMaExLckEntry 4 }    
    
rcCfmMaExLckAge OBJECT-TYPE
    SYNTAX      Unsigned32
    MAX-ACCESS  read-only
    STATUS      current
    DESCRIPTION
        "The storage time (ms) when last receiving lck packet."  
	::= { rcCfmMaExLckEntry 5 }
	
rcCfmMaExLckStatisticsTx OBJECT-TYPE
    SYNTAX      Unsigned32
    MAX-ACCESS  read-only
    STATUS      current
    DESCRIPTION
        "The counters of sended lck packets."  
	::= { rcCfmMaExLckEntry 6 }	
	
rcCfmMaExLckStatisticsRx OBJECT-TYPE
    SYNTAX      Unsigned32
    MAX-ACCESS  read-only
    STATUS      current
    DESCRIPTION
        "The counters of received lck packets."  
	::= { rcCfmMaExLckEntry 7 }
	
rcCfmMaExLckLspName OBJECT-TYPE
    SYNTAX      OCTET STRING (SIZE (0..32)) 
    MAX-ACCESS  read-write
    STATUS      deprecated
    DESCRIPTION
        "The LSP name associated with the LCK action."
	::= { rcCfmMaExLckEntry 8 }	

rcCfmMaExLckVcid OBJECT-TYPE
    SYNTAX      INTEGER
    MAX-ACCESS  read-write
    STATUS      deprecated
    DESCRIPTION
        "The VC ID associated with the LCK action."
	::= { rcCfmMaExLckEntry 9 }	

rcCfmMaExLckVlan OBJECT-TYPE
    SYNTAX      VlanIdOrNone 
    MAX-ACCESS  read-write
    STATUS      current
    DESCRIPTION
        "The Vlan Id associated with the PW LCK action."
	::= { rcCfmMaExLckEntry 10 }	

rcCfmMaExLckPwPeerAddrType OBJECT-TYPE
     SYNTAX        InetAddressType
     MAX-ACCESS    read-write
     STATUS        deprecated
     DESCRIPTION
          "Denotes the address type of the peer node.  It should be
           set to 'unknown' if PE/PW maintenance protocol is not used
           and the address is unknown."
     DEFVAL { unknown }
     ::= { rcCfmMaExLckEntry 11 }

rcCfmMaExLckPwPeerAddr OBJECT-TYPE
     SYNTAX        InetAddress
     MAX-ACCESS    read-write
     STATUS        deprecated
     DESCRIPTION
          "This object contains the value of the peer node address
           of the PW/PE maintenance protocol entity.  This object
           SHOULD contain a value of all zeroes if not applicable
           (rcCfmMaExLckPwPeerAddrType is 'unknown')."
     ::= { rcCfmMaExLckEntry 12 }

		
-- trap notification 
rcCfmNotifications           OBJECT IDENTIFIER ::= { rcCfm 23 }
rcCfmPmFLRRaisingThreshFaultAlarm
NOTIFICATION-TYPE
    OBJECTS     { rcCfmPMFLRRisingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 1 }

rcCfmPmFLRFallingThreshFaultAlarm
NOTIFICATION-TYPE
    OBJECTS     { rcCfmPMFLRFallingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 2 }

rcCfmPmDelayRisingThreshFaultAlarm
NOTIFICATION-TYPE
    OBJECTS     { rcCfmPMDelayRisingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 3 }  
    
rcCfmPmDelayFallingThreshFaultAlarm
NOTIFICATION-TYPE
    OBJECTS     { rcCfmPMDelayFallingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 4 }

rcCfmPmDVRisingThreshFaultAlarm
NOTIFICATION-TYPE
    OBJECTS     { rcCfmPMDVRisingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 5 }

rcCfmPmDVFallingThreshFaultAlarm
NOTIFICATION-TYPE
    OBJECTS     { 
                  rcCfmPMDVFallingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 6 }

rcCfmAisAlarm NOTIFICATION-TYPE
    OBJECTS     { 
                  rcCfmMaExAisStatus
                }
    STATUS      current
    DESCRIPTION
       "When receiving ais or not receiving ais with in 3.5 multiple period, 
        the  trap  will be raised and OLT will notify this event to the NMS.
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable)."
    ::= { rcCfmNotifications 7 }
    
rcCfmLckAlarm NOTIFICATION-TYPE
    OBJECTS     { 
                  rcCfmMaExLckStatus
                }
    STATUS      current
    DESCRIPTION
       ""
    ::= { rcCfmNotifications 8 }   
    
rcCfmCsfAlarm NOTIFICATION-TYPE
    OBJECTS     { 
                  rcCfmMaExCsfRxLatestType
                }
    STATUS      current
    DESCRIPTION
       "When receiving the lateset CSF type from the peer mep is changeing,  
        the  trap  will be raised and OLT will notify this event to the NMS.
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable)."
    ::= { rcCfmNotifications 9 }

    
rcCfmY1731FaultTrap
NOTIFICATION-TYPE
    OBJECTS     { 
                  rcCfmMepExY1731DefectList
                }
    STATUS      deprecated
    DESCRIPTION
       "Y1731 fault trap"
    ::= { rcCfmNotifications 10 }    

rcCfmY1731FaultUNL
NOTIFICATION-TYPE
    OBJECTS     {  
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                 }
    STATUS      current
    DESCRIPTION
       "Y1731-based fault UNL happen"
    ::= { rcCfmNotifications 11 } 

rcCfmY1731RecoverUNL
NOTIFICATION-TYPE
    OBJECTS     {  
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                }
    STATUS      current
    DESCRIPTION
       "Y1731-based fault UNL recover"
    ::= { rcCfmNotifications 12 }


 
rcCfmY1731FaultMMG
NOTIFICATION-TYPE
    OBJECTS     {  
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                }
    STATUS      current
    DESCRIPTION
       "Y1731-based fault MMG happen"
    ::= { rcCfmNotifications 13 }

rcCfmY1731RecoverMMG
NOTIFICATION-TYPE
    OBJECTS     { 
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                }
    STATUS      current
    DESCRIPTION
       "Y1731-based fault MMG recover"
    ::= { rcCfmNotifications 14 }

rcCfmY1731FaultUNM
NOTIFICATION-TYPE
    OBJECTS     { 
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                }
    STATUS      current
    DESCRIPTION
       "Y1731-based fault UNM happen"
    ::= { rcCfmNotifications 15 }

rcCfmY1731RecoverUNM
NOTIFICATION-TYPE
    OBJECTS     {  
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                }
    STATUS      current
    DESCRIPTION
       "Y1731-based fault UNM recover"
    ::= { rcCfmNotifications 16 }   
    
rcCfmY1731FaultUNP
NOTIFICATION-TYPE
    OBJECTS     { 
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                }
    STATUS      current
    DESCRIPTION
       "Y1731-based fault UNP happen"
    ::= { rcCfmNotifications 17 }

rcCfmY1731RecoverUNP
NOTIFICATION-TYPE
    OBJECTS     {  
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                }
    STATUS      current
    DESCRIPTION
       "Y1731-based fault UNP recover"
    ::= { rcCfmNotifications 18 }


rcCfmY1731FaultLOC
NOTIFICATION-TYPE
    OBJECTS     {  
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                }
    STATUS      current
    DESCRIPTION
       "Y1731-based fault LOC happen"
    ::= { rcCfmNotifications 19 }

rcCfmY1731RecoverLOC
NOTIFICATION-TYPE
    OBJECTS     { 
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                }
    STATUS      current
    DESCRIPTION
       "Y1731-based fault LOC recover"
    ::= { rcCfmNotifications 20 }


rcCfmY1731FaultRDI
NOTIFICATION-TYPE
    OBJECTS     { 
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                }
    STATUS      current
    DESCRIPTION
       "Y1731-based fault RDI happen"
    ::= { rcCfmNotifications 21 }

rcCfmY1731RecoverRDI
NOTIFICATION-TYPE
    OBJECTS     {  
                  rcCfmMaExOamType,
                  rcCfmMaExPrimaryVlanId,      
                  rcCfmMaExIngressLspId,      
                  rcCfmMaExEgressLspId,       
                  rcCfmMaExVcid,               
                  rcCfmMaExPwPeerAddrType,  
                  rcCfmMaExPwPeerAddr,      
                  rcCfmMaExSectionPort,      
                  rcCfmMaExSncLsridAddrType, 
                  rcCfmMaExSncLsridAddr,             
                  dot1agCfmMepIfIndex, 
                  rcCfmMepExY1731DefectList
                }
    STATUS      current
    DESCRIPTION
       "Y1731-based fault RDI recover"
    ::= { rcCfmNotifications 22 }

rcCfmDot1agFaultRDI
NOTIFICATION-TYPE
    OBJECTS     { 
                  rcCfmMaExPrimaryVlanId,
                  dot1agCfmMepIfIndex,
                  rcCfmMepExDot1agDefectList
                }
    STATUS      current
    DESCRIPTION
       "Dot1ag-based fault RDI fault"
    ::= { rcCfmNotifications 23 }

rcCfmDot1agRecoverRDI
NOTIFICATION-TYPE
    OBJECTS     {   
                  rcCfmMaExPrimaryVlanId,
                  dot1agCfmMepIfIndex,
                  rcCfmMepExDot1agDefectList
                }
    STATUS      current
    DESCRIPTION
       "Dot1ag-based fault RDI recover"
    ::= { rcCfmNotifications 24 }

rcCfmDot1agFaultMacStatus
NOTIFICATION-TYPE
    OBJECTS     {  
                  rcCfmMaExPrimaryVlanId,
                  dot1agCfmMepIfIndex,
                  rcCfmMepExDot1agDefectList
                }
    STATUS      current
    DESCRIPTION
       "Dot1ag-based fault MacStatus fault"
    ::= { rcCfmNotifications 25 }

rcCfmDot1agRecoverMacStatus
NOTIFICATION-TYPE
    OBJECTS     { 
                  rcCfmMaExPrimaryVlanId,
                  dot1agCfmMepIfIndex,
                  rcCfmMepExDot1agDefectList
                }
    STATUS      current
    DESCRIPTION
       "Dot1ag-based fault MacStatus recover"
    ::= { rcCfmNotifications 26 }

rcCfmDot1agFaultRemoteCcm
NOTIFICATION-TYPE
    OBJECTS     { 
                  rcCfmMaExPrimaryVlanId,
                  dot1agCfmMepIfIndex,
                  rcCfmMepExDot1agDefectList
                }
    STATUS      current
    DESCRIPTION
       "Dot1ag-based fault RemoteCcm fault"
    ::= { rcCfmNotifications 27 }

rcCfmDot1agRecoverRemoteCcm
NOTIFICATION-TYPE
    OBJECTS     { 
                  rcCfmMaExPrimaryVlanId,
                  dot1agCfmMepIfIndex,
                  rcCfmMepExDot1agDefectList
                }
    STATUS      current
    DESCRIPTION
       "Dot1ag-based fault RemoteCcm recover"
    ::= { rcCfmNotifications 28 }


rcCfmDot1agFaultErrorCcm
NOTIFICATION-TYPE
    OBJECTS     { 
                  rcCfmMaExPrimaryVlanId,
                  dot1agCfmMepIfIndex,
                  rcCfmMepExDot1agDefectList
                }
    STATUS      current
    DESCRIPTION
       "Dot1ag-based fault ErrorCcm fault"
    ::= { rcCfmNotifications 29 }

rcCfmDot1agRecoverErrorCcm
NOTIFICATION-TYPE
    OBJECTS     { 
                  rcCfmMaExPrimaryVlanId,
                  dot1agCfmMepIfIndex,
                  rcCfmMepExDot1agDefectList
                }
    STATUS      current
    DESCRIPTION
       "Dot1ag-based fault ErrorCcm recover"
    ::= { rcCfmNotifications 30 }

rcCfmDot1agFaultXcon
NOTIFICATION-TYPE
    OBJECTS     { 
                  rcCfmMaExPrimaryVlanId,
                  dot1agCfmMepIfIndex,
                  rcCfmMepExDot1agDefectList
                }
    STATUS      current
    DESCRIPTION
       "Dot1ag-based fault Xcon fault"
    ::= { rcCfmNotifications 31 }

rcCfmDot1agRecoverXcon
NOTIFICATION-TYPE
    OBJECTS     { 
                  rcCfmMaExPrimaryVlanId,
                  dot1agCfmMepIfIndex,
                  rcCfmMepExDot1agDefectList
                }
    STATUS      current
    DESCRIPTION
       "Dot1ag-based fault Xcon recover"
    ::= { rcCfmNotifications 32 }

rcCfmLbResultAlarm
NOTIFICATION-TYPE
    OBJECTS     { 
                  rcCfmMepExLbResultOk
                }
    STATUS      current
    DESCRIPTION
       "When lb operation result is ok or not,the  trap  will be raised and OLT 
       will notify this event to the NMS."
    ::= { rcCfmNotifications 33 }
   
--Y.1731 Ma Extern CSF table
rcCfmMaExCsfTable OBJECT-TYPE
    SYNTAX      SEQUENCE OF RcCfmMaExCsfEntry
    MAX-ACCESS  not-accessible
    STATUS      current
    DESCRIPTION
        "Y.1731 MA Extended CSF table"
    ::= { rcCfm 24 }
    
rcCfmMaExCsfEntry OBJECT-TYPE
	  SYNTAX      RcCfmMaExCsfEntry
    MAX-ACCESS  not-accessible
    STATUS      current
    DESCRIPTION
        "An entry in the rcCfmMaExCsfTable. "
    INDEX	{ dot1agCfmMdIndex, 
    		  dot1agCfmMaIndex
    		}
    ::= { rcCfmMaExCsfTable 1 } 
    
RcCfmMaExCsfEntry ::= SEQUENCE 
    {
		rcCfmMaExCsfTxPeriod INTEGER,
		rcCfmMaExCsfRxTrapEnable TruthValue,
		rcCfmMaExCsfRxLatestType INTEGER,
		rcCfmMaExCsfRxStats INTEGER  		
	}
     
rcCfmMaExCsfRxTrapEnable OBJECT-TYPE
    SYNTAX  TruthValue
  
    MAX-ACCESS  read-write
    STATUS      current
    DESCRIPTION
       "Whether trap will send or not when CSF occurs."   
    DEFVAL {false}
    ::= { rcCfmMaExCsfEntry 1}

rcCfmMaExCsfTxPeriod OBJECT-TYPE
    SYNTAX  INTEGER{
	          csfTxPeriod_1s(1),
	          csfTxPeriod_60s(60)
	        }
  
    MAX-ACCESS  read-write
    STATUS      current
    DESCRIPTION
       "When setting the period of sending CSF in this MA,it's periodically 
       send csf when the timer arrived because of some errors occur."   
    DEFVAL {csfTxPeriod_1s}
    ::= { rcCfmMaExCsfEntry 2 }
  
rcCfmMaExCsfRxLatestType OBJECT-TYPE
    SYNTAX  INTEGER{              
              csf_los(0),
	          csf_fdi(1),
	          csf_rdi(2),
	          csf_clr(3),
	          csf_invalid(255)
	        }
  
    MAX-ACCESS  read-only
    STATUS      current
    DESCRIPTION
       "The lateset CSF type recieved from the peer mep." 
    DEFVAL {csf_invalid}
    ::= { rcCfmMaExCsfEntry 3 }

 rcCfmMaExCsfRxStats OBJECT-TYPE
    SYNTAX  INTEGER  
    MAX-ACCESS  read-only
    STATUS      current
    DESCRIPTION
       "The total CSF packets recieved from the peer mep."
    ::= { rcCfmMaExCsfEntry 4 }
 
rcCfmMaExMepCsfTable OBJECT-TYPE
    SYNTAX      SEQUENCE OF RcCfmMaExMepCsfEntry
    MAX-ACCESS  not-accessible
    STATUS      current
    DESCRIPTION
        "Y.1731 MA Extended  MEP CSF  table"
    ::= { rcCfm 25 }
    
rcCfmMaExMepCsfEntry OBJECT-TYPE
	  SYNTAX      RcCfmMaExMepCsfEntry
    MAX-ACCESS  not-accessible
    STATUS      current
    DESCRIPTION
        "An entry in the rcCfmMaExCsfTable. "
    INDEX	{ dot1agCfmMdIndex, 
    		  dot1agCfmMaIndex,
    		  dot1agCfmMepIdentifier
    		}
    ::= { rcCfmMaExMepCsfTable 1 } 
    
RcCfmMaExMepCsfEntry ::= SEQUENCE 
    {  
		rcCfmMaExMepCsfTxAdmin TruthValue,  
		rcCfmMaExMepCsfTxStatus INTEGER,                        
		rcCfmMaExMepCsfTxStats INTEGER
	}

  rcCfmMaExMepCsfTxAdmin OBJECT-TYPE
    SYNTAX  TruthValue 
    MAX-ACCESS  read-write
    STATUS      current
    DESCRIPTION
       "Whether CSF function is enabled or not."  
    DEFVAL {false}
    ::= { rcCfmMaExMepCsfEntry 1 }
  
  rcCfmMaExMepCsfTxStatus OBJECT-TYPE
    SYNTAX  INTEGER{              
              csf_los(0),
	          csf_fdi(1),
	          csf_rdi(2),
	          csf_clr(3),
	          csf_invalid(255)
	        }
  
    MAX-ACCESS  read-only
    STATUS      current
    DESCRIPTION
       "The current CSF type."    
    DEFVAL {csf_invalid}
    ::= { rcCfmMaExMepCsfEntry 2 }

 rcCfmMaExMepCsfTxStats OBJECT-TYPE
    SYNTAX  INTEGER  
    MAX-ACCESS  read-only
    STATUS      current
    DESCRIPTION
       "The total CSF packets sent to the peer mep."
    ::= { rcCfmMaExMepCsfEntry 3 }

--------------------------------------------------------------------------------
--CFM multicast  loopback result Table 
--------------------------------------------------------------------------------
rcCfmMulticastLbResultTable 	OBJECT-TYPE
    SYNTAX      SEQUENCE OF RcCfmMulticastLbResultEntry
    MAX-ACCESS  not-accessible
    STATUS      current
    DESCRIPTION
        "CFM Multicast Loopback Result Table "  
    ::= { rcCfm 26 }
    
rcCfmMulticastLbResultEntry          			OBJECT-TYPE
	SYNTAX      RcCfmMulticastLbResultEntry
    MAX-ACCESS  not-accessible
    STATUS      current
    DESCRIPTION
        "An entry in the rcCfmMulticastLbResultTable.  "
    INDEX	{ dot1agCfmMdIndex, 
    		  dot1agCfmMaIndex,
    		  dot1agCfmMepIdentifier,
    		  rcCfmMcastLbResultIndex
    		}
    ::= { rcCfmMulticastLbResultTable 1 }   
    
RcCfmMulticastLbResultEntry ::= SEQUENCE {
    rcCfmMcastLbResultIndex         Unsigned32 (1..256),
	rcCfmMcastLbResultRemoteMepId   Unsigned32 (0..8191),
	rcCfmMcastLbResultRecvPort      Unsigned32 (0..65535),
	rcCfmMcastLbResultMacAddress	MacAddress,
	rcCfmMcastLbResultRtt           Unsigned32(0..5000)	
}                    

rcCfmMcastLbResultIndex    OBJECT-TYPE 
	SYNTAX      Unsigned32 (1..256)
	MAX-ACCESS  not-accessible
	STATUS      current
    DESCRIPTION
            "The fourth index to the multicast loopback table."
	::= { rcCfmMulticastLbResultEntry 1 }   
	
rcCfmMcastLbResultRemoteMepId    OBJECT-TYPE 
	SYNTAX      Unsigned32 (0..8191)
	MAX-ACCESS  read-only
	STATUS      current
    DESCRIPTION
            "The remote mep id."
	::= { rcCfmMulticastLbResultEntry 2 }  

rcCfmMcastLbResultRecvPort    OBJECT-TYPE 
	SYNTAX      Unsigned32 (0..65535)
	MAX-ACCESS  read-only
	STATUS      current
    DESCRIPTION
            "The lbr reveived port,0 means no lbr received."
	::= { rcCfmMulticastLbResultEntry 3 } 
	  
rcCfmMcastLbResultMacAddress    OBJECT-TYPE 
	SYNTAX      MacAddress
	MAX-ACCESS  read-only
	STATUS      current
    DESCRIPTION
            "The remote mep mac address,0000.0000.0000 means no remote mep mac."
	::= { rcCfmMulticastLbResultEntry 4 }  

rcCfmMcastLbResultRtt    OBJECT-TYPE 
	SYNTAX      Unsigned32
	MAX-ACCESS  read-only
	STATUS      current
    DESCRIPTION
            "lb rtt time,0 means rtt <1ms,5000 means timeout."
	::= { rcCfmMulticastLbResultEntry 5 }  

--------------------------------------------------------------------------------
--CFM MEP Extended Mpls-tp Loopback Table
--------------------------------------------------------------------------------
rcCfmMepExMplstpPingTable 	OBJECT-TYPE
    SYNTAX      SEQUENCE OF RcCfmMepExMplstpPingEntry
    MAX-ACCESS  not-accessible
    STATUS      current
    DESCRIPTION
        "CFM MEP Extended Mpls-tp Loopback Table "  
    ::= { rcCfm 27 }
    
rcCfmMepExMplstpPingEntry          			OBJECT-TYPE
	SYNTAX      RcCfmMepExMplstpPingEntry
    MAX-ACCESS  not-accessible
    STATUS      current
    DESCRIPTION
        "An entry in the rcCfmMepExMplstpPingTable.  "
    INDEX	{ dot1agCfmMdIndex, 
    		  dot1agCfmMaIndex,
    		  dot1agCfmMepIdentifier
    		}
    ::= { rcCfmMepExMplstpPingTable 1 }   
    
RcCfmMepExMplstpPingEntry ::= SEQUENCE {
    rcCfmMepExMplstpPingType        INTEGER,
	rcCfmMepExMplstpPingDestMepId   Unsigned32 (0..8191),
	rcCfmMepExMplstpPingMipId	    Unsigned32 (0..8191),
	rcCfmMepExMplstpPingDirection   INTEGER,
	rcCfmMepExMplstpPingTtl         Unsigned32 (1..255),
	rcCfmMepExMplstpPingTimeout     Unsigned32 (1..60),  
	rcCfmMepExMplstpPingLbmPadType  INTEGER, 
	rcCfmMepExMplstpPingDestMipICC     OCTET STRING (SIZE(1..6)),	
	rcCfmMepExMplstpPingDestMipNodeId  Unsigned32,
	rcCfmMepExMplstpPingDestMipIfNum   Unsigned32, 
    rcCfmMepExMplstpPingDestMipMode    INTEGER
}                    

rcCfmMepExMplstpPingType    OBJECT-TYPE 
	SYNTAX      INTEGER{
                        cfm_mpls_tp_ping_none(0),
                        cfm_mpls_tp_ping_mep(1),
                        cfm_mpls_tp_ping_mip(2),
                        cfm_mpls_tp_ping_direction(3)
                }
	MAX-ACCESS  read-write
	STATUS      current
    DESCRIPTION
            "The type of the mpls-tp ping action."  
    DEFVAL {cfm_mpls_tp_ping_none}
	::= { rcCfmMepExMplstpPingEntry 1 }   
	
rcCfmMepExMplstpPingDestMepId    OBJECT-TYPE 
	SYNTAX      Unsigned32 (0..8191)
	MAX-ACCESS  read-write
	STATUS      current
    DESCRIPTION
            "The mep Identifier of another MEP in the same Ma to which the LBM
            is to be sent.This address will be used if the value of the column 
            rcCfmMepExMplstpPingType is equal to 1."
	::= { rcCfmMepExMplstpPingEntry 2 }  

rcCfmMepExMplstpPingMipId    OBJECT-TYPE 
	SYNTAX      Unsigned32 (0..8191)
	MAX-ACCESS  read-write
	STATUS      deprecated
    DESCRIPTION
            "The destination mip Identifier to which the LBM is to be sent.
             This address will be used if the value of the column 
             rcCfmMepExMplstpPingType is equal to 2."
	::= { rcCfmMepExMplstpPingEntry 3 } 
	  
rcCfmMepExMplstpPingDirection    OBJECT-TYPE 
	SYNTAX      INTEGER{
	                    cfm_ping_none(0), 
	                    cfm_ping_ingress(1),
                        cfm_ping_egress(2)
                }
	MAX-ACCESS  read-write
	STATUS      current
    DESCRIPTION
            "Set the direction of the ping action which used only in mpls layer.
             This address will be used if the value of the column 
             rcCfmMepExMplstpPingType is equal to 3."  
    DEFVAL {cfm_ping_none}
	::= { rcCfmMepExMplstpPingEntry 4 }  

rcCfmMepExMplstpPingTtl    OBJECT-TYPE 
	SYNTAX      Unsigned32(1..255)
	MAX-ACCESS  read-write
	STATUS      current 
    DESCRIPTION
            "The LBM TTL field. Default value, if not specified, is 64.The TTL field
            indicates the number of hops remaining to the LBM. Decremented by 1 when
            each LBM handler. The value returned in the LBR is one less
            than that received in the LBM."   
    DEFVAL {64}
	::= { rcCfmMepExMplstpPingEntry 5 }     
	
	rcCfmMepExMplstpPingTimeout    OBJECT-TYPE 
	SYNTAX      Unsigned32(1..60)
	MAX-ACCESS  read-write
	STATUS      current
    DESCRIPTION
            "The time wait for LBR once sending LBM,when out of time, it indicates that 
            mpls-tp ping operation has falied."  
    DEFVAL {5}        
	::= { rcCfmMepExMplstpPingEntry 6 }  
	
	rcCfmMepExMplstpPingLbmPadType    OBJECT-TYPE 
	SYNTAX      INTEGER{
                         cfm_mpls_tp_ping_invalid(0),
                         cfm_mpls_tp_ping_prbs(1),
                         cfm_mpls_tp_ping_prbs_crc(2),  
                         cfm_mpls_tp_ping_null(3),
                         cfm_mpls_tp_ping_null_crc(4)
                }
	MAX-ACCESS  read-write
	STATUS      current
    DESCRIPTION
            "The tlv type of lbm packet to send.when the value equals to cfm_mpls_tp_ping_invalid,
            the tlv type is data tlv"  
    DEFVAL {cfm_mpls_tp_ping_invalid}
	::= { rcCfmMepExMplstpPingEntry 7 }    
rcCfmMepExMplstpPingDestMipICC   OBJECT-TYPE 
	SYNTAX      OCTET STRING (SIZE(1..6))
    MAX-ACCESS  read-write
	STATUS      current
    DESCRIPTION
            "The ICC of MPLS-TP LB target MIP."
	::= {rcCfmMepExMplstpPingEntry 8}

rcCfmMepExMplstpPingDestMipNodeId   OBJECT-TYPE 
	SYNTAX      Unsigned32 
    MAX-ACCESS  read-write
	STATUS      current
    DESCRIPTION
            "The Node-ID of MPLS-TP LB target MIP."
	::= {rcCfmMepExMplstpPingEntry 9}

rcCfmMepExMplstpPingDestMipIfNum   OBJECT-TYPE 
	SYNTAX      Unsigned32 
    MAX-ACCESS  read-write
	STATUS      current
    DESCRIPTION
            "The If-Num of MPLS-TP LB target MIP."
	::= {rcCfmMepExMplstpPingEntry 10}

rcCfmMepExMplstpPingDestMipMode   OBJECT-TYPE 
	SYNTAX      INTEGER{
                         mpls_tp_mip_mode_none(0),
                         mpls_tp_mip_mode_node(1),
                         mpls_tp_mip_mode_interface(2)
                }
    MAX-ACCESS  read-write
	STATUS      current
    DESCRIPTION
            "The Mode of MPLS-TP LB target MIP."
	::= {rcCfmMepExMplstpPingEntry 11}
	
--------------------------------------------------------------------------------
--CFM AIS/LCK source information Table 
--------------------------------------------------------------------------------  
rcCfmMaExAisLckSrcTable 	OBJECT-TYPE
    SYNTAX      SEQUENCE OF RcCfmMaExAisLckSrcEntry
    MAX-ACCESS  not-accessible
    STATUS      current
    DESCRIPTION
        "CFM AIS/LCK source information Table "                              
    ::= { rcCfm 28 }      
    
rcCfmMaExAisLckSrcEntry  	OBJECT-TYPE
	SYNTAX      RcCfmMaExAisLckSrcEntry
    MAX-ACCESS  not-accessible
    STATUS      current
    DESCRIPTION
        "An entry in the rcCfmMaExAisLckSrcTable."
    INDEX	{ dot1agCfmMdIndex, 
    		  dot1agCfmMaIndex,
    		  rcCfmMaExAisLckSrcMac,
    		  rcCfmMaExAisLckSrcType
    		}
    ::= { rcCfmMaExAisLckSrcTable 1 }   
    
RcCfmMaExAisLckSrcEntry ::= SEQUENCE {
    rcCfmMaExAisLckSrcMac         MacAddress,
	rcCfmMaExAisLckSrcType        INTEGER,
	rcCfmMaExAisLckSrcPeriod      INTEGER,
	rcCfmMaExAisLckSrcTime	      TimeTicks,
	rcCfmMaExAisLckSrcInPkts      INTEGER	
}	

rcCfmMaExAisLckSrcMac   OBJECT-TYPE 
	SYNTAX      MacAddress
	MAX-ACCESS  not-accessible
	STATUS      current
    DESCRIPTION
            "The source mac of ais or lck."
	::= {rcCfmMaExAisLckSrcEntry 1 }

rcCfmMaExAisLckSrcType   OBJECT-TYPE 
	SYNTAX      INTEGER{
	                   ais(1),
	                   lck(2)
	                   }
	MAX-ACCESS  not-accessible
	STATUS      current
    DESCRIPTION
            "The type of source information."
	::= {rcCfmMaExAisLckSrcEntry 2 }	

rcCfmMaExAisLckSrcPeriod   OBJECT-TYPE 
	SYNTAX      INTEGER{
	                 period_1s(1),
	                 period_60s(60)
	                   }
	MAX-ACCESS  read-only
	STATUS      current
    DESCRIPTION
            "The period of AIS/LCK."     
	::= {rcCfmMaExAisLckSrcEntry 3 }
	
rcCfmMaExAisLckSrcTime   OBJECT-TYPE 
	SYNTAX      TimeTicks
	MAX-ACCESS  read-only
	STATUS      current
    DESCRIPTION
            "Time when received the latest AIS/LCK source information."
	::= {rcCfmMaExAisLckSrcEntry 4 }
	
rcCfmMaExAisLckSrcInPkts   OBJECT-TYPE 
	SYNTAX      INTEGER
	MAX-ACCESS  read-only
	STATUS      current
    DESCRIPTION
            "The statistics of received ais or lck packet."
	::= {rcCfmMaExAisLckSrcEntry 5}


--------------------------------------------------------------------------------
--CFM MPLS-TP LT Operation Table 
--------------------------------------------------------------------------------
rcCfmMepExMplstpLtTable 	OBJECT-TYPE
    SYNTAX      SEQUENCE OF RcCfmMepExMplstpLtEntry
    MAX-ACCESS  not-accessible
    STATUS      current
    DESCRIPTION
        "Operation table of MPLS-TP LT"                              
    ::= { rcCfm 29 }
    
rcCfmMepExMplstpLtEntry  	OBJECT-TYPE
	SYNTAX      RcCfmMepExMplstpLtEntry
    MAX-ACCESS  not-accessible
    STATUS      current
    DESCRIPTION
        "An entry in the rcCfmMepExMplstpLtTable."
    INDEX	{ dot1agCfmMdIndex, 
    		  dot1agCfmMaIndex,
    		  dot1agCfmMepIdentifier
    		}
    ::= { rcCfmMepExMplstpLtTable 1 }   
    
RcCfmMepExMplstpLtEntry ::= SEQUENCE {
    rcCfmMepExMplstpLtLtmStatus           TruthValue,
	rcCfmMepExMplstpLtLtmType             INTEGER,
	rcCfmMepExMplstpLtLtmMode             INTEGER,
	rcCfmMepExMplstpLtLtmTargetMepId	  Unsigned32 (0..8191),
	rcCfmMepExMplstpLtLtmTargetMipICC     OCTET STRING (SIZE(1..6)),	
	rcCfmMepExMplstpLtLtmTargetMipNodeId  Unsigned32,
	rcCfmMepExMplstpLtLtmTargetMipIfNum   Unsigned32,
	rcCfmMepExMplstpLtLtmMaxTtl           Unsigned32 (0..255),
	rcCfmMepExMplstpLtLtmTimeout          Unsigned32 (0..60),
	rcCfmMepExMplstpLtLtmResult           INTEGER
}	

rcCfmMepExMplstpLtLtmStatus   OBJECT-TYPE 
	SYNTAX      TruthValue
    MAX-ACCESS  read-write
	STATUS      current
    DESCRIPTION
            "A Boolean flag set to true by the bridge 
             port to indicate that another LTM may be transmitted."
	::= {rcCfmMepExMplstpLtEntry 1 }

rcCfmMepExMplstpLtLtmType   OBJECT-TYPE 
	SYNTAX      INTEGER{
	                   mep(1),
	                   mip(2),
	                   ttl(3)
	                   }
    MAX-ACCESS  read-write
	STATUS      current
    DESCRIPTION
            "The type of MPLS-TP LT."
	::= {rcCfmMepExMplstpLtEntry 2 }	

rcCfmMepExMplstpLtLtmMode   OBJECT-TYPE 
	SYNTAX      INTEGER{
	                   node(1),
	                   interface(2)
	                   }
    MAX-ACCESS  read-write
	STATUS      current
    DESCRIPTION
            "The mode of MPLS-TP LT."
	::= {rcCfmMepExMplstpLtEntry 3 }
	
rcCfmMepExMplstpLtLtmTargetMepId   OBJECT-TYPE 
	SYNTAX      Unsigned32 (0..8191)
    MAX-ACCESS  read-write
	STATUS      current
    DESCRIPTION
            "The ID of MPLS-TP LT target MEP."
	::= {rcCfmMepExMplstpLtEntry 4 }
	
rcCfmMepExMplstpLtLtmTargetMipICC   OBJECT-TYPE 
	SYNTAX      OCTET STRING (SIZE(1..6))
    MAX-ACCESS  read-write
	STATUS      current
    DESCRIPTION
            "The ICC of MPLS-TP LT target MIP."
	::= {rcCfmMepExMplstpLtEntry 5}

rcCfmMepExMplstpLtLtmTargetMipNodeId   OBJECT-TYPE 
	SYNTAX      Unsigned32 
    MAX-ACCESS  read-write
	STATUS      current
    DESCRIPTION
            "The Node-ID of MPLS-TP LT target MIP."
	::= {rcCfmMepExMplstpLtEntry 6 }

rcCfmMepExMplstpLtLtmTargetMipIfNum   OBJECT-TYPE 
	SYNTAX      Unsigned32 
    MAX-ACCESS  read-write
	STATUS      current
    DESCRIPTION
            "The If-Num of MPLS-TP LT target MIP."
	::= {rcCfmMepExMplstpLtEntry 7 }	

rcCfmMepExMplstpLtLtmMaxTtl   OBJECT-TYPE 
	SYNTAX      Unsigned32 (0..255)
    MAX-ACCESS  read-write
	STATUS      current
    DESCRIPTION
            "The max TTL of MPLS-TP LT."
	::= {rcCfmMepExMplstpLtEntry 8 }
	
rcCfmMepExMplstpLtLtmTimeout   OBJECT-TYPE 
	SYNTAX      Unsigned32 (0..60)
    MAX-ACCESS  read-write
	STATUS      current
    DESCRIPTION
            "The timeout of MPLS-TP LT."
	::= {rcCfmMepExMplstpLtEntry 9 }
	
rcCfmMepExMplstpLtLtmResult   OBJECT-TYPE 
	SYNTAX      INTEGER{
	                   ok(1),
	                   failed(2)
	                   }
	MAX-ACCESS  read-only
	STATUS      current
    DESCRIPTION
            "The result of MPLS-TP LT."
	::= {rcCfmMepExMplstpLtEntry 10}


--------------------------------------------------------------------------------
--CFM MPLS-TP LT Result Table 
--------------------------------------------------------------------------------
rcCfmMepExMplstpLtResultTable 	OBJECT-TYPE
    SYNTAX      SEQUENCE OF RcCfmMepExMplstpLtResultEntry
    MAX-ACCESS  not-accessible
    STATUS      current
    DESCRIPTION
        "Result table of MPLS-TP LT"                              
    ::= { rcCfm 30 }
    
rcCfmMepExMplstpLtResultEntry  	OBJECT-TYPE
	SYNTAX      RcCfmMepExMplstpLtResultEntry
    MAX-ACCESS  not-accessible
    STATUS      current
    DESCRIPTION
        "An entry in the rcCfmMepExMplstpLtResultTable."
    INDEX	{ dot1agCfmMdIndex, 
    		  dot1agCfmMaIndex,
    		  dot1agCfmMepIdentifier,
    		  rcCfmMepExMplstpLtResultTtl,
    		  rcCfmMepExMplstpLtResultDirection
    		}
    ::= { rcCfmMepExMplstpLtResultTable 1 }   
    
RcCfmMepExMplstpLtResultEntry ::= SEQUENCE {
    rcCfmMepExMplstpLtResultTtl        Unsigned32 (0..255),
	rcCfmMepExMplstpLtResultDirection  INTEGER,
	rcCfmMepExMplstpLtResultType       INTEGER,
	rcCfmMepExMplstpLtResultMepId	   Unsigned32 (0..8191),
	rcCfmMepExMplstpLtResultMipICC     OCTET STRING (SIZE(1..6)),	
	rcCfmMepExMplstpLtResultMipNodeId  Unsigned32,
	rcCfmMepExMplstpLtResultMipIfNum   Unsigned32,
	rcCfmMepExMplstpLtResultIsDes      TruthValue
}	

rcCfmMepExMplstpLtResultTtl   OBJECT-TYPE 
	SYNTAX      Unsigned32 (0..255)
    MAX-ACCESS  not-accessible
	STATUS      current
    DESCRIPTION
            "The hops of MPLS-TP LT result."
	::= {rcCfmMepExMplstpLtResultEntry 1 }
	
rcCfmMepExMplstpLtResultDirection   OBJECT-TYPE 
	SYNTAX      INTEGER{
	                   ingressAndNode(1),
	                   egress(2)
	                   }
    MAX-ACCESS  not-accessible
	STATUS      current
    DESCRIPTION
            "The dierection of MPLS-TP LT result."
	::= {rcCfmMepExMplstpLtResultEntry 2 }

rcCfmMepExMplstpLtResultType   OBJECT-TYPE 
	SYNTAX      INTEGER{
	                   mep(1),
	                   mip(2),
	                   timeout(3)
	                   }
    MAX-ACCESS  read-only
	STATUS      current
    DESCRIPTION
            "The type of MPLS-TP LT result."
	::= {rcCfmMepExMplstpLtResultEntry 3 }	
	
rcCfmMepExMplstpLtResultMepId   OBJECT-TYPE 
	SYNTAX      Unsigned32 (0..8191)
    MAX-ACCESS  read-only
	STATUS      current
    DESCRIPTION
            "The MEP ID of MPLS-TP LT result."
	::= {rcCfmMepExMplstpLtResultEntry 4 }
	
rcCfmMepExMplstpLtResultMipICC   OBJECT-TYPE 
	SYNTAX      OCTET STRING (SIZE(1..6))
    MAX-ACCESS  read-only
	STATUS      current
    DESCRIPTION
            "The MIP ICC of MPLS-TP LT result."
	::= {rcCfmMepExMplstpLtResultEntry 5}

rcCfmMepExMplstpLtResultMipNodeId   OBJECT-TYPE 
	SYNTAX      Unsigned32 
    MAX-ACCESS  read-only
	STATUS      current
    DESCRIPTION
            "The MIP ICC of MPLS-TP LT result."
	::= {rcCfmMepExMplstpLtResultEntry 6 }

rcCfmMepExMplstpLtResultMipIfNum   OBJECT-TYPE 
	SYNTAX      Unsigned32
    MAX-ACCESS  read-only
	STATUS      current
    DESCRIPTION
            "The MIP If-Num of MPLS-TP LT result."
	::= {rcCfmMepExMplstpLtResultEntry 7 }	
      
rcCfmMepExMplstpLtResultIsDes    OBJECT-TYPE 
	SYNTAX      TruthValue
    MAX-ACCESS  read-only
	STATUS      current
    DESCRIPTION
            "True indicates that the lt operation has reached the destination,
            False indicates that the destination has not been reached."
	::= {rcCfmMepExMplstpLtResultEntry 8 }	

--------------------------------------------------------------------------------
--CFM LB Result Table 
--------------------------------------------------------------------------------
rcCfmMepExLbResultTable 	OBJECT-TYPE
    SYNTAX      SEQUENCE OF RcCfmMepExLbResultEntry
    MAX-ACCESS  not-accessible
    STATUS      current
    DESCRIPTION
        "Result table of LB"                              
    ::= { rcCfm 31 }
    
rcCfmMepExLbResultEntry  	OBJECT-TYPE
	SYNTAX      RcCfmMepExLbResultEntry
    MAX-ACCESS  not-accessible
    STATUS      current
    DESCRIPTION
        "An entry in the rcCfmMepExLbResultTable."
    INDEX	{ dot1agCfmMdIndex, 
    		  dot1agCfmMaIndex,
    		  dot1agCfmMepIdentifier,
    		  rcCfmMepExLbResultTransId
    		}
    ::= { rcCfmMepExLbResultTable 1 }   
    
RcCfmMepExLbResultEntry ::= SEQUENCE {
    rcCfmMepExLbResultTransId       Unsigned32,
	rcCfmMepExLbResultStatus        INTEGER,
	rcCfmMepExLbResultRtt           Unsigned32,
	rcCfmMepExLbResultType          INTEGER,
	rcCfmMepExLbResultMepId	        Unsigned32 (0..8191),
	rcCfmMepExLbResultMipICC        OCTET STRING (SIZE(1..6)),	
	rcCfmMepExLbResultMipNodeId     Unsigned32,
	rcCfmMepExLbResultIfNum         Unsigned32 
}	

rcCfmMepExLbResultTransId   OBJECT-TYPE 
	SYNTAX      Unsigned32 
    MAX-ACCESS  not-accessible
	STATUS      current
    DESCRIPTION
            "The TransId of LB result."
	::= {rcCfmMepExLbResultEntry 1 }
	
rcCfmMepExLbResultStatus   OBJECT-TYPE 
	SYNTAX      INTEGER{
	                none(0),
	                correct(1),
	                bad(2),
	                unexpected(3),
	                timeout(4)}
    MAX-ACCESS  read-only
	STATUS      current
    DESCRIPTION
            "The Result status of Received LBR. 
            The param used in both mpls-tp and ethernet."
          	::= {rcCfmMepExLbResultEntry 2 }
	
rcCfmMepExLbResultRtt OBJECT-TYPE 
	SYNTAX      Unsigned32  
    MAX-ACCESS  read-only
	STATUS      current
    DESCRIPTION
            "The cost of th ping."
	::= {rcCfmMepExLbResultEntry 3 }
	
rcCfmMepExLbResultType   OBJECT-TYPE 
	SYNTAX      INTEGER {
	                    none(0),
	                    mep(1),
	                    mip(2)}
    MAX-ACCESS  read-only
	STATUS      current
    DESCRIPTION
            "The target Type of LB, which only used in mpls-tp."
	::= {rcCfmMepExLbResultEntry 4 }
	
rcCfmMepExLbResultMepId   OBJECT-TYPE 
	SYNTAX      Unsigned32 (0..8191) 
    MAX-ACCESS  read-only
	STATUS      current
    DESCRIPTION
            "The mep id of the target, which only used in mpls-tp."
	::= {rcCfmMepExLbResultEntry 5 }
	
rcCfmMepExLbResultMipICC   OBJECT-TYPE 
	SYNTAX      OCTET STRING (SIZE(1..6)) 
    MAX-ACCESS  read-only
	STATUS      current
    DESCRIPTION
            "The icc code of the target MIP, only used in mpls-tp."
	::= {rcCfmMepExLbResultEntry 6 }
	
rcCfmMepExLbResultMipNodeId   OBJECT-TYPE 
	SYNTAX      Unsigned32 
    MAX-ACCESS  read-only
	STATUS      current
    DESCRIPTION
            "The node id of target mip, only used in mpls-tp."
	::= {rcCfmMepExLbResultEntry 7 }
	
rcCfmMepExLbResultIfNum   OBJECT-TYPE 
	SYNTAX      Unsigned32 
    MAX-ACCESS  read-only
	STATUS      current
    DESCRIPTION
            "The interface of target mip, only used in mpls-tp"
	::= {rcCfmMepExLbResultEntry 8 }
	
--------------------------------------------------------------------------------
--MPLS-TP Service Quick Create Table
--------------------------------------------------------------------------------
rcCfmMplstpServiceQuickCreateTable 					OBJECT-TYPE
    SYNTAX      SEQUENCE OF RcCfmMplstpServiceQuickCreateEntry
    MAX-ACCESS  not-accessible
    STATUS      current
    DESCRIPTION
        "MPLS-TP Service Quick Create Table "  
        
    ::= { rcCfm 32 }
    
rcCfmMplstpServiceQuickCreateEntry          			OBJECT-TYPE
	SYNTAX      RcCfmMplstpServiceQuickCreateEntry
    MAX-ACCESS  not-accessible
    STATUS      current
    DESCRIPTION
        "An entry in the rcCfmMplstpServiceQuickCreateTable. "
    INDEX	{
               rcCfmMplstpServiceQuickCreateIndex,
               rcCfmMplstpServiceQuickCreateMaIndex
        	}
    ::= { rcCfmMplstpServiceQuickCreateTable 1 } 
    
    RcCfmMplstpServiceQuickCreateEntry ::= SEQUENCE 
    {     
        rcCfmMplstpServiceQuickCreateIndex           Unsigned32,  
        rcCfmMplstpServiceQuickCreateMaIndex         Unsigned32, 
        rcCfmMplstpMdLevel                           Unsigned32 (0..7),
        rcCfmMplstpMaNetName			             Dot1agCfmMaintAssocName,
        rcCfmMplstpMaNetPduPriority                  Unsigned32 (0..7),
        rcCfmMplstpMaNetCcmInterval                  Dot1agCfmCcmInterval,
        rcCfmMplstpMaOamType                         INTEGER,  
        rcCfmMplstpMaSectionPort                     InterfaceIndexOrZero,
        rcCfmMplstpMaIngressLspId                    OCTET STRING (SIZE (0..32)),
		rcCfmMplstpMaEgressLspId                     OCTET STRING (SIZE (0..32)),
   		rcCfmMplstpMaPwVcid                          Unsigned32,
        rcCfmMplstpMaPwPeerAddrType                  InetAddressType,
        rcCfmMplstpMaPwPeerAddr                      InetAddress,
        rcCfmMplstpMaSncTtl                          INTEGER(0..255),
        rcCfmMplstpMaSncLsridAddrType                InetAddressType,
        rcCfmMplstpMaSncLsridAddr                    InetAddress,
        rcCfmMplstpMaTransitForwardPwVcid            Unsigned32,
        rcCfmMplstpMaTransitForwardPwPeerAddrType    InetAddressType,
        rcCfmMplstpMaTransitForwardPwPeerAddr        InetAddress,
        rcCfmMplstpMaTransitBackwardPwVcid           Unsigned32,
        rcCfmMplstpMaTransitBackwardPwPeerAddrType   InetAddressType,
        rcCfmMplstpMaTransitBackwardPwPeerAddr       InetAddress,
        rcCfmMplstpMepIdentifier                     Dot1agCfmMepId,
        rcCfmMplstpMepCciEnabled                     TruthValue,
        rcCfmMplstpServiceCreateRowStatus            RowStatus
 	}
      
rcCfmMplstpServiceQuickCreateIndex OBJECT-TYPE
    SYNTAX      Unsigned32 
    MAX-ACCESS  not-accessible
    STATUS      current
    DESCRIPTION
       "The index of quick create Table，the value always equal to 1."
    ::= { rcCfmMplstpServiceQuickCreateEntry 1 }     
    
 rcCfmMplstpServiceQuickCreateMaIndex OBJECT-TYPE
    SYNTAX      Unsigned32 
    MAX-ACCESS  not-accessible
    STATUS      current
    DESCRIPTION
       "The index of quick create Table，the value always equal to 1."
    ::= { rcCfmMplstpServiceQuickCreateEntry 2 }
         
rcCfmMplstpMdLevel OBJECT-TYPE
    SYNTAX      Unsigned32 (0..7)
    MAX-ACCESS  read-write
    STATUS      current
    DESCRIPTION
        "The Mpls-tp Maintenance Domain Level."
  	::= { rcCfmMplstpServiceQuickCreateEntry 3 }
   
rcCfmMplstpMaNetName OBJECT-TYPE
    SYNTAX      Dot1agCfmMaintAssocName
    MAX-ACCESS  read-write
    STATUS      current
    DESCRIPTION
       "The Short Maintenance Association name."
    REFERENCE
       "802.1ag clauses 21.6.5.6, and Table 21-20"
    ::= { rcCfmMplstpServiceQuickCreateEntry 4 }  
  
rcCfmMplstpMaNetPduPriority          OBJECT-TYPE 
	SYNTAX      Unsigned32 (0..7)
	MAX-ACCESS  read-write
    STATUS      current
    DESCRIPTION
            "The pdu Priority. default priority is 7."    
    DEFVAL {7}
	::= { rcCfmMplstpServiceQuickCreateEntry 5 }    
	 
rcCfmMplstpMaNetCcmInterval OBJECT-TYPE
    SYNTAX      Dot1agCfmCcmInterval
    MAX-ACCESS  read-write
    STATUS      current
    DESCRIPTION
       "Interval between CCM transmissions to be used by MEP in the MA."
    REFERENCE
       "802.1ag clause 12.14.6.1.3:e"
    DEFVAL { interval1s }
    ::= { rcCfmMplstpServiceQuickCreateEntry 6 }    
    
rcCfmMplstpMaOamType          OBJECT-TYPE 
	SYNTAX      INTEGER{  
	              mode-none(0),
                  ether-oam(1),
                  pw-oam(2),
                  lsp-oam(3),
                  section-oam(4),
                  transit-lsp-oam(5),
                  transit-pw-oam(6)
                }
	MAX-ACCESS  read-write
    STATUS      current
    DESCRIPTION
            "The OAM Type associated with the ma."    
    DEFVAL {mode-none}
	::= { rcCfmMplstpServiceQuickCreateEntry 7 } 

rcCfmMplstpMaSectionPort             OBJECT-TYPE
    SYNTAX      InterfaceIndexOrZero
    MAX-ACCESS  read-write
    STATUS      current
    DESCRIPTION
            "Port specified when Ma associates with Section. 
            When rcCfmMaExOamType is section-oam(4) allowed 
            to be configurated." 
    DEFVAL { 0 }
    ::= { rcCfmMplstpServiceQuickCreateEntry 8 }	                  
	
rcCfmMplstpMaIngressLspId        OBJECT-TYPE 
	SYNTAX     OCTET STRING (SIZE (0..32))
	MAX-ACCESS  read-write
    STATUS      current
    DESCRIPTION
            "The ingress LSP name associated with the ma.
            When rcCfmMaExOamType is lsp-oam(3) allowed to be configurated."    
	::= { rcCfmMplstpServiceQuickCreateEntry 9 } 

rcCfmMplstpMaEgressLspId        OBJECT-TYPE 
	SYNTAX     OCTET STRING (SIZE (0..32))
	MAX-ACCESS  read-write
    STATUS      current
    DESCRIPTION
            "The egress LSP name associated with the ma.
            When rcCfmMaExOamType is lsp-oam(3) allowed to be configurated."    
	::= { rcCfmMplstpServiceQuickCreateEntry 10 } 
 	
rcCfmMplstpMaPwVcid              OBJECT-TYPE 
	SYNTAX      Unsigned32
	MAX-ACCESS  read-write
    STATUS      current
    DESCRIPTION
            "The VC ID associated with the ma.
            When rcCfmMaExOamType is pw-oam(2) allowed to be configurated."  
     DEFVAL {0}         
	::= { rcCfmMplstpServiceQuickCreateEntry 11 }     
	
rcCfmMplstpMaPwPeerAddrType OBJECT-TYPE
     SYNTAX        InetAddressType
     MAX-ACCESS    read-write
     STATUS        current
     DESCRIPTION
          "Denotes the address type of the peer node.  It should be
           set to 'unknown' if PE/PW maintenance protocol is not used
           and the address is unknown."
     DEFVAL { unknown }
     ::= { rcCfmMplstpServiceQuickCreateEntry 12 }

rcCfmMplstpMaPwPeerAddr OBJECT-TYPE
     SYNTAX        InetAddress
     MAX-ACCESS    read-write
     STATUS        current
     DESCRIPTION
          "This object contains the value of the peer node address
           of the PW/PE maintenance protocol entity.  This object
           SHOULD contain a value of all zeroes if not applicable
           (rcCfmMaExPwPeerAddrType is 'unknown')."  
     DEFVAL { 0 }    
     ::= { rcCfmMplstpServiceQuickCreateEntry 13 }

rcCfmMplstpMaSncTtl OBJECT-TYPE
     SYNTAX        INTEGER(0..255)
     MAX-ACCESS    read-write
     STATUS        current
     DESCRIPTION
          "The ttl of ma based transit."  
     DEFVAL { 0 }    
     ::= { rcCfmMplstpServiceQuickCreateEntry 14 }

rcCfmMplstpMaSncLsridAddrType OBJECT-TYPE
     SYNTAX        InetAddressType
     MAX-ACCESS    read-write
     STATUS        current
     DESCRIPTION
          "Denotes the address type of Lsirid. It should be 
           set to 'unknown' if protocol is not used and the 
           address is unknown." 
     DEFVAL { unknown }
     ::= { rcCfmMplstpServiceQuickCreateEntry 15 }

rcCfmMplstpMaSncLsridAddr OBJECT-TYPE
     SYNTAX        InetAddress
     MAX-ACCESS    read-write
     STATUS        current
     DESCRIPTION
          "This object contains the value of the lsrid address
           of the lsp maintenance protocol entity.  This object
           should contain a value of all zeroes if not applicable
           (rcCfmMaExSncLsridAddrType is 'unknown')." 
     DEFVAL { 0 }    
     ::= { rcCfmMplstpServiceQuickCreateEntry 16 }

rcCfmMplstpMaTransitForwardPwVcid OBJECT-TYPE
     SYNTAX        Unsigned32
     MAX-ACCESS    read-write
     STATUS        current
     DESCRIPTION
          "Transit PW forward VCID, and it is valid when 
           rcCfmMaExOamType is transit-pw-oam."  
     DEFVAL { 0 }    
     ::= { rcCfmMplstpServiceQuickCreateEntry 17 }

rcCfmMplstpMaTransitForwardPwPeerAddrType OBJECT-TYPE
     SYNTAX        InetAddressType
     MAX-ACCESS    read-write
     STATUS        current
     DESCRIPTION
          "Transit PW forward peer address type, and it is
           valid when rcCfmMaExOamType is transit-pw-oam." 
     DEFVAL { unknown }
     ::= { rcCfmMplstpServiceQuickCreateEntry 18 }

rcCfmMplstpMaTransitForwardPwPeerAddr OBJECT-TYPE
     SYNTAX        InetAddress
     MAX-ACCESS    read-write
     STATUS        current
     DESCRIPTION
          "Transit PW forward peer address, and it is valid
           when rcCfmMaExOamType is transit-pw-oam." 
     DEFVAL { 0 }    
     ::= { rcCfmMplstpServiceQuickCreateEntry 19 }

rcCfmMplstpMaTransitBackwardPwVcid OBJECT-TYPE
     SYNTAX        Unsigned32
     MAX-ACCESS    read-write
     STATUS        current
     DESCRIPTION
          "Transit PW backward VCID, and it is valid when 
           rcCfmMaExOamType is transit-pw-oam."  
     DEFVAL { 0 }    
     ::= { rcCfmMplstpServiceQuickCreateEntry 20 }

rcCfmMplstpMaTransitBackwardPwPeerAddrType OBJECT-TYPE
     SYNTAX        InetAddressType
     MAX-ACCESS    read-write
     STATUS        current
     DESCRIPTION
          "Transit PW backward peer address type, and it is
           valid when rcCfmMaExOamType is transit-pw-oam." 
     DEFVAL { unknown }
     ::= { rcCfmMplstpServiceQuickCreateEntry 21 }

rcCfmMplstpMaTransitBackwardPwPeerAddr OBJECT-TYPE
     SYNTAX        InetAddress
     MAX-ACCESS    read-write
     STATUS        current
     DESCRIPTION
          "Transit PW backward peer address, and it is valid
           when rcCfmMaExOamType is transit-pw-oam." 
     DEFVAL { 0 }    
     ::= { rcCfmMplstpServiceQuickCreateEntry 22 }

rcCfmMplstpMepIdentifier  OBJECT-TYPE
     SYNTAX        Dot1agCfmMepId
     MAX-ACCESS    read-write
     STATUS        current
     DESCRIPTION
          "Identifier of a specific Maintenance association End Point." 
     DEFVAL { 0 }    
     ::= { rcCfmMplstpServiceQuickCreateEntry 23 }

rcCfmMplstpMepCciEnabled OBJECT-TYPE
     SYNTAX        TruthValue
     MAX-ACCESS    read-write
     STATUS        current
     DESCRIPTION
          "If set to true, the MEP will generate CCM messages." 
     DEFVAL { false }    
     ::= { rcCfmMplstpServiceQuickCreateEntry 24 }     
     
 rcCfmMplstpServiceCreateRowStatus OBJECT-TYPE
    SYNTAX      RowStatus
    MAX-ACCESS  read-create
    STATUS      current
    DESCRIPTION
       "The status of the row."
    ::= {rcCfmMplstpServiceQuickCreateEntry 25 }

--------------------------------------------------------------------------------
--MPLS-TP Service Quick Destroy Table
--------------------------------------------------------------------------------
rcCfmMplstpServiceQuickDestroyTable 					OBJECT-TYPE
    SYNTAX      SEQUENCE OF RcCfmMplstpServiceQuickDestroyEntry
    MAX-ACCESS  not-accessible
    STATUS      current
    DESCRIPTION
        "MPLS-TP Service Quick Destroy Table "  
        
    ::= { rcCfm 33 }
    
rcCfmMplstpServiceQuickDestroyEntry          			OBJECT-TYPE
	SYNTAX      RcCfmMplstpServiceQuickDestroyEntry
    MAX-ACCESS  not-accessible
    STATUS      current
    DESCRIPTION
        "An entry in the rcCfmMplstpServiceQuickDestroyTable. "
    INDEX	{
              dot1agCfmMdIndex,
              dot1agCfmMaIndex 
            }
    ::= { rcCfmMplstpServiceQuickDestroyTable 1 } 
    
    RcCfmMplstpServiceQuickDestroyEntry ::= SEQUENCE 
    {     
        rcCfmMplstpServiceRowStatus           RowStatus 
 	}
      	
rcCfmMplstpServiceRowStatus OBJECT-TYPE
    SYNTAX      RowStatus
    MAX-ACCESS  read-create
    STATUS      current
    DESCRIPTION
       "The status of the row."
    ::= {rcCfmMplstpServiceQuickDestroyEntry 1 }

--------------------------------------------------------------------------------
--ETHERNET Service Quick Create Table
--------------------------------------------------------------------------------
rcCfmEthServiceQuickCreateTable 					OBJECT-TYPE
    SYNTAX      SEQUENCE OF RcCfmEthServiceQuickCreateEntry
    MAX-ACCESS  not-accessible
    STATUS      current
    DESCRIPTION
        "Ethernet  Service Quick Create Table "  
        
    ::= { rcCfm 34 }
    
rcCfmEthServiceQuickCreateEntry          			OBJECT-TYPE
	SYNTAX      RcCfmEthServiceQuickCreateEntry
    MAX-ACCESS  not-accessible
    STATUS      current
    DESCRIPTION
        "An entry in the rcCfmEthServiceQuickCreateTable. "
    INDEX	{
               rcCfmEthServiceQuickCreateIndex,
               rcCfmEthServiceQuickCreateMaIndex
        	}
    ::= { rcCfmEthServiceQuickCreateTable 1 } 
    
    RcCfmEthServiceQuickCreateEntry ::= SEQUENCE 
    {     
        rcCfmEthServiceQuickCreateIndex           Unsigned32,  
        rcCfmEthServiceQuickCreateMaIndex         Unsigned32, 
        rcCfmEthMdLevel                           Dot1agCfmMDLevel,  
        rcCfmEthMdFormat                          Dot1agCfmMaintDomainNameType,
        rcCfmEthMdName                            Dot1agCfmMaintDomainName,
        rcCfmEthMaFormat                          Dot1agCfmMaintAssocNameType,
        rcCfmEthMaNetName			              Dot1agCfmMaintAssocName,   
        rcCfmEthMaVlanList                        OCTET STRING (SIZE (512)),
        rcCfmEthMaPrimaryVlanId                   VlanIdOrNone,
        rcCfmEthMaCostumerVlan                    VlanIdOrNone,
        rcCfmEthMaNetPduPriority                  Unsigned32 (0..7),
        rcCfmEthMaNetCcmInterval                  Dot1agCfmCcmInterval,
        rcCfmEthMepIdentifier                     Dot1agCfmMepId,  
        rcCfmEthMepDirection                      Dot1agCfmMpDirection,
        rcCfmEthMepIfindex                        InterfaceIndexOrZero, 
        rcCfmEthMepCciEnabled                     TruthValue,
        rcCfmEthServiceCreateRowStatus            RowStatus
 	}
      
rcCfmEthServiceQuickCreateIndex OBJECT-TYPE
    SYNTAX      Unsigned32 
    MAX-ACCESS  not-accessible
    STATUS      current
    DESCRIPTION
       "The index of quick create Table，the value always equal to 1."
    ::= { rcCfmEthServiceQuickCreateEntry 1 }     
    
rcCfmEthServiceQuickCreateMaIndex OBJECT-TYPE
    SYNTAX      Unsigned32 
    MAX-ACCESS  not-accessible
    STATUS      current
    DESCRIPTION
       "The index of quick create Table，the value always equal to 1."
    ::= { rcCfmEthServiceQuickCreateEntry 2 }
         
rcCfmEthMdLevel OBJECT-TYPE
    SYNTAX      Dot1agCfmMDLevel
    MAX-ACCESS  read-write
    STATUS      current
    DESCRIPTION
        "The Ethernet Maintenance Domain Level."
  	::= { rcCfmEthServiceQuickCreateEntry 3 }
  
rcCfmEthMdFormat OBJECT-TYPE
    SYNTAX      Dot1agCfmMaintDomainNameType
    MAX-ACCESS  read-create
    STATUS      current
    DESCRIPTION
       "The type (and thereby format) of the Maintenance Domain Name.       "
    ::= { rcCfmEthServiceQuickCreateEntry 4 }
   
rcCfmEthMdName OBJECT-TYPE
    SYNTAX      Dot1agCfmMaintDomainName
    MAX-ACCESS  read-write
    STATUS      current
    DESCRIPTION
       "The Maintenance Domain name. The type/format of this object
 	is determined by the value of the dot1agCfmMdNameType object."
    ::= { rcCfmEthServiceQuickCreateEntry 5 }  
  
rcCfmEthMaFormat OBJECT-TYPE
    SYNTAX      Dot1agCfmMaintAssocNameType
    MAX-ACCESS  read-create
    STATUS      current
    DESCRIPTION
       "The type (and thereby format) of the Maintenance Association
        Name.
       "    ::= { rcCfmEthServiceQuickCreateEntry 6 }
   
rcCfmEthMaNetName OBJECT-TYPE
    SYNTAX      Dot1agCfmMaintAssocName
    MAX-ACCESS  read-write
    STATUS      current
    DESCRIPTION
       "The Short Maintenance Association name."
    ::= { rcCfmEthServiceQuickCreateEntry 7 }  
 
rcCfmEthMaVlanList OBJECT-TYPE
    SYNTAX      OCTET STRING (SIZE (512))  
    MAX-ACCESS  read-create
    STATUS      current
    DESCRIPTION
       "The mapping VLANs with which the Maintenance Association is
        associated, or 0 if the MA is not attached to any VID.
        When rcCfmMaExOamType is ether-oam(1) allowed to be configurated."
    ::= { rcCfmEthServiceQuickCreateEntry 8 }
 
rcCfmEthMaPrimaryVlanId          OBJECT-TYPE 
	SYNTAX      VlanIdOrNone
	MAX-ACCESS  read-create
    STATUS      current
    DESCRIPTION
            "The PrimaryVlanId. default the minimum vlan in the vlanlist.
            When rcCfmMaExOamType is ether-oam(1) allowed to be configurated."    
    DEFVAL { 0 }
	::= { rcCfmEthServiceQuickCreateEntry 9 }   

rcCfmEthMaCostumerVlan OBJECT-TYPE
    SYNTAX      VlanIdOrNone
    MAX-ACCESS  read-create
    STATUS      current
    DESCRIPTION
        "costumer vlan in oam pdu. the value of 0 indicates oam Pdu transmited 
            without costumer vlan."
    DEFVAL{0}
	::= { rcCfmEthServiceQuickCreateEntry 10 }
	
rcCfmEthMaNetPduPriority          OBJECT-TYPE 
	SYNTAX      Unsigned32 (0..7)
	MAX-ACCESS  read-write
    STATUS      current
    DESCRIPTION
            "The pdu Priority. default priority is 7."    
    DEFVAL {7}
	::= { rcCfmEthServiceQuickCreateEntry 11 }    
	 
rcCfmEthMaNetCcmInterval OBJECT-TYPE
    SYNTAX      Dot1agCfmCcmInterval
    MAX-ACCESS  read-write
    STATUS      current
    DESCRIPTION
       "Interval between CCM transmissions to be used by MEP in the MA."
    DEFVAL { interval1s }
    ::= { rcCfmEthServiceQuickCreateEntry 12 }    
  
rcCfmEthMepIdentifier  OBJECT-TYPE
     SYNTAX        Dot1agCfmMepId
     MAX-ACCESS    read-write
     STATUS        current
     DESCRIPTION
          "Identifier of a specific Maintenance association End Point." 
     DEFVAL { 0 }    
     ::= { rcCfmEthServiceQuickCreateEntry 13 }  
  
rcCfmEthMepDirection  OBJECT-TYPE
     SYNTAX        Dot1agCfmMpDirection
     MAX-ACCESS    read-write
     STATUS        current
     DESCRIPTION
          "The direction in which the MEP faces on the Bridge port."    
     DEFVAL { 0 }    
     ::= { rcCfmEthServiceQuickCreateEntry 14 }  
          
rcCfmEthMepIfindex  OBJECT-TYPE
     SYNTAX        InterfaceIndexOrZero
     MAX-ACCESS    read-write
     STATUS        current
     DESCRIPTION
          "This object is the interface index of the interface either a
 	       bridge port, or an aggregated IEEE 802.1 link within a bridge
 	       port, to which the MEP is attached." 
     DEFVAL { 0 }    
     ::= { rcCfmEthServiceQuickCreateEntry 15 }  
        
rcCfmEthMepCciEnabled OBJECT-TYPE
     SYNTAX        TruthValue
     MAX-ACCESS    read-write
     STATUS        current
     DESCRIPTION
          "If set to true, the MEP will generate CCM messages." 
     DEFVAL { false }    
     ::= { rcCfmEthServiceQuickCreateEntry 16 }     
     
rcCfmEthServiceCreateRowStatus OBJECT-TYPE
    SYNTAX      RowStatus
    MAX-ACCESS  read-create
    STATUS      current
    DESCRIPTION
       "The status of the row."
    ::= {rcCfmEthServiceQuickCreateEntry 17 }

--------------------------------------------------------------------------------
--ETHERNET Service Quick Destroy Table
--------------------------------------------------------------------------------
rcCfmEthServiceQuickDestroyTable 					OBJECT-TYPE
    SYNTAX      SEQUENCE OF RcCfmEthServiceQuickDestroyEntry
    MAX-ACCESS  not-accessible
    STATUS      current
    DESCRIPTION
        "Ethernet Service Quick Destroy Table "  
        
    ::= { rcCfm 35 }
    
rcCfmEthServiceQuickDestroyEntry          			OBJECT-TYPE
	SYNTAX      RcCfmEthServiceQuickDestroyEntry
    MAX-ACCESS  not-accessible
    STATUS      current
    DESCRIPTION
        "An entry in the rcCfmEthServiceQuickDestroyTable. "
    INDEX	{
              dot1agCfmMdIndex,
              dot1agCfmMaIndex 
            }
    ::= { rcCfmEthServiceQuickDestroyTable 1 } 
    
    RcCfmEthServiceQuickDestroyEntry ::= SEQUENCE 
    {     
        rcCfmEthServiceRowStatus           RowStatus 
 	}
      	
rcCfmEthServiceRowStatus OBJECT-TYPE
    SYNTAX      RowStatus
    MAX-ACCESS  read-create
    STATUS      current
    DESCRIPTION
       "The status of the row."
    ::= {rcCfmEthServiceQuickDestroyEntry 1 }
		  	
END
