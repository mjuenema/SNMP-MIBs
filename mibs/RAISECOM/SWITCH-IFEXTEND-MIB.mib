--MibName=rcIfExtend
-- *****************************************************************
-- switch-ifextend-mib.mib:  Raisecom ifindex MIB file
--
-- May 2005, zhaohongce
--
-- Copyright (c) 1994-2000, 2001 by Raisecom, Inc.
-- All rights reserved.
-- 
-- *****************************************************************

SWITCH-IFEXTEND-MIB  DEFINITIONS ::= BEGIN

IMPORTS
	MODULE-IDENTITY, OBJECT-TYPE,
        Integer32, Counter64                    FROM SNMPv2-SMI
        
        MODULE-COMPLIANCE, OBJECT-GROUP         FROM SNMPv2-CONF
        
        iscomSwitch
                FROM RAISECOM-BASE-MIB;  

	rcIfExtend MODULE-IDENTITY
        LAST-UPDATED    "20050220000Z"
        ORGANIZATION    "Raisecom, Inc."
        CONTACT-INFO
                "       Raise Systems
                        
                Postal: Beijing,
                        China

                   Tel: 86-010-82884499

                E-mail: zhaohongce@raisecom.com"
        DESCRIPTION
                "Modified description of if extend object."
                ::= { iscomSwitch 20 }
------------------------------------------------------------------------------
-- Textual Conventions (i.e., these do not affect object encoding):
------------------------------------------------------------------------------
--
-- "DURABLE":
--    Objects that are saved across a system reset and/or power cycle
--    are noted as "DURABLE" for convenience in the DESCRIPTION
--    section of the object definition.  Code must be explicitly
--    written to implement these DURABLE objects.
--

------------------------------------------------------------------------------

------------------------------------------------------------------------------
--  define groups in SWITCH-IFExtend-MIB
------------------------------------------------------------------------------
    rcIfExtendMib			OBJECT IDENTIFIER ::= { rcIfExtend 1 }						
------------------------------------------------------------------------------

----------------------------------------------
----rcIfExtend group rcIfExtendTable----
----------------------------------------------
rcIfExtendTable OBJECT-TYPE
        SYNTAX SEQUENCE OF RcIfExtendEntry
        MAX-ACCESS not-accessible
        STATUS current
        DESCRIPTION
            "A description table of interface extended."
        ::= { rcIfExtendMib 1 }

rcIfExtendEntry OBJECT-TYPE
        SYNTAX RcIfExtendEntry
        MAX-ACCESS not-accessible
        STATUS current
        DESCRIPTION
            "Table entry for switch interface extended information."
        INDEX { rcIfindex }
        ::= { rcIfExtendTable 1 }

RcIfExtendEntry ::= SEQUENCE {
        rcIfindex     		INTEGER,
        rcIfDescription		OCTET STRING
    }

rcIfindex OBJECT-TYPE
        SYNTAX INTEGER
        MAX-ACCESS not-accessible
        STATUS current
        DESCRIPTION
            "An index that uniquely identifies a interface of the swtich."
        ::= { rcIfExtendEntry 1}

rcIfDescription OBJECT-TYPE
        SYNTAX      OCTET STRING
        MAX-ACCESS  read-write
        STATUS      current
        DESCRIPTION
            "The description of a interface of the swtich."
        ::= { rcIfExtendEntry 2}
        

--end--raisecomIfindex group ----------------------------
          
END
