--MibName=rcSntp
------------------------------------------------------------------------------
------------------------------------------------------------------------------
--
--  File         : sntp.mib
--  Description  : rose software system command  mib defination 
--  Version      : 0.1   
--  Date         : Dec 20, 2004     
--
--  Copyright (c) 2003-2004 Beijing Raisecom Science & Technology Co., ltd  All Rights Reserved.
--
------------------------------------------------------------------------------
------------------------------------------------------------------------------

    SWITCH-SNTP-MIB DEFINITIONS ::= BEGIN

    IMPORTS
        MODULE-IDENTITY, OBJECT-TYPE,
        IpAddress                    FROM SNMPv2-SMI 
        EnableVar				   FROM SWITCH-TC                               
        iscomSwitch                FROM RAISECOM-BASE-MIB;  

    rcSntp MODULE-IDENTITY
    
        LAST-UPDATED    "0412200000Z"  -- Dec 20, 2004
        ORGANIZATION    "Raisecom Science & Technology Co., ltd"
        CONTACT-INFO    "Raisecom Science & Technology Co., ltd.
                         E-mail: support@raisecom.com"

        DESCRIPTION     "ROSE SYSinfo Enterprise MIB definition."

        REVISION        "0412200000Z"  -- Dec 20, 2004
        DESCRIPTION     "Initial MIB creation."

                ::= { iscomSwitch 8 }      
                
----groups---------------------------------                
rcSntpServer        OBJECT IDENTIFIER ::= { rcSntp 1 }  
rcSntpClient       	OBJECT IDENTIFIER ::= { rcSntp 2 }
--------------------------------------------------   

----------rcSntpServer    
--rcSntpServer
	--rcSntpServerEnable
	--rcSntpServerBroadcastAddress
	--rcSntpServerSendInterval        

rcSntpServerEnable OBJECT-TYPE
        SYNTAX EnableVar        
        MAX-ACCESS read-write
        STATUS current
        DESCRIPTION
            "enable system to send sntp message or disable such function  "
        DEFVAL {disable}
        ::= { rcSntpServer 1 }
        
rcSntpServerBroadcastAddress OBJECT-TYPE
        SYNTAX IpAddress
        MAX-ACCESS read-write
        STATUS current
        DESCRIPTION
            "system sntp server host ip address  ."
        ::= { rcSntpServer 2 }


rcSntpServerSendInterval OBJECT-TYPE
        SYNTAX INTEGER(1..65535)
        MAX-ACCESS read-write
        STATUS current
        DESCRIPTION
            "the interval for  system to send sntp message. "
        ::= { rcSntpServer 3 }




--------------------------------------------------------------------------------------
--sysSntpClient  tempory defination for snmp trap server
--------------------------------------------------------------------------------------
--rcSntpClient
	--rcSntpClientAddress
	--rcSntpClientGet
	--rcSntpClientListenEnable

rcSntpClientAddress OBJECT-TYPE
        SYNTAX IpAddress
        MAX-ACCESS read-write
        STATUS current
        DESCRIPTION
            "system sntp server host ip address which to get sntp message ."
        ::= { rcSntpClient 1 }

rcSntpClientGet OBJECT-TYPE
        SYNTAX INTEGER{
        	enable(1),disable(2)        	
        	}        
        MAX-ACCESS read-write
        STATUS current
        DESCRIPTION
            "The operation of system to specific sntp server host ip address which to get sntp message ."
        ::= { rcSntpClient 2 }
        
rcSntpClientListenEnable   OBJECT-TYPE
        SYNTAX EnableVar
        MAX-ACCESS read-write
        STATUS current
        DESCRIPTION
            "enable system to listen broadcast sntp message or disable such function  "
        DEFVAL {disable}
        ::= { rcSntpClient 3 }      

--
-- END of SWITCH-SNTP-MIB                
--

END
