--MibName=rcPortStatistics
-- *****************************************************************
-- RAISECOM-PORTSTATISTIC-MIB.mi2:  Raisecom port statistic MIB file
--
-- Nov 2004, gaohongwei
--
-- Copyright (c) 1994-2000, 2004 by Raisecom, Inc.
-- All rights reserved.
-- 
-- *****************************************************************
SWITCH-PORTSTATISTIC-MIB  DEFINITIONS ::= BEGIN
 
IMPORTS
       iscomSwitch         				FROM RAISECOM-BASE-MIB 
       TruthValue  	FROM SNMPv2-TC
       NOTIFICATION-TYPE,Counter64      FROM SNMPv2-SMI; 
                
	rcPortStatistics MODULE-IDENTITY
        LAST-UPDATED    "200412200000Z"
        ORGANIZATION    "Raisecom, Inc." 
        CONTACT-INFO
                "       Raise Systems
                        
                Postal: Beijing,
                        China

                   Tel: 86-010-82884499

                E-mail: surport@raisecom.com"
        DESCRIPTION
                "port statistic mib."
                ::= { iscomSwitch 7}
-------------------------------------------------------------------------
  
    rcPortStatsTable OBJECT-TYPE
        SYNTAX SEQUENCE OF RcPortStatsEntry
        MAX-ACCESS not-accessible
        STATUS current
        DESCRIPTION
            "A table of port statistic."
        ::= { rcPortStatistics 1 }

    rcPortStatsEntry OBJECT-TYPE
        SYNTAX RcPortStatsEntry
        MAX-ACCESS not-accessible
        STATUS current
        DESCRIPTION
            "Table entry of port statistic."
        INDEX { rcStatsPortIndex }
        ::= { rcPortStatsTable 1 }

    RcPortStatsEntry ::= SEQUENCE {
        rcStatsPortIndex               	INTEGER,
        rcStatsInPacket			Counter64,
        rcStatInPktType			INTEGER,
        rcStatsOutPacket		Counter64,
        rcStatOutPktType		INTEGER,
        rcStatsClear			TruthValue
        }      
     
   	rcStatsPortIndex OBJECT-TYPE
        SYNTAX INTEGER 
        MAX-ACCESS read-only
        STATUS current
        DESCRIPTION
            "An index based 1 that uniquely identifies a system interface."
        ::= { rcPortStatsEntry 1 }
                    
   	rcStatsInPacket OBJECT-TYPE
        SYNTAX  Counter64 
        ACCESS read-only
        STATUS current
        DESCRIPTION
                "count of packets received. "
        ::= { rcPortStatsEntry 2 }   
                        
        rcStatInPktType OBJECT-TYPE
    	SYNTAX      INTEGER {
                    		goodPacket(1),
			        badPacket(2),
			        localPacket(3)
                    } 
    	MAX-ACCESS  read-write
    	STATUS      current
    	DESCRIPTION
            "port ingress packet Statistic type"  
    	::= { rcPortStatsEntry 3 }           
   	 
                                     
   	rcStatsOutPacket OBJECT-TYPE
        SYNTAX  Counter64 
        ACCESS read-only
        STATUS current
        DESCRIPTION
                "count of packets transmitted. "
        ::= { rcPortStatsEntry 4 }   
                                   
  	rcStatOutPktType OBJECT-TYPE
   	SYNTAX      INTEGER {
                    		goodPacket(1),
			        badPacket(2),
			        abortPacket(3)
                    } 
    	MAX-ACCESS  read-write
    	STATUS      current
    	DESCRIPTION
            "port egress packet Statistic type"  
    	::= { rcPortStatsEntry 5 } 	
        
        rcStatsClear OBJECT-TYPE
    	SYNTAX      TruthValue
    	MAX-ACCESS  read-write
    	STATUS      current
    	DESCRIPTION
            "clear port statistics"
   	::= { rcPortStatsEntry 6 }       
   	
  --  rcPortStatsAllBitsTable

   	rcPortStatsAllBitsTable OBJECT-TYPE
        SYNTAX SEQUENCE OF RcPortStatsAllBitsEntry
        MAX-ACCESS not-accessible
        STATUS current
        DESCRIPTION
            "A table of port statistic about all bits transmitted or received."
        ::= { rcPortStatistics 2 }

    rcPortStatsAllBitsEntry OBJECT-TYPE
        SYNTAX RcPortStatsAllBitsEntry
        MAX-ACCESS not-accessible
        STATUS current
        DESCRIPTION
            "Table entry of port statistic about all bits transmitted or received."
        INDEX { rcStatsPortIndex }
        ::= { rcPortStatsAllBitsTable 1 }

    RcPortStatsAllBitsEntry ::= SEQUENCE {
        rcStatsInAllBits              Counter64,
        rcStatsOutAllBits             Counter64
        }        
        
   rcStatsInAllBits OBJECT-TYPE
       SYNTAX      Counter64
       MAX-ACCESS  read-only
       STATUS      current
       DESCRIPTION
               "The total number of bits received on the interface,
               including framing characters.

               Discontinuities in the value of this counter can occur
               at re-initialization of the management system, and at
               other times as indicated by the value of
               ifCounterDiscontinuityTime."
       ::= { rcPortStatsAllBitsEntry 1 }   
        
    rcStatsOutAllBits OBJECT-TYPE
       SYNTAX      Counter64
       MAX-ACCESS  read-only
       STATUS      current
       DESCRIPTION
               "The total number of bits transmitted out of the
               interface, including framing characters.

               Discontinuities in the value of this counter can occur
               at re-initialization of the management system, and at
               other times as indicated by the value of
               ifCounterDiscontinuityTime."
       ::= { rcPortStatsAllBitsEntry 2 } 	
END
