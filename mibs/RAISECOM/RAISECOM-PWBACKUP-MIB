--MibName=raisecom-pwbackup
-- *****************************************************************
-- RAISECOM-PWBACKUP-MIB.mib:   Raisecom pwBackup MIB file 
--
-- Copyright (c) 1994-2004 by Raisecom, Inc.
-- All rights reserved.
--
-- *****************************************************************
RAISECOM-PWBACKUP-MIB  DEFINITIONS ::= BEGIN

IMPORTS
        raisecomAgent                     FROM RAISECOM-BASE-MIB
        RowStatus, 
        TimeStamp,
        TruthValue                        FROM SNMPv2-TC
        EnableVar,ClearVar                FROM SWITCH-TC
        InetAddressType, InetAddress      FROM INET-ADDRESS-MIB              -- [RFC4001] 
        PwIDType                          FROM PW-TC-STD-MIB                 -- [RFC5542]
; 

raisecomPwBackup   MODULE-IDENTITY
    LAST-UPDATED   "201112150000Z"
    ORGANIZATION   "Raisecom, Inc."
    CONTACT-INFO  
                "       Raisecom Systems
                                                                                                               
                Postal: Beijing,
                        China

                   Tel: 86-010-82884499

                E-mail: wangjing03@raisecom.com"
        DESCRIPTION
        "This MIB module defines objects to pwBackup "
        REVISION   "201112150000Z"
        DESCRIPTION
            "The initial revision of this MIB."
        ::={ raisecomAgent 68 } 

raisecomPwBackupCfg                    OBJECT IDENTIFIER ::= { raisecomPwBackup 1 }
raisecomPwBackupState                  OBJECT IDENTIFIER ::= { raisecomPwBackup 2 }
raisecomPwBackupNotification           OBJECT IDENTIFIER ::= { raisecomPwBackup 3 }


-- -------------------------------------------------------------
-- raisecomPwBackupCfgTable
-- -------------------------------------------------------------
raisecomPwBackupCfgTable               OBJECT-TYPE
        SYNTAX      SEQUENCE OF RaisecomPwBackupCfgEntry
        MAX-ACCESS  not-accessible
        STATUS      current
        DESCRIPTION 
            "Pwbackup configure table."
        ::= { raisecomPwBackupCfg 1 }

raisecomPwBackupCfgEntry               OBJECT-TYPE
        SYNTAX      RaisecomPwBackupCfgEntry
        MAX-ACCESS  not-accessible
        STATUS      current
        DESCRIPTION
            "An entry in the raisecomPwBackupCfgTable. It contains
            config information of each pwbackup."
	    INDEX        { raisecomPwBackupCfgId }    
        ::={ raisecomPwBackupCfgTable 1 }
    
        RaisecomPwBackupCfgEntry ::= SEQUENCE
        {
    	    raisecomPwBackupCfgId	                 INTEGER,
    	    raisecomPwBackupCfgWorkVcid              PwIDType,
    	    raisecomPwBackupCfgWorkPeerType          InetAddressType,
    	    raisecomPwBackupCfgWorkPeer              InetAddress,
    	    raisecomPwBackupCfgWorkMaName            OCTET STRING,
    	    raisecomPwBackupCfgWorkMep               INTEGER,
    	    raisecomPwBackupCfgProtectionVcid        PwIDType,
    	    raisecomPwBackupCfgProtectionPeerType    InetAddressType,
    	    raisecomPwBackupCfgProtectionPeer        InetAddress, 
    	    raisecomPwBackupCfgProtectionMaName      OCTET STRING,
            raisecomPwBackupCfgProtectionMep         INTEGER,
    	    raisecomPwBackupCfgRevertiveMode         INTEGER,
    	    raisecomPwBackupCfgWtrTimer              INTEGER,
    	    raisecomPwBackupCfgForceSwitch           ClearVar,
    	    raisecomPwBackupCfgManualSwitch          ClearVar,
    	    raisecomPwBackupCfgManualSwitchtoWork    ClearVar,
    	    raisecomPwBackupCfgLockout               ClearVar,
    	    raisecomPwBackupCfgClear                 ClearVar,
    	    raisecomPwBackupCfgRowStatus             RowStatus
        }
                                        
raisecomPwBackupCfgId             OBJECT-TYPE
        SYNTAX INTEGER
        MAX-ACCESS not-accessible
        STATUS current
        DESCRIPTION
            "Pwbackup id, the index of raisecomPwBackupCfgTable."
        ::= { raisecomPwBackupCfgEntry 1 }

raisecomPwBackupCfgWorkVcid        OBJECT-TYPE
        SYNTAX PwIDType
        MAX-ACCESS read-create
        STATUS current
        DESCRIPTION
            "Working pw vcid of pwbackup."
        ::= { raisecomPwBackupCfgEntry 2 }

raisecomPwBackupCfgWorkPeerType        OBJECT-TYPE
        SYNTAX InetAddressType
        MAX-ACCESS read-create
        STATUS current
        DESCRIPTION                                                                                
            "Working pw peer address type."
        ::= { raisecomPwBackupCfgEntry 3 }

raisecomPwBackupCfgWorkPeer        OBJECT-TYPE
        SYNTAX InetAddress
        MAX-ACCESS read-create
        STATUS current
        DESCRIPTION                                                                                
            "Working pw peer address."
        ::= { raisecomPwBackupCfgEntry 4 }

raisecomPwBackupCfgWorkMaName OBJECT-TYPE
        SYNTAX OCTET STRING(SIZE (1..13))
  		MAX-ACCESS read-create
  		STATUS current
        DESCRIPTION
            "The Short Maintenance Association name. The type/format of this object is determined by the 
            value of the dot1agCfmMaNetNameType object. This name must be unique within a device."
        ::= { raisecomPwBackupCfgEntry 5 }

raisecomPwBackupCfgWorkMep OBJECT-TYPE
        SYNTAX INTEGER(1..8191)
  		MAX-ACCESS read-create
  		STATUS current
        DESCRIPTION
            "The mep id."
        ::= { raisecomPwBackupCfgEntry 6 }

raisecomPwBackupCfgProtectionVcid       OBJECT-TYPE
        SYNTAX PwIDType
        MAX-ACCESS read-create
        STATUS current
        DESCRIPTION
            "Protection pw vcid of pwbackup."
        ::= { raisecomPwBackupCfgEntry 7 }

raisecomPwBackupCfgProtectionPeerType        OBJECT-TYPE
        SYNTAX InetAddressType
        MAX-ACCESS read-create
        STATUS current
        DESCRIPTION                                                                                
            "Protection pw peer address type."
        ::= { raisecomPwBackupCfgEntry 8 }

raisecomPwBackupCfgProtectionPeer        OBJECT-TYPE
        SYNTAX InetAddress
        MAX-ACCESS read-create
        STATUS current
        DESCRIPTION                                                                                
            "Protection pw peer address."
        ::= { raisecomPwBackupCfgEntry 9 }

raisecomPwBackupCfgProtectionMaName OBJECT-TYPE
        SYNTAX OCTET STRING(SIZE (1..13))
  		MAX-ACCESS read-create
  		STATUS current
        DESCRIPTION
            "The Short Maintenance Association name. The type/format of this object is determined by the 
            value of the dot1agCfmMaNetNameType object. This name must be unique within a device."
        ::= { raisecomPwBackupCfgEntry 10 }

raisecomPwBackupCfgProtectionMep OBJECT-TYPE
        SYNTAX INTEGER(1..8191)
  		MAX-ACCESS read-create
  		STATUS current
        DESCRIPTION
            "The mep id."
        ::= { raisecomPwBackupCfgEntry 11 }

raisecomPwBackupCfgRevertiveMode        OBJECT-TYPE
        SYNTAX INTEGER {
                           revertive(1),
                           non-revertive(2)
                       }
        MAX-ACCESS read-create
        STATUS current
        DESCRIPTION                                                                                
            "The revertive mode of pwbackup."                                            
        ::= { raisecomPwBackupCfgEntry 12 }

raisecomPwBackupCfgWtrTimer        OBJECT-TYPE
        SYNTAX INTEGER (0..12)
        MAX-ACCESS read-create
        STATUS deprecated
        DESCRIPTION
            "In revertive mode of operation, to prevent frequent operation of the protection switch 
            due to an intermittent defect. After the failed working transport entity meets this criterion,
            a fixed period of time shall elapse before a normal traffic signal uses it again. This period, called 
            wait-to-restore (WTR) period, may be configured by the operator in 1 minute steps 
            between 1 and 12 minutes; the default value is 5 minutes."
        DEFVAL { 0 }                                          
        ::= { raisecomPwBackupCfgEntry 13 }

raisecomPwBackupCfgForceSwitch           OBJECT-TYPE
        SYNTAX  ClearVar
        MAX-ACCESS read-create
        STATUS deprecated
        DESCRIPTION
            "Forces normal traffic signal to be selected from the protection transport entity."    
        DEFVAL{ Clear }
        ::= { raisecomPwBackupCfgEntry 14 }

raisecomPwBackupCfgManualSwitch           OBJECT-TYPE
       SYNTAX  ClearVar
        MAX-ACCESS read-create
        STATUS deprecated
        DESCRIPTION
            "In the absence of a failure of a working or protection transport entity, forces normal 
            traffic signal to be selected from the protection transport entity."    
        DEFVAL{ Clear }
        ::= { raisecomPwBackupCfgEntry 15 }

raisecomPwBackupCfgManualSwitchtoWork           OBJECT-TYPE
        SYNTAX  ClearVar
        MAX-ACCESS read-create
        STATUS deprecated
        DESCRIPTION
            "In the absence of a failure of a working or protection transport entity, 
            forces normal traffic signal to be selected from the working transport entity."    
        DEFVAL{ Clear }
        ::= { raisecomPwBackupCfgEntry 16 }

raisecomPwBackupCfgLockout           OBJECT-TYPE
        SYNTAX  ClearVar
        MAX-ACCESS read-create
        STATUS deprecated
        DESCRIPTION
            "This command prevents a working signal from being selected from the protection transport 
            entity. This effectively disables the protection group."    
        DEFVAL{ Clear }
        ::= { raisecomPwBackupCfgEntry 17 }

raisecomPwBackupCfgClear             OBJECT-TYPE
        SYNTAX  ClearVar
        MAX-ACCESS read-create
        STATUS deprecated
        DESCRIPTION
            "Clears the active near end Lockout of Protection, Forced Switch, Manual Switch, 
            or WTR state."    
        DEFVAL{ Clear }
        ::= { raisecomPwBackupCfgEntry 18 }

raisecomPwBackupCfgRowStatus           OBJECT-TYPE
        SYNTAX RowStatus
        MAX-ACCESS read-create
        STATUS current
        DESCRIPTION
            "This object is responsible for managing the creation, deletion and modification of rows,
             which support active status and CreatAndGo, destroy operation."
        ::= { raisecomPwBackupCfgEntry 19 }

-- -------------------------------------------------------------
-- raisecomPwBackupStateTable
-- -------------------------------------------------------------
raisecomPwBackupStateTable               OBJECT-TYPE
        SYNTAX      SEQUENCE OF RaisecomPwBackupStateEntry
        MAX-ACCESS  not-accessible
        STATUS      current
        DESCRIPTION 
            "Pwbackup state table."
        ::= { raisecomPwBackupState 1 }

raisecomPwBackupStateEntry               OBJECT-TYPE
        SYNTAX      RaisecomPwBackupStateEntry
        MAX-ACCESS  not-accessible
        STATUS      current
        DESCRIPTION
            "An entry in the raisecomPwBackupStateTable. It contains
            state information of each pwbackup."
	    INDEX  { raisecomPwBackupCfgId }    
        ::={ raisecomPwBackupStateTable 1 }
    
        RaisecomPwBackupStateEntry ::= SEQUENCE
        {
    	    raisecomPwBackupWorkState	     INTEGER,
    	    raisecomPwBackupProtectionState  INTEGER,
    	    raisecomPwBackupProtocolState    INTEGER,
    	    raisecomPwBackupLastSwitchOccur  TimeStamp,
    	    raisecomPwBackupSwitchCount      INTEGER,
    	    raisecomPwBackupStateClear       ClearVar
        }                          

raisecomPwBackupWorkState        OBJECT-TYPE
        SYNTAX INTEGER {
                           active(1),
                           standby(2)
                       }
        MAX-ACCESS read-only
        STATUS current
        DESCRIPTION                                                                                
            "The working state of pwbackup, active or standby."                                            
        ::= { raisecomPwBackupStateEntry 1 }

raisecomPwBackupProtectionState        OBJECT-TYPE
        SYNTAX INTEGER {
                           active(1),
                           standby(2)
                       }
        MAX-ACCESS read-only
        STATUS current
        DESCRIPTION                                                                                
            "The protection state of pwbackup, active or standby."                                            
        ::= { raisecomPwBackupStateEntry 2 }

raisecomPwBackupProtocolState        OBJECT-TYPE
        SYNTAX INTEGER{
						nr-w(1),
						nr-p(2),
						lo(3),
						fs(4),
						sf-w(5),
						sf-p(6),
						ms-p(7),
						ms-w(8),
						wtr(9),
						dnr(10)
  				      }
        MAX-ACCESS read-only
        STATUS current
        DESCRIPTION
            "Pwbackup protocol status. The default state is No Request (Working/Active Protection/Standby)."
        DEFVAL { 1 }                                           
        ::= { raisecomPwBackupStateEntry 3 }

raisecomPwBackupLastSwitchOccur         OBJECT-TYPE
        SYNTAX TimeStamp
        MAX-ACCESS read-only
        STATUS current
        DESCRIPTION                                                                                
            "The time from the last switch happened to now."                                            
        ::= { raisecomPwBackupStateEntry 4 }        
        
raisecomPwBackupSwitchCount         OBJECT-TYPE
        SYNTAX INTEGER
        MAX-ACCESS read-only
        STATUS current
        DESCRIPTION                                                                                
            "The numbers of pwbackup switched."                                            
        ::= { raisecomPwBackupStateEntry 5 } 
        
raisecomPwBackupStateClear         OBJECT-TYPE
        SYNTAX ClearVar
        MAX-ACCESS read-write
        STATUS current
        DESCRIPTION                                                                                
            "Clears pwbackup switched information."    
        DEFVAL{ Clear }                                        
        ::= { raisecomPwBackupStateEntry 6 }

-- -------------------------------------------------------------
-- raisecomPwBackupSwitchOccur
-- -------------------------------------------------------------
raisecomPwBackupSwitchOccur NOTIFICATION-TYPE
         OBJECTS {
                     raisecomPwBackupProtocolState,
                     raisecomPwBackupLastSwitchOccur
                 }
         STATUS  current
         DESCRIPTION
             "Send this trap when pwbackup switched."
         ::= { raisecomPwBackupNotification 1 }

END
