-- PAN-TRAPS.my
--
-- MIB for the extended common MIB objects implemented by all
-- Palo Alto devices.
-- *********************************************** 

PAN-TRAPS DEFINITIONS ::= BEGIN

	 IMPORTS
		 MODULE-IDENTITY, OBJECT-IDENTITY,
		 OBJECT-TYPE, NOTIFICATION-TYPE,
		 Integer32, Counter64, Counter32
			 FROM SNMPv2-SMI
-- 		 MODULE-COMPLIANCE, OBJECT-GROUP
-- 			 FROM SNMPv2-CONF
		 DisplayString, TimeStamp, TruthValue
			 FROM SNMPv2-TC
		 TcChassisType
			 FROM PAN-GLOBAL-TC
		 panModules, panCommonMib
			 FROM PAN-GLOBAL-REG
		 panCommonEventObjs, panCommonEventEventsV2
			 FROM PAN-COMMON-MIB ;
    panTrapMibsModule MODULE-IDENTITY 
        LAST-UPDATED             "201106271040Z" 
        ORGANIZATION            "Palo Alto Networks" 
        CONTACT-INFO            " 
                    Customer Support 
                    Palo Alto Networks 
                    3300 Olcott St. 
                    Santa Clara, CA 95054 
 
                    +1 866-898-9087 
                    support at paloaltonetworks dot com" 
 
        DESCRIPTION             " 
            A MIB module containing definitions of managed objects 
            implemented by specific Palo Alto Networks products." 
 
        REVISION                "201106271040Z" 
        DESCRIPTION             " 
            Rev 1.0 
            Initial version of MIB module PAN-TRAPS." 
 
        ::= { panModules 5 } 
 
------------------------------------------------------------------------------
-- VARBINDS
------------------------------------------------------------------------------
--
--

	 panReceiveTime OBJECT-TYPE
		 SYNTAX 	 TimeStamp
		 MAX-ACCESS 	 accessible-for-notify
		 STATUS 	 current
		 DESCRIPTION
		   "Time the log was received at the management plane."
		 ::= { panCommonEventObjs 2}
--
--

	 panSerial OBJECT-TYPE
		 SYNTAX 	 OCTET STRING (SIZE (1..16))
		 MAX-ACCESS 	 accessible-for-notify
		 STATUS 	 current
		 DESCRIPTION
		   "Serial number of the device that generated the log."
		 ::= { panCommonEventObjs 3}
--
--

	 panEventType OBJECT-TYPE
		 SYNTAX 	 OCTET STRING (SIZE (1..16))
		 MAX-ACCESS 	 accessible-for-notify
		 STATUS 	 current
		 DESCRIPTION
		   "Specifies type of log; Values are traffic, threat, config, system and hip-match."
		 ::= { panCommonEventObjs 4}
--
--

	 panEventSubType OBJECT-TYPE
		 SYNTAX 	 OCTET STRING (SIZE (1..16))
		 MAX-ACCESS 	 accessible-for-notify
		 STATUS 	 current
		 DESCRIPTION
		   "Subtype of traffic log; Values are start, end, drop, and deny."
		 ::= { panCommonEventObjs 5}
--
--

	 panHost OBJECT-TYPE
		 SYNTAX 	 IpAddress
		 MAX-ACCESS 	 accessible-for-notify
		 STATUS 	 current
		 DESCRIPTION
		   "Host address of PAN device that generated the event."
		 ::= { panCommonEventObjs 6}
--
--

	 panVsys OBJECT-TYPE
		 SYNTAX 	 OCTET STRING (SIZE (0..32))
		 MAX-ACCESS 	 accessible-for-notify
		 STATUS 	 current
		 DESCRIPTION
		   "Virtual System associated with the session."
		 ::= { panCommonEventObjs 7}
--
--

	 panSeqno OBJECT-TYPE
		 SYNTAX 	 Counter64
		 MAX-ACCESS 	 accessible-for-notify
		 STATUS 	 current
		 DESCRIPTION
		   "A 64-bit log entry identifier incremented sequentially. Each log type has a unique number space"
		 ::= { panCommonEventObjs 8}
--
--

	 panActionflags OBJECT-TYPE
		 SYNTAX 	 Counter64
		 MAX-ACCESS 	 accessible-for-notify
		 STATUS 	 current
		 DESCRIPTION
		   "A bit field indicating if the log was forwarded to Panorama."
		 ::= { panCommonEventObjs 9}
--
--

	 panSource OBJECT-TYPE
		 SYNTAX 	 IpAddress
		 MAX-ACCESS 	 accessible-for-notify
		 STATUS 	 current
		 DESCRIPTION
		   "Original session source IP address."
		 ::= { panCommonEventObjs 50}
--
--

	 panDestination OBJECT-TYPE
		 SYNTAX 	 IpAddress
		 MAX-ACCESS 	 accessible-for-notify
		 STATUS 	 current
		 DESCRIPTION
		   "Original session destination IP address."
		 ::= { panCommonEventObjs 51}
--
--

	 panNatSource OBJECT-TYPE
		 SYNTAX 	 IpAddress
		 MAX-ACCESS 	 accessible-for-notify
		 STATUS 	 current
		 DESCRIPTION
		   "If Source NAT performed, the post-NAT Source IP address."
		 ::= { panCommonEventObjs 52}
--
--

	 panNatDestination OBJECT-TYPE
		 SYNTAX 	 IpAddress
		 MAX-ACCESS 	 accessible-for-notify
		 STATUS 	 current
		 DESCRIPTION
		   "If Destination NAT performed, the post-NAT Destination IP address."
		 ::= { panCommonEventObjs 53}
--
--

	 panRule OBJECT-TYPE
		 SYNTAX 	 OCTET STRING (SIZE (1..32))
		 MAX-ACCESS 	 accessible-for-notify
		 STATUS 	 current
		 DESCRIPTION
		   "Name of the rule that the session matched."
		 ::= { panCommonEventObjs 54}
--
--

	 panSrcUser OBJECT-TYPE
		 SYNTAX 	 OCTET STRING (SIZE (1..32))
		 MAX-ACCESS 	 accessible-for-notify
		 STATUS 	 current
		 DESCRIPTION
		   "User name of the user that initiated the session."
		 ::= { panCommonEventObjs 55}
--
--

	 panDstUser OBJECT-TYPE
		 SYNTAX 	 OCTET STRING (SIZE (1..32))
		 MAX-ACCESS 	 accessible-for-notify
		 STATUS 	 current
		 DESCRIPTION
		   "User name of the user to which the session was destined."
		 ::= { panCommonEventObjs 56}
--
--

	 panApplication OBJECT-TYPE
		 SYNTAX 	 OCTET STRING (SIZE (1..32))
		 MAX-ACCESS 	 accessible-for-notify
		 STATUS 	 current
		 DESCRIPTION
		   "Application associated with the session."
		 ::= { panCommonEventObjs 57}
--
--

	 panSourceZone OBJECT-TYPE
		 SYNTAX 	 OCTET STRING (SIZE (1..16))
		 MAX-ACCESS 	 accessible-for-notify
		 STATUS 	 current
		 DESCRIPTION
		   "Zone the session was sourced from."
		 ::= { panCommonEventObjs 58}
--
--

	 panDestinationZone OBJECT-TYPE
		 SYNTAX 	 OCTET STRING (SIZE (1..16))
		 MAX-ACCESS 	 accessible-for-notify
		 STATUS 	 current
		 DESCRIPTION
		   "Zone the session was destined to."
		 ::= { panCommonEventObjs 59}
--
--

	 panIngressInterface OBJECT-TYPE
		 SYNTAX 	 Counter64
		 MAX-ACCESS 	 accessible-for-notify
		 STATUS 	 current
		 DESCRIPTION
		   "Interface that the session was sourced form."
		 ::= { panCommonEventObjs 60}
--
--

	 panEgressInterface OBJECT-TYPE
		 SYNTAX 	 Counter64
		 MAX-ACCESS 	 accessible-for-notify
		 STATUS 	 current
		 DESCRIPTION
		   "Interface that the session was destined to."
		 ::= { panCommonEventObjs 61}
--
--

	 panLogForwardingProfile OBJECT-TYPE
		 SYNTAX 	 OCTET STRING (SIZE (1..32))
		 MAX-ACCESS 	 accessible-for-notify
		 STATUS 	 current
		 DESCRIPTION
		   "Log Forwarding Profile that was applied to the session"
		 ::= { panCommonEventObjs 62}
--
--

	 panSessionID OBJECT-TYPE
		 SYNTAX 	 Counter32
		 MAX-ACCESS 	 accessible-for-notify
		 STATUS 	 current
		 DESCRIPTION
		   "An internal numerical identifier applied to each session."
		 ::= { panCommonEventObjs 63}
--
--

	 panRepeatCount OBJECT-TYPE
		 SYNTAX 	 Counter32
		 MAX-ACCESS 	 accessible-for-notify
		 STATUS 	 current
		 DESCRIPTION
		   "Number of sessions with same Source IP, Destination IP, Application, and Subtype seen within 5 seconds; Used for ICMP only."
		 ::= { panCommonEventObjs 64}
--
--

	 panSourcePort OBJECT-TYPE
		 SYNTAX 	 Counter32
		 MAX-ACCESS 	 accessible-for-notify
		 STATUS 	 current
		 DESCRIPTION
		   "Source port utilized by the session."
		 ::= { panCommonEventObjs 65}
--
--

	 panDestinationPort OBJECT-TYPE
		 SYNTAX 	 Counter32
		 MAX-ACCESS 	 accessible-for-notify
		 STATUS 	 current
		 DESCRIPTION
		   "Destination port utilized by the session."
		 ::= { panCommonEventObjs 66}
--
--

	 panNatSourcePort OBJECT-TYPE
		 SYNTAX 	 Counter32
		 MAX-ACCESS 	 accessible-for-notify
		 STATUS 	 current
		 DESCRIPTION
		   "Post-NAT source port."
		 ::= { panCommonEventObjs 67}
--
--

	 panNatDestinationPort OBJECT-TYPE
		 SYNTAX 	 Counter32
		 MAX-ACCESS 	 accessible-for-notify
		 STATUS 	 current
		 DESCRIPTION
		   "Post-NAT destination port."
		 ::= { panCommonEventObjs 68}
--
--

	 panFlags OBJECT-TYPE
		 SYNTAX 	 Counter32
		 MAX-ACCESS 	 accessible-for-notify
		 STATUS 	 current
		 DESCRIPTION
		   "32 bit field that provides details on session."
		 ::= { panCommonEventObjs 69}
--
--

	 panProtocol OBJECT-TYPE
		 SYNTAX 	 Counter32
		 MAX-ACCESS 	 accessible-for-notify
		 STATUS 	 current
		 DESCRIPTION
		   "IP protocol associated with the session"
		 ::= { panCommonEventObjs 70}
--
--

	 panAction OBJECT-TYPE
		 SYNTAX 	 Counter32
		 MAX-ACCESS 	 accessible-for-notify
		 STATUS 	 current
		 DESCRIPTION
		   "Action taken for the session; Values are allow or deny"
		 ::= { panCommonEventObjs 71}
--
--

	 panTimeGenerated OBJECT-TYPE
		 SYNTAX 	 TimeStamp
		 MAX-ACCESS 	 accessible-for-notify
		 STATUS 	 current
		 DESCRIPTION
		   "Time the log was generated on the data plane"
		 ::= { panCommonEventObjs 72}
--
--

	 panSrcloc OBJECT-TYPE
		 SYNTAX 	 OCTET STRING (SIZE (1..32))
		 MAX-ACCESS 	 accessible-for-notify
		 STATUS 	 current
		 DESCRIPTION
		   "Source country or Internal region for private addresses. Maximum length is 32 bytes."
		 ::= { panCommonEventObjs 73}
--
--

	 panDstloc OBJECT-TYPE
		 SYNTAX 	 OCTET STRING (SIZE (1..32))
		 MAX-ACCESS 	 accessible-for-notify
		 STATUS 	 current
		 DESCRIPTION
		   "Destination country or Internal region for private addresses. Maximum length is 32 bytes."
		 ::= { panCommonEventObjs 74}
--
--

	 panTrafficBytes OBJECT-TYPE
		 SYNTAX 	 Counter64
		 MAX-ACCESS 	 accessible-for-notify
		 STATUS 	 current
		 DESCRIPTION
		   "Number of total bytes (transmit and receive) for the session."
		 ::= { panCommonEventObjs 100}
--
--

	 panTrafficPackets OBJECT-TYPE
		 SYNTAX 	 Counter32
		 MAX-ACCESS 	 accessible-for-notify
		 STATUS 	 current
		 DESCRIPTION
		   "Number of total packets (transmit and receive) for the session."
		 ::= { panCommonEventObjs 101}
--
--

	 panTrafficStartTime OBJECT-TYPE
		 SYNTAX 	 TimeStamp
		 MAX-ACCESS 	 accessible-for-notify
		 STATUS 	 current
		 DESCRIPTION
		   "Time of session start."
		 ::= { panCommonEventObjs 102}
--
--

	 panTrafficElapsed OBJECT-TYPE
		 SYNTAX 	 Counter32
		 MAX-ACCESS 	 accessible-for-notify
		 STATUS 	 current
		 DESCRIPTION
		   "Elapsed time of the session."
		 ::= { panCommonEventObjs 103}
--
--

	 panTrafficCategory OBJECT-TYPE
		 SYNTAX 	 OCTET STRING (SIZE (1..32))
		 MAX-ACCESS 	 accessible-for-notify
		 STATUS 	 current
		 DESCRIPTION
		   "URL category associated with the session (if applicable)."
		 ::= { panCommonEventObjs 104}
--
--

	 panConfigCmd OBJECT-TYPE
		 SYNTAX 	 OCTET STRING (SIZE (0..16))
		 MAX-ACCESS 	 accessible-for-notify
		 STATUS 	 current
		 DESCRIPTION
		   "Configuration command."
		 ::= { panCommonEventObjs 150}
--
--

	 panConfigAdmin OBJECT-TYPE
		 SYNTAX 	 OCTET STRING (SIZE (0..32))
		 MAX-ACCESS 	 accessible-for-notify
		 STATUS 	 current
		 DESCRIPTION
		   "Admin name who issued configuration command."
		 ::= { panCommonEventObjs 151}
--
--

	 panConfigClient OBJECT-TYPE
		 SYNTAX 	 OCTET STRING (SIZE (1..255))
		 MAX-ACCESS 	 accessible-for-notify
		 STATUS 	 current
		 DESCRIPTION
		   "Configuration client that generated command."
		 ::= { panCommonEventObjs 152}
--
--

	 panConfigResult OBJECT-TYPE
		 SYNTAX 	 OCTET STRING (SIZE (1..255))
		 MAX-ACCESS 	 accessible-for-notify
		 STATUS 	 current
		 DESCRIPTION
		   "Configuration command execution result success/failure ."
		 ::= { panCommonEventObjs 153}
--
--

	 panConfigPath OBJECT-TYPE
		 SYNTAX 	 OCTET STRING (SIZE (1..255))
		 MAX-ACCESS 	 accessible-for-notify
		 STATUS 	 current
		 DESCRIPTION
		   "Configuration path."
		 ::= { panCommonEventObjs 154}
--
--

	 panThreatId OBJECT-TYPE
		 SYNTAX 	 Counter32
		 MAX-ACCESS 	 accessible-for-notify
		 STATUS 	 current
		 DESCRIPTION
		   "Palo Alto Networks identifier for the threat. It is a numerical identifier followed by a description in parenthesis for some Subtypes."
		 ::= { panCommonEventObjs 200}
--
--

	 panThreatCategory OBJECT-TYPE
		 SYNTAX 	 OCTET STRING (SIZE (1..32))
		 MAX-ACCESS 	 accessible-for-notify
		 STATUS 	 current
		 DESCRIPTION
		   "Provides URL Category for URL Subtype; For other subtypes the value is æanyÆ."
		 ::= { panCommonEventObjs 201}
--
--

	 panThreatContentType OBJECT-TYPE
		 SYNTAX 	 OCTET STRING (SIZE (1..32))
		 MAX-ACCESS 	 accessible-for-notify
		 STATUS 	 current
		 DESCRIPTION
		   "Content type of the HTTP response data. Maximum length 32 bytes. Applicable only when Subtype is URL."
		 ::= { panCommonEventObjs 202}
--
--

	 panThreatSeverity OBJECT-TYPE
		 SYNTAX 	 INTEGER { unused (1), informational (2), low (3), medium (4), high (5), critical (6) }
		 MAX-ACCESS 	 accessible-for-notify
		 STATUS 	 current
		 DESCRIPTION
		   "Severity associated with the threat; Values are informational, low, medium, high, critical."
		 ::= { panCommonEventObjs 203}
--
--

	 panThreatDirection OBJECT-TYPE
		 SYNTAX 	 Counter32
		 MAX-ACCESS 	 accessible-for-notify
		 STATUS 	 current
		 DESCRIPTION
		   "Indicates the direction of the attack, æclient-to-serverÆ or æserver-to-clientÆ."
		 ::= { panCommonEventObjs 204}
--
--

	 panMiscellaneous OBJECT-TYPE
		 SYNTAX 	 OCTET STRING (SIZE (1..1024))
		 MAX-ACCESS 	 accessible-for-notify
		 STATUS 	 current
		 DESCRIPTION
		   "The actual URI when the subtype is URL; File name or file type when the subtype is file; and File name when the subtype is virus."
		 ::= { panCommonEventObjs 205}
--
--

	 panHipSourceUser OBJECT-TYPE
		 SYNTAX 	 OCTET STRING (SIZE (1..32))
		 MAX-ACCESS 	 accessible-for-notify
		 STATUS 	 current
		 DESCRIPTION
		   "User name of the Source user."
		 ::= { panCommonEventObjs 250}
--
--

	 panHipMachineName OBJECT-TYPE
		 SYNTAX 	 OCTET STRING (SIZE (1..32))
		 MAX-ACCESS 	 accessible-for-notify
		 STATUS 	 current
		 DESCRIPTION
		   "Name of the Users machine."
		 ::= { panCommonEventObjs 251}
--
--

	 panHipSource OBJECT-TYPE
		 SYNTAX 	 IpAddress
		 MAX-ACCESS 	 accessible-for-notify
		 STATUS 	 current
		 DESCRIPTION
		   "HIP Match source IP"
		 ::= { panCommonEventObjs 252}
--
--

	 panHipMatch OBJECT-TYPE
		 SYNTAX 	 OCTET STRING (SIZE (1..32))
		 MAX-ACCESS 	 accessible-for-notify
		 STATUS 	 current
		 DESCRIPTION
		   "Name of the HIP Object or Profile."
		 ::= { panCommonEventObjs 253}
--
--

	 panHipRepeatCount OBJECT-TYPE
		 SYNTAX 	 Counter32
		 MAX-ACCESS 	 accessible-for-notify
		 STATUS 	 current
		 DESCRIPTION
		   "Number of times the HIP profile matched."
		 ::= { panCommonEventObjs 254}
--
--

	 panHipMatchType OBJECT-TYPE
		 SYNTAX 	 Counter32
		 MAX-ACCESS 	 accessible-for-notify
		 STATUS 	 current
		 DESCRIPTION
		   "Specifies whether the HIP field represents a HIP Object or a HIP Profile."
		 ::= { panCommonEventObjs 255}
--
--

	 panSystemEventId OBJECT-TYPE
		 SYNTAX 	 Counter32
		 MAX-ACCESS 	 accessible-for-notify
		 STATUS 	 current
		 DESCRIPTION
		   "System log event ID"
		 ::= { panCommonEventObjs 300}
--
--

	 panSystemObject OBJECT-TYPE
		 SYNTAX 	 OCTET STRING (SIZE (1..32))
		 MAX-ACCESS 	 accessible-for-notify
		 STATUS 	 current
		 DESCRIPTION
		   "System log event object"
		 ::= { panCommonEventObjs 301}
--
--

	 panSystemModule OBJECT-TYPE
		 SYNTAX 	 Counter32
		 MAX-ACCESS 	 accessible-for-notify
		 STATUS 	 current
		 DESCRIPTION
		   "System log event module"
		 ::= { panCommonEventObjs 302}
--
--

	 panSystemSeverity OBJECT-TYPE
		 SYNTAX 	 INTEGER { unused (1), informational (2), low (3), medium (4), high (5), critical (6) }
		 MAX-ACCESS 	 accessible-for-notify
		 STATUS 	 current
		 DESCRIPTION
		   "System log event severity"
		 ::= { panCommonEventObjs 303}
--
--

	 panSystemDescription OBJECT-TYPE
		 SYNTAX 	 OCTET STRING (SIZE (1..512))
		 MAX-ACCESS 	 accessible-for-notify
		 STATUS 	 current
		 DESCRIPTION
		   "System log event description"
		 ::= { panCommonEventObjs 304}
----------------------------------------------------------------------------
-- TRAPS: CONFIG TRAFFIC THREAT HIPMATCH
----------------------------------------------------------------------------

	 panConfigTrap NOTIFICATION-TYPE
	   OBJECTS {
		 panReceiveTime, panSerial, panEventType, panEventSubType, panHost, panVsys, panConfigCmd, panConfigAdmin, panConfigClient, panConfigResult, panConfigPath, panSeqno, panActionflags
		 }
	 STATUS 	 current
	 DESCRIPTION
	   "A configuratioon event trap."
	 ::={panCommonEventEventsV2 2}

	 panTrafficTrap NOTIFICATION-TYPE
	   OBJECTS {
		 panReceiveTime, panSerial, panEventType, panEventSubType, panTimeGenerated, panSource, panDestination, panNatSource, panNatDestination, panRule, panSrcUser, panDstUser, panApplication, panVsys, panSourceZone, panDestinationZone, panIngressInterface, panEgressInterface, panLogForwardingProfile, panSessionID, panRepeatCount, panSourcePort, panDestinationPort, panNatSourcePort, panNatDestinationPort, panFlags, panProtocol, panAction, panTrafficBytes, panTrafficPackets, panTrafficStartTime, panTrafficElapsed, panTrafficCategory, panSeqno, panActionflags, panSrcloc, panDstloc
		 }
	 STATUS 	 current
	 DESCRIPTION
	   "A traffic event trap."
	 ::={panCommonEventEventsV2 3}

	 panThreatTrap NOTIFICATION-TYPE
	   OBJECTS {
		 panReceiveTime, panSerial, panEventType, panEventSubType, panTimeGenerated, panSource, panDestination, panNatSource, panNatDestination, panRule, panSrcUser, panDstUser, panApplication, panVsys, panSourceZone, panDestinationZone, panIngressInterface, panEgressInterface, panLogForwardingProfile, panSessionID, panRepeatCount, panSourcePort, panDestinationPort, panNatSourcePort, panNatDestinationPort, panFlags, panProtocol, panAction, panMiscellaneous, panThreatId, panThreatCategory, panThreatSeverity, panThreatDirection, panSeqno, panActionflags, panSrcloc, panDstloc, panThreatContentType
		 }
	 STATUS 	 current
	 DESCRIPTION
	   "A threat/URL event trap."
	 ::={panCommonEventEventsV2 4}

	 panHipMatchTrap NOTIFICATION-TYPE
	   OBJECTS {
		 panReceiveTime, panSerial, panEventType, panEventSubType, panHipSourceUser, panVsys, panHipMachineName, panHipSource, panHipMatch, panHipRepeatCount, panHipMatchType, panSeqno, panActionflags
		 }
	 STATUS 	 current
	 DESCRIPTION
	   "A Hipmatch event trap."
	 ::={panCommonEventEventsV2 5}
----------------------------------------------------------------------------
-- TRAPS: SYSTEM LOG EVENTS
----------------------------------------------------------------------------

	 panCryptoCertExpiryTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Certificate expired"
	 ::={panCommonEventEventsV2 100}

	 panCryptoMkeyExpiryTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Master key expired"
	 ::={panCommonEventEventsV2 101}

	 panCryptoMkeyExpiryReminderTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Master key expiry reminder"
	 ::={panCommonEventEventsV2 102}

	 panDHCPLeaseStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP lease started"
	 ::={panCommonEventEventsV2 200}

	 panDHCPLeaseEndTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP lease ended"
	 ::={panCommonEventEventsV2 201}

	 panDHCPServerOnTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP server on"
	 ::={panCommonEventEventsV2 202}

	 panDHCPServerAutoProbeOnTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP server auto-probe finished turn on DHCP server since no offer received"
	 ::={panCommonEventEventsV2 203}

	 panDHCPServerAutoProbeOffTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP server auto-probe finished turn off DHCP server since received offer"
	 ::={panCommonEventEventsV2 204}

	 panDHCPServerNoFreeIpTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP server runs out of ip pool"
	 ::={panCommonEventEventsV2 205}

	 panDHCPIpAlreadyInUseTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "ip address is already in use"
	 ::={panCommonEventEventsV2 206}

	 panDHCPRelayOnTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP relay on"
	 ::={panCommonEventEventsV2 207}

	 panDHCPRelayOffTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP relay off"
	 ::={panCommonEventEventsV2 208}

	 panDHCPRelay6OnTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCPv6 relay on"
	 ::={panCommonEventEventsV2 209}

	 panDHCPRelay6OffTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCPv6 relay off"
	 ::={panCommonEventEventsV2 210}

	 panDHCPIfUpdateFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP client interface update fail"
	 ::={panCommonEventEventsV2 211}

	 panDHCPIfUpdateOkTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP client interface update successful"
	 ::={panCommonEventEventsV2 212}

	 panDHCPIfClearTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP client interface info cleared"
	 ::={panCommonEventEventsV2 213}

	 panDHCPIfRenewTriggerTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP client interface renew triggered"
	 ::={panCommonEventEventsV2 214}

	 panDHCPIfReleaseTriggerTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP client interface release triggered"
	 ::={panCommonEventEventsV2 215}

	 panDHCPIfRcvNakTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP client interface received nak"
	 ::={panCommonEventEventsV2 216}

	 panDHCPIfInheritTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DHCP server interface inherited settings"
	 ::={panCommonEventEventsV2 217}

	 panDNSProxyCacheClearedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DNS Proxy cache cleared"
	 ::={panCommonEventEventsV2 300}

	 panDNSProxyResolveFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Failed to resolve domain name"
	 ::={panCommonEventEventsV2 301}

	 panDNSProxyObjectEnableTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Enabled/Disabled DNS proxy object"
	 ::={panCommonEventEventsV2 302}

	 panDNSProxyIfAddTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Assigned interface to DNS proxy object"
	 ::={panCommonEventEventsV2 303}

	 panDNSProxyIfDelTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Removed interface from DNS proxy object"
	 ::={panCommonEventEventsV2 304}

	 panDNSProxyIfInheritTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DNS Proxy object inherited settings"
	 ::={panCommonEventEventsV2 305}

	 panDOSDosRuleChangedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "DOS rule changed"
	 ::={panCommonEventEventsV2 500}

	 panGeneralGeneralTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "General system event"
	 ::={panCommonEventEventsV2 600}

	 panGeneralSystemStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "System start"
	 ::={panCommonEventEventsV2 601}

	 panGeneralSystemShutdownTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "System shutdown"
	 ::={panCommonEventEventsV2 602}

	 panGeneralAuthFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Authentication attempt faliure"
	 ::={panCommonEventEventsV2 603}

	 panGeneralAuthSuccessTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Authentication attempt success"
	 ::={panCommonEventEventsV2 604}

	 panGlobalProtectGatewayRegistSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway user login succeeded."
	 ::={panCommonEventEventsV2 700}

	 panGlobalProtectGatewayRegistFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway user login failed."
	 ::={panCommonEventEventsV2 701}

	 panGlobalProtectGatewayLogoutSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway user logout succeeded."
	 ::={panCommonEventEventsV2 702}

	 panGlobalProtectGatewayLogoutFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway user logout failed."
	 ::={panCommonEventEventsV2 703}

	 panGlobalProtectGatewayConfigSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway client configuration generated."
	 ::={panCommonEventEventsV2 704}

	 panGlobalProtectGatewayConfigFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway client configuration failed."
	 ::={panCommonEventEventsV2 705}

	 panGlobalProtectGatewayConfigReleaseTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway client configuration released."
	 ::={panCommonEventEventsV2 706}

	 panGlobalProtectGatewaySwitchSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway client switch to SSL tunnel mode succeeded."
	 ::={panCommonEventEventsV2 707}

	 panGlobalProtectGatewaySwitchFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway client switch to SSL tunnel mode failed."
	 ::={panCommonEventEventsV2 708}

	 panGlobalProtectGatewayAuthSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway user authentication succeeded."
	 ::={panCommonEventEventsV2 709}

	 panGlobalProtectGatewayAuthFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway user authentication failed."
	 ::={panCommonEventEventsV2 710}

	 panGlobalProtectGatewayAgentMsgTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway agent message."
	 ::={panCommonEventEventsV2 711}

	 panGlobalProtectGatewayInvalidLicenseTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway invalid gateway license."
	 ::={panCommonEventEventsV2 712}

	 panGlobalProtectGatewayInheritanceTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect gateway inheritance."
	 ::={panCommonEventEventsV2 713}

	 panGlobalProtectPortalConfigSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect portal client configuration generated."
	 ::={panCommonEventEventsV2 714}

	 panGlobalProtectPortalConfigFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect portal client configuration failed."
	 ::={panCommonEventEventsV2 715}

	 panGlobalProtectPortalAuthSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect portal user authentication succeeded."
	 ::={panCommonEventEventsV2 716}

	 panGlobalProtectPortalAuthFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "GlobalProtect portal user authentication failed."
	 ::={panCommonEventEventsV2 717}

	 panHAPreemptTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA device going passive due to preemption"
	 ::={panCommonEventEventsV2 800}

	 panHAStateChangeTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA device has changed states"
	 ::={panCommonEventEventsV2 801}

	 panHAStateOverrideTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA device state override change"
	 ::={panCommonEventEventsV2 802}

	 panHADataplaneDownTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA has detected a dataplane down"
	 ::={panCommonEventEventsV2 803}

	 panHAPolicyPushFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA policy push to dataplane failed"
	 ::={panCommonEventEventsV2 804}

	 panHAHa1LinkChangeTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA1 peer link change"
	 ::={panCommonEventEventsV2 805}

	 panHAHa2LinkChangeTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA2 peer link change"
	 ::={panCommonEventEventsV2 806}

	 panHAConnectChangeTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer connection change"
	 ::={panCommonEventEventsV2 807}

	 panHAPathMonitorDownTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA monitored path down"
	 ::={panCommonEventEventsV2 808}

	 panHALinkMonitorDownTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA monitored link down"
	 ::={panCommonEventEventsV2 809}

	 panHAHa3LinkChangeTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA3 peer link change"
	 ::={panCommonEventEventsV2 810}

	 panHAPathMonitorUpTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA monitored path up"
	 ::={panCommonEventEventsV2 811}

	 panHALinkMonitorUpTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA monitored link up"
	 ::={panCommonEventEventsV2 812}

	 panHAPeerSyncFailureTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA can't synch non-configuration controlplane data to peer"
	 ::={panCommonEventEventsV2 813}

	 panHAConfigFailureTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA configuration push to peer has failed"
	 ::={panCommonEventEventsV2 814}

	 panHAConfigNotSynchTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA config not automatically synched"
	 ::={panCommonEventEventsV2 815}

	 panHAPeerErrorTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA error message from peer"
	 ::={panCommonEventEventsV2 816}

	 panHAPre13Trap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer is running pre-1.3 software"
	 ::={panCommonEventEventsV2 817}

	 panHAPre20Trap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer is running pre-2.0 software"
	 ::={panCommonEventEventsV2 818}

	 panHAPeerVersionMatchTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer other software version matching"
	 ::={panCommonEventEventsV2 819}

	 panHAPeerVersionSupportedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer version is supported with our local version"
	 ::={panCommonEventEventsV2 820}

	 panHAPeerVersionUnsupportedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer version is not supported with our local version"
	 ::={panCommonEventEventsV2 821}

	 panHAPeerVersionDegradedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer version is degraded in our local version"
	 ::={panCommonEventEventsV2 822}

	 panHAPeerCompatMismatchTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer compatibility mismatch"
	 ::={panCommonEventEventsV2 823}

	 panHAPeerCompatMatchTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer compatibility now matches"
	 ::={panCommonEventEventsV2 824}

	 panHAPeerCompatFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer compatibility failure"
	 ::={panCommonEventEventsV2 825}

	 panHAPeerSplitBrainTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer detected split-brain"
	 ::={panCommonEventEventsV2 826}

	 panHASplitBrainTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA device detected split-brain"
	 ::={panCommonEventEventsV2 827}

	 panHAPreemptLoopTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA device going suspend due to preemption-loop"
	 ::={panCommonEventEventsV2 828}

	 panHANonFunctionalLoopTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA device going suspend due to non-functional-loop"
	 ::={panCommonEventEventsV2 829}

	 panHAPeerShutdownTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA peer change caused a local shutdown"
	 ::={panCommonEventEventsV2 830}

	 panHANfsPanlogsFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "NFS panlogs failure"
	 ::={panCommonEventEventsV2 831}

	 panHAInternalHaErrorTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "HA is not working properly; please call support"
	 ::={panCommonEventEventsV2 832}

	 panHWDiskErrorsTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Hard drive physical issues"
	 ::={panCommonEventEventsV2 900}

	 panNTDPRestartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Restarted ntpd"
	 ::={panCommonEventEventsV2 1000}

	 panNTDPTimeLearnTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Restarted ntpd on config change"
	 ::={panCommonEventEventsV2 1001}

	 panPBFNhUpTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "PBF nexthop is reachable"
	 ::={panCommonEventEventsV2 1100}

	 panPBFNhDownTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "PBF nexthop is unreachable"
	 ::={panCommonEventEventsV2 1101}

	 panPORTLinkChangeTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Interface link state change"
	 ::={panCommonEventEventsV2 1200}

	 panPORTNonqualSfpTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Non-qualified SFP inserted"
	 ::={panCommonEventEventsV2 1201}

	 panPORTNonqualSfpPlusTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Non-qualified SFP-plus inserted"
	 ::={panCommonEventEventsV2 1202}

	 panPORTNonqualXfpTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Non-qualified XFP inserted"
	 ::={panCommonEventEventsV2 1203}

	 panPPPOEInitiateTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "PPPOE initiated"
	 ::={panCommonEventEventsV2 1300}

	 panPPPOEConnectTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "PPPOE connected"
	 ::={panCommonEventEventsV2 1301}

	 panPPPOEConnectFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "PPPOE failed to connect"
	 ::={panCommonEventEventsV2 1302}

	 panPPPOETerminateTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "PPPOE terminated"
	 ::={panCommonEventEventsV2 1303}

	 panPPPOEIfUpdateFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "PPPOE interface update failed"
	 ::={panCommonEventEventsV2 1304}

	 panRASRasmgrConfigP1SuccessTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon configuration load phase-1 succeeded."
	 ::={panCommonEventEventsV2 1400}

	 panRASRasmgrConfigP1FailedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon configuration load phase-1 failed."
	 ::={panCommonEventEventsV2 1401}

	 panRASRasmgrConfigP1AbortTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon configuration load phase-1 aborted."
	 ::={panCommonEventEventsV2 1402}

	 panRASRasmgrConfigP2SuccessTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon configuration load phase-2 succeeded."
	 ::={panCommonEventEventsV2 1403}

	 panRASRasmgrConfigP2FailedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon configuration load phase-2 failed."
	 ::={panCommonEventEventsV2 1404}

	 panRASRasmgrDaemonStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon is ready."
	 ::={panCommonEventEventsV2 1405}

	 panRASRasmgrDaemonExitTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon has exit."
	 ::={panCommonEventEventsV2 1406}

	 panRASRasmgrDaemonInitTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon is initializing."
	 ::={panCommonEventEventsV2 1407}

	 panRASRasmgrFlowFullSyncStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon sync all user info to Flow started."
	 ::={panCommonEventEventsV2 1408}

	 panRASRasmgrFlowFullSyncAbortTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon sync all user info to Flow no longer needed."
	 ::={panCommonEventEventsV2 1409}

	 panRASRasmgrFlowFullSyncDoneTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon sync all user info to Flow exit."
	 ::={panCommonEventEventsV2 1410}

	 panRASRasmgrHaFullSyncStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon sync all user info to HA peer started."
	 ::={panCommonEventEventsV2 1411}

	 panRASRasmgrHaFullSyncAbortTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon sync all user info to HA peer no longer needed."
	 ::={panCommonEventEventsV2 1412}

	 panRASRasmgrHaFullSyncDoneTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RASMGR daemon sync all user info to HA peer exit."
	 ::={panCommonEventEventsV2 1413}

	 panROUTINGRoutedConfigP1SuccessTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Route daemon configuration load phase-1 succeeded."
	 ::={panCommonEventEventsV2 1500}

	 panROUTINGRoutedConfigP1FailedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Route daemon configuration load phase-1 failed."
	 ::={panCommonEventEventsV2 1501}

	 panROUTINGRoutedConfigP1AbortTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Route daemon configuration load phase-1 aborted."
	 ::={panCommonEventEventsV2 1502}

	 panROUTINGRoutedConfigP2SuccessTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Route daemon configuration load phase-2 succeeded."
	 ::={panCommonEventEventsV2 1503}

	 panROUTINGRoutedConfigP2FailedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Route daemon configuration load phase-2 failed."
	 ::={panCommonEventEventsV2 1504}

	 panROUTINGRoutedDaemonStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Route daemon is ready."
	 ::={panCommonEventEventsV2 1505}

	 panROUTINGRoutedDaemonExitTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Route daemon has exit."
	 ::={panCommonEventEventsV2 1506}

	 panROUTINGRoutedDaemonInitTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Route daemon is initializing."
	 ::={panCommonEventEventsV2 1507}

	 panROUTINGRoutedFibSyncPeerBackupTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "FIB HA sync started when peer device becomes passive."
	 ::={panCommonEventEventsV2 1508}

	 panROUTINGRoutedFibSyncSelfMasterTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "FIB HA sync started when local device becomes master."
	 ::={panCommonEventEventsV2 1509}

	 panROUTINGRoutedRTMBadRouteTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "An invalid dynamic route has been rejected:"
	 ::={panCommonEventEventsV2 1510}

	 panROUTINGRoutedOSPFLSAChksumFailedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF LSA checksum generating failed due to memory corruption."
	 ::={panCommonEventEventsV2 1511}

	 panROUTINGRoutedOSPFLSAChksumInvalidTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF received LSA with invalid checksum."
	 ::={panCommonEventEventsV2 1512}

	 panROUTINGRoutedOSPFAuthtypeBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF packet dropped due to unexpected authentication type."
	 ::={panCommonEventEventsV2 1513}

	 panROUTINGRoutedOSPFPasswordBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF packet dropped due to incorrect simple password."
	 ::={panCommonEventEventsV2 1514}

	 panROUTINGRoutedOSPFChksumBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF packet dropped due to incorrect OSPF checksum."
	 ::={panCommonEventEventsV2 1515}

	 panROUTINGRoutedOSPFSequenceBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF packet dropped due to incorrect sequence number."
	 ::={panCommonEventEventsV2 1516}

	 panROUTINGRoutedOSPFMd5chksumBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF packet dropped due to incorrect MD5 checksum."
	 ::={panCommonEventEventsV2 1517}

	 panROUTINGRoutedOSPFMd5lengthBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF packet dropped due to incorrect MD5 digest length."
	 ::={panCommonEventEventsV2 1518}

	 panROUTINGRoutedOSPFHelloHelloIntvalBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF hello packet dropped due to hello-interval mismatch."
	 ::={panCommonEventEventsV2 1519}

	 panROUTINGRoutedOSPFHelloDeadIntvalBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF hello packet dropped due to dead-interval mismatch."
	 ::={panCommonEventEventsV2 1520}

	 panROUTINGRoutedOSPFHelloNetmaskBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF hello packet dropped due to network masks mismatch."
	 ::={panCommonEventEventsV2 1521}

	 panROUTINGRoutedOSPFHelloAreaTypeBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF hello packet dropped due to area type mismatch."
	 ::={panCommonEventEventsV2 1522}

	 panROUTINGRoutedOSPFNeighbor2dirTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF two-way communication established with neighbor."
	 ::={panCommonEventEventsV2 1523}

	 panROUTINGRoutedOSPFNeighborFullTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF full adjacency established with neighbor."
	 ::={panCommonEventEventsV2 1524}

	 panROUTINGRoutedOSPFNeighborDownTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "OSPF adjacency with neighbor has gone down."
	 ::={panCommonEventEventsV2 1525}

	 panROUTINGRoutedRIPPeerAddTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RIP peer discovered."
	 ::={panCommonEventEventsV2 1526}

	 panROUTINGRoutedRIPPeerDelTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RIP peer disappeared."
	 ::={panCommonEventEventsV2 1527}

	 panROUTINGRoutedRIPAuthtypeBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RIP packet dropped due to unexpected authentication type."
	 ::={panCommonEventEventsV2 1528}

	 panROUTINGRoutedRIPAuthFailedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RIP packet dropped due to authentication failure."
	 ::={panCommonEventEventsV2 1529}

	 panROUTINGRoutedRIPMd5lengthBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "RIP packet dropped due to incorrect MD5 digest length."
	 ::={panCommonEventEventsV2 1530}

	 panROUTINGRoutedBGPPeerEnterEstablishedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "BGP peer session enters established state."
	 ::={panCommonEventEventsV2 1531}

	 panROUTINGRoutedBGPPeerLeftEstablishedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "BGP peer session left established state."
	 ::={panCommonEventEventsV2 1532}

	 panROUTINGRoutedBGPPeerFailedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "BGP peer session has failed and may restart."
	 ::={panCommonEventEventsV2 1533}

	 panROUTINGRoutedBGPPeerRestartedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Initiated graceful-restart with a BGP peer."
	 ::={panCommonEventEventsV2 1534}

	 panROUTINGRoutedBGPPeerRestartFailedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Graceful-restart with a BGP peer failed."
	 ::={panCommonEventEventsV2 1535}

	 panROUTINGRoutedBGPRefreshSentTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "ROUTE REFRESH message sent to a BGP peer."
	 ::={panCommonEventEventsV2 1536}

	 panROUTINGRoutedBGPRibinRecalcTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "An RIB-In is being recalculated as a result of changed import policy."
	 ::={panCommonEventEventsV2 1537}

	 panROUTINGRoutedPIMInterfaceStateChangedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "PIM interface state changed"
	 ::={panCommonEventEventsV2 1538}

	 panROUTINGRoutedPIMNewDrElectedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "PIM elected a new DR"
	 ::={panCommonEventEventsV2 1539}

	 panROUTINGRoutedPIMNeighborDiscoveredTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "PIM discovered a new neighbor"
	 ::={panCommonEventEventsV2 1540}

	 panROUTINGRoutedPIMNeighborDisappearedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "PIM neighbor disappeared"
	 ::={panCommonEventEventsV2 1541}

	 panROUTINGRoutedIGMPWrongVersionTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Wrong IGMP query version"
	 ::={panCommonEventEventsV2 1542}

	 panSSLVPNSslvpnRegistSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "SSL VPN user login succeeded."
	 ::={panCommonEventEventsV2 1600}

	 panSSLVPNSslvpnRegistFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "SSL VPN user login failed."
	 ::={panCommonEventEventsV2 1601}

	 panSSLVPNSslvpnLogoutSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "SSL VPN user logout succeeded."
	 ::={panCommonEventEventsV2 1602}

	 panSSLVPNSslvpnLogoutFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "SSL VPN user logout failed."
	 ::={panCommonEventEventsV2 1603}

	 panSSLVPNSslvpnConfigSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "SSL VPN client configuration generated."
	 ::={panCommonEventEventsV2 1604}

	 panSSLVPNSslvpnConfigFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "SSL VPN client configuration failed."
	 ::={panCommonEventEventsV2 1605}

	 panSSLVPNSslvpnConfigReleaseTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "SSL VPN client configuration released."
	 ::={panCommonEventEventsV2 1606}

	 panSSLVPNSslvpnSwitchSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "SSL VPN client switch to SSL tunnel mode succeeded."
	 ::={panCommonEventEventsV2 1607}

	 panSSLVPNSslvpnSwitchFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "SSL VPN client switch to SSL tunnel mode failed."
	 ::={panCommonEventEventsV2 1608}

	 panSSLVPNSslvpnAuthSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "SSL VPN user authentication succeeded."
	 ::={panCommonEventEventsV2 1609}

	 panSSLVPNSslvpnAuthFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "SSL VPN user authentication failed."
	 ::={panCommonEventEventsV2 1610}

	 panVPNIkeConfigP1SuccessTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE daemon configuration load phase-1 succeeded."
	 ::={panCommonEventEventsV2 1700}

	 panVPNIkeConfigP1FailedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE daemon configuration load phase-1 failed."
	 ::={panCommonEventEventsV2 1701}

	 panVPNIkeConfigP1AbortTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE daemon configuration load phase-1 aborted."
	 ::={panCommonEventEventsV2 1702}

	 panVPNIkeConfigP2SuccessTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE daemon configuration load phase-2 succeeded."
	 ::={panCommonEventEventsV2 1703}

	 panVPNIkeConfigP2FailedTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE daemon configuration load phase-2 failed."
	 ::={panCommonEventEventsV2 1704}

	 panVPNIkeDaemonStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE daemon is ready."
	 ::={panCommonEventEventsV2 1705}

	 panVPNIkeDaemonExitTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE daemon has exit."
	 ::={panCommonEventEventsV2 1706}

	 panVPNIkeDaemonInitTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE daemon is initializing."
	 ::={panCommonEventEventsV2 1707}

	 panVPNIkeNegoP1StartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-1 negotiation is started"
	 ::={panCommonEventEventsV2 1708}

	 panVPNIkeNegoP1FailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-1 negotiation is failed"
	 ::={panCommonEventEventsV2 1709}

	 panVPNIkeNegoP1SuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-1 negotiation is succeeded"
	 ::={panCommonEventEventsV2 1710}

	 panVPNIkeNegoP1ExpireTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-1 SA is expired"
	 ::={panCommonEventEventsV2 1711}

	 panVPNIkeNegoP1DeleteTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-1 SA is deleted"
	 ::={panCommonEventEventsV2 1712}

	 panVPNIkeNegoP1DpdDnTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-1 SA is down determined by DPD."
	 ::={panCommonEventEventsV2 1713}

	 panVPNIkeNegoP1PskIdtypeTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-1 negotiation is failed. When pre-shared key is used peer-ID must be type IP address."
	 ::={panCommonEventEventsV2 1714}

	 panVPNIkeNegoP1FailPskTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-1 negotiation is failed likely due to pre-shared key mismatch."
	 ::={panCommonEventEventsV2 1715}

	 panVPNIkeNegoP1FailCommonTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-1 negotiation is failed."
	 ::={panCommonEventEventsV2 1716}

	 panVPNIkeNegoP2StartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-2 negotiation is started"
	 ::={panCommonEventEventsV2 1717}

	 panVPNIkeNegoP2FailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-2 negotiation is failed"
	 ::={panCommonEventEventsV2 1718}

	 panVPNIkeNegoP2SuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-2 negotiation is succeeded"
	 ::={panCommonEventEventsV2 1719}

	 panVPNIkeNegoP2StaleP1Trap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Deleting a possible stale phase-1 SA."
	 ::={panCommonEventEventsV2 1720}

	 panVPNIkeNegoP2DupRekeyTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "duplicate phase-2 rekey request detected ignore new request."
	 ::={panCommonEventEventsV2 1721}

	 panVPNIkeNegoP2SimulContTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "simultaneous phase-2 rekey request detected peer is PANOS. Ignore this new request."
	 ::={panCommonEventEventsV2 1722}

	 panVPNIkeNegoP2SimulFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "simultaneous phase-2 rekey request detected peer is PANOS. Previous request removed."
	 ::={panCommonEventEventsV2 1723}

	 panVPNIkeNegoP2SimulDelayTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "simultaneous phase-2 rekey request detected peer is not PANOS. Delay processing this new request."
	 ::={panCommonEventEventsV2 1724}

	 panVPNIkeNegoP2NoP1Trap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-2 negotiation request received but no phase-1 SA is found."
	 ::={panCommonEventEventsV2 1725}

	 panVPNIkeNegoP2P1NotReadyTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-2 negotiation request received but no active phase-1 SA is available."
	 ::={panCommonEventEventsV2 1726}

	 panVPNIkeNegoP2ProxyIdBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-2 negotiation failed when processing proxy ID."
	 ::={panCommonEventEventsV2 1727}

	 panVPNIkeNegoP2ProposalBadTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE phase-2 negotiation failed when processing SA payload."
	 ::={panCommonEventEventsV2 1728}

	 panVPNIpsecKeyInstallTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IPSec key installed."
	 ::={panCommonEventEventsV2 1729}

	 panVPNIpsecKeyDeleteTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IPSec key deleted."
	 ::={panCommonEventEventsV2 1730}

	 panVPNIpsecKeyExpireTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IPSec key lifetime expired."
	 ::={panCommonEventEventsV2 1731}

	 panVPNIkeRecvNotifyTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE protocol notification message received:"
	 ::={panCommonEventEventsV2 1732}

	 panVPNIkeRecvP1DeleteTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE protocol phase-1 SA delete message received from peer."
	 ::={panCommonEventEventsV2 1733}

	 panVPNIkeRecvP2DeleteTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE protocol IPSec SA delete message received from peer."
	 ::={panCommonEventEventsV2 1734}

	 panVPNIkeSendNotifyTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE protocol notification message sent:"
	 ::={panCommonEventEventsV2 1735}

	 panVPNIkeSendP1DeleteTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE protocol phase-1 SA delete message sent to peer."
	 ::={panCommonEventEventsV2 1736}

	 panVPNIkeSendP2DeleteTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKE protocol IPSec SA delete message sent to peer."
	 ::={panCommonEventEventsV2 1737}

	 panVPNIkev2NegoIkeStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKEv2 IKE SA negotiation is started"
	 ::={panCommonEventEventsV2 1738}

	 panVPNIkev2NegoIkeFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKEv2 IKE SA negotiation is failed"
	 ::={panCommonEventEventsV2 1739}

	 panVPNIkev2NegoIkeSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKEv2 IKE SA negotiation is succeeded"
	 ::={panCommonEventEventsV2 1740}

	 panVPNIkev2NegoIkeExpireTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKEv2 IKE SA is expired"
	 ::={panCommonEventEventsV2 1741}

	 panVPNIkev2NegoIkeDeleteTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKEv2 IKE SA is deleted"
	 ::={panCommonEventEventsV2 1742}

	 panVPNIkev2NegoChildStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKEv2 Child SA negotiation is started"
	 ::={panCommonEventEventsV2 1743}

	 panVPNIkev2NegoChildFailTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKEv2 Child SA negotiation is failed"
	 ::={panCommonEventEventsV2 1744}

	 panVPNIkev2NegoChildSuccTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "IKEv2 Child SA negotiation is succeeded"
	 ::={panCommonEventEventsV2 1745}

	 panVPNTunnelStatusUpTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Tunnel status change to UP."
	 ::={panCommonEventEventsV2 1746}

	 panVPNTunnelStatusDownTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "Tunnel status change to DOWN."
	 ::={panCommonEventEventsV2 1747}

	 panVPNKeymgrDaemonStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR daemon is ready."
	 ::={panCommonEventEventsV2 1748}

	 panVPNKeymgrDaemonExitTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR daemon has exit."
	 ::={panCommonEventEventsV2 1749}

	 panVPNKeymgrDaemonInitTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR daemon is initializing."
	 ::={panCommonEventEventsV2 1750}

	 panVPNKeymgrFlowFullSyncStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR sync all IPSec SA to Flow started."
	 ::={panCommonEventEventsV2 1751}

	 panVPNKeymgrFlowFullSyncAbortTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR sync all IPSec SA to Flow no longer needed."
	 ::={panCommonEventEventsV2 1752}

	 panVPNKeymgrFlowFullSyncDoneTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR sync all IPSec SA to Flow exit."
	 ::={panCommonEventEventsV2 1753}

	 panVPNKeymgrIkeFullSyncStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR sync all IPSec SA to IKE daemon started."
	 ::={panCommonEventEventsV2 1754}

	 panVPNKeymgrIkeFullSyncAbortTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR sync all IPSec SA to IKE daemon no longer needed."
	 ::={panCommonEventEventsV2 1755}

	 panVPNKeymgrIkeFullSyncDoneTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR sync all IPSec SA to IKE daemon exit."
	 ::={panCommonEventEventsV2 1756}

	 panVPNKeymgrHaFullSyncStartTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR sync all IPSec SA to HA peer started."
	 ::={panCommonEventEventsV2 1757}

	 panVPNKeymgrHaFullSyncAbortTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR sync all IPSec SA to HA peer no longer needed."
	 ::={panCommonEventEventsV2 1758}

	 panVPNKeymgrHaFullSyncDoneTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   "KEYMGR sync all IPSec SA to HA peer exit."
	 ::={panCommonEventEventsV2 1759}

	 panVPNIkeGenericEventTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   ""
	 ::={panCommonEventEventsV2 1760}

	 panVPNKeymgrGenericEventTrap NOTIFICATION-TYPE
	   OBJECTS {
		 panReceiveTime, panSerial, panEventType, panEventSubType, panVsys, panSystemEventId, panSystemObject, panSystemModule, panSystemSeverity, panSystemDescription
		 }
	 STATUS 	 current
	 DESCRIPTION
	   ""
	 ::={panCommonEventEventsV2 1761}
END
