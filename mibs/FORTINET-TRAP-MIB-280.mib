FORTINET-TRAP-MIB-280 DEFINITIONS ::= BEGIN
	IMPORTS
		DisplayString
			FROM SNMPv2-TC
		MODULE-IDENTITY, OBJECT-TYPE, NOTIFICATION-TYPE,
		Integer32, Gauge32, enterprises, IpAddress
			FROM SNMPv2-SMI
		ifIndex
			FROM IF-MIB
		fnTraps, fnSysSerial
			FROM FORTINET-MIB-280;

--

	fnTrapCpuHigh  NOTIFICATION-TYPE
		OBJECTS       { fnSysSerial }
		STATUS        current
		DESCRIPTION   "Trap being sent if CPU usage becomes too high"
		::=  {  fnTraps  101  }

	fnTrapMemLow  NOTIFICATION-TYPE
		OBJECTS       { fnSysSerial }
		STATUS        current
		DESCRIPTION   "Trap being sent if memory usage becomes too high"
		::=  {  fnTraps  102  }

	fnTrapLogFull  NOTIFICATION-TYPE
		OBJECTS       { fnSysSerial }
		STATUS        current
		DESCRIPTION   "Trap being sent if log becomes full"
		::=  {  fnTraps  103  }

--

	fnTrapIpChange	NOTIFICATION-TYPE
		OBJECTS       { fnSysSerial, ifIndex }
		STATUS        current
		DESCRIPTION   "Trap being sent when IP address of
		               the specified interface has been
		               changed"
		::=  {  fnTraps  201  }

--

	fnTrapVpnTunUp	NOTIFICATION-TYPE
		OBJECTS       { fnSysSerial }
		STATUS        current
		DESCRIPTION   "Trap being sent when VPN tunnel is
		               brought up"
		::=  {  fnTraps  301  }

	fnTrapVpnTunDown	NOTIFICATION-TYPE
		OBJECTS       { fnSysSerial }
		STATUS        current
		DESCRIPTION   "Trap being sent when VPN tunnel is
		               brought down"
		::=  {  fnTraps  302  }

--

	fnTrapHaSwitch	NOTIFICATION-TYPE
		OBJECTS       { fnSysSerial }
		STATUS        current
		DESCRIPTION   "Trap being sent when the HA cluster 
		               master changes"
		::=  {  fnTraps  401  }

	fnTrapHaStateChange	NOTIFICATION-TYPE
		OBJECTS       { fnSysSerial }
		STATUS        current
		DESCRIPTION   "Trap being sent when the HA cluster 
		               member changes its state"
		::=  {  fnTraps  402  }

--

	fnTrapIdsSynFlood	NOTIFICATION-TYPE
		OBJECTS       { fnSysSerial }
		STATUS        current
		DESCRIPTION   "Trap being sent when SYN flood attack
		               is detected"
		::=  {  fnTraps  501  }

	fnTrapIdsPortScan	NOTIFICATION-TYPE
		OBJECTS       { fnSysSerial }
		STATUS        current
		DESCRIPTION   "Trap being sent when port scan attack
		               is detected"
		::=  {  fnTraps  502  }

	fnTrapIpsSignature	NOTIFICATION-TYPE
		OBJECTS       { fnSysSerial, fnIpsSigId, fnIpsSigSrcIp }
		STATUS        current
		DESCRIPTION   "Trap being sent when IPS signature is detected"
		::=  {  fnTraps  503  }

	fnTrapIpsAnomaly	NOTIFICATION-TYPE
		OBJECTS       { fnSysSerial }
		STATUS        current
		DESCRIPTION   "Trap being sent when IPS anomaly is detected"
		::=  {  fnTraps  504  }

--

	fnTrapAvEvent	NOTIFICATION-TYPE
		OBJECTS      { fnSysSerial }
		STATUS       current
		DESCRIPTION   "Trap being sent when antivirus scanner
		               detects a virus"
		::=  {  fnTraps  601  }

--

	fnTrapBridge	 NOTIFICATION-TYPE
		OBJECTS      { fnSysSerial }
		STATUS       current
		DESCRIPTION  "Trap being sent by FortiBridge when 
		              detecting a FortiGate failure"
		::=  {  fnTraps  701  }

--

	fnTrapImTableFull	 NOTIFICATION-TYPE
		OBJECTS      { fnSysSerial }
		STATUS       current
		DESCRIPTION  "Trap sent when Instant Message  
		              white/black list table is full"
		::=  {  fnTraps  801  }
--

	fnTrapFlgEventCount	 NOTIFICATION-TYPE
		OBJECTS      { fnSysSerial }
		STATUS       current
		DESCRIPTION  "Trap sent when FortiLog event number
		              exceeds limit"
		::=  {  fnTraps  901  }

END
