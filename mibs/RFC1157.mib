RFC1157  DEFINITIONS ::= BEGIN

--
    IMPORTS
       enterprises, Counter, Gauge, TimeTicks
                    FROM RFC1155-SMI
       OBJECT-TYPE
                    FROM RFC-1212
       TRAP-TYPE
                    FROM RFC-1215;

    siemensRFC1157  OBJECT IDENTIFIER ::= { enterprises 311 }

siemensRFC1157a			OBJECT IDENTIFIER ::= { siemensRFC1157 1 }
siemensRFC1157b			OBJECT IDENTIFIER ::= { siemensRFC1157a 1 }
siemensRFC1157c				OBJECT IDENTIFIER ::= { siemensRFC1157b 3 }
siemensRFC1157d			OBJECT IDENTIFIER ::= { siemensRFC1157c 1 }
siemensRFC1157e				OBJECT IDENTIFIER ::= { siemensRFC1157d 2 }


    rfc1157ColdStart TRAP-TYPE
       ENTERPRISE   siemensRFC1157e
       DESCRIPTION  "Cold start."
	--#TYPE         "Cold start"
	--#SUMMARY      "Station reinitialized."
	--#SEVERITY     INFORMATIONAL
    --#HELP         "Traps.hlp"
    --#HELPTAG      6000
	--#STATE        OPERATIONAL
	::= 0

   rfc1157WarmStart TRAP-TYPE
       ENTERPRISE   siemensRFC1157e
       DESCRIPTION  "Warm start."
	--#TYPE         "Warm start"
	--#SUMMARY      "Station reinitialized."
	--#SEVERITY     INFORMATIONAL
    --#HELP         "Traps.hlp"
    --#HELPTAG      6004
	--#STATE        OPERATIONAL
	::= 0

   rfc1157LinkDown TRAP-TYPE
       ENTERPRISE   siemensRFC1157e
       VARIABLES  	{ifIndex}
       DESCRIPTION  "Link down."
	--#TYPE         "Link down"
	--#SUMMARY      "Communication link failed at the station %d."
    --#ARGUMENTS { 0 }
	--#SEVERITY     CRITICAL
	--#STATE        DEGRADED
	::= 0

   rfc1157LinkUp TRAP-TYPE
       ENTERPRISE   siemensRFC1157e
       VARIABLES  	{ifIndex}
       DESCRIPTION  "Link up."
	--#TYPE         "Link up"
	--#SUMMARY      "Communication link restored at the station %d."
    --#ARGUMENTS { 0 }
	--#SEVERITY     INFORMATIONAL
	--#STATE        OPERATIONAL
	::= 0

   rfc1157AuthenticationFailure TRAP-TYPE
       ENTERPRISE   siemensRFC1157e
       DESCRIPTION  "Authentication failure."
	--#TYPE         "Authentication failure"
	--#SUMMARY      "Unauthorized message received."
	--#SEVERITY     MINOR
	--#STATE        OPERATIONAL
	::= 0

   rfc1157EGPNeighborLost TRAP-TYPE
       ENTERPRISE   siemensRFC1157e
       DESCRIPTION  "EGP neighbor lost."
	--#TYPE         "EGP neighbor lost"
	--#SUMMARY      "Neighboring station down."
	--#SEVERITY     MAJOR
    --#HELP         "Traps.hlp"
    --#HELPTAG      6001
	--#STATE        OPERATIONAL
	::= 0


END
