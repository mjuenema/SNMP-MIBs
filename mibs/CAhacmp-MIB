--  CA, INC.
-- Proprietary and Confidential Information
--  
-- This material contains, and is part of a computer software program
-- which is, proprietary and confidential information owned by COMPUTER
-- ASSOCIATES INTERNATIONAL, INC.  The program, including this material,
-- may not be duplicated, disclosed or reproduced in whole or in part for
-- any purpose without the express written authorization of COMPUTER
-- ASSOCIATES. All authorized reproductions must be marked with this
-- legend.
-- Computer Associates International, Inc    
-- 
-- Copyright (c) 2011
-- All rights reserved
-- 
-- ------------------------------------------------------------------------
-- Mib name: cahacmp-aim
-- ------------------------------------------------------------------------
-- This is the MIB for HACMP Cluster
-- ------------------------------------------------------------------------
-- 

    CAhacmp-MIB DEFINITIONS ::= BEGIN
 
        IMPORTS
            OBJECT-TYPE            
                FROM RFC-1212            
            TRAP-TYPE            
                FROM RFC-1215            
            enterprises            
                FROM RFC1155-SMI            
            DisplayString            
                FROM RFC1213-MIB;
    
    
    
--
-- Node definitions
--
    
-- *****************************************************************************
-- OIDs of hacmp agent start with 1.3.6.1.4.1.546.16.51
-- *****************************************************************************
-- 
        empire OBJECT IDENTIFIER ::= { enterprises 546 }

        
--      1.3.6.1.4.1.546.1
        unix OBJECT IDENTIFIER ::= { empire 1 }

        
--      1.3.6.1.4.1.546.1.1
        sysmgmt OBJECT IDENTIFIER ::= { unix 1 }

        
--      1.3.6.1.4.1.546.1.1.9
        traps OBJECT IDENTIFIER ::= { empire 9 }

        
--        1.3.6.1.4.1.546.16
        applications OBJECT IDENTIFIER ::= { empire 16 }

        
--        1.3.6.1.4.1.546.16.56
        cahacmpaim OBJECT IDENTIFIER ::= { applications 55 }

        
--        1.3.6.1.4.1.546.16.51.1
        hacmpAimGroup OBJECT IDENTIFIER ::= { cahacmpaim 1 }

        
--        1.3.6.1.4.1.546.16.56.1.1
        hacmpAimInstanceCount OBJECT-TYPE
            SYNTAX INTEGER
            ACCESS read-only
            STATUS mandatory
            DESCRIPTION
                "Number of instances in hacmpAimInstanceTable."
            ::= { hacmpAimGroup 1 }

        
--        1.3.6.1.4.1.546.16.56.1.2
        hacmpAimInstanceTable OBJECT-TYPE
            SYNTAX SEQUENCE OF hacmpAimInstanceEntry
            ACCESS not-accessible
            STATUS mandatory
            DESCRIPTION
                "A table containing the hacmp instances."
            ::= { hacmpAimGroup 2 }

        
--        1.3.6.1.4.1.546.16.56.1.2.1
        hacmpAimInstanceEntry OBJECT-TYPE
            SYNTAX hacmpAimInstanceEntry
            ACCESS not-accessible
            STATUS mandatory
            DESCRIPTION
                "The hacmp instances table entry."
            INDEX { hacmpAimInstanceIndex }
            ::= { hacmpAimInstanceTable 1 }

        
        hacmpAimInstanceEntry ::=
            SEQUENCE { 
                hacmpAimInstanceIndex
                    INTEGER,
                hacmpAimInstanceName
                    DisplayString,
                hacmpAimInstanceUserName
                    DisplayString,
                hacmpAimInstancePassword
                    DisplayString,
                hacmpAimInstancePort
                    INTEGER,
                hacmpAimInstanceRowStatus
                    INTEGER,
                hacmpAimInstanceDataStatus
                    INTEGER
             }

--        1.3.6.1.4.1.546.16.51.1.2.1.1
        hacmpAimInstanceIndex OBJECT-TYPE
            SYNTAX INTEGER (1..2147483647)
            ACCESS read-only
            STATUS mandatory
            DESCRIPTION
                " The unique index of the instance."
            ::= { hacmpAimInstanceEntry 1 }

        
--        1.3.6.1.4.1.546.16.51.1.2.1.2
        hacmpAimInstanceName OBJECT-TYPE
            SYNTAX DisplayString
            ACCESS read-write
            STATUS mandatory
            DESCRIPTION
                "Name of the instance"
            ::= { hacmpAimInstanceEntry 2 }

        
--        1.3.6.1.4.1.546.16.51.1.2.1.3
        hacmpAimInstanceUserName OBJECT-TYPE
            SYNTAX DisplayString
            ACCESS read-write
            STATUS mandatory
            DESCRIPTION
                "User name for connecting to the instance."
            ::= { hacmpAimInstanceEntry 3 }

        
--        1.3.6.1.4.1.546.16.51.1.2.1.4
        hacmpAimInstancePassword OBJECT-TYPE
            SYNTAX DisplayString
            ACCESS read-write
            STATUS mandatory
            DESCRIPTION
                "Password for the user name provided to connect to the instance."
            ::= { hacmpAimInstanceEntry 4 }

        
--        1.3.6.1.4.1.546.16.51.1.2.1.4
        hacmpAimInstancePort OBJECT-TYPE
            SYNTAX INTEGER
            ACCESS read-write
            STATUS mandatory
            DESCRIPTION
                "Port used for connection to the cluster."
            ::= { hacmpAimInstanceEntry 5 }

        
--        1.3.6.1.4.1.546.16.51.1.2.1.5
        hacmpAimInstanceRowStatus OBJECT-TYPE
            SYNTAX INTEGER
                {
                active(1),
                notInService(2),
                notReady(3),
                createAndGo(4),
                createAndWait(5),
                destroy(6)
                }
            ACCESS read-write
            STATUS mandatory
            DESCRIPTION
                "The status of this monitor entry according to the Textual Conventions for SNMPv2 (see RFC 1443).
                active(1) - the row is available for usage
                notInService(2) - setting to this value disables usage of the row
                notReady(3) - an error occurred during usage of the row
                createAndGo(4) - setting to this value creates the row with row status set to active(1)
                createAndWait(5) - setting to this value creates the row with row status set to notInService(2)
                destroy(6) - setting to this value deletes the row"
            DEFVAL { 5 }
            ::= { hacmpAimInstanceEntry 6 }

        
--        1.3.6.1.4.1.546.16.51.1.2.1.6
        hacmpAimInstanceDataStatus OBJECT-TYPE
            SYNTAX INTEGER
                {
                ready(1),
                notReady(2),
                hostUnreachable(3),
                hostIsSlave(4),
                authenticationFailed(5),
                unknownError(6)
                }
            ACCESS read-only
            STATUS mandatory
            DESCRIPTION
                "The status of data of the  hacmp Instance (Server), i.e. status of Aim caches for the instance.
                ready(1) - data are ready in Aim cache, caches were populated
                notReady(2)  - data are Not ready, caches were not populated yet
                hostUnreachable(3) - hacmp host unreachable, data are kept in Aim caches
                hostIsSlave(4) -  hacmp host is a slave server, data are kept in Aim caches
                authenticationFailed(5) - authentication failed for host, data are kept in Aim caches
                unknownError(6) - unknow error, data are kept in Aim caches"
            ::= { hacmpAimInstanceEntry 7 }

        
        hacmpAimInstanceUnusedIndex OBJECT-TYPE
            SYNTAX INTEGER
            ACCESS read-only
            STATUS mandatory
            DESCRIPTION
                "An SNMP GET of this attribute returns an unused Instance UID. This
                is normally used to expedite safe table row creation."
            ::= { hacmpAimGroup 3 }

        
--        1.3.6.1.4.1.546.16.51.2
        hacmpAimStatGroup OBJECT IDENTIFIER ::= { cahacmpaim 2 }

        
        hacmpAimStatClusterGroup OBJECT IDENTIFIER ::= { hacmpAimStatGroup 1 }

        
        hacmpAimStatClusterCount OBJECT-TYPE
            SYNTAX INTEGER
            ACCESS read-only
            STATUS mandatory
            DESCRIPTION
                "The number of rows in the table."
            ::= { hacmpAimStatClusterGroup 1 }

        
        hacmpAimStatClusterTable OBJECT-TYPE
            SYNTAX SEQUENCE OF HacmpAimStatClusterEntry
            ACCESS not-accessible
            STATUS mandatory
            DESCRIPTION
                "The table of monitored clusters."
            ::= { hacmpAimStatClusterGroup 2 }

        
        hacmpAimStatClusterEntry OBJECT-TYPE
            SYNTAX HacmpAimStatClusterEntry
            ACCESS not-accessible
            STATUS mandatory
            INDEX { hacmpAimStatClusterIndex }
            ::= { hacmpAimStatClusterTable 1 }

        
        HacmpAimStatClusterEntry ::=
            SEQUENCE { 
                hacmpAimStatClusterIndex
                    INTEGER,
                hacmpAimStatClusterInstanceName
                    DisplayString,
                hacmpAimStatClusterName
                    DisplayString,
                hacmpAimStatClusterState
                    INTEGER,
                hacmpAimStatClusterSubState
                    INTEGER,
                hacmpAimStatNumNodes
                    INTEGER,
                hacmpAimStatNodeID
                    INTEGER
             }

        hacmpAimStatClusterIndex OBJECT-TYPE
            SYNTAX INTEGER (1..2147483647)
            ACCESS read-only
            STATUS mandatory
            DESCRIPTION
                "The index of this table row"
            ::= { hacmpAimStatClusterEntry 1 }

        
        hacmpAimStatClusterInstanceName OBJECT-TYPE
            SYNTAX DisplayString
            ACCESS read-only
            STATUS mandatory
            DESCRIPTION
                "The instance this table row belongs to."
            ::= { hacmpAimStatClusterEntry 2 }

        
        hacmpAimStatClusterName OBJECT-TYPE
            SYNTAX DisplayString
            ACCESS read-only
            STATUS mandatory
            DESCRIPTION
                "Specifies the name of the cluster."
            ::= { hacmpAimStatClusterEntry 3 }

        
        hacmpAimStatClusterState OBJECT-TYPE
            SYNTAX INTEGER
                {
                up(2),
                down(4),
                unknown(8),
                notconfigured(256)
                }
            ACCESS read-only
            STATUS mandatory
            DESCRIPTION
                "The state of the cluster"
            ::= { hacmpAimStatClusterEntry 4 }

        
        hacmpAimStatClusterSubState OBJECT-TYPE
            SYNTAX INTEGER
                {
                unknown(8),
                unstable(16),
                stable(32),
                error(64),
                reconfig(128),
                notconfigured(256),
                notsynced(512)
                }
            ACCESS read-only
            STATUS mandatory
            DESCRIPTION
                "The substate of the cluster"
            ::= { hacmpAimStatClusterEntry 5 }

        
        hacmpAimStatNumNodes OBJECT-TYPE
            SYNTAX INTEGER
            ACCESS read-only
            STATUS mandatory
            DESCRIPTION
                "The number of local nodes"
            ::= { hacmpAimStatClusterEntry 6 }

        
        hacmpAimStatNodeID OBJECT-TYPE
            SYNTAX INTEGER
            ACCESS read-only
            STATUS mandatory
            DESCRIPTION
                "The ID of the local node"
            ::= { hacmpAimStatClusterEntry 7 }

        
        hacmpAimStatNodeGroup OBJECT IDENTIFIER ::= { hacmpAimStatGroup 2 }

        
        hacmpAimStatNodeCount OBJECT-TYPE
            SYNTAX INTEGER
            ACCESS read-only
            STATUS mandatory
            DESCRIPTION
                "The number of rows in the table."
            ::= { hacmpAimStatNodeGroup 1 }

        
        hacmpAimStatNodeTable OBJECT-TYPE
            SYNTAX SEQUENCE OF HacmpAimStatNodeEntry
            ACCESS not-accessible
            STATUS mandatory
            DESCRIPTION
                "The table of monitored nodes."
            ::= { hacmpAimStatNodeGroup 2 }

        
        hacmpAimStatNodeEntry OBJECT-TYPE
            SYNTAX HacmpAimStatNodeEntry
            ACCESS not-accessible
            STATUS mandatory
            INDEX { hacmpAimStatNodeIndex }
            ::= { hacmpAimStatNodeTable 1 }

        
        HacmpAimStatNodeEntry ::=
            SEQUENCE { 
                hacmpAimStatNodeIndex
                    INTEGER,
                hacmpAimStatNodeInstanceName
                    DisplayString,
                hacmpAimStatNodeClusterIndex
                    INTEGER,
                hacmpAimStatNodeName
                    DisplayString,
                hacmpAimStatNodeState
                    INTEGER,
                hacmpAimStatNodeNumIf
                    INTEGER,
                hacmpAimStatNodeTotalMemory
                    INTEGER,
                hacmpAimStatNodeUsedMemory
                    INTEGER,
                hacmpAimStatNodeMemoryUsage
                    INTEGER,
                hacmpAimStatNodeCPUUsage
                    INTEGER
             }

        hacmpAimStatNodeIndex OBJECT-TYPE
            SYNTAX INTEGER (1..2147483647)
            ACCESS read-only
            STATUS mandatory
            ::= { hacmpAimStatNodeEntry 1 }

        
        hacmpAimStatNodeInstanceName OBJECT-TYPE
            SYNTAX DisplayString
            ACCESS read-only
            STATUS mandatory
            DESCRIPTION
                "The instance this table row belongs to."
            ::= { hacmpAimStatNodeEntry 2 }

        
        hacmpAimStatNodeClusterIndex OBJECT-TYPE
            SYNTAX INTEGER
            ACCESS read-only
            STATUS mandatory
            DESCRIPTION
                "The index of the cluster this table row belongs to."
            ::= { hacmpAimStatNodeEntry 3 }

        
        hacmpAimStatNodeName OBJECT-TYPE
            SYNTAX DisplayString
            ACCESS read-only
            STATUS mandatory
            DESCRIPTION
                "Defines the label by which the node is known."
            ::= { hacmpAimStatNodeEntry 4 }

        
        hacmpAimStatNodeState OBJECT-TYPE
            SYNTAX INTEGER
                {
                up(2),
                down(4),
                unknown(8),
                joining(32),
                leaving(64)
                }
            ACCESS read-only
            STATUS mandatory
            DESCRIPTION
                "The state of the node."
            ::= { hacmpAimStatNodeEntry 5 }

        
        hacmpAimStatNodeNumIf OBJECT-TYPE
            SYNTAX INTEGER
            ACCESS read-only
            STATUS mandatory
            DESCRIPTION
                "Number of network interfaces for this node."
            ::= { hacmpAimStatNodeEntry 6 }

        
        hacmpAimStatNodeTotalMemory OBJECT-TYPE
            SYNTAX INTEGER
            ACCESS read-only
            STATUS mandatory
            DESCRIPTION
                "Total memory of this node in kBytes."
            ::= { hacmpAimStatNodeEntry 7 }

        
        hacmpAimStatNodeUsedMemory OBJECT-TYPE
            SYNTAX INTEGER
            ACCESS read-only
            STATUS mandatory
            DESCRIPTION
                "Used memory of this node in kBytes."
            ::= { hacmpAimStatNodeEntry 8 }

        
        hacmpAimStatNodeMemoryUsage OBJECT-TYPE
            SYNTAX INTEGER
            ACCESS read-only
            STATUS mandatory
            DESCRIPTION
                "Memory usage of this node in %."
            ::= { hacmpAimStatNodeEntry 9 }

        
        hacmpAimStatNodeCPUUsage OBJECT-TYPE
            SYNTAX INTEGER
            ACCESS read-only
            STATUS mandatory
            DESCRIPTION
                "CPU usage of this node in %."
            ::= { hacmpAimStatNodeEntry 10 }

        
        hacmpAimStatResourceGroupGroup OBJECT IDENTIFIER ::= { hacmpAimStatGroup 3 }

        
        hacmpAimStatResourceGroupCount OBJECT-TYPE
            SYNTAX INTEGER
            ACCESS read-only
            STATUS mandatory
            DESCRIPTION
                "The number of rows in the table.
                "
            ::= { hacmpAimStatResourceGroupGroup 1 }

        
        hacmpAimStatResourceGroupTable OBJECT-TYPE
            SYNTAX SEQUENCE OF HacmpAimStatResourceGroupEntry
            ACCESS not-accessible
            STATUS mandatory
            DESCRIPTION
                "The table of monitored resource groups"
            ::= { hacmpAimStatResourceGroupGroup 2 }

        
        hacmpAimStatResourceGroupEntry OBJECT-TYPE
            SYNTAX HacmpAimStatResourceGroupEntry
            ACCESS not-accessible
            STATUS mandatory
            INDEX { hacmpAimStatResourceGroupIndex }
            ::= { hacmpAimStatResourceGroupTable 1 }

        
        HacmpAimStatResourceGroupEntry ::=
            SEQUENCE { 
                hacmpAimStatResourceGroupIndex
                    INTEGER,
                hacmpAimStatResourceGroupInstanceName
                    DisplayString,
                hacmpAimStatResourceGroupClusterIndex
                    INTEGER,
                hacmpAimStatResourceGroupNodeIndex
                    INTEGER,
                hacmpAimStatResourceGroupNodeName
                    DisplayString,
                hacmpAimStatResourceGroupName
                    DisplayString,
                hacmpAimStatResourceGroupState
                    INTEGER,
                hacmpAimStatResourceGroupNumResources
                    INTEGER,
                hacmpAimStatResourceGroupNumNodes
                    INTEGER,
                hacmpAimStatResourceGroupStartupPolicy
                    INTEGER,
                hacmpAimStatResourceGroupFalloverPolicy
                    INTEGER,
                hacmpAimStatResourceGroupFallbackPolicy
                    INTEGER,
                hacmpAimStatResourceGroupPrevNodeName
                    DisplayString
             }

        hacmpAimStatResourceGroupIndex OBJECT-TYPE
            SYNTAX INTEGER (1..2147483647)
            ACCESS read-only
            STATUS mandatory
            DESCRIPTION
                "The numeric index of this row.
                "
            ::= { hacmpAimStatResourceGroupEntry 1 }

        
        hacmpAimStatResourceGroupInstanceName OBJECT-TYPE
            SYNTAX DisplayString
            ACCESS read-only
            STATUS mandatory
            DESCRIPTION
                "The instance this table row belongs to."
            ::= { hacmpAimStatResourceGroupEntry 2 }

        
        hacmpAimStatResourceGroupClusterIndex OBJECT-TYPE
            SYNTAX INTEGER
            ACCESS read-only
            STATUS mandatory
            DESCRIPTION
                "The index of the cluster this table row belongs to."
            ::= { hacmpAimStatResourceGroupEntry 3 }

        
        hacmpAimStatResourceGroupNodeIndex OBJECT-TYPE
            SYNTAX INTEGER
            ACCESS read-only
            STATUS mandatory
            DESCRIPTION
                "The index of the node this table row belongs to."
            ::= { hacmpAimStatResourceGroupEntry 4 }

        
        hacmpAimStatResourceGroupNodeName OBJECT-TYPE
            SYNTAX DisplayString
            ACCESS read-only
            STATUS mandatory
            DESCRIPTION
                "The name of the node currently owning this resource group."
            ::= { hacmpAimStatResourceGroupEntry 5 }

        
        hacmpAimStatResourceGroupName OBJECT-TYPE
            SYNTAX DisplayString
            ACCESS read-only
            STATUS mandatory
            DESCRIPTION
                "The name of the resource group."
            ::= { hacmpAimStatResourceGroupEntry 6 }

        
        hacmpAimStatResourceGroupState OBJECT-TYPE
            SYNTAX INTEGER
                {
                online(2),
                offline(4),
                unknown(8),
                acquiring(16),
                releasing(32),
                error(64),
                onlineSec(256),
                acquiringSec(1024),
                releasingSec(4096),
                errorSec(16384),
                offlineDueToFallover(65536),
                offlineDueToParentOff(131072),
                unmanagedSec(149576),
                offlineDueToLackOfNode(262144),
                unmanaged(524288)
                }
            ACCESS read-only
            STATUS mandatory
            DESCRIPTION
                "The state of the resource group.
                "
            ::= { hacmpAimStatResourceGroupEntry 7 }

        
        hacmpAimStatResourceGroupNumResources OBJECT-TYPE
            SYNTAX INTEGER (0..1)
            ACCESS read-only
            STATUS mandatory
            DESCRIPTION
                " The number of resources defined in the group"
            ::= { hacmpAimStatResourceGroupEntry 8 }

        
        hacmpAimStatResourceGroupNumNodes OBJECT-TYPE
            SYNTAX INTEGER
            ACCESS read-only
            STATUS mandatory
            DESCRIPTION
                "The number of participating nodes in the group"
            ::= { hacmpAimStatResourceGroupEntry 9 }

        
        hacmpAimStatResourceGroupStartupPolicy OBJECT-TYPE
            SYNTAX INTEGER
                {
                homeNodeOnly(1),
                firstAvailNode(2),
                usingDistPolicy(3),
                allAvailNodes(4)
                }
            ACCESS read-only
            STATUS mandatory
            DESCRIPTION
                "The Resource Group's Startup Policy:
                
                This can have the following values:
                Online On HomeNode Only  1
                Online On First Available Node  2
                Online Using Distribution Policy  3
                Online On All Available Nodes  4"
            ::= { hacmpAimStatResourceGroupEntry 10 }

        
        hacmpAimStatResourceGroupFalloverPolicy OBJECT-TYPE
            SYNTAX INTEGER
                {
                toNextPrioNode(5),
                usingDNP(6),
                bringOffline(7)
                }
            ACCESS read-only
            STATUS mandatory
            DESCRIPTION
                "The Resource Group's Fallover Policy
                This can have the following values:
                
                Fallover To Next Priority Node On the List  5
                Fallover Using DNP 6
                Bring Offline  7"
            ::= { hacmpAimStatResourceGroupEntry 11 }

        
        hacmpAimStatResourceGroupFallbackPolicy OBJECT-TYPE
            SYNTAX INTEGER
                {
                toHigherPrioNode(8),
                neverFallback(9)
                }
            ACCESS read-only
            STATUS mandatory
            DESCRIPTION
                "The Resource Group's Fallback Policy
                
                Fallback to Higher Priority Node in the List  8
                Never Fallback  9"
            ::= { hacmpAimStatResourceGroupEntry 12 }

        
        hacmpAimStatResourceGroupPrevNodeName OBJECT-TYPE
            SYNTAX DisplayString
            ACCESS read-only
            STATUS mandatory
            DESCRIPTION
                "The name of the node previously owning this resource group (used for traps)"
            ::= { hacmpAimStatResourceGroupEntry 13 }

        
        hacmpAimStatResourceGroup OBJECT IDENTIFIER ::= { hacmpAimStatGroup 4 }

        
        hacmpAimStatResourceCount OBJECT-TYPE
            SYNTAX INTEGER
            ACCESS read-only
            STATUS mandatory
            DESCRIPTION
                "The number of rows in the table.
                "
            ::= { hacmpAimStatResourceGroup 1 }

        
        hacmpAimStatResourceTable OBJECT-TYPE
            SYNTAX SEQUENCE OF HacmpAimStatResourceEntry
            ACCESS not-accessible
            STATUS mandatory
            DESCRIPTION
                "The table of monitored resources."
            ::= { hacmpAimStatResourceGroup 2 }

        
        hacmpAimStatResourceEntry OBJECT-TYPE
            SYNTAX HacmpAimStatResourceEntry
            ACCESS not-accessible
            STATUS mandatory
            INDEX { hacmpAimStatResourceIndex }
            ::= { hacmpAimStatResourceTable 1 }

        
        HacmpAimStatResourceEntry ::=
            SEQUENCE { 
                hacmpAimStatResourceIndex
                    INTEGER,
                hacmpAimStatResourceInstanceName
                    DisplayString,
                hacmpAimStatResourceClusterIndex
                    INTEGER,
                hacmpAimStatResourceResourceGroupIndex
                    INTEGER,
                hacmpAimStatResourceName
                    DisplayString,
                hacmpAimStatResourceType
                    INTEGER
             }

        hacmpAimStatResourceIndex OBJECT-TYPE
            SYNTAX INTEGER (1..2147483647)
            ACCESS read-only
            STATUS mandatory
            DESCRIPTION
                "The numeric index of this row.
                "
            ::= { hacmpAimStatResourceEntry 1 }

        
        hacmpAimStatResourceInstanceName OBJECT-TYPE
            SYNTAX DisplayString
            ACCESS read-only
            STATUS mandatory
            DESCRIPTION
                "The instance this table row belongs to."
            ::= { hacmpAimStatResourceEntry 2 }

        
        hacmpAimStatResourceClusterIndex OBJECT-TYPE
            SYNTAX INTEGER
            ACCESS read-only
            STATUS mandatory
            DESCRIPTION
                "The index of the cluster this table row belongs to."
            ::= { hacmpAimStatResourceEntry 3 }

        
        hacmpAimStatResourceResourceGroupIndex OBJECT-TYPE
            SYNTAX INTEGER
            ACCESS read-only
            STATUS mandatory
            DESCRIPTION
                "The index of the Resource Group this table row belongs to.
                "
            ::= { hacmpAimStatResourceEntry 4 }

        
        hacmpAimStatResourceName OBJECT-TYPE
            SYNTAX DisplayString
            ACCESS read-only
            STATUS mandatory
            DESCRIPTION
                "The name of the resource.
                "
            ::= { hacmpAimStatResourceEntry 5 }

        
        hacmpAimStatResourceType OBJECT-TYPE
            SYNTAX INTEGER
                {
                serviceLabel(1000),
                htyServiceLabel(1001),
                fileSystem(1002),
                volumeGroup(1003),
                disk(1004),
                aixConnectionServices(1005),
                application(1006),
                concurrentVolumeGroup(1007),
                haCommunicationLinks(1008),
                haFastConnectServices(1009)
                }
            ACCESS read-only
            STATUS mandatory
            DESCRIPTION
                "Index of the type of the resource.
                
                serviceLabel (1000)
                htyServiceLabel (1001)
                fileSystem (1002)
                volumeGroup (1003)
                disk (1004)
                aixConnectionServices (1005)
                application (1006)
                concurrentVolumeGroup (1007)
                haCommunicationLinks (1008)
                haFastConnectServices (1009)
                "
            ::= { hacmpAimStatResourceEntry 6 }

        
        hacmpAimStatNetworkGroup OBJECT IDENTIFIER ::= { hacmpAimStatGroup 5 }

        
        hacmpAimStatNetworkCount OBJECT-TYPE
            SYNTAX INTEGER
            ACCESS read-only
            STATUS mandatory
            DESCRIPTION
                "The number of rows in the table.
                "
            ::= { hacmpAimStatNetworkGroup 1 }

        
        hacmpAimStatNetworkTable OBJECT-TYPE
            SYNTAX SEQUENCE OF HacmpAimStatNetworkEntry
            ACCESS not-accessible
            STATUS mandatory
            ::= { hacmpAimStatNetworkGroup 2 }
-- The table of monitored networks.
        
        hacmpAimStatNetworkEntry OBJECT-TYPE
            SYNTAX HacmpAimStatNetworkEntry
            ACCESS not-accessible
            STATUS mandatory
            INDEX { hacmpAimStatNetworkIndex }
            ::= { hacmpAimStatNetworkTable 1 }

        
        HacmpAimStatNetworkEntry ::=
            SEQUENCE { 
                hacmpAimStatNetworkIndex
                    INTEGER,
                hacmpAimStatNetworkInstanceName
                    DisplayString,
                hacmpAimStatNetworkClusterIndex
                    INTEGER,
                hacmpAimStatNetworkNodeIndex
                    INTEGER,
                hacmpAimStatNetworkName
                    DisplayString,
                hacmpAimStatNetworkAttribute
                    INTEGER,
                hacmpAimStatNetworkState
                    INTEGER
             }

        hacmpAimStatNetworkIndex OBJECT-TYPE
            SYNTAX INTEGER (1..2147483647)
            ACCESS read-only
            STATUS mandatory
            DESCRIPTION
                "The numeric index of this row.
                "
            ::= { hacmpAimStatNetworkEntry 1 }

        
        hacmpAimStatNetworkInstanceName OBJECT-TYPE
            SYNTAX DisplayString
            ACCESS read-only
            STATUS mandatory
            DESCRIPTION
                "The instance this table row belongs to."
            ::= { hacmpAimStatNetworkEntry 2 }

        
        hacmpAimStatNetworkClusterIndex OBJECT-TYPE
            SYNTAX INTEGER
            ACCESS read-only
            STATUS mandatory
            DESCRIPTION
                "The index of the cluster this table row belongs to.
                "
            ::= { hacmpAimStatNetworkEntry 3 }

        
        hacmpAimStatNetworkNodeIndex OBJECT-TYPE
            SYNTAX INTEGER
            ACCESS read-only
            STATUS mandatory
            DESCRIPTION
                "The index of the node this table row belongs to.
                "
            ::= { hacmpAimStatNetworkEntry 4 }

        
        hacmpAimStatNetworkName OBJECT-TYPE
            SYNTAX DisplayString
            ACCESS read-only
            STATUS mandatory
            DESCRIPTION
                "The name of the network.
                "
            ::= { hacmpAimStatNetworkEntry 5 }

        
        hacmpAimStatNetworkAttribute OBJECT-TYPE
            SYNTAX INTEGER
                {
                private(1),
                public(2),
                serial(4)
                }
            ACCESS read-only
            STATUS mandatory
            DESCRIPTION
                "The attribute of the network. 
                Possible values:
                private(1)
                public(2)
                serial(4)
                "
            ::= { hacmpAimStatNetworkEntry 6 }
-- The attribute of the network
        
        hacmpAimStatNetworkState OBJECT-TYPE
            SYNTAX INTEGER
                {
                Unknown(-1),
                Unavailable(0),
                Down(1),
                Partitioned(2),
                Up(3)
                }
            ACCESS read-only
            STATUS mandatory
            DESCRIPTION
                "The current state of the network. 
                Possible values:
                StateUnknown (-1)
                StateUnavailable (0)
                Down (1)
                Partitioned (2)
                Up (3)
                "
            ::= { hacmpAimStatNetworkEntry 7 }

        
        hacmpAimStatNetworkInterfaceGroup OBJECT IDENTIFIER ::= { hacmpAimStatGroup 6 }

        
        hacmpAimStatNetworkInterfaceCount OBJECT-TYPE
            SYNTAX INTEGER
            ACCESS read-only
            STATUS mandatory
            DESCRIPTION
                "The number of rows in the table.
                "
            ::= { hacmpAimStatNetworkInterfaceGroup 1 }

        
        hacmpAimStatNetworkInterfaceTable OBJECT-TYPE
            SYNTAX SEQUENCE OF HacmpAimStatNetworkInterfaceEntry
            ACCESS not-accessible
            STATUS mandatory
            ::= { hacmpAimStatNetworkInterfaceGroup 2 }
-- The table of monitored network interfaces.
        
        hacmpAimStatNetworkInterfaceEntry OBJECT-TYPE
            SYNTAX HacmpAimStatNetworkInterfaceEntry
            ACCESS not-accessible
            STATUS mandatory
            INDEX { hacmpAimStatNetworkInterfaceIndex }
            ::= { hacmpAimStatNetworkInterfaceTable 1 }

        
        HacmpAimStatNetworkInterfaceEntry ::=
            SEQUENCE { 
                hacmpAimStatNetworkInterfaceIndex
                    INTEGER,
                hacmpAimStatNetworkInterfaceInstanceName
                    DisplayString,
                hacmpAimStatNetworkInterfaceClusterIndex
                    INTEGER,
                hacmpAimStatNetworkInterfaceNetworkIndex
                    INTEGER,
                hacmpAimStatNetworkInterfaceNodeIndex
                    INTEGER,
                hacmpAimStatNetworkInterfaceName
                    DisplayString,
                hacmpAimStatNetworkInterfaceAddress
                    DisplayString,
                hacmpAimStatNetworkInterfaceState
                    INTEGER,
                hacmpAimStatNetworkInterfaceRole
                    INTEGER
             }

        hacmpAimStatNetworkInterfaceIndex OBJECT-TYPE
            SYNTAX INTEGER (1..2147483647)
            ACCESS read-only
            STATUS mandatory
            DESCRIPTION
                "The numeric index of this row.
                "
            ::= { hacmpAimStatNetworkInterfaceEntry 1 }

        
        hacmpAimStatNetworkInterfaceInstanceName OBJECT-TYPE
            SYNTAX DisplayString
            ACCESS read-only
            STATUS mandatory
            DESCRIPTION
                "The instance this table row belongs to."
            ::= { hacmpAimStatNetworkInterfaceEntry 2 }

        
        hacmpAimStatNetworkInterfaceClusterIndex OBJECT-TYPE
            SYNTAX INTEGER
            ACCESS read-only
            STATUS mandatory
            DESCRIPTION
                "The index of the cluster this table row belongs to.
                "
            ::= { hacmpAimStatNetworkInterfaceEntry 3 }

        
        hacmpAimStatNetworkInterfaceNetworkIndex OBJECT-TYPE
            SYNTAX INTEGER
            ACCESS read-only
            STATUS mandatory
            DESCRIPTION
                "The index of the network this table row belongs to.
                "
            ::= { hacmpAimStatNetworkInterfaceEntry 4 }

        
        hacmpAimStatNetworkInterfaceNodeIndex OBJECT-TYPE
            SYNTAX INTEGER
            ACCESS read-only
            STATUS mandatory
            DESCRIPTION
                "The index of the node in which the network interface is installed.
                
                
                "
            ::= { hacmpAimStatNetworkInterfaceEntry 5 }

        
        hacmpAimStatNetworkInterfaceName OBJECT-TYPE
            SYNTAX DisplayString
            ACCESS read-only
            STATUS mandatory
            DESCRIPTION
                "The name of this network interface."
            ::= { hacmpAimStatNetworkInterfaceEntry 6 }

        
        hacmpAimStatNetworkInterfaceAddress OBJECT-TYPE
            SYNTAX DisplayString
            ACCESS read-only
            STATUS mandatory
            DESCRIPTION
                "The primary network address that the node uses for the network interface.
                "
            ::= { hacmpAimStatNetworkInterfaceEntry 7 }

        
        hacmpAimStatNetworkInterfaceState OBJECT-TYPE
            SYNTAX INTEGER
                {
                up(2),
                down(4),
                unknown(8)
                }
            ACCESS read-only
            STATUS mandatory
            DESCRIPTION
                "The state of the interface
                
                up(2),
                down(4),
                unknown(8)
                "
            ::= { hacmpAimStatNetworkInterfaceEntry 8 }

        
        hacmpAimStatNetworkInterfaceRole OBJECT-TYPE
            SYNTAX INTEGER
                {
                persistent(8),
                service(16),
                standby(32),
                boot(64),
                sharedService(128)
                }
            ACCESS read-only
            STATUS mandatory
            DESCRIPTION
                "The role of the interface
                
                persistent(8),
                service(16),
                standby(32),
                boot(64),
                sharedService(128)
                "
            ::= { hacmpAimStatNetworkInterfaceEntry 9 }

        
        hacmpAimStatServiceGroup OBJECT IDENTIFIER ::= { hacmpAimStatGroup 7 }

        
        hacmpAimStatServiceCount OBJECT-TYPE
            SYNTAX INTEGER
            ACCESS read-only
            STATUS mandatory
            DESCRIPTION
                "The number of rows in the table.
                "
            ::= { hacmpAimStatServiceGroup 1 }

        
        hacmpAimStatServiceTable OBJECT-TYPE
            SYNTAX SEQUENCE OF HacmpAimStatServiceEntry
            ACCESS not-accessible
            STATUS mandatory
            DESCRIPTION
                "The table of monitored cluster services."
            ::= { hacmpAimStatServiceGroup 2 }

        
        hacmpAimStatServiceEntry OBJECT-TYPE
            SYNTAX HacmpAimStatServiceEntry
            ACCESS not-accessible
            STATUS mandatory
            INDEX { hacmpAimStatServiceIndex }
            ::= { hacmpAimStatServiceTable 1 }

        
        HacmpAimStatServiceEntry ::=
            SEQUENCE { 
                hacmpAimStatServiceIndex
                    INTEGER,
                hacmpAimStatServiceInstanceName
                    DisplayString,
                hacmpAimStatServiceClusterIndex
                    INTEGER,
                hacmpAimStatServiceNodeIndex
                    INTEGER,
                hacmpAimStatServiceName
                    DisplayString,
                hacmpAimStatServicePID
                    INTEGER,
                hacmpAimStatServiceState
                    INTEGER
             }

        hacmpAimStatServiceIndex OBJECT-TYPE
            SYNTAX INTEGER (1..2147483647)
            ACCESS read-only
            STATUS mandatory
            DESCRIPTION
                "The numeric index of this row.
                "
            ::= { hacmpAimStatServiceEntry 1 }

        
        hacmpAimStatServiceInstanceName OBJECT-TYPE
            SYNTAX DisplayString
            ACCESS read-only
            STATUS mandatory
            DESCRIPTION
                "The instance this table row belongs to."
            ::= { hacmpAimStatServiceEntry 2 }

        
        hacmpAimStatServiceClusterIndex OBJECT-TYPE
            SYNTAX INTEGER
            ACCESS read-only
            STATUS mandatory
            DESCRIPTION
                "The index of the cluster this table row belongs to.
                "
            ::= { hacmpAimStatServiceEntry 3 }

        
        hacmpAimStatServiceNodeIndex OBJECT-TYPE
            SYNTAX INTEGER
            ACCESS read-only
            STATUS mandatory
            DESCRIPTION
                "The index of the node this services belongs to.
                
                
                "
            ::= { hacmpAimStatServiceEntry 4 }

        
        hacmpAimStatServiceName OBJECT-TYPE
            SYNTAX DisplayString
            ACCESS read-only
            STATUS mandatory
            DESCRIPTION
                "The name of the cluster service."
            ::= { hacmpAimStatServiceEntry 5 }

        
        hacmpAimStatServicePID OBJECT-TYPE
            SYNTAX INTEGER
            ACCESS read-only
            STATUS mandatory
            DESCRIPTION
                "The PID of the cluster service."
            ::= { hacmpAimStatServiceEntry 6 }

        
        hacmpAimStatServiceState OBJECT-TYPE
            SYNTAX INTEGER
                {
                running(2),
                stopped(4)
                }
            ACCESS read-only
            STATUS mandatory
            DESCRIPTION
                "The status of the cluster service.
                
                running(2)
                stopped(4)
                "
            ::= { hacmpAimStatServiceEntry 7 }

        
--        1.3.6.1.4.1.546.16.56.3
        hacmpAimConfigGroup OBJECT IDENTIFIER ::= { cahacmpaim 3 }

        
--     *****************************************************************************
-- Configuration Groups
-- *****************************************************************************
-- 1.3.6.1.4.1.546.16.51.3.1
        hacmpAimCfgGeneralGroup OBJECT IDENTIFIER ::= { hacmpAimConfigGroup 1 }

        
--        1.3.6.1.4.1.546.16.51.3.1.1
        hacmpAimCfgname OBJECT-TYPE
            SYNTAX DisplayString
            ACCESS read-only
            STATUS mandatory
            DESCRIPTION
                "The agent's name."
            ::= { hacmpAimCfgGeneralGroup 1 }

        
--        1.3.6.1.4.1.546.16.51.3.1.2
        hacmpAimCfgversion OBJECT-TYPE
            SYNTAX DisplayString
            ACCESS read-only
            STATUS mandatory
            DESCRIPTION
                "Version of the agent."
            ::= { hacmpAimCfgGeneralGroup 2 }

        
--        1.3.6.1.4.1.546.16.51.3.1.3
        hacmpAimCfgstarttime OBJECT-TYPE
            SYNTAX DisplayString
            ACCESS read-only
            STATUS mandatory
            DESCRIPTION
                "Time the agent was started."
            ::= { hacmpAimCfgGeneralGroup 3 }

        
--        1.3.6.1.4.1.546.16.51.3.1.4
        hacmpAimCfglastupdatetime OBJECT-TYPE
            SYNTAX DisplayString
            ACCESS read-only
            STATUS mandatory
            DESCRIPTION
                "Time the MIB was last updated."
            ::= { hacmpAimCfgGeneralGroup 4 }

        
--        1.3.6.1.4.1.546.16.51.3.1.5
        hacmpAimCfgagentpollinterval OBJECT-TYPE
            SYNTAX INTEGER
            ACCESS read-write
            STATUS mandatory
            DESCRIPTION
                "Poll Interval for the agent."
            DEFVAL { 120 }
            ::= { hacmpAimCfgGeneralGroup 5 }

        
    
--
-- Trap definitions
--
    
--  Trap definitions
-- 
        hacmpAimInstanceAddedTrap TRAP-TYPE 
            ENTERPRISE sysmgmt
            VARIABLES { hacmpAimInstanceIndex, hacmpAimInstanceName, hacmpAimInstanceRowStatus, hacmpAimInstanceDataStatus }
            DESCRIPTION 
                "This trap is sent when a new Instance/Server is added.
                
                Parameters:
                hacmpAimInstanceIndex
                hacmpAimInstanceName
                hacmpAimInstanceRowStatus
                hacmpAimInstanceDataStatus"
            ::=  165800

        hacmpAimInstanceRemovedTrap TRAP-TYPE 
            ENTERPRISE sysmgmt
            VARIABLES { hacmpAimInstanceIndex, hacmpAimInstanceName, hacmpAimInstanceRowStatus, hacmpAimInstanceDataStatus }
            DESCRIPTION 
                "This trap is sent when an Instance/Server is removed.
                
                Parameters:
                hacmpAimInstanceIndex
                hacmpAimInstanceName
                hacmpAimInstanceRowStatus
                hacmpAimInstanceDataStatus"
            ::=  165801

        hacmpAimInstanceDataStatusChanged TRAP-TYPE 
            ENTERPRISE sysmgmt
            VARIABLES { hacmpAimInstanceIndex, hacmpAimInstanceName, hacmpAimInstanceRowStatus, hacmpAimInstanceDataStatus }
            DESCRIPTION 
                "This trap is sent when Instance/Server Data Status is changed.
                
                Parameters:
                hacmpAimInstanceIndex
                hacmpAimInstanceName
                hacmpAimInstanceRowStatus
                hacmpAimInstanceDataStatus"
            ::=  165802

        hacmpAimNodeAddedTrap TRAP-TYPE 
            ENTERPRISE sysmgmt
            VARIABLES { hacmpAimStatNodeInstanceName, hacmpAimStatNodeClusterIndex, hacmpAimStatNodeName }
            DESCRIPTION 
                "This trap is sent when a node is added
                
                Parameters:
                hacmpAimInstanceName
                hacmpAimStatNodeClusterIndex
                hacmpAimStatNodeName
                "
            ::=  165803

        hacmpAimNodeRemovedTrap TRAP-TYPE 
            ENTERPRISE sysmgmt
            VARIABLES { hacmpAimStatNodeInstanceName, hacmpAimStatNodeClusterIndex, hacmpAimStatNodeName }
            DESCRIPTION 
                "This trap is sent when a node is removed
                
                Parameters:
                hacmpAimInstanceName
                hacmpAimStatNodeClusterIndex
                hacmpAimStatNodeName
                "
            ::=  165804

        hacmpAimResourceGroupAddedTrap TRAP-TYPE 
            ENTERPRISE sysmgmt
            VARIABLES { hacmpAimStatResourceGroupInstanceName, hacmpAimStatResourceGroupClusterIndex, hacmpAimStatResourceGroupName }
            DESCRIPTION 
                "This trap is sent when a resource group is added
                
                Parameters:
                hacmpAimInstanceName
                hacmpAimStatResourceGroupClusterIndex
                hacmpAimStatResourceGroupName
                
                "
            ::=  165805

        hacmpAimResourceGroupRemovedTrap TRAP-TYPE 
            ENTERPRISE sysmgmt
            VARIABLES { hacmpAimStatResourceGroupInstanceName, hacmpAimStatResourceGroupClusterIndex, hacmpAimStatResourceGroupName }
            DESCRIPTION 
                "This trap is sent when a resource group is removed
                
                Parameters:
                hacmpAimInstanceName
                hacmpAimStatResourceGroupClusterIndex
                hacmpAimStatResourceGroupName
                "
            ::=  165806

        hacmpAimResourceGroupMigration TRAP-TYPE 
            ENTERPRISE sysmgmt
            VARIABLES { hacmpAimStatResourceGroupInstanceName, hacmpAimStatResourceGroupClusterIndex, hacmpAimStatResourceGroupName, hacmpAimStatResourceGroupNodeName, hacmpAimStatResourceGroupPrevNodeName
                 }
            DESCRIPTION 
                "This trap is sent when a resource group is migrated.
                
                Parameters:
                
                hacmpAimInstanceName
                hacmpAimStatResourceGroupClusterIndex
                hacmpAimStatResourceGroupName
                hacmpAimStatResourceGroupNodeName
                hacmpAimStatResourceGroupPreviousNodeName
                
                
                
                         
                "
            ::=  165807

        hacmpAimResourceAddedTrap TRAP-TYPE 
            ENTERPRISE sysmgmt
            VARIABLES { hacmpAimStatResourceInstanceName, hacmpAimStatResourceClusterIndex, hacmpAimStatResourceResourceGroupIndex, hacmpAimStatResourceName }
            DESCRIPTION 
                "This trap is sent when a resource is added
                
                Parameters:
                hacmpAimInstanceName
                hacmpAimStatResourceClusterIndex
                hacmpAimStatResourceResourceGroupIndex
                hacmpAimStatResourceName
                "
            ::=  165808

        hacmpAimResourceRemovedTrap TRAP-TYPE 
            ENTERPRISE sysmgmt
            VARIABLES { hacmpAimStatResourceInstanceName, hacmpAimStatResourceClusterIndex, hacmpAimStatResourceResourceGroupIndex, hacmpAimStatResourceName }
            DESCRIPTION 
                "This trap is sent when a resource is removed
                
                Parameters:
                hacmpAimInstanceName
                hacmpAimStatResourceClusterIndex
                hacmpAimStatResourceResourceGroupIndex
                hacmpAimStatResourceName
                "
            ::=  165809

    
        hacmpAimResourceGroupOffline TRAP-TYPE 
            ENTERPRISE sysmgmt
            VARIABLES { hacmpAimStatResourceGroupInstanceName, hacmpAimStatResourceGroupClusterIndex, hacmpAimStatResourceGroupName, hacmpAimStatResourceGroupNodeName
                 }
            DESCRIPTION 
                "This trap is sent when a resource group is brought offline.
                
                Parameters:
                
                hacmpAimInstanceName
                hacmpAimStatResourceGroupClusterIndex
                hacmpAimStatResourceGroupName
                hacmpAimStatResourceGroupNodeName
                "
            ::=  165810

        hacmpAimResourceGroupOnline TRAP-TYPE 
            ENTERPRISE sysmgmt
            VARIABLES { hacmpAimStatResourceGroupInstanceName, hacmpAimStatResourceGroupClusterIndex, hacmpAimStatResourceGroupName, hacmpAimStatResourceGroupNodeName
                 }
            DESCRIPTION 
                "This trap is sent when a resource group is brought online.
                
                Parameters:
                
                hacmpAimInstanceName
                hacmpAimStatResourceGroupClusterIndex
                hacmpAimStatResourceGroupName
                hacmpAimStatResourceGroupNodeName
                "
            ::=  165811

    END

--
