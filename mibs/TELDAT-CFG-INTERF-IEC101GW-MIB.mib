-- Teldat, S.A.

                -- Parque Tecnolgico de Madrid

                -- 28760, Tres Cantos (Madrid)

                -- Tlf: +34-918076565

                -- Fax: +34-918076521

                -- e-mail: id@teldat.com


                -- MIB privada de Teldat

                -- MIB de configuracin del interfaz IEC-101-GW


    -- Historial:
    --      07/02/14    M.A. Pastor     XH 3523. Errors with HP Openview 9.20
    -- 1.2  11-01-13    E. Amorena      XH 2610. MIBs compilation.
    -- 1.1  03/01/13  F. Hernandez     XH 2610. Compilation error
    -- 1.0  15/06/11  Benjamin G.      Implementacin inicial

    --------------------------------------------------------------------------

TELDAT-CFG-INTERF-IEC101GW-MIB DEFINITIONS ::= BEGIN

-- Tipos importados

    IMPORTS
        OBJECT-TYPE
            FROM RFC-1212
        telProdNpConfInterface
            FROM TELDAT-SW-STRUCTURE-MIB;


    telProdNpConfInterfIec101GW OBJECT IDENTIFIER ::= { telProdNpConfInterface 16 }


--  = = = = = = = = = = = = = = = = = = = = = = = = = = = = = = = = = = = = = =
--  Interface IEC-101 GW global configuration variables
--  = = = = = = = = = = = = = = = = = = = = = = = = = = = = = = = = = = = = = =

  -- Grupo telProdNpGW104Global

   telProdNpIec101GWTable OBJECT-TYPE
         SYNTAX  SEQUENCE OF TelProdNpIec101GWEntry
        ACCESS  not-accessible
        STATUS  mandatory
        DESCRIPTION
            "Table of global configuration for IEC101 GW interfaces.
             Each row represents an interface"
    ::= { telProdNpConfInterfIec101GW 1 }

   telProdNpIec101GWEntry OBJECT-TYPE
        SYNTAX  TelProdNpIec101GWEntry
        ACCESS  not-accessible
        STATUS  mandatory
        DESCRIPTION
            "A base list of objects that are configuration information about an
             IEC101 GW interface. The index is the number of the interface."
        INDEX   { telProdNpIec101GWIfcIndex }
        ::={ telProdNpIec101GWTable 1 }

    TelProdNpIec101GWEntry ::=
        SEQUENCE{
            telProdNpIec101GWIfcIndex       INTEGER,
            telProdNpIec101GWIfcAsduCAddr   INTEGER,
            telProdNpIec101GWIfcBaudRate    INTEGER,
            telProdNpIec101GWIfcLinkAddr    INTEGER,
            telProdNpIec101GWIfcLinkAddrSz  INTEGER,
            telProdNpIec101GWIfcLongResp    INTEGER,
            telProdNpIec101GWIfcMultilink   INTEGER,
            telProdNpIec101GWIfcBuffNum     INTEGER,
            telProdNpIec101GWIfcOrigAddr    INTEGER,
            telProdNpIec101GWIfcRetransMax  INTEGER,
            telProdNpIec101GWIfcRetransTime INTEGER,
            telProdNpIec101GWIfcRxTimeout   INTEGER,
            telProdNpIec101GWIfcSyncTime    INTEGER,
            telProdNpIec101GWIfcTestTime    INTEGER,
            telProdNpIec101GWIfcTestType    INTEGER
        }

    telProdNpIec101GWIfcIndex OBJECT-TYPE
        SYNTAX  INTEGER
        ACCESS  read-only
        STATUS  mandatory
        DESCRIPTION
            "IEC101-GW interface index. It is the index table."
        ::={ telProdNpIec101GWEntry 1 }

    telProdNpIec101GWIfcAsduCAddr OBJECT-TYPE
        SYNTAX  INTEGER (1..65534)
        ACCESS  read-write
        STATUS  mandatory
        DESCRIPTION
            "Set RTU ASDU common Adress for no multilink mode."
        ::={ telProdNpIec101GWEntry 2 }

    telProdNpIec101GWIfcBaudRate OBJECT-TYPE
        SYNTAX  INTEGER {
            a(300),
            b(600),
            c(1200),
            d(2400),
            e(4800),
            f(9600),
            g(19200),
            h(28800),
            i(38400),
            j(57600)
            }
        ACCESS  read-write
        STATUS  mandatory
        DESCRIPTION
            "Set baud reate for serial interface."
        ::={ telProdNpIec101GWEntry 3 }

    telProdNpIec101GWIfcLinkAddr OBJECT-TYPE
        SYNTAX  INTEGER (1..65534)
        ACCESS  read-write
        STATUS  mandatory
        DESCRIPTION
            "Set RTU Link Adress for no multilink mode."
        ::={ telProdNpIec101GWEntry 4 }

    telProdNpIec101GWIfcLinkAddrSz OBJECT-TYPE
        SYNTAX  INTEGER (1..2)
        ACCESS  read-write
        STATUS  mandatory
        DESCRIPTION
            "Set Link Adress field size."
        ::={ telProdNpIec101GWEntry 5 }

    telProdNpIec101GWIfcLongResp OBJECT-TYPE
        SYNTAX  INTEGER {
            disabled(0),
            enabled(1)
            }
        ACCESS  read-write
        STATUS  mandatory
        DESCRIPTION
            " Enable sends long frame responses to RTU's."
        ::={ telProdNpIec101GWEntry 6 }

    telProdNpIec101GWIfcMultilink OBJECT-TYPE
        SYNTAX  INTEGER {
            disabled(0),
            enabled(1)
            }
        ACCESS  read-write
        STATUS  mandatory
        DESCRIPTION
            " Enable RTU's multilink mode."
        ::={ telProdNpIec101GWEntry 7 }

    telProdNpIec101GWIfcBuffNum OBJECT-TYPE
        SYNTAX  INTEGER (1..1024)
        ACCESS  read-write
        STATUS  mandatory
        DESCRIPTION
            " Configure number of IEC-101 transmission buffers."
        ::={ telProdNpIec101GWEntry 8 }

    telProdNpIec101GWIfcOrigAddr OBJECT-TYPE
        SYNTAX  INTEGER (1..65534)
        ACCESS  read-write
        STATUS  mandatory
        DESCRIPTION
            " Configure IEC-101 Originator Address."
        ::={ telProdNpIec101GWEntry 9 }

    telProdNpIec101GWIfcRetransMax OBJECT-TYPE
        SYNTAX  INTEGER (1..300)
        ACCESS  read-write
        STATUS  mandatory
        DESCRIPTION
            " Configure maximum number of IEC-101 messages retransmissions."
        ::={ telProdNpIec101GWEntry 10 }

    telProdNpIec101GWIfcRetransTime OBJECT-TYPE
        SYNTAX  INTEGER (1..10000)
        ACCESS  read-write
        STATUS  mandatory
        DESCRIPTION
            " Configure time for IEC-101 messages retransmissions. Time in milliseconds"
        ::={ telProdNpIec101GWEntry 11 }

    telProdNpIec101GWIfcRxTimeout OBJECT-TYPE
        SYNTAX  INTEGER (1..10000)
        ACCESS  read-write
        STATUS  mandatory
        DESCRIPTION
            " Configure input frame timeout. Time in milliseconds"
        ::={ telProdNpIec101GWEntry 12 }

    telProdNpIec101GWIfcSyncTime OBJECT-TYPE
        SYNTAX  INTEGER (1..43200)
        ACCESS  read-write
        STATUS  mandatory
        DESCRIPTION
            " Configure period time to sent IEC-101 Synchronization message
              to RTU. Time in minutes"
        ::={ telProdNpIec101GWEntry 13 }

    telProdNpIec101GWIfcTestTime OBJECT-TYPE
        SYNTAX  INTEGER (1..86400)
        ACCESS  read-write
        STATUS  mandatory
        DESCRIPTION
            " Configure period time to sent IEC-101 Link Test message to RTU.
              Time in seconds"
        ::={ telProdNpIec101GWEntry 14 }

    telProdNpIec101GWIfcTestType OBJECT-TYPE
        SYNTAX  INTEGER {
            none(0),
            test(1),
            status(2)
            }
        ACCESS  read-write
        STATUS  mandatory
        DESCRIPTION
            " Configure type of IEC-101 Link Test message to send to RTU.
                0  Don't send message,
                1  Send Test message,
                2  Send Status message.
              "
        ::={ telProdNpIec101GWEntry 15 }


--  = = = = = = = = = = = = = = = = = = = = = = = = = = = = = = = = = = = = = =
--  Interface IEC-101 GW RTU's configuration variables
--  = = = = = = = = = = = = = = = = = = = = = = = = = = = = = = = = = = = = = =

--  Interface IEC-101 GW RTUs link address table (Start).

   telProdNpIec101GWIfcRtuTable OBJECT-TYPE
        SYNTAX  SEQUENCE OF TelProdNpIec101GWIfcRtuEntry
        ACCESS  not-accessible
        STATUS  mandatory
        DESCRIPTION
            " Table of RTU Link Address configuration for IEC101 GW interfaces.
              There are two table indexes: the interface and the RTU index."

    ::= { telProdNpConfInterfIec101GW 2 }

   telProdNpIec101GWIfcRtuEntry OBJECT-TYPE
        SYNTAX  TelProdNpIec101GWIfcRtuEntry
        ACCESS  not-accessible
        STATUS  mandatory
        DESCRIPTION
            " Each entry contains an RTU link address. Each entry consist on an
             interfece index and an RTU index.
            "
        INDEX   { telProdNpIec101GWIfcRtuIfcIndex, telProdNpIec101GWIfcRtuIndex }
        ::={ telProdNpIec101GWIfcRtuTable 1 }

    TelProdNpIec101GWIfcRtuEntry ::=
        SEQUENCE{
            telProdNpIec101GWIfcRtuIfcIndex INTEGER,
            telProdNpIec101GWIfcRtuIndex    INTEGER,
            telProdNpIec101GWIfcRtuStatus   INTEGER,
            telProdNpIec101GWIfcRtuAddress  INTEGER
        }

    telProdNpIec101GWIfcRtuIfcIndex OBJECT-TYPE
        SYNTAX  INTEGER
        ACCESS  read-only
        STATUS  mandatory
        DESCRIPTION
            "IEC101-GW interface index. It is the index table."
        ::={ telProdNpIec101GWIfcRtuEntry 1 }

    telProdNpIec101GWIfcRtuIndex OBJECT-TYPE
        SYNTAX  INTEGER
        ACCESS  read-only
        STATUS  mandatory
        DESCRIPTION
            " RTU table index."
        ::={ telProdNpIec101GWIfcRtuEntry 2 }

    telProdNpIec101GWIfcRtuStatus OBJECT-TYPE
        SYNTAX  INTEGER{
            valid(1),
            add(2),
            delete(3)
            }
        ACCESS  read-write
        STATUS  mandatory
        DESCRIPTION
            "Table control variable.
            Set to 1 does nothing.
            Set to 2 adds a new row (RTU link address) in the table with default
            value(65534) and returns 2. If it already exists, then it returns error.
            It must be added immediately after the last index. To greate a new row
            RTU address 65534 must not exist. After greate you must modify RTU address.
            Set to 3 deletes all table fields corresponding to that Agent,
            and returns 3.
            Get returns 1 if the control exists."
        ::={ telProdNpIec101GWIfcRtuEntry 3 }

    telProdNpIec101GWIfcRtuAddress OBJECT-TYPE
        SYNTAX  INTEGER (1..65534)
        ACCESS  read-write
        STATUS  mandatory
        DESCRIPTION
            "Set link address for a RTU in multilink mode. RTU link address
            can not be repeated. If address already exists, then it returns error."
        ::={ telProdNpIec101GWIfcRtuEntry 4 }

--  Interface IEC-101 GW RTUs link address table (END).


END
