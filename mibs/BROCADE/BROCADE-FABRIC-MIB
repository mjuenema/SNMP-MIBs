BROCADE-FABRIC-MIB DEFINITIONS ::= BEGIN

IMPORTS
   MODULE-IDENTITY, OBJECT-TYPE, Unsigned32, Counter32
      FROM SNMPv2-SMI                  -- [RFC2578]
   brcdFabric
      FROM FOUNDRY-SN-ROOT-MIB;        -- [snrootu]

brcdFabricMIB MODULE-IDENTITY
   LAST-UPDATED "201205270000Z"  -- May 27, 2012
   ORGANIZATION "Brocade Communications Systems, Inc."
   CONTACT-INFO
            "Technical Support Center
             130 Holger Way,
             San Jose, CA  95134
             Email:  ipsupport@brocade.com
             Phone: 1-800-752-8061
             URL:  www.brocade.com"
   DESCRIPTION
            "The MIB module contains the managed object definition for
             Brocade Switch Fabric Module.

             Supported Platforms:
                  - supported on NI XMR/MLX platforms.

             Copyright 1996-2010 Brocade Communications Systems, Inc.
             All rights reserved.
             This Brocade Communications Systems SNMP Management Information
             Base Specification embodies Brocade Communications Systems'
             confidential and proprietary intellectual property.
             Brocade Communications Systems retains all title and ownership
             in the Specification, including any revisions.

             This Specification is supplied AS IS, and Brocade Communications
             Systems makes no warranty, either express or implied, as to the
             use, operation, condition, or performance of the specification,
             and any unintended consequence it may on the user environment."

   REVISION      "201205270000Z"  -- May 27, 2012
   DESCRIPTION
            "Initial version"

   ::= { brcdFabric 1 }

--
-- high level object identifiers
--
brcdFabricObjects    OBJECT IDENTIFIER ::= { brcdFabricMIB 1 }

-- the brcdFabricStatsTable table

-- The brcdFabricStatsTable table contains information of Switch Fabric Module
-- (SFM) related information on NI XMR/MLX platform.

brcdFabricStatsTable OBJECT-TYPE
   SYNTAX        SEQUENCE OF BrcdFabricStatsEntry
   MAX-ACCESS    not-accessible
   STATUS        current
   DESCRIPTION
       "A list of brcdFabricStats entries. This table contains information of
        various Switch Fabric Module(SFM) counters supported by this system."
   ::= { brcdFabricObjects 1 }

brcdFabricStatsEntry OBJECT-TYPE
   SYNTAX        BrcdFabricStatsEntry
   MAX-ACCESS    not-accessible
   STATUS        current
   DESCRIPTION
       "An entry containing SFM and FE counter information."
   INDEX   { brcdFabricSfmId, brcdFabricSfmFeId }
   ::= { brcdFabricStatsTable 1 }

BrcdFabricStatsEntry ::=  SEQUENCE {
   brcdFabricSfmId           Unsigned32,
   brcdFabricSfmFeId         Unsigned32,
   brcdFabricDropMAC0Count   Counter32,
   brcdFabricDropMAC1Count   Counter32,
   brcdFabricDropMAC2Count   Counter32,
   brcdFabricDropMAC3Count   Counter32
}

brcdFabricSfmId OBJECT-TYPE
   SYNTAX        Unsigned32
   MAX-ACCESS    not-accessible
   STATUS        current
   DESCRIPTION
       "Switch Fabric Module(SFM) number"
   ::= { brcdFabricStatsEntry 1 }

brcdFabricSfmFeId OBJECT-TYPE
   SYNTAX        Unsigned32
   MAX-ACCESS    not-accessible
   STATUS        current
   DESCRIPTION
       "Fabric Element(FE) number"
   ::= { brcdFabricStatsEntry 2 }

brcdFabricDropMAC0Count OBJECT-TYPE
   SYNTAX        Counter32
   MAX-ACCESS    read-only
   STATUS        current
   DESCRIPTION
       "The number of packets dropped for MAC0 link group (links 0 to 23)"
   ::= { brcdFabricStatsEntry 3 }

brcdFabricDropMAC1Count OBJECT-TYPE
   SYNTAX        Counter32
   MAX-ACCESS    read-only
   STATUS        current
   DESCRIPTION
       "The number of packets dropped for MAC1 link group (links 24 to 47)"
   ::= { brcdFabricStatsEntry 4 }

brcdFabricDropMAC2Count OBJECT-TYPE
   SYNTAX        Counter32
   MAX-ACCESS    read-only
   STATUS        current
   DESCRIPTION
       "The number of packets dropped for MAC2 link group (links 48 to 71)"
   ::= { brcdFabricStatsEntry 5 }

brcdFabricDropMAC3Count OBJECT-TYPE
   SYNTAX        Counter32
   MAX-ACCESS    read-only
   STATUS        current
   DESCRIPTION
       "The number of packets dropped for MAC3 link group (links 72 to 95)"
   ::= { brcdFabricStatsEntry 6 }

END
