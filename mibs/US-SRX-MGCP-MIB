-- ==================================================================
-- Copyright © 1999 - 2008 Siemens Enterprise Communications 
--
--  All Rights Reserved.
--
--  Reproduction of this document is authorized on condition that
--  this copyright notice is included.
--
--  This MIB document embodies proprietary intellectual property. 
--  of Siemens Network Convergence LLC, which retains all title and
--  ownership in this MIB, including any revisions.
--
--  This module will be extended, as required.
--
--  Siemens Network Convergence LLC reserves the right to make 
--  changes in specification and other information contained in this 
--  document without prior notice. The reader should consult 
--  Siemens Network Convergence LLC to determine whether any such
--  changes have been made.
--
-- Copyright © 1999 - 2008 Siemens Enterprise Communications 
-- ==================================================================
--
--  Revision History
--
--  08/31/99      Mangping Chang      initial code
--  01/31/00      Mangping Chang      Unisphere renaming
--  04/04/00      Mangping Chang      MIB review update. Indices to all
--                                    tables are unique non-reusable integers
--                                    (generated on creation). Added 
--                                    usSrxMgcpTrunkCircuitTable.
--  04/24/00      Mangping Chang      Added usSrxMgcpGatewayTypeTable and
--                                    usSrxMgcpGatewayObjTable
--  05/02/00      Mangping Chang      Changed the index of usSrxMgcpTrunkCircuitTable.
--  06/16/00      Ken Teelucksingh    Removed usSrxMgcpTrunkCircuitTable, modified 
--                                    usSrxMgcpMGCircuitTable to allow create/modify/delete.
--                                    Changed usSrxMgcpTuningTable index.
--
--  06/29/00      Mangping Chang      Changed the index of usSrxMgcpTuningTable. 
--                                    Updated comments of gateway parameters.  
--                                     
--  07/10/00      Mangping Chang      Combined usSrxMgcpGatewayTable and usSrxMgcpTuningTable.
--  08/10/00      Vidya S. Pandey     removed all the traps
--  09/13/00      Mangping Chang      Changed the default MGC listen port 1 and
--                                    receive port 1 from 2747 to 2427.
--  11/28/00      Ken Teelucksinagh   Comments on modify of circuit formats.usSrxMgcp515ErrorCounter
--  11/29/00      Mangping Chang      More comments on MG Circuit formats.
--  06/01/01      Badri narayan      Changed the default MGC listen port 1 and
--                                    receive port 1 from 2427 to 2727.
--  06/14/01	  Badri Narayan	      Added PRIRowCount, TrunkRowCount and
--				      LineRowCount to usSrxMgcpGatewayTable
--				      and usSrxMgcpGatewayTypeTable. Changed
--				      usSrxMgcpGatewayTypeTableRowCount into 
--				      Vector.
--				      Obsoleted usSrxMgcpMGCircuitTable.
--				      Added usSrxMgcpMGDS1Table. Addded
--				      usSrxMgcpDS0AllocationTable. Added
--				      usSrxMgcpMGDS1RowCountTable 
--  03/14/02	  Badri Narayan	      Added descriptions to DS0Allocation map 
--				      table to include China, Also changed 
--				      usSrxMgcpDS0OffSetIndex range for China.
-- 03/18/2002	  Badri Narayan	      Added new Media Gateway Server Type 
--				      media_server(3). Added New Tables
--				      usSrxMgcpMGEndPointTable,
--				      usSrxMgcpMGTypeEPRCTable  
--			 	      Provided more description for Circuit 
--				      Format
-- 05/06/2002	 Badri Narayan	      Added comments on LataDigits,NPA and DN 
--				      for LineTable,ListLineTable and  added 
--				      new type of gateway  (megaco). 
--				      Added more description for Megaco Receive 
--				      Port.
--
-- 05/06/2002	 Badri Narayan	      Added new Protocol Type mgcp10tgcp10
-- 07/02/2002	 Badri Narayan	      Changed the ProtocolType  ordering.
--				      Changed the values of MgcpMediaGatewayType
--				      Added 4 new oid's to the 
--				      usSrxMgcpGatewayTable. Changed the 
--				      usSrxMgcpGatewayTypeTable to be 
--				      retrievable  on the basis of GatewayType.
--				      Added a new Table usSrxMgcpVendorTypeTable
--				      which is actually the old
--			 	      usSrxMgcpGatewayTypeTable which is 
--				      indexed by VendorType(smx2100 or other).
--				      Added a new 
--				      usSrxMgcpVendorTypeRowCountTable which is
--				      similar to 
--				      usSrxMgcpGatewayTypeTableRowCount.
-- 07/26/2002  Badri Narayan	      Remove RateArea and ClassOfService from
--				      Line Table for Celica Release..
-- 08/15/2002  Badri Narayan	      Changed the MediaGatewayTable to include 
--				      3 indecies. Removed readonly MgcpMediaGatewayType
--				      table. Changed usSrxMgcpGatewayTypeTableRowCount 
--				      to retreive row counts based on  VendorType
--				      and GatewayType added three new fields  
--				      usSrxMgcpMTATimer1, usSrxMgcpMTATimer2, 
--				      usSrxMgcpMTAActivityCount to the 
--				      usSrxMgcpGatewayTable
-- 08/22/2002   Mangping Chang        Changed VendorType to MGUsage and 
--                                    MediaGatewayType as before.
--                                    Added usSrxMgcpMGKeepAlive, 
--                                    usSrxMgcpMTAMaxActivityCount and 
--                                    usSrxMgcpMTACurrActivityCount 
-- 09/20/2002   Badri Narayan	      Added usSrxMgcpSecProfName, 
--				      usSrxMgcpSecProfIndex for referencing 
--				      security objects. 
-- 10/10/2002   Badri Narayan	      Added usSrxMgcpMGFQDName, 
--				      usSrxMgcpFQDNFlag,usSrxMgcpMGIPStatus to 
--				      the usSrxMgcpGatewayTable and 
--				      usSrxMgcpNetworkElementRefreshTable for 
--				      refreshing IP addresses when FQDN 
--				      is used. 
-- 10/22/2002   Badri Narayan	      changed FQDNFlag to usSrxMgcpIPAllocationMethod
-- 11/14/2002   Badri Narayan	      Added usSrxMgcpGatewayClli to GatewayTable
-- 11/20/2002   Badri Narayan	      Removed MTATimer2 from gateway table. 
-- 				      Added usSrxMgcpSendRekeyMessage Table
-- 11/21/2002   Badri Narayan	      Added usSrxMgcpSendWakeupMessage Table
-- 11/22/2002   Badri Narayan	      Removed usSrxMgcpSendWakeupMessage Table
--				      and removed usSrxMgcpSendRekeyMessage 
--				      Table, added extra enums to
--				      usSrxMgcpMGOperStatus
-- 11/24/2002   Badri Narayan	      Added SrxNetworkElementOperStatus as enum
--				      type for MGOperStatus, and added
--				      SrxNetworkElementAdminStatus for 
--				      MGAdminStatus
-- 11/26/2002   Badri Narayan	      Changed SrxNetworkElementOperStatus 
--				      and SrxNetworkElementAdminStatus to
--				      SrxGatewayOperStatus 
--				      and SrxGatewayAdminStatus
-- 12/06/2002   Badri Narayan	      Added usSrxMgcpGtwSigIPAddrSelection
--				      to Media Gateway Table for selection
--				      of MGC Signalling IP Address. 
-- 1/10/2003   Badri Narayan	      Changed Description of LineNPA for Japan
-- 1/13/2003   Badri Narayan	      Added new Intercept and Intercept Row 
--				      Count Table. Also added description for 
--				      which fields belong to which media 
--				      gateway  type for the gateway table.
-- 3/06/2003   Badri Narayan	      Changed for CW 26 Added RtpCipherSuites 
--			  	      and RTCPCipherSuites  to Gateway Table
-- 4/03/2003   Badri Narayan	      Added support for variable markets 
--			  	      DN and NPA fields. Added the following
--			  	      usSrxLineDnLengthMin,
--			  	      usSrxLineDnLengthMax,
--			  	      usSrxLineTotalDigitsLengthMin, 
--			  	      usSrxLineTotalDigitsLengthMax to
--			  	      usSrxMgcpConfigData 
-- 05/08/03    Polly Yu               Updated copyright text
-- 05/12/03    Badri Narayan          Changed  usSrxMgcpMGDS1Table's  and
--				      usSrxMgcpMGDS1TableRowCount description
--				      and added usSrxMgcpMGMultiCircuitTable
-- 10/10/03    Badri Narayan          Added Circuit type to denote media
--				      server circuit usage. Specifically added
--				      usSrxMgcpMGMultiCirCircuitType and
--				      MediaServerCircuitType and
--				      usSrxMgcpMGDS1CircuitType 
-- 12/01/03    Badri Narayan          Changed usSrxMgcpMGRequestTimeout 
--				      Range and defval
-- 12/09/03    Badri Narayan          Added None to MediaServerCircuitType
-- 01/28/04    Mangping Chang         Merged new parms to RTCPCipherSuites
-- 04/02/04    Badri Narayan          Added usSrxMgcpLineVMWIStatus
-- 05/05/04    Badri Narayan          Added usSrxMgcpMediaServerVersion
-- 07/14/04    Ren Luo                Added 43 new counters
-- 07/08/04    Badri Narayan          Added new MgcpMediaGatewayType hig1100
--			              and added description for circuit format
--			              for this gateway and updated the 
--			              descriptions in the usSrxMgcpDS0AllocationTable
-- 11/29/04    Badri Narayan          Added new usSrxMgcpT38FaxCapability
-- 11/29/04    Badri Narayan          Added new usSrxMgcpDtmfCapability
-- 05/20/05    Ren Luo                Updated MgcpLineOperStatus for line 2
--                                    call status
-- 06/08/05    Badri Narayan          Updated Description for 
--				      SrxGatewayOperStatus
-- 09/08/05    Pedro Henriques        For FRN1317-R10.1, New values in
--                                      MgcpLineAdminStatus=blockAndRelease
--                                      MgcpLineOperStatus=auditBlocked
--                                    Added usSrxMgcpLineOperStatusTime
--                                      in UsSrxMgcpLineEntry
--				      Added usSrxMgcpListLineOperStatus,
--                                      and usSrxMgcpListLineOperStatusTime
--                                      in UsSrxMgcpListLineEntry
-- 10/20/05    Nikos Vittas 	       Removed usSrxMgcpLineLataDigits for FRN1017
-- 01/03/06    Badri Narayan 	       Added VMWI and AMWI
-- 04/11/06    Emilio Negron           for FRN0988 - R11.0, Added new 
--                                     MediaServerCircuitType called 'Audit'
-- 04/20/06    C.Georgantonis	      Modified status to 'deprecated' for
--				      usSrxMgcpMGCListenPort2 and usSrxMgcpMGReceivePort2
-- 06/21/06    A.Nixarlidis           Added ten new parameters in the MGCP Gateway Table
--                                    for FRN1905 (MG overload controls)
-- 07/11/06    Marco Silva            FRN1892 - Updates to MEGACO - Added support for 
--                                    hiG 1400 and AMR codec  
-- 08/25/06    Emilio Negron          FRN2065 - New oSI feature configuration data added.
-- 10/10/06    Carlos Amaral          FRN2229 - Disable NCS signaling when MTA
--                                    is manually blocked.
-- 12/11/2006  Carlos Gregorio        Removed PRI references for R12 - FRN2271 - Decommission PRI
-- 01/02/07    Emilio Negron          Modifed range for usSrxMgcpTtlongtranTimer to 5-35, 
--                                    default to 30.
-- 01/03/07    Emilio Negron          Modified range for usSrxMgcpTtlongtranTimer to 5-35.
--                                    Also, modified default to 30 for same.
-- 04/10/08    C. Chatzidimitriou     FRN3208. Cleanup of MIBS      
-- 06/12/2008  C. Chatzidimitriou     Updated MIB to be fully compatible with SNMPv2  
--
-- ***********************************************************************

US-SRX-MGCP-MIB DEFINITIONS ::= BEGIN

IMPORTS
    MODULE-IDENTITY, OBJECT-TYPE, Counter32
        FROM SNMPv2-SMI 
    TEXTUAL-CONVENTION
        FROM SNMPv2-TC
    surpassRtp
	FROM SURPASS-RTP-MIB
    hiq8000Admin
        FROM SURPASS-RTP-ADMIN-MIB
    SrxRowCountType,SrxOnOffType,IkeKeyGenMethod,IkeKeyType,IkeKey,IkeKeyLength,NameType
        FROM HIQ-ADMIN-MIB
    Boolean, TimeStampSeconds
        FROM FSC-RTP-MIB;

-- ########################################################

usSrxMgcp MODULE-IDENTITY
    LAST-UPDATED "200806111500Z"
    ORGANIZATION "Siemens Network Convergence LLC"
    CONTACT-INFO " "
    DESCRIPTION
        "SRX MGCP Connection Control Manager MIB Module which 
         includes management of PSTN Gateway and PSTN Circuits." 
    
    REVISION "200806111500Z"    
    DESCRIPTION
            "Updated the MIB to be fully compatible with SNMPv2"

    ::= { hiq8000Admin 3 }

-- *****************************************************
-- Textual Conventions used in the Zone Translations MIB
-- *****************************************************

MediaServerCircuitType ::= TEXTUAL-CONVENTION
	STATUS current
	DESCRIPTION "Indicates the usage of the Media Server Circuit..
		     The following ussages apply
		     None --- Is used by Trunking and Residential Gateways
		     Any--- can be used for any circuit
		     Announcement--- is to be used for annoucement only
		     Surveillance--- is to be used for surveillance only
		     Conference  --- is to be used for conference only
		     ConferenceAdhoc  --- is to be used for ad hoc 
					  conference only
                     Audit --- is offered in the list of circuit types 
                               when creating a circuit"
        SYNTAX INTEGER { none(0),
			 any(5),
			 announcement(6), 
			 surveillance(7), 
			 conference(8),
			 conferenceadhoc(9),
                         audit(10)}

MwiStatus ::= TEXTUAL-CONVENTION
	STATUS current
	DESCRIPTION "Indicates the status of Message Waiting Indicator
		     notSubscriber --- The customer has not subscribed to this service
		     subscribedOff --- The customer has subscribed but no messages are present.
		     subscribedOn  --- The customer has subscribed and messages are present "  
        SYNTAX      INTEGER {notSubscribed(1),	
	                     subscribedOff(2),
			     subscribedOn(3)}

MgcpLineLineType ::= TEXTUAL-CONVENTION
	STATUS current
	DESCRIPTION "Indicates the type of line belonging 
		     belonging to this circuit
		     Pots Line (several types exist)
		     Data Line (typically pots line connected to Data equipment)
		     CLASS Line (enhanced POTS with Display capabilities)
		     Coin Line (Pay phones)
		     BRI Line  (ISDN)"
	SYNTAX INTEGER {potsLine(1),
			dataLine(2),
			classLine(3),
			coinLine(4),
			briLine(5)}

MgcpGatewayUsageType ::= TEXTUAL-CONVENTION
	STATUS current
	DESCRIPTION "Indicates the type of gateway that is supported."
	SYNTAX INTEGER { trunking(1),
			residential(2),
			mediaServer(3)}

MgcpProtocolType ::= TEXTUAL-CONVENTION
	STATUS current
    	DESCRIPTION "MG supported protocol versions. The protocol versions
                     must be one of the protocol names defined in the MGCP
                     configuration parameter file.
                     For now, there are 6 supported protocol names:
                     0. mgcp 0.0
                     1. mgcp 0.1
                     2. mgcp 1.0 ncs 1.0 (Applicable for cable labs and in  
				          conjunction with Residential 
					  gateways and media server only.)
                     3. mgcp 1.0  
                     4. mgcp 0.5
                     5. mgcp 1.0 tgcp 1.0 (Applicable only for Trunking gateway)
		     
		     We are reserving values upto 10 for MGCP
		     For Megaco this value is 
		     11. MEGACO
		     All Values from 11-20 are reserved for MEGACO

		     mgcp 1.0 ncs 1.0  is used for packet cable 
		     The mgcp 1.0 tgcp 1.0 is used in conjunction
		     with trunking gateways only."
	SYNTAX INTEGER {  mgcp00(0),
                          mgcp01(1), 
			  mgcp10ncs10(2),
			  mgcp10(3),
                          mgcp05(4),
			  mgcp10tgcp10(5),
			  megaco(11)}


MgcpMediaGatewayType ::= TEXTUAL-CONVENTION
	STATUS current
    	DESCRIPTION "An integer variable indicating the gateway type. 
                     For now, the gateway type is SMX2100,hig1100,hig1400 and others. 
                     More gateway types can be added in the future. "
	SYNTAX INTEGER {  smx2100(1), 
			  other(2),
			  hig1100(3),
              		  hig1400(4),
			  ata(5)}	

MgcpLineCurrentDialTonePattern ::= TEXTUAL-CONVENTION
        STATUS current
        DESCRIPTION "Indicates the type of dialtone belonging to this 
                     Line belonging to the circuit
		     dl -- Dial Tone
       		     sdl -- Stutter Dial Tone"
        SYNTAX INTEGER {dl(1),sdl(2)}

MgcpLineAdminStatus ::= TEXTUAL-CONVENTION
        STATUS current
        DESCRIPTION "Indicates the Administration Status of the
                     Line belonging to the circuit
		     blocked -- Indicates that the line is blocked
		     active -- Indicates that the line is active
		     blockAndRelease -- It indicates that the line is blocked
                     and in addition it will release any existing call. This
                     value is only used for setting."
        SYNTAX INTEGER {active(1),blocked(2), blockAndRelease(3)}

MgcpLineOperStatus ::= TEXTUAL-CONVENTION
        STATUS current
        DESCRIPTION "Indicates the Operational Status of the
                     virtual lines belonging to the circuit.
                     
                     First line and second line are legs of an MTA call
                     and second leg would be a Call Waiting call or a TWC 
                     or a second call while first leg is on hold.

		     blocked -- Indicates that the lines are blocked
		     active -- Indicates that the lines are idle 
                     auditBlocked -- Indicates that the lines are blocked
                            and being audited

                     In addition, it indicates the following call
                     status:

                     OperStatus        1st line         2nd line
                     -----------------------------------------------
                     busyOut-idle      busy outgoing    idle
                     busyIn-idle       busy incoming    idle
                     idle-busy0ut      idle             busy outgoing
                     idle-busyIn       idle             busy incoming
                     busyIn-busyIn     busy incoming    busy incoming
                     busyIn-busyOut    busy incoming    busy outgoing
                     busyOut-busyIn    busy outgoing    busy incoming
                     busyOut-busyOut   busy outgoing    busy outgoing
                     "
        SYNTAX INTEGER {active(1),
                        blocked(2),
                        busyOut-idle(4),
                        busyIn-idle(5),
                        audit-blocked(512),
                        idle-busyOut(1024),
                        busyOut-busyOut(1028),
                        busyIn-busyOut(1029),
                        idle-busyIn(5120),
                        busyOut-busyIn(5124),
                        busyIn-busyIn(5125)
                       }

SrxGatewayOperStatus ::= TEXTUAL-CONVENTION
        STATUS   current
        DESCRIPTION "Indicates the Operational Status of the Network element.
                     Currently only the media gateway is supported. For future
                     releases cmts and other network elements will be supported
	             For CMTS Objects the values used will be 
			 ADMIN ACTIVE(1),
			 ADMIN BLOCKED(2),
			 ADMIN ACTIVE OVERLOAD(7),
			 ADMIN BLOCKED OVERLOAD(8),
		     For release 08.01.US.04 onwards the values for Media Gateway 
		     will be Admin Active (1) , Admin Blocked(2), Admin Active Overload(7),
		     Admin Blocked Overload(8), the values 3 to 6 are obsolete."
        SYNTAX INTEGER { active(1),
                         blocked(2),
                         mgActiveSecurityEnabled(3),
                         mgBlockedSecurityEnabled(4),
                         mgActiveSecurityDisabled(5),
                         mgBlockedSecurityDisabled(6),
			 activeoverload(7),
                         blockedoverload(8)}

SrxGatewayAdminStatus ::= TEXTUAL-CONVENTION
           STATUS   current
           DESCRIPTION "Indicates the Administrational Status of
                         the Network element.Currently only the media
                         gateway is supported. For future releases cmts and
                         other network elements will be supported"
           SYNTAX INTEGER {active(1),blocked(2),precut(3)}



--####################
-- OBJECT IDENTIFIER 
--####################

usSrxMgcpObjects         OBJECT IDENTIFIER     ::= { usSrxMgcp 1 } 

usSrxMgcpPerformData     OBJECT IDENTIFIER     ::= { usSrxMgcpObjects 1 }

-- *****************************************************************
-- MGCP Performance  Data                                   
-- Every statistics counter will be shared by all instances of the   
-- MGCP process.                                                     
-- *****************************************************************

usSrxMgcpCreateConnSentCounter     OBJECT-TYPE
    SYNTAX      Counter32
    MAX-ACCESS  read-only
    STATUS      current
    DESCRIPTION
        " This object refers to the counter of total create connection 
          messages sent. " 
    ::= { usSrxMgcpPerformData 1  }


usSrxMgcpCreateConnAckReceivedCounter     OBJECT-TYPE
    SYNTAX      Counter32
    MAX-ACCESS  read-only
    STATUS      current
    DESCRIPTION
        " This object refers to the counter of total create connection 
          acknowledgements received. "
    ::= { usSrxMgcpPerformData 2  }

     
usSrxMgcpModifyConnSentCounter     OBJECT-TYPE
    SYNTAX      Counter32
    MAX-ACCESS  read-only
    STATUS      current
    DESCRIPTION
        " This object refers to the counter of total modify connection 
          messages sent. "
    ::= { usSrxMgcpPerformData 3  }
      
usSrxMgcpModifyConnAckReceivedCounter     OBJECT-TYPE
    SYNTAX      Counter32
    MAX-ACCESS  read-only
    STATUS      current
    DESCRIPTION
        " This object refers to the counter of total modify connection
          acknowledgements received. "
    ::= { usSrxMgcpPerformData 4  }

usSrxMgcpDeleteConnSentCounter       OBJECT-TYPE
    SYNTAX      Counter32
    MAX-ACCESS  read-only
    STATUS      current
    DESCRIPTION
        " This object refers to the counter of total delete connection 
          messages sent. "
    ::= { usSrxMgcpPerformData  5 }      
      
usSrxMgcpDeleteConnAckReceivedCounter       OBJECT-TYPE
    SYNTAX      Counter32
    MAX-ACCESS  read-only
    STATUS      current
    DESCRIPTION
        " This object refers to the counter of total delete connection
          acknowledgements received. "
    ::= { usSrxMgcpPerformData  6 }


usSrxMgcpDeleteConnReceivedCounter        OBJECT-TYPE
    SYNTAX      Counter32
    MAX-ACCESS  read-only
    STATUS      current
    DESCRIPTION
        " This object refers to the counter of total delete connection
          messages received. "
    ::= { usSrxMgcpPerformData 7 }

usSrxMgcpDeleteConnAckSentCounter        OBJECT-TYPE
    SYNTAX      Counter32
    MAX-ACCESS  read-only
    STATUS      current
    DESCRIPTION
        " This object refers to the counter of total delete connection
          acknowledgements sent. "
    ::= { usSrxMgcpPerformData 8 }

         
usSrxMgcpRestartInProgressReceivedCounter      OBJECT-TYPE
    SYNTAX      Counter32
    MAX-ACCESS  read-only
    STATUS      current
    DESCRIPTION
        " This object refers to the counter of total Gateway Restart in Progress
          messages received. "
    ::= { usSrxMgcpPerformData 9 }
  

usSrxMgcpRestartInProgressAckSentCounter      OBJECT-TYPE
    SYNTAX      Counter32
    MAX-ACCESS  read-only
    STATUS      current
    DESCRIPTION
        " This object refers to the counter of total Gateway Restart in Progress
          acknowledgements sent. "
    ::= { usSrxMgcpPerformData 10 }

usSrxMgcpNotifyRequestSentCounter       OBJECT-TYPE
    SYNTAX      Counter32
    MAX-ACCESS  read-only
    STATUS      current
    DESCRIPTION
        " This object refers to the counter of total notify request 
          messages sent. "
    ::= { usSrxMgcpPerformData  11 }

usSrxMgcpNotifyRequestAckReceivedCounter       OBJECT-TYPE
    SYNTAX      Counter32
    MAX-ACCESS  read-only
    STATUS      current
    DESCRIPTION
        " This object refers to the counter of total notify request  
          acknowledgements received. "
    ::= { usSrxMgcpPerformData  12 }


usSrxMgcpNotifyReceivedCounter       OBJECT-TYPE
    SYNTAX      Counter32
    MAX-ACCESS  read-only
    STATUS      current
    DESCRIPTION
        " This object refers to the counter of total notify  
          messages received. "
    ::= { usSrxMgcpPerformData  13 }

usSrxMgcpNotifyAckSentCounter       OBJECT-TYPE
    SYNTAX      Counter32
    MAX-ACCESS  read-only
    STATUS      current
    DESCRIPTION
        " This object refers to the counter of total notify 
          acknowledgements sent. "
    ::= { usSrxMgcpPerformData  14 }

usSrxMgcpAuditEndPointSentCounter       OBJECT-TYPE
    SYNTAX      Counter32
    MAX-ACCESS  read-only
    STATUS      current
    DESCRIPTION
        " This object refers to the counter of total audit endpoint 
          messages sent. "
    ::= { usSrxMgcpPerformData  15 }

usSrxMgcpAuditEndPointAckReceivedCounter       OBJECT-TYPE
    SYNTAX      Counter32
    MAX-ACCESS  read-only
    STATUS      current
    DESCRIPTION
        " This object refers to the counter of total audit endpoint 
          acknowledgements received. "
    ::= { usSrxMgcpPerformData  16 }

usSrxMgcpAuditConnSentCounter       OBJECT-TYPE
    SYNTAX      Counter32
    MAX-ACCESS  read-only
    STATUS      current
    DESCRIPTION
        " This object refers to the counter of total audit connection 
          messages sent. "
    ::= { usSrxMgcpPerformData  17 }

usSrxMgcpAuditConnAckReceivedCounter       OBJECT-TYPE
    SYNTAX      Counter32
    MAX-ACCESS  read-only
    STATUS      current
    DESCRIPTION
        " This object refers to the counter of total audit connection 
          acknowledgements received. "
    ::= { usSrxMgcpPerformData  18 }


usSrxMgcpEndPointConfigSentCounter       OBJECT-TYPE
    SYNTAX      Counter32
    MAX-ACCESS  read-only
    STATUS      current
    DESCRIPTION
        " This object refers to the counter of total endpoint Config 
          messages sent. "
    ::= { usSrxMgcpPerformData  19 }

usSrxMgcpEndPointConfigAckReceivedCounter       OBJECT-TYPE
    SYNTAX      Counter32
    MAX-ACCESS  read-only
    STATUS      current
    DESCRIPTION
        " This object refers to the counter of total endpoint Config  
          acknowledgements received. "
    ::= { usSrxMgcpPerformData  20 }

-- the following 43 counters are added for 05.02.01.13 Patch xxx

usSrxMgcpMTATransientErrorCounter       OBJECT-TYPE
    SYNTAX      Counter32
    MAX-ACCESS  read-only
    STATUS      current
    DESCRIPTION
        " This object refers to the counter of MTA Transient Errors with ranges from 400-499 "
    ::= { usSrxMgcpPerformData  21 }

usSrxMgcp500ErrorCounter       OBJECT-TYPE
    SYNTAX      Counter32
    MAX-ACCESS  read-only
    STATUS      current
    DESCRIPTION
        " This object refers to the counter of MGCP return code 500:The 
          transaction could not be executed, because the endpoint is
          unknown."
    ::= { usSrxMgcpPerformData  22 }

usSrxMgcp501ErrorCounter       OBJECT-TYPE
    SYNTAX      Counter32
    MAX-ACCESS  read-only
    STATUS      current
    DESCRIPTION
        " This object refers to the counter of MGCP return code 501:The 
          transaction could not be executed, because the endpoint is
          not ready.  This includes the case where the endpoint is 
          out-of-service."
    ::= { usSrxMgcpPerformData  23 }

usSrxMgcp502ErrorCounter       OBJECT-TYPE
    SYNTAX      Counter32
    MAX-ACCESS  read-only
    STATUS      current
    DESCRIPTION
        " This object refers to the counter of MGCP return code 502: The
          transaction could not be executed, because the endpoint does
          not have sufficient resources (permanent condition)."
    ::= { usSrxMgcpPerformData  24 }

usSrxMgcp503ErrorCounter       OBJECT-TYPE
    SYNTAX      Counter32
    MAX-ACCESS  read-only
    STATUS      current
    DESCRIPTION
        " This object refers to the counter of MGCP return code 503: r'All of' 
          wildcard too complicated."
    ::= { usSrxMgcpPerformData  25 }

usSrxMgcp504ErrorCounter       OBJECT-TYPE
    SYNTAX      Counter32
    MAX-ACCESS  read-only
    STATUS      current
    DESCRIPTION
        " This object refers to the counter of MGCP return code 504: Unknown or unsupported command."
    ::= { usSrxMgcpPerformData  26 }

usSrxMgcp505ErrorCounter       OBJECT-TYPE
    SYNTAX      Counter32
    MAX-ACCESS  read-only
    STATUS      current
    DESCRIPTION
        " This object refers to the counter of MGCP return code 505: 
          Unsupported RemoteConnectionDescriptor.  This SHOULD be used when
          one or more mandatory parameters or values in the
          RemoteConnectionDescriptor is not supported."
    ::= { usSrxMgcpPerformData  27 }

usSrxMgcp506ErrorCounter       OBJECT-TYPE
    SYNTAX      Counter32
    MAX-ACCESS  read-only
    STATUS      current
    DESCRIPTION
        " This object refers to the counter of MGCP return code 506: Unable 
          to satisfy both LocalConnectionOptions and
          RemoteConnectionDescriptor.  This SHOULD be used when the
          LocalConnectionOptions and RemoteConnectionDescriptor contain one
          or more mandatory parameters or values that conflict with each
          other and/or cannot be supported at the same time (except for
          codec negotiation failure - see error code 534)."
    ::= { usSrxMgcpPerformData  28 }

usSrxMgcp507ErrorCounter       OBJECT-TYPE
    SYNTAX      Counter32
    MAX-ACCESS  read-only
    STATUS      current
    DESCRIPTION
        " This object refers to the counter of MGCP return code 
          507:Unsupported functionality. Some unspecified functionality
          required to carry out the command is not supported. Note that
          several other error codes have been defined for specific areas of
          unsupported functionality (e.g. 508, 511, etc.), and this error
          code SHOULD only be used if there is no other more specific error
          code for the unsupported functionality."
    ::= { usSrxMgcpPerformData  29 }

usSrxMgcp508ErrorCounter       OBJECT-TYPE
    SYNTAX      Counter32
    MAX-ACCESS  read-only
    STATUS      current
    DESCRIPTION
        " This object refers to the counter of MGCP return code 508: Unknown
           or unsupported quarantine handling."
    ::= { usSrxMgcpPerformData  30 }

usSrxMgcp509ErrorCounter       OBJECT-TYPE
    SYNTAX      Counter32
    MAX-ACCESS  read-only
    STATUS      current
    DESCRIPTION
        " This object refers to the counter of MGCP return code 509: Error in
          RemoteConnectionDescriptor.  This SHOULD be used when
          there is a syntax or semantic error in the
          RemoteConnectionDescriptor."
    ::= { usSrxMgcpPerformData  31 }

usSrxMgcp510ErrorCounter       OBJECT-TYPE
    SYNTAX      Counter32
    MAX-ACCESS  read-only
    STATUS      current
    DESCRIPTION
        " This object refers to the counter of MGCP return code 510: 
          The transaction could not be executed, because some unspecified
          protocol error was detected.  Automatic recovery from such an
          error will be very difficult, and hence this code SHOULD only be
          used as a last resort."
    ::= { usSrxMgcpPerformData  32 }

usSrxMgcp511ErrorCounter       OBJECT-TYPE
    SYNTAX      Counter32
    MAX-ACCESS  read-only
    STATUS      current
    DESCRIPTION
        " This object refers to the counter of MGCP return code 511:The 
          transaction could not be executed, because the command
          contained an unrecognized extension.  This code SHOULD be used
          for unsupported critical parameter extensions."
    ::= { usSrxMgcpPerformData  33 }

usSrxMgcp512ErrorCounter       OBJECT-TYPE
    SYNTAX      Counter32
    MAX-ACCESS  read-only
    STATUS      current
    DESCRIPTION
        " This object refers to the counter of MGCP return code 512: 
          The transaction could not be executed, because the gateway is not
          equipped to detect one of the requested events."
    ::= { usSrxMgcpPerformData  34 }

usSrxMgcp513ErrorCounter       OBJECT-TYPE
    SYNTAX      Counter32
    MAX-ACCESS  read-only
    STATUS      current
    DESCRIPTION
        " This object refers to the counter of MGCP return code 513: 
          The transaction could not be executed, because the gateway is not
          equipped to generate one of the requested signals."
    ::= { usSrxMgcpPerformData  35 }

usSrxMgcp514ErrorCounter       OBJECT-TYPE
    SYNTAX      Counter32
    MAX-ACCESS  read-only
    STATUS      current
    DESCRIPTION
        " This object refers to the counter of MGCP return code 514: The 
          transaction could not be executed, because the gateway cannot
          send the specified announcemen."
    ::= { usSrxMgcpPerformData  36 }

usSrxMgcp515ErrorCounter       OBJECT-TYPE
    SYNTAX      Counter32
    MAX-ACCESS  read-only
    STATUS      current
    DESCRIPTION
        " This object refers to the counter of MGCP return code 515: 
          The transaction refers to an incorrect connection-id (may have
          been already deleted)."
    ::= { usSrxMgcpPerformData  37 }

usSrxMgcp516ErrorCounter       OBJECT-TYPE
    SYNTAX      Counter32
    MAX-ACCESS  read-only
    STATUS      current
    DESCRIPTION
        " This object refers to the counter of MGCP return code 516: 
          The transaction refers to an unknown call-id, or the call-id
          supplied is incorrect "
    ::= { usSrxMgcpPerformData  38 }

usSrxMgcp517ErrorCounter       OBJECT-TYPE
    SYNTAX      Counter32
    MAX-ACCESS  read-only
    STATUS      current
    DESCRIPTION
        " This object refers to the counter of MGCP return code 517:
          Unsupported or invalid mode."
    ::= { usSrxMgcpPerformData  39 }

usSrxMgcp518ErrorCounter       OBJECT-TYPE
    SYNTAX      Counter32
    MAX-ACCESS  read-only
    STATUS      current
    DESCRIPTION
        " This object refers to the counter of MGCP return code 518:
          Unsupported or unknown package.  It is RECOMMENDED to include a
          PackageList parameter with the list of supported packages in the
          response, especially if the response is generated by the Call
          Agent."
    ::= { usSrxMgcpPerformData  40 }

usSrxMgcp519ErrorCounter       OBJECT-TYPE
    SYNTAX      Counter32
    MAX-ACCESS  read-only
    STATUS      current
    DESCRIPTION
        " This object refers to the counter of MGCP return code 519:
          Endpoint does not have a digit map."
    ::= { usSrxMgcpPerformData  41  }

usSrxMgcp520ErrorCounter       OBJECT-TYPE
    SYNTAX      Counter32
    MAX-ACCESS  read-only
    STATUS      current
    DESCRIPTION
        " This object refers to the counter of MGCP return code 520:
          The transaction could not be executed, because the endpoint is
          'restarting'.  In most cases this would be a transient error, in
          which case, error code 405 SHOULD be used instead.  The error
          code is only included here for backwards compatibility."
    ::= { usSrxMgcpPerformData  42 }

usSrxMgcp521ErrorCounter       OBJECT-TYPE
    SYNTAX      Counter32
    MAX-ACCESS  read-only
    STATUS      current
    DESCRIPTION
        " This object refers to the counter of MGCP return code 521:
          Endpoint redirected to another Call Agent.  The associated
          redirection behavior is only well-defined when this response is
          issued for a RestartInProgress command."
    ::= { usSrxMgcpPerformData  43 }

usSrxMgcp522ErrorCounter       OBJECT-TYPE
    SYNTAX      Counter32
    MAX-ACCESS  read-only
    STATUS      current
    DESCRIPTION
        " This object refers to the counter of MGCP return code 522:
          such event or signal.  The request referred to an event or
          signal that is not defined in the relevant package (which could
          be the default package)."
    ::= { usSrxMgcpPerformData  44 }

usSrxMgcp523ErrorCounter       OBJECT-TYPE
    SYNTAX      Counter32
    MAX-ACCESS  read-only
    STATUS      current
    DESCRIPTION
        " This object refers to the counter of MGCP return code 523:
          Unknown action or illegal combination of actions."
    ::= { usSrxMgcpPerformData  45 }

usSrxMgcp524ErrorCounter       OBJECT-TYPE
    SYNTAX      Counter32
    MAX-ACCESS  read-only
    STATUS      current
    DESCRIPTION
        " This object refers to the counter of MGCP return code 524:
          Internal inconsistency in LocalConnectionOptions."
    ::= { usSrxMgcpPerformData  46 }

usSrxMgcp525ErrorCounter       OBJECT-TYPE
    SYNTAX      Counter32
    MAX-ACCESS  read-only
    STATUS      current
    DESCRIPTION
        " This object refers to the counter of MGCP return code 525:
          Unknown extension in LocalConnectionOptions.  This code SHOULD be
          used for unsupported mandatory vendor extensions."
    ::= { usSrxMgcpPerformData  47 }

usSrxMgcp526ErrorCounter       OBJECT-TYPE
    SYNTAX      Counter32
    MAX-ACCESS  read-only
    STATUS      current
    DESCRIPTION
        " This object refers to the counter of MGCP return code 526:
          Insufficient bandwidth.  In cases where this is a transient
          error, error code 404 SHOULD be used instead."
    ::= { usSrxMgcpPerformData  48 }

usSrxMgcp527ErrorCounter       OBJECT-TYPE
    SYNTAX      Counter32
    MAX-ACCESS  read-only
    STATUS      current
    DESCRIPTION
        " This object refers to the counter of MGCP return code 527:
          Missing RemoteConnectionDescriptor."
    ::= { usSrxMgcpPerformData  49 }

usSrxMgcp528ErrorCounter       OBJECT-TYPE
    SYNTAX      Counter32
    MAX-ACCESS  read-only
    STATUS      current
    DESCRIPTION
        " This object refers to the counter of MGCP return code 528:
          Incompatible protocol version."
    ::= { usSrxMgcpPerformData  50 }

usSrxMgcp529ErrorCounter       OBJECT-TYPE
    SYNTAX      Counter32
    MAX-ACCESS  read-only
    STATUS      current
    DESCRIPTION
        " This object refers to the counter of MGCP return code 529:
          Internal hardware failure."
    ::= { usSrxMgcpPerformData  51 }

usSrxMgcp530ErrorCounter       OBJECT-TYPE
    SYNTAX      Counter32
    MAX-ACCESS  read-only
    STATUS      current
    DESCRIPTION
        " This object refers to the counter of MGCP return code 530:
          CAS signaling protocol error."
    ::= { usSrxMgcpPerformData  52 }

usSrxMgcp531ErrorCounter       OBJECT-TYPE
    SYNTAX      Counter32
    MAX-ACCESS  read-only
    STATUS      current
    DESCRIPTION
        " This object refers to the counter of MGCP return code 531:
          Failure of a grouping of trunks (e.g., facility failure)."
    ::= { usSrxMgcpPerformData  53 }

usSrxMgcp532ErrorCounter       OBJECT-TYPE
    SYNTAX      Counter32
    MAX-ACCESS  read-only
    STATUS      current
    DESCRIPTION
        " This object refers to the counter of MGCP return code 532:
          Unsupported value(s) in LocalConnectionOptions."
    ::= { usSrxMgcpPerformData  54 }

usSrxMgcp533ErrorCounter       OBJECT-TYPE
    SYNTAX      Counter32
    MAX-ACCESS  read-only
    STATUS      current
    DESCRIPTION
        " This object refers to the counter of MGCP return code 533:
          Response too large."
    ::= { usSrxMgcpPerformData  55 }

usSrxMgcp534ErrorCounter       OBJECT-TYPE
    SYNTAX      Counter32
    MAX-ACCESS  read-only
    STATUS      current
    DESCRIPTION
        " This object refers to the counter of MGCP return code 534:
          Codec negotiation failure."
    ::= { usSrxMgcpPerformData  56 }

usSrxMgcp535ErrorCounter       OBJECT-TYPE
    SYNTAX      Counter32
    MAX-ACCESS  read-only
    STATUS      current
    DESCRIPTION
        " This object refers to the counter of MGCP return code 535:
          Packetization period not supported."
    ::= { usSrxMgcpPerformData  57 }

usSrxMgcp536ErrorCounter       OBJECT-TYPE
    SYNTAX      Counter32
    MAX-ACCESS  read-only
    STATUS      current
    DESCRIPTION
        " This object refers to the counter of MGCP return code 536:
          Unknown or unsupported RestartMethod."
    ::= { usSrxMgcpPerformData  58 }

usSrxMgcp537ErrorCounter       OBJECT-TYPE
    SYNTAX      Counter32
    MAX-ACCESS  read-only
    STATUS      current
    DESCRIPTION
        " This object refers to the counter of MGCP return code 537:
          Unknown or unsupported digit map extension."
    ::= { usSrxMgcpPerformData  59 }

usSrxMgcp538ErrorCounter       OBJECT-TYPE
    SYNTAX      Counter32
    MAX-ACCESS  read-only
    STATUS      current
    DESCRIPTION
        " This object refers to the counter of MGCP return code 538:
          Event/signal parameter error "
    ::= { usSrxMgcpPerformData  60 }

usSrxMgcp539ErrorCounter       OBJECT-TYPE
    SYNTAX      Counter32
    MAX-ACCESS  read-only
    STATUS      current
    DESCRIPTION
        " This object refers to the counter of MGCP return code 539:
          Invalid or unsupported command parameter. This code SHOULD 
          only be used when the parameter is neither a package or vendor
          extension parameter."
    ::= { usSrxMgcpPerformData  61 }

usSrxMgcp540ErrorCounter       OBJECT-TYPE
    SYNTAX      Counter32
    MAX-ACCESS  read-only
    STATUS      current
    DESCRIPTION
        " This object refers to the counter of MGCP return code 540: 
          Per endpoint connection limit exceeded."
    ::= { usSrxMgcpPerformData  62 }

usSrxMgcp541ErrorCounter       OBJECT-TYPE
    SYNTAX      Counter32
    MAX-ACCESS  read-only
    STATUS      current
    DESCRIPTION
        " This object refers to the counter of MGCP return code 541: 
          Invalid or unsupported LocalConnectionOptions. This code SHOULD
          only be used when the LocalConnectionOptions is neither a package
          nor a vendor extension LocalConnectionOptions."
    ::= { usSrxMgcpPerformData  63 }

END
