CP-MIB DEFINITIONS ::= BEGIN

-- Title:      RADWARE
--             This Private MIB supports the WSD/CSD/FP/LP
-- Version:    2.9
-- Date:       2/4/2001
-- By:         RMA (Radware MIB Authority)
-- E-mail:     US:   support@radware.com
--             International: support_int@radware.com
--
IMPORTS
       IpAddress,
       TimeTicks
              FROM RFC1155-SMI
       OBJECT-TYPE
              FROM RFC-1212
       DisplayString
              FROM RFC1213-MIB
       TRAP-TYPE
                   FROM RFC1215
       rsCP,
       rndErrorDesc,
       rndErrorSeverity
                    FROM RADWARE-MIB;
    RowStatus ::= INTEGER {
        active(1),
        notInService(2),
        notReady(3),
        createAndGo(4),
        createAndWait(5),
        destroy(6)
        }

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }


--;;;;;;;;;;;;;;;;;;;;;;;;;;;;;;;;;;;;;;;;;;;;;;;;;;;;;;
--;
--;   The file contains all the MIB variables defined
--;   especially for the CongestionProof product.
--;
--;;;;;;;;;;;;;;;;;;;;;;;;;;;;;;;;;;;;;;;;;;;;;;;;;;;;;;

--;;;;;;;;;;;;;;;;;;;;;;;;;;;;;;;;;;;;;;;;;;;;;;;;;;;;;;
--;
--; Module : CIDR
--; Date   : 14/06/01
--;
--;;;;;;;;;;;;;;;;;;;;;;;;;;;;;;;;;;;;;;;;;;;;;;;;;;;;;;

rsCPCIDRsTable OBJECT-TYPE
    SYNTAX SEQUENCE OF RsCPCIDREntry
    ACCESS not-accessible
    STATUS mandatory
    DESCRIPTION
      "Table containing the list of CIDRs."
    ::=  {rsCP 1}

rsCPCIDREntry OBJECT-TYPE
    SYNTAX RsCPCIDREntry
    ACCESS not-accessible
    STATUS mandatory
    DESCRIPTION
       " The row definition for this table. The table is made of four fields:
	 1) The CIDR's subnet.
	 2) The mask for the CIDR.
     3) The static assignment to peer IP.
     4) The static assignment to router IP.
	 The table's key is made of fields 1+2.
     Fields 3+4 are 0.0.0.0 by default and should always both be zero or a real IP."
    INDEX { rsCPCIDRSubnet,
            rsCPCIDRMask }
    ::=  {rsCPCIDRsTable 1}

RsCPCIDREntry ::= SEQUENCE {
  rsCPCIDRSubnet	                IpAddress,
  rsCPCIDRMask  	                IpAddress,
  rsCPCIDRStaticNeighborIPAddress	IpAddress,--opt
  rsCPCIDRStaticRouterIPAddress     IpAddress,--opt
  rsCPCIDRAssignedNeighborIP        IpAddress,
  rsCPCIDRAssignedLocalRouterIP     IpAddress,
  rsCPCIDRPrefixListIndex           INTEGER,
  rsCPCIDRLastMinuteLoad            INTEGER,--ronly
  rsCPCIDRDescription               DisplayString,--opt
  rsCPCIDRStatsTimePeriod1          INTEGER,
  rsCPCIDRStatsTimePeriod2          INTEGER,
  rsCPCIDRStatsTimePeriod3          INTEGER,
  rsCPCIDRStatsTimePeriod4          INTEGER,
  rsCPCIDRStatsTimePeriod5          INTEGER,
  rsCPCIDRStatsTimePeriod6          INTEGER,
  rsCPCIDRStatus   	                RowStatus
  }

rsCPCIDRSubnet  OBJECT-TYPE
    SYNTAX  IpAddress
    ACCESS  read-only
    STATUS  mandatory
    DESCRIPTION
      "The CIDR's subnet."
    ::=  {rsCPCIDREntry 1}

rsCPCIDRMask  OBJECT-TYPE
    SYNTAX  IpAddress
    ACCESS  read-only
    STATUS  mandatory
    DESCRIPTION
      "The CIDR's mask represented as an IP."
    ::=  {rsCPCIDREntry 2}

rsCPCIDRStaticNeighborIPAddress  OBJECT-TYPE
    SYNTAX  IpAddress
    ACCESS  read-write
    STATUS  mandatory
    DESCRIPTION
      "The peer's IP Address the CIDR is statically assigned to."
    ::=  {rsCPCIDREntry 3}

rsCPCIDRStaticRouterIPAddress  OBJECT-TYPE
    SYNTAX  IpAddress
    ACCESS  read-write
    STATUS  mandatory
    DESCRIPTION
      "The router's IP Address the CIDR is statically assigned to."
    ::=  {rsCPCIDREntry 4}

rsCPCIDRAssignedNeighborIP  OBJECT-TYPE
    SYNTAX  IpAddress
    ACCESS  read-write
    STATUS  mandatory
    DESCRIPTION
      "The peer's IP Address the CIDR is statically assigned to."
    ::=  {rsCPCIDREntry 5}

rsCPCIDRAssignedLocalRouterIP  OBJECT-TYPE
    SYNTAX  IpAddress
    ACCESS  read-write
    STATUS  mandatory
    DESCRIPTION
      "The router's IP Address the CIDR is statically assigned to."
    ::=  {rsCPCIDREntry 6}

rsCPCIDRPrefixListIndex  OBJECT-TYPE
    SYNTAX  INTEGER
    ACCESS  read-write
    STATUS  mandatory
    DESCRIPTION
      "The index in the access list."
    ::=  {rsCPCIDREntry 7}

rsCPCIDRLastMinuteLoad  OBJECT-TYPE
    SYNTAX  INTEGER
    ACCESS  read-only
    STATUS  mandatory
    DESCRIPTION
      "The last minute load of the CIDR."
    ::=  {rsCPCIDREntry 8}

rsCPCIDRDescription  OBJECT-TYPE
    SYNTAX  DisplayString (SIZE(0..19))
    ACCESS  read-write
    STATUS  mandatory
    DESCRIPTION
      "CIDR's description."
    ::=  {rsCPCIDREntry 9}

rsCPCIDRStatsTimePeriod1  OBJECT-TYPE
    SYNTAX  INTEGER
    ACCESS  read-only
    STATUS  mandatory
    DESCRIPTION
      "Statistics for period."
    ::=  {rsCPCIDREntry 10}

rsCPCIDRStatsTimePeriod2  OBJECT-TYPE
    SYNTAX  INTEGER
    ACCESS  read-only
    STATUS  mandatory
    DESCRIPTION
      "Statistics for period."
    ::=  {rsCPCIDREntry 11}

rsCPCIDRStatsTimePeriod3  OBJECT-TYPE
    SYNTAX  INTEGER
    ACCESS  read-only
    STATUS  mandatory
    DESCRIPTION
      "Statistics for period."
    ::=  {rsCPCIDREntry 12}

rsCPCIDRStatsTimePeriod4  OBJECT-TYPE
    SYNTAX  INTEGER
    ACCESS  read-only
    STATUS  mandatory
    DESCRIPTION
      "Statistics for period."
    ::=  {rsCPCIDREntry 13}

rsCPCIDRStatsTimePeriod5  OBJECT-TYPE
    SYNTAX  INTEGER
    ACCESS  read-only
    STATUS  mandatory
    DESCRIPTION
      "Statistics for period."
    ::=  {rsCPCIDREntry 14}

rsCPCIDRStatsTimePeriod6  OBJECT-TYPE
    SYNTAX  INTEGER
    ACCESS  read-only
    STATUS  mandatory
    DESCRIPTION
      "Statistics for period."
    ::=  {rsCPCIDREntry 15}

rsCPCIDRStatus OBJECT-TYPE
    SYNTAX RowStatus
    ACCESS read-write
    STATUS mandatory
    DESCRIPTION
       "This variable indicates the administrative status of this entry."
    ::=  {rsCPCIDREntry 16}



--;;;;;;;;;;;;;;;;;;;;;;;;;;;;;;;;;;;;;;;;;;;;;;;;;;;;;;
--;
--; Module : Peers
--; Date   : 14/06/01
--;
--;;;;;;;;;;;;;;;;;;;;;;;;;;;;;;;;;;;;;;;;;;;;;;;;;;;;;;

rsCPPeersTable OBJECT-TYPE
    SYNTAX SEQUENCE OF RsCPPeerEntry
    ACCESS not-accessible
    STATUS mandatory
    DESCRIPTION
      "Table containing the list of peers."
    ::=  {rsCP 2}

rsCPPeerEntry OBJECT-TYPE
    SYNTAX RsCPPeerEntry
    ACCESS not-accessible
    STATUS mandatory
    DESCRIPTION
       " The row definition for this table. The table is made of three fields:
	 1) The peer's IP address.
	 2) The router's local IP for telnet & snmp.
     3) The carrier's name.
	 The table's key is made of fields 1+2."
    INDEX { rsCPPeerNeighborIPAddress,
            rsCPPeerRouterLocalIPAddress }
    ::=  {rsCPPeersTable 1}

RsCPPeerEntry ::= SEQUENCE {
  rsCPPeerNeighborIPAddress	    IpAddress,
  rsCPPeerRouterLocalIPAddress  IpAddress,
  rsCPPeerRoutemapName          DisplayString,
  rsCPPeerPeerState             INTEGER,--ronly
  rsCPPeerCurrentCapacity       INTEGER,--ronly
  rsCPPeerOriginalCapacity      INTEGER,--ronly
  rsCPPeerCurrentLoad           INTEGER,--ronly
  rsCPPeerStatus   	            RowStatus,
  rsCPPeerCriticalLoadThreshold	INTEGER,
  rsCPPeerOptimalLoad			INTEGER
  }

rsCPPeerNeighborIPAddress  OBJECT-TYPE
    SYNTAX  IpAddress
    ACCESS  read-only
    STATUS  mandatory
    DESCRIPTION
      "The peer's IP address."
    ::=  {rsCPPeerEntry 1}

rsCPPeerRouterLocalIPAddress  OBJECT-TYPE
    SYNTAX  IpAddress
    ACCESS  read-only
    STATUS  mandatory
    DESCRIPTION
      "The router's local IP for telnet & snmp."
    ::=  {rsCPPeerEntry 2}

rsCPPeerRoutemapName  OBJECT-TYPE
    SYNTAX  DisplayString (SIZE(1..20))
    ACCESS  read-write
    STATUS  mandatory
    DESCRIPTION
      "The carrier's name."
    ::=  {rsCPPeerEntry 3}

rsCPPeerPeerState OBJECT-TYPE
    SYNTAX INTEGER {
        unknown(0),
        active(1),
        inactive(2)
    }
    ACCESS read-only
    STATUS mandatory
    DESCRIPTION
        "The BGP peer connection state."
    ::=  {rsCPPeerEntry 4}

rsCPPeerCurrentCapacity OBJECT-TYPE
    SYNTAX INTEGER
    ACCESS read-only
    STATUS mandatory
    DESCRIPTION
        "The Sum of all current capacities of this Peer's interfaces."
    ::=  {rsCPPeerEntry 5}

rsCPPeerOriginalCapacity OBJECT-TYPE
    SYNTAX INTEGER
    ACCESS read-only
    STATUS mandatory
    DESCRIPTION
        "sum of original capacities of the interfaces that belong to this peer."
    ::=  {rsCPPeerEntry 6}

rsCPPeerCurrentLoad OBJECT-TYPE
    SYNTAX INTEGER
    ACCESS read-only
    STATUS mandatory
    DESCRIPTION
        "sum of rate load of interfaces that belong to this peer as informed by the router."
    ::=  {rsCPPeerEntry 7}

rsCPPeerStatus OBJECT-TYPE
    SYNTAX RowStatus
    ACCESS read-write
    STATUS mandatory
    DESCRIPTION
       "This variable indicates the administrative status of this entry."
    ::=  {rsCPPeerEntry 8}

rsCPPeerCriticalLoadThreshold  OBJECT-TYPE
    SYNTAX  INTEGER(0..100)
	ACCESS  read-write
    STATUS  mandatory
    DESCRIPTION
      "Critical Load Threshold"
    ::=  {rsCPPeerEntry 9}

rsCPPeerOptimalLoad  OBJECT-TYPE
    SYNTAX  INTEGER(0..100)
    ACCESS  read-write
    STATUS  mandatory
    DESCRIPTION
      "Optimal Load Threshold"
    ::=  {rsCPPeerEntry 10}


--;;;;;;;;;;;;;;;;;;;;;;;;;;;;;;;;;;;;;;;;;;;;;;;;;;;;;;
--;
--; Module : Peers
--; Date   : 14/06/01
--;
--;;;;;;;;;;;;;;;;;;;;;;;;;;;;;;;;;;;;;;;;;;;;;;;;;;;;;;

rsCPPeersPhysicalInterfaceTable OBJECT-TYPE
    SYNTAX SEQUENCE OF RsCPPeerPhysicalInterfaceEntry
    ACCESS not-accessible
    STATUS mandatory
    DESCRIPTION
      "Table containing the list of peer's physical interface."
    ::=  {rsCP 3}

rsCPPeerPhysicalInterfaceEntry OBJECT-TYPE
    SYNTAX RsCPPeerPhysicalInterfaceEntry
    ACCESS not-accessible
    STATUS mandatory
    DESCRIPTION
       " The row definition for this table. The table is made of four fields:
	 1) The peer's IP address.
	 2) The router's local IP for telnet & snmp.
     3) The physical interface's IP address.
     4) The interface's original capacity.
	 The table's key is made of field 1."
    INDEX { rsCPPeerPhysicalInterfaceInterfaceIPAddress }
    ::=  {rsCPPeersPhysicalInterfaceTable 1}

RsCPPeerPhysicalInterfaceEntry ::= SEQUENCE {
  rsCPPeerPhysicalInterfaceInterfaceIPAddress  	IpAddress,
  rsCPPeerPhysicalInterfaceNeighborIPAddress    IpAddress,
  rsCPPeerPhysicalInterfaceLocalRouterIPAddress IpAddress,
  rsCPPeerPhysicalInterfaceCapacity             INTEGER,
  rsCPPeerPhysicalInterfaceIncomingLoad         INTEGER,--ronly
  rsCPPeerPhysicalInterfaceIndex                INTEGER,--ronly
  rsCPPeerPhysicalInterfaceOperStatus           INTEGER,--ronly
  rsCPPeerPhysicalInterfaceDescription          DisplayString,--opt
  rsCPPeerPhysicalInterfaceStatus               RowStatus
  }

rsCPPeerPhysicalInterfaceInterfaceIPAddress  OBJECT-TYPE
    SYNTAX  IpAddress
    ACCESS  read-only
    STATUS  mandatory
    DESCRIPTION
      "The physical interface's IP address."
    ::=  {rsCPPeerPhysicalInterfaceEntry 1}

rsCPPeerPhysicalInterfaceNeighborIPAddress  OBJECT-TYPE
    SYNTAX  IpAddress
    ACCESS  read-write
    STATUS  mandatory
    DESCRIPTION
      "The peer's IP address."
    ::=  {rsCPPeerPhysicalInterfaceEntry 2}

rsCPPeerPhysicalInterfaceLocalRouterIPAddress  OBJECT-TYPE
    SYNTAX  IpAddress
    ACCESS  read-write
    STATUS  mandatory
    DESCRIPTION
      "The router's local IP for telnet & snmp."
    ::=  {rsCPPeerPhysicalInterfaceEntry 3}

rsCPPeerPhysicalInterfaceCapacity  OBJECT-TYPE
    SYNTAX  INTEGER
    ACCESS  read-write
    STATUS  mandatory
    DESCRIPTION
      "The interface's original capacity."
    ::=  {rsCPPeerPhysicalInterfaceEntry 4}

rsCPPeerPhysicalInterfaceIncomingLoad  OBJECT-TYPE
    SYNTAX  INTEGER
    ACCESS  read-only
    STATUS  mandatory
    DESCRIPTION
      "The last polled interval's inbound load rate."
    ::=  {rsCPPeerPhysicalInterfaceEntry 5}

rsCPPeerPhysicalInterfaceIndex  OBJECT-TYPE
    SYNTAX  INTEGER
    ACCESS  read-only
    STATUS  mandatory
    DESCRIPTION
      "Physical index of the peer."
    ::=  {rsCPPeerPhysicalInterfaceEntry 6}

rsCPPeerPhysicalInterfaceOperStatus  OBJECT-TYPE
    SYNTAX INTEGER {
        unknown(0),
        active(1),
        inactive(2)
    }
    ACCESS  read-only
    STATUS  mandatory
    DESCRIPTION
      "Operational status of the interface."
    ::=  {rsCPPeerPhysicalInterfaceEntry 7}

rsCPPeerPhysicalInterfaceDescription  OBJECT-TYPE
    SYNTAX  DisplayString (SIZE(0..19))
    ACCESS  read-write
    STATUS  mandatory
    DESCRIPTION
      "A name the administrator can give the peer on interface."
    ::=  {rsCPPeerPhysicalInterfaceEntry 8}

rsCPPeerPhysicalInterfaceStatus OBJECT-TYPE
    SYNTAX RowStatus
    ACCESS read-write
    STATUS mandatory
    DESCRIPTION
       "This variable indicates the administrative status of this entry."
    ::=  {rsCPPeerPhysicalInterfaceEntry 9}



--;;;;;;;;;;;;;;;;;;;;;;;;;;;;;;;;;;;;;;;;;;;;;;;;;;;;;;
--;
--; Module : Peers
--; Date   : 14/06/01
--;
--;;;;;;;;;;;;;;;;;;;;;;;;;;;;;;;;;;;;;;;;;;;;;;;;;;;;;;

rsCPPrependInterval OBJECT-TYPE
    SYNTAX INTEGER(1..300)
    ACCESS  read-write
    STATUS  mandatory
    DESCRIPTION
      "Determines the minimum time interval (in minutes) between changes 
       in the CIDRs distibution."
    DEFVAL  { 20 }
 ::=  {rsCP 4}




--;;;;;;;;;;;;;;;;;;;;;;;;;;;;;;;;;;;;;;;;;;;;;;;;;;;;;;
--;
--; Module : Peers
--; Date   : 14/06/01
--;
--;;;;;;;;;;;;;;;;;;;;;;;;;;;;;;;;;;;;;;;;;;;;;;;;;;;;;;

rsCPRedistributeInterval OBJECT-TYPE
    SYNTAX INTEGER(0..1000000)
    ACCESS  read-write
    STATUS  mandatory
    DESCRIPTION
      "Indicates how long to wait with distribution change after a peer or interface status
       changed from up to down."
    DEFVAL  { 2 }
 ::=  {rsCP 5}



--;;;;;;;;;;;;;;;;;;;;;;;;;;;;;;;;;;;;;;;;;;;;;;;;;;;;;;
--;
--; Module : Peers
--; Date   : 14/06/01
--;
--;;;;;;;;;;;;;;;;;;;;;;;;;;;;;;;;;;;;;;;;;;;;;;;;;;;;;;

rsCPCriticalPeerLoadThreshold OBJECT-TYPE
    SYNTAX INTEGER(0..100)
    ACCESS  read-write
    STATUS  mandatory
    DESCRIPTION
      "If reaching this bound - trigger reorganization of CIDRs.
       This value is kept as an integer - divide by 100 in code."
    DEFVAL  { 95 }
 ::=  {rsCP 6}



--;;;;;;;;;;;;;;;;;;;;;;;;;;;;;;;;;;;;;;;;;;;;;;;;;;;;;;
--;
--; Module : Peers
--; Date   : 14/06/01
--;
--;;;;;;;;;;;;;;;;;;;;;;;;;;;;;;;;;;;;;;;;;;;;;;;;;;;;;;

rsCPOptimalPeerLoad OBJECT-TYPE
    SYNTAX INTEGER(0..100)
    ACCESS  read-write
    STATUS  mandatory
    DESCRIPTION
      "Above this bound the link is considered as too loaded.
       This value is kept as an integer - divide by 100 in code."
    DEFVAL  { 80 }
 ::=  {rsCP 7}



--;;;;;;;;;;;;;;;;;;;;;;;;;;;;;;;;;;;;;;;;;;;;;;;;;;;;;;
--;
--; Module : Peers
--; Date   : 14/06/01
--;
--;;;;;;;;;;;;;;;;;;;;;;;;;;;;;;;;;;;;;;;;;;;;;;;;;;;;;;

rsCPAdequateTotalPeakLoad OBJECT-TYPE
    SYNTAX INTEGER(101..1000)
    ACCESS  read-write
    STATUS  mandatory
    DESCRIPTION
      "Time interval in which we calculate average load, 
	   later we remember the most loaded time interval as the pick load in the period.
       This value is kept as an integer - divide by 100 in code."
    DEFVAL  { 140 }
 ::=  {rsCP 8}



--;;;;;;;;;;;;;;;;;;;;;;;;;;;;;;;;;;;;;;;;;;;;;;;;;;;;;;
--;
--; Module : Peers
--; Date   : 14/06/01
--;
--;;;;;;;;;;;;;;;;;;;;;;;;;;;;;;;;;;;;;;;;;;;;;;;;;;;;;;

rsCPOptimalTotalPeakLoad OBJECT-TYPE
    SYNTAX INTEGER(101..1000)
    ACCESS  read-write
    STATUS  mandatory
    DESCRIPTION
      "This value is kept as an integer - divide by 100 in code."
    DEFVAL  { 120 }
 ::=  {rsCP 9}



--;;;;;;;;;;;;;;;;;;;;;;;;;;;;;;;;;;;;;;;;;;;;;;;;;;;;;;
--;
--; Module : CIDR
--; Date   : 14/06/01
--;
--;;;;;;;;;;;;;;;;;;;;;;;;;;;;;;;;;;;;;;;;;;;;;;;;;;;;;;

rsCPSubPeriodInterval OBJECT-TYPE
    SYNTAX INTEGER(2..60)
    ACCESS  read-write
    STATUS  mandatory
    DESCRIPTION
      "This value is kept in minutes."
    DEFVAL  { 15 }
 ::=  {rsCP 10}



--;;;;;;;;;;;;;;;;;;;;;;;;;;;;;;;;;;;;;;;;;;;;;;;;;;;;;;
--;
--; Module : MAIN
--; Date   : 14/06/01
--;
--;;;;;;;;;;;;;;;;;;;;;;;;;;;;;;;;;;;;;;;;;;;;;;;;;;;;;;

rsCPRouterPollingInterval OBJECT-TYPE
    SYNTAX INTEGER
    ACCESS  read-write
    STATUS  mandatory
    DESCRIPTION
      "The interval at which routers should be polled after atleast 20 mins passed.
       This value is kept in minutes."
    DEFVAL  { 120 }
 ::=  {rsCP 11}



--;;;;;;;;;;;;;;;;;;;;;;;;;;;;;;;;;;;;;;;;;;;;;;;;;;;;;;
--;
--; Module : Router Polling
--; Date   : 14/06/01
--;
--;;;;;;;;;;;;;;;;;;;;;;;;;;;;;;;;;;;;;;;;;;;;;;;;;;;;;;

rsCPRouterPollingIntervalTimeout OBJECT-TYPE
    SYNTAX INTEGER(1..29)
    ACCESS  read-write
    STATUS  mandatory
    DESCRIPTION
      "Timeout for router polls.
       This value is kept in seconds."
    DEFVAL  { 10 }
 ::=  {rsCP 12}



--;;;;;;;;;;;;;;;;;;;;;;;;;;;;;;;;;;;;;;;;;;;;;;;;;;;;;;
--;
--; Module : MAIN
--; Date   : 14/06/01
--;
--;;;;;;;;;;;;;;;;;;;;;;;;;;;;;;;;;;;;;;;;;;;;;;;;;;;;;;

rsCPInitializeInterval OBJECT-TYPE
    SYNTAX INTEGER
    ACCESS  read-write
    STATUS  mandatory
    DESCRIPTION
      "Timeout for router polls.
       This value is kept in minutes."
    DEFVAL  { 1440 }
 ::=  {rsCP 13}



--;;;;;;;;;;;;;;;;;;;;;;;;;;;;;;;;;;;;;;;;;;;;;;;;;;;;;;
--;
--; Module : CIDR
--; Date   : 14/06/01
--;
--;;;;;;;;;;;;;;;;;;;;;;;;;;;;;;;;;;;;;;;;;;;;;;;;;;;;;;

rsCPPeriodStartTimesTable OBJECT-TYPE
    SYNTAX SEQUENCE OF RsCPPeriodStartTimeEntry
    ACCESS not-accessible
    STATUS mandatory
    DESCRIPTION
      "Table containing the list of period start times."
    ::=  {rsCP 14}

rsCPPeriodStartTimeEntry OBJECT-TYPE
    SYNTAX RsCPPeriodStartTimeEntry
    ACCESS not-accessible
    STATUS mandatory
    DESCRIPTION
       " The row definition for this table. The table is made of three fields:
	 1) Hours.
	 2) Minutes.
	 The table's key is made of all fields."
    INDEX { rsCPPeriodStartTimeHours, rsCPPeriodStartTimeMinutes }
    ::=  {rsCPPeriodStartTimesTable 1}

RsCPPeriodStartTimeEntry ::= SEQUENCE {
  rsCPPeriodStartTimeHours          INTEGER,
  rsCPPeriodStartTimeMinutes	    INTEGER,
  rsCPPeriodStartTimeDescription    DisplayString,
  rsCPPeriodStartTimeStatus         RowStatus
  }

rsCPPeriodStartTimeHours  OBJECT-TYPE
    SYNTAX  INTEGER
    ACCESS  read-only
    STATUS  mandatory
    ::=  {rsCPPeriodStartTimeEntry 1}

rsCPPeriodStartTimeMinutes  OBJECT-TYPE
    SYNTAX  INTEGER
    ACCESS  read-only
    STATUS  mandatory
    ::=  {rsCPPeriodStartTimeEntry 2}

rsCPPeriodStartTimeDescription  OBJECT-TYPE
    SYNTAX  DisplayString (SIZE(0..19))
    ACCESS  read-write
    STATUS  mandatory
    DESCRIPTION
      "Time period's description."
    ::=  {rsCPPeriodStartTimeEntry 3}

rsCPPeriodStartTimeStatus OBJECT-TYPE
    SYNTAX RowStatus
    ACCESS read-write
    STATUS mandatory
    DESCRIPTION
       "This variable indicates the administrative status of this entry."
    ::=  {rsCPPeriodStartTimeEntry 4}



--;;;;;;;;;;;;;;;;;;;;;;;;;;;;;;;;;;;;;;;;;;;;;;;;;;;;;;
--;
--; Module : Router Configuration
--; Date   : 14/06/01
--;
--;;;;;;;;;;;;;;;;;;;;;;;;;;;;;;;;;;;;;;;;;;;;;;;;;;;;;;

rsCPLocalASNumber OBJECT-TYPE
    SYNTAX INTEGER(1..65535)
    ACCESS  read-write
    STATUS  mandatory
    DESCRIPTION
      "Local site's AS number."
 ::=  {rsCP 15}



--;;;;;;;;;;;;;;;;;;;;;;;;;;;;;;;;;;;;;;;;;;;;;;;;;;;;;;
--;
--; Module : Router Configuration
--; Date   : 14/06/01
--;
--;;;;;;;;;;;;;;;;;;;;;;;;;;;;;;;;;;;;;;;;;;;;;;;;;;;;;;

rsCPPrefixListPrefix  OBJECT-TYPE
    SYNTAX  DisplayString (SIZE(0..10))
    ACCESS  read-write
    STATUS  mandatory
    DESCRIPTION
      "access list prefix."
    DEFVAL {"PEERD"}
    ::=  {rsCP 16}



--;;;;;;;;;;;;;;;;;;;;;;;;;;;;;;;;;;;;;;;;;;;;;;;;;;;;;;
--;
--; Module : Router Configuration
--; Date   : 14/06/01
--;
--;;;;;;;;;;;;;;;;;;;;;;;;;;;;;;;;;;;;;;;;;;;;;;;;;;;;;;

rsCPPrependsNumber  OBJECT-TYPE
    SYNTAX  INTEGER(1..12)
    ACCESS  read-write
    STATUS  mandatory
    DESCRIPTION
      "Number of times to prepend the local AS number when peer isn't chosen."
    DEFVAL { 1 }
    ::=  {rsCP 17}



--;;;;;;;;;;;;;;;;;;;;;;;;;;;;;;;;;;;;;;;;;;;;;;;;;;;;;;
--;
--; Module : Main
--; Date   : 14/06/01
--;
--;;;;;;;;;;;;;;;;;;;;;;;;;;;;;;;;;;;;;;;;;;;;;;;;;;;;;;

rsCPRouterConnectionsTable OBJECT-TYPE
    SYNTAX SEQUENCE OF RsCPRouterConnectionEntry
    ACCESS not-accessible
    STATUS mandatory
    DESCRIPTION
      "Table containing the list of routers to telnet."
    ::=  {rsCP 18}

rsCPRouterConnectionEntry OBJECT-TYPE
    SYNTAX RsCPRouterConnectionEntry
    ACCESS not-accessible
    STATUS mandatory
    INDEX { rsCPRouterConnectionRouterIPAddress }
    ::=  {rsCPRouterConnectionsTable 1}

RsCPRouterConnectionEntry ::= SEQUENCE {
  rsCPRouterConnectionRouterIPAddress	IpAddress,
  rsCPRouterConnectionUserName     	    DisplayString,
  rsCPRouterConnectionUserPassword   	DisplayString,
  rsCPRouterConnectionConfPassword      DisplayString,
  rsCPRouterConnectionProtocol          INTEGER,
  rsCPRouterConnectionCommunity	        DisplayString,--opt
  rsCPRouterConnectionPort              INTEGER,
  rsCPRouterConnectionEnableLevel       INTEGER,
  rsCPRouterConnectionTerminalMode      INTEGER,
  rsCPRouterConnectionLastSysUpTime     TimeTicks,--ronly
  rsCPRouterConnectionStatus            RowStatus
  }

rsCPRouterConnectionRouterIPAddress  OBJECT-TYPE
    SYNTAX  IpAddress
    ACCESS  read-only
    STATUS  mandatory
    DESCRIPTION
      "router's IP address."
    ::=  {rsCPRouterConnectionEntry 1}

rsCPRouterConnectionUserName  OBJECT-TYPE
    SYNTAX  DisplayString (SIZE(0..15))
    ACCESS  read-write
    STATUS  mandatory
    DESCRIPTION
      "user name for connection."
    ::=  {rsCPRouterConnectionEntry 2}

rsCPRouterConnectionUserPassword  OBJECT-TYPE
    SYNTAX  DisplayString (SIZE(1..15))
    ACCESS  read-write
    STATUS  mandatory
    DESCRIPTION
      "password for connection."
    ::=  {rsCPRouterConnectionEntry 3}

rsCPRouterConnectionConfPassword  OBJECT-TYPE
    SYNTAX  DisplayString (SIZE(1..16))
    ACCESS  read-write
    STATUS  mandatory
    DESCRIPTION
      "password for connection."
    ::=  {rsCPRouterConnectionEntry 4}

rsCPRouterConnectionProtocol  OBJECT-TYPE
    SYNTAX  INTEGER {telnet(1),ssh(2)}
    ACCESS  read-write
    STATUS  mandatory
    DESCRIPTION
      "The protocol to communicate with the router."
    ::=  {rsCPRouterConnectionEntry 5}

rsCPRouterConnectionCommunity  OBJECT-TYPE
    SYNTAX  DisplayString (SIZE(0..20))
    ACCESS  read-write
    STATUS  mandatory
    DESCRIPTION
      "community password to use for this polled router."
    DEFVAL {"public"}
    ::=  {rsCPRouterConnectionEntry 6}

rsCPRouterConnectionPort  OBJECT-TYPE
    SYNTAX  INTEGER
    ACCESS  read-write
    STATUS  mandatory
    DESCRIPTION
      "The used port for communicating with the router."
    ::=  {rsCPRouterConnectionEntry 7}

rsCPRouterConnectionEnableLevel  OBJECT-TYPE
    SYNTAX  INTEGER
    ACCESS  read-write
    STATUS  mandatory
    DESCRIPTION
      "The level to use with the enable command - default 1000 means unused."
    ::=  {rsCPRouterConnectionEntry 8}

rsCPRouterConnectionTerminalMode  OBJECT-TYPE
    SYNTAX  INTEGER {charByCharMode(1), fullLineMode(2)}
    ACCESS  read-write
    STATUS  mandatory
    DESCRIPTION
      "The telnet terminal mode - transmit a full line or char after char."
    ::=  {rsCPRouterConnectionEntry 9}

rsCPRouterConnectionLastSysUpTime OBJECT-TYPE
    SYNTAX  TimeTicks
    ACCESS  read-only
    STATUS  mandatory
    DESCRIPTION
       "The time (in hundredths of a second) as informed by the router since the
       network management portion of the router's system was last
       re-initialized."
    ::=  {rsCPRouterConnectionEntry 10}

rsCPRouterConnectionStatus OBJECT-TYPE
    SYNTAX RowStatus
    ACCESS read-write
    STATUS mandatory
    DESCRIPTION
       "This variable indicates the administrative status of this entry."
    ::=  {rsCPRouterConnectionEntry 11}



--;;;;;;;;;;;;;;;;;;;;;;;;;;;;;;;;;;;;;;;;;;;;;;;;;;;;;;
--;
--; Module : CIDR
--; Date   : 14/06/01
--;
--;;;;;;;;;;;;;;;;;;;;;;;;;;;;;;;;;;;;;;;;;;;;;;;;;;;;;;

rsCPPrevStatisticsWeight  OBJECT-TYPE
    SYNTAX  INTEGER(0..100)
    ACCESS  read-write
    STATUS  mandatory
    DESCRIPTION
      "The weight at which to multiple previous days' statistics."
    DEFVAL { 0 }
    ::=  {rsCP 19}


--;;;;;;;;;;;;;;;;;;;;;;;;;;;;;;;;;;;;;;;;;;;;;;;;;;;;;;
--;
--; Module : Peers
--; Date   : 14/06/01
--;
--;;;;;;;;;;;;;;;;;;;;;;;;;;;;;;;;;;;;;;;;;;;;;;;;;;;;;;

rsCPOperationMode   OBJECT-TYPE
    SYNTAX INTEGER {
        autoConfiguration(1),
        recommendConfiguration(2)
    }
    ACCESS  read-write
    STATUS  mandatory
    DESCRIPTION
      "The mode at which the device works:
       auto     - send decided changes to router to update route-map
       suggest  - ask for user's approval of changes."
    DEFVAL { 1 }
    ::=  {rsCP 20}


--;;;;;;;;;;;;;;;;;;;;;;;;;;;;;;;;;;;;;;;;;;;;;;;;;;;;;;
--;
--; Module : Medium
--; Date   : 10/07/01
--;
--;;;;;;;;;;;;;;;;;;;;;;;;;;;;;;;;;;;;;;;;;;;;;;;;;;;;;;

rsCPUserNamePromptsTable OBJECT-TYPE
    SYNTAX SEQUENCE OF RsCPUserNamePromptEntry
    ACCESS not-accessible
    STATUS mandatory
    DESCRIPTION
      "Table containing the list of allowed user name prompts."
    ::=  {rsCP 21}

rsCPUserNamePromptEntry OBJECT-TYPE
    SYNTAX RsCPUserNamePromptEntry
    ACCESS not-accessible
    STATUS mandatory
    INDEX { rsCPUserNamePromptDispString }
    ::=  {rsCPUserNamePromptsTable 1}

RsCPUserNamePromptEntry ::= SEQUENCE {
  rsCPUserNamePromptDispString  DisplayString,
  rsCPUserNamePromptStatus      RowStatus
  }

rsCPUserNamePromptDispString  OBJECT-TYPE
    SYNTAX  DisplayString (SIZE(1..12))
    ACCESS  read-only
    STATUS  mandatory
    ::=  {rsCPUserNamePromptEntry 1}

rsCPUserNamePromptStatus OBJECT-TYPE
    SYNTAX RowStatus
    ACCESS read-write
    STATUS mandatory
    DESCRIPTION
       "This variable indicates the administrative status of this entry."
    ::=  {rsCPUserNamePromptEntry 2}




--;;;;;;;;;;;;;;;;;;;;;;;;;;;;;;;;;;;;;;;;;;;;;;;;;;;;;;
--;
--; Module : Medium
--; Date   : 10/07/01
--;
--;;;;;;;;;;;;;;;;;;;;;;;;;;;;;;;;;;;;;;;;;;;;;;;;;;;;;;

rsCPPasswordPromptsTable OBJECT-TYPE
    SYNTAX SEQUENCE OF RsCPPasswordPromptEntry
    ACCESS not-accessible
    STATUS mandatory
    DESCRIPTION
      "Table containing the list of allowed password prompts."
    ::=  {rsCP 22}

rsCPPasswordPromptEntry OBJECT-TYPE
    SYNTAX RsCPPasswordPromptEntry
    ACCESS not-accessible
    STATUS mandatory
    INDEX { rsCPPasswordPromptDispString }
    ::=  {rsCPPasswordPromptsTable 1}

RsCPPasswordPromptEntry ::= SEQUENCE {
  rsCPPasswordPromptDispString  DisplayString,
  rsCPPasswordPromptStatus      RowStatus
  }

rsCPPasswordPromptDispString  OBJECT-TYPE
    SYNTAX  DisplayString (SIZE(1..12))
    ACCESS  read-only
    STATUS  mandatory
    ::=  {rsCPPasswordPromptEntry 1}

rsCPPasswordPromptStatus OBJECT-TYPE
    SYNTAX RowStatus
    ACCESS read-write
    STATUS mandatory
    DESCRIPTION
       "This variable indicates the administrative status of this entry."
    ::=  {rsCPPasswordPromptEntry 2}



--;;;;;;;;;;;;;;;;;;;;;;;;;;;;;;;;;;;;;;;;;;;;;;;;;;;;;;
--;
--; Module : Medium
--; Date   : 12/07/01
--;
--;;;;;;;;;;;;;;;;;;;;;;;;;;;;;;;;;;;;;;;;;;;;;;;;;;;;;;

rsCPLegalStringsTable OBJECT-TYPE
    SYNTAX SEQUENCE OF RsCPLegalStringEntry
    ACCESS not-accessible
    STATUS mandatory
    DESCRIPTION
      "Table containing the list of allowed password prompts."
    ::=  {rsCP 23}

rsCPLegalStringEntry OBJECT-TYPE
    SYNTAX RsCPLegalStringEntry
    ACCESS not-accessible
    STATUS mandatory
    INDEX { rsCPLegalStringDispString }
    ::=  {rsCPLegalStringsTable 1}

RsCPLegalStringEntry ::= SEQUENCE {
  rsCPLegalStringDispString  DisplayString,
  rsCPLegalStringStatus      RowStatus
  }

rsCPLegalStringDispString  OBJECT-TYPE
    SYNTAX  DisplayString (SIZE(1..19))
    ACCESS  read-only
    STATUS  mandatory
    ::=  {rsCPLegalStringEntry 1}

rsCPLegalStringStatus OBJECT-TYPE
    SYNTAX RowStatus
    ACCESS read-write
    STATUS mandatory
    DESCRIPTION
       "This variable indicates the administrative status of this entry."
    ::=  {rsCPLegalStringEntry 2}



--;;;;;;;;;;;;;;;;;;;;;;;;;;;;;;;;;;;;;;;;;;;;;;;;;;;;;;
--;
--; Module : Medium
--; Date   : 23/07/01
--;
--;;;;;;;;;;;;;;;;;;;;;;;;;;;;;;;;;;;;;;;;;;;;;;;;;;;;;;

rsCPTerminalHostnamesTable OBJECT-TYPE
    SYNTAX SEQUENCE OF RsCPTerminalHostnameEntry
    ACCESS not-accessible
    STATUS mandatory
    DESCRIPTION
      "Table containing the list of TerminalHostnames."
    ::=  {rsCP 24}

rsCPTerminalHostnameEntry OBJECT-TYPE
    SYNTAX RsCPTerminalHostnameEntry
    ACCESS not-accessible
    STATUS mandatory
    INDEX { rsCPTerminalHostnameDispString }
    ::=  {rsCPTerminalHostnamesTable 1}

RsCPTerminalHostnameEntry ::= SEQUENCE {
  rsCPTerminalHostnameDispString  DisplayString,
  rsCPTerminalHostnameStatus      RowStatus
  }

rsCPTerminalHostnameDispString  OBJECT-TYPE
    SYNTAX  DisplayString (SIZE(1..10))
    ACCESS  read-only
    STATUS  mandatory
    ::=  {rsCPTerminalHostnameEntry 1}

rsCPTerminalHostnameStatus OBJECT-TYPE
    SYNTAX RowStatus
    ACCESS read-write
    STATUS mandatory
    DESCRIPTION
       "This variable indicates the administrative status of this entry."
    ::=  {rsCPTerminalHostnameEntry 2}

--;;;;;;;;;;;;;;;;;;;;;;;;;;;;;;;;;;;;;;;;;;;;;;;;;;;;;;
--;
--; Module : Statistics
--; Date   : 19/11/01
--;
--;;;;;;;;;;;;;;;;;;;;;;;;;;;;;;;;;;;;;;;;;;;;;;;;;;;;;;

rsCPFlowExportPort OBJECT-TYPE
    SYNTAX INTEGER(1025..65535)
    ACCESS  read-write
    STATUS  mandatory
    DESCRIPTION
      "The port flow records are exported to from the router."
    DEFVAL  { 10000 }
 ::=  {rsCP 25}



--;;;;;;;;;;;;;;;;;;;;;;;;;;;;;;;;;;;;;;;;;;;;;;;;;;;;;;
--;
--; Module : Statistics / Main
--; Date   : 21/11/01
--;
--;;;;;;;;;;;;;;;;;;;;;;;;;;;;;;;;;;;;;;;;;;;;;;;;;;;;;;

rsCPStatisticsCollectionMethod OBJECT-TYPE
    SYNTAX INTEGER {
        selfCount(1),
        flowExport(2),
		both(3)
    }
    ACCESS  read-write
    STATUS  mandatory
    DESCRIPTION
      "The method by which statistics will be collected: 
       1) count pkts either when inline or using copyport.
       2) receive flow export from the router."
    DEFVAL  { 1 }
 ::=  {rsCP 26}

rsCPMaxCIDREntriesTuning OBJECT IDENTIFIER ::= { rsCP 27}

rsCPMaxCIDREntries OBJECT-TYPE
    SYNTAX INTEGER
    ACCESS  read-only
    STATUS  mandatory
    DESCRIPTION
      "Maximal number of entries in the CIDRs table."
    ::=  { rsCPMaxCIDREntriesTuning 1 }

rsCPMaxCIDREntriesAfterReset OBJECT-TYPE
    SYNTAX INTEGER(50..300)
    ACCESS  read-write
    STATUS  mandatory
    DESCRIPTION
      "Future maximal number of entries in the CIDRs table."
    ::=  { rsCPMaxCIDREntriesTuning 2 }

rsCPMaxPeersPerRouterEntriesTuning OBJECT IDENTIFIER ::= { rsCP 28}

rsCPMaxPeersPerRouterEntries OBJECT-TYPE
    SYNTAX INTEGER
    ACCESS  read-only
    STATUS  mandatory
    DESCRIPTION
      "Maximal number of entries in the peers table."
    ::=  { rsCPMaxPeersPerRouterEntriesTuning 1 }

rsCPMaxPeersPerRouterEntriesAfterReset OBJECT-TYPE
    SYNTAX INTEGER(1..8)
    ACCESS  read-write
    STATUS  mandatory
    DESCRIPTION
      "Future maximal number of entries in the peers table."
    ::=  { rsCPMaxPeersPerRouterEntriesTuning 2 }


--;;;;;;;;;;;;;;;;;;;;;;;;;;;;;;;;;;;;;;;;;;;;;;;;;;;;;;
--;
--; Module : Main
--; Date   : 10/04/02
--;
--;;;;;;;;;;;;;;;;;;;;;;;;;;;;;;;;;;;;;;;;;;;;;;;;;;;;;;

rsCPCIDRPeerProhibitedMatchTable OBJECT-TYPE
    SYNTAX SEQUENCE OF RsCPCIDRPeerProhibitedMatchEntry
    ACCESS not-accessible
    STATUS mandatory
    DESCRIPTION
      "Table containing the list of CIDR-Peer prohibited associations."
    ::=  {rsCP 29}

rsCPCIDRPeerProhibitedMatchEntry OBJECT-TYPE
    SYNTAX RsCPCIDRPeerProhibitedMatchEntry
    ACCESS not-accessible
    STATUS mandatory
    DESCRIPTION
       " The row definition for this table."
    INDEX { rsCPCIDRPeerProhibitedMatchNeighborIP,
            rsCPCIDRPeerProhibitedMatchLocalRouterIP,
			rsCPCIDRPeerProhibitedMatchCIDRSubnet,
			rsCPCIDRPeerProhibitedMatchCIDRMask }
    ::=  {rsCPCIDRPeerProhibitedMatchTable 1}

RsCPCIDRPeerProhibitedMatchEntry ::= SEQUENCE {
  rsCPCIDRPeerProhibitedMatchNeighborIP		IpAddress,
  rsCPCIDRPeerProhibitedMatchLocalRouterIP  IpAddress,
  rsCPCIDRPeerProhibitedMatchCIDRSubnet		IpAddress,
  rsCPCIDRPeerProhibitedMatchCIDRMask		IpAddress,
  rsCPCIDRPeerProhibitedMatchDescription	DisplayString,
  rsCPCIDRPeerProhibitedMatchStatus   	    RowStatus
  }

rsCPCIDRPeerProhibitedMatchNeighborIP  OBJECT-TYPE
    SYNTAX  IpAddress
    ACCESS  read-only
    STATUS  mandatory
    DESCRIPTION
      "The Peer's neighbor's address."
    ::=  {rsCPCIDRPeerProhibitedMatchEntry 1}

rsCPCIDRPeerProhibitedMatchLocalRouterIP  OBJECT-TYPE
    SYNTAX  IpAddress
    ACCESS  read-only
    STATUS  mandatory
    DESCRIPTION
      "The Peer's local router's address."
    ::=  {rsCPCIDRPeerProhibitedMatchEntry 2}

rsCPCIDRPeerProhibitedMatchCIDRSubnet  OBJECT-TYPE
    SYNTAX  IpAddress
    ACCESS  read-only
    STATUS  mandatory
    DESCRIPTION
      "The CIDR's subnet."
    ::=  {rsCPCIDRPeerProhibitedMatchEntry 3}

rsCPCIDRPeerProhibitedMatchCIDRMask  OBJECT-TYPE
    SYNTAX  IpAddress
    ACCESS  read-only
    STATUS  mandatory
    DESCRIPTION
      "The CIDR's network mask."
    ::=  {rsCPCIDRPeerProhibitedMatchEntry 4}

rsCPCIDRPeerProhibitedMatchDescription  OBJECT-TYPE
    SYNTAX  DisplayString (SIZE(0..19))
    ACCESS  read-write
    STATUS  mandatory
    DESCRIPTION
      "The record's description."
    ::=  {rsCPCIDRPeerProhibitedMatchEntry 5}

rsCPCIDRPeerProhibitedMatchStatus OBJECT-TYPE
    SYNTAX RowStatus
    ACCESS read-write
    STATUS mandatory
    DESCRIPTION
       "This variable indicates the administrative status of this entry."
    ::=  {rsCPCIDRPeerProhibitedMatchEntry 6}


--;;;;;;;;;;;;;;;;;;;;;;;;;;;;;;;;;;;;;;;;;;;;;;;;;;;;;;
--;
--; Module : Redun
--; Date   : 22/04/02
--;
--;;;;;;;;;;;;;;;;;;;;;;;;;;;;;;;;;;;;;;;;;;;;;;;;;;;;;;

rsCPPDRedundancyStatus OBJECT-TYPE
    SYNTAX INTEGER {
        main(1),
        backup(2)
    }
    ACCESS  read-only
    STATUS  mandatory
    DESCRIPTION
      "This variable shows which of the two PD redundant devices is now acting as a PD."
    DEFVAL  { 2 }
 ::=  {rsCP 30}

--;;;;;;;;;;;;;;;;;;;;;;;;;;;;;;;;;;;;;;;;;;;;;;;;;;;;;;
--;
--; Module : Peer
--; Date   : 22/04/02
--;
--;;;;;;;;;;;;;;;;;;;;;;;;;;;;;;;;;;;;;;;;;;;;;;;;;;;;;;


rsCPPriceTable OBJECT-TYPE
    SYNTAX SEQUENCE OF RsCPPriceEntry
    ACCESS not-accessible
    STATUS  mandatory
    DESCRIPTION
      "Table containing the  price levels for a given peer"
    ::=  {rsCP 31}

rsCPPriceEntry OBJECT-TYPE
    SYNTAX RsCPPriceEntry
    ACCESS not-accessible
    STATUS  mandatory
    DESCRIPTION
       " The row definition for this table. the table containing the  price levels for a given peer.
	 	 The table's key is made of the key of the peer(local router and neighbor IP) and the upper threshold of BW 
		 for that price level. "
   INDEX {rsCPPriceNeighborIPAddress, rsCPPriceRouterLocalIPAddress, rsCPPriceThreshold }
    ::=  {rsCPPriceTable 1}

RsCPPriceEntry ::= SEQUENCE {
  rsCPPriceNeighborIPAddress	IpAddress,
  rsCPPriceRouterLocalIPAddress	IpAddress,
  rsCPPriceThreshold			INTEGER,
  rsCPPriceMethod				INTEGER,
  rsCPPriceBWUnit				INTEGER,
  rsCPPricePrice				INTEGER,
  rsCPPriceStatus				INTEGER
  }

rsCPPriceNeighborIPAddress  OBJECT-TYPE
    SYNTAX  IpAddress
    ACCESS  read-only
    STATUS  mandatory
    DESCRIPTION
      "The peer's IP address."
    ::=  {rsCPPriceEntry 1}

rsCPPriceRouterLocalIPAddress  OBJECT-TYPE
    SYNTAX  IpAddress
    ACCESS  read-only
    STATUS  mandatory
    DESCRIPTION
      "The router's local IP."
    ::=  {rsCPPriceEntry 2}

rsCPPriceThreshold OBJECT-TYPE
    SYNTAX  INTEGER 
    ACCESS  read-only
    STATUS  mandatory
    DESCRIPTION
      "The upper BW threshold of that price level in Kbps"
    ::=  {rsCPPriceEntry 3}

rsCPPriceMethod  OBJECT-TYPE
    SYNTAX INTEGER {
      absolute(1),
      perKbps(2)
    }
    ACCESS  read-write
    STATUS  mandatory
    DESCRIPTION
     "Whether the price is in Absolute price units or price units per Kbps"
-- DEFVAL {2}
 ::=  {rsCPPriceEntry 4 }

rsCPPriceBWUnit OBJECT-TYPE
    SYNTAX  INTEGER {
      tenKbps(1),
      hundredKbps(2),
	  thousandKbps(3)
    } 
    ACCESS  read-write
    STATUS  mandatory
    DESCRIPTION
      " For how many Kbps this price refer to "
-- DEFVAL {1}
    ::=  {rsCPPriceEntry 5}

rsCPPricePrice OBJECT-TYPE
    SYNTAX  INTEGER 
    ACCESS  read-write
    STATUS  mandatory
    DESCRIPTION
      "The price of this level"
    ::=  {rsCPPriceEntry 6}


rsCPPriceStatus OBJECT-TYPE
    SYNTAX INTEGER {
              active(1),
              notInService(2),
              notReady(3),
              createAndGo(4),
              createAndWait(5),
              destroy(6) }
    ACCESS read-write
    STATUS mandatory
    DESCRIPTION
       "This variable indicates the administrative status of this entry."
    ::=  {rsCPPriceEntry 7}


--;;;;;;;;;;;;;;;;;;;;;;;;;;;;;;;;;;;;;;;;;;;;;;;;;;;;;;
--;
--; Module : Peer
--; Date   : 22/04/02
--;
--;;;;;;;;;;;;;;;;;;;;;;;;;;;;;;;;;;;;;;;;;;;;;;;;;;;;;;

rsCPCostAdminStatus  OBJECT-TYPE
    SYNTAX INTEGER {
      enable(1),
      disable(2)
   }
    ACCESS  read-write
    STATUS  mandatory
    DESCRIPTION
      "Enable/Disable cost feature."
    ::=  {rsCP 32}



--;;;;;;;;;;;;;;;;;;;;;;;;;;;;;;;;;;;;;;;;;;;;;;;;;;;;;;
--;
--; Module : Peer
--; Date   : 22/04/02
--;
--;;;;;;;;;;;;;;;;;;;;;;;;;;;;;;;;;;;;;;;;;;;;;;;;;;;;;;

rsCPCostWeight  OBJECT-TYPE
   SYNTAX INTEGER (0..100)
   ACCESS  read-write
   STATUS  mandatory
   DESCRIPTION
       "The weight given to the price of the peer in the LB decision"
-- DEFVAL { 1 }
   ::=  {rsCP 33}


   --;;;;;;;;;;;;;;;;;;;;;;;;;;;;;;;;;;;;;;;;;;;;;;;;;;;;;;
--;
--; Module : Peer
--; Date   : 22/04/02
--;
--;;;;;;;;;;;;;;;;;;;;;;;;;;;;;;;;;;;;;;;;;;;;;;;;;;;;;;

rsCPLoadWeight  OBJECT-TYPE
   SYNTAX INTEGER (0..100)
   ACCESS  read-write
   STATUS  mandatory
   DESCRIPTION
       "The weight given to the load of the peer in the LB decision"
-- DEFVAL { 1 }
   ::=  {rsCP 34}

rsCPMaxPeerEntriesTuning OBJECT IDENTIFIER ::= { rsCP 35}

rsCPMaxPeerEntries OBJECT-TYPE
    SYNTAX INTEGER
    ACCESS  read-only
    STATUS  mandatory
    DESCRIPTION
      "Maximal number of entries in the Peers table."
    ::=  { rsCPMaxPeerEntriesTuning 1 }

rsCPMaxPeerEntriesAfterReset OBJECT-TYPE
    SYNTAX INTEGER(8..256)
    ACCESS  read-write
    STATUS  mandatory
    DESCRIPTION
      "Future maximal number of entries in the Peers table."
    ::=  { rsCPMaxPeerEntriesTuning 2 }

rsCPMaxPeerInfEntriesTuning OBJECT IDENTIFIER ::= { rsCP 36}

rsCPMaxPeerInfEntries OBJECT-TYPE
    SYNTAX INTEGER
    ACCESS  read-only
    STATUS  mandatory
    DESCRIPTION
      "Maximal number of entries in the Peers Inf table."
    ::=  { rsCPMaxPeerInfEntriesTuning 1 }

rsCPMaxPeerInfEntriesAfterReset OBJECT-TYPE
    SYNTAX INTEGER(16..512)
    ACCESS  read-write
    STATUS  mandatory
    DESCRIPTION
      "Future maximal number of entries in the Peers Inf table."
    ::=  { rsCPMaxPeerInfEntriesTuning 2 }

-- Application-specific traps for PeerDirector
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------

rsPDGeneralError TRAP-TYPE
         ENTERPRISE rsCP
         VARIABLES { rndErrorDesc, rndErrorSeverity }
         DESCRIPTION
             "This is a trap for all Peer Director's errors."
     ::=  1

rsPDInfoTrap TRAP-TYPE
         ENTERPRISE rsCP
         VARIABLES { rndErrorDesc, rndErrorSeverity }
     ::=  2

rsPDWarningTrap TRAP-TYPE
         ENTERPRISE rsCP
         VARIABLES { rndErrorDesc, rndErrorSeverity }
     ::=  3

rsPDErrorTrap TRAP-TYPE
         ENTERPRISE rsCP
         VARIABLES { rndErrorDesc, rndErrorSeverity }
     ::=  4

rsPDFatalErrorTrap TRAP-TYPE
         ENTERPRISE rsCP
         VARIABLES { rndErrorDesc, rndErrorSeverity }
     ::=  5


END
