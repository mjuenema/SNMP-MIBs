-- =============================================================================
-- Copyright (C) 2009 by HUAWEI TECHNOLOGIES. All rights reserved.
--    
-- Description: The MIB is designed to get HRP information. 
-- Reference: Huawei Enterprise MIB
-- Version: 1.0
-- History: 
--          V1.0 The initial version created by Cao Jiancang 00005275. 
-- =============================================================================

HUAWEI-SECURITY-HRP-MIB DEFINITIONS ::= BEGIN
 
	IMPORTS    
	        Integer32, OBJECT-TYPE            
            FROM SNMPv2-SMI

			MacAddress
			FROM SNMPv2-TC
    		
			SnmpAdminString
            FROM SNMP-FRAMEWORK-MIB
			
			enterprises			
		            FROM RFC1155-SMI; 

    hwHrp MODULE-IDENTITY 
		        LAST-UPDATED "201212141000Z"        -- December 14, 2012 at 10:00 GMT
		        ORGANIZATION 
		            "Huawei Symantec Technologies Co., Ltd."
		        CONTACT-INFO 
		            "3rd Floor,Section D, Keshi Building, No.28, Xinxi Rd., Shangdi,
		         	 Hai-Dian District Beijing P.R. China
			         Zip:100085
			         Http://www.huaweisymantec.com
                     "
		        DESCRIPTION 
		            "V1.00
			         The HRP mib is for Eudemon and USG product series."

		        ::= { hwSecurity 51 }
           
		
-- ===============================================
-- Node definitions
-- ===============================================
	    
	    -- 1.3.6.1.4.1.2011
		huawei OBJECT IDENTIFIER ::= { enterprises 2011 }
	        
		-- 1.3.6.1.4.1.2011.6
		huaweiUtility OBJECT IDENTIFIER ::= { huawei 6 }
	        
		-- 1.3.6.1.4.1.2011.6.122
		hwSecurity OBJECT IDENTIFIER ::= { huaweiUtility 122 }     
		       
		  
		hwHrpObjects OBJECT IDENTIFIER ::= { hwHrp 1 }  
		hwHrpNotification OBJECT IDENTIFIER ::= { hwHrp 2 }   
		hwHrpTrapObjects OBJECT IDENTIFIER ::= { hwHrpNotification 1 }
		hwHrpTraps OBJECT IDENTIFIER ::= { hwHrpNotification 2 }
		
-- ===============================================
-- HrpObject.
-- ===============================================
	-- 1.3.6.1.4.1.2011.6.122.51.1.1
        hwHrpLocalID OBJECT-TYPE
            SYNTAX MacAddress
            MAX-ACCESS read-only
            STATUS current
            DESCRIPTION
                "The local device ID(The mac address of ethernet interface)."
            ::= { hwHrpObjects 1 }
			
	-- 1.3.6.1.4.1.2011.6.122.51.1.2
        hwHrpPeerID OBJECT-TYPE
            SYNTAX MacAddress
            MAX-ACCESS read-only
            STATUS current
            DESCRIPTION
                "The peer device ID(The mac address of ethernet interface)."
            ::= { hwHrpObjects 2 }
        
        -- 1.3.6.1.4.1.2011.6.122.51.1.3
        hwHrpState OBJECT-TYPE
            SYNTAX SnmpAdminString
            MAX-ACCESS read-only
            STATUS current
            DESCRIPTION
                "The current state of device."
            ::= { hwHrpObjects 3 }    
			
-- ===============================================
-- TrapObject.
-- ===============================================
	
	-- 1.3.6.1.4.1.2011.6.122.51.2.1.1
 		    hwHrpTrapOldState  OBJECT-TYPE
	        	SYNTAX SnmpAdminString 
	        	MAX-ACCESS accessible-for-notify
	        	STATUS current
	        	DESCRIPTION
	            		"The old state of hrp."
	        	::= { hwHrpTrapObjects 1 }     
	
	-- 1.3.6.1.4.1.2011.6.122.51.2.1.2
 		    hwHrpTrapNewState  OBJECT-TYPE
	        	SYNTAX SnmpAdminString 
	        	MAX-ACCESS accessible-for-notify
	        	STATUS current
	        	DESCRIPTION
	            		"The new state of hrp."
	        	::= { hwHrpTrapObjects 2 }

	-- 1.3.6.1.4.1.2011.6.122.51.2.1.3
 		    hwHrpTrapLocalPriority  OBJECT-TYPE
	        	SYNTAX Integer32 
	        	MAX-ACCESS accessible-for-notify
	        	STATUS current
	        	DESCRIPTION
	            		"The local priority of hrp."
	        	::= { hwHrpTrapObjects 3 }
	
	-- 1.3.6.1.4.1.2011.6.122.51.2.1.4
 		    hwHrpTrapPeerPriority  OBJECT-TYPE
	        	SYNTAX SnmpAdminString 
	        	MAX-ACCESS accessible-for-notify
	        	STATUS current
	        	DESCRIPTION
	            		"The peer priority of hrp."
	        	::= { hwHrpTrapObjects 4 }
	

	-- 1.3.6.1.4.1.2011.6.122.51.2.1.5
 		    hwHrpTrapLocalID  OBJECT-TYPE
	        	SYNTAX MacAddress 
	        	MAX-ACCESS accessible-for-notify
	        	STATUS current
	        	DESCRIPTION
	            		"The local device ID(The mac address of ethernet interface)."
	        	::= { hwHrpTrapObjects 5 }
				
	-- 1.3.6.1.4.1.2011.6.122.51.2.1.6
 		    hwHrpTrapPeerID  OBJECT-TYPE
	        	SYNTAX MacAddress 
	        	MAX-ACCESS accessible-for-notify
	        	STATUS current
	        	DESCRIPTION
	            		"The peer device ID(The mac address of ethernet interface)."
	        	::= { hwHrpTrapObjects 6 }    	
	        
-- ===============================================
-- definition of traps.      
-- ===============================================                        
	        hwHrpStateChange NOTIFICATION-TYPE
			OBJECTS { 
				hwHrpTrapOldState,
				hwHrpTrapNewState,
				hwHrpTrapLocalPriority,
				hwHrpTrapPeerPriority
			        }
			STATUS     current
			DESCRIPTION
			    "HRP state changed."
			::= { hwHrpTraps 1}
			
	        hwHrpDeviceID NOTIFICATION-TYPE
			OBJECTS { 
				hwHrpTrapLocalID,
				hwHrpTrapPeerID
				    }
			STATUS     current
			DESCRIPTION
			    "Heartbeat status changed in dual-system hot backup."
			::= { hwHrpTraps 2}     
			
	END
