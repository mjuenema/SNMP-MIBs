-- file automatically created


TELDAT-TRAP-SNAT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


snatTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SNAT event subsystem."
    REVISION "201401200930Z"
    DESCRIPTION "Initial implementation"
        ::= { telEventTraps 186 }


snatEventsGroup	OBJECT IDENTIFIER	::= { snatTrapsMIB 1 }

snatNotifications	OBJECT IDENTIFIER	::= { snatTrapsMIB 2 }
snatNotificationsPrefix	OBJECT IDENTIFIER	::= { snatNotifications 0 }

snatEventObjects1 OBJECT-IDENTITY
    STATUS current
    DESCRIPTION
        "Event SNAT.1
        This message is generated for each packet which has passed
        NAT in."
    ::= { snatEventsGroup 1 }

snat1_source_ip_address OBJECT-TYPE
    SYNTAX IpAddress
    MAX-ACCESS accessible-for-notify
    STATUS current
    DESCRIPTION
        "Parameter 'source_ip_address' in event SNAT.1"
    ::= { snatEventObjects1 1 }

snat1_destination_ip_address OBJECT-TYPE
    SYNTAX IpAddress
    MAX-ACCESS accessible-for-notify
    STATUS current
    DESCRIPTION
        "Parameter 'destination_ip_address' in event SNAT.1"
    ::= { snatEventObjects1 2 }

snat1_source_ip_address_nat OBJECT-TYPE
    SYNTAX IpAddress
    MAX-ACCESS accessible-for-notify
    STATUS current
    DESCRIPTION
        "Parameter 'source_ip_address_nat' in event SNAT.1"
    ::= { snatEventObjects1 3 }

snat1_destination_ip_address_nat OBJECT-TYPE
    SYNTAX IpAddress
    MAX-ACCESS accessible-for-notify
    STATUS current
    DESCRIPTION
        "Parameter 'destination_ip_address_nat' in event SNAT.1"
    ::= { snatEventObjects1 4 }

snatEventObjects2 OBJECT-IDENTITY
    STATUS current
    DESCRIPTION
        "Event SNAT.2
        This message is generated for each packet which has passed
        NAT out."
    ::= { snatEventsGroup 2 }

snat2_source_ip_address OBJECT-TYPE
    SYNTAX IpAddress
    MAX-ACCESS accessible-for-notify
    STATUS current
    DESCRIPTION
        "Parameter 'source_ip_address' in event SNAT.2"
    ::= { snatEventObjects2 1 }

snat2_destination_ip_address OBJECT-TYPE
    SYNTAX IpAddress
    MAX-ACCESS accessible-for-notify
    STATUS current
    DESCRIPTION
        "Parameter 'destination_ip_address' in event SNAT.2"
    ::= { snatEventObjects2 2 }

snat2_source_ip_address_nat OBJECT-TYPE
    SYNTAX IpAddress
    MAX-ACCESS accessible-for-notify
    STATUS current
    DESCRIPTION
        "Parameter 'source_ip_address_nat' in event SNAT.2"
    ::= { snatEventObjects2 3 }

snat2_destination_ip_address_nat OBJECT-TYPE
    SYNTAX IpAddress
    MAX-ACCESS accessible-for-notify
    STATUS current
    DESCRIPTION
        "Parameter 'destination_ip_address_nat' in event SNAT.2"
    ::= { snatEventObjects2 4 }

snatEventObjects3 OBJECT-IDENTITY
    STATUS current
    DESCRIPTION
        "Event SNAT.3
        This message is generated for each packet which has no been
        NATed in."
    ::= { snatEventsGroup 3 }

snat3_source_ip_address OBJECT-TYPE
    SYNTAX IpAddress
    MAX-ACCESS accessible-for-notify
    STATUS current
    DESCRIPTION
        "Parameter 'source_ip_address' in event SNAT.3"
    ::= { snatEventObjects3 1 }

snat3_destination_ip_address OBJECT-TYPE
    SYNTAX IpAddress
    MAX-ACCESS accessible-for-notify
    STATUS current
    DESCRIPTION
        "Parameter 'destination_ip_address' in event SNAT.3"
    ::= { snatEventObjects3 2 }

snatEventObjects4 OBJECT-IDENTITY
    STATUS current
    DESCRIPTION
        "Event SNAT.4
        This message is generated for each packet which has no been
        NATed out."
    ::= { snatEventsGroup 4 }

snat4_source_ip_address OBJECT-TYPE
    SYNTAX IpAddress
    MAX-ACCESS accessible-for-notify
    STATUS current
    DESCRIPTION
        "Parameter 'source_ip_address' in event SNAT.4"
    ::= { snatEventObjects4 1 }

snat4_destination_ip_address OBJECT-TYPE
    SYNTAX IpAddress
    MAX-ACCESS accessible-for-notify
    STATUS current
    DESCRIPTION
        "Parameter 'destination_ip_address' in event SNAT.4"
    ::= { snatEventObjects4 2 }

snatEventObjects5 OBJECT-IDENTITY
    STATUS current
    DESCRIPTION
        "Event SNAT.5
        This message is generated for each unvalid SNAT rule loaded
        that is not valid."
    ::= { snatEventsGroup 5 }

snat5_rule_num OBJECT-TYPE
    SYNTAX Integer32
    MAX-ACCESS accessible-for-notify
    STATUS current
    DESCRIPTION
        "Parameter 'rule_num' in event SNAT.5"
    ::= { snatEventObjects5 1 }

snat5_reason_txt OBJECT-TYPE
    SYNTAX DisplayString
    MAX-ACCESS accessible-for-notify
    STATUS current
    DESCRIPTION
        "Parameter 'reason_txt' in event SNAT.5"
    ::= { snatEventObjects5 2 }


snatNotification1 NOTIFICATION-TYPE
    OBJECTS { 
              snat1_source_ip_address, 
              snat1_destination_ip_address,
              snat1_source_ip_address_nat,
              snat1_destination_ip_address_nat 
            }
    STATUS current
    DESCRIPTION
        "Notification of Event SNAT.1

        Message: 'NAT_IN: ($1, $2)->($3, $4)'

        Parameters list:
              $1: snat1_source_ip_address
              $2: snat1_destination_ip_address
              $3: snat1_source_ip_address_nat
              $4: snat1_destination_ip_address_nat

        This message is generated for each packet which has passed
        NAT in."
    ::= { snatNotificationsPrefix 1 }

snatNotification2 NOTIFICATION-TYPE
    OBJECTS { 
              snat2_source_ip_address, 
              snat2_destination_ip_address,
              snat2_source_ip_address_nat,
              snat2_destination_ip_address_nat 
            }
    STATUS current
    DESCRIPTION
        "Notification of Event SNAT.2

        Message: 'NAT_OUT: ($1, $2)->($3, $4)'

        Parameters list:
              $1: snat2_source_ip_address
              $2: snat2_destination_ip_address
              $3: snat2_source_ip_address_nat
              $4: snat2_destination_ip_address_nat

        This message is generated for each packet which has passed
        NAT out."
    ::= { snatNotificationsPrefix 2 }

snatNotification3 NOTIFICATION-TYPE
    OBJECTS { 
              snat3_source_ip_address, 
              snat3_destination_ip_address 
            }
    STATUS current
    DESCRIPTION
        "Notification of Event SNAT.3

        Message: 'NAT_IN: ($1, $2)-> no nat'

        Parameters list:
              $1: snat3_source_ip_address
              $2: snat3_destination_ip_address

        This message is generated for each packet which has no been
        NATed in."
    ::= { snatNotificationsPrefix 3 }

snatNotification4 NOTIFICATION-TYPE
    OBJECTS { 
              snat4_source_ip_address, 
              snat4_destination_ip_address 
            }
    STATUS current
    DESCRIPTION
        "Notification of Event SNAT.4

        Message: 'NAT_OUT: ($1, $2)-> no nat'

        Parameters list:
              $1: snat4_source_ip_address
              $2: snat4_destination_ip_address

        This message is generated for each packet which has no been
        NATed out."
    ::= { snatNotificationsPrefix 4 }

snatNotification5 NOTIFICATION-TYPE
    OBJECTS { 
              snat5_rule_num, 
              snat5_reason_txt 
            }
    STATUS current
    DESCRIPTION
        "Notification of Event SNAT.5

        Message: 'Invalid SNAT rule (#$1): $2'

        Parameters list:
              $1: snat5_rule_num
              $2: snat5_reason_txt

        This message is generated for each unvalid SNAT rule loaded
        that is not valid."
    ::= { snatNotificationsPrefix 5 }


END
