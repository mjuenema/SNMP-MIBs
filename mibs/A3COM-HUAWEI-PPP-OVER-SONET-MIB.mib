--==============================================================================
-- Copyright (C) 2004 by  HUAWEI-3COM TECHNOLOGIES. All rights reserved.
--
-- Description:Huawei-3COM POS MIB
-- Reference:HUAWEI-3COM Enterprise MIB
-- Version: V1.3
-- History:
--  V1.0 2004-10-28 created by fuzhenyu
--  V1.1 2004-12-13 add notifications(9-13) under h3cPosMIBNotifications by fuzhenyu.
--  V1.2 2005-04-12 add h3cPosFlagJ0Type, h3cPosFlagJ1Type in h3cPosParamTable by zhaotingqi.
--  V1.3 2007-07-19 add h3cPosNormalAlarm in h3cPosMIBNotifications by chenfangchun
--==============================================================================
A3COM-HUAWEI-PPP-OVER-SONET-MIB DEFINITIONS ::= BEGIN

IMPORTS
		ifIndex
	FROM RFC1213-MIB
		Counter64, OBJECT-TYPE, MODULE-IDENTITY, NOTIFICATION-TYPE
	FROM SNMPv2-SMI
		DisplayString, TruthValue
	FROM SNMPv2-TC
		h3cCommon
	FROM A3COM-HUAWEI-OID-MIB;

h3cPos MODULE-IDENTITY
	LAST-UPDATED "200707191700Z"        -- Jul 19, 2007  GMT
	ORGANIZATION
		"HUAWEI-3COM Technologies Co., Ltd."
	CONTACT-INFO
		"Platform Team HUAWEI-3COM Technologies Co., Ltd.
		 Hai-Dian District Beijing P.R. China
		 Http://www.huawei-3com.com
		 Zip:100085"
	DESCRIPTION
		"This MIB manages POS(PPP Over Sonet)interfaces by providing
		an operational table which controls parameters of each POS
		interface and reports alarm conditions.
		"
	REVISION "200707191700Z"        -- Jul 19, 2007 at 17:00 GMT
	DESCRIPTION "The initial version of this MIB module"
	::= { h3cCommon 19 }

h3cPosMIBObjects OBJECT IDENTIFIER ::= { h3cPos 1 }

h3cPosParamTable OBJECT-TYPE
	SYNTAX      SEQUENCE OF H3cPosParamTableEntry
	MAX-ACCESS  not-accessible
	STATUS      current
	DESCRIPTION
		"The pos parameter table."
	::= { h3cPosMIBObjects 1 }

h3cPosParamTableEntry OBJECT-TYPE
	SYNTAX      H3cPosParamTableEntry
	MAX-ACCESS  not-accessible
	STATUS      current
	DESCRIPTION
		""
	INDEX
		{
			ifIndex
		}
	::= { h3cPosParamTable 1 }

H3cPosParamTableEntry ::= SEQUENCE
	{
		h3cPosCRC                 INTEGER,
		h3cPosMTU                 INTEGER,
		h3cPosScramble            TruthValue,
		h3cPosClockSource         INTEGER,
		h3cPosSdhFlagJ0           DisplayString,
		h3cPosSdhFlagJ1           DisplayString,
		h3cPosSonetFlagJ0         INTEGER,
		h3cPosSonetFlagJ1         DisplayString,
		h3cPosFlagC2              INTEGER,
		h3cPosFrameType           INTEGER,
		h3cPosBindVlanId          INTEGER,
		h3cPosEncapsulation       INTEGER,
		h3cPoskeepaliveTimeout    INTEGER,
		h3cPosBERthresholdSF      INTEGER,
		h3cPosBERthresholdSD      INTEGER,
		h3cPosB1Error             Counter64,
		h3cPosB2Error             Counter64,
		h3cPosB3Error             Counter64,
		h3cPosM1Error             Counter64,
		h3cPosG1Error             Counter64,
		h3cPosFlagJ0Type          INTEGER,
		h3cPosFlagJ1Type          INTEGER
	}

h3cPosCRC OBJECT-TYPE
	SYNTAX      INTEGER{crc32(1),crc16(2)}
	MAX-ACCESS  read-write
	STATUS      current
	DESCRIPTION
		"The length of CRC"
	DEFVAL { crc32 }
	::= { h3cPosParamTableEntry 1 }

h3cPosMTU OBJECT-TYPE
	SYNTAX      INTEGER(64..9192)
	MAX-ACCESS  read-write
	STATUS      current
	DESCRIPTION
		"Maximum Transfer Unit (MTU) of POS interface"
	::= { h3cPosParamTableEntry 2 }

h3cPosScramble OBJECT-TYPE
	SYNTAX      TruthValue
	MAX-ACCESS  read-write
	STATUS      current
	DESCRIPTION
		"Scrambling is used to avoid continuous 0 or 1 in signals. This
		object is to decide whether to scramble or not"
	DEFVAL { true }
	::= { h3cPosParamTableEntry 3 }

h3cPosClockSource OBJECT-TYPE
	SYNTAX      INTEGER{system(1),line(2)}
	MAX-ACCESS  read-write
	STATUS      current
	DESCRIPTION
		"The value indicates the source of clock signal. System indicates
		that clock signals are from device itself and line for clock signals
		from remote"
	DEFVAL { line }
	::= { h3cPosParamTableEntry 4 }

h3cPosSdhFlagJ0 OBJECT-TYPE
	SYNTAX      DisplayString(SIZE(1..15))
	MAX-ACCESS  read-write
	STATUS      current
	DESCRIPTION
		"The section trace byte. This node is used when the frame type is sdh."
	::= { h3cPosParamTableEntry 5 }

h3cPosSdhFlagJ1 OBJECT-TYPE
	SYNTAX      DisplayString(SIZE(1..15))
	MAX-ACCESS  read-write
	STATUS      current
	DESCRIPTION
		"The path trace byte. This node is used when the frame type is sdh."
	::= { h3cPosParamTableEntry 6 }

h3cPosSonetFlagJ0 OBJECT-TYPE
	SYNTAX      INTEGER(0..127)
	MAX-ACCESS  read-write
	STATUS      current
	DESCRIPTION
		"The section trace byte. This node is used when the frame type is sonet."
	::= { h3cPosParamTableEntry 7 }

h3cPosSonetFlagJ1 OBJECT-TYPE
	SYNTAX      DisplayString(SIZE(1..63))
	MAX-ACCESS  read-write
	STATUS      current
	DESCRIPTION
		"The path trace byte. This node is used when the frame type is sonet."
	::= { h3cPosParamTableEntry 8 }


h3cPosFlagC2 OBJECT-TYPE
	SYNTAX      INTEGER(0..255)
	MAX-ACCESS  read-write
	STATUS      current
	DESCRIPTION
		"The parameter for the channel signal value of C2 byte"
	DEFVAL { 22 }
	::= { h3cPosParamTableEntry 9 }

h3cPosFrameType OBJECT-TYPE
	SYNTAX      INTEGER{sdh(1),sonet(2)}
	MAX-ACCESS  read-write
	STATUS      current
	DESCRIPTION
		"The frame type that encapsulates the packet. Default frame type is
		sdh(Synchronous Digital Hierarchy) It also can be configured using
		sonet type(Synchronous Optical Network)."
	DEFVAL      { sdh }
	::= { h3cPosParamTableEntry 10 }

h3cPosBindVlanId OBJECT-TYPE
	SYNTAX      INTEGER(0..4095)
	MAX-ACCESS  read-write
	STATUS      current
	DESCRIPTION
		"The vlan that this pos port binds. The vlan can not include any other
		port, otherwise error will be returned. If the vlan has a virtual
		interface, the status of virtual interface will be up or down according
		to the link status or this pos."
	::= { h3cPosParamTableEntry 11 }

h3cPosEncapsulation OBJECT-TYPE
	SYNTAX      INTEGER{ppp(1),hdlc(2)}
	MAX-ACCESS  read-write
	STATUS      current
	DESCRIPTION
		"The type of encapsulation "
	DEFVAL      { ppp }
	::= { h3cPosParamTableEntry 12 }

h3cPoskeepaliveTimeout OBJECT-TYPE
	SYNTAX      INTEGER(0..32767)
	MAX-ACCESS  read-write
	STATUS      current
	DESCRIPTION
		"The keeplive of hdlc. It is the query interval of link status. Two
		members of a link should have same keeplive. The default 0 prohibits
		detecting status of link."
	::= { h3cPosParamTableEntry 13 }

h3cPosBERthresholdSF OBJECT-TYPE
	SYNTAX      INTEGER(3..9)
	MAX-ACCESS  read-write
	STATUS      current
	DESCRIPTION
		"The bit-error rate threshold for Signal Fault. SF threshold should
		be greater than SD threshold."
	DEFVAL      { 3 }
	::= { h3cPosParamTableEntry 14 }

h3cPosBERthresholdSD OBJECT-TYPE
	SYNTAX      INTEGER(3..9)
	MAX-ACCESS  read-write
	STATUS      current
	DESCRIPTION
		"The bit-error rate threshold for Signal Degrade. SD threshold should
		be less than SF threshold."
	DEFVAL      { 6 }
	::= { h3cPosParamTableEntry 15 }

h3cPosB1Error OBJECT-TYPE
	SYNTAX      Counter64
	MAX-ACCESS  read-only
	STATUS      current
	DESCRIPTION
		"Counter for SBIPE(Section Bit Interleave Parity Error)"
	::= { h3cPosParamTableEntry 16 }

h3cPosB2Error OBJECT-TYPE
	SYNTAX      Counter64
	MAX-ACCESS  read-only
	STATUS      current
	DESCRIPTION
		"Counter for LBIPE(Line Bit Interleave Parity Error)"
	::= { h3cPosParamTableEntry 17 }

h3cPosB3Error OBJECT-TYPE
	SYNTAX      Counter64
	MAX-ACCESS  read-only
	STATUS      current
	DESCRIPTION
		"Counter for PBIPE(Path Bit Interleave Parity Error)"
	::= { h3cPosParamTableEntry 18 }

h3cPosM1Error OBJECT-TYPE
	SYNTAX      Counter64
	MAX-ACCESS  read-only
	STATUS      current
	DESCRIPTION
		"How many times does LREI(Line Remote Error Indication) occur"
	::= { h3cPosParamTableEntry 19 }

h3cPosG1Error OBJECT-TYPE
	SYNTAX      Counter64
	MAX-ACCESS  read-only
	STATUS      current
	DESCRIPTION
		"How many times does PREI(Path Remote Error Indication) occur"
	::= { h3cPosParamTableEntry 20 }

h3cPosFlagJ0Type OBJECT-TYPE
	SYNTAX      INTEGER{sdh(1),sonet(2)}
	MAX-ACCESS  read-write
	STATUS      current
	DESCRIPTION
		"The frame type that encapsulates the flag J0. Default frame type is
		sdh(Synchronous Digital Hierarchy). It also can be configured using
		sonet(Synchronous Optical Network) type."
	DEFVAL      { sdh }
	::= { h3cPosParamTableEntry 21 }

h3cPosFlagJ1Type OBJECT-TYPE
	SYNTAX      INTEGER{sdh(1),sonet(2)}
	MAX-ACCESS  read-write
	STATUS      current
	DESCRIPTION
		"The frame type that encapsulates the flag J1. Default frame type is
		sdh(Synchronous Digital Hierarchy). It also can be configured using
		sonet(Synchronous Optical Network) type."
	DEFVAL      { sdh }
	::= { h3cPosParamTableEntry 22 }

h3cPosMIBNotificationsPrefix OBJECT IDENTIFIER ::= { h3cPos 2 }
h3cPosMIBNotifications OBJECT IDENTIFIER ::= { h3cPosMIBNotificationsPrefix 0 }

h3cPosLOSAlarm NOTIFICATION-TYPE
	OBJECTS
		{
			ifIndex
		}
	STATUS      current
	DESCRIPTION
		"This alarm indicates loss of signal."
	::= { h3cPosMIBNotifications 1 }

h3cPosLOFAlarm NOTIFICATION-TYPE
	OBJECTS
		{
			ifIndex
		}
	STATUS      current
	DESCRIPTION
		"This alarm indicates loss of frame."
	::= { h3cPosMIBNotifications 2 }

h3cPosOOFAlarm NOTIFICATION-TYPE
	OBJECTS
		{
			ifIndex
		}
	STATUS      current
	DESCRIPTION
		"This alarm indicates out of frame."
	::= { h3cPosMIBNotifications 3 }

h3cPosLAISAlarm NOTIFICATION-TYPE
	OBJECTS
		{
			ifIndex
		}
	STATUS      current
	DESCRIPTION
		"This alarm is generated when LAIS(Line  Alarm  Indication  Signal) arrives."
	::= { h3cPosMIBNotifications 4 }

h3cPosLRDIAlarm NOTIFICATION-TYPE
	OBJECTS
		{
			ifIndex
		}
	STATUS      current
	DESCRIPTION
		"This alarm is generated when LRDI(Line  Remote  Defect  Indication) arrives."
	::= { h3cPosMIBNotifications 5 }

h3cPosPRDIAlarm NOTIFICATION-TYPE
	OBJECTS
		{
			ifIndex
		}
	STATUS      current
	DESCRIPTION
		"This alarm is generated when PRDI(Path  Remote  Defect  Indication) arrives."
	::= { h3cPosMIBNotifications 6 }

h3cPosPAISAlarm NOTIFICATION-TYPE
	OBJECTS
		{
			ifIndex
		}
	STATUS      current
	DESCRIPTION
		"This alarm is generated when PAIS(Path  Alarm  Indication  Signal) arrives."
	::= { h3cPosMIBNotifications 7 }

h3cPosLOPAlarm NOTIFICATION-TYPE
	OBJECTS
		{
			ifIndex
		}
	STATUS      current
	DESCRIPTION
		"This alarm indicates loss of pointer."
	::= { h3cPosMIBNotifications 8 }

h3cPosSTIMAlarm NOTIFICATION-TYPE
	OBJECTS
		{
			ifIndex
		}
	STATUS      current
	DESCRIPTION
		"This alarm indicates inconsistency between sent and received J0 bytes."
	::= { h3cPosMIBNotifications 9 }

h3cPosPTIMAlarm NOTIFICATION-TYPE
	OBJECTS
		{
			ifIndex
		}
	STATUS      current
	DESCRIPTION
		"This alarm indicates inconsistency between sent and received J1 bytes."
	::= { h3cPosMIBNotifications 10 }

h3cPosPSLMAlarm NOTIFICATION-TYPE
	OBJECTS
		{
			ifIndex
		}
	STATUS      current
	DESCRIPTION
		"This Alarm indicates a mismatched C2 byte."
	::= { h3cPosMIBNotifications 11 }

h3cPosLSDAlarm NOTIFICATION-TYPE
	OBJECTS
		{
			ifIndex
		}
	STATUS      current
	DESCRIPTION
		"This alarm indicates that the B2 bit-error rate exceeds SD threshold."
	::= { h3cPosMIBNotifications 12 }

h3cPosLSFAlarm NOTIFICATION-TYPE
	OBJECTS
		{
			ifIndex
		}
	STATUS      current
	DESCRIPTION
		"This alarm indicates that the B2 bit-error rate exceeds SF threshold."
	::= { h3cPosMIBNotifications 13 }

h3cPosNormalAlarm NOTIFICATION-TYPE
	OBJECTS
		{
			ifIndex
		}
	STATUS      current
	DESCRIPTION
		"This alarm indicates that the Pos interface state returns normal."
	::= { h3cPosMIBNotifications 14 }

END
