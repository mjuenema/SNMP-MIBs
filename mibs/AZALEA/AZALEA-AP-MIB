-- *****************************************************************
--
-- Copyright (c) 2009 - 2010 by Azalea Networks, Inc.
-- All rights reserved.
--
-- Description: Azalea AP MIB file
-- *****************************************************************

AZALEA-AP-MIB DEFINITIONS ::= BEGIN

IMPORTS
    MODULE-IDENTITY, OBJECT-TYPE, NOTIFICATION-TYPE,
    enterprises,Integer32,Counter32,Gauge32,Unsigned32,
    TimeTicks,IpAddress
                                    FROM SNMPv2-SMI
    DisplayString,RowStatus,TruthValue,MacAddress,TEXTUAL-CONVENTION
				     FROM SNMPv2-TC
    
    ifIndex,ifPhysAddress,ifAdminStatus,ifOperStatus FROM RFC1213-MIB

    IANAifType                          FROM IANAifType-MIB;

    
    
azalea OBJECT IDENTIFIER ::= { enterprises 23631 }

azaleaDevice OBJECT IDENTIFIER ::= { azalea 1 }   

azaleaMgmt OBJECT IDENTIFIER ::= { azalea 4 }

azaleaAlarmInfoGroup OBJECT IDENTIFIER ::= { azalea 100 }

azaleaRefMib    OBJECT IDENTIFIER ::= { azaleaMgmt 9 }

basicSysInfoGroup        OBJECT IDENTIFIER ::= { azaleaRefMib 2 }

sysCountryRegion OBJECT-TYPE
	SYNTAX INTEGER
		{
		australia(36),
		austria(40),
		canada(124),
		china(156),
		taiwan(158),
		denmark(208),
		finland(246),
		france(250),
		germany(276),
		hongkong(344),
		iceland(352),
		ireland(372),
		italy(380),
		japan(392),
		liechtenstein(438),
		luxembourg(442),
		netherlands(528),
		newzealand(554),
		norway(578),
		portugal(620),
		russia(643),
		singapore(702),
		spain(724),
		sweden(752),
		switzerland(756),
		unitedkingdom(826),
		unitedstates(840)
		}
	MAX-ACCESS read-only
	STATUS current
	DESCRIPTION
			"The country/region of wireless domain."
    ::= { basicSysInfoGroup 1 } 

sysGetIpWay    OBJECT-TYPE
        SYNTAX INTEGER{static(0),dhcp(1)}
        MAX-ACCESS      read-only
        STATUS current
        DESCRIPTION
        "Represents how the Ap get Ip address."
    ::= { basicSysInfoGroup 2 } 

--sysGatewayAddress OBJECT-TYPE
--    SYNTAX      IpAddress
--    MAX-ACCESS  read-write
--    STATUS      current
--    DESCRIPTION
--        "The IP address of the gateway currently used by the system"
--    ::= { basicSysInfoGroup 3 } 
--
--sysConfigBSSIDNum OBJECT-TYPE
--                        SYNTAX Integer32 (0..32)
--                        MAX-ACCESS read-only
--                        STATUS current
--                        DESCRIPTION
--                                "The field indicates the number of AP's SSID."
--    ::= { basicSysInfoGroup 4 } 
--
--sysNumStations OBJECT-TYPE
--        SYNTAX Integer32
--        MAX-ACCESS read-only
--        STATUS current
--        DESCRIPTION
--        "THE USER NUM ON THE AP"
--    ::= { basicSysInfoGroup 5 } 

--  not supported
--sysBridgeMode OBJECT-TYPE
--                SYNTAX INTEGER{normal(1),bridge(2),semiBridge(3)}
--                MAX-ACCESS read-only
--                STATUS current
--                DESCRIPTION
--                        "Bridge Mode of the device."
--    ::= { basicSysInfoGroup 6 } 

sysStoredSoftwareVersion OBJECT-TYPE
        SYNTAX      DisplayString
        MAX-ACCESS  read-only
        STATUS      current
        DESCRIPTION
            "The software version of the image stored in flash"
        ::= { basicSysInfoGroup 10 }

sysIpAddress OBJECT-TYPE
        SYNTAX      IpAddress
        MAX-ACCESS  read-only
        STATUS      current
        DESCRIPTION
            "The management IP of the device"
        ::= { basicSysInfoGroup 11 }

--  not supported
--advancedSysInfoGroup        OBJECT IDENTIFIER ::= { azaleaRefMib 3 }
--
--sysAntiDosAttackStatus	OBJECT-TYPE	
--	SYNTAX			INTEGER {
--	    on(1),
--	    off(2)
--	}
--	MAX-ACCESS		read-only
--	STATUS			current
--	DESCRIPTION		"Current state of Anti DOS Attack feature"
--	::=  {  advancedSysInfoGroup  1  } 

--sysFramesRxMgmt OBJECT-TYPE
--   SYNTAX Counter32
--   MAX-ACCESS read-only
--   STATUS current
--   DESCRIPTION ""
--	::=  {  advancedSysInfoGroup  2  } 
--
--sysFramesTxMgmt OBJECT-TYPE
--   SYNTAX Counter32
--   MAX-ACCESS read-only
--   STATUS current
--   DESCRIPTION
--   ""
--	::=  {  advancedSysInfoGroup  3  } 

--  not supported
--sysWireInPackets OBJECT-TYPE
--   SYNTAX Counter32
--   MAX-ACCESS read-only
--   STATUS current
--   DESCRIPTION
--   ""
--	::=  {  advancedSysInfoGroup  4  } 
--
--sysWireOutPackets OBJECT-TYPE
--   SYNTAX Counter32
--   MAX-ACCESS read-only
--   STATUS current
--   DESCRIPTION
--   ""
--	::=  {  advancedSysInfoGroup  5  } 

--sysPerfmanceSampleInterval OBJECT-TYPE
--   SYNTAX INTEGER(1..3600)
--   MAX-ACCESS read-write
--   STATUS current
--   DESCRIPTION
--   ""
--	::=  {  advancedSysInfoGroup  6  } 

--sysSuccAssocDelta OBJECT-TYPE
--   SYNTAX Integer32
--   MAX-ACCESS read-only
--   STATUS current
--   DESCRIPTION
--   ""
--	::=  {  advancedSysInfoGroup  7  } 

--*********************************************************************
--    Major sections
--*********************************************************************

    agentInfoGroup          OBJECT IDENTIFIER ::= { azaleaDevice 1 }
    agentConfigGroup        OBJECT IDENTIFIER ::= { azaleaDevice 2 }
    -- agentSystemGroup        OBJECT IDENTIFIER ::= { azaleaDevice 3 }
    -- stats                   OBJECT IDENTIFIER ::= { azaleaDevice 4 }
    deviceTraps            OBJECT IDENTIFIER ::= { azaleaDevice 50 }


--*****************************************************************
-- agentInventoryGroup
--
--*****************************************************************

    agentInventoryGroup        OBJECT IDENTIFIER ::= { agentInfoGroup 1 }

    agentInventorySerialNumber OBJECT-TYPE
        SYNTAX      DisplayString
        MAX-ACCESS  read-only
        STATUS      current
        DESCRIPTION
            "Serial number of the Device, should be a 14(Azalea format) or 9(Aruba format) characters long string."
        ::= { agentInventoryGroup 4 }

    agentInventoryHardwareVersion OBJECT-TYPE
        SYNTAX      DisplayString
        MAX-ACCESS  read-only
        STATUS      current
        DESCRIPTION
            "Hardware version of the Device."
        ::= { agentInventoryGroup 5 }
                                       
    agentInventorySoftwareName OBJECT-TYPE
        SYNTAX      DisplayString
        MAX-ACCESS  read-only
        STATUS      current
        DESCRIPTION
            "Name of the device software, such as MeshOS."
        ::= { agentInventoryGroup 10 }

    agentInventorySoftwareVendorName OBJECT-TYPE
        SYNTAX      DisplayString
        MAX-ACCESS  read-only
        STATUS      current
        DESCRIPTION
            "Name of the software vendor."
        ::= { agentInventoryGroup 11 }

    agentInventoryManufacturerName OBJECT-TYPE
        SYNTAX      DisplayString
        MAX-ACCESS  read-only
        STATUS      current
        DESCRIPTION
            "Name of the device manufacturer."
        ::= { agentInventoryGroup 12 }

    agentInventoryProductName OBJECT-TYPE
        SYNTAX      DisplayString
        MAX-ACCESS  read-only
        STATUS      current
        DESCRIPTION
            "Name of the product, such as MSR1200, MSR2000, MSR4000 and MST200."
        ::= { agentInventoryGroup 13 }

    agentInventoryProductVersion OBJECT-TYPE
        SYNTAX      DisplayString
        MAX-ACCESS  read-only
        STATUS      current
        DESCRIPTION
            "Version of the product, such as 4.4.0.0 ."
        ::= { agentInventoryGroup 14 }

    agentInventoryMainBoardName OBJECT-TYPE
        SYNTAX      DisplayString
        MAX-ACCESS  read-only
        STATUS      current
        DESCRIPTION
            "Main board name of the product."
        ::= { agentInventoryGroup 21 }

    agentInventoryPowerType OBJECT-TYPE
        SYNTAX    DisplayString
        MAX-ACCESS  read-only
        STATUS      current
        DESCRIPTION
            "Power type of the product, such as PoE, AC and DC."
        ::= { agentInventoryGroup 22 }

    agentInventoryFlashNumber OBJECT-TYPE
        SYNTAX      INTEGER
        MAX-ACCESS  read-only
        STATUS      current
        DESCRIPTION
            "Flash chip number of the product."
        ::= { agentInventoryGroup 23 }

    agentInventoryFlashTotalMB OBJECT-TYPE
        SYNTAX      INTEGER
        MAX-ACCESS  read-only
        STATUS      current
        DESCRIPTION
            "Total flash size of the product in MB."
        ::= { agentInventoryGroup 24 }

    agentInventoryRadioNumber OBJECT-TYPE
        SYNTAX      INTEGER
        MAX-ACCESS  read-only
        STATUS      current
        DESCRIPTION
            "The radio number of the product."
        ::= { agentInventoryGroup 32 }

    agentInventoryManufactureDate OBJECT-TYPE
        SYNTAX      DisplayString
        MAX-ACCESS  read-only
        STATUS      current
        DESCRIPTION
            "Manufacture Date of the product, the format is YYYY-MM-DD."
        ::= { agentInventoryGroup 31 }


    agentDeviceInfoGroup        OBJECT IDENTIFIER ::= { agentInfoGroup 10 }

    agentNodeRole OBJECT-TYPE
        SYNTAX      INTEGER  {
            nonMeshAp(1),
            meshAp(2),
            meshGateway(3)
        }
        MAX-ACCESS  read-only
        STATUS      current
        DESCRIPTION
            "Role of the device."
        ::= { agentDeviceInfoGroup 1 }

    agentNodeForwardMode OBJECT-TYPE
        SYNTAX      INTEGER  {
            layer2(1),
            layer3(2)
        }
        MAX-ACCESS  read-only
        STATUS      current
        DESCRIPTION
            "Forwarding mode."
        ::= { agentDeviceInfoGroup 2 }

    agentNodeMeshEnabled OBJECT-TYPE
        SYNTAX      TruthValue
        MAX-ACCESS  read-only
        STATUS      current
        DESCRIPTION
            "Whether mesh is enabled."
        ::= { agentDeviceInfoGroup 3 }

    agentSystemConfigGroup OBJECT IDENTIFIER ::= { agentConfigGroup 2 }

    agentSystemName OBJECT-TYPE	
        SYNTAX        DisplayString (SIZE(0..32))
        MAX-ACCESS    read-write
	    STATUS        current
	    DESCRIPTION
	        "The device's name."
	    ::= { agentSystemConfigGroup 1 }


--*********************************************************************
-- agentInterfaceConfigGroup - Configuration of Device Interfaces
--
--*********************************************************************

     agentInterfaceConfigGroup OBJECT IDENTIFIER ::= { agentConfigGroup 10 }
     
-------------------------------------------------------
-- agentInterfaceConfigTable
-------------------------------------------------------

    agentInterfaceConfigTable OBJECT-TYPE
        SYNTAX      SEQUENCE OF AgentInterfaceConfigEntry
        MAX-ACCESS  not-accessible
        STATUS      current
        DESCRIPTION
            "A table of the device's Interface Config entries. Typically, 
            it will contain entries for Service Port Interface, DS Port 
            Interface and Virtual Gateway Interface apart from other 
            entries."
        ::= { agentInterfaceConfigGroup 1 }

    agentInterfaceConfigEntry OBJECT-TYPE
        SYNTAX      AgentInterfaceConfigEntry
        MAX-ACCESS  not-accessible
        STATUS      current
        DESCRIPTION
            "Device's Interface Config entry"
        INDEX       { ifIndex }
        ::= { agentInterfaceConfigTable 1 }

    AgentInterfaceConfigEntry ::= SEQUENCE {
        agentInterfaceName                      OCTET STRING
    }

    agentInterfaceName OBJECT-TYPE
        SYNTAX     OCTET STRING (SIZE(1..32))
        MAX-ACCESS read-only
        STATUS     current
        DESCRIPTION
            "Interace Name of the device."
        ::= { agentInterfaceConfigEntry 1 }
    

    --*****************************************************************
    -- agentDeviceConfigGroup
    --
    --*****************************************************************

    agentDeviceConfigGroup OBJECT IDENTIFIER ::= { agentConfigGroup 8 }

    agentDeviceRouterID OBJECT-TYPE
        SYNTAX      IpAddress
        MAX-ACCESS  read-only
        STATUS      current
        DESCRIPTION
            "The Router ID of this device"
        ::= { agentDeviceConfigGroup 2 }
         
--    agentSysNeID OBJECT-TYPE
--        SYNTAX      DisplayString
--        MAX-ACCESS  read-write
--        STATUS      current
--        DESCRIPTION
--            "The Network Element ID of the node"
--        ::= { agentDeviceConfigGroup 3 }
         
    agentDeviceTimeToReboot OBJECT-TYPE
        SYNTAX      INTEGER (0..3600)
        MAX-ACCESS  read-write
        STATUS      current
        DESCRIPTION
            "To reboot system set this value to an integer between 1 and 3600 and 
             the system will reboot after that many seconds.  To cancel the reboot,
             set this value to 0."
        ::= { agentDeviceConfigGroup 4 }     

    agentDeviceUpgradeStatus OBJECT-TYPE
        SYNTAX      INTEGER  { 
            upgrading(1), 
            normal(2) 
        } 
        MAX-ACCESS  read-only
        STATUS      current
        DESCRIPTION
            "The upgarde status of the device."
        ::= { agentDeviceConfigGroup 5 }     

    agentDeviceCountryCode OBJECT-TYPE
        SYNTAX      OCTET STRING (SIZE(2))
        MAX-ACCESS  read-only
        STATUS      current
        DESCRIPTION
             "This attribute identifies the country in which the device radio are operating. The country codes supported now are following :
			 AU(AUSTRALIA), CN(CHINA), EU(GERMANY), GB(UNITED_KINGDOM), IN(INDIA), JP(JAPAN1), US(UNITED_STATES), TW(TAIWAN), RU(RUSSIA), 
			SA(SAUDI_ARABIA), PH(PHILIPPINES), BD(BANGLADESH), TH(THAILAND), ID(INDONESIA), GA(GHANA), IQ(IRAQ), D1(DEBUG1), BH(BAHRAIN), 
			BR(BRAZIL), CA(CANADA), EG(EGYPT), HK(HONG_KONG), IL(ISRAEL), KR(KOREA_ROC), KW(KUWAIT), LB(LEBANON), MY(MALAYSIA), MX(MEXICO), 
			NZ(NEW_ZEALAND), OM(OMAN), QA(QATAR), SG(SINGAPORE), AE(UAE), PR(PUERTO_RICO), ZA(SOUTH_AFRICA), IE(IRELAND), CY(CYPRUS). " 
        ::= { agentDeviceConfigGroup 6 }     

    agentDeviceWriteMemory OBJECT-TYPE
        SYNTAX      INTEGER { none(0),	write(1) }
        MAX-ACCESS  read-write
        STATUS      current
        DESCRIPTION
            "The action of save device configuration to flash."
        ::= { agentDeviceConfigGroup 7 }  

    agentDeviceFactoryDefault OBJECT-TYPE
        SYNTAX      INTEGER {
        	false(0),
        	true(1)
        }
        MAX-ACCESS  read-write
        STATUS      current
        DESCRIPTION
            "If set to true, device will use factory default configuration at next reboot, 
             if set to false, device will use current configuration at next reboot."
        ::= { agentDeviceConfigGroup 8 }     

    agentDeviceHeartBeatInterval OBJECT-TYPE
        SYNTAX      INTEGER (0..3600)
        MAX-ACCESS  read-write
        STATUS      current
        DESCRIPTION
            "If set to a value between 1 to 3600, device will send azaleaHeartBeat trap
             every that many seconds;
             if set to 0, device will not send heart beat trap."
        ::= { agentDeviceConfigGroup 9 }

    agentDeviceIPMask OBJECT-TYPE
        SYNTAX      IpAddress
        MAX-ACCESS  read-only
        STATUS      current
        DESCRIPTION
            "Netmask of the device IP"
        ::= { agentDeviceConfigGroup 10 }

    agentDeviceIPType OBJECT-TYPE
        SYNTAX      INTEGER {
		none (1),
		static (2),
		dhcp (3),
		bootp (4)
		}
        MAX-ACCESS  read-only
        STATUS      current
        DESCRIPTION
            "The method that the IP of this device is obtained."
        ::= { agentDeviceConfigGroup 11 }

    agentDeviceMacAddress OBJECT-TYPE
        SYNTAX      MacAddress
        MAX-ACCESS  read-only
        STATUS      current
        DESCRIPTION
            "MAC Address of this device"
        ::= { agentDeviceConfigGroup 12 }

--    agentApSysRestart OBJECT-TYPE
--        SYNTAX      INTEGER {
--	    normal(1),
--	    restart(2)
--	}
--        MAX-ACCESS  read-write
--        STATUS      current
--        DESCRIPTION
--            "To reboot system set this value to restart. To cancel the reboot,
--             set this value to normal."
--        ::= { agentDeviceConfigGroup 20 }     

--  not support
--    agentApSysReset OBJECT-TYPE
--        SYNTAX      INTEGER {
--	    normal(1),
--	    reset(2)
--		}
--        MAX-ACCESS  read-write
--        STATUS      current
--        DESCRIPTION
--            "load default config"
--        ::= { agentDeviceConfigGroup 21 }     


--*********************************************************************
--   Traps
--*********************************************************************

      azaleaColdStartFinishTrap NOTIFICATION-TYPE
         OBJECTS    {
						agentDeviceRouterID,
                        agentInventorySerialNumber
                    }
         STATUS             current
         DESCRIPTION
             "The device cold start event trap"
         ::= { deviceTraps 201 }

      azaleaWarmRestartFinishTrap NOTIFICATION-TYPE
         OBJECTS    {
						agentDeviceRouterID,
                        agentInventorySerialNumber
                    }
         STATUS             current
         DESCRIPTION
             "The device warm start event trap"
         ::= { deviceTraps 202 }

      azaleaInterfaceLinkDownTrap NOTIFICATION-TYPE
         OBJECTS    {
                        ifIndex,
						ifAdminStatus,
						ifOperStatus
                    }
         STATUS             current
         DESCRIPTION
             "The device interface link down event trap"
         ::= { deviceTraps 203 }

      azaleaInterfaceLinkUpTrap NOTIFICATION-TYPE
         OBJECTS    {
                        ifIndex,
						ifAdminStatus,
						ifOperStatus
                    }
         STATUS             current
         DESCRIPTION
             "The device interface link up event trap"
         ::= { deviceTraps 204 }

      azaleaWDSDownTrap NOTIFICATION-TYPE
         OBJECTS    {
                        ifIndex,
						ifAdminStatus,
						ifOperStatus,
						azlDot11WdsRemoteMacAddr
                    }
         STATUS             current
         DESCRIPTION
             "The device WDS interface down event trap"
         ::= { deviceTraps 206 }

      azaleaWDSUpTrap NOTIFICATION-TYPE
         OBJECTS    {
                        ifIndex,
						ifAdminStatus,
						ifOperStatus,
						azlDot11WdsRemoteMacAddr
                    }
         STATUS             current
         DESCRIPTION
             "The device WDS interface up event trap"
         ::= { deviceTraps 207 }

      azaleaRebootTrap NOTIFICATION-TYPE
         OBJECTS    {
                        sysRebootReason
                    }
         STATUS             current
         DESCRIPTION
             "The device reboot event trap"
         ::= { deviceTraps 215 }

--        azaleaFlashWriteFailTrap NOTIFICATION-TYPE
--           STATUS             current
--           DESCRIPTION
--               "The device write flash fail trap"
--           ::= { deviceTraps 220 }

      azaleaNTPSyncFailTrap NOTIFICATION-TYPE
         STATUS             current
         DESCRIPTION
             "The device NTP client update time from NTP server fail event trap"
         ::= { deviceTraps 221 }

      azaleaSystemIPChangeTrap NOTIFICATION-TYPE
         OBJECTS    {
                        sysIpAddress
                    }
         STATUS             current
         DESCRIPTION
             "The device management IP change event trap"
         ::= { deviceTraps 225 }

      azaleaRunningImageTrap NOTIFICATION-TYPE
         OBJECTS    {
                        agentInventorySoftwareName,
						agentInventoryProductVersion,
						azlRunningPartition
                    }
         STATUS             current
         DESCRIPTION
             "The device's running image information trap, send when device boot up"
         ::= { deviceTraps 401 }

      azaleaBackupImageTrap NOTIFICATION-TYPE
         OBJECTS    {
                        agentInventorySoftwareName,
						agentInventoryProductVersion,
						azlRunningPartition
                    }
         STATUS             current
         DESCRIPTION
             "The device's running image is backup image information trap, send when device boot up and the running image is backup image"
         ::= { deviceTraps 402 }

--      azaleaAPSWUpdateFailTrap NOTIFICATION-TYPE
--         OBJECTS    {
--    			agentInventoryProductVersion
--                    }
--         STATUS             current
--         DESCRIPTION
--             "Software upgrade failure trap"
--         ::= { deviceTraps 300 }
--
--      azaleaAPMtWorkModeChgTrap NOTIFICATION-TYPE
--         OBJECTS    {
--                        agentInventorySerialNumber
--                    }
--         STATUS             current
--         DESCRIPTION
--             ""
--         ::= { deviceTraps 311 }
--
--      azaleaAttackDetectedTrap NOTIFICATION-TYPE
--         OBJECTS    {
--                        agentInventorySerialNumber
--                    }
--         STATUS             current
--         DESCRIPTION
--             ""
--         ::= { deviceTraps 312 }
--
--      azaleaNeighborInterferenceTrap NOTIFICATION-TYPE
--         OBJECTS    {
--                        agentInventorySerialNumber
--                    }
--         STATUS             current
--         DESCRIPTION
--             ""
--         ::= { deviceTraps 313 }
--
--      azaleaRadioFaultTrap NOTIFICATION-TYPE
--         OBJECTS    {
--                        agentInventorySerialNumber
--                    }
--         STATUS             current
--         DESCRIPTION
--             ""
--         ::= { deviceTraps 314 }
--
--      azaleaRadioFaultRecovTrap NOTIFICATION-TYPE
--         OBJECTS    {
--                        agentInventorySerialNumber
--                    }
--         STATUS             current
--         DESCRIPTION
--             ""
--         ::= { deviceTraps 315 }
--
--      azaleaWarmRestartTrap NOTIFICATION-TYPE
--         OBJECTS    {
--                        agentInventorySerialNumber
--                    }
--         STATUS             current
--         DESCRIPTION
--             ""
--         ::= { deviceTraps 316 }
--
--      azaleaColdRestartTrap NOTIFICATION-TYPE
--         OBJECTS    {
--                        agentInventorySerialNumber
--                    }
--         STATUS             current
--         DESCRIPTION
--             ""
--         ::= { deviceTraps 317 }
--
--      azaleaRogueDeviceTrap NOTIFICATION-TYPE
--         OBJECTS    {
--                        agentInventorySerialNumber
--                    }
--         STATUS             current
--         DESCRIPTION
--             ""
--         ::= { deviceTraps 318 }
--
--      azaleaConfigModifiedTrap NOTIFICATION-TYPE
--         OBJECTS    {
--                        agentInventorySerialNumber
--                    }
--         STATUS             current
--         DESCRIPTION
--             ""
--         ::= { deviceTraps 319 }

agentProductName	OBJECT-TYPE	
		SYNTAX			DisplayString
		MAX-ACCESS		read-only
		STATUS			current
		DESCRIPTION		"The product name of this device"
		::=  {  azaleaDevice 51  }        


--*****************************************************************
-- azaleaSysMgmt
--
--*****************************************************************

azaleaSysMgmt    OBJECT IDENTIFIER ::= { azaleaMgmt 2 }

sysRebootTimes  OBJECT-TYPE
    SYNTAX      Counter32
    MAX-ACCESS  read-only
    STATUS      current
    DESCRIPTION
        "The number of times that the system has rebooted."
    ::= { azaleaSysMgmt 1 } 

sysRebootReason OBJECT-TYPE
    SYNTAX      INTEGER {
        unknown (1),
        crash   (2),
        powerOff(3),
        normal  (4),
        lostGateway(5)
    }
    MAX-ACCESS  read-only
    STATUS  current
    DESCRIPTION 
        "This node specifies the reason of last reboot.
        unknown (1): Can not tell what causes reboot
        crash   (2): Software crash
        powerOff(3): Power off then reboot
        normal  (4): Normal reboot"
    ::= { azaleaSysMgmt 2 } 

sysUpTime OBJECT-TYPE
    SYNTAX      TimeTicks
    MAX-ACCESS  read-only
    STATUS      current
    DESCRIPTION
        "The time (in hundredths of a second) since the system was last
        re-boot."
    ::= { azaleaSysMgmt 3 }    

azaleaSysCpuMgmt OBJECT IDENTIFIER ::= { azaleaSysMgmt 4 }   
sysCpuLoadPercentage	OBJECT-TYPE	
		SYNTAX			INTEGER (0..100)
		MAX-ACCESS		read-only
		STATUS			current
		DESCRIPTION		"The percentage of Cpu Usage"
		::=  {  azaleaSysCpuMgmt  1  }    
sysCpuType	OBJECT-TYPE	
		SYNTAX			DisplayString
		MAX-ACCESS		read-only
		STATUS			current
		DESCRIPTION		"The name CPU type"
		::=  {  azaleaSysCpuMgmt  2  }

sysCpuSpeed	OBJECT-TYPE	
		SYNTAX			DisplayString
		MAX-ACCESS		read-only
		STATUS			current
		DESCRIPTION		"The CPU Speed String"
		::=  {  azaleaSysCpuMgmt  3  }

--sysCpuUsageThreshhd	OBJECT-TYPE	
--		SYNTAX			INTEGER (0..100)
--		MAX-ACCESS		read-write
--		STATUS			current
--		DESCRIPTION		"CPU Usage Threshhold"
--		::=  {  azaleaSysCpuMgmt  4  }

sysCpuAvgUsage	OBJECT-TYPE	
		SYNTAX			INTEGER (0..100)
		MAX-ACCESS		read-only
		STATUS			current
		DESCRIPTION		"The percentage of CPU Average Usage"
		::=  {  azaleaSysCpuMgmt  5  }


azaleaSysMemoryMgmt OBJECT IDENTIFIER ::= { azaleaSysMgmt 5 }  
sysMemoryTotalKB	OBJECT-TYPE	
		SYNTAX			Integer32
		MAX-ACCESS		read-only
		STATUS			current
		DESCRIPTION		"Total Memory size in KB"
		::=  {  azaleaSysMemoryMgmt  1  }     
sysMemoryFreeKB		OBJECT-TYPE	
		SYNTAX			Integer32
		MAX-ACCESS		read-only
		STATUS			current
		DESCRIPTION		"Free Memory size in KB"
		::=  {  azaleaSysMemoryMgmt  2  }

sysMemoryUsedPercentage	OBJECT-TYPE	
		SYNTAX			INTEGER (0..100)
		MAX-ACCESS		read-only
		STATUS			current
		DESCRIPTION		"Percentage of Used Memory"
		::=  {  azaleaSysMemoryMgmt  3  }

sysMemoryType	OBJECT-TYPE	
		SYNTAX			DisplayString
		MAX-ACCESS		read-only
		STATUS			current
		DESCRIPTION		"Type of memory"
		::=  {  azaleaSysMemoryMgmt  4  }

--sysMemUsageThreshhd OBJECT-TYPE	
--		SYNTAX			INTEGER (0..100)
--		MAX-ACCESS		read-write
--		STATUS			current
--		DESCRIPTION		"Memory usage threshhold"
--		::=  {  azaleaSysMemoryMgmt  5  }

--sysMemAvgUsage OBJECT-TYPE	
--		SYNTAX			INTEGER (0..100)
--		MAX-ACCESS		read-only
--		STATUS			current
--		DESCRIPTION		"Memory average usage"
--		::=  {  azaleaSysMemoryMgmt  6  }


azaleaSysStorageMgmt OBJECT IDENTIFIER ::= { azaleaSysMgmt 6 }  

sysStorageTotalKB	OBJECT-TYPE	
		SYNTAX			Integer32
		MAX-ACCESS		read-only
		STATUS			current
		DESCRIPTION		"Total Storage size in KB"
		::=  {  azaleaSysStorageMgmt  1  }     
sysStorageFreeKB		OBJECT-TYPE	
		SYNTAX			Integer32
		MAX-ACCESS		read-only
		STATUS			current
		DESCRIPTION		"Free Storage size in KB"
		::=  {  azaleaSysStorageMgmt  2  }

sysStorageUsedPercentage	OBJECT-TYPE	
		SYNTAX			INTEGER (0..100)
		MAX-ACCESS		read-only
		STATUS			current
		DESCRIPTION		"Percentage of Used Storage"
		::=  {  azaleaSysStorageMgmt  3  }        
		
sysStorageFlashType	OBJECT-TYPE	
		SYNTAX			DisplayString
		MAX-ACCESS		read-only
		STATUS			current
		DESCRIPTION		"Storage flash type"
		::=  {  azaleaSysStorageMgmt  4  }        

azaleaSysHardwareMgmt OBJECT IDENTIFIER ::= { azaleaSysMgmt 7 }   
 
sysHardwareTemperature	OBJECT-TYPE	
		SYNTAX			Gauge32
		MAX-ACCESS		read-only
		STATUS			current
		DESCRIPTION		"Temperature of device"
		::=  {  azaleaSysHardwareMgmt  1  }   

azaleaTimeMgmt  OBJECT IDENTIFIER ::= { azaleaSysMgmt 8 }    
timeZoneOffSetFromGMT  	OBJECT-TYPE	
		SYNTAX			INTEGER(0..1440)
		MAX-ACCESS		read-only
		STATUS			current
		DESCRIPTION		"The timezone in which the device is located,
		represented as an offset from GMT in Minutes."
		::=  {  azaleaTimeMgmt  1  }         
		
azaleaUtcClock	OBJECT-TYPE
	SYNTAX		Integer32
	MAX-ACCESS		read-only
	STATUS		current
	DESCRIPTION	"Current time of clock on device, in UTC seconds (seconds since 1/1/1970 12:00am GMT)."
	REFERENCE 	"UTC Clock"
	::= { azaleaTimeMgmt 2 }


azaleaSysMgmtTrapObjects  OBJECT IDENTIFIER ::= { azaleaSysMgmt 15 }    
                                                      
azaleaSysMgmtTraps   OBJECT IDENTIFIER ::= { azaleaSysMgmtTrapObjects 1 }      

sysCpuUsageTrap     NOTIFICATION-TYPE
    OBJECTS    {
               sysCpuLoadPercentage
                   }
    STATUS  current
    DESCRIPTION
        "The trap of CPU usage reach to threshold"
::= { azaleaSysMgmtTraps 1}     

sysMemoryUsageTrap      NOTIFICATION-TYPE
    OBJECTS    {
               sysMemoryUsedPercentage
                   }
    STATUS  current
    DESCRIPTION
        "The trap of memory usage reach to threshold"
::= { azaleaSysMgmtTraps 2}


sysStorageUsageTrap      NOTIFICATION-TYPE
    OBJECTS    {
               sysStorageUsedPercentage
                   }
    STATUS  current
    DESCRIPTION
        "The trap of flash usage reach to threshold"
::= { azaleaSysMgmtTraps 3}
 
sysHarewareTemperatureTrap       NOTIFICATION-TYPE
    OBJECTS    {
               sysHardwareTemperature
                   }
    STATUS  current
    DESCRIPTION
        "The trap of temperature reach to threshold"
::= { azaleaSysMgmtTraps 4}

--sysCpuUsageTooHighTrap     NOTIFICATION-TYPE
--    OBJECTS    {
--               sysCpuLoadPercentage
--                   }
--    STATUS  current
--    DESCRIPTION
--        ""
--::= { azaleaSysMgmtTraps 10}     
--
--sysCpuUsageTooHighRecovTrap     NOTIFICATION-TYPE
--    OBJECTS    {
--               sysCpuLoadPercentage
--                   }
--    STATUS  current
--    DESCRIPTION
--        ""
--::= { azaleaSysMgmtTraps 11}     
--
--sysMemUsageTooHighTrap     NOTIFICATION-TYPE
--    OBJECTS    {
--               sysMemoryUsedPercentage
--                   }
--    STATUS  current
--    DESCRIPTION
--        ""
--::= { azaleaSysMgmtTraps 12}     

--sysMemUsageTooHighCleanTrap     NOTIFICATION-TYPE
--    OBJECTS    {
--               sysMemoryUsedPercentage
--                   }
--    STATUS  current
--    DESCRIPTION
--        ""
--::= { azaleaSysMgmtTraps 13} 
--
--sysTemperatureTooHighTrap     NOTIFICATION-TYPE
--    OBJECTS    {
--		sysHardwareTemperature
--                   }
--    STATUS  current
--    DESCRIPTION
--        ""
--::= { azaleaSysMgmtTraps 14} 
    
--sysTemperatureTooHighRecovTrap     NOTIFICATION-TYPE
--    OBJECTS    {
--		sysHardwareTemperature
--                   }
--    STATUS  current
--    DESCRIPTION
--        ""
--::= { azaleaSysMgmtTraps 15} 
    
azaleaFlashMgmtMib OBJECT IDENTIFIER ::= { azaleaMgmt 5 }
   
    
azaleaRunningInfo OBJECT IDENTIFIER ::= { azaleaFlashMgmtMib 3 }

azlRunningPartition OBJECT-TYPE
    SYNTAX      INTEGER { primary(1), backup(0) }
    MAX-ACCESS  read-only
    STATUS      current
        DESCRIPTION
            "It describes the origin of the running image"
    ::= { azaleaRunningInfo 1 }
    
azlRunningVersion OBJECT-TYPE
    SYNTAX      OCTET STRING(SIZE(56))
    MAX-ACCESS  read-only
    STATUS      current
    DESCRIPTION
        "It describes the version of the running image"
    ::= { azaleaRunningInfo 2 }

azlRunningCreateTime OBJECT-TYPE
    SYNTAX      OCTET STRING
    MAX-ACCESS  read-only
    STATUS      current
    DESCRIPTION
        "It describes the create time of the running image"
    ::= { azaleaRunningInfo 3 }

azlRunningType OBJECT-TYPE
    SYNTAX      OCTET STRING
    MAX-ACCESS  read-only
    STATUS      current
    DESCRIPTION
        "see the definition of azlPartitionType"
    ::= { azaleaRunningInfo 4 }

--  not supported	
--  azlRunningNextPartition OBJECT-TYPE
--      SYNTAX        Integer32
--      MAX-ACCESS    read-write
--      STATUS        current
--      DESCRIPTION
--          "It describes the next boot partition "
--      ::= { azaleaRunningInfo 5 }

azlBootLoaderName OBJECT-TYPE
    SYNTAX      OCTET STRING
    MAX-ACCESS  read-only
    STATUS      current
    DESCRIPTION
        "Boot loader name of the product, such as RedBoot ver x.x.x and APBoot ver x.x.x.x"
    ::= { azaleaRunningInfo 11 }

azaleaIfMib OBJECT IDENTIFIER ::= { azaleaMgmt 4 }

azaleaIfTable OBJECT-TYPE
	SYNTAX      SEQUENCE OF AzaleaIfEntry
	MAX-ACCESS  not-accessible
	STATUS      current
	DESCRIPTION
		"A list of interface entries.  The number of entries
		is given by the value of azlIfNumber"
	::= { azaleaIfMib 2 }

azaleaIfEntry OBJECT-TYPE
	SYNTAX      AzaleaIfEntry
	MAX-ACCESS  not-accessible
	STATUS      current
	DESCRIPTION
		"An entry containing management information applicable
		to a particular interface."
	INDEX       { ifIndex }
	::= { azaleaIfTable 1 }

AzaleaIfEntry ::= SEQUENCE {
	azlIfName          OCTET STRING,
	azlIfType          INTEGER,
	azlIfPhysAddress   MacAddress,

	azlIfIpAddress     IpAddress,
	azlIfIpMask        IpAddress,

	azlIfMtu           Integer32,
	azlIfAdminStatus   INTEGER,
	azlIfOperStatus    INTEGER,

	azlIfTxRate        Integer32,
	azlIfRxRate        Integer32,

	azlIfTotalUpDown   Counter32,
	azlIfDescription   DisplayString,
--	azlIfTimeSinceLastChange TimeTicks,
	azlIfTxRateKb        Counter32,
	azlIfRxRateKb        Counter32
}

azlIfName OBJECT-TYPE
	SYNTAX      OCTET STRING
	MAX-ACCESS  read-only
	STATUS      current
	DESCRIPTION
		"It provides the name of the interface."
	::= { azaleaIfEntry 1 }

azlIfType OBJECT-TYPE
	SYNTAX      INTEGER { ether(1), dot11radio(2), dot11wds(3) }
	MAX-ACCESS  read-only
	STATUS      current
	DESCRIPTION
		"It describles the type of interface, It provides three
		values:

		ether(1):      ethernet interface
		dot11radio(2): a 802.11 radio interface
		dot11wds(3):   a WDS(Wireless Distrution System)
		               interface on 802.11 radio."
	::= { azaleaIfEntry 2 }

azlIfPhysAddress OBJECT-TYPE
	SYNTAX      MacAddress
	MAX-ACCESS  read-only
	STATUS      current
	DESCRIPTION
		"It describles the mac address of interface."
	::= { azaleaIfEntry 3 }


azlIfIpAddress OBJECT-TYPE
	SYNTAX      IpAddress
	MAX-ACCESS  read-only
	STATUS      current
	DESCRIPTION
		"The IP address to which this entry's addressing
		information pertains."
	::= { azaleaIfEntry 5 }

azlIfIpMask OBJECT-TYPE
	SYNTAX      IpAddress
	MAX-ACCESS  read-only
	STATUS      current
	DESCRIPTION
		"The subnet mask associated with the IP address of
		this entry.  The value of the mask is an IP
		address with all the network bits set to 1 and all
		the hosts bits set to 0."
	::= { azaleaIfEntry 6 }

azlIfMtu OBJECT-TYPE
	SYNTAX      Integer32
	MAX-ACCESS  read-only
	STATUS      current
	DESCRIPTION
		"The size of the largest packet which can be
		sent/received on the interface, specified in octets.
		For interfaces that are used for transmitting network
		datagrams, this is the size of the largest network
		datagram that can be sent on the interface."
	::= { azaleaIfEntry 7 }

azlIfAdminStatus OBJECT-TYPE
	SYNTAX      INTEGER { enable(1), disable(2) }
	MAX-ACCESS  read-only
	STATUS      current
	DESCRIPTION
		"The desired state of the interface."
	::= { azaleaIfEntry 8 }

azlIfOperStatus OBJECT-TYPE
	SYNTAX      INTEGER { up(1), down(2) }
	MAX-ACCESS  read-only
	STATUS      current
	DESCRIPTION
		"The current operational state of the interface."
	::= { azaleaIfEntry 9 }

azlIfTxRate OBJECT-TYPE
	SYNTAX      Integer32
	MAX-ACCESS  read-only
	STATUS      current
	DESCRIPTION
		"It describles the TxRate of the interface"
	::= { azaleaIfEntry 12 }

azlIfRxRate OBJECT-TYPE
	SYNTAX      Integer32
	MAX-ACCESS  read-only
	STATUS      current
	DESCRIPTION
		"It describles the RxRate of the interface"
	::= { azaleaIfEntry 13 }

azlIfTotalUpDown  OBJECT-TYPE
	SYNTAX      Counter32
	MAX-ACCESS  read-only
	STATUS      current
	DESCRIPTION
		"It describles the up/down times of the interface"
	::= { azaleaIfEntry 14 }

azlIfDescription OBJECT-TYPE
        SYNTAX      DisplayString
        MAX-ACCESS  read-only
        STATUS      current
        DESCRIPTION
                "The description of this interface."
        ::= { azaleaIfEntry 17 }

--azlIfTimeSinceLastChange OBJECT-TYPE
--        SYNTAX      TimeTicks
--        MAX-ACCESS  read-only
--        STATUS      current
--        DESCRIPTION
--                "Amount of time interface has spent since last change into the current state"
--        ::= { azaleaIfEntry 50 }

azlIfTxRateKb OBJECT-TYPE
	SYNTAX      Counter32
	MAX-ACCESS  read-only
	STATUS      current
	DESCRIPTION
		"It describles the TxRate of the interface"
	::= { azaleaIfEntry 60 }

azlIfRxRateKb OBJECT-TYPE
	SYNTAX      Counter32
	MAX-ACCESS  read-only
	STATUS      current
	DESCRIPTION
		"It describles the RxRate of the interface"
	::= { azaleaIfEntry 61 }

azaleaIfDot11Table OBJECT-TYPE
	SYNTAX      SEQUENCE OF AzaleaIfDot11Entry
	MAX-ACCESS  not-accessible
	STATUS      current
	DESCRIPTION
		"A list of 802.11 radio interface entries"
	::= { azaleaIfMib 3 }

azaleaIfDot11Entry OBJECT-TYPE
	SYNTAX      AzaleaIfDot11Entry
	MAX-ACCESS  not-accessible
	STATUS      current
        DESCRIPTION
        	"An entry containing management information applicable
		to a 802.11 radio interface."
	INDEX       { ifIndex }
	::= { azaleaIfDot11Table 1 }


AzaleaIfDot11Entry ::= SEQUENCE {
	azlDot11PhysMode           INTEGER,
	azlDot11Channel            Integer32,
	azlDot11Antenna            Integer32,
	azlDot11CtsProtection      INTEGER,
	azlDot11RadioNoiseFloor    Integer32,
	azlDot11RadioInterferenceLevel Integer32,
	azlDot11TxPowerConfigured            Integer32,
	azlDot11BeaconInterval Integer32,
	azlDot11AntennaGain            Integer32,
	azlDot11TxPowerReduction       Integer32,
        azlDot11ChStatsMonitoredTime    TimeTicks,
        azlDot11ChannelUsagePercentage Integer32,
	azlDot11TxPowerCurrent Integer32,
        azlDot11TransmittedAssocRespFrameCount Integer32,
        azlDot11TransmittedReassocRespFrameCount Integer32,
        azlDot11TransmittedProbeRespFrameCount Integer32,
        azlDot11TransmittedDisassocFrameCount Integer32,
        azlDot11TransmittedDeauthFrameCount Integer32,
        azlDot11TransmittedActionFrameCount Integer32,
        azlDot11TransmittedAuthFrameCount Integer32,
        azlDot11TransmittedMgmtFrameCount Integer32,
        azlDot11ChannelChangeCount Integer32,
	azlDot11ConfiguredPhysMode Integer32,
	azlDot11ConfiguredChannel Integer32,
	azlDot11ChannelPolicy INTEGER,
	azlDot11AutoChannelChangeInterval Integer32,
	azlDot11PhyErrPkts Integer32,
	azlDot11FrameErrorRate Integer32,
	azlDot11FrameRetryRate Integer32,
--	azlDot11CurrentSNR Gauge32,
	azlDot11MaxSsidCount Integer32,
	azlDot11ForwardingMode INTEGER,
--	azlDot11MonitorMode INTEGER,
--	azlDot11DiversitySelectionRx TruthValue,
--	azlDot11CurRadioModeSupport INTEGER,
--	azlDot11MaxTxPwrLvl OCTET STRING,
--	azlDot11PwrAttRange Integer32,
--	azlDot11AutoPowerEnabled TruthValue,
	azlDot11PreambleLen INTEGER,
--	azlDot11AllStaTotalMin TimeTicks,
--	azlDot11AssocFailNum Counter32,
--	azlDot11BSSNotSupportAssocFailSum Counter32,
--	azlDot11AvgRxSignalStrength Integer32,
--	azlDot11HighestRxSignalStrength Integer32,
--	azlDot11LowestRxSignalStrength Integer32,
--	azlDot11TxDataPkts Counter32,
--	azlDot11RxDataPkts Counter32,
--	azlDot11TotalReassociation Counter32,
--	azlDot11TotalAssociationFailOther Counter32,
--	azlDot11ChStatsMacMicErrPkts Counter32,
--	azlDot11ChStatsFrameErrorCnt Counter32,
--	azlDot11ShtRetryThld Integer32,
--	azlDot11LongRetryThld Integer32,
--	azlDot11MaxRxLifetime Unsigned32,
--	azlDot11NotContainedInStdReasonAssocFailSum Counter32,
--	azlDot11PreAssCannotShiftDeassocFailSum Counter32,
--	azlDot11SnrBSSIDTxSignalPkts Counter32,
--	azlDot11SnrBSSIDRxSignalPkts Counter32,
--	azlDot11ModeConfig INTEGER,
--	azlDot11DisassocAPNoRec Counter32,
--	azlDot11DisassocUserLeaving Counter32,
--	azlDot11DisassocSum Counter32,
--	azlDot11AuthWrongPassword Counter32,
--	azlDot11AuthInvalid Counter32,
--	azlDot11AuthTimeout Counter32,
--	azlDot11AuthRejected Counter32,
--	azlDot11AuthOtherFail Counter32,
--	azlDot11AuthSuccess Counter32,
--	azlDot11ReassocFailInvalidAlgorithmSequence Counter32,
--	azlDot11ReassocFailNextTimeout Counter32,
--	azlDot11ReassocFailRejected Counter32,
--	azlDot11ReassocFailOther Counter32,
--	azlDot11ReassocSuccess Counter32,
--	azlDot11ReassocAttempts Counter32,
--	azlDot11AssocFailInvalidAlgorithmSequence Counter32,
--	azlDot11AssocFailNextTimeout Counter32,
--	azlDot11AssocFailRejected Counter32,
--	azlDot11AssocFailOther Counter32,
--	azlDot11SuccAssocDelta Counter32,
	azlDot11RadioRole Integer32,
	azlDot11RadioChannelWidth Integer32,
	azlDot11PreferedChannelList2G OCTET STRING,
	azlDot11PreferedChannelList5G OCTET STRING,
	azlDot11RadioCardChipName DisplayString,
	azlDot11RadioMaxPower Integer32
}

azlDot11PhysMode OBJECT-TYPE
	SYNTAX      INTEGER {
		ieee80211a(1),
		ieee80211b(2),
		ieee80211g(3),
		ieee80211na(7), 
		ieee80211ng(8), 
		ieee80211na-ht40plus(9), 
		ieee80211na-ht40minus(10), 
		ieee80211ng-ht40plus(11), 
		ieee80211ng-ht40minus(12), 
		ieee80211g-only(15),
		unknown(255)
	}
	MAX-ACCESS  read-only
	STATUS      current
        DESCRIPTION
        	"IEEE Std 802.11-Jan 14 1999, Wireless LAN Medium Access
        	Control and Physical Layer Specifications, LAN MAN Standards
        	Committee of the IEEE Computer Society, section 3."
	::= { azaleaIfDot11Entry 1 }


azlDot11Channel OBJECT-TYPE
	SYNTAX      Integer32
	MAX-ACCESS  read-only
	STATUS      current
    DESCRIPTION
        	"This attribute shall indicate the value of the
        	channel number in the subband for the associated
        	domain country string."
	::= { azaleaIfDot11Entry 3 }

azlDot11Antenna OBJECT-TYPE
	SYNTAX      Integer32 (1..255)
	MAX-ACCESS  read-only
	STATUS      current
        DESCRIPTION
        	"The antenna being used to transmit.
        	This may be used by a management agent to control
        	which antenna is used for transmission. "
	::= { azaleaIfDot11Entry 4 }

azlDot11CtsProtection OBJECT-TYPE
	SYNTAX      INTEGER {
		enable(1),
		disable(2),
		withOLBC(3),
		withoutOLBC(4)
	}
	MAX-ACCESS  read-only
	STATUS      current
        DESCRIPTION
        "enable(1): Always enable CTS protection
		disable(2): Always disable CTS protection
		withOLBC(3): Enable CTS protection when there are both
		802.11g and 802.11b stations associated with this
		access point or when Overlapping Legacy BSS Condition
		(OLBC) is detected.
		withoutOLBC(4): Enable CTS protection when there are
		both 802.11g and 802.11b stations associated with
		this access point but not when OLBC is detected."
	::= { azaleaIfDot11Entry 6 }

azlDot11RadioNoiseFloor OBJECT-TYPE
	SYNTAX      Integer32
	MAX-ACCESS  read-only
	STATUS      current
        DESCRIPTION
        	"It describes the Noise Floor of this radio"
	::= { azaleaIfDot11Entry 10 }

azlDot11RadioInterferenceLevel OBJECT-TYPE
	SYNTAX      Integer32 (0..100)
	MAX-ACCESS  read-only
	STATUS      current
        DESCRIPTION
        	"It describes the interference level of this radio"
	::= { azaleaIfDot11Entry 11 } 

azlDot11TxPowerConfigured  OBJECT-TYPE
	SYNTAX      Integer32 (1..50)
	MAX-ACCESS  read-only
	STATUS      current
        DESCRIPTION
        	"The configured radio transmit power, the unit is dB."
	::= { azaleaIfDot11Entry 14 }
	
azlDot11BeaconInterval  OBJECT-TYPE
	SYNTAX      Integer32 (100..1000)
	MAX-ACCESS  read-only
	STATUS      current
        DESCRIPTION
        	"The beacon interval of radio, the unit is ms."
	::= { azaleaIfDot11Entry 17 }

azlDot11AntennaGain  OBJECT-TYPE
	SYNTAX      Integer32 (1..255)
	MAX-ACCESS  read-only
	STATUS      current
        DESCRIPTION
        	"The Antenna Gain of the radio, the unit is db."
	::= { azaleaIfDot11Entry 18 }

azlDot11TxPowerReduction  OBJECT-TYPE
	SYNTAX      Integer32 (1..50)
	MAX-ACCESS  read-only
	STATUS      current
        DESCRIPTION
        	"The transmit power reduction of the radio, the unit is dbm."
	::= { azaleaIfDot11Entry 19 }

azlDot11ChStatsMonitoredTime  OBJECT-TYPE
        SYNTAX      TimeTicks
        MAX-ACCESS  read-only
        STATUS      current
        DESCRIPTION
                "The amount of time that channel statistics has been collected on this radio."
        ::= { azaleaIfDot11Entry 21 }

azlDot11ChannelUsagePercentage OBJECT-TYPE
        SYNTAX      Integer32
        MAX-ACCESS  read-only
        STATUS      current
        DESCRIPTION
                "It describes the channel usage percentage (%) of this radio"
        ::= { azaleaIfDot11Entry 23 }
	
azlDot11TxPowerCurrent OBJECT-TYPE
	SYNTAX      Integer32
	MAX-ACCESS  read-only
	STATUS      current
        DESCRIPTION
        	"The transmit power of the radio"
	::= { azaleaIfDot11Entry 24 } 

azlDot11TransmittedAssocRespFrameCount OBJECT-TYPE
        SYNTAX      Integer32
        MAX-ACCESS  read-only
        STATUS      current
        DESCRIPTION
                "The number of the transmitted association response frame"
        ::= { azaleaIfDot11Entry 25 }

azlDot11TransmittedReassocRespFrameCount  OBJECT-TYPE
        SYNTAX      Integer32
        MAX-ACCESS  read-only
        STATUS      current
        DESCRIPTION
                "The number of  transmitted re-association response frame"
        ::= { azaleaIfDot11Entry 26 }

azlDot11TransmittedProbeRespFrameCount  OBJECT-TYPE
        SYNTAX      Integer32
        MAX-ACCESS  read-only
        STATUS      current
        DESCRIPTION
                "The number of  transmitted probe response frame"
        ::= { azaleaIfDot11Entry 27 }


azlDot11TransmittedDisassocFrameCount  OBJECT-TYPE
        SYNTAX      Integer32
        MAX-ACCESS  read-only
        STATUS      current
        DESCRIPTION
                "The number of transmitted disassociation response frame"
        ::= { azaleaIfDot11Entry 28 }

azlDot11TransmittedDeauthFrameCount  OBJECT-TYPE
        SYNTAX      Integer32
        MAX-ACCESS  read-only
        STATUS      current
        DESCRIPTION
                "The number of transmitted deauthentication frame"
        ::= { azaleaIfDot11Entry 29 }

azlDot11TransmittedActionFrameCount  OBJECT-TYPE
        SYNTAX      Integer32
        MAX-ACCESS  read-only
        STATUS      current
        DESCRIPTION
                "The number of transmitted action frame"
        ::= { azaleaIfDot11Entry 30 }

azlDot11TransmittedAuthFrameCount  OBJECT-TYPE
        SYNTAX      Integer32
        MAX-ACCESS  read-only
        STATUS      current
        DESCRIPTION
                "The number of transmitted authentication frame"
        ::= { azaleaIfDot11Entry 31 }

azlDot11TransmittedMgmtFrameCount  OBJECT-TYPE
        SYNTAX      Integer32
        MAX-ACCESS  read-only
        STATUS      current
        DESCRIPTION
                "The number of transmitted management frame"
        ::= { azaleaIfDot11Entry 32 }

azlDot11ChannelChangeCount  OBJECT-TYPE
        SYNTAX      Integer32
        MAX-ACCESS  read-only
        STATUS      current
        DESCRIPTION
                "The number of channel change"
        ::= { azaleaIfDot11Entry 33 }
	
azlDot11ConfiguredPhysMode OBJECT-TYPE
	SYNTAX      INTEGER { ieee80211a(1), ieee80211b(2), ieee80211g(3), ieee80211na(7), ieee80211ng(8), ieee80211na-ht40plus(9), ieee80211na-ht40minus(10), ieee80211ng-ht40plus(11), ieee80211ng-ht40minus(12), ieee80211g-only(15) }
	MAX-ACCESS  read-only
	STATUS      current
        DESCRIPTION
        	"Configured physical mode of this radio"
	::= { azaleaIfDot11Entry 35 } 

azlDot11ConfiguredChannel OBJECT-TYPE
	SYNTAX      Integer32
	MAX-ACCESS  read-only
	STATUS      current
        DESCRIPTION
        	"Configured channel number of this radio, and value (-1) represent this radio's channel is in auto-select mode"
	::= { azaleaIfDot11Entry 36 } 

azlDot11ChannelPolicy OBJECT-TYPE
        SYNTAX INTEGER {
            manual(0),
            automatic(1)
        }
	MAX-ACCESS  read-only
	STATUS      current
        DESCRIPTION
        	"Configured channel policy of this radio"
	::= { azaleaIfDot11Entry 37 }

azlDot11AutoChannelChangeInterval OBJECT-TYPE
        SYNTAX Integer32
	MAX-ACCESS  read-only
	STATUS      current
        DESCRIPTION
        	"Configured channel change interval of this radio"
	::= { azaleaIfDot11Entry 38 }

--  not supported
--azlDot11PhyErrPkts OBJECT-TYPE
--        SYNTAX Integer32
--	MAX-ACCESS  read-only
--	STATUS      current
--        DESCRIPTION
--        	"The number of physical error packets of the radio"
--	::= { azaleaIfDot11Entry 39 }

azlDot11FrameErrorRate OBJECT-TYPE
	SYNTAX Integer32
	MAX-ACCESS  read-only
	STATUS      current
	DESCRIPTION
		"The frame error rate of the radio"
	::= { azaleaIfDot11Entry 40 }

azlDot11FrameRetryRate OBJECT-TYPE
	SYNTAX Integer32
	MAX-ACCESS  read-only
	STATUS      current
	DESCRIPTION
		"The frame retry rate of the radio"
	::= { azaleaIfDot11Entry 41 }

--azlDot11CurrentSNR OBJECT-TYPE
--	SYNTAX Gauge32
--	MAX-ACCESS  read-only
--	STATUS      current
--	DESCRIPTION
--		""
--	::= { azaleaIfDot11Entry 42 }

azlDot11MaxSsidCount OBJECT-TYPE
	SYNTAX Integer32
	MAX-ACCESS  read-only
	STATUS      current
	DESCRIPTION
		"Maximum number of SSIDs supported on this radio"
	::= { azaleaIfDot11Entry 50 }

azlDot11ForwardingMode OBJECT-TYPE
        SYNTAX INTEGER {
	    bridge(0),
	    route(1)
        }
        MAX-ACCESS read-only
        STATUS current
        DESCRIPTION
            "The operation mode of wireless module.
		  bridge(0),route(1),Default: bridge(0)."
        ::= { azaleaIfDot11Entry 51 }

--azlDot11MonitorMode OBJECT-TYPE
--        SYNTAX  INTEGER{normal(1),monitor(2),semiMonitor(3)}
--        MAX-ACCESS read-write
--        STATUS  current
--        DESCRIPTION
--        "ApMonitorMode
--        Value list:
--        1: normal(1)
--        2: monitor(2)
--        3: semiMonitor(3)"
--        ::= { azaleaIfDot11Entry 52 }

--azlDot11DiversitySelectionRx OBJECT-TYPE
--                SYNTAX   TruthValue
--                MAX-ACCESS read-only
--                STATUS current
--                DESCRIPTION
--                ""
--        ::= { azaleaIfDot11Entry 53 }

--azlDot11CurRadioModeSupport OBJECT-TYPE
--            SYNTAX INTEGER {
--	 	dot11a(1),dot11b(2),dot11g(4),dot11an(8),dot11gn(16)
--		}
--                MAX-ACCESS read-only
--                STATUS current
--                DESCRIPTION
--                        ""
--        ::= { azaleaIfDot11Entry 54 }

--azlDot11MaxTxPwrLvl OBJECT-TYPE
--            SYNTAX OCTET STRING
--                MAX-ACCESS read-only
--                STATUS current
--                DESCRIPTION
--                        "the max transmit power,unit:dbm"
--        ::= { azaleaIfDot11Entry 55 }

--azlDot11PwrAttRange OBJECT-TYPE
--             SYNTAX Integer32
--                MAX-ACCESS read-only
--                STATUS current
--                DESCRIPTION
--                        "unit:dB,>=20dB"
--        ::= { azaleaIfDot11Entry 56 }

--azlDot11AutoPowerEnabled OBJECT-TYPE
--                        SYNTAX TruthValue
--                        MAX-ACCESS read-write
--                        STATUS current
--                        DESCRIPTION
--                                "This attribute shall indicate the function of autoPower."
--        ::= { azaleaIfDot11Entry 57 }

azlDot11PreambleLen OBJECT-TYPE
            SYNTAX INTEGER{long(1),short(2)}
                MAX-ACCESS read-only
                STATUS current
                DESCRIPTION
                        "the type of preamble,
                        1:long,2:short"
        ::= { azaleaIfDot11Entry 59 }

--	azlDot11AllStaTotalMin OBJECT-TYPE
--                SYNTAX TimeTicks
--                MAX-ACCESS read-only
--                STATUS current
--                DESCRIPTION ""
--        ::= { azaleaIfDot11Entry 64 }
--
--	azlDot11AssocFailNum  OBJECT-TYPE
--                        SYNTAX Counter32
--                        MAX-ACCESS read-only
--                        STATUS current
--                        DESCRIPTION
--                        "AP wirelessUser Asso of failure Number"
--        ::= { azaleaIfDot11Entry 65 }
--
--	azlDot11BSSNotSupportAssocFailSum OBJECT-TYPE
--                        SYNTAX Counter32
--                        MAX-ACCESS read-only
--                        STATUS current
--                        DESCRIPTION
--                                "znApBSSNotSupportAssocFailSum"
--        ::= { azaleaIfDot11Entry 66 }
--
--	azlDot11AvgRxSignalStrength OBJECT-TYPE
--                        SYNTAX Integer32
--                        MAX-ACCESS read-only
--                        STATUS current
--                        DESCRIPTION ""
--
--        ::= { azaleaIfDot11Entry 67 }

--	azlDot11HighestRxSignalStrength OBJECT-TYPE
--                        SYNTAX Integer32
--                        MAX-ACCESS read-only
--                        STATUS current
--                        DESCRIPTION ""
--        ::= { azaleaIfDot11Entry 68 }
--
--	azlDot11LowestRxSignalStrength OBJECT-TYPE
--                SYNTAX Integer32
--                MAX-ACCESS read-only
--                        STATUS current
--                        DESCRIPTION ""
--        ::= { azaleaIfDot11Entry 69 }
--
--	azlDot11TxDataPkts OBJECT-TYPE
--                        SYNTAX Counter32
--                        MAX-ACCESS read-only
--                        STATUS current
--                        DESCRIPTION
--                        "The field indicates the sum of transmit pkts."
--        ::= { azaleaIfDot11Entry 70 }
--
--	azlDot11RxDataPkts OBJECT-TYPE
--                        SYNTAX Counter32
--                        MAX-ACCESS read-only
--                        STATUS current
--                        DESCRIPTION
--                        "The field indicates the sum of receive pkts."
--        ::= { azaleaIfDot11Entry 71 }

--	azlDot11TotalReassociation OBJECT-TYPE
--                        SYNTAX Counter32
--                        MAX-ACCESS read-only
--                        STATUS current
--                        DESCRIPTION ""
--        ::= { azaleaIfDot11Entry 72 }
--
--	azlDot11TotalAssociationFailOther OBJECT-TYPE
--                        SYNTAX Counter32
--                        MAX-ACCESS read-only
--                        STATUS current
--                        DESCRIPTION ""
--        ::= { azaleaIfDot11Entry 73 }
--
--	azlDot11ChStatsMacMicErrPkts OBJECT-TYPE
--                        SYNTAX Counter32
--                        MAX-ACCESS read-only
--                        STATUS current
--                        DESCRIPTION "znApChStatsFrameRetryCnt"
--        ::= { azaleaIfDot11Entry 74 }
--
--	azlDot11ChStatsFrameErrorCnt OBJECT-TYPE
--                        SYNTAX Counter32
--                        MAX-ACCESS read-only
--                        STATUS current
--                        DESCRIPTION "znApChStatsFrameRetryCnt"
--        ::= { azaleaIfDot11Entry 75 }
--
--	azlDot11ShtRetryThld OBJECT-TYPE
--            SYNTAX Integer32
--                MAX-ACCESS read-only
--                STATUS current
--                DESCRIPTION "the ShtRetryThld."
--        ::= { azaleaIfDot11Entry 76 }

--	azlDot11LongRetryThld OBJECT-TYPE
--            SYNTAX Integer32
--                MAX-ACCESS read-only
--                STATUS current
--                DESCRIPTION "the LongRetryThld."
--        ::= { azaleaIfDot11Entry 77 }
--
--	azlDot11MaxRxLifetime OBJECT-TYPE
--            SYNTAX Unsigned32
--                MAX-ACCESS read-only
--                STATUS current
--                DESCRIPTION
--                        "the MaxRxLifetime."
--        ::= { azaleaIfDot11Entry 78 }
--
--	azlDot11NotContainedInStdReasonAssocFailSum OBJECT-TYPE
--                        SYNTAX Counter32
--                        MAX-ACCESS read-only
--                        STATUS current
--                        DESCRIPTION
--                        "znApNotContainedInStdReasonAssocFailSum"
--        ::= { azaleaIfDot11Entry 79 }
--
--	azlDot11PreAssCannotShiftDeassocFailSum OBJECT-TYPE
--                        SYNTAX Counter32
--                        MAX-ACCESS read-only
--                        STATUS current
--                        DESCRIPTION
--                        "znPreAssCannotShiftDeassocFailSum"
--        ::= { azaleaIfDot11Entry 80 }

--	azlDot11SnrBSSIDTxSignalPkts OBJECT-TYPE
--                        SYNTAX Counter32
--                        MAX-ACCESS read-only
--                        STATUS current
--                        DESCRIPTION ""
--        ::= { azaleaIfDot11Entry 81 }
--
--	azlDot11SnrBSSIDRxSignalPkts OBJECT-TYPE
--                        SYNTAX Counter32
--                        MAX-ACCESS read-only
--                        STATUS current
--                        DESCRIPTION ""
--        ::= { azaleaIfDot11Entry 82 }
--
--azlDot11ModeConfig OBJECT-TYPE
--        SYNTAX INTEGER{dot11a(1),dot11b(2),dot11g(4),dot11an(8),dot11gn(16)}
--        MAX-ACCESS  read-write
--        STATUS      current
--        DESCRIPTION
--                "Configured physical mode of this radio"
--        ::= { azaleaIfDot11Entry 100 }
--                                        
--azlDot11DisassocAPNoRec OBJECT-TYPE
--        SYNTAX Counter32
--        MAX-ACCESS  read-only
--        STATUS      current
--        DESCRIPTION
--                ""
--        ::= { azaleaIfDot11Entry 120 }
                                        
--azlDot11DisassocUserLeaving OBJECT-TYPE
--        SYNTAX Counter32
--        MAX-ACCESS  read-only
--        STATUS      current
--        DESCRIPTION
--                ""
--        ::= { azaleaIfDot11Entry 121 }
--                                        
--azlDot11DisassocSum OBJECT-TYPE
--        SYNTAX Counter32
--        MAX-ACCESS  read-only
--        STATUS      current
--        DESCRIPTION
--                ""
--        ::= { azaleaIfDot11Entry 122 }
--                                        
--azlDot11AuthWrongPassword OBJECT-TYPE
--        SYNTAX Counter32
--        MAX-ACCESS  read-only
--        STATUS      current
--        DESCRIPTION
--                ""
--        ::= { azaleaIfDot11Entry 123 }
--
--azlDot11AuthInvalid OBJECT-TYPE
--        SYNTAX Counter32
--        MAX-ACCESS  read-only
--        STATUS      current
--        DESCRIPTION
--                ""
--        ::= { azaleaIfDot11Entry 124 }

--azlDot11AuthTimeout OBJECT-TYPE
--        SYNTAX Counter32
--        MAX-ACCESS  read-only
--        STATUS      current
--        DESCRIPTION
--                ""
--        ::= { azaleaIfDot11Entry 125 }
--
--azlDot11AuthRejected OBJECT-TYPE
--        SYNTAX Counter32
--        MAX-ACCESS  read-only
--        STATUS      current
--        DESCRIPTION
--                ""
--        ::= { azaleaIfDot11Entry 126 }
--
--azlDot11AuthOtherFail OBJECT-TYPE
--        SYNTAX Counter32
--        MAX-ACCESS  read-only
--        STATUS      current
--        DESCRIPTION
--                ""
--        ::= { azaleaIfDot11Entry 127 }
--
--azlDot11AuthSuccess OBJECT-TYPE
--        SYNTAX Counter32
--        MAX-ACCESS  read-only
--        STATUS      current
--        DESCRIPTION
--                ""
--        ::= { azaleaIfDot11Entry 128 }

--azlDot11ReassocFailInvalidAlgorithmSequence OBJECT-TYPE
--        SYNTAX Counter32
--        MAX-ACCESS  read-only
--        STATUS      current
--        DESCRIPTION
--                ""
--        ::= { azaleaIfDot11Entry 130 }
--
--azlDot11ReassocFailNextTimeout OBJECT-TYPE
--        SYNTAX Counter32
--        MAX-ACCESS  read-only
--        STATUS      current
--        DESCRIPTION
--                ""
--        ::= { azaleaIfDot11Entry 131 }
--
--azlDot11ReassocFailRejected OBJECT-TYPE
--        SYNTAX Counter32
--        MAX-ACCESS  read-only
--        STATUS      current
--        DESCRIPTION
--                ""
--        ::= { azaleaIfDot11Entry 132 }
--
--azlDot11ReassocFailOther OBJECT-TYPE
--        SYNTAX Counter32
--        MAX-ACCESS  read-only
--        STATUS      current
--        DESCRIPTION
--                ""
--        ::= { azaleaIfDot11Entry 133 }

--azlDot11ReassocSuccess OBJECT-TYPE
--        SYNTAX Counter32
--        MAX-ACCESS  read-only
--        STATUS      current
--        DESCRIPTION
--                ""
--        ::= { azaleaIfDot11Entry 134 }
--
--azlDot11ReassocAttempts OBJECT-TYPE
--        SYNTAX Counter32
--        MAX-ACCESS  read-only
--        STATUS      current
--        DESCRIPTION
--                ""
--        ::= { azaleaIfDot11Entry 135 }
--
--azlDot11AssocFailInvalidAlgorithmSequence OBJECT-TYPE
--        SYNTAX Counter32
--        MAX-ACCESS  read-only
--        STATUS      current
--        DESCRIPTION
--                ""
--        ::= { azaleaIfDot11Entry 140 }

--azlDot11AssocFailNextTimeout OBJECT-TYPE
--        SYNTAX Counter32
--        MAX-ACCESS  read-only
--        STATUS      current
--        DESCRIPTION
--                ""
--        ::= { azaleaIfDot11Entry 141 }
--
--azlDot11AssocFailRejected OBJECT-TYPE
--        SYNTAX Counter32
--        MAX-ACCESS  read-only
--        STATUS      current
--        DESCRIPTION
--                ""
--        ::= { azaleaIfDot11Entry 142 }
--
--azlDot11AssocFailOther OBJECT-TYPE
--        SYNTAX Counter32
--        MAX-ACCESS  read-only
--        STATUS      current
--        DESCRIPTION
--                ""
--        ::= { azaleaIfDot11Entry 143 }
--
--azlDot11SuccAssocDelta OBJECT-TYPE
--        SYNTAX Counter32
--        MAX-ACCESS  read-only
--        STATUS      current
--        DESCRIPTION
--                ""
--        ::= { azaleaIfDot11Entry 144 }

azlDot11RadioRole OBJECT-TYPE
        SYNTAX INTEGER { access(6), mesh(9), client(1) }
        MAX-ACCESS  read-only
        STATUS      current
        DESCRIPTION
                "The role of the radio such as access, mesh, client"
        ::= { azaleaIfDot11Entry 201 }

azlDot11RadioChannelWidth OBJECT-TYPE
        SYNTAX INTEGER { channelWidth5M(5), channelWidth10M(10), channelWidth20M(20), channelWidth40M(40) }
        MAX-ACCESS  read-only
        STATUS      current
        DESCRIPTION
                "The channel width of the radio"
        ::= { azaleaIfDot11Entry 211 }

azlDot11PreferedChannelList2G OBJECT-TYPE
	SYNTAX      OCTET STRING (SIZE(0..32))
	MAX-ACCESS  read-only
	STATUS      current
        DESCRIPTION
        	"The prefer 2G channel list of this radio"
	::= { azaleaIfDot11Entry 212 } 

azlDot11PreferedChannelList5G OBJECT-TYPE
	SYNTAX      OCTET STRING (SIZE(0..32))
	MAX-ACCESS  read-only
	STATUS      current
        DESCRIPTION
        	"The prefer 5G channel list of this radio"
	::= { azaleaIfDot11Entry 213 } 

azlDot11RadioCardChipName OBJECT-TYPE
        SYNTAX DisplayString
        MAX-ACCESS  read-only
        STATUS      current
        DESCRIPTION
                "The card chip name of the radio"
        ::= { azaleaIfDot11Entry 221 }

azlDot11RadioMaxPower OBJECT-TYPE
        SYNTAX Integer32
        MAX-ACCESS  read-only
        STATUS      current
        DESCRIPTION
                "The MAX transmit power of the radio (mW)"
        ::= { azaleaIfDot11Entry 222 }

		
		
		
-- *****************************************************
--  azaleaIfDot11StatTable
-- *****************************************************
--azaleaIfDot11StatTable OBJECT-TYPE
--	SYNTAX      SEQUENCE OF AzaleaIfDot11StatEntry
--	MAX-ACCESS  not-accessible
--	STATUS      current
--	DESCRIPTION
--		""
--	::= { azaleaIfMib 13 }
--
--azaleaIfDot11StatEntry OBJECT-TYPE
--	SYNTAX      AzaleaIfDot11StatEntry
--	MAX-ACCESS  not-accessible
--	STATUS      current
--        DESCRIPTION ""
--	INDEX       { ifIndex }
--	::= { azaleaIfDot11StatTable 1 }
--
--
--AzaleaIfDot11StatEntry ::= SEQUENCE {
--	azlDot11StatTotalAssocCount Counter32,
--	azlDot11StatSuccAssocDelta Counter32,
--	azlDot11StatAssocReqDelta Counter32,
--	azlDot11StatAssocRespDelta Counter32,
--	azlDot11StatAllStaTotalSec Counter32
--}
--
--azlDot11StatTotalAssocCount OBJECT-TYPE
--        SYNTAX Counter32
--        MAX-ACCESS  read-only
--        STATUS      current
--        DESCRIPTION
--                ""
--        ::= { azaleaIfDot11StatEntry 1 }

--azlDot11StatSuccAssocDelta OBJECT-TYPE
--        SYNTAX Counter32
--        MAX-ACCESS  read-only
--        STATUS      current
--        DESCRIPTION
--                ""
--        ::= { azaleaIfDot11StatEntry 2 }
--
--azlDot11StatAssocReqDelta OBJECT-TYPE
--        SYNTAX Counter32
--        MAX-ACCESS  read-only
--        STATUS      current
--        DESCRIPTION
--                ""
--        ::= { azaleaIfDot11StatEntry 3 }
--
--azlDot11StatAssocRespDelta OBJECT-TYPE
--        SYNTAX Counter32
--        MAX-ACCESS  read-only
--        STATUS      current
--        DESCRIPTION
--                ""
--        ::= { azaleaIfDot11StatEntry 4 }
--
--azlDot11StatAllStaTotalSec OBJECT-TYPE
--        SYNTAX Counter32
--        MAX-ACCESS  read-only
--        STATUS      current
--        DESCRIPTION
--                ""
--        ::= { azaleaIfDot11StatEntry 5 }

--azaleaIfDot11ConfigTable OBJECT-TYPE
--	SYNTAX      SEQUENCE OF AzaleaIfDot11ConfigEntry
--	MAX-ACCESS  not-accessible
--	STATUS      current
--	DESCRIPTION
--		""
--	::= { azaleaIfMib 14 }
--
--azaleaIfDot11ConfigEntry OBJECT-TYPE
--	SYNTAX      AzaleaIfDot11ConfigEntry
--	MAX-ACCESS  not-accessible
--	STATUS      current
--        DESCRIPTION ""
--	INDEX       { ifIndex }
--	::= { azaleaIfDot11ConfigTable 1 }
--
--
--AzaleaIfDot11ConfigEntry ::= SEQUENCE {
--	azlDot11AMPDUEnabled INTEGER,
--	azlDot11BWMode INTEGER,
--	azlDot11ShortGIEnabled INTEGER,
--	azlDot11Is11nOnly TruthValue
--}

--azlDot11AMPDUEnabled OBJECT-TYPE
--        SYNTAX   INTEGER{off(0),on(1)}
--        MAX-ACCESS read-write
--        STATUS current
--        DESCRIPTION
--                ""
--        ::= { azaleaIfDot11ConfigEntry 1 }
--
--azlDot11BWMode OBJECT-TYPE
--        SYNTAX INTEGER{mode20M(0),mode40M(1)}
--        MAX-ACCESS read-write
--        STATUS current
--        DESCRIPTION
--                ""
--        ::= { azaleaIfDot11ConfigEntry 2 }
--        
--azlDot11ShortGIEnabled OBJECT-TYPE
--        SYNTAX   INTEGER{off(0),on(1)}
--        MAX-ACCESS read-write
--        STATUS current
--        DESCRIPTION
--                ""
--        ::= { azaleaIfDot11ConfigEntry 3 }
--
--azlDot11Is11nOnly OBJECT-TYPE
--        SYNTAX   TruthValue
--        MAX-ACCESS read-write
--        STATUS current
--        DESCRIPTION
--                ""
--        ::= { azaleaIfDot11ConfigEntry 4 }

--azaleaIfDot11QoSTable OBJECT-TYPE
--	SYNTAX      SEQUENCE OF AzaleaIfDot11QoSEntry
--	MAX-ACCESS  not-accessible
--	STATUS      current
--	DESCRIPTION
--		"A list of 802.11 radio interface QoS entries"
--	::= { azaleaIfMib 10 }
--
--azaleaIfDot11QoSEntry OBJECT-TYPE
--	SYNTAX      AzaleaIfDot11QoSEntry
--	MAX-ACCESS  not-accessible
--	STATUS      current
--        DESCRIPTION
--        	"An entry containing management information applicable
--		to a 802.11 radio interface's QoS parameters."
--	INDEX       { ifIndex, azlDot11QoSQueueIndex }
--	::= { azaleaIfDot11QoSTable 1 }
--
--
--AzaleaIfDot11QoSEntry ::= SEQUENCE {
--	azlDot11QoSQueueIndex INTEGER,
--	azlDot11QoSAIFS Integer32,
--	azlDot11QoSCWmin Integer32,
--	azlDot11QoSCWMax Integer32,
--	azlDot11QoSTXOPLim Integer32
--}
--
--	azlDot11QoSQueueIndex OBJECT-TYPE
--                SYNTAX INTEGER(0..3)
--                MAX-ACCESS not-accessible
--                STATUS current
--                DESCRIPTION
--                        ""
--        ::= { azaleaIfDot11QoSEntry 1 }

--	azlDot11QoSAIFS OBJECT-TYPE
--                SYNTAX Integer32
--                MAX-ACCESS read-write
--                STATUS current
--                DESCRIPTION
--                        ""
--        ::= { azaleaIfDot11QoSEntry 2 }
--
--	azlDot11QoSCWmin OBJECT-TYPE
--                SYNTAX Integer32
--                MAX-ACCESS read-write
--                STATUS current
--                DESCRIPTION
--                        ""
--        ::= { azaleaIfDot11QoSEntry 3 }
--
--	azlDot11QoSCWMax OBJECT-TYPE
--                SYNTAX Integer32
--                MAX-ACCESS read-write
--                STATUS current
--                DESCRIPTION
--                        ""
--        ::= { azaleaIfDot11QoSEntry 4 }
--
--	azlDot11QoSTXOPLim OBJECT-TYPE
--                SYNTAX Integer32
--                MAX-ACCESS read-write
--                STATUS current
--                DESCRIPTION
--                        ""
--        ::= { azaleaIfDot11QoSEntry 5 }

azaleaIfTrapObjects OBJECT IDENTIFIER ::= { azaleaIfMib 5 }

--  not supported - YES IT IS!!! (MJ, 06-June-2019)
azaleaIfTrapThreshold OBJECT IDENTIFIER ::= { azaleaIfTrapObjects 1 }

azaleaIfTraps OBJECT IDENTIFIER ::= { azaleaIfTrapObjects 2  }

azlInterfaceTrafficTrap  NOTIFICATION-TYPE
    OBJECTS    {
        ifIndex,
        azlIfTxRate,
        azlIfRxRate
    }
    STATUS  current
    DESCRIPTION
        "When WDS interface traffic over or below threshold, send trap"
    ::= { azaleaIfTraps 6 }

azlDot11ChannelChangeTrap  NOTIFICATION-TYPE
    OBJECTS    {
        ifIndex,
        azlDot11PhysMode,
        azlDot11Channel
    }
    STATUS  current
    DESCRIPTION
        "When Radio Interface Channel values change, take the 
        initiative to report changes in values after the Channel"
    ::= { azaleaIfTraps 7 }

azlDot11RadioInterferenceLevelTrap    NOTIFICATION-TYPE
    OBJECTS    {
        ifIndex,  
        azlDot11RadioInterferenceLevel
                   }
    STATUS  current
    DESCRIPTION
        "When interference level crosses the trigger value, report to NMS"
::= { azaleaIfTraps 10}

--azaleaIfDot11CmdTable OBJECT-TYPE
--	SYNTAX      SEQUENCE OF AzaleaIfDot11CmdEntry
--	MAX-ACCESS  not-accessible
--	STATUS      current
--	DESCRIPTION
--		"A list of 802.11 radio interface entries"
--	::= { azaleaIfMib 6 }
--
--azaleaIfDot11CmdEntry OBJECT-TYPE
--	SYNTAX      AzaleaIfDot11CmdEntry
--	MAX-ACCESS  not-accessible
--	STATUS      current
--        DESCRIPTION
--        	"An entry for sending commands to a 802.11 radio interface."
--	INDEX       { ifIndex }
--	::= { azaleaIfDot11CmdTable 1 }


--AzaleaIfDot11CmdEntry ::= SEQUENCE {
--	azlDot11AdmissionAllowed   INTEGER,
--	azlDot11KickOffCount       INTEGER,
--	azlDot11TxPowerRelative    INTEGER
--}
--
--azlDot11AdmissionAllowed OBJECT-TYPE
--	SYNTAX      INTEGER (0..1)
--	MAX-ACCESS  read-write
--	STATUS      current
--        DESCRIPTION
--        	"Whether this radio is to allow admission, 0 is to not allow, 1 is to allow"
--	::= { azaleaIfDot11CmdEntry 1 }
--
--azlDot11KickOffCount OBJECT-TYPE
--	SYNTAX      INTEGER (1..10)
--	MAX-ACCESS  read-write
--	STATUS      current
--        DESCRIPTION
--        	"Number of clients to kick off from this radio"
--	::= { azaleaIfDot11CmdEntry 2 }
--
--azlDot11TxPowerRelative OBJECT-TYPE
--	SYNTAX      INTEGER (1..10)
--	MAX-ACCESS  read-write
--	STATUS      current
--        DESCRIPTION
--        	"Number of clients to kick off from this radio"
--	::= { azaleaIfDot11CmdEntry 3 }

azaleaDot11BssMib	OBJECT IDENTIFIER ::=  {  azalea  3  }

-- not supported
-- TEXTUAL-CONVENTIONS --
--	AzaleaSTAFailureReason ::= TEXTUAL-CONVENTION 
--		DISPLAY-HINT	""
--		STATUS			current
--		DESCRIPTION
--			""
--		SYNTAX 	INTEGER  { 
--					staOk ( 0 ) , 
--					staFailAPBusy ( 1 ) , 
--					staFailAssocBeforeAuth ( 2 ) , 
--					staFailForcedAssocFailure ( 3 ) , 
--					staFailInvalidAssocReq ( 4 ) , 
--					staFailUnknownSsid ( 5 ) , 
--					staFailAssocNoWPAElement ( 6 ) , 
--					staFailAssocInvalidWPAElement ( 7 ) , 
--					staFailAssocNoSuppRatesElement ( 8 ) , 
--					staFailAssocInvalidSuppRatesElement ( 9 ) , 
--					staFailMinRateNotSupported ( 10 ) , 
--					staFailBasicRatesNotSupported ( 11 ) , 
--					staFailLoadBalancingTemporary ( 12 ) , 
--					staFailAssocNoAID ( 13 ) , 
--					staFailAssocNoAck ( 14 ) , 
--					staFail1xAuthFailed ( 15 ) , 
--					staFailWPAPairwiseTimeout ( 16 ) , 
--					staFailWPAGroupTimeout ( 17 ) , 
--					staFailLoadBalanceDisassoc ( 18 ) , 
--					staFailInactivityDisassoc ( 19 ) , 
--					staFailInactivityDeauth ( 20 ) , 
--					staFailWPAMichaelCounter32measures ( 21 ) , 
--					staFailWPAInvalidPairwiseKeyMic2 ( 22 ) , 
--					staFailWPAInvalidPairwiseKeyMic4 ( 23 ) , 
--					staFailWpaInvalidGroupKeyMic ( 24 ) , 
--					staFailMacAclRejectAuth ( 25 ) , 
--					staFailIEEE80211Auth ( 26 ) , 
--					staFailAuthTempoparilyDenied ( 27 ) , 
--					staFailAtherosSuperAg ( 28 ) , 
--					staFailAtherosTurboPrimeBoost ( 29 ) 
--				} 

	azaleaDot11BssObjects	OBJECT IDENTIFIER
		::=  {  azaleaDot11BssMib  1  }

	azaleaDot11BssTrapObjects	OBJECT IDENTIFIER
		::=  {  azaleaDot11BssMib  2  }

	azaleaDot11BssTable	OBJECT-TYPE
		SYNTAX		SEQUENCE  OF  AzaleaDot11BssEntry
		MAX-ACCESS	not-accessible
		STATUS		current
		DESCRIPTION	"This table contains attributes to configure radio
        BSS radio interfaces managed by this agent. The attributes
        are extensions to the configuration parameters in
        the dot11ConfigTable defined in the
        IEEE802dot11-MIB. This table configures the role of
        the interface, propriety extensions, hierarchy,
        security option and parameters, and
        communication settings. This table has a sparse
        dependent relationship on the ifTable.
        For each entry in this table, there exists an entry
        in the ifTable of ifType ieee80211(71).
        Entries in this table cannot be created or deleted
        by the network management system. All entries are
        created or deleted by the agent."
		REFERENCE
		"IEEE Std 802.11-Jan 14 1999, Wireless LAN Medium
        Access Control and Physical Layer Specifications,
        LAN MAN Standards Committee of the IEEE Computer
        Society, IEEE802dot11-MIB."
		::=  { azaleaDot11BssObjects  1 }

	azaleaDot11BssEntry	OBJECT-TYPE
		SYNTAX		AzaleaDot11BssEntry
		MAX-ACCESS	not-accessible
		STATUS		current
		DESCRIPTION	"A collection of configuration attributes for
        a hostapd BSS radio interface. These attributes
        are supplements to attributes defined in the
        dot11StationConfigTable in IEEE802dot11-MIB."
		REFERENCE		"IEEE Std 802.11-Jan 14 1999, Wireless LAN Medium
        Access Control and Physical Layer Specifications,
        LAN MAN Standards Committee of the IEEE Computer
        Society, IEEE802dot11-MIB."
		INDEX		{  ifIndex, azlDot11BssIndex  }
		::=  { azaleaDot11BssTable 1 }

	AzaleaDot11BssEntry  ::=  SEQUENCE {
		azlDot11BssIndex  INTEGER,
		azlDot11BssName  OCTET STRING,
		azlDot11BssMacAddressAuthenticationType  INTEGER,
		azlDot11BssAuthenticationAlgorithm  INTEGER,
		azlDot11BssWepDefaultKey  Integer32,
		azlDot11BssAuthenticationProfile  DisplayString,
		azlDot11BssAccessCategory  INTEGER,
		azlDot11BssAccessVlan  DisplayString,
--		azlDot11BssQoSPolicy   DisplayString,
		azlDot11BssMacACLProfile  DisplayString,
		azlDot11BssMaxInactivity  Integer32,
		azlDot11BssInactivityPolicy  INTEGER,
		azlDot11BssForcedUnicastRate  INTEGER,
--		azlDot11BssIpAddress  IpAddress,
--		azlDot11BssNetmask  IpAddress,
--		azlDot11BssDhcpType  INTEGER,
--		azlDot11BssDhcpPoolName  DisplayString,
--		azlDot11BssDhcpPoolInfo  DisplayString,
--		azlDot11BssDhcpRelayOptionCircuitId  DisplayString,  
		azlDot11BssMaxStationNumberAllowed  Integer32,
		azlDot11BssId MacAddress,
		azlDot11BssWpaType INTEGER,
--		azlDot11BssStationIsolation INTEGER,
		azlDot11BssFragmentationThreshold INTEGER,
		azlDot11BssRTSThreshold INTEGER,
		azlDot11BssLoadBalanceState INTEGER,
		azlDot11BssWmmState INTEGER,
		azlDot11BssSecurityType  INTEGER,
		azlDot11PSKWord  OCTET STRING,
		azlDot11KeyAsciiHex INTEGER
--		azlDot11WAPIPSKWord  OCTET STRING,
--		azlDot11WAPIKeyAsciiHex INTEGER
		}


	azlDot11BssIndex	OBJECT-TYPE	
		SYNTAX			INTEGER(0..15) 
		MAX-ACCESS		read-only
		STATUS			current
		DESCRIPTION		"The Index of this BSS."
		::=  {  azaleaDot11BssEntry  1  }


	azlDot11BssName	OBJECT-TYPE	
		SYNTAX			OCTET STRING  ( SIZE ( 0 .. 32  ) ) 
		MAX-ACCESS		read-only
		STATUS			current
		DESCRIPTION		"The name of this BSS."
		::=  {  azaleaDot11BssEntry  2  }


	azlDot11BssMacAddressAuthenticationType	OBJECT-TYPE	
		SYNTAX			INTEGER  { allowUnlessExplicitlyDenied ( 1 ) , denyUnlessExplicitlyAllowed ( 2 ) , useRadius ( 3 ) } 
		MAX-ACCESS		read-only
		STATUS			current
		DESCRIPTION		"
			How mac lists are used in authentication:
			allowUnlessExplicitlyDenied(0) 
			   means AP accepts all clients unless their macs are in the
			   deny mac table
			denyUnlessExplicitlyAllowed(1) 
			   means AP denies all clients unless their macs are in the 
			   accept mac table
			useRadius(2) 
			   means AP will query the external RADIUS server for accept/deny
			   if the maclists do not include the client
		   "
		::=  {  azaleaDot11BssEntry  3  }


	azlDot11BssAuthenticationAlgorithm	OBJECT-TYPE	
		SYNTAX			INTEGER  {
			open(1),
			openWep(2),
			sharedWep(3),
			dot1x(4),
			wpa(5),
			wpa2(6)
		} 
		MAX-ACCESS		read-only
		STATUS			current
		DESCRIPTION		"The type of data encryption supported by this BSS"
		::=  {  azaleaDot11BssEntry  4  }


	azlDot11BssWepDefaultKey	OBJECT-TYPE	
		SYNTAX			Integer32  ( 1 .. 4  ) 
		MAX-ACCESS		read-only
		STATUS			current
		DESCRIPTION		"The index of the static WEP key in use by this BSS"
		::=  {  azaleaDot11BssEntry  5  }

--  not supported
--	azlDot11BssAuthenticationProfile	OBJECT-TYPE	
--		SYNTAX			DisplayString
--		MAX-ACCESS		read-only
--		STATUS			current
--		DESCRIPTION		"The name of the authentication profile used by this BSS"
--		::=  {  azaleaDot11BssEntry  6  }


	azlDot11BssAccessCategory	OBJECT-TYPE	
		SYNTAX			INTEGER  { notSet(-1), bestEffort(0), background(1), standard(2), excellentEffort(3), controlLoad(4), video(5), voice(6), networkControl(7)} 
		MAX-ACCESS		read-only
		STATUS			current
		DESCRIPTION		"The access category used by this BSS"
		::=  {  azaleaDot11BssEntry  7  }


	azlDot11BssAccessVlan	OBJECT-TYPE	
		SYNTAX			DisplayString
		MAX-ACCESS		read-only
		STATUS			current
		DESCRIPTION		"The VLAN ID used by this BSS, (1..4094)"
		::=  {  azaleaDot11BssEntry  8  }


--  not supported
--	azlDot11BssQoSPolicy	OBJECT-TYPE	
--		SYNTAX			DisplayString ( SIZE ( 0 .. 32  ) ) 
--		MAX-ACCESS		read-only
--		STATUS			current
--		DESCRIPTION		"The name of QoS policy used by this BSS"
--		::=  {  azaleaDot11BssEntry  9  }

--  not supported
--	azlDot11BssMacACLProfile	OBJECT-TYPE	
--		SYNTAX			DisplayString
--		MAX-ACCESS		read-only
--		STATUS			current
--		DESCRIPTION		"The  mac list profile used by this BSS"
--		::=  {  azaleaDot11BssEntry  10  }

	azlDot11BssMaxInactivity	OBJECT-TYPE	
		SYNTAX			Integer32 (15..65535)
		MAX-ACCESS		read-only
		STATUS			current
		DESCRIPTION		"The maximum inactivity time in second allowed for a client before it 
        would be polled or deauthenticated."
		::=  {  azaleaDot11BssEntry  12  }

--  not supported
--	azlDot11BssInactivityPolicy	OBJECT-TYPE	
--		SYNTAX			INTEGER  { poll ( 0 ) , deauthenticate ( 1 ) } 
--		MAX-ACCESS		read-only
--		STATUS			current
--		DESCRIPTION		"The action taken when a client reaches the maximum inactivity time.
--        poll(0):            the client is polled with data frame and is 
--                            deauthenticated if it doesn't respond.
--        deauthenticate(1):  the client is deauthenticated immediately."
--		::=  {  azaleaDot11BssEntry  13  }

	azlDot11BssForcedUnicastRate	OBJECT-TYPE	
		SYNTAX	INTEGER  { 
			rate1M(2),
			rate2M(4),
			rate5M(11),
			rate11M(22),
			rate6M(12),
			rate9M(18),
			rate12M(24),
			rate18M(36),
			rate24M(48),
			rate36M(72),
			rate48M(96),
			rate54M(108),
			rate72M(144),
			rate96M(192),
			rate108M(216),
			rateMCS0(32768),
			rateMCS1(32769),
			rateMCS2(32770),
			rateMCS3(32771),
			rateMCS4(32772),
			rateMCS5(32773),
			rateMCS6(32774),
			rateMCS7(32775),
			rateMCS8(32776),
			rateMCS9(32777),
			rateMCS10(32778),
			rateMCS11(32779),
			rateMCS12(32780),
			rateMCS13(32781),
			rateMCS14(32782),
			rateMCS15(32783)
		}
		MAX-ACCESS		read-only
		STATUS			current
		DESCRIPTION		"The forced unicast rate of the BSS"
		::=  {  azaleaDot11BssEntry  14  }


--		azlDot11BssIpAddress  OBJECT-TYPE
--		SYNTAX			IpAddress
--		MAX-ACCESS		read-create
--		STATUS			current
--		DESCRIPTION		"The IP address of the BSS"
--		::=  {  azaleaDot11BssEntry  15  }
--
--		azlDot11BssNetmask  OBJECT-TYPE
--		SYNTAX			IpAddress
--		MAX-ACCESS		read-create
--		STATUS			current
--		DESCRIPTION		"The IP netmask of the BSS"
--		::=  {  azaleaDot11BssEntry  16  }

--	azlDot11BssDhcpType	OBJECT-TYPE	
--		SYNTAX			INTEGER  { dhcpServerManu ( 1 ) , dhcpServerAuto ( 2 ) , dhcpRelay ( 3 ) , invalid ( 4 ) } 
--		MAX-ACCESS		read-create
--		STATUS			current
--		DESCRIPTION		"The type of DHCP in this BSS"
--		::=  {  azaleaDot11BssEntry  17  }
--
--
--	azlDot11BssDhcpPoolName	OBJECT-TYPE	
--		SYNTAX			DisplayString
--		MAX-ACCESS		read-only
--		STATUS			current
--		DESCRIPTION		"The DHCP pool name used by this BSS in DHCP server mode"
--		::=  {  azaleaDot11BssEntry  18  }
--
--
--	azlDot11BssDhcpPoolInfo	OBJECT-TYPE	
--		SYNTAX			DisplayString
--		MAX-ACCESS		read-only
--		STATUS			current
--		DESCRIPTION		"Precompiled information of the DHCP pool used by this BSS"
--		::=  {  azaleaDot11BssEntry  19  }
--
--        
--	azlDot11BssDhcpRelayOptionCircuitId	OBJECT-TYPE	
--		SYNTAX			DisplayString
--		MAX-ACCESS		read-only
--		STATUS			current
--		DESCRIPTION		"The option 82 information used by this BSS in DHCP relay mode"
--		::=  {  azaleaDot11BssEntry  20  }   
		
    azlDot11BssMaxStationNumberAllowed	OBJECT-TYPE	
		SYNTAX			Integer32
		MAX-ACCESS		read-only
		STATUS			current
		DESCRIPTION		"The max allowed stations"
		::=  {  azaleaDot11BssEntry  21  }

    azlDot11BssId	OBJECT-TYPE	
		SYNTAX			MacAddress
		MAX-ACCESS		read-only
		STATUS			current
		DESCRIPTION		"The BSSID (Mac) of this BSS"
		::=  {  azaleaDot11BssEntry  22  }

    azlDot11BssWpaType	OBJECT-TYPE	
		SYNTAX			INTEGER  { wpaPsk( 1 ), wpa8021x ( 2 ) }
		MAX-ACCESS		read-only
		STATUS			current
		DESCRIPTION		"The WPA Type of this BSS, only valid in WPA or WPA2 mode"
		::=  {  azaleaDot11BssEntry  23  }

--    azlDot11BssStationIsolation	OBJECT-TYPE	
--		SYNTAX			INTEGER  { enable ( 1 ) , disable ( 2 ) }
--		MAX-ACCESS		read-only
--		STATUS			current
--		DESCRIPTION		"The state of station isolation of this BSS"
--		::=  {  azaleaDot11BssEntry  24  }

    azlDot11BssFragmentationThreshold	OBJECT-TYPE	
		SYNTAX			INTEGER(256..2346)
		MAX-ACCESS		read-only
		STATUS			current
		DESCRIPTION		"The fragmentation threshold of this BSS"
		::=  {  azaleaDot11BssEntry  25  }

    azlDot11BssRTSThreshold	OBJECT-TYPE	
		SYNTAX			INTEGER(0..2347)
		MAX-ACCESS		read-only
		STATUS			current
		DESCRIPTION		"The RTS threshold of this BSS"
		::=  {  azaleaDot11BssEntry  26  }

    azlDot11BssLoadBalanceState OBJECT-TYPE	
		SYNTAX			INTEGER { enable ( 1 ) , disable ( 2 ) }
		MAX-ACCESS		read-only
		STATUS			current
		DESCRIPTION		"Load balance state of this BSS"
		::=  {  azaleaDot11BssEntry  27  }

    azlDot11BssWmmState OBJECT-TYPE	
		SYNTAX			INTEGER { enable ( 1 ) , disable ( 2 ) }
		MAX-ACCESS		read-only
		STATUS			current
		DESCRIPTION		"WMM state of this BSS"
		::=  {  azaleaDot11BssEntry  28  }

    azlDot11BssSecurityType 	OBJECT-TYPE	
		SYNTAX			INTEGER  {
        		open(1),
       			openWep(2),
        		sharedWep(3),
        		wpa(4),
        		wpa2(5),
        		wapi(6)
		}
		MAX-ACCESS		read-only
		STATUS			current
		DESCRIPTION		"The security type of the BSS"
		::=  {  azaleaDot11BssEntry  29  }

	azlDot11PSKWord	OBJECT-TYPE	
		SYNTAX			OCTET STRING  ( SIZE ( 0 .. 128  ) ) 
		MAX-ACCESS		read-only
		STATUS			current
		DESCRIPTION		"The PSK keyword of the BSS"
		::=  {  azaleaDot11BssEntry  30  }

	azlDot11KeyAsciiHex	OBJECT-TYPE	
		SYNTAX			INTEGER  {keyHex(0), keyAscii(1)}
		MAX-ACCESS		read-only
		STATUS			current
		DESCRIPTION		"The key type of the BSS"
		::=  {  azaleaDot11BssEntry  31  }
		
--	azlDot11WAPIPSKWord	OBJECT-TYPE	
--		SYNTAX			OCTET STRING  ( SIZE ( 0 .. 128  ) ) 
--		MAX-ACCESS		read-write
--		STATUS			current
--		DESCRIPTION		"The WAPI PSK keyword of the BSS."
--		::=  {  azaleaDot11BssEntry  32  }
--
--	azlDot11WAPIKeyAsciiHex	OBJECT-TYPE	
--		SYNTAX			INTEGER  {keyHex(0), keyAscii(1)}
--		MAX-ACCESS		read-write
--		STATUS			current
--		DESCRIPTION		"key type."
--		::=  {  azaleaDot11BssEntry  33  }
		
	azaleaDot11BssStatTable	OBJECT-TYPE
		SYNTAX		SEQUENCE  OF  AzaleaDot11BssStatEntry
		MAX-ACCESS	not-accessible
		STATUS		current
		DESCRIPTION	"A table of BSS statistics"
		::=  { azaleaDot11BssObjects  2 }

	azaleaDot11BssStatEntry	OBJECT-TYPE
		SYNTAX		AzaleaDot11BssStatEntry
		MAX-ACCESS	not-accessible
		STATUS		current
		DESCRIPTION	"A statistics entry for this BSS"
		INDEX		{  ifIndex, azlDot11BssIndex  }
		::=  { azaleaDot11BssStatTable 1 }

	AzaleaDot11BssStatEntry  ::=  SEQUENCE {
		azlDot11BssAssociatedStation  Integer32,
		azlDot11BssAssociatedRoamingStation Integer32,
		azlDot11BssTotalAssociationRequests Counter32,
		azlDot11BssTotalFailedAssociation Counter32,
		azlDot11BssTotalRepeatedAssociation Counter32,
		azlDot11BssTotalRejectedAssociation Counter32,
		azlDot11BssTotalRoamAssociation Counter32,
		azlDot11BssFailedRoamAssociation Counter32,
		azlDot11BssIntraDomainRoamSuccessPercentage Counter32,
		azlDot11BssClientLeaveDisassoc Counter32,
		azlDot11BssInsufResDisassoc Counter32,
		azlDot11BssErrorDisassoc Counter32,
		azlDot11BssOtherDisassoc Counter32,
		azlDOt11BssLoadBalanceRejectedAssociation Counter32,
		azlDot11BssStationLimitRejectedAssociation Counter32,
		azlDot11BssLoadBalanceDisassociatedStation Counter32,
		azlDot11BssNfaInsufficientResource Counter32,
--		azlDot11BssTotalSuccAssociation Counter32,
--		azlDot11BssExceptionDisassoc Counter32,
--		azlDot11BssTotalAssociationCount Counter32,
--		azlDot11BssTotalAssociationMinutes Counter32,
		azlDot11BssRxBytes Counter32,
		azlDot11BssRxPackets Counter32,
		azlDot11BssRxErrors Counter32,
		azlDot11BssRxDropped Counter32,
		azlDot11BssRxNonUnicast Counter32,
		azlDot11BssTxBytes Counter32,
		azlDot11BssTxPackets Counter32,
		azlDot11BssTxErrors Counter32,
		azlDot11BssTxDropped Counter32
--		azlDot11BssRxDataFrameCnt Counter32,
--		azlDot11BssRxAuthenFrameCnt Counter32,
--		azlDot11BssRxAssociateFrameCnt Counter32,
--		azlDot11BssTxDataFrameCnt Counter32,
--		azlDot11BssTxAuthenFrameCnt Counter32,
--		azlDot11BssTxAssociateFrameCnt Counter32,
--		azlDot11BssWirelessOutPackets Counter32,
--		azlDot11BssWirelessInPackets Counter32,
--		azlDot11BssWirelessOutOctets Counter32,
--		azlDot11BssWirelessInOctets Counter32,
--		azlDot11BssDwlinkRetryPkts Counter32,
--		azlDot11BssChStatsUpLinkUniFrameCnt Counter32,
--		azlDot11BssChStatsDwlinkUniFrameCnt Counter32,
--		azlDot11BssUpLinkNonUniFrameCnt Counter32,
--		azlDot11BssDwlinkNonUniFrameCnt Counter32,
--		azlDot11BssTxDataFrameCntDup Counter32,
--		azlDot11BssTxSignalPkts Counter32,
--		azlDot11BssRxSignalPkts Counter32,
--		azlDot11BssRxCtrlFrameCnt Counter32,
--		azlDot11BssTxCtrlFrameCnt Counter32,
--		azlDot11BssChannelUsagePercentage Gauge32,
--		azlDot11BssSuccAssocDelta Counter32,
--		azlDot11BssAssocReqDelta Counter32,
--		azlDot11BssAssocRespDelta Counter32
		}


        azlDot11BssAssociatedStation    OBJECT-TYPE
                SYNTAX                  Integer32
                MAX-ACCESS              read-only
                STATUS                  current
                DESCRIPTION             "The number of associated stations on this BSS"
                ::=  {  azaleaDot11BssStatEntry  1  }
        azlDot11BssAssociatedRoamingStation     OBJECT-TYPE
                SYNTAX                  Integer32
                MAX-ACCESS              read-only
                STATUS                  current
                DESCRIPTION             "Current number of roaming clients on this BSS"
                ::=  {  azaleaDot11BssStatEntry  2  }
        azlDot11BssTotalAssociationRequests     OBJECT-TYPE
                SYNTAX                  Counter32
                MAX-ACCESS              read-only
                STATUS                  current
                DESCRIPTION             "Total number of association requests received"
                ::=  {  azaleaDot11BssStatEntry  3  }
        azlDot11BssTotalFailedAssociation       OBJECT-TYPE
                SYNTAX                  Counter32
                MAX-ACCESS              read-only
                STATUS                  current
                DESCRIPTION             "Total number of failed associations on this BSS"
                ::=  {  azaleaDot11BssStatEntry  4  }
        azlDot11BssTotalRepeatedAssociation     OBJECT-TYPE
                SYNTAX                  Counter32
                MAX-ACCESS              read-only
                STATUS                  current
                DESCRIPTION             "Total number of repeat associations on this BSS"
                ::=  {  azaleaDot11BssStatEntry  5  }
        azlDot11BssTotalRejectedAssociation     OBJECT-TYPE
                SYNTAX                  Counter32
                MAX-ACCESS              read-only
                STATUS                  current
                DESCRIPTION             "Total number of layer-2 rejected associations on this BSS"
                ::=  {  azaleaDot11BssStatEntry  6  }
        azlDot11BssTotalRoamAssociation OBJECT-TYPE
                SYNTAX                  Counter32
                MAX-ACCESS              read-only
                STATUS                  current
                DESCRIPTION             "Total number of roamed associations on this BSS"
                ::=  {  azaleaDot11BssStatEntry  7  }
        azlDot11BssFailedRoamAssociation        OBJECT-TYPE
                SYNTAX                  Counter32
                MAX-ACCESS              read-only
                STATUS                  current
                DESCRIPTION             "Total number of failed roamed associations on this BSS"
                ::=  {  azaleaDot11BssStatEntry  8  }
        azlDot11BssIntraDomainRoamSuccessPercentage     OBJECT-TYPE
                SYNTAX                  Counter32
                MAX-ACCESS              read-only
                STATUS                  current
                DESCRIPTION             "Percentage (0-100) of successful roamed associations on this BSS"
                ::=  {  azaleaDot11BssStatEntry  9  }

        azlDot11BssClientLeaveDisassoc OBJECT-TYPE
                SYNTAX                  Counter32
                MAX-ACCESS              read-only
                STATUS                  current
                DESCRIPTION             "Total number of client leave disassociation events"
                ::=  {  azaleaDot11BssStatEntry  10  }

        azlDot11BssInsufResDisassoc OBJECT-TYPE
                SYNTAX                  Counter32
                MAX-ACCESS              read-only
                STATUS                  current
                DESCRIPTION             "Total number of client disassociation events due to AP resource issue"
                ::=  {  azaleaDot11BssStatEntry  11  }

        azlDot11BssErrorDisassoc OBJECT-TYPE
                SYNTAX                  Counter32
                MAX-ACCESS              read-only
                STATUS                  current
                DESCRIPTION             "Total number of client disassociation events due to exceptions"
                ::=  {  azaleaDot11BssStatEntry  12  }

        azlDot11BssOtherDisassoc OBJECT-TYPE
                SYNTAX                  Counter32
                MAX-ACCESS              read-only
                STATUS                  current
                DESCRIPTION             "Total number of client disassociation events due to other reasons"
                ::=  {  azaleaDot11BssStatEntry  13  }
        
	azlDOt11BssLoadBalanceRejectedAssociation OBJECT-TYPE
                SYNTAX                  Counter32
                MAX-ACCESS              read-only
                STATUS                  current
                DESCRIPTION             "Total number of rejected client associations due to load balancing"
                ::=  {  azaleaDot11BssStatEntry  14  }

	azlDot11BssStationLimitRejectedAssociation OBJECT-TYPE
                SYNTAX                  Counter32
                MAX-ACCESS              read-only
                STATUS                  current
                DESCRIPTION             "Total number of rejected client associations due to max station limit"
                ::=  {  azaleaDot11BssStatEntry  15  }
        
	azlDot11BssLoadBalanceDisassociatedStation OBJECT-TYPE
                SYNTAX                  Counter32
                MAX-ACCESS              read-only
                STATUS                  current
                DESCRIPTION             "Total number of disassociated stations due to load balancing"
                ::=  {  azaleaDot11BssStatEntry  16  }

	azlDot11BssNfaInsufficientResource OBJECT-TYPE
                SYNTAX                  Counter32
                MAX-ACCESS              read-only
                STATUS                  current
                DESCRIPTION             "Total number of ejected associations on this BSS due to insufficient resource"
                ::=  {  azaleaDot11BssStatEntry  17  }

--	azlDot11BssTotalSuccAssociation OBJECT-TYPE
--                SYNTAX                  Counter32
--                MAX-ACCESS              read-only
--                STATUS                  current
--                DESCRIPTION             "Total number of successful assocations on this BSS"
--                ::=  {  azaleaDot11BssStatEntry  18  }
--
--	azlDot11BssExceptionDisassoc OBJECT-TYPE
--                SYNTAX                  Counter32
--                MAX-ACCESS              read-only
--                STATUS                  current
--                DESCRIPTION             "Total number of disasscoations on this BSS that were caused by exceptions"
--                ::=  {  azaleaDot11BssStatEntry  19  }
--
--        azlDot11BssTotalAssociationCount     OBJECT-TYPE
--                SYNTAX                  Counter32
--                MAX-ACCESS              read-only
--                STATUS                  current
--                DESCRIPTION             "Total number of completed client associations"
--                ::=  {  azaleaDot11BssStatEntry  20  }
--
--        azlDot11BssTotalAssociationMinutes     OBJECT-TYPE
--                SYNTAX                  Counter32
--                MAX-ACCESS              read-only
--                STATUS                  current
--                DESCRIPTION             "Total time of all associated client sessions"
--                ::=  {  azaleaDot11BssStatEntry  21  }

	azlDot11BssRxBytes OBJECT-TYPE
                SYNTAX                  Counter32
                MAX-ACCESS              read-only
                STATUS                  current
                DESCRIPTION             "Total number of received bytes on this BSS"
                ::=  {  azaleaDot11BssStatEntry  30  }

	azlDot11BssRxPackets OBJECT-TYPE
                SYNTAX                  Counter32
                MAX-ACCESS              read-only
                STATUS                  current
                DESCRIPTION             "Total number of receveid packets on this BSS"
                ::=  {  azaleaDot11BssStatEntry  31  }

	azlDot11BssRxErrors OBJECT-TYPE
                SYNTAX                  Counter32
                MAX-ACCESS              read-only
                STATUS                  current
                DESCRIPTION             "Total number of receive errors on this BSS"
                ::=  {  azaleaDot11BssStatEntry  32  }

	azlDot11BssRxDropped OBJECT-TYPE
                SYNTAX                  Counter32
                MAX-ACCESS              read-only
                STATUS                  current
                DESCRIPTION             "Total number of received but dropped packets on this BSS"
                ::=  {  azaleaDot11BssStatEntry  33  }

	azlDot11BssRxNonUnicast OBJECT-TYPE
                SYNTAX                  Counter32
                MAX-ACCESS              read-only
                STATUS                  current
                DESCRIPTION             "Total number of non-unicast packets received on this BSS"
                ::=  {  azaleaDot11BssStatEntry  34  }

	azlDot11BssTxBytes OBJECT-TYPE
                SYNTAX                  Counter32
                MAX-ACCESS              read-only
                STATUS                  current
                DESCRIPTION             "Total number of successfully transmitted bytes on this BSS"
                ::=  {  azaleaDot11BssStatEntry  35  }

	azlDot11BssTxPackets OBJECT-TYPE
                SYNTAX                  Counter32
                MAX-ACCESS              read-only
                STATUS                  current
                DESCRIPTION             "Total number of successful transmitted packets on this BSS"
                ::=  {  azaleaDot11BssStatEntry  36  }

	azlDot11BssTxErrors OBJECT-TYPE
                SYNTAX                  Counter32
                MAX-ACCESS              read-only
                STATUS                  current
                DESCRIPTION             "Total number of transmit Errors on this BSS"
                ::=  {  azaleaDot11BssStatEntry  37  }

	azlDot11BssTxDropped OBJECT-TYPE
                SYNTAX                  Counter32
                MAX-ACCESS              read-only
                STATUS                  current
                DESCRIPTION             "Total number of dropped packets in transmit queue on this BSS"
                ::=  {  azaleaDot11BssStatEntry  38  }

--		azlDot11BssRxDataFrameCnt OBJECT-TYPE
--        SYNTAX Counter32
--        MAX-ACCESS read-only
--        STATUS current
--        DESCRIPTION "Total number of RX data frame on this BSS"
--                ::=  {  azaleaDot11BssStatEntry  39  }
--
--		azlDot11BssRxAuthenFrameCnt OBJECT-TYPE
--        SYNTAX Counter32
--        MAX-ACCESS read-only
--        STATUS current
--        DESCRIPTION "Total number of RX authentication frame on this BSS"
--                ::=  {  azaleaDot11BssStatEntry  40  }
--
--		azlDot11BssRxAssociateFrameCnt OBJECT-TYPE
--        SYNTAX Counter32
--        MAX-ACCESS read-only
--        STATUS current
--        DESCRIPTION
--        "Total number of RX associate frame on this BSS"
--                ::=  {  azaleaDot11BssStatEntry  41  }
--
--		azlDot11BssTxDataFrameCnt OBJECT-TYPE
--        SYNTAX Counter32
--        MAX-ACCESS read-only
--        STATUS current
--        DESCRIPTION "Total number of TX data frame on this BSS"
--                ::=  {  azaleaDot11BssStatEntry  42  }

--		azlDot11BssTxAuthenFrameCnt OBJECT-TYPE
--        SYNTAX Counter32
--        MAX-ACCESS read-only
--        STATUS current
--        DESCRIPTION "Total number of TX authentication frame on this BSS"
--                ::=  {  azaleaDot11BssStatEntry  43  }
--
--		azlDot11BssTxAssociateFrameCnt OBJECT-TYPE
--        SYNTAX Counter32
--        MAX-ACCESS read-only
--        STATUS current
--        DESCRIPTION "Total number of TX associate frame on this BSS"
--                ::=  {  azaleaDot11BssStatEntry  44  }
--
--	azlDot11BssWirelessOutPackets OBJECT-TYPE
--        SYNTAX Counter32
--        MAX-ACCESS read-only
--        STATUS current
--        DESCRIPTION "octets the wireless side had sended"
--                ::=  {  azaleaDot11BssStatEntry  45  }
--
--	azlDot11BssWirelessInPackets OBJECT-TYPE
--        SYNTAX Counter32
--        MAX-ACCESS read-only
--        STATUS current
--        DESCRIPTION "receive Packets on the wireless side"
--                ::=  {  azaleaDot11BssStatEntry  46  }
--
--	azlDot11BssWirelessOutOctets OBJECT-TYPE
--        SYNTAX Counter32
--        MAX-ACCESS read-only
--        STATUS current
--        DESCRIPTION "octets the wireless side had sended"
--                ::=  {  azaleaDot11BssStatEntry  47  }

--	azlDot11BssWirelessInOctets OBJECT-TYPE
--        SYNTAX Counter32
--        MAX-ACCESS read-only
--        STATUS current
--        DESCRIPTION "receive octets on the wireless side"
--                ::=  {  azaleaDot11BssStatEntry  48  }
--
--	azlDot11BssDwlinkRetryPkts OBJECT-TYPE
--        SYNTAX Counter32
--        MAX-ACCESS read-only
--        STATUS current
--        DESCRIPTION "downlink retry packets"
--                ::=  {  azaleaDot11BssStatEntry  49  }
--
--	azlDot11BssChStatsUpLinkUniFrameCnt OBJECT-TYPE
--        SYNTAX Counter32
--        MAX-ACCESS read-only
--        STATUS current
--        DESCRIPTION ""
--                ::=  {  azaleaDot11BssStatEntry  50  }
--
--	azlDot11BssChStatsDwlinkUniFrameCnt OBJECT-TYPE
--        SYNTAX Counter32
--        MAX-ACCESS read-only
--        STATUS current
--        DESCRIPTION "znBssidChStatsDwlinkUniFrameCnt"
--                ::=  {  azaleaDot11BssStatEntry  51  }
--
--	azlDot11BssUpLinkNonUniFrameCnt OBJECT-TYPE
--        SYNTAX Counter32
--        MAX-ACCESS read-only
--        STATUS current
--        DESCRIPTION "uplink NonUniFrame count"
--                ::=  {  azaleaDot11BssStatEntry  52  }

--	azlDot11BssDwlinkNonUniFrameCnt OBJECT-TYPE
--        SYNTAX Counter32
--        MAX-ACCESS read-only
--        STATUS current
--        DESCRIPTION "downlink NonUniFrame count"
--                ::=  {  azaleaDot11BssStatEntry  53  }
--
--		azlDot11BssTxDataFrameCntDup OBJECT-TYPE
--        SYNTAX Counter32
--        MAX-ACCESS read-only
--        STATUS current
--        DESCRIPTION "uplink NonUniFrame count"
--                ::=  {  azaleaDot11BssStatEntry  54  }
--
--		azlDot11BssTxSignalPkts OBJECT-TYPE
--        SYNTAX Counter32
--        MAX-ACCESS read-only
--        STATUS current
--        DESCRIPTION "TxSignalPkts"
--                ::=  {  azaleaDot11BssStatEntry  55  }
--
--		azlDot11BssRxSignalPkts OBJECT-TYPE
--        SYNTAX Counter32
--        MAX-ACCESS read-only
--        STATUS current
--        DESCRIPTION "RxSignalPkts"
--                ::=  {  azaleaDot11BssStatEntry  56  }

--		azlDot11BssRxCtrlFrameCnt OBJECT-TYPE
--        SYNTAX Counter32
--        MAX-ACCESS read-only
--        STATUS current
--        DESCRIPTION
--        "znBssidRxCtrlFrameCnt"
--                ::=  {  azaleaDot11BssStatEntry  57  }
--
--		azlDot11BssTxCtrlFrameCnt OBJECT-TYPE
--        SYNTAX Counter32
--        MAX-ACCESS read-only
--        STATUS current
--        DESCRIPTION "znBssidTxCtrlFrameCnt"
--
--                ::=  {  azaleaDot11BssStatEntry  58  }
--
--		azlDot11BssChannelUsagePercentage OBJECT-TYPE
--        SYNTAX Gauge32
--        MAX-ACCESS read-only
--        STATUS current
--        DESCRIPTION ""
--
--                ::=  {  azaleaDot11BssStatEntry  59  }
--
--		azlDot11BssSuccAssocDelta OBJECT-TYPE
--        SYNTAX Counter32
--        MAX-ACCESS read-only
--        STATUS current
--        DESCRIPTION ""
--
--                ::=  {  azaleaDot11BssStatEntry  100  }

--			azlDot11BssAssocReqDelta OBJECT-TYPE
--			SYNTAX Counter32
--			MAX-ACCESS read-only
--			STATUS current
--			DESCRIPTION ""
--	
--					::=  {  azaleaDot11BssStatEntry  101  }
--	
--			azlDot11BssAssocRespDelta OBJECT-TYPE
--			SYNTAX Counter32
--			MAX-ACCESS read-only
--			STATUS current
--			DESCRIPTION ""
--	
--               ::=  {  azaleaDot11BssStatEntry  102  }


	azaleaDot11ClientInfoTable	OBJECT-TYPE
		SYNTAX		SEQUENCE  OF  AzaleaDot11ClientInfoEntry
		MAX-ACCESS	not-accessible
		STATUS		current
		DESCRIPTION	"This table contains configuration information and 
            statistics of client devices.  Entries on this table are
            created by the device radio driver when clients establish
            association with the device.  Entries are removed
            when clients disassociate with the device."
		::=  { azaleaDot11BssObjects  4 }

	azaleaDot11ClientInfoEntry	OBJECT-TYPE
		SYNTAX		AzaleaDot11ClientInfoEntry
		MAX-ACCESS	not-accessible
		STATUS		current
		DESCRIPTION	"Each entry is the device specification of a client
            of this device on the IEEE 802.11 radio interfaces.
            Clients are grouped according to the SSIDs of the
            interfaces they use for associations"
		INDEX		{  ifIndex, azlDot11BssIndex, azlDot11ClientMacAddress }
		::=  { azaleaDot11ClientInfoTable 1 }

	AzaleaDot11ClientInfoEntry  ::=  SEQUENCE {
		azlDot11ClientMacAddress  MacAddress,
		azlDot11ClientAid  Integer32,  
		azlDot11ClientFlags  Integer32,
		azlDot11ClientListenInterval  Integer32,
		azlDot11ClientSessionStart  Integer32,
		azlDot11ClientAssocTime  TimeTicks,
		azlDot11ClientRssi  Integer32,
		azlDot11ClientIpAddress  IpAddress,
		azlDot11ClientRxPackets  Counter32,
		azlDot11ClientTxSuccPackets  Counter32,
		azlDot11ClientRxBytes  Counter32,
		azlDot11ClientTxBytes  Counter32,
		azlDot11ClientTxRateCurrent Gauge32,
		azlDot11ClientTxRateAve  Gauge32,
		azlDot11ClientRxRateAve  Gauge32,
		azlDot11ClientTxRetryPackets Counter32,
		azlDot11ClientRxDroppedPackets Counter32,
		azlDot11ClientTxFailedPackets Counter32,
		azlDot11ClientTxRetryBytes  Counter32,
		azlDot11ClientRxRetryBytes  Counter32,
		azlDot11ClientRxRetryPackets  Counter32,
		azlDot11ClientRxErrorPackets Counter32,
--		azlDot11ClientPowerSaveMode  Integer32,  
		azlDot11ClientAzModel  DisplayString,
		azlDot11ClientOemModel  DisplayString,
		azlDot11ClientAssocSSID  DisplayString,
		azlDot11ClientSecurity  Integer32,
		azlDot11ClientAuthMode  Integer32,
		azlDot11ClientCipher  Integer32,
		azlDot11ClientSNR  Integer32,
		azlDot11ClientWirelessMode  Integer32,
		azlDot11ClientChannelWidth  Integer32,
		azlDot11ClientHAPMACAddress  MacAddress,
		azlDot11ClientCAPMACAddress  MacAddress,
		azlDot11ClientPAPMACAddress  MacAddress
		}


	azlDot11ClientMacAddress	OBJECT-TYPE	
		SYNTAX			MacAddress
		MAX-ACCESS		read-only
		STATUS			current
		DESCRIPTION		"The MAC address of the client."
		::=  {  azaleaDot11ClientInfoEntry  1  }

	azlDot11ClientAid	OBJECT-TYPE	
		SYNTAX			Integer32  ( 0 .. 2007  ) 
		MAX-ACCESS		read-only
		STATUS			current
		DESCRIPTION		" Association ID of the client, (1 .. 2007) or 0 if not yet assigned."
		::=  {  azaleaDot11ClientInfoEntry  2  }

	azlDot11ClientFlags	OBJECT-TYPE	
		SYNTAX			Integer32
		MAX-ACCESS		read-only
		STATUS			current
		DESCRIPTION		"Client's status :
            bit0 Authorized, 
			bit1 QoS enabled, 
			bit2 Effective Radiated Power enabled,
            bit3 High Throughput enabled, 
			bit4 Power save mode enabled, 
--			bit5 Authentication ref held,
--            bit6 U-APSD power save enabled, 
--			bit7 U-APSD triggerable state,
--            bit8 U-APSD SP in progress, 
--			bit9 Atheros Owl or follow-on device, 
--			bit10 Owl WDS workaround needed,
--            bit11 WDS link, 
--			bit12 No AMPDU support, 
--			bit13 Atheros proprietary wep/tkip aggregation support,
--            bit14 TKIP CIPHER
			"
		::=  {  azaleaDot11ClientInfoEntry  4  }


	azlDot11ClientListenInterval	OBJECT-TYPE	
		SYNTAX			Integer32
		MAX-ACCESS		read-only
		STATUS			current
		DESCRIPTION		"Listen interval of client, the unit is beacon interval"
		::=  {  azaleaDot11ClientInfoEntry  5  }

--  not supported
--	azlDot11ClientSessionStart	OBJECT-TYPE	
--		SYNTAX			Integer32
--		MAX-ACCESS		read-only
--		STATUS			current
--		DESCRIPTION		"time_t value of sesson start time"
--		::=  {  azaleaDot11ClientInfoEntry  7  }


	azlDot11ClientAssocTime	OBJECT-TYPE	
		SYNTAX			TimeTicks
		MAX-ACCESS		read-only
		STATUS			current
		DESCRIPTION		"The time value of sta associated time in 1/100 second"
		::=  {  azaleaDot11ClientInfoEntry  8  }


	azlDot11ClientRssi	OBJECT-TYPE	
		SYNTAX			Integer32
		MAX-ACCESS		read-only
		STATUS			current
		DESCRIPTION		"The RSSI of the association station between BSS"
		::=  {  azaleaDot11ClientInfoEntry  9  }


	azlDot11ClientIpAddress	OBJECT-TYPE	
		SYNTAX			IpAddress
		MAX-ACCESS		read-only
		STATUS			current
		DESCRIPTION		"The IP Address of the station"
		::=  {  azaleaDot11ClientInfoEntry  10  }


	azlDot11ClientRxPackets	OBJECT-TYPE	
		SYNTAX			Counter32
		MAX-ACCESS		read-only
		STATUS			current
		DESCRIPTION		"The number of the received packets of this station"
		::=  {  azaleaDot11ClientInfoEntry  11  }


	azlDot11ClientTxSuccPackets	OBJECT-TYPE	
		SYNTAX			Counter32
		MAX-ACCESS		read-only
		STATUS			current
		DESCRIPTION		"The number of the transmitted packets of this station"
		::=  {  azaleaDot11ClientInfoEntry  12  }


	azlDot11ClientRxBytes	OBJECT-TYPE	
		SYNTAX			Counter32
		MAX-ACCESS		read-only
		STATUS			current
		DESCRIPTION		"The number of the received data bytes of this station"
		::=  {  azaleaDot11ClientInfoEntry  13  }


	azlDot11ClientTxBytes	OBJECT-TYPE	
		SYNTAX			Counter32
		MAX-ACCESS		read-only
		STATUS			current
		DESCRIPTION		"The number of the transmitted data bytes of this station"
		::=  {  azaleaDot11ClientInfoEntry  14  }


	azlDot11ClientTxRateCurrent OBJECT-TYPE
			SYNTAX                  Gauge32
			MAX-ACCESS              read-only
			STATUS                  current
			DESCRIPTION             "The current transmit rate (in 100kbps)"
			::=  {  azaleaDot11ClientInfoEntry  15  }

	azlDot11ClientTxRateAve OBJECT-TYPE
			SYNTAX                  Gauge32
			MAX-ACCESS              read-only
			STATUS                  current
			DESCRIPTION             "The recent average transmit rate (in 100kbps)"
			::=  {  azaleaDot11ClientInfoEntry  16  }


	azlDot11ClientRxRateAve OBJECT-TYPE
			SYNTAX                  Gauge32
			MAX-ACCESS              read-only
			STATUS                  current
			DESCRIPTION             "The recent average receive rate (in 100kbps)"
			::=  {  azaleaDot11ClientInfoEntry  17  }

	azlDot11ClientTxRetryPackets OBJECT-TYPE	
		SYNTAX			Counter32
		MAX-ACCESS		read-only
		STATUS			current
		DESCRIPTION		"The number of recent transmit retry packets"
		::=  {  azaleaDot11ClientInfoEntry  18  }   
		
	azlDot11ClientTxFailedPackets OBJECT-TYPE	
		SYNTAX			Counter32
		MAX-ACCESS		read-only
		STATUS			current
		DESCRIPTION		"The number of recent transmit failed packets"
		::=  {  azaleaDot11ClientInfoEntry  19  }

    azlDot11ClientTxRetryBytes OBJECT-TYPE	
		SYNTAX			Counter32
		MAX-ACCESS		read-only
		STATUS			current
		DESCRIPTION		"The number of recent transmit retry bytes"
		::=  {  azaleaDot11ClientInfoEntry  20  }  
		   
	azlDot11ClientRxRetryBytes OBJECT-TYPE	
		SYNTAX			Counter32
		MAX-ACCESS		read-only
		STATUS			current
		DESCRIPTION		"The number of recent receive retry bytes"
		::=  {  azaleaDot11ClientInfoEntry  21  }

	azlDot11ClientRxDroppedPackets OBJECT-TYPE	
		SYNTAX			Counter32
		MAX-ACCESS		read-only
		STATUS			current
		DESCRIPTION		"Total receive dropped packets"
		::=  {  azaleaDot11ClientInfoEntry  22 }

	azlDot11ClientRxRetryPackets OBJECT-TYPE	
		SYNTAX			Counter32
		MAX-ACCESS		read-only
		STATUS			current
		DESCRIPTION		"Total receive retry packets"
		::=  {  azaleaDot11ClientInfoEntry  23 }

	azlDot11ClientRxErrorPackets OBJECT-TYPE	
		SYNTAX			Counter32
		MAX-ACCESS		read-only
		STATUS			current
		DESCRIPTION		"Total receive error packets"
		::=  {  azaleaDot11ClientInfoEntry  24 }

--  commented for cleanup
--	azlDot11ClientPowerSaveMode OBJECT-TYPE
--                SYNTAX INTEGER {active(0),powersave(1)}
--                MAX-ACCESS read-only
--                STATUS current
--                DESCRIPTION
--                     "The StaPowerSaveMode."
--		::=  {  azaleaDot11ClientInfoEntry  33 }

	azlDot11ClientAzModel	OBJECT-TYPE	
		SYNTAX			DisplayString
		MAX-ACCESS		read-only
		STATUS			current
		DESCRIPTION		"the Azalea model name of associated client"
		::=  {  azaleaDot11ClientInfoEntry  42  }

	azlDot11ClientOemModel	OBJECT-TYPE	
		SYNTAX			DisplayString
		MAX-ACCESS		read-only
		STATUS			current
		DESCRIPTION		"the OEM model name of associated client"
		::=  {  azaleaDot11ClientInfoEntry  43  }

	azlDot11ClientAssocSSID	OBJECT-TYPE	
		SYNTAX			DisplayString
		MAX-ACCESS		read-only
		STATUS			current
		DESCRIPTION		"the SSID of the AP the client associated client"
		::=  {  azaleaDot11ClientInfoEntry  51  }

	azlDot11ClientSecurity	OBJECT-TYPE	
		SYNTAX			INTEGER { open(0), wep(1), wpa(2), wpa2(3), shared-wep(4) }
		MAX-ACCESS		read-only
		STATUS			current
		DESCRIPTION		"the Security policy the client used"
		::=  {  azaleaDot11ClientInfoEntry  52  }

	azlDot11ClientAuthMode	OBJECT-TYPE	
		SYNTAX			INTEGER { none(0), psk(1), ieee8021x(2), wapi-cert(3), other(4) }
		MAX-ACCESS		read-only
		STATUS			current
		DESCRIPTION		"the authentication method the client used"
		::=  {  azaleaDot11ClientInfoEntry  53  }

	azlDot11ClientCipher	OBJECT-TYPE	
		SYNTAX			INTEGER { none(0), wep(1), tkip(2), aes(3), other(4) }
		MAX-ACCESS		read-only
		STATUS			current
		DESCRIPTION		"the cipher method the client used"
		::=  {  azaleaDot11ClientInfoEntry  54  }

	azlDot11ClientSNR	OBJECT-TYPE	
		SYNTAX			INTEGER (0..127)
		MAX-ACCESS		read-only
		STATUS			current
		DESCRIPTION		"the SNR of the client connected"
		::=  {  azaleaDot11ClientInfoEntry  61  }

	azlDot11ClientWirelessMode	OBJECT-TYPE	
		SYNTAX			INTEGER { ieee80211a(1), ieee80211b(2), ieee80211g(3), ieee80211g-only(4), ieee80211na(5), ieee80211na-ht40minus(6), ieee80211na-ht40plus(7), ieee80211ng(8), ieee80211ng-ht40minus(9), ieee80211ng-ht40plus(10) }
		MAX-ACCESS		read-only
		STATUS			current
		DESCRIPTION		"the wireless mode of the client connected"
		::=  {  azaleaDot11ClientInfoEntry  62  }

	azlDot11ClientChannelWidth	OBJECT-TYPE	
		SYNTAX			INTEGER { channelWidth5M(5), channelWidth10M(10), channelWidth20M(20), channelWidth40M(40) }
		MAX-ACCESS		read-only
		STATUS			current
		DESCRIPTION		"the Channel Width the client connected"
		::=  {  azaleaDot11ClientInfoEntry  63  }

	azlDot11ClientHAPMACAddress	OBJECT-TYPE	
		SYNTAX			MacAddress
		MAX-ACCESS		read-only
		STATUS			current
		DESCRIPTION		"the MAC address of the Home AP the client connected"
		::=  {  azaleaDot11ClientInfoEntry  71  }

	azlDot11ClientPAPMACAddress	OBJECT-TYPE	
		SYNTAX			MacAddress
		MAX-ACCESS		read-only
		STATUS			current
		DESCRIPTION		"the MAC address of the Previous AP the client connected"
		::=  {  azaleaDot11ClientInfoEntry  72  }

	azlDot11ClientCAPMACAddress	OBJECT-TYPE	
		SYNTAX			MacAddress
		MAX-ACCESS		read-only
		STATUS			current
		DESCRIPTION		"the MAC address of the Current AP the client connected"
		::=  {  azaleaDot11ClientInfoEntry  73  }		
		

--*****************************************************************
-- azaleaDot11BssTraps
--*****************************************************************

	azaleaDot11BssTraps	OBJECT IDENTIFIER
		::=  {  azaleaDot11BssTrapObjects  2 }

	azlClientOnlineTrap 	NOTIFICATION-TYPE
		OBJECTS			{ 
			ifIndex,
			azlDot11BssIndex,
			azlDot11ClientMacAddress
			}
		STATUS			current
		DESCRIPTION		"Client Online event trap"
		::=  {  azaleaDot11BssTraps  2  }

	azlClientRoamTrap 	NOTIFICATION-TYPE
		OBJECTS			{
			ifIndex,
			azlDot11BssIndex,
			azlDot11ClientMacAddress,
			azlDot11ClientIpAddress,
			azlDot11ClientHAPMACAddress,
			azlDot11ClientCAPMACAddress,
			azlDot11ClientPAPMACAddress			
			}
		STATUS			current
		DESCRIPTION		"Client Roam event trap"
		::=  {  azaleaDot11BssTraps  3  }   

	azlClientOfflineTrap 	NOTIFICATION-TYPE
		OBJECTS			{
			ifIndex,
			azlDot11BssIndex,
			azlDot11ClientMacAddress
			}
		STATUS			current
		DESCRIPTION		"Clinet Offline event trap"
		::=  {  azaleaDot11BssTraps  4  }

	azlBSSCreateTrap 	NOTIFICATION-TYPE
		OBJECTS			{ ifIndex,
						 azlDot11BssIndex}
		STATUS			current
		DESCRIPTION		"BSS create event trap"
		::=  {  azaleaDot11BssTraps  5  }

	azlBSSRemoveTrap 	NOTIFICATION-TYPE
		OBJECTS			{ ifIndex,
						 azlDot11BssIndex}
		STATUS			current
		DESCRIPTION		"BSS remove event trap"
		::=  {  azaleaDot11BssTraps  6  }

	azlClientGetIPTrap 	NOTIFICATION-TYPE
		OBJECTS			{ azlDot11ClientMacAddress,
						 azlDot11ClientIpAddress}
		STATUS			current
		DESCRIPTION		"Clinet Get IP address event trap"
		::=  {  azaleaDot11BssTraps  20  }


	azaleaProvisioningMib	OBJECT IDENTIFIER ::=  {  azaleaMgmt  6  }

	azlProvisioningFileUrl	OBJECT-TYPE	
		SYNTAX			OCTET STRING
		MAX-ACCESS		read-write
		STATUS			current
		DESCRIPTION		"URL of provisioning file to download"
		::=  {  azaleaProvisioningMib  1  }


	azlProvisioningFileType	OBJECT-TYPE	
		SYNTAX			INTEGER  { partialConfigFile ( 1 ) , fullConfigFile (2), imageFile ( 3 ) } 
		MAX-ACCESS		read-write
		STATUS			current
		DESCRIPTION		"Type of provisioning file"
		::=  {  azaleaProvisioningMib  2  }


	azlProvisioningFileChecksum	OBJECT-TYPE	
		SYNTAX			OCTET STRING
		MAX-ACCESS		read-write
		STATUS			current
		DESCRIPTION		"Checksum of provisioning file"
		::=  {  azaleaProvisioningMib  3  }


	azlProvisioningApplyTime	OBJECT-TYPE	
		SYNTAX			Integer32
		MAX-ACCESS		read-write
		STATUS			current
		DESCRIPTION		"Number of seconds before applying the configuration file"
		::=  {  azaleaProvisioningMib  4  }


	azlProvisioningCurrentStatus	OBJECT-TYPE	
		SYNTAX			INTEGER  { downloading ( 1 ) , 
		downloadFailed ( 2 ) , 
		checksumFailed ( 3 ) , 
		saveFailed ( 4 ) , 
		saveSuccessful ( 5 ) , 
		appyFailed ( 6 ) , 
		applySuccessful ( 7 ), 
		inactive(8),
		applying(9)} 
		MAX-ACCESS		read-only
		STATUS			current
		DESCRIPTION		"The current status of apply provisioning file"
		::=  {  azaleaProvisioningMib  5  }

	azlProvisioningDownloadRetryNumber OBJECT-TYPE
		SYNTAX      Integer32 (0..10)
		MAX-ACCESS  read-write
		STATUS      current
		DESCRIPTION
			"The retry number when download provisioning file failed. "
		::= { azaleaProvisioningMib 6 }


azlProvisioningTraps OBJECT IDENTIFIER  ::=  {  azaleaProvisioningMib  10  }

azlProvisioningFailTrap  NOTIFICATION-TYPE
    OBJECTS    {
	azlProvisioningCurrentStatus
    }
    STATUS  current
    DESCRIPTION
        "When Provisioning fails, the trap is reported with the
        current provisioning status"
    ::= { azlProvisioningTraps 1 }

--  not supported	
--azaleaSysStatus    OBJECT IDENTIFIER ::= { azaleaSysMgmt 16 }
--
--azaleaPowerMgmt OBJECT-TYPE
--    SYNTAX      INTEGER {
--        on    (1),
--        off   (2)
--           }
--    MAX-ACCESS  read-only
--    STATUS  current
--    DESCRIPTION 
--        ""
--    ::= { azaleaSysStatus 1 } 
--
--azaleaEapAuthSupport OBJECT-TYPE
--    SYNTAX      INTEGER {
--	enable-EAP-Authentication		(0),
--	disable-EAP-Authentication		(1),
--	not-Supporting-EAP-Authentication	(2)
--    }
--    MAX-ACCESS  read-only
--    STATUS  current
--    DESCRIPTION 
--        ""
--    ::= { azaleaSysStatus 2 } 
--
--azalea11bSupport OBJECT-TYPE
--    SYNTAX      INTEGER {
--        on    (1),
--        off   (2)
--           }
--    MAX-ACCESS  read-only
--    STATUS  current
--    DESCRIPTION 
--        ""
--    ::= { azaleaSysStatus 3 } 
--
--azalea11gSupport OBJECT-TYPE
--    SYNTAX      INTEGER {
--        on    (1),
--        off   (2)
--           }
--    MAX-ACCESS  read-only
--    STATUS  current
--    DESCRIPTION 
--        ""
--    ::= { azaleaSysStatus 4 } 
--
--azalea11aSupport OBJECT-TYPE
--    SYNTAX      INTEGER {
--        on    (1),
--        off   (2)
--           }
--    MAX-ACCESS  read-only
--    STATUS  current
--    DESCRIPTION 
--        ""
--    ::= { azaleaSysStatus 5 } 
--
--azalea11nSupport OBJECT-TYPE
--    SYNTAX      INTEGER {
--        on    (1),
--        off   (2)
--           }
--    MAX-ACCESS  read-only
--    STATUS  current
--    DESCRIPTION 
--        ""
--    ::= { azaleaSysStatus 6 } 
--
--azaleaMacModeSupport OBJECT-TYPE
--    SYNTAX      INTEGER {
--        localMac  (0),
--        splitMac  (1),
--        both      (2)
--           }
--    MAX-ACCESS  read-only
--    STATUS  current
--    DESCRIPTION 
--        "AP Mac Mode Support"
--    ::= { azaleaSysStatus 7 } 
--
--azaleaEthernetDataRate OBJECT-TYPE
--    SYNTAX      INTEGER
--    MAX-ACCESS  read-only
--    STATUS  current
--    DESCRIPTION 
--        "Ethernet port data rate, in Mbps"
--    ::= { azaleaSysStatus 8 } 

sysLoggingInfoGroup        OBJECT IDENTIFIER ::= { azaleaRefMib 4 }

sysLoggingServerTable OBJECT-TYPE
	SYNTAX      SEQUENCE OF SysLoggingServerEntry
	MAX-ACCESS  not-accessible
	STATUS      current
	DESCRIPTION
		"A list of syslog server entries."
	::= { sysLoggingInfoGroup 1 }

sysLoggingServerEntry OBJECT-TYPE
	SYNTAX      SysLoggingServerEntry
	MAX-ACCESS  not-accessible
	STATUS      current
	DESCRIPTION
		"An entry containing management information applicable
		to a particular syslog server."
	INDEX       { sysLoggingServerAddress }
	::= { sysLoggingServerTable 1 }

SysLoggingServerEntry ::= SEQUENCE {
	sysLoggingServerAddress    IpAddress
}

sysLoggingServerAddress OBJECT-TYPE
	SYNTAX      IpAddress
	MAX-ACCESS  read-only
	STATUS      current
	DESCRIPTION
		"The IP address of the system log server."
	::= { sysLoggingServerEntry 1 }

--apScanInfoGroup        OBJECT IDENTIFIER ::= { azaleaRefMib 5 }

--apScanInfoTable OBJECT-TYPE
--	SYNTAX      SEQUENCE OF ApScanInfoEntry
--	MAX-ACCESS  not-accessible
--	STATUS      current
--	DESCRIPTION
--		"A list of neighbors scanned by the AP."
--	::= { apScanInfoGroup 1 }
--
--apScanInfoEntry OBJECT-TYPE
--	SYNTAX      ApScanInfoEntry
--	MAX-ACCESS  not-accessible
--	STATUS      current
--	DESCRIPTION
--		"Each entry is a neighbor of this AP."
--	INDEX       { apScanInfoId }
--	::= { apScanInfoTable 1 }
--
--ApScanInfoEntry ::=  SEQUENCE {
--    apScanInfoId   Integer32,
--    apScanInfoRssi Integer32,
--    apScanInfoSnr  Integer32,
--    apScanInfoChan Integer32,
--    apScanInfoSsid DisplayString
--}

--apScanInfoId    OBJECT-TYPE
--    SYNTAX          Integer32
--    MAX-ACCESS      read-only
--    STATUS          current
--    DESCRIPTION     "The neighbor ID."
--    ::=  {  apScanInfoEntry  1  }
--
--apScanInfoRssi    OBJECT-TYPE
--    SYNTAX          Integer32
--    MAX-ACCESS      read-only
--    STATUS          current
--    DESCRIPTION     "The neighbor RSSI scanned by this AP."
--    ::=  {  apScanInfoEntry  2  }
--
--apScanInfoSnr    OBJECT-TYPE
--    SYNTAX          Integer32
--    MAX-ACCESS      read-only
--    STATUS          current
--    DESCRIPTION     "The neighbor SNR scanned by this AP."
--    ::=  {  apScanInfoEntry  3  }
--
--apScanInfoChan    OBJECT-TYPE
--    SYNTAX          Integer32
--    MAX-ACCESS      read-only
--    STATUS          current
--    DESCRIPTION     "The channel scanned by this AP."
--    ::=  {  apScanInfoEntry  4  }
--
--apScanInfoSsid    OBJECT-TYPE
--    SYNTAX          DisplayString
--    MAX-ACCESS      read-only
--    STATUS          current
--    DESCRIPTION     "The neighbor SSID ssanned by this AP."
--    ::=  {  apScanInfoEntry  5  }

azaleaNtpMgmt    OBJECT IDENTIFIER ::= { azaleaMgmt 16 }

	azaleaNtpPeersTable OBJECT-TYPE
		SYNTAX		SEQUENCE  OF  AzaleaNtpPeersEntry
		MAX-ACCESS	not-accessible
		STATUS		current
		DESCRIPTION	"This table contains the NTP peer List."
		::=  { azaleaNtpMgmt  2 }

	azaleaNtpPeersEntry	OBJECT-TYPE
		SYNTAX		AzaleaNtpPeersEntry
		MAX-ACCESS	not-accessible
		STATUS		current
		DESCRIPTION	"The entry of the NTP peer table"
		INDEX		{azaleaNtpPeersID }
		::=  { azaleaNtpPeersTable 1 }

	AzaleaNtpPeersEntry  ::=  SEQUENCE {
		azaleaNtpPeersID    INTEGER, 
		azaleaNtpPeersConfigured  TruthValue,
		azaleaNtpPeersAddress   IpAddress 
		}

	azaleaNtpPeersID	OBJECT-TYPE	
		SYNTAX			INTEGER  
		MAX-ACCESS		read-only
		STATUS			current
		DESCRIPTION		"An integer ID that uniquely 
		identifies a peer with which the local NTP server is associated."
		::=  {  azaleaNtpPeersEntry  1  } 
		 
	azaleaNtpPeersConfigured	OBJECT-TYPE	
		SYNTAX			TruthValue 
		MAX-ACCESS		read-only
		STATUS			current
		DESCRIPTION		"This value indicate that if the association
				was created from configuration information and should not
				be demobilized if the peer becomes unreachable."
		::=  {  azaleaNtpPeersEntry  2  }
	
	azaleaNtpPeersAddress	OBJECT-TYPE	
		SYNTAX			IpAddress
		MAX-ACCESS		read-only
		STATUS			current
		DESCRIPTION		"The IP address of the NTP server."
		::=  {  azaleaNtpPeersEntry  3  }
         
	azaleaNtpSynchronizedTimeSecs OBJECT-TYPE
		SYNTAX		INTEGER
		MAX-ACCESS	read-only
		STATUS		current
		DESCRIPTION	"Current NTP synchronized network time in seconds since 1/1/1970 12:00am GMT"
		::=  { azaleaNtpMgmt  3 }

	azaleaNtpSynchronizedTimeUTCString OBJECT-TYPE
		SYNTAX		DisplayString
		MAX-ACCESS	read-only
		STATUS		current
		DESCRIPTION	"Current NTP synchronized network time in UTC string"
		::=  { azaleaNtpMgmt  4 }

--*****************************************************************
-- agentTrapMgmtGroup
--
--*****************************************************************

    agentTrapMgmtGroup OBJECT IDENTIFIER ::= { azaleaMgmt 17 }

-------------------------------------------------------
-- agentTrapDestTable
-------------------------------------------------------

    agentTrapDestTable OBJECT-TYPE
        SYNTAX      SEQUENCE OF AgentTrapDestEntry
        MAX-ACCESS  not-accessible
        STATUS      current
        DESCRIPTION
            "A table of the device's trap destination entries."
        ::= { agentTrapMgmtGroup 1 }

    agentTrapDestEntry OBJECT-TYPE
        SYNTAX      AgentTrapDestEntry
        MAX-ACCESS  not-accessible
        STATUS      current
        DESCRIPTION
            "Device's trap destination entry"
        INDEX       { agentTrapDestIpAddress }
        ::= { agentTrapDestTable 1 }

    AgentTrapDestEntry ::= SEQUENCE {
        agentTrapDestIpAddress                  IpAddress,
        agentTrapDestPort                       INTEGER,
        agentTrapDestTrapCommunity                  DisplayString,
        agentTrapDestTrapVersion                INTEGER,
        agentTrapDestTrapType                   INTEGER
    }

    agentTrapDestIpAddress OBJECT-TYPE
        SYNTAX     IpAddress
        MAX-ACCESS read-only
        STATUS     current
        DESCRIPTION
            "Trap Destination's IP Address"
        ::= { agentTrapDestEntry 1 }
    
    agentTrapDestPort OBJECT-TYPE
        SYNTAX     INTEGER (1..65535)
        MAX-ACCESS read-only
        STATUS     current
        DESCRIPTION
            "Trap Destination's Port"
        ::= { agentTrapDestEntry 2 }
    
    agentTrapDestTrapCommunity OBJECT-TYPE
        SYNTAX     DisplayString
        MAX-ACCESS read-only
        STATUS     current
        DESCRIPTION
            "The trap community used when sending trap to this destination"
        ::= { agentTrapDestEntry 3 }
    
    agentTrapDestTrapVersion OBJECT-TYPE
        SYNTAX     INTEGER {
        	v1(1),
        	v2c(2)
	}
        MAX-ACCESS read-only
        STATUS     current
        DESCRIPTION
            "The trap version used when sending trap to this destination"
        ::= { agentTrapDestEntry 4 }
    
    agentTrapDestTrapType OBJECT-TYPE
        SYNTAX     INTEGER {
        	trap(1),
        	inform(2)
	}
        MAX-ACCESS read-only
        STATUS     current
        DESCRIPTION
            "The trap type used when sending trap to this destination"
        ::= { agentTrapDestEntry 5 }

--  not supported
--********************************************************************************
--* azaleaAutoDeployment
--********************************************************************************
--    azaleaAutoDeployment OBJECT IDENTIFIER ::= { azaleaMgmt 19 }
--
--    azlAutoDepDHCPEnabled	OBJECT-TYPE
--    SYNTAX      INTEGER{disable(0), enable(1)}
--    MAX-ACCESS  read-write
--    STATUS      current
--    DESCRIPTION
--        "Azalea automatic deployment function DHCP server mode."
--    ::= { azaleaAutoDeployment  1 }
--     
--    azlAutoDepIPRangeStart	OBJECT-TYPE
--    SYNTAX      IpAddress
--    MAX-ACCESS  read-write
--    STATUS      current
--    DESCRIPTION
--        "Azalea automatic deployment function IP range start."
--    ::= { azaleaAutoDeployment  2 }
--     
--    azlAutoDepIpRangeEnd	OBJECT-TYPE
--    SYNTAX      IpAddress
--    MAX-ACCESS  read-write
--    STATUS      current
--    DESCRIPTION
--        "Azalea automatic deployment function IP range end."
--    ::= { azaleaAutoDeployment  3 }

--********************************************************************************
--* wlanAPLocation
--********************************************************************************
    wlanAPLocation OBJECT IDENTIFIER ::= { azaleaMgmt 20 }

	wlanAPLongitude OBJECT-TYPE
         SYNTAX       DisplayString
         MAX-ACCESS   read-write
         STATUS       current
         DESCRIPTION
            "Longitude of the device in DMS (Degrees,Minutes,Seconds) format, for example: '122 02 34.29 W' (DDD MM SS.SS D)."
        ::= { wlanAPLocation 1 }

    wlanAPLatitude OBJECT-TYPE
         SYNTAX       DisplayString
         MAX-ACCESS   read-write
         STATUS       current
         DESCRIPTION
            "Latitude of the device in DMS (Degrees,Minutes,Seconds) format, for example: '37 22 08.75 N'  (DD MM SS.SS D)."
        ::= { wlanAPLocation 2 }

    wlanAPAltitude OBJECT-TYPE
         SYNTAX       DisplayString
         MAX-ACCESS   read-write
         STATUS       current
         DESCRIPTION
            "Altitude of the device in decimal format, (-10000..10000) meter."
        ::= { wlanAPLocation 3 }
	

--********************************************************************************
--* Alarm information
--********************************************************************************
azaleaAlarmSerialNumber    OBJECT-TYPE
        SYNTAX INTEGER
        MAX-ACCESS      read-only
        STATUS current
        DESCRIPTION
        "The serial number of this alarm."
    ::= { azaleaAlarmInfoGroup 1 } 
	
azaleaAlarmSysIdentity    OBJECT-TYPE
        SYNTAX OCTET STRING
        MAX-ACCESS      read-only
        STATUS current
        DESCRIPTION
        "The system identity of the sender of this alarm."
    ::= { azaleaAlarmInfoGroup 2 } 
	
azaleaAlarmLevel    OBJECT-TYPE
        SYNTAX INTEGER{critical(1),major(2),minor(3),warning(4),informational(5)}
        MAX-ACCESS      read-only
        STATUS current
        DESCRIPTION
        "The level of this alarm."
    ::= { azaleaAlarmInfoGroup 3 } 
	
azaleaAlarmType    OBJECT-TYPE
        SYNTAX OCTET STRING
        MAX-ACCESS      read-only
        STATUS current
        DESCRIPTION
        "The type of this alarm."
    ::= { azaleaAlarmInfoGroup 4 } 
	
azaleaAlarmOccurTime    OBJECT-TYPE
        SYNTAX OCTET STRING
        MAX-ACCESS      read-only
        STATUS current
        DESCRIPTION
        "The occur time of this alarm."
    ::= { azaleaAlarmInfoGroup 5 } 
	
azaleaAlarmStatus    OBJECT-TYPE
        SYNTAX INTEGER{active(1),clear(2)}
        MAX-ACCESS      read-only
        STATUS current
        DESCRIPTION
        "The status of this alarm."
    ::= { azaleaAlarmInfoGroup 6 } 
	
azaleaAlarmTitle    OBJECT-TYPE
        SYNTAX OCTET STRING
        MAX-ACCESS      read-only
        STATUS current
        DESCRIPTION
        "The title of this alarm."
    ::= { azaleaAlarmInfoGroup 7 } 
	

END
