-- *****************************************************************
--
-- Copyright (c) 2005 - 2006 by Azalea Networks, Inc.
-- All rights reserved.
--
-- Description: azalea reference mib file
-- Version: V1.1
-- History:
--    V1.0
--            Initial version.
--    V1.1  03/27/2006 Jesse Song
--            assign oid to azaleaMgmt, azaleaMeshMgmt.
-- *****************************************************************

AZALEA-MESH-MIB DEFINITIONS ::= BEGIN

IMPORTS
    enterprises         FROM RFC1155-SMI
    MODULE-IDENTITY, OBJECT-TYPE,Integer32,TimeTicks,IpAddress
                                    FROM SNMPv2-SMI
    DisplayString,MacAddress,RowStatus,TruthValue	FROM SNMPv2-TC
    ifIndex	FROM RFC1213-MIB
    azalea,azaleaMgmt,basicSysInfoGroup,azaleaIfMib,azaleaIfTraps,azaleaIfTrapThreshold
		FROM AZALEA-AP-MIB;


    azaleaMeshMgmt OBJECT IDENTIFIER ::= { azaleaMgmt 1 }

sysMeshId OBJECT-TYPE
                SYNTAX DisplayString
                MAX-ACCESS read-write
                STATUS current
                DESCRIPTION "The Mesh ID of the device"
    ::= { basicSysInfoGroup 7 } 

--  not supported
--	sysMeshDeviceType OBJECT-TYPE
--                SYNTAX INTEGER {point(1),portal(2)}
--                MAX-ACCESS read-write
--                STATUS current
--                DESCRIPTION "The type of the device"
--    ::= { basicSysInfoGroup 8 } 

azaleaNewMeshMibGroup        OBJECT IDENTIFIER ::= { azaleaMeshMgmt 100 }

--sysMeshNeighborGroup        OBJECT IDENTIFIER ::= { azaleaNewMeshMibGroup 1 }

--sysMeshNeighborCount OBJECT-TYPE
--   SYNTAX Integer32
--   MAX-ACCESS read-only
--   STATUS current
--   DESCRIPTION
--   ""
--	::=  {  sysMeshNeighborGroup  1  } 
--
--
--sysMeshNeighborTable OBJECT-TYPE
--	SYNTAX      SEQUENCE OF SysMeshNeighborEntry
--	MAX-ACCESS  not-accessible
--	STATUS      current
--	DESCRIPTION
--		""
--	::= { sysMeshNeighborGroup 2 }
--
--sysMeshNeighborEntry OBJECT-TYPE
--	SYNTAX      SysMeshNeighborEntry
--	MAX-ACCESS  not-accessible
--	STATUS      current
--	DESCRIPTION ""
--	INDEX       { sysMeshNeighborIndex }
--	::= { sysMeshNeighborTable 1 }
--
--SysMeshNeighborEntry ::= SEQUENCE {
--	sysMeshNeighborIndex   Integer32,
--	sysMeshNeighborMacAddress  OCTET STRING,
--	sysMeshNeighborIpAddressStr DisplayString,
--        sysMeshNeighborRssi	Integer32
--}

--sysMeshNeighborIndex OBJECT-TYPE
--	SYNTAX      Integer32
--	MAX-ACCESS  read-only
--	STATUS      current
--	DESCRIPTION
--		""
--	::= { sysMeshNeighborEntry 1 }
--
--sysMeshNeighborMacAddress OBJECT-TYPE
--	SYNTAX      OCTET STRING
--	MAX-ACCESS  read-only
--	STATUS      current
--	DESCRIPTION
--		""
--	::= { sysMeshNeighborEntry 2 }
--
--sysMeshNeighborIpAddressStr OBJECT-TYPE
--	SYNTAX      DisplayString
--	MAX-ACCESS  read-only
--	STATUS      current
--	DESCRIPTION
--		""
--	::= { sysMeshNeighborEntry 3 }
--
--sysMeshNeighborRssi OBJECT-TYPE
--	SYNTAX      Integer32
--	MAX-ACCESS  read-only
--	STATUS      current
--	DESCRIPTION
--		""
--	::= { sysMeshNeighborEntry 4 }

sysMeshPortalListGroup        OBJECT IDENTIFIER ::= { azaleaNewMeshMibGroup 2 }

sysMeshChosenPortalIpAddressStr OBJECT-TYPE
   SYNTAX DisplayString
   MAX-ACCESS read-only
   STATUS current
   DESCRIPTION
   "The IP address of the chosen portal"
	::=  {  sysMeshPortalListGroup  1  } 

sysMeshPortalListCount OBJECT-TYPE
   SYNTAX Integer32
   MAX-ACCESS read-only
   STATUS current
   DESCRIPTION
   "The count of the entry in the portal list"
	::=  {  sysMeshPortalListGroup  2  } 


sysMeshPortalListTable OBJECT-TYPE
	SYNTAX      SEQUENCE OF SysMeshPortalListEntry
	MAX-ACCESS  not-accessible
	STATUS      current
	DESCRIPTION
		"The table of the portal list"
	::= { sysMeshPortalListGroup 3 }

sysMeshPortalListEntry OBJECT-TYPE
	SYNTAX      SysMeshPortalListEntry
	MAX-ACCESS  not-accessible
	STATUS      current
	DESCRIPTION "The entry of the portal list"
	INDEX       { sysMeshPortalMacAddress }
	::= { sysMeshPortalListTable 1 }

SysMeshPortalListEntry ::= SEQUENCE {
--        sysMeshPortalIndex Integer32,
	sysMeshPortalMacAddress  OCTET STRING,
	sysMeshPortalHopCount Integer32,
	sysMeshPortalIpAddressStr DisplayString
}

--sysMeshPortalIndex OBJECT-TYPE
--	SYNTAX      Integer32
--	MAX-ACCESS  read-only
--	STATUS      current
--	DESCRIPTION
--		""
--	::= { sysMeshPortalListEntry 1 }

sysMeshPortalMacAddress OBJECT-TYPE
	SYNTAX      OCTET STRING
	MAX-ACCESS  read-only
	STATUS      current
	DESCRIPTION
		"The MAC address of the portal"
	::= { sysMeshPortalListEntry 2 }

sysMeshPortalHopCount OBJECT-TYPE
	SYNTAX      Integer32
	MAX-ACCESS  read-only
	STATUS      current
	DESCRIPTION
		"The hop count of the portal"
	::= { sysMeshPortalListEntry 3 }

sysMeshPortalIpAddressStr OBJECT-TYPE
	SYNTAX      DisplayString
	MAX-ACCESS  read-only
	STATUS      current
	DESCRIPTION
		"The IP address of the portal"
	::= { sysMeshPortalListEntry 4 }

--sysMeshPreferPortalIpAddressStr OBJECT-TYPE
--   SYNTAX DisplayString
--   MAX-ACCESS read-write
--   STATUS current
--   DESCRIPTION
--		"The IP address of prefered portal"
--	::=  {  sysMeshPortalListGroup  4  } 

--sysMeshRoutingGroup        OBJECT IDENTIFIER ::= { azaleaNewMeshMibGroup 3 }

--sysMeshRoutingHopCountToPortal OBJECT-TYPE
--   SYNTAX Integer32
--   MAX-ACCESS read-only
--   STATUS current
--   DESCRIPTION
--   ""
--	::=  {  sysMeshRoutingGroup  1  } 
--
--sysMeshRoutingChangeCount OBJECT-TYPE
--   SYNTAX Integer32
--   MAX-ACCESS read-only
--   STATUS current
--   DESCRIPTION
--   ""
--	::=  {  sysMeshRoutingGroup  2  } 
--
--sysMeshRoutingLastChangeTime OBJECT-TYPE
--   SYNTAX DisplayString
--   MAX-ACCESS read-only
--   STATUS current
--   DESCRIPTION
--   ""
--	::=  {  sysMeshRoutingGroup  3  } 

--sysMeshRoutingLastChangeReason OBJECT-TYPE
--   SYNTAX INTEGER {
--	noChangeRecorded(0),
--	neighborUp(1),
--	neighborDown(2),
--	neighborInfoChange(3)
--   }
--   MAX-ACCESS read-only
--   STATUS current
--   DESCRIPTION
--   ""
--	::=  {  sysMeshRoutingGroup  4  } 
--
--sysMeshRoutingIntermediaryNodeTable OBJECT-TYPE
--	SYNTAX      SEQUENCE OF SysMeshRoutingIntermediaryNodeEntry
--	MAX-ACCESS  not-accessible
--	STATUS      current
--	DESCRIPTION
--		""
--	::= { sysMeshRoutingGroup 5 }
--
--sysMeshRoutingIntermediaryNodeEntry OBJECT-TYPE
--	SYNTAX      SysMeshRoutingIntermediaryNodeEntry
--	MAX-ACCESS  not-accessible
--	STATUS      current
--	DESCRIPTION ""
--	INDEX       { sysMeshRoutingIntermediaryNodeIndex }
--	::= { sysMeshRoutingIntermediaryNodeTable 1 }

--SysMeshRoutingIntermediaryNodeEntry ::= SEQUENCE {
--	sysMeshRoutingIntermediaryNodeIndex  Integer32,
--	sysMeshRoutingIntermediaryNodeMacAddress  OCTET STRING,
--	sysMeshRoutingIntermediaryNodeIpAddress DisplayString
--}
--
--sysMeshRoutingIntermediaryNodeIndex OBJECT-TYPE
--	SYNTAX      Integer32
--	MAX-ACCESS  read-only
--	STATUS      current
--	DESCRIPTION
--		""
--	::= { sysMeshRoutingIntermediaryNodeEntry 1 }
--
--sysMeshRoutingIntermediaryNodeMacAddress OBJECT-TYPE
--	SYNTAX      OCTET STRING
--	MAX-ACCESS  read-only
--	STATUS      current
--	DESCRIPTION
--		""
--	::= { sysMeshRoutingIntermediaryNodeEntry 2 }
--
--sysMeshRoutingIntermediaryNodeIpAddress OBJECT-TYPE
--	SYNTAX      DisplayString
--	MAX-ACCESS  read-only
--	STATUS      current
--	DESCRIPTION
--		""
--	::= { sysMeshRoutingIntermediaryNodeEntry 3 }

azaleaNodeInfoSyncGroup OBJECT IDENTIFIER ::=  { azaleaNewMeshMibGroup  4 }    

azaleaNodeInfoSyncEnable OBJECT-TYPE
       SYNTAX      INTEGER{disable(0), enable(1)}
       MAX-ACCESS  read-write
       STATUS      current
       DESCRIPTION
           "To enable or disable the router discover function."
       ::= { azaleaNodeInfoSyncGroup 1 } 
       
agentNodeInfoSyncTable OBJECT-TYPE
       SYNTAX      SEQUENCE OF AgentNodeInfoSyncEntry
       MAX-ACCESS  not-accessible
       STATUS      current
       DESCRIPTION
           "The list of all discovered routers in mesh."
       ::= { azaleaNodeInfoSyncGroup 2 } 
        
agentNodeInfoSyncEntry OBJECT-TYPE
       SYNTAX      AgentNodeInfoSyncEntry
       MAX-ACCESS  not-accessible                                                                                     
       STATUS      current                                                                                       
       DESCRIPTION                                                                                               
           "The entry of the discovered routers list."  
       INDEX { agentRouterID }                                                                          
       ::= { agentNodeInfoSyncTable 1 }     
       
AgentNodeInfoSyncEntry ::= SEQUENCE {
        agentRouterID  IpAddress,
        agentRouterMgmtIP   IpAddress                                                                                                                                                          
     } 
     
agentRouterID OBJECT-TYPE
       SYNTAX      IpAddress
       MAX-ACCESS  read-only
       STATUS      current
       DESCRIPTION
           "The router ID of the discovered router."
       ::= { agentNodeInfoSyncEntry 1 } 
        
agentRouterMgmtIP OBJECT-TYPE
       SYNTAX      IpAddress
       MAX-ACCESS  read-only                                                                                     
       STATUS      current                                                                                       
       DESCRIPTION                                                                                               
           "Management IP of the discovered router."                                                                            
       ::= { agentNodeInfoSyncEntry 2 } 

azaleaIfDot11WdsTable OBJECT-TYPE
	SYNTAX      SEQUENCE OF AzaleaIfDot11WdsEntry
	MAX-ACCESS  not-accessible
	STATUS      current
	DESCRIPTION
		"A list of WDS(wireless Distruction System) interface
		entries"
	::= { azaleaIfMib 4 }

azaleaIfDot11WdsEntry OBJECT-TYPE
	SYNTAX      AzaleaIfDot11WdsEntry
	MAX-ACCESS  not-accessible
	STATUS      current
        DESCRIPTION
        	"An entry containing management information applicable
		to a WDS interface."
	INDEX       { ifIndex }
	::= { azaleaIfDot11WdsTable 1 }

AzaleaIfDot11WdsEntry ::= SEQUENCE {
	azlDot11RadioIndex            Integer32,
	azlDot11WdsIndex              Integer32,
	azlDot11WdsName               OCTET STRING,
	azlDot11WdsRemoteMacAddr      MacAddress,
	azlDot11WdsRemoteNodeId       Integer32,
	azlDot11WdsRemoteRadio        Integer32,
--	azlDot11WdsRole               INTEGER,
	azlDot11WdsSsid               OCTET STRING,
--	azlDot11WdsQosProfile         OCTET STRING,
	azlDot11WdsDataRate           Integer32,
	azlDot11WdsLinkQuality        Integer32,
	azlDot11WdsRssi               Integer32,
	azlDot11WdsSnr                Integer32,
--	azlDot11WdsVlan               OCTET STRING,
	azlDot11WdsAuthenticationPolicy     INTEGER,
--	azlDot11WdsAuthenticationProfile    OCTET STRING,
--	azlDot11WdsWEPDefaultKey      Integer32,
	azlDot11WdsIpAddr             IpAddress,
	azlDot11WdsRemoteIpAddr       IpAddress,
	azlDot11WdsRemoteRouterID     OCTET STRING,
	azlDot11WdsRemoteHostname     OCTET STRING,
	azlDot11WdsRemoteLogic        Integer32,
	azlDot11WdsFlapCount          Integer32,
	azlDot11WdsLinkState          Integer32,
	azlDot11WdsSecurityType	      INTEGER,
--	azlDot11WdsRowStatus          RowStatus,
	azlDot11WdsRemoteRadioId	  MacAddress, 
	azlDot11WdsRemoteDeviceId     MacAddress 
}

azlDot11RadioIndex OBJECT-TYPE
	SYNTAX      Integer32
	MAX-ACCESS  read-only
	STATUS      current
        DESCRIPTION
        	"This attribute describes the parent ifIndex of this
        	WDS. actually it's an radio index."
	::= { azaleaIfDot11WdsEntry 1 }

azlDot11WdsIndex OBJECT-TYPE
	SYNTAX     Integer32(0..10)
	MAX-ACCESS read-only
	STATUS     current
	DESCRIPTION
		"This attribute describes which logic number on the
		radio interface"
	::= { azaleaIfDot11WdsEntry 2 }

azlDot11WdsName OBJECT-TYPE
	SYNTAX      OCTET STRING
	MAX-ACCESS  read-only
	STATUS      current
    DESCRIPTION
       	"The name of the WDS interface"
	::= { azaleaIfDot11WdsEntry 3 }

azlDot11WdsRemoteMacAddr OBJECT-TYPE
	SYNTAX      MacAddress
	MAX-ACCESS  read-only
	STATUS      current
        DESCRIPTION
        	"It describes the Mac Address of remote WDS neighbor."
	::= { azaleaIfDot11WdsEntry 4 }

azlDot11WdsRemoteNodeId OBJECT-TYPE
	SYNTAX      Integer32(1..16777215)
	MAX-ACCESS  read-only
	STATUS      current
        DESCRIPTION
        	"It describes the node id of remote WDS neighbor."
	::= { azaleaIfDot11WdsEntry 5 }

azlDot11WdsRemoteRadio OBJECT-TYPE
	SYNTAX      Integer32(0..15)
	MAX-ACCESS  read-only
	STATUS      current
        DESCRIPTION
        	"It describes the radio index of remote WDS neighbor."
	::= { azaleaIfDot11WdsEntry 6 }

azlDot11WdsSsid OBJECT-TYPE
	SYNTAX      OCTET STRING
	MAX-ACCESS  read-only
	STATUS      current
        DESCRIPTION
        	"This attribute shall indicate the value of the WDS link."
	::= { azaleaIfDot11WdsEntry 7 }

--  not supported
--azlDot11WdsQosProfile OBJECT-TYPE
--	SYNTAX      OCTET STRING
--	MAX-ACCESS  read-only
--	STATUS      current
--        DESCRIPTION
--        	"This attirbute shall indicate the QOS policy on this
--        	WDS link."
--	::= { azaleaIfDot11WdsEntry 8 }

azlDot11WdsDataRate OBJECT-TYPE
	SYNTAX      Integer32
	MAX-ACCESS  read-only
	STATUS      current
        DESCRIPTION
        	"It describes the data rate of WDS link."
	::= { azaleaIfDot11WdsEntry 9 }

azlDot11WdsLinkQuality OBJECT-TYPE
	SYNTAX      Integer32(0..100)
	MAX-ACCESS  read-only
	STATUS      current
    DESCRIPTION
		"It describes the link quality of WDS link."
	::= { azaleaIfDot11WdsEntry 10 }

azlDot11WdsRssi OBJECT-TYPE
	SYNTAX      Integer32
	MAX-ACCESS  read-only
	STATUS      current
	DESCRIPTION
		"It describes the RSSI(receive signal strength indicator).
		 RSSI is a measurement of the received radio signal strength, not the quality."
	::= { azaleaIfDot11WdsEntry 11 }

azlDot11WdsSnr OBJECT-TYPE
	SYNTAX      Integer32
	MAX-ACCESS  read-only
	STATUS      current
	DESCRIPTION
		"It describes the SNR of the wds link."
	::= { azaleaIfDot11WdsEntry 12 }

--  not supported
--azlDot11WdsVlan OBJECT-TYPE
--    SYNTAX      OCTET STRING
--    MAX-ACCESS  read-only
--    STATUS      current
--    DESCRIPTION
--        ""
--    ::= { azaleaIfDot11WdsEntry 13 }

azlDot11WdsAuthenticationPolicy OBJECT-TYPE
    SYNTAX      INTEGER {
        open(1),
        shardkey(2),
        wpa(3),
        wpa2(4)
    }
    MAX-ACCESS  read-only
    STATUS      current
    DESCRIPTION
        "The Authentication Policy of the WDS"
    ::= { azaleaIfDot11WdsEntry 14 }

--  not supported
--azlDot11WdsAuthenticationProfile OBJECT-TYPE
--    SYNTAX      OCTET STRING
--    MAX-ACCESS  read-only
--    STATUS      current
--    DESCRIPTION
--        ""
--    ::= { azaleaIfDot11WdsEntry 15 }

--azlDot11WdsWEPDefaultKey    OBJECT-TYPE
--    SYNTAX      Integer32
--    MAX-ACCESS  read-only
--    STATUS      current
--    DESCRIPTION
--        ""
--    ::= { azaleaIfDot11WdsEntry 16 }

azlDot11WdsIpAddr OBJECT-TYPE
	SYNTAX      IpAddress
	MAX-ACCESS  read-only
	STATUS      current
        DESCRIPTION
        	"It describes the Ip Address of local WDS interface."
	::= { azaleaIfDot11WdsEntry 17 }

azlDot11WdsRemoteIpAddr OBJECT-TYPE
	SYNTAX      IpAddress
	MAX-ACCESS  read-only
	STATUS      current
        DESCRIPTION
        	"It describes the Ip Address of remote WDS neighbor."
	::= { azaleaIfDot11WdsEntry 18 }


azlDot11WdsRemoteRouterID OBJECT-TYPE
	SYNTAX      OCTET STRING
	MAX-ACCESS  read-only
	STATUS      current
        DESCRIPTION
        	"It describes the router id of remote WDS neighbor."
	::= { azaleaIfDot11WdsEntry 19 }

azlDot11WdsRemoteHostname OBJECT-TYPE
	SYNTAX      OCTET STRING
	MAX-ACCESS  read-only
	STATUS      current
        DESCRIPTION
        	"It describes the host name of remote WDS neighbor."
	::= { azaleaIfDot11WdsEntry 20 }

azlDot11WdsRemoteLogic OBJECT-TYPE
	SYNTAX      Integer32(0..15)
	MAX-ACCESS  read-only
	STATUS      current
        DESCRIPTION
        	"It describes the logical index of remote WDS neighbor."
	::= { azaleaIfDot11WdsEntry 21 }

azlDot11WdsFlapCount OBJECT-TYPE
	SYNTAX      Integer32
	MAX-ACCESS  read-only
	STATUS      current
        DESCRIPTION
        	"It describes the flap count of WDS link."
	::= { azaleaIfDot11WdsEntry 22 }

azlDot11WdsLinkState OBJECT-TYPE
	SYNTAX      Integer32 {up(1), down(0)}
	MAX-ACCESS  read-only
	STATUS      current
        DESCRIPTION
        	"It describes the physical state of WDS link."
	::= { azaleaIfDot11WdsEntry 23 }

azlDot11WdsSecurityType OBJECT-TYPE
    SYNTAX      INTEGER {
        open(1),
        openWep(2),
        sharedWep(3),
        wpa(4),
        wpa2(5)
    }
    MAX-ACCESS  read-only
    STATUS      current
    DESCRIPTION
        "The security type of this WDS"
    ::= { azaleaIfDot11WdsEntry 24 }

--  not supported
--azlDot11WdsRowStatus OBJECT-TYPE
--	SYNTAX      RowStatus
--	MAX-ACCESS  read-create
--	STATUS      current
--        DESCRIPTION
--        	"The status of this conceptual row"
--	::= { azaleaIfDot11WdsEntry 25 }

azlDot11WdsRemoteRadioId OBJECT-TYPE
	SYNTAX      MacAddress 
	MAX-ACCESS  read-only
	STATUS      current
        DESCRIPTION
        	"The describes the radio id of remote WDS link"
	::= { azaleaIfDot11WdsEntry 26 }

azlDot11WdsRemoteDeviceId OBJECT-TYPE
	SYNTAX       MacAddress 
	MAX-ACCESS  read-only
	STATUS      current
        DESCRIPTION
        	"The describes the device id remote WDS link"
	::= { azaleaIfDot11WdsEntry 27 }

	
--azlDot11WdsTxRateOffset OBJECT-TYPE
--	SYNTAX      Integer32
--	MAX-ACCESS  read-write
--	STATUS      current
--    DESCRIPTION
--        	""
--	::= { azaleaIfTrapThreshold 1 }
--
--azlDot11WdsRxRateOffset OBJECT-TYPE
--	SYNTAX      Integer32
--	MAX-ACCESS  read-write
--	STATUS      current
--        DESCRIPTION
--        	""
--	::= { azaleaIfTrapThreshold 2 }
--
--azlDot11WdsRssiOffset OBJECT-TYPE
--	SYNTAX      Integer32
--	MAX-ACCESS  read-write
--	STATUS      current
--        DESCRIPTION
--        	""
--	::= { azaleaIfTrapThreshold 3 }
--
--azlDot11WdsSnrOffset OBJECT-TYPE
--	SYNTAX      Integer32
--	MAX-ACCESS  read-write
--	STATUS      current
--        DESCRIPTION
--        	""
--	::= { azaleaIfTrapThreshold 4 }

--azlDot11WdsTxRateHThreshold OBJECT-TYPE
--	SYNTAX      Integer32
--	MAX-ACCESS  read-write
--	STATUS      current
--        DESCRIPTION
--        	""
--	::= { azaleaIfTrapThreshold 5 }
--
--azlDot11WdsTxRateLThreshold OBJECT-TYPE
--	SYNTAX      Integer32
--	MAX-ACCESS  read-write
--	STATUS      current
--        DESCRIPTION
--        	""
--	::= { azaleaIfTrapThreshold 6 }
--
--azlDot11WdsRxRateHThreshold OBJECT-TYPE
--	SYNTAX      Integer32
--	MAX-ACCESS  read-write
--	STATUS      current
--        DESCRIPTION
--        	""
--	::= { azaleaIfTrapThreshold 7 }
--
--azlDot11WdsRxRateLThreshold OBJECT-TYPE
--	SYNTAX      Integer32
--	MAX-ACCESS  read-write
--	STATUS      current
--        DESCRIPTION
--        	""
--	::= { azaleaIfTrapThreshold 8 }

--azlDot11WdsRssiHThreshold OBJECT-TYPE
--	SYNTAX      Integer32
--	MAX-ACCESS  read-write
--	STATUS      current
--        DESCRIPTION
--        	""
--	::= { azaleaIfTrapThreshold 9 }
--
--azlDot11WdsRssiLThreshold OBJECT-TYPE
--	SYNTAX      Integer32
--	MAX-ACCESS  read-write
--	STATUS      current
--        DESCRIPTION
--        	""
--	::= { azaleaIfTrapThreshold 10 }
--
--azlDot11WdsSnrHThreshold OBJECT-TYPE
--	SYNTAX      Integer32
--	MAX-ACCESS  read-write
--	STATUS      current
--        DESCRIPTION
--        	""
--	::= { azaleaIfTrapThreshold 11 }
--
--azlDot11WdsSnrLThreshold OBJECT-TYPE
--	SYNTAX      Integer32
--	MAX-ACCESS  read-write
--	STATUS      current
--        DESCRIPTION
--        	""
--	::= { azaleaIfTrapThreshold 12 }


--*********************************************************************
--    Mesh Interface traps
--*********************************************************************

azlWDSPerformanceTrap  NOTIFICATION-TYPE
    OBJECTS    {
        ifIndex,
        azlDot11WdsSnr,
        azlDot11WdsRssi,
		azlDot11WdsRemoteMacAddr
    }
    STATUS  current
    DESCRIPTION
        "When WDS interface signal strength over or below threshold, send trap"
    ::= { azaleaIfTraps 8 }

azlWDSRemoveTrap  NOTIFICATION-TYPE
    OBJECTS    {
        ifIndex
    }
    STATUS  current
    DESCRIPTION
        "When WDS interface is removed, send trap"
    ::= { azaleaIfTraps 9 }


azlWDSLinkQualityLowTrap  NOTIFICATION-TYPE
    OBJECTS    {
        ifIndex,
        azlDot11WdsLinkQuality
    }
    STATUS  current
    DESCRIPTION
        "When WDS link quality low, send trap"
    ::= { azaleaIfTraps 10 }

azlWDSLinkQualityClearTrap  NOTIFICATION-TYPE
    OBJECTS    {
        ifIndex,
        azlDot11WdsLinkQuality
    }
    STATUS  current
    DESCRIPTION
        "When WDS link quality high, clear trap"
    ::= { azaleaIfTraps 11 }




--*********************************************************************
--    VPLM management
--*********************************************************************

azVPLMMgmt OBJECT IDENTIFIER ::= { azaleaMgmt 21 }

	azVPLMMibGroup OBJECT IDENTIFIER ::= { azVPLMMgmt 1 }

	azVPLMConfigStatus OBJECT-TYPE
	   SYNTAX Integer32 { enable(1), disable(0) }
	   MAX-ACCESS read-write
	   STATUS current
	   DESCRIPTION
	   "VPLM mode configuration status"
		::=  {  azVPLMMibGroup  1  } 


--*********************************************************************
--    AVT management
--*********************************************************************

azAVTMgmt OBJECT IDENTIFIER ::= { azaleaMgmt 22 }

	azAVTMibGroup OBJECT IDENTIFIER ::= { azAVTMgmt 1 }

--  not supported	
--	azAVTEventCode OBJECT-TYPE
--	   SYNTAX Integer32
--	   MAX-ACCESS read-only
--	   STATUS current
--	   DESCRIPTION	
--	   "The event code of the AVT"
--		::=  {  azAVTMibGroup  1  } 

	azAVTStreamNumber OBJECT-TYPE
	   SYNTAX Integer32
	   MAX-ACCESS read-only
	   STATUS current
	   DESCRIPTION	
	   "The Stream Number of the AVT"
		::=  {  azAVTMibGroup  2  } 

	azAVTTotalMemory OBJECT-TYPE
	   SYNTAX Integer32
	   MAX-ACCESS read-only
	   STATUS current
	   DESCRIPTION	
	   "The Total Memory of the AVT"
		::=  {  azAVTMibGroup  3  } 

      azAVTCameraTable	OBJECT-TYPE
		SYNTAX		SEQUENCE  OF  AzAVTCameraEntry
		MAX-ACCESS	not-accessible
		STATUS		current
		DESCRIPTION	"A list of discovered camera."
		::=  {  azAVTMibGroup  4 }

      azAVTCameraEntry	OBJECT-TYPE
		SYNTAX		AzAVTCameraEntry
		MAX-ACCESS	not-accessible
		STATUS		current
		DESCRIPTION	"Each entry is a camera discovered by AVT, includes the ip, mac and type."
		INDEX		{ azAVTCameraIpAddress }
		::=  { azAVTCameraTable 1 }

      AzAVTCameraEntry  ::=  SEQUENCE {
        azAVTCameraIpAddress  IpAddress,
		azAVTCameraMacAddress  MacAddress,
		azAVTCameraType  DisplayString
		}

     azAVTCameraIpAddress  	OBJECT-TYPE	
		SYNTAX		IpAddress
		MAX-ACCESS		read-only
		STATUS		current
		DESCRIPTION		"The IP Address of the camera"
		::=  {  azAVTCameraEntry  1  }

     azAVTCameraMacAddress 	OBJECT-TYPE	
		SYNTAX		MacAddress
		MAX-ACCESS		read-only
		STATUS		current
		DESCRIPTION		"The MAC address of the camera."
		::=  {  azAVTCameraEntry  2  }

	 azAVTCameraType	OBJECT-TYPE	
		SYNTAX		DisplayString
		MAX-ACCESS		read-only
		STATUS		current
		DESCRIPTION		"the type of the camera, such as AXIS, SONY, PANASONIC, PELCO, D-LINK, CANON."
		::=  {  azAVTCameraEntry  3  }


	azAVTTrapGroup OBJECT IDENTIFIER ::= { azAVTMgmt 2 }

	azAVTMemoryEventTrap NOTIFICATION-TYPE
		OBJECTS			{azAVTStreamNumber,
						 azAVTTotalMemory}
		STATUS current
		DESCRIPTION		
		"The Trap of Memory Event of AVT"
		::=  {  azAVTTrapGroup  1  } 

	azAVTMemoryEventClearTrap NOTIFICATION-TYPE
		OBJECTS			{azAVTStreamNumber,
						 azAVTTotalMemory}
		STATUS current
		DESCRIPTION		
		"The Trap of Memory Event Clear of AVT"
		::=  {  azAVTTrapGroup  2  } 

	azAVTStreamEventTrap NOTIFICATION-TYPE
		OBJECTS			{azAVTStreamNumber,
						 azAVTTotalMemory}
		STATUS current
		DESCRIPTION		
		"The Trap of Stream Event of AVT"
		::=  {  azAVTTrapGroup  3 } 

	azAVTStreamEventClearTrap NOTIFICATION-TYPE
		OBJECTS			{azAVTStreamNumber,
						 azAVTTotalMemory}
		STATUS current
		DESCRIPTION		
		"The Trap of Stream Event Clear of AVT"
		::=  {  azAVTTrapGroup  4  } 

	azAVTCameraUpTrap NOTIFICATION-TYPE
		OBJECTS			{azAVTCameraIpAddress,
						 azAVTCameraMacAddress,
						 azAVTCameraType}
		STATUS current
		DESCRIPTION		
		"The Trap of New Camera Up."
		::=  {  azAVTTrapGroup  5  }

	azAVTCameraDownTrap NOTIFICATION-TYPE
		OBJECTS			{azAVTCameraIpAddress,
						 azAVTCameraMacAddress,
						 azAVTCameraType}
		STATUS current
		DESCRIPTION		
		"The Trap of Camera down."
		::=  {  azAVTTrapGroup  6  } 

	azAVTCameraUpdateTrap NOTIFICATION-TYPE
		OBJECTS			{azAVTCameraIpAddress,
						 azAVTCameraMacAddress,
						 azAVTCameraType}
		STATUS current
		DESCRIPTION		
		"The Trap of Updated Camera."
		::=  {  azAVTTrapGroup  7  } 


-- ********************************************************************************
-- 		azDot11RadioMib
-- ********************************************************************************
azDot11RadioMib	OBJECT IDENTIFIER ::=  {  azaleaMgmt  23  }

	azDot11RadioMIBGroup	OBJECT IDENTIFIER
			::=  {  azDot11RadioMib  1  }

	azDot11RadioNeighborAPTable	OBJECT-TYPE
		SYNTAX		SEQUENCE  OF  AzDot11RadioNeighborAPEntry
		MAX-ACCESS	not-accessible
		STATUS		current
		DESCRIPTION	"This table contains attributes of neighbor APs of 
        radio interfaces managed by this agent."
		::=  { azDot11RadioMIBGroup  1 }

	azDot11RadioNeighborAPEntry	OBJECT-TYPE
		SYNTAX		AzDot11RadioNeighborAPEntry
		MAX-ACCESS	not-accessible
		STATUS		current
		DESCRIPTION	"A collection of attributes for neighbor APs of radio interface."
		INDEX		{  ifIndex, azDot11RadioNeighborAPMACAddr  }
		::=  { azDot11RadioNeighborAPTable 1 }

	AzDot11RadioNeighborAPEntry  ::=  SEQUENCE {
		azDot11RadioNeighborAPMACAddr  MacAddress,
		azDot11RadioNeighborAPSSID  DisplayString,
		azDot11RadioNeighborAPWirelessMode  Integer32,
		azDot11RadioNeighborAPChannel  Integer32,
		azDot11RadioNeighborAPRSSI  Integer32,
		azDot11RadioNeighborAPSNR  Integer32,
		azDot11RadioNeighborAPCipher  Integer32,
		azDot11RadioNeighborAPAdHoc  Integer32
		}

	azDot11RadioNeighborAPMACAddr	OBJECT-TYPE	
		SYNTAX			MacAddress
		MAX-ACCESS		read-only
		STATUS			current
		DESCRIPTION		"The MAC address of this Neighbor AP."
		::=  {  azDot11RadioNeighborAPEntry  1  }

	azDot11RadioNeighborAPSSID	OBJECT-TYPE	
		SYNTAX			DisplayString
		MAX-ACCESS		read-only
		STATUS			current
		DESCRIPTION		"The SSID of this Neighbor AP."
		::=  {  azDot11RadioNeighborAPEntry  2  }

	azDot11RadioNeighborAPWirelessMode	OBJECT-TYPE	
		SYNTAX			Integer32 { ieee80211a(1), ieee80211b(2), ieee80211g(3), ieee80211g-only(4), ieee80211na(5), ieee80211na-ht40minus(6), ieee80211na-ht40plus(7), ieee80211ng(8), ieee80211ng-ht40minus(9), ieee80211ng-ht40plus(10) }
		MAX-ACCESS		read-only
		STATUS			current
		DESCRIPTION		"The Wireless Mode of this Neighbor AP."
		::=  {  azDot11RadioNeighborAPEntry  3  }

	azDot11RadioNeighborAPChannel	OBJECT-TYPE	
		SYNTAX			Integer32
		MAX-ACCESS		read-only
		STATUS			current
		DESCRIPTION		"The channel of this Neighbor AP."
		::=  {  azDot11RadioNeighborAPEntry  4  }

	azDot11RadioNeighborAPRSSI	OBJECT-TYPE	
		SYNTAX			Integer32
		MAX-ACCESS		read-only
		STATUS			current
		DESCRIPTION		"The RSSI of this Neighbor AP."
		::=  {  azDot11RadioNeighborAPEntry  5  }

	azDot11RadioNeighborAPSNR	OBJECT-TYPE	
		SYNTAX			Integer32
		MAX-ACCESS		read-only
		STATUS			current
		DESCRIPTION		"The SNR of this Neighbor AP."
		::=  {  azDot11RadioNeighborAPEntry  6  }

	azDot11RadioNeighborAPCipher	OBJECT-TYPE	
		SYNTAX			Integer32 { none(0), wep(1), tkip(2), aes(3), other(4) }
		MAX-ACCESS		read-only
		STATUS			current
		DESCRIPTION		"The cipher type of this Neighbor AP."
		::=  {  azDot11RadioNeighborAPEntry  7  }

	azDot11RadioNeighborAPAdHoc	OBJECT-TYPE	
		SYNTAX			Integer32
		MAX-ACCESS		read-only
		STATUS			current
		DESCRIPTION		"The ad hoc flag of this Neighbor AP."
		::=  {  azDot11RadioNeighborAPEntry  8  }



--*********************************************************************
--    AOR management
--*********************************************************************

azAORMgmt OBJECT IDENTIFIER ::= { azaleaMgmt 30 }

azAORMibGroup OBJECT IDENTIFIER ::= { azAORMgmt 1 }
	
	azAORMeshOrphanMac OBJECT-TYPE
		SYNTAX MacAddress
		MAX-ACCESS  read-only
    	STATUS      current
		DESCRIPTION
			"The ethenet MAC address of the orphan node which AOR function recovered."
        ::=  {  azAORMibGroup  1  }

azAORTrapGroup OBJECT IDENTIFIER ::= { azAORMgmt 2 }

    azAORMONMacTrap NOTIFICATION-TYPE
        OBJECTS         {azAORMeshOrphanMac}
        STATUS current
        DESCRIPTION
			"The Trap of the event of AOR recovered an orphan node."
        ::=  {  azAORTrapGroup  1  }


END
