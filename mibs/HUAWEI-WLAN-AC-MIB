--
-- HUAWEI-WLAN-AC-MIB.mib
-- MIB generated by MG-SOFT Visual MIB Builder Version 3.0 Build 253
-- Thursday, October 22, 2009 at 10:20:23
--

--  HUAWEI-WLAN-AC-MIB.mib
-- MIB generated by MG-SOFT Visual MIB Builder Version 3.0 Build 253
-- Tuesday, October 20, 2009 at 19:42:51
-- 
--  HUAWEI-WLAN-AC-MIB.mib
-- MIB generated by MG-SOFT Visual MIB Builder Version 3.0 Build 253
-- Tuesday, October 13, 2009 at 15:19:28
-- 
--  HUAWEI-WLAN-AC-MIB.mib
-- MIB generated by MG-SOFT Visual MIB Builder Version 3.0 Build 253
-- Tuesday, October 13, 2009 at 15:16:57
-- 
--  HUAWEI-WLAN-AC-MIB.mib
-- MIB generated by MG-SOFT Visual MIB Builder Version 3.0 Build 253
-- Tuesday, August 11, 2009 at 12:04:37
-- 
--  HUAWEI-WLAN-AC-MIB.my
-- MIB generated by MG-SOFT Visual MIB Builder Version 3.0 Build 253
-- Friday, July 31, 2009 at 11:09:59
-- 

	HUAWEI-WLAN-AC-MIB DEFINITIONS ::= BEGIN
 
		IMPORTS
			hwWlan			
				FROM HUAWEI-WLAN-MIB			
			InterfaceIndex			
				FROM IF-MIB			
			EnabledStatus			
				FROM P-BRIDGE-MIB			
			OBJECT-GROUP			
				FROM SNMPv2-CONF			
			IpAddress, Integer32, OBJECT-TYPE, MODULE-IDENTITY			
				FROM SNMPv2-SMI			
			RowStatus			
				FROM SNMPv2-TC;
	
	
--     July 25, 2009 at 16:14 GMT
-- July 25, 2009 at 16:14 GMT
-- July 25, 2009 at 16:14 GMT
-- July 25, 2009 at 16:14 GMT
-- July 25, 2009 at 16:14 GMT
		hwWlanACManagement MODULE-IDENTITY 
			LAST-UPDATED "200907251614Z"		-- July 25, 2009 at 16:14 GMT
			ORGANIZATION 
				"Huawei Technologies co.,Ltd."
			CONTACT-INFO 
				"Contact-info."
			DESCRIPTION 
				"Wlan AC management."
			::= { hwWlan 100 }
		
	
	
--
-- Node definitions
--
	
		-- 1.3.6.1.4.1.2011.6.139.100.1
		hwWlanAcSourceBind OBJECT-TYPE
			SYNTAX Integer32
			MAX-ACCESS read-write
			STATUS current
			DESCRIPTION
				"Bind the loopback number as ac source."
			::= { hwWlanACManagement 1 }
		
		-- 1.3.6.1.4.1.2011.6.139.100.2
		hwWlanTunnelAccessInterfaceBindTable OBJECT-TYPE
			SYNTAX SEQUENCE OF HwWlanTunnelAccessInterfaceBindEntry
			MAX-ACCESS not-accessible
			STATUS current
			DESCRIPTION
				"Bind the interface as the access interface when the access type is tunnle access."
			::= { hwWlanACManagement 2 }
		
		-- 1.3.6.1.4.1.2011.6.139.100.2.1
		hwWlanTunnelAccessInterfaceBindEntry OBJECT-TYPE
			SYNTAX HwWlanTunnelAccessInterfaceBindEntry
			MAX-ACCESS not-accessible
			STATUS current
			DESCRIPTION
				"The entry of hwWlanTunnelAccessInterfaceBindTable."
			INDEX { hwWlanTunnelAccessInterfaceIndex, hwWlanTunnelAccessSlotId }
			::= { hwWlanTunnelAccessInterfaceBindTable 1 }
		
		HwWlanTunnelAccessInterfaceBindEntry ::=
			SEQUENCE { 
				hwWlanTunnelAccessInterfaceIndex
					InterfaceIndex,
				hwWlanTunnelAccessSlotId
					Integer32,
				hwWlanTunnelAccessInterfaceBindRawStatus
					RowStatus
			 }

		-- 1.3.6.1.4.1.2011.6.139.100.2.1.1
		hwWlanTunnelAccessInterfaceIndex OBJECT-TYPE
			SYNTAX InterfaceIndex
			MAX-ACCESS not-accessible
			STATUS current
			DESCRIPTION
				"The index of the tunnel access interface."
			::= { hwWlanTunnelAccessInterfaceBindEntry 1 }
		
		-- 1.3.6.1.4.1.2011.6.139.100.2.1.2
		hwWlanTunnelAccessSlotId OBJECT-TYPE
			SYNTAX Integer32 (1..16)
			MAX-ACCESS not-accessible
			STATUS current
			DESCRIPTION
				"The slot id of the board which receive the user packets."
			::= { hwWlanTunnelAccessInterfaceBindEntry 2 }
		
		-- 1.3.6.1.4.1.2011.6.139.100.2.1.3
		hwWlanTunnelAccessInterfaceBindRawStatus OBJECT-TYPE
			SYNTAX RowStatus
			MAX-ACCESS read-write
			STATUS current
			DESCRIPTION
				"This table can be created and deleted."
			::= { hwWlanTunnelAccessInterfaceBindEntry 3 }
		
		-- 1.3.6.1.4.1.2011.6.139.100.3
		hwWlanRessembleBoardBindTable OBJECT-TYPE
			SYNTAX SEQUENCE OF HwWlanRessembleBoardBindEntry
			MAX-ACCESS not-accessible
			STATUS current
			DESCRIPTION
				"The table which configrate wlan ressemble board bind table."
			::= { hwWlanACManagement 3 }
		
		-- 1.3.6.1.4.1.2011.6.139.100.3.1
		hwWlanRessembleBoardBindEntry OBJECT-TYPE
			SYNTAX HwWlanRessembleBoardBindEntry
			MAX-ACCESS not-accessible
			STATUS current
			DESCRIPTION
				"The entry of hwWlanRessembleBoardBindTable."
			INDEX { hwWlanRessembleBoardBindSlotId }
			::= { hwWlanRessembleBoardBindTable 1 }
		
		HwWlanRessembleBoardBindEntry ::=
			SEQUENCE { 
				hwWlanRessembleBoardBindSlotId
					Integer32,
				hwWlanRessembleBoardBindRawStatus
					RowStatus
			 }

		-- 1.3.6.1.4.1.2011.6.139.100.3.1.1
		hwWlanRessembleBoardBindSlotId OBJECT-TYPE
			SYNTAX Integer32 (1..16)
			MAX-ACCESS not-accessible
			STATUS current
			DESCRIPTION
				"The slot id of the board which will be bind as the ressemble board."
			::= { hwWlanRessembleBoardBindEntry 1 }
		
		-- 1.3.6.1.4.1.2011.6.139.100.3.1.2
		hwWlanRessembleBoardBindRawStatus OBJECT-TYPE
			SYNTAX RowStatus
			MAX-ACCESS read-write
			STATUS current
			DESCRIPTION
				"This table can be created and deleted."
			::= { hwWlanRessembleBoardBindEntry 2 }
		
		-- 1.3.6.1.4.1.2011.6.139.100.4
		hwWlanAccessTypeEnableTable OBJECT-TYPE
			SYNTAX SEQUENCE OF HwWlanAccessTypeEnableEntry
			MAX-ACCESS not-accessible
			STATUS current
			DESCRIPTION
				"The table configurate the wlan access type of the access interface. It can be used for ethernet interface/ethernet sub interface/trunk interface/trunk sub interface."
			::= { hwWlanACManagement 4 }
		
		-- 1.3.6.1.4.1.2011.6.139.100.4.1
		hwWlanAccessTypeEnableEntry OBJECT-TYPE
			SYNTAX HwWlanAccessTypeEnableEntry
			MAX-ACCESS not-accessible
			STATUS current
			DESCRIPTION
				"The entry of hwWlanAccessTypeEnableTable."
			INDEX { hwWlanAccessIfIndex }
			::= { hwWlanAccessTypeEnableTable 1 }
		
		HwWlanAccessTypeEnableEntry ::=
			SEQUENCE { 
				hwWlanAccessIfIndex
					InterfaceIndex,
				hwWlanDirectAccessEnable
					EnabledStatus
			 }

		-- 1.3.6.1.4.1.2011.6.139.100.4.1.1
		hwWlanAccessIfIndex OBJECT-TYPE
			SYNTAX InterfaceIndex
			MAX-ACCESS not-accessible
			STATUS current
			DESCRIPTION
				"The index of the wlan access interface."
			::= { hwWlanAccessTypeEnableEntry 1 }
		
		-- 1.3.6.1.4.1.2011.6.139.100.4.1.2
		hwWlanDirectAccessEnable OBJECT-TYPE
			SYNTAX EnabledStatus
			MAX-ACCESS read-create
			STATUS current
			DESCRIPTION
				"Enable the access type of the wlan access interface as direct access."
			DEFVAL { disable }
			::= { hwWlanAccessTypeEnableEntry 2 }
		

		-- 1.3.6.1.4.1.2011.6.139.100.5
		hwWlanAccessInfoTable OBJECT-TYPE
			SYNTAX SEQUENCE OF HwWlanAccessInfoEntry
			MAX-ACCESS not-accessible
			STATUS current
			DESCRIPTION
				"The table of wlan ap access infomation."
			::= { hwWlanACManagement 5 }
		
		-- 1.3.6.1.4.1.2011.6.139.100.5.1
		hwWlanAccessInfoEntry OBJECT-TYPE
			SYNTAX HwWlanAccessInfoEntry
			MAX-ACCESS not-accessible
			STATUS current
			DESCRIPTION
				"The entry of hwWlanAccessInfoTable."
			INDEX { hwWlanAccessInfoApIndex }
			::= { hwWlanAccessInfoTable 1 }
		
		HwWlanAccessInfoEntry ::=
			SEQUENCE { 
				hwWlanAccessInfoApIndex
					Integer32,
				hwWlanAccessInfoApIP
					IpAddress,
				hwWlanAccessInfoApControlPort
					Integer32,
				hwWlanAccessInfoApDataPort
					Integer32,
				hwWlanAccessInfoAccessInterfaceName
					OCTET STRING,
				hwWlanAccessInfoAccessType
					Integer32
			 }

		-- 1.3.6.1.4.1.2011.6.139.100.5.1.1
		hwWlanAccessInfoApIndex OBJECT-TYPE
			SYNTAX Integer32 (1..4096)
			MAX-ACCESS not-accessible
			STATUS current
			DESCRIPTION
				"The index of ap device."
			::= { hwWlanAccessInfoEntry 1 }
		

		-- 1.3.6.1.4.1.2011.6.139.100.5.1.2
		hwWlanAccessInfoApIP OBJECT-TYPE
			SYNTAX IpAddress
			MAX-ACCESS read-only
			STATUS current
			DESCRIPTION
				"The ip address of the ap device."
			::= { hwWlanAccessInfoEntry 2 }
		
		-- 1.3.6.1.4.1.2011.6.139.100.5.1.3
		hwWlanAccessInfoApControlPort OBJECT-TYPE
			SYNTAX Integer32
			MAX-ACCESS read-only
			STATUS current
			DESCRIPTION
				"The control port of the ap device."
			::= { hwWlanAccessInfoEntry 3 }
		
		-- 1.3.6.1.4.1.2011.6.139.100.5.1.4
		hwWlanAccessInfoApDataPort OBJECT-TYPE
			SYNTAX Integer32
			MAX-ACCESS read-only
			STATUS current
			DESCRIPTION
				"The data port of the ap device."
			::= { hwWlanAccessInfoEntry 4 }
		
		-- 1.3.6.1.4.1.2011.6.139.100.5.1.5
		hwWlanAccessInfoAccessInterfaceName OBJECT-TYPE
			SYNTAX OCTET STRING
			MAX-ACCESS read-only
			STATUS current
			DESCRIPTION
				"The access interface name of the ap device."
			::= { hwWlanAccessInfoEntry 5 }
		
		-- 1.3.6.1.4.1.2011.6.139.100.5.1.6
		hwWlanAccessInfoAccessType OBJECT-TYPE
			SYNTAX Integer32 (0..1)
			MAX-ACCESS read-only
			STATUS current
			DESCRIPTION
				"The access type of the ap device."
			::= { hwWlanAccessInfoEntry 6 }
		
		-- 1.3.6.1.4.1.2011.6.139.100.6
		hwWlanVeSubInterfaceWlanEnableTable OBJECT-TYPE
			SYNTAX SEQUENCE OF HwWlanVeSubInterfaceWlanEnableEntry
			MAX-ACCESS not-accessible
			STATUS current
			DESCRIPTION
				"When the wlan access type is tunnle access, the virtual ethernet sub interface must be configurated wlan enble to be used by the wlan user."
			::= { hwWlanACManagement 6 }
		
		-- 1.3.6.1.4.1.2011.6.139.100.6.1
		hwWlanVeSubInterfaceWlanEnableEntry OBJECT-TYPE
			SYNTAX HwWlanVeSubInterfaceWlanEnableEntry
			MAX-ACCESS not-accessible
			STATUS current
			DESCRIPTION
				"The entry of hwWlanVeSubInterfaceWlanEnableTable."
			INDEX { hwWlanVeSubInterfaceIndex }
			::= { hwWlanVeSubInterfaceWlanEnableTable 1 }
		
		HwWlanVeSubInterfaceWlanEnableEntry ::=
			SEQUENCE { 
				hwWlanVeSubInterfaceIndex
					InterfaceIndex,
				hwWlanVeSubInterfaceWlanEnable
					EnabledStatus
			 }

		-- 1.3.6.1.4.1.2011.6.139.100.6.1.1
		hwWlanVeSubInterfaceIndex OBJECT-TYPE
			SYNTAX InterfaceIndex
			MAX-ACCESS not-accessible
			STATUS current
			DESCRIPTION
				"The index of the WLAN virtual etherner interface which used for the wlan user access."
			::= { hwWlanVeSubInterfaceWlanEnableEntry 1 }
		
		-- 1.3.6.1.4.1.2011.6.139.100.6.1.2
		hwWlanVeSubInterfaceWlanEnable OBJECT-TYPE
			SYNTAX EnabledStatus
			MAX-ACCESS read-write
			STATUS current
			DESCRIPTION
				"Enable wlan."
			::= { hwWlanVeSubInterfaceWlanEnableEntry 2 }
		
		-- 1.3.6.1.4.1.2011.6.139.100.7
		hwWlanAcManageGroups OBJECT IDENTIFIER ::= { hwWlanACManagement 7 }
		
		-- 1.3.6.1.4.1.2011.6.139.100.7.1
		hwWlanAcSourceBindGroup OBJECT-GROUP
			OBJECTS { hwWlanAcSourceBind }
			STATUS current
			DESCRIPTION 
				"Bind the loopback number as ac source."
			::= { hwWlanAcManageGroups 1 }
		
		-- 1.3.6.1.4.1.2011.6.139.100.7.2
		hwWlanTunnelAccessInterfaceBindGroup OBJECT-GROUP
			OBJECTS { hwWlanTunnelAccessInterfaceBindRawStatus }
			STATUS current
			DESCRIPTION 
				"Bind the interface as the access interface when the access type is tunnle access."
			::= { hwWlanAcManageGroups 2 }
		
		-- 1.3.6.1.4.1.2011.6.139.100.7.3
		hwWlanRessembleBoardBindGroup OBJECT-GROUP
			OBJECTS { hwWlanRessembleBoardBindRawStatus }
			STATUS current
			DESCRIPTION 
				"Configurate wlan ressemble board bind."
			::= { hwWlanAcManageGroups 3 }
		
		-- 1.3.6.1.4.1.2011.6.139.100.7.4
		hwWlanAccessTypeEnableGroup OBJECT-GROUP
			OBJECTS { hwWlanDirectAccessEnable }
			STATUS current
			DESCRIPTION 
				"Configurate the wlan access type of the access interface."
			::= { hwWlanAcManageGroups 4 }
		
		-- 1.3.6.1.4.1.2011.6.139.100.7.5
		hwWlanAccessInfoGroup OBJECT-GROUP
			OBJECTS { hwWlanAccessInfoApIP, hwWlanAccessInfoApControlPort, hwWlanAccessInfoApDataPort, hwWlanAccessInfoAccessInterfaceName, hwWlanAccessInfoAccessType
				 }
			STATUS current
			DESCRIPTION 
				"Wlan ap access infomation."
			::= { hwWlanAcManageGroups 5 }
		
		-- 1.3.6.1.4.1.2011.6.139.100.7.6
		hwWlanVeSubInterfaceWlanEnableGroup OBJECT-GROUP
			OBJECTS { hwWlanVeSubInterfaceWlanEnable }
			STATUS current
			DESCRIPTION 
				"When the wlan access type is tunnle access, the virtual ethernet sub interface must be configurated wlan enble to be used by the wlan user."
			::= { hwWlanAcManageGroups 6 }
		
	
	END

--
-- HUAWEI-WLAN-AC-MIB.mib
--
