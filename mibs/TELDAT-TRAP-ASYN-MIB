-- file automatically created


TELDAT-TRAP-ASYN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


asynTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ASYN event subsystem."
    REVISION "201401200930Z"
    DESCRIPTION "Initial implementation"
        ::= { telEventTraps 150 }


asynEventsGroup	OBJECT IDENTIFIER	::= { asynTrapsMIB 1 }

asynNotifications	OBJECT IDENTIFIER	::= { asynTrapsMIB 2 }
asynNotificationsPrefix	OBJECT IDENTIFIER	::= { asynNotifications 0 }

asynEventObjects1 OBJECT-IDENTITY
    STATUS current
    DESCRIPTION
        "Event ASYN.1
        Selftest completed successfully."
    ::= { asynEventsGroup 1 }

asyn1_interface OBJECT-TYPE
    SYNTAX DisplayString
    MAX-ACCESS accessible-for-notify
    STATUS current
    DESCRIPTION
        "Parameter 'interface' in event ASYN.1"
    ::= { asynEventObjects1 1 }

asynEventObjects2 OBJECT-IDENTITY
    STATUS current
    DESCRIPTION
        "Event ASYN.2
        Maintenance failure."
    ::= { asynEventsGroup 2 }

asyn2_interface OBJECT-TYPE
    SYNTAX DisplayString
    MAX-ACCESS accessible-for-notify
    STATUS current
    DESCRIPTION
        "Parameter 'interface' in event ASYN.2"
    ::= { asynEventObjects2 1 }

asynEventObjects3 OBJECT-IDENTITY
    STATUS current
    DESCRIPTION
        "Event ASYN.3
        An IP packet has been received with a CRC error."
    ::= { asynEventsGroup 3 }

asyn3_frame_size OBJECT-TYPE
    SYNTAX Integer32
    MAX-ACCESS accessible-for-notify
    STATUS current
    DESCRIPTION
        "Parameter 'frame_size' in event ASYN.3"
    ::= { asynEventObjects3 1 }

asyn3_interface OBJECT-TYPE
    SYNTAX DisplayString
    MAX-ACCESS accessible-for-notify
    STATUS current
    DESCRIPTION
        "Parameter 'interface' in event ASYN.3"
    ::= { asynEventObjects3 2 }

asynEventObjects4 OBJECT-IDENTITY
    STATUS current
    DESCRIPTION
        "Event ASYN.4
        End flag is not found on received frame."
    ::= { asynEventsGroup 4 }

asyn4_frame_size OBJECT-TYPE
    SYNTAX Integer32
    MAX-ACCESS accessible-for-notify
    STATUS current
    DESCRIPTION
        "Parameter 'frame_size' in event ASYN.4"
    ::= { asynEventObjects4 1 }

asyn4_interface OBJECT-TYPE
    SYNTAX DisplayString
    MAX-ACCESS accessible-for-notify
    STATUS current
    DESCRIPTION
        "Parameter 'interface' in event ASYN.4"
    ::= { asynEventObjects4 2 }

asynEventObjects5 OBJECT-IDENTITY
    STATUS current
    DESCRIPTION
        "Event ASYN.5
        Incorrect packet format: last character of frame is escape character."
    ::= { asynEventsGroup 5 }

asyn5_frame_size OBJECT-TYPE
    SYNTAX Integer32
    MAX-ACCESS accessible-for-notify
    STATUS current
    DESCRIPTION
        "Parameter 'frame_size' in event ASYN.5"
    ::= { asynEventObjects5 1 }

asyn5_interface OBJECT-TYPE
    SYNTAX DisplayString
    MAX-ACCESS accessible-for-notify
    STATUS current
    DESCRIPTION
        "Parameter 'interface' in event ASYN.5"
    ::= { asynEventObjects5 2 }


asynNotification1 NOTIFICATION-TYPE
    OBJECTS { 
              asyn1_interface 
            }
    STATUS current
    DESCRIPTION
        "Notification of Event ASYN.1

        Message: 'Serial port came up sucessfully on interface $1'

        Parameters list:
              $1: asyn1_interface

        Selftest completed successfully."
    ::= { asynNotificationsPrefix 1 }

asynNotification2 NOTIFICATION-TYPE
    OBJECTS { 
              asyn2_interface 
            }
    STATUS current
    DESCRIPTION
        "Notification of Event ASYN.2

        Message: 'Maintenance failure on interface $1'

        Parameters list:
              $1: asyn2_interface

        Maintenance failure."
    ::= { asynNotificationsPrefix 2 }

asynNotification3 NOTIFICATION-TYPE
    OBJECTS { 
              asyn3_frame_size, 
              asyn3_interface 
            }
    STATUS current
    DESCRIPTION
        "Notification of Event ASYN.3

        Message: 'Received packed with bad crc, frame size $1, on interface $2'

        Parameters list:
              $1: asyn3_frame_size
              $2: asyn3_interface

        An IP packet has been received with a CRC error."
    ::= { asynNotificationsPrefix 3 }

asynNotification4 NOTIFICATION-TYPE
    OBJECTS { 
              asyn4_frame_size, 
              asyn4_interface 
            }
    STATUS current
    DESCRIPTION
        "Notification of Event ASYN.4

        Message: 'Not received end flag on frame with size $1, on interface $2'

        Parameters list:
              $1: asyn4_frame_size
              $2: asyn4_interface

        End flag is not found on received frame."
    ::= { asynNotificationsPrefix 4 }

asynNotification5 NOTIFICATION-TYPE
    OBJECTS { 
              asyn5_frame_size, 
              asyn5_interface 
            }
    STATUS current
    DESCRIPTION
        "Notification of Event ASYN.5

        Message: 'Frame ended with escape character with size $1, on interface $2'

        Parameters list:
              $1: asyn5_frame_size
              $2: asyn5_interface

        Incorrect packet format: last character of frame is escape character."
    ::= { asynNotificationsPrefix 5 }


END
