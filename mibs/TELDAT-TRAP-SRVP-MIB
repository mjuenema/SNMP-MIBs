-- file automatically created


TELDAT-TRAP-SRVP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


srvpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SRVP event subsystem."
    REVISION "201401200930Z"
    DESCRIPTION "Initial implementation"
        ::= { telEventTraps 222 }


srvpEventsGroup	OBJECT IDENTIFIER	::= { srvpTrapsMIB 1 }

srvpNotifications	OBJECT IDENTIFIER	::= { srvpTrapsMIB 2 }
srvpNotificationsPrefix	OBJECT IDENTIFIER	::= { srvpNotifications 0 }

srvpEventObjects1 OBJECT-IDENTITY
    STATUS current
    DESCRIPTION
        "Event SRVP.1
        A packet has been classified in the class-map"
    ::= { srvpEventsGroup 1 }

srvp1_class_name OBJECT-TYPE
    SYNTAX DisplayString
    MAX-ACCESS accessible-for-notify
    STATUS current
    DESCRIPTION
        "Parameter 'class_name' in event SRVP.1"
    ::= { srvpEventObjects1 1 }

srvp1_interface_name OBJECT-TYPE
    SYNTAX DisplayString
    MAX-ACCESS accessible-for-notify
    STATUS current
    DESCRIPTION
        "Parameter 'interface_name' in event SRVP.1"
    ::= { srvpEventObjects1 2 }

srvpEventObjects2 OBJECT-IDENTITY
    STATUS current
    DESCRIPTION
        "Event SRVP.2
        A packet has been discarded by the class-map"
    ::= { srvpEventsGroup 2 }

srvp2_class_name OBJECT-TYPE
    SYNTAX DisplayString
    MAX-ACCESS accessible-for-notify
    STATUS current
    DESCRIPTION
        "Parameter 'class_name' in event SRVP.2"
    ::= { srvpEventObjects2 1 }

srvp2_interface_name OBJECT-TYPE
    SYNTAX DisplayString
    MAX-ACCESS accessible-for-notify
    STATUS current
    DESCRIPTION
        "Parameter 'interface_name' in event SRVP.2"
    ::= { srvpEventObjects2 2 }

srvpEventObjects3 OBJECT-IDENTITY
    STATUS current
    DESCRIPTION
        "Event SRVP.3
        A packet has not matched with an access-list"
    ::= { srvpEventsGroup 3 }

srvp3_prtcl_type OBJECT-TYPE
    SYNTAX DisplayString
    MAX-ACCESS accessible-for-notify
    STATUS current
    DESCRIPTION
        "Parameter 'prtcl_type' in event SRVP.3"
    ::= { srvpEventObjects3 1 }

srvp3_acl_num OBJECT-TYPE
    SYNTAX Integer32
    MAX-ACCESS accessible-for-notify
    STATUS current
    DESCRIPTION
        "Parameter 'acl_num' in event SRVP.3"
    ::= { srvpEventObjects3 2 }

srvp3_interface_name OBJECT-TYPE
    SYNTAX DisplayString
    MAX-ACCESS accessible-for-notify
    STATUS current
    DESCRIPTION
        "Parameter 'interface_name' in event SRVP.3"
    ::= { srvpEventObjects3 3 }

srvpEventObjects4 OBJECT-IDENTITY
    STATUS current
    DESCRIPTION
        "Event SRVP.4
        Notifies when service policy is started properly"
    ::= { srvpEventsGroup 4 }

srvp4_interface_name OBJECT-TYPE
    SYNTAX DisplayString
    MAX-ACCESS accessible-for-notify
    STATUS current
    DESCRIPTION
        "Parameter 'interface_name' in event SRVP.4"
    ::= { srvpEventObjects4 1 }

srvpEventObjects5 OBJECT-IDENTITY
    STATUS current
    DESCRIPTION
        "Event SRVP.5
        Notifies when service policy is disabled"
    ::= { srvpEventsGroup 5 }

srvp5_interface_name OBJECT-TYPE
    SYNTAX DisplayString
    MAX-ACCESS accessible-for-notify
    STATUS current
    DESCRIPTION
        "Parameter 'interface_name' in event SRVP.5"
    ::= { srvpEventObjects5 1 }

srvpEventObjects6 OBJECT-IDENTITY
    STATUS current
    DESCRIPTION
        "Event SRVP.6
        A packet has been transmitted to the protocol"
    ::= { srvpEventsGroup 6 }

srvp6_interface_name OBJECT-TYPE
    SYNTAX DisplayString
    MAX-ACCESS accessible-for-notify
    STATUS current
    DESCRIPTION
        "Parameter 'interface_name' in event SRVP.6"
    ::= { srvpEventObjects6 1 }

srvp6_prtcl OBJECT-TYPE
    SYNTAX DisplayString
    MAX-ACCESS accessible-for-notify
    STATUS current
    DESCRIPTION
        "Parameter 'prtcl' in event SRVP.6"
    ::= { srvpEventObjects6 2 }

srvpEventObjects7 OBJECT-IDENTITY
    STATUS current
    DESCRIPTION
        "Event SRVP.7
        A packet does not match with any class-map"
    ::= { srvpEventsGroup 7 }

srvp7_prtcl OBJECT-TYPE
    SYNTAX DisplayString
    MAX-ACCESS accessible-for-notify
    STATUS current
    DESCRIPTION
        "Parameter 'prtcl' in event SRVP.7"
    ::= { srvpEventObjects7 1 }

srvp7_interface_name OBJECT-TYPE
    SYNTAX DisplayString
    MAX-ACCESS accessible-for-notify
    STATUS current
    DESCRIPTION
        "Parameter 'interface_name' in event SRVP.7"
    ::= { srvpEventObjects7 2 }

srvpEventObjects8 OBJECT-IDENTITY
    STATUS current
    DESCRIPTION
        "Event SRVP.8
        A timer has been scheduled in a class-map"
    ::= { srvpEventsGroup 8 }

srvp8_timer_name OBJECT-TYPE
    SYNTAX DisplayString
    MAX-ACCESS accessible-for-notify
    STATUS current
    DESCRIPTION
        "Parameter 'timer_name' in event SRVP.8"
    ::= { srvpEventObjects8 1 }

srvp8_class_name OBJECT-TYPE
    SYNTAX DisplayString
    MAX-ACCESS accessible-for-notify
    STATUS current
    DESCRIPTION
        "Parameter 'class_name' in event SRVP.8"
    ::= { srvpEventObjects8 2 }

srvp8_new_time OBJECT-TYPE
    SYNTAX Integer32
    MAX-ACCESS accessible-for-notify
    STATUS current
    DESCRIPTION
        "Parameter 'new_time' in event SRVP.8"
    ::= { srvpEventObjects8 3 }

srvp8_new_time_out OBJECT-TYPE
    SYNTAX Integer32
    MAX-ACCESS accessible-for-notify
    STATUS current
    DESCRIPTION
        "Parameter 'new_time_out' in event SRVP.8"
    ::= { srvpEventObjects8 4 }

srvpEventObjects9 OBJECT-IDENTITY
    STATUS current
    DESCRIPTION
        "Event SRVP.9
        A timer has expired in a class-map"
    ::= { srvpEventsGroup 9 }

srvp9_timer_name OBJECT-TYPE
    SYNTAX DisplayString
    MAX-ACCESS accessible-for-notify
    STATUS current
    DESCRIPTION
        "Parameter 'timer_name' in event SRVP.9"
    ::= { srvpEventObjects9 1 }

srvp9_class_name OBJECT-TYPE
    SYNTAX DisplayString
    MAX-ACCESS accessible-for-notify
    STATUS current
    DESCRIPTION
        "Parameter 'class_name' in event SRVP.9"
    ::= { srvpEventObjects9 2 }

srvpEventObjects10 OBJECT-IDENTITY
    STATUS current
    DESCRIPTION
        "Event SRVP.10
        A packet has been tagged with a new label value"
    ::= { srvpEventsGroup 10 }

srvp10_class_name OBJECT-TYPE
    SYNTAX DisplayString
    MAX-ACCESS accessible-for-notify
    STATUS current
    DESCRIPTION
        "Parameter 'class_name' in event SRVP.10"
    ::= { srvpEventObjects10 1 }

srvp10_num_label OBJECT-TYPE
    SYNTAX Integer32
    MAX-ACCESS accessible-for-notify
    STATUS current
    DESCRIPTION
        "Parameter 'num_label' in event SRVP.10"
    ::= { srvpEventObjects10 2 }

srvpEventObjects12 OBJECT-IDENTITY
    STATUS current
    DESCRIPTION
        "Event SRVP.12
        A packet has not the same cos value"
    ::= { srvpEventsGroup 12 }

srvp12_cos_pkt OBJECT-TYPE
    SYNTAX Integer32
    MAX-ACCESS accessible-for-notify
    STATUS current
    DESCRIPTION
        "Parameter 'cos_pkt' in event SRVP.12"
    ::= { srvpEventObjects12 1 }

srvp12_cos_config OBJECT-TYPE
    SYNTAX Integer32
    MAX-ACCESS accessible-for-notify
    STATUS current
    DESCRIPTION
        "Parameter 'cos_config' in event SRVP.12"
    ::= { srvpEventObjects12 2 }

srvpEventObjects13 OBJECT-IDENTITY
    STATUS current
    DESCRIPTION
        "Event SRVP.13
        A packet has not the same src MAC addr value"
    ::= { srvpEventsGroup 13 }

srvp13_src_mac_addr_pkt OBJECT-TYPE
    SYNTAX DisplayString
    MAX-ACCESS accessible-for-notify
    STATUS current
    DESCRIPTION
        "Parameter 'src_mac_addr_pkt' in event SRVP.13"
    ::= { srvpEventObjects13 1 }

srvp13_src_mac_addr_config OBJECT-TYPE
    SYNTAX DisplayString
    MAX-ACCESS accessible-for-notify
    STATUS current
    DESCRIPTION
        "Parameter 'src_mac_addr_config' in event SRVP.13"
    ::= { srvpEventObjects13 2 }

srvpEventObjects14 OBJECT-IDENTITY
    STATUS current
    DESCRIPTION
        "Event SRVP.14
        A packet has not the same dst MAC addr value"
    ::= { srvpEventsGroup 14 }

srvp14_src_mac_addr_pkt OBJECT-TYPE
    SYNTAX DisplayString
    MAX-ACCESS accessible-for-notify
    STATUS current
    DESCRIPTION
        "Parameter 'src_mac_addr_pkt' in event SRVP.14"
    ::= { srvpEventObjects14 1 }

srvp14_src_mac_addr_config OBJECT-TYPE
    SYNTAX DisplayString
    MAX-ACCESS accessible-for-notify
    STATUS current
    DESCRIPTION
        "Parameter 'src_mac_addr_config' in event SRVP.14"
    ::= { srvpEventObjects14 2 }

srvpEventObjects15 OBJECT-IDENTITY
    STATUS current
    DESCRIPTION
        "Event SRVP.15
        A packet has the same [not] src/dst MAC address value, and then the packet is discarded"
    ::= { srvpEventsGroup 15 }

srvp15_mac_addr_type OBJECT-TYPE
    SYNTAX DisplayString
    MAX-ACCESS accessible-for-notify
    STATUS current
    DESCRIPTION
        "Parameter 'mac_addr_type' in event SRVP.15"
    ::= { srvpEventObjects15 1 }

srvp15_mac_addr_pkt OBJECT-TYPE
    SYNTAX DisplayString
    MAX-ACCESS accessible-for-notify
    STATUS current
    DESCRIPTION
        "Parameter 'mac_addr_pkt' in event SRVP.15"
    ::= { srvpEventObjects15 2 }

srvp15_mac_addr_type_config OBJECT-TYPE
    SYNTAX DisplayString
    MAX-ACCESS accessible-for-notify
    STATUS current
    DESCRIPTION
        "Parameter 'mac_addr_type_config' in event SRVP.15"
    ::= { srvpEventObjects15 3 }

srvp15_mac_addr_config OBJECT-TYPE
    SYNTAX DisplayString
    MAX-ACCESS accessible-for-notify
    STATUS current
    DESCRIPTION
        "Parameter 'mac_addr_config' in event SRVP.15"
    ::= { srvpEventObjects15 4 }

srvpEventObjects16 OBJECT-IDENTITY
    STATUS current
    DESCRIPTION
        "Event SRVP.16
        A packet has matched with an access-list"
    ::= { srvpEventsGroup 16 }

srvp16_msg_prtcl_type OBJECT-TYPE
    SYNTAX DisplayString
    MAX-ACCESS accessible-for-notify
    STATUS current
    DESCRIPTION
        "Parameter 'msg_prtcl_type' in event SRVP.16"
    ::= { srvpEventObjects16 1 }

srvp16_acl_num OBJECT-TYPE
    SYNTAX Integer32
    MAX-ACCESS accessible-for-notify
    STATUS current
    DESCRIPTION
        "Parameter 'acl_num' in event SRVP.16"
    ::= { srvpEventObjects16 2 }

srvp16_interface_name OBJECT-TYPE
    SYNTAX DisplayString
    MAX-ACCESS accessible-for-notify
    STATUS current
    DESCRIPTION
        "Parameter 'interface_name' in event SRVP.16"
    ::= { srvpEventObjects16 3 }

srvpEventObjects17 OBJECT-IDENTITY
    STATUS current
    DESCRIPTION
        "Event SRVP.17
        A packet has the same cos value src"
    ::= { srvpEventsGroup 17 }

srvp17_cos_pkt OBJECT-TYPE
    SYNTAX Integer32
    MAX-ACCESS accessible-for-notify
    STATUS current
    DESCRIPTION
        "Parameter 'cos_pkt' in event SRVP.17"
    ::= { srvpEventObjects17 1 }

srvpEventObjects18 OBJECT-IDENTITY
    STATUS current
    DESCRIPTION
        "Event SRVP.18
        A packet has the same src/dst MAC address value"
    ::= { srvpEventsGroup 18 }

srvp18_mac_addr_type OBJECT-TYPE
    SYNTAX DisplayString
    MAX-ACCESS accessible-for-notify
    STATUS current
    DESCRIPTION
        "Parameter 'mac_addr_type' in event SRVP.18"
    ::= { srvpEventObjects18 1 }

srvp18_mac_addr_pkt OBJECT-TYPE
    SYNTAX DisplayString
    MAX-ACCESS accessible-for-notify
    STATUS current
    DESCRIPTION
        "Parameter 'mac_addr_pkt' in event SRVP.18"
    ::= { srvpEventObjects18 2 }

srvp18_mac_addr_type_config OBJECT-TYPE
    SYNTAX DisplayString
    MAX-ACCESS accessible-for-notify
    STATUS current
    DESCRIPTION
        "Parameter 'mac_addr_type_config' in event SRVP.18"
    ::= { srvpEventObjects18 3 }

srvp18_mac_addr_config OBJECT-TYPE
    SYNTAX DisplayString
    MAX-ACCESS accessible-for-notify
    STATUS current
    DESCRIPTION
        "Parameter 'mac_addr_config' in event SRVP.18"
    ::= { srvpEventObjects18 4 }

srvpEventObjects19 OBJECT-IDENTITY
    STATUS current
    DESCRIPTION
        "Event SRVP.19
        A packet has a different src/dst MAC address value"
    ::= { srvpEventsGroup 19 }

srvp19_mac_addr_type OBJECT-TYPE
    SYNTAX DisplayString
    MAX-ACCESS accessible-for-notify
    STATUS current
    DESCRIPTION
        "Parameter 'mac_addr_type' in event SRVP.19"
    ::= { srvpEventObjects19 1 }

srvp19_mac_addr_pkt OBJECT-TYPE
    SYNTAX DisplayString
    MAX-ACCESS accessible-for-notify
    STATUS current
    DESCRIPTION
        "Parameter 'mac_addr_pkt' in event SRVP.19"
    ::= { srvpEventObjects19 2 }

srvp19_mac_addr_config OBJECT-TYPE
    SYNTAX DisplayString
    MAX-ACCESS accessible-for-notify
    STATUS current
    DESCRIPTION
        "Parameter 'mac_addr_config' in event SRVP.19"
    ::= { srvpEventObjects19 3 }

srvp19_mac_addr_type_config OBJECT-TYPE
    SYNTAX DisplayString
    MAX-ACCESS accessible-for-notify
    STATUS current
    DESCRIPTION
        "Parameter 'mac_addr_type_config' in event SRVP.19"
    ::= { srvpEventObjects19 4 }

srvpEventObjects20 OBJECT-IDENTITY
    STATUS current
    DESCRIPTION
        "Event SRVP.20
        A packet has been discarded by policing (rate-limit)"
    ::= { srvpEventsGroup 20 }

srvp20_protocol_type OBJECT-TYPE
    SYNTAX DisplayString
    MAX-ACCESS accessible-for-notify
    STATUS current
    DESCRIPTION
        "Parameter 'protocol_type' in event SRVP.20"
    ::= { srvpEventObjects20 1 }

srvp20_class_name OBJECT-TYPE
    SYNTAX DisplayString
    MAX-ACCESS accessible-for-notify
    STATUS current
    DESCRIPTION
        "Parameter 'class_name' in event SRVP.20"
    ::= { srvpEventObjects20 2 }

srvp20_interface_name OBJECT-TYPE
    SYNTAX DisplayString
    MAX-ACCESS accessible-for-notify
    STATUS current
    DESCRIPTION
        "Parameter 'interface_name' in event SRVP.20"
    ::= { srvpEventObjects20 3 }


srvpNotification1 NOTIFICATION-TYPE
    OBJECTS { 
              srvp1_class_name, 
              srvp1_interface_name 
            }
    STATUS current
    DESCRIPTION
        "Notification of Event SRVP.1

        Message: 'packet has been classified class-map $1 at interface $2'

        Parameters list:
              $1: srvp1_class_name
              $2: srvp1_interface_name

        A packet has been classified in the class-map"
    ::= { srvpNotificationsPrefix 1 }

srvpNotification2 NOTIFICATION-TYPE
    OBJECTS { 
              srvp2_class_name, 
              srvp2_interface_name 
            }
    STATUS current
    DESCRIPTION
        "Notification of Event SRVP.2

        Message: 'packet has been discarded by the class-map $1 at interface $2'

        Parameters list:
              $1: srvp2_class_name
              $2: srvp2_interface_name

        A packet has been discarded by the class-map"
    ::= { srvpNotificationsPrefix 2 }

srvpNotification3 NOTIFICATION-TYPE
    OBJECTS { 
              srvp3_prtcl_type, 
              srvp3_acl_num,
              srvp3_interface_name 
            }
    STATUS current
    DESCRIPTION
        "Notification of Event SRVP.3

        Message: 'a packet of protocol $1 does not match with ACL $2 at interface $3'

        Parameters list:
              $1: srvp3_prtcl_type
              $2: srvp3_acl_num
              $3: srvp3_interface_name

        A packet has not matched with an access-list"
    ::= { srvpNotificationsPrefix 3 }

srvpNotification4 NOTIFICATION-TYPE
    OBJECTS { 
              srvp4_interface_name 
            }
    STATUS current
    DESCRIPTION
        "Notification of Event SRVP.4

        Message: 'service policy is enabled at the interface $1'

        Parameters list:
              $1: srvp4_interface_name

        Notifies when service policy is started properly"
    ::= { srvpNotificationsPrefix 4 }

srvpNotification5 NOTIFICATION-TYPE
    OBJECTS { 
              srvp5_interface_name 
            }
    STATUS current
    DESCRIPTION
        "Notification of Event SRVP.5

        Message: 'service policy is disabled at the interface $1'

        Parameters list:
              $1: srvp5_interface_name

        Notifies when service policy is disabled"
    ::= { srvpNotificationsPrefix 5 }

srvpNotification6 NOTIFICATION-TYPE
    OBJECTS { 
              srvp6_interface_name, 
              srvp6_prtcl 
            }
    STATUS current
    DESCRIPTION
        "Notification of Event SRVP.6

        Message: 'packet transmitted from interface $1 to the protocol $2'

        Parameters list:
              $1: srvp6_interface_name
              $2: srvp6_prtcl

        A packet has been transmitted to the protocol"
    ::= { srvpNotificationsPrefix 6 }

srvpNotification7 NOTIFICATION-TYPE
    OBJECTS { 
              srvp7_prtcl, 
              srvp7_interface_name 
            }
    STATUS current
    DESCRIPTION
        "Notification of Event SRVP.7

        Message: 'packet of protocol $1 at interface $2 does not match with any class-map'

        Parameters list:
              $1: srvp7_prtcl
              $2: srvp7_interface_name

        A packet does not match with any class-map"
    ::= { srvpNotificationsPrefix 7 }

srvpNotification8 NOTIFICATION-TYPE
    OBJECTS { 
              srvp8_timer_name, 
              srvp8_class_name,
              srvp8_new_time,
              srvp8_new_time_out 
            }
    STATUS current
    DESCRIPTION
        "Notification of Event SRVP.8

        Message: 'timer '$1' launched on class-map $2 new time $3, new time-out $4'

        Parameters list:
              $1: srvp8_timer_name
              $2: srvp8_class_name
              $3: srvp8_new_time
              $4: srvp8_new_time_out

        A timer has been scheduled in a class-map"
    ::= { srvpNotificationsPrefix 8 }

srvpNotification9 NOTIFICATION-TYPE
    OBJECTS { 
              srvp9_timer_name, 
              srvp9_class_name 
            }
    STATUS current
    DESCRIPTION
        "Notification of Event SRVP.9

        Message: 'timer '$1' has expired in class-map $2'

        Parameters list:
              $1: srvp9_timer_name
              $2: srvp9_class_name

        A timer has expired in a class-map"
    ::= { srvpNotificationsPrefix 9 }

srvpNotification10 NOTIFICATION-TYPE
    OBJECTS { 
              srvp10_class_name, 
              srvp10_num_label 
            }
    STATUS current
    DESCRIPTION
        "Notification of Event SRVP.10

        Message: 'Packet of class-map $1, has been tagged with the label $2'

        Parameters list:
              $1: srvp10_class_name
              $2: srvp10_num_label

        A packet has been tagged with a new label value"
    ::= { srvpNotificationsPrefix 10 }

srvpNotification11 NOTIFICATION-TYPE
    STATUS current
    DESCRIPTION
        "Notification of Event SRVP.11

        Message: 'match criteria is pending to be checked, packet not match'

        A packet has not enough information to check the match criteria"
    ::= { srvpNotificationsPrefix 11 }

srvpNotification12 NOTIFICATION-TYPE
    OBJECTS { 
              srvp12_cos_pkt, 
              srvp12_cos_config 
            }
    STATUS current
    DESCRIPTION
        "Notification of Event SRVP.12

        Message: 'packet cos $1 does not match with cos config value $2'

        Parameters list:
              $1: srvp12_cos_pkt
              $2: srvp12_cos_config

        A packet has not the same cos value"
    ::= { srvpNotificationsPrefix 12 }

srvpNotification13 NOTIFICATION-TYPE
    OBJECTS { 
              srvp13_src_mac_addr_pkt, 
              srvp13_src_mac_addr_config 
            }
    STATUS current
    DESCRIPTION
        "Notification of Event SRVP.13

        Message: 'packet MAC source address $1 does not match with the config value $2'

        Parameters list:
              $1: srvp13_src_mac_addr_pkt
              $2: srvp13_src_mac_addr_config

        A packet has not the same src MAC addr value"
    ::= { srvpNotificationsPrefix 13 }

srvpNotification14 NOTIFICATION-TYPE
    OBJECTS { 
              srvp14_src_mac_addr_pkt, 
              srvp14_src_mac_addr_config 
            }
    STATUS current
    DESCRIPTION
        "Notification of Event SRVP.14

        Message: 'packet MAC destination address $1 does not match with the config value $2'

        Parameters list:
              $1: srvp14_src_mac_addr_pkt
              $2: srvp14_src_mac_addr_config

        A packet has not the same dst MAC addr value"
    ::= { srvpNotificationsPrefix 14 }

srvpNotification15 NOTIFICATION-TYPE
    OBJECTS { 
              srvp15_mac_addr_type, 
              srvp15_mac_addr_pkt,
              srvp15_mac_addr_type_config,
              srvp15_mac_addr_config 
            }
    STATUS current
    DESCRIPTION
        "Notification of Event SRVP.15

        Message: 'packet MAC $1 address $2 match with the unwanted MAC $3 address config $4, packet is discarded'

        Parameters list:
              $1: srvp15_mac_addr_type
              $2: srvp15_mac_addr_pkt
              $3: srvp15_mac_addr_type_config
              $4: srvp15_mac_addr_config

        A packet has the same [not] src/dst MAC address value, and then the packet is discarded"
    ::= { srvpNotificationsPrefix 15 }

srvpNotification16 NOTIFICATION-TYPE
    OBJECTS { 
              srvp16_msg_prtcl_type, 
              srvp16_acl_num,
              srvp16_interface_name 
            }
    STATUS current
    DESCRIPTION
        "Notification of Event SRVP.16

        Message: 'a packet of protocol $1 matchs with ACL $2 at interface $3'

        Parameters list:
              $1: srvp16_msg_prtcl_type
              $2: srvp16_acl_num
              $3: srvp16_interface_name

        A packet has matched with an access-list"
    ::= { srvpNotificationsPrefix 16 }

srvpNotification17 NOTIFICATION-TYPE
    OBJECTS { 
              srvp17_cos_pkt 
            }
    STATUS current
    DESCRIPTION
        "Notification of Event SRVP.17

        Message: 'packet cos $1 matchs with cos config value'

        Parameters list:
              $1: srvp17_cos_pkt

        A packet has the same cos value src"
    ::= { srvpNotificationsPrefix 17 }

srvpNotification18 NOTIFICATION-TYPE
    OBJECTS { 
              srvp18_mac_addr_type, 
              srvp18_mac_addr_pkt,
              srvp18_mac_addr_type_config,
              srvp18_mac_addr_config 
            }
    STATUS current
    DESCRIPTION
        "Notification of Event SRVP.18

        Message: 'packet MAC $1 address $2 matchs with the MAC $3 address config value $4'

        Parameters list:
              $1: srvp18_mac_addr_type
              $2: srvp18_mac_addr_pkt
              $3: srvp18_mac_addr_type_config
              $4: srvp18_mac_addr_config

        A packet has the same src/dst MAC address value"
    ::= { srvpNotificationsPrefix 18 }

srvpNotification19 NOTIFICATION-TYPE
    OBJECTS { 
              srvp19_mac_addr_type, 
              srvp19_mac_addr_pkt,
              srvp19_mac_addr_config,
              srvp19_mac_addr_type_config 
            }
    STATUS current
    DESCRIPTION
        "Notification of Event SRVP.19

        Message: 'packet MAC $1 address $2, has a different MAC $3 address of the config value $4'

        Parameters list:
              $1: srvp19_mac_addr_type
              $2: srvp19_mac_addr_pkt
              $3: srvp19_mac_addr_config
              $4: srvp19_mac_addr_type_config

        A packet has a different src/dst MAC address value"
    ::= { srvpNotificationsPrefix 19 }

srvpNotification20 NOTIFICATION-TYPE
    OBJECTS { 
              srvp20_protocol_type, 
              srvp20_class_name,
              srvp20_interface_name 
            }
    STATUS current
    DESCRIPTION
        "Notification of Event SRVP.20

        Message: 'packet of protocol $1 has been discarded by policing of class-map $2 at interface $3'

        Parameters list:
              $1: srvp20_protocol_type
              $2: srvp20_class_name
              $3: srvp20_interface_name

        A packet has been discarded by policing (rate-limit)"
    ::= { srvpNotificationsPrefix 20 }


END
