OPTC-VCA-MIB DEFINITIONS ::= BEGIN

IMPORTS
	optcServices
		FROM OPTC-SMI
	MODULE-IDENTITY,
	OBJECT-IDENTITY,
	OBJECT-TYPE,
	NOTIFICATION-TYPE,
	Integer32
		FROM SNMPv2-SMI
	TruthValue
		FROM SNMPv2-TC
	OBJECT-GROUP,
	NOTIFICATION-GROUP
		FROM SNMPv2-CONF;

optcVca MODULE-IDENTITY
	LAST-UPDATED "201105180644Z"	-- May 18, 2011 6:44:00 AM
	ORGANIZATION "Optelecom-NKF"
	CONTACT-INFO
		"WWW.OPTELECOM-NKF.COM"
	DESCRIPTION
		"This MIB contains objects that provide information about the video content of a particular Optelecom-NKF device."
	REVISION "201105180644Z"	-- May 18, 2011 6:44:00 AM
	DESCRIPTION
		"Initial version."
	-- 1.3.6.1.4.1.17534.2.2.3
	::= { optcServices 3 }


optcImageQualityTable OBJECT-TYPE
	SYNTAX  SEQUENCE OF OptcImageQualityEntry
	MAX-ACCESS not-accessible
	STATUS current
	DESCRIPTION
		"A list of video inputs that support content analysis."
	-- 1.3.6.1.4.1.17534.2.2.3.1
	::= { optcVca 1 }


optcImageQualityEntry OBJECT-TYPE
	SYNTAX  OptcImageQualityEntry
	MAX-ACCESS not-accessible
	STATUS current
	DESCRIPTION
		"An entry containing specific video content analysis information applicable to a certain input."
	INDEX {
		optcImageQualityDeviceIndex,
		optcImageQualityInputIndex }
	-- 1.3.6.1.4.1.17534.2.2.3.1.1
	::= { optcImageQualityTable 1 }


OptcImageQualityEntry ::= SEQUENCE {

	optcImageQualityDeviceIndex Integer32,
	optcImageQualityInputIndex  Integer32,
	optcBadContrastAlarm        TruthValue,
	optcBadExposureAlarm        TruthValue,
	optcLowDetailAlarm          TruthValue,
	optcLowSnrAlarm             TruthValue }


optcImageQualityDeviceIndex OBJECT-TYPE
	SYNTAX  Integer32 (1..2147483647)
	MAX-ACCESS accessible-for-notify
	STATUS current
	DESCRIPTION
		"A unique value, greater than zero, for each device."
	-- 1.3.6.1.4.1.17534.2.2.3.1.1.1
	::= { optcImageQualityEntry 1 }


optcImageQualityInputIndex OBJECT-TYPE
	SYNTAX  Integer32 (1..2147483647)
	MAX-ACCESS accessible-for-notify
	STATUS current
	DESCRIPTION
		"A unique value, greater than zero, for each input."
	-- 1.3.6.1.4.1.17534.2.2.3.1.1.2
	::= { optcImageQualityEntry 2 }


optcBadContrastAlarm OBJECT-TYPE
	SYNTAX  TruthValue
	MAX-ACCESS read-only
	STATUS current
	DESCRIPTION
		"This variable identifies whether or not the input image has a bad 
		contrast. When a bad contrast is detected on an input,
		an optcImageQualityBad notification will be sent."
	-- 1.3.6.1.4.1.17534.2.2.3.1.1.5
	::= { optcImageQualityEntry 5 }


optcBadExposureAlarm OBJECT-TYPE
	SYNTAX  TruthValue
	MAX-ACCESS read-only
	STATUS current
	DESCRIPTION
		"This variable identifies whether or not the input image has a bad 
		exposure. When a bad exposure is detected on an input,
		an optcImageQualityBad notification will be sent."
	-- 1.3.6.1.4.1.17534.2.2.3.1.1.6
	::= { optcImageQualityEntry 6 }


optcLowDetailAlarm OBJECT-TYPE
	SYNTAX  TruthValue
	MAX-ACCESS read-only
	STATUS current
	DESCRIPTION
		"This variable identifies whether or not the input image has a low 
		detail. When a low detail is detected on an input,
		an optcImageQualityBad notification will be sent."
	-- 1.3.6.1.4.1.17534.2.2.3.1.1.7
	::= { optcImageQualityEntry 7 }


optcLowSnrAlarm OBJECT-TYPE
	SYNTAX  TruthValue
	MAX-ACCESS read-only
	STATUS current
	DESCRIPTION
		"This variable identifies whether or not the input image has a low 
		signal to noise ratio. When a low signal to noise ratio s detected 
		on an input, an optcImageQualityBad notification will be sent."
	-- 1.3.6.1.4.1.17534.2.2.3.1.1.8
	::= { optcImageQualityEntry 8 }


optcTamperingTable OBJECT-TYPE
	SYNTAX  SEQUENCE OF OptcTamperingEntry
	MAX-ACCESS not-accessible
	STATUS current
	DESCRIPTION
		"A list of video inputs that support content analysis."
	-- 1.3.6.1.4.1.17534.2.2.3.2
	::= { optcVca 2 }


optcTamperingEntry OBJECT-TYPE
	SYNTAX  OptcTamperingEntry
	MAX-ACCESS not-accessible
	STATUS current
	DESCRIPTION
		"An entry containing specific video content analysis information applicable to a certain input."
	INDEX {
		optcTamperingDeviceIndex,
		optcTamperingInputIndex }
	-- 1.3.6.1.4.1.17534.2.2.3.2.1
	::= { optcTamperingTable 1 }


OptcTamperingEntry ::= SEQUENCE {

	optcTamperingDeviceIndex Integer32,
	optcTamperingInputIndex  Integer32,
	optcNoMatchAlarm         TruthValue,
	optcPositionChangedAlarm TruthValue }


optcTamperingDeviceIndex OBJECT-TYPE
	SYNTAX  Integer32 (1..2147483647)
	MAX-ACCESS accessible-for-notify
	STATUS current
	DESCRIPTION
		"A unique value, greater than zero, for each device."
	-- 1.3.6.1.4.1.17534.2.2.3.2.1.1
	::= { optcTamperingEntry 1 }


optcTamperingInputIndex OBJECT-TYPE
	SYNTAX  Integer32 (1..2147483647)
	MAX-ACCESS accessible-for-notify
	STATUS current
	DESCRIPTION
		"A unique value, greater than zero, for each input."
	-- 1.3.6.1.4.1.17534.2.2.3.2.1.2
	::= { optcTamperingEntry 2 }


optcNoMatchAlarm OBJECT-TYPE
	SYNTAX  TruthValue
	MAX-ACCESS read-only
	STATUS current
	DESCRIPTION
		"This variable identifies whether or not the input image matches 
		a reference image. When an image mismatch is detected on an input,
		an optcTamperingDetected notification will be sent."
	-- 1.3.6.1.4.1.17534.2.2.3.2.1.3
	::= { optcTamperingEntry 3 }


optcPositionChangedAlarm OBJECT-TYPE
	SYNTAX  TruthValue
	MAX-ACCESS read-only
	STATUS current
	DESCRIPTION
		"This variable identifies whether or not the position of the camera 
		has been changed. When a position change is detected on an input,
		an optcTamperingDetected notification will be sent."
	-- 1.3.6.1.4.1.17534.2.2.3.2.1.4
	::= { optcTamperingEntry 4 }


optcVcaNotifications OBJECT-IDENTITY
	STATUS current
	DESCRIPTION
		"The VCA notifications (traps)"
	-- 1.3.6.1.4.1.17534.2.2.3.3
	::= { optcVca 3 }


optcImageQualityOk NOTIFICATION-TYPE
	OBJECTS {
		optcImageQualityDeviceIndex,
		optcImageQualityInputIndex,
		optcBadContrastAlarm,
		optcBadExposureAlarm,
		optcLowDetailAlarm,
		optcLowSnrAlarm}
	STATUS current
	DESCRIPTION
		"An optcImageQualityOk notification will be 
		sent by the device when the conditions that 
		cause an optcImageQualityBad situatation 
		have passed."
	-- 1.3.6.1.4.1.17534.2.2.3.3.1
	::= { optcVcaNotifications 1 }


optcImageQualityBad NOTIFICATION-TYPE
	OBJECTS {
		optcImageQualityDeviceIndex,
		optcImageQualityInputIndex,
		optcBadContrastAlarm,
		optcBadExposureAlarm,
		optcLowDetailAlarm,
		optcLowSnrAlarm}
	STATUS current
	DESCRIPTION
		"An optcImageQualityBad notification will be sent by the 
		device when a bad contrast, bad exposure, 
		low detail or a low signal to noise ratio in an 
		image is detected."
	-- 1.3.6.1.4.1.17534.2.2.3.3.2
	::= { optcVcaNotifications 2 }


optcTamperingOk NOTIFICATION-TYPE
	OBJECTS {
		optcTamperingDeviceIndex,
		optcTamperingInputIndex,
		optcNoMatchAlarm,
		optcPositionChangedAlarm}
	STATUS current
	DESCRIPTION
		"An optcTamperingOk notification will be sent by 
		the device when the conditions that cause 
		the optcImageTamperingDetected situation have passed

		"
	-- 1.3.6.1.4.1.17534.2.2.3.3.3
	::= { optcVcaNotifications 3 }


optcTamperingDetected NOTIFICATION-TYPE
	OBJECTS {
		optcTamperingDeviceIndex,
		optcTamperingInputIndex,
		optcNoMatchAlarm,
		optcPositionChangedAlarm}
	STATUS current
	DESCRIPTION
		"An optcTamperingDetected notification will be sent by 
		the device when there is an image mismatch 
		or a position changed is detected."
	-- 1.3.6.1.4.1.17534.2.2.3.3.4
	::= { optcVcaNotifications 4 }

optcImageQualityGroup OBJECT-GROUP
	OBJECTS {
		optcImageQualityDeviceIndex,
		optcImageQualityInputIndex,
		optcBadContrastAlarm,
		optcBadExposureAlarm,
		optcLowDetailAlarm,
		optcLowSnrAlarm }
	STATUS current
	DESCRIPTION
		""
	-- 1.3.6.1.4.1.17534.2.2.3.4
	::= { optcVca 4 }

optcTamperingGroup OBJECT-GROUP
	OBJECTS {
		optcTamperingDeviceIndex,
		optcTamperingInputIndex,
		optcNoMatchAlarm,
		optcPositionChangedAlarm }
	STATUS current
	DESCRIPTION
		""
	-- 1.3.6.1.4.1.17534.2.2.3.5
	::= { optcVca 5 }

optcVcaNotificationsGroup NOTIFICATION-GROUP
	NOTIFICATIONS {
		optcImageQualityOk,
		optcImageQualityBad,
		optcTamperingOk,
		optcTamperingDetected }
	STATUS current
	DESCRIPTION
		"Group of objects describing notifications (traps)."
	-- 1.3.6.1.4.1.17534.2.2.3.6
	::= { optcVca 6 }

END
