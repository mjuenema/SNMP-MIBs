OPTC-STATUS-MIB DEFINITIONS ::= BEGIN

IMPORTS
	optcServices
		FROM OPTC-SMI
	MODULE-IDENTITY,
	OBJECT-IDENTITY,
	OBJECT-TYPE,
	NOTIFICATION-TYPE,
	Counter64,
	Integer32
		FROM SNMPv2-SMI
	DisplayString,
	TruthValue
		FROM SNMPv2-TC
	OBJECT-GROUP,
	NOTIFICATION-GROUP
		FROM SNMPv2-CONF;

optcStatus MODULE-IDENTITY
	LAST-UPDATED "200511020000Z"	-- Nov 2, 2005 12:00:00 AM
	ORGANIZATION "Optelecom-NKF"
	CONTACT-INFO
		"WWW.OPTELECOM-NKF.COM"
	DESCRIPTION
		"This MIB contains objects that provide information about inputs and streams
		for a particular Optelecom-NKF device."
	REVISION "200511020000Z"	-- Nov 2, 2005 12:00:00 AM
	DESCRIPTION
		"Minor modifications before final release."
	REVISION "200509100000Z"	-- Sep 10, 2005 12:00:00 AM
	DESCRIPTION
		"The initial revision of this module."
	-- 1.3.6.1.4.1.17534.2.2.2
	::= { optcServices 2 }


optcStreamTable OBJECT-TYPE
	SYNTAX  SEQUENCE OF OptcStreamEntry
	MAX-ACCESS not-accessible
	STATUS current
	DESCRIPTION
		"A list of streams."
	-- 1.3.6.1.4.1.17534.2.2.2.2
	::= { optcStatus 2 }


optcStreamEntry OBJECT-TYPE
	SYNTAX  OptcStreamEntry
	MAX-ACCESS not-accessible
	STATUS current
	DESCRIPTION
		"An entry containing specific stream information applicable to
		a certain stream."
	INDEX {
		optcStreamDeviceIndex,
		optcStreamIndex }
	-- 1.3.6.1.4.1.17534.2.2.2.2.1
	::= { optcStreamTable 1 }


OptcStreamEntry ::= SEQUENCE {

	optcStreamDeviceIndex Integer32,
	optcStreamIndex       Integer32,
	optcStreamType        INTEGER,
	optcStreamMedia       INTEGER,
	optcStreamDescription DisplayString,
	optcStreamStatus      DisplayString,
	optcStreamEnabled     TruthValue,
	optcStreamPkts        Counter64,
	optcStreamPktsLost    Counter64,
	optcStreamDownAlarm   TruthValue }


optcStreamDeviceIndex OBJECT-TYPE
	SYNTAX  Integer32 (1..2147483647)
	MAX-ACCESS accessible-for-notify
	STATUS current
	DESCRIPTION
		"A unique value, greater than zero, for each device."
	-- 1.3.6.1.4.1.17534.2.2.2.2.1.1
	::= { optcStreamEntry 1 }


optcStreamIndex OBJECT-TYPE
	SYNTAX  Integer32 (1..2147483647)
	MAX-ACCESS accessible-for-notify
	STATUS current
	DESCRIPTION
		"A unique value, greater than zero, for each stream."
	-- 1.3.6.1.4.1.17534.2.2.2.2.1.2
	::= { optcStreamEntry 2 }


optcStreamType OBJECT-TYPE
	SYNTAX  INTEGER {
			rx(1), 	-- Rx stream
			tx(2) 	-- Tx stream
			}
	MAX-ACCESS read-only
	STATUS current
	DESCRIPTION
		"The stream type, either transmitting or receiving."
	-- 1.3.6.1.4.1.17534.2.2.2.2.1.3
	::= { optcStreamEntry 3 }


optcStreamMedia OBJECT-TYPE
	SYNTAX  INTEGER {
			video(1), 	-- Video
			audio(2), 	-- Audio
			data(3),  	-- Data
			cc(4)    	-- Contact Closure
			}
	MAX-ACCESS read-only
	STATUS current
	DESCRIPTION
		"The media type of this stream. A stream contains information for one
		media type. Examples of media types are: video, audio, data, cc."
	-- 1.3.6.1.4.1.17534.2.2.2.2.1.4
	::= { optcStreamEntry 4 }


optcStreamDescription OBJECT-TYPE
	SYNTAX  DisplayString
	MAX-ACCESS read-only
	STATUS current
	DESCRIPTION
		"A textual string containing a description for this stream."
	-- 1.3.6.1.4.1.17534.2.2.2.2.1.5
	::= { optcStreamEntry 5 }


optcStreamStatus OBJECT-TYPE
	SYNTAX  DisplayString
	MAX-ACCESS read-only
	STATUS current
	DESCRIPTION
		"A textual string containing the status of this stream."
	-- 1.3.6.1.4.1.17534.2.2.2.2.1.6
	::= { optcStreamEntry 6 }


optcStreamEnabled OBJECT-TYPE
	SYNTAX  TruthValue
	MAX-ACCESS read-only
	STATUS current
	DESCRIPTION
		"This variable identifies whether or not the stream is enabled."
	-- 1.3.6.1.4.1.17534.2.2.2.2.1.7
	::= { optcStreamEntry 7 }


optcStreamPkts OBJECT-TYPE
	SYNTAX  Counter64
	MAX-ACCESS read-only
	STATUS current
	DESCRIPTION
		"The number of packets sent or received by this stream."
	-- 1.3.6.1.4.1.17534.2.2.2.2.1.8
	::= { optcStreamEntry 8 }


optcStreamPktsLost OBJECT-TYPE
	SYNTAX  Counter64
	MAX-ACCESS read-only
	STATUS current
	DESCRIPTION
		"The number of packets lost by this stream. Only applicable to
		receiving (optcStreamType = rx(1)) streams."
	-- 1.3.6.1.4.1.17534.2.2.2.2.1.9
	::= { optcStreamEntry 9 }


optcStreamDownAlarm OBJECT-TYPE
	SYNTAX  TruthValue
	MAX-ACCESS read-only
	STATUS current
	DESCRIPTION
		"This variable identifies whether or not the stream down alarm is
		active for this stream. When a stream goes down, an optcStreamDown
		notification will be sent."
	-- 1.3.6.1.4.1.17534.2.2.2.2.1.10
	::= { optcStreamEntry 10 }


optcInputTable OBJECT-TYPE
	SYNTAX  SEQUENCE OF OptcInputEntry
	MAX-ACCESS not-accessible
	STATUS current
	DESCRIPTION
		"A list of inputs."
	-- 1.3.6.1.4.1.17534.2.2.2.3
	::= { optcStatus 3 }


optcInputEntry OBJECT-TYPE
	SYNTAX  OptcInputEntry
	MAX-ACCESS not-accessible
	STATUS current
	DESCRIPTION
		"An entry containing specific input information applicable to a certain input."
	INDEX {
		optcInputDeviceIndex,
		optcInputIndex }
	-- 1.3.6.1.4.1.17534.2.2.2.3.1
	::= { optcInputTable 1 }


OptcInputEntry ::= SEQUENCE {

	optcInputDeviceIndex Integer32,
	optcInputIndex       Integer32,
	optcInputMedia       INTEGER,
	optcInputDescription DisplayString,
	optcInputStatus      DisplayString,
	optcInputEnabled     TruthValue,
	optcSignalLostAlarm  TruthValue,
	optcFormatAlarm      TruthValue }


optcInputDeviceIndex OBJECT-TYPE
	SYNTAX  Integer32 (1..2147483647)
	MAX-ACCESS accessible-for-notify
	STATUS current
	DESCRIPTION
		"A unique value, greater than zero, for each device."
	-- 1.3.6.1.4.1.17534.2.2.2.3.1.1
	::= { optcInputEntry 1 }


optcInputIndex OBJECT-TYPE
	SYNTAX  Integer32 (1..2147483647)
	MAX-ACCESS accessible-for-notify
	STATUS current
	DESCRIPTION
		"A unique value, greater than zero, for each input."
	-- 1.3.6.1.4.1.17534.2.2.2.3.1.2
	::= { optcInputEntry 2 }


optcInputMedia OBJECT-TYPE
	SYNTAX  INTEGER {
			video(1), 	-- Video
			audio(2), 	-- Audio
			data(3),  	-- Data
			cc(4)    	-- Contact Closure
			}
	MAX-ACCESS read-only
	STATUS current
	DESCRIPTION
		"The media type of this input. An input is always of a certain
		type. Examples of media types are: video, audio, data, cc."
	-- 1.3.6.1.4.1.17534.2.2.2.3.1.3
	::= { optcInputEntry 3 }


optcInputDescription OBJECT-TYPE
	SYNTAX  DisplayString
	MAX-ACCESS read-only
	STATUS current
	DESCRIPTION
		"A textual string containing a description for this input."
	-- 1.3.6.1.4.1.17534.2.2.2.3.1.4
	::= { optcInputEntry 4 }


optcInputStatus OBJECT-TYPE
	SYNTAX  DisplayString
	MAX-ACCESS read-only
	STATUS current
	DESCRIPTION
		"A textual string containing the status of this input."
	-- 1.3.6.1.4.1.17534.2.2.2.3.1.5
	::= { optcInputEntry 5 }


optcInputEnabled OBJECT-TYPE
	SYNTAX  TruthValue
	MAX-ACCESS read-only
	STATUS current
	DESCRIPTION
		"This variable identifies whether or not the input is enabled."
	-- 1.3.6.1.4.1.17534.2.2.2.3.1.6
	::= { optcInputEntry 6 }


optcSignalLostAlarm OBJECT-TYPE
	SYNTAX  TruthValue
	MAX-ACCESS read-only
	STATUS current
	DESCRIPTION
		"This variable identifies whether or not the input signal lost alarm is
		active for this input. When an input looses its signal, an
		optcSignalLost notification will be sent."
	-- 1.3.6.1.4.1.17534.2.2.2.3.1.7
	::= { optcInputEntry 7 }


optcFormatAlarm OBJECT-TYPE
	SYNTAX  TruthValue
	MAX-ACCESS read-only
	STATUS current
	DESCRIPTION
		"This variable identifies whether or not the input format alarm is
		active for this input. When a format error is detected on an input,
		an optcFormatError notification will be sent."
	-- 1.3.6.1.4.1.17534.2.2.2.3.1.8
	::= { optcInputEntry 8 }


optcNetworkTable OBJECT-TYPE
	SYNTAX  SEQUENCE OF OptcNetworkEntry
	MAX-ACCESS not-accessible
	STATUS current
	DESCRIPTION
		"A list of networks."
	-- 1.3.6.1.4.1.17534.2.2.2.4
	::= { optcStatus 4 }


optcNetworkEntry OBJECT-TYPE
	SYNTAX  OptcNetworkEntry
	MAX-ACCESS not-accessible
	STATUS current
	DESCRIPTION
		"An entry containing specific network information applicable to
		a certain network."
	INDEX {
		optcNetworkDeviceIndex }
	-- 1.3.6.1.4.1.17534.2.2.2.4.1
	::= { optcNetworkTable 1 }


OptcNetworkEntry ::= SEQUENCE {

	optcNetworkDeviceIndex   Integer32,
	optcNetworkOverloadAlarm TruthValue }


optcNetworkDeviceIndex OBJECT-TYPE
	SYNTAX  Integer32 (1..2147483647)
	MAX-ACCESS accessible-for-notify
	STATUS current
	DESCRIPTION
		"A unique value, greater than zero, for each device."
	-- 1.3.6.1.4.1.17534.2.2.2.4.1.1
	::= { optcNetworkEntry 1 }


optcNetworkOverloadAlarm OBJECT-TYPE
	SYNTAX  TruthValue
	MAX-ACCESS read-only
	STATUS current
	DESCRIPTION
		"This variable identifies whether or not the network overload alarm is active
		for this device."
	-- 1.3.6.1.4.1.17534.2.2.2.4.1.2
	::= { optcNetworkEntry 2 }


optcStatusNotifications OBJECT-IDENTITY
	STATUS current
	DESCRIPTION
		"The status notifications (traps)."
	-- 1.3.6.1.4.1.17534.2.2.2.5
	::= { optcStatus 5 }


optcStreamUp NOTIFICATION-TYPE
	OBJECTS {
		optcStreamDeviceIndex,
		optcStreamIndex,
		optcStreamType,
		optcStreamMedia,
		optcStreamStatus}
	STATUS current
	DESCRIPTION
		"An optcStreamUp notification will be sent by the device when a
		stream goes from the down to up state. The optcStreamDownAlarm
		variable will be set to false(2) for that particular stream."
	-- 1.3.6.1.4.1.17534.2.2.2.5.1
	::= { optcStatusNotifications 1 }


optcStreamDown NOTIFICATION-TYPE
	OBJECTS {
		optcStreamDeviceIndex,
		optcStreamIndex,
		optcStreamType,
		optcStreamMedia,
		optcStreamStatus}
	STATUS current
	DESCRIPTION
		"An optcStreamUp notification will be sent by the device when a
		stream goes from the up to down state. The optcStreamDownAlarm
		variable will be set to true(2) for that particular stream."
	-- 1.3.6.1.4.1.17534.2.2.2.5.2
	::= { optcStatusNotifications 2 }


optcSignalPresent NOTIFICATION-TYPE
	OBJECTS {
		optcInputDeviceIndex,
		optcInputIndex,
		optcInputMedia,
		optcInputStatus}
	STATUS current
	DESCRIPTION
		"An optcSignalPresent notification will be sent by the device when there was
		no signal present on the particular input, but now an input signal is detected.
		The optcSignalLostAlarm variable will be set to false(1) for that particular
		input."
	-- 1.3.6.1.4.1.17534.2.2.2.5.3
	::= { optcStatusNotifications 3 }


optcSignalLost NOTIFICATION-TYPE
	OBJECTS {
		optcInputDeviceIndex,
		optcInputIndex,
		optcInputMedia,
		optcInputStatus}
	STATUS current
	DESCRIPTION
		"An optcSignalLost notification will be sent by the device when there was
		a signal present on the particular input, but now its no longer detected.
		The optcSignalLostAlarm variable will be set to true(2) for that particular
		input."
	-- 1.3.6.1.4.1.17534.2.2.2.5.4
	::= { optcStatusNotifications 4 }


optcFormatError NOTIFICATION-TYPE
	OBJECTS {
		optcInputDeviceIndex,
		optcInputIndex,
		optcInputMedia,
		optcInputStatus}
	STATUS current
	DESCRIPTION
		"An optcFormatError notification will be sent by the device when a bad
		input signal is detected. The optcFormatAlarm variable will be set to
		true(2) for that particular input."
	-- 1.3.6.1.4.1.17534.2.2.2.5.5
	::= { optcStatusNotifications 5 }


optcFormatOk NOTIFICATION-TYPE
	OBJECTS {
		optcInputDeviceIndex,
		optcInputIndex,
		optcInputMedia,
		optcInputStatus}
	STATUS current
	DESCRIPTION
		"An optcFormatOk notification will be sent by the device when a good
		input signal is detected. The optcFormatAlarm variable will be set to
		false(1) for that particular input."
	-- 1.3.6.1.4.1.17534.2.2.2.5.6
	::= { optcStatusNotifications 6 }


optcNetworkLoadError NOTIFICATION-TYPE
	OBJECTS {
		optcNetworkDeviceIndex}
	STATUS current
	DESCRIPTION
		"An optcNetworkLoadError will be sent by the device when network overload
		is detected and video packets must be dropped."
	-- 1.3.6.1.4.1.17534.2.2.2.5.7
	::= { optcStatusNotifications 7 }


optcNetworkLoadOk NOTIFICATION-TYPE
	OBJECTS {
		optcNetworkDeviceIndex}
	STATUS current
	DESCRIPTION
		"An optcNetworkLoadOk notification will be sent by the device when network
		was overloaded, but now the network load is o.k. again. I.e. no video packets
		are dropped."
	-- 1.3.6.1.4.1.17534.2.2.2.5.8
	::= { optcStatusNotifications 8 }

optcNetworkGroup OBJECT-GROUP
	OBJECTS {
		optcNetworkDeviceIndex,
		optcNetworkOverloadAlarm }
	STATUS current
	DESCRIPTION
		"Network information for this device."
	-- 1.3.6.1.4.1.17534.2.2.2.6
	::= { optcStatus 6 }

optcStreamGroup OBJECT-GROUP
	OBJECTS {
		optcStreamDeviceIndex,
		optcStreamIndex,
		optcStreamType,
		optcStreamMedia,
		optcStreamDescription,
		optcStreamStatus,
		optcStreamEnabled,
		optcStreamPkts,
		optcStreamPktsLost,
		optcStreamDownAlarm }
	STATUS current
	DESCRIPTION
		"Stream information for this device."
	-- 1.3.6.1.4.1.17534.2.2.2.7
	::= { optcStatus 7 }

optcInputGroup OBJECT-GROUP
	OBJECTS {
		optcInputDeviceIndex,
		optcInputIndex,
		optcInputMedia,
		optcInputDescription,
		optcInputStatus,
		optcInputEnabled,
		optcSignalLostAlarm,
		optcFormatAlarm }
	STATUS current
	DESCRIPTION
		"Input information for this device."
	-- 1.3.6.1.4.1.17534.2.2.2.8
	::= { optcStatus 8 }

optcStatusNotificationsGroup NOTIFICATION-GROUP
	NOTIFICATIONS {
		optcStreamUp,
		optcStreamDown,
		optcSignalPresent,
		optcSignalLost,
		optcFormatError,
		optcFormatOk,
		optcNetworkLoadError,
		optcNetworkLoadOk }
	STATUS current
	DESCRIPTION
		"Group of objects describing notifications (traps)."
	-- 1.3.6.1.4.1.17534.2.2.2.9
	::= { optcStatus 9 }

END
