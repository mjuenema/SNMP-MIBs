OPTC-DEVICE-MIB DEFINITIONS ::= BEGIN

IMPORTS
        optcServices
                FROM OPTC-SMI
        MODULE-IDENTITY,
        OBJECT-IDENTITY,
        OBJECT-TYPE,
        NOTIFICATION-TYPE,
        Integer32,
        IpAddress,
        Unsigned32
                FROM SNMPv2-SMI
        TruthValue,
        DateAndTime,
        DisplayString
                FROM SNMPv2-TC
        OBJECT-GROUP,
        NOTIFICATION-GROUP
                FROM SNMPv2-CONF;

optcDevice MODULE-IDENTITY
        LAST-UPDATED "200602010823Z"    -- Feb 1, 2006 8:23:00 AM
        ORGANIZATION "Optelecom-NKF"
        CONTACT-INFO
                "WWW.OPTELECOM-NKF.COM"
        DESCRIPTION
                "Generic device MIB holding information applicable to all Optelecom-NKF Ethernet products."
        REVISION "200602010000Z"        -- Feb 1, 2006 12:00:00 AM
        DESCRIPTION
                "Fixed minor spelling errors."
        REVISION "200511020000Z"        -- Nov 2, 2005 12:00:00 AM
        DESCRIPTION
                "Minor modifications before final release."
        REVISION "200509200000Z"        -- Sep 20, 2005 12:00:00 AM
        DESCRIPTION
                "The initial revision of this module."
        -- 1.3.6.1.4.1.17534.2.2.1
        ::= { optcServices 1 }


optcSysInfoTable OBJECT-TYPE
        SYNTAX  SEQUENCE OF OptcSysInfoEntry
        MAX-ACCESS not-accessible
        STATUS current
        DESCRIPTION
                "A list of devices."
        -- 1.3.6.1.4.1.17534.2.2.1.1
        ::= { optcDevice 1 }


optcSysInfoEntry OBJECT-TYPE
        SYNTAX  OptcSysInfoEntry
        MAX-ACCESS not-accessible
        STATUS current
        DESCRIPTION
                "An entry containing general information applicable
                to a particular device."
        INDEX {
                optcDeviceIndex }
        -- 1.3.6.1.4.1.17534.2.2.1.1.1
        ::= { optcSysInfoTable 1 }


OptcSysInfoEntry ::= SEQUENCE {

        optcDeviceIndex         Integer32,
        optcArticleCode         DisplayString,
        optcModuleID            Unsigned32,
        optcProductName         DisplayString,
        optcProductDescription  DisplayString,
        optcSerialNumber        DisplayString,
        optcProductVersion      DisplayString,
        optcUserLabel1          DisplayString,
        optcUserLabel2          DisplayString,
        optcSoftwareArticleCode DisplayString,
        optcDeviceStatus        DisplayString,
        optcDeviceUpTime        DisplayString,
        optcDateTime            DateAndTime }


optcDeviceIndex OBJECT-TYPE
        SYNTAX  Integer32 (1..2147483647)
        MAX-ACCESS accessible-for-notify
        STATUS current
        DESCRIPTION
                "A unique value, greater than zero, for each device."
        -- 1.3.6.1.4.1.17534.2.2.1.1.1.1
        ::= { optcSysInfoEntry 1 }


optcArticleCode OBJECT-TYPE
        SYNTAX  DisplayString
        MAX-ACCESS read-only
        STATUS current
        DESCRIPTION
                "A textual string containing the Optelecom-NKF specific
                article code."
        -- 1.3.6.1.4.1.17534.2.2.1.1.1.2
        ::= { optcSysInfoEntry 2 }


optcModuleID OBJECT-TYPE
        SYNTAX  Unsigned32
        MAX-ACCESS read-only
        STATUS current
        DESCRIPTION
                "The number, equal or greater than zero, identifying
                the device type. E.g. 1045 =  C23e MPEG2 encoder."
        -- 1.3.6.1.4.1.17534.2.2.1.1.1.3
        ::= { optcSysInfoEntry 3 }


optcProductName OBJECT-TYPE
        SYNTAX  DisplayString
        MAX-ACCESS read-only
        STATUS current
        DESCRIPTION
                "A textual string containing the Optelecom-NKF specific
                product name. E.g. C23 E/IP."
        -- 1.3.6.1.4.1.17534.2.2.1.1.1.4
        ::= { optcSysInfoEntry 4 }


optcProductDescription OBJECT-TYPE
        SYNTAX  DisplayString
        MAX-ACCESS read-only
        STATUS current
        DESCRIPTION
                "A textual string containing a short product description.
                E.g. MPEG-2 triple video encoder."
        -- 1.3.6.1.4.1.17534.2.2.1.1.1.5
        ::= { optcSysInfoEntry 5 }


optcSerialNumber OBJECT-TYPE
        SYNTAX  DisplayString
        MAX-ACCESS read-only
        STATUS current
        DESCRIPTION
                "A textual string containing the unique serial number."
        -- 1.3.6.1.4.1.17534.2.2.1.1.1.6
        ::= { optcSysInfoEntry 6 }


optcProductVersion OBJECT-TYPE
        SYNTAX  DisplayString
        MAX-ACCESS read-only
        STATUS current
        DESCRIPTION
                "A textual string containing the product version number.
                E.g. V2.1.2R01"
        -- 1.3.6.1.4.1.17534.2.2.1.1.1.7
        ::= { optcSysInfoEntry 7 }


optcUserLabel1 OBJECT-TYPE
        SYNTAX  DisplayString
        MAX-ACCESS read-only
        STATUS current
        DESCRIPTION
                "A textual string containing a user defined description."
        -- 1.3.6.1.4.1.17534.2.2.1.1.1.8
        ::= { optcSysInfoEntry 8 }


optcUserLabel2 OBJECT-TYPE
        SYNTAX  DisplayString
        MAX-ACCESS read-only
        STATUS current
        DESCRIPTION
                "A textual string containing a user defined description."
        -- 1.3.6.1.4.1.17534.2.2.1.1.1.9
        ::= { optcSysInfoEntry 9 }


optcSoftwareArticleCode OBJECT-TYPE
        SYNTAX  DisplayString
        MAX-ACCESS read-only
        STATUS current
        DESCRIPTION
                "A textual string containing the Optelecom-NKF specific
                software article code. E.g. 199925123456-01."
        -- 1.3.6.1.4.1.17534.2.2.1.1.1.10
        ::= { optcSysInfoEntry 10 }


optcDeviceStatus OBJECT-TYPE
        SYNTAX  DisplayString
        MAX-ACCESS read-only
        STATUS current
        DESCRIPTION
                "A textual string containing the device alarm status. The
                different status are identified by a one character digit
                ranging from A to O. Where O means no alarm active.
                Any character other than O means there's an alarm active."
        -- 1.3.6.1.4.1.17534.2.2.1.1.1.11
        ::= { optcSysInfoEntry 11 }


optcDateTime OBJECT-TYPE
        SYNTAX  DateAndTime
        MAX-ACCESS read-only
        STATUS current
        DESCRIPTION
                "A textual string containing the current date-time in the format:
                yyyy-m-d, h:m:s E.g. 2005-10-8, 23:3:12."
        -- 1.3.6.1.4.1.17534.2.2.1.1.1.13
        ::= { optcSysInfoEntry 13 }


optcDeviceUpTime OBJECT-TYPE
        SYNTAX  DisplayString
        MAX-ACCESS read-only
        STATUS current
        DESCRIPTION
                "A textual string containing the device uptime in the format:
                d days hh:mm:ss. E.g. 85 days 13:45:24."
        -- 1.3.6.1.4.1.17534.2.2.1.1.1.12
        ::= { optcSysInfoEntry 12 }


optcDeviceControlTable OBJECT-TYPE
        SYNTAX  SEQUENCE OF OptcDeviceControlEntry
        MAX-ACCESS not-accessible
        STATUS current
        DESCRIPTION
                "A list of devices. This table contains additional objects
                for the optcSysInfo table."
        -- 1.3.6.1.4.1.17534.2.2.1.2
        ::= { optcDevice 2 }


optcDeviceControlEntry OBJECT-TYPE
        SYNTAX  OptcDeviceControlEntry
        MAX-ACCESS not-accessible
        STATUS current
        DESCRIPTION
                "An entry containing additional management information
                applicable to a particular device."
        AUGMENTS {
                optcSysInfoEntry }
        -- 1.3.6.1.4.1.17534.2.2.1.2.1
        ::= { optcDeviceControlTable 1 }


OptcDeviceControlEntry ::= SEQUENCE {

        optcDeviceReset INTEGER }


optcDeviceReset OBJECT-TYPE
        SYNTAX  INTEGER {
                        false(1),
                        true(2) }
        MAX-ACCESS read-write
        STATUS current
        DESCRIPTION
                "A control object which, if set to true, will reset (reboot) the device.
                NOTE: User settings will NOT be lost."
        -- 1.3.6.1.4.1.17534.2.2.1.2.1.1
        ::= { optcDeviceControlEntry 1 }


optcPhysicalEnvironment OBJECT IDENTIFIER 
        -- 1.3.6.1.4.1.17534.2.2.1.3
        ::= { optcDevice 3 }

optcTemperatureTable OBJECT-TYPE
        SYNTAX  SEQUENCE OF OptcTemperatureEntry
        MAX-ACCESS not-accessible
        STATUS current
        DESCRIPTION
                "A list of temperatures. For each device from the
                optcSysInfo table a list of temperatures is maintained."
        -- 1.3.6.1.4.1.17534.2.2.1.3.1
        ::= { optcPhysicalEnvironment 1 }


optcTemperatureEntry OBJECT-TYPE
        SYNTAX  OptcTemperatureEntry
        MAX-ACCESS not-accessible
        STATUS current
        DESCRIPTION
                "An entry containing temperature information applicable
                to a particular device."
        INDEX {
                optcDeviceIndex,
                optcTemperatureIndex }
        -- 1.3.6.1.4.1.17534.2.2.1.3.1.1
        ::= { optcTemperatureTable 1 }


OptcTemperatureEntry ::= SEQUENCE {

        optcTemperatureIndex      Integer32,
        optcActualTemperature     INTEGER,
        optcPeakTemperature       INTEGER,
        optcTemperatureAlarmLevel INTEGER,
        optcTemperatureAlarm      TruthValue }


optcTemperatureIndex OBJECT-TYPE
        SYNTAX  Integer32 (1..2147483647)
        MAX-ACCESS accessible-for-notify
        STATUS current
        DESCRIPTION
                "A unique value, greater than zero, for each temperature."
        -- 1.3.6.1.4.1.17534.2.2.1.3.1.1.1
        ::= { optcTemperatureEntry 1 }


optcTemperatureAlarmLevel OBJECT-TYPE
        SYNTAX  INTEGER (-200..200)
        UNITS
                "Degrees Celsius"
        MAX-ACCESS read-only
        STATUS current
        DESCRIPTION
                "The alarm value for this temperature. A temperatureTooHigh
                trap will be generated if the actual value exceeds this
                alarm value."
        -- 1.3.6.1.4.1.17534.2.2.1.3.1.1.4
        ::= { optcTemperatureEntry 4 }


optcActualTemperature OBJECT-TYPE
        SYNTAX  INTEGER (-200..200)
        UNITS
                "Degrees Celsius"
        MAX-ACCESS read-only
        STATUS current
        DESCRIPTION
                "The current value for this temperature."
        -- 1.3.6.1.4.1.17534.2.2.1.3.1.1.2
        ::= { optcTemperatureEntry 2 }


optcPeakTemperature OBJECT-TYPE
        SYNTAX  INTEGER (-200..200)
        UNITS
                "Degrees Celsius"
        MAX-ACCESS read-only
        STATUS current
        DESCRIPTION
                "The peak value for this temperature."
        -- 1.3.6.1.4.1.17534.2.2.1.3.1.1.3
        ::= { optcTemperatureEntry 3 }


optcTemperatureAlarm OBJECT-TYPE
        SYNTAX  TruthValue
        MAX-ACCESS read-only
        STATUS current
        DESCRIPTION
                "A boolean value which identifies whether a alarm is active
                for this temperature. When an alarm is active, this means
                the current value exceeds the alarm value."
        -- 1.3.6.1.4.1.17534.2.2.1.3.1.1.5
        ::= { optcTemperatureEntry 5 }


optcPowerSupplyTable OBJECT-TYPE
        SYNTAX  SEQUENCE OF OptcPowerSupplyEntry
        MAX-ACCESS not-accessible
        STATUS current
        DESCRIPTION
                "A list of power supplies. For each device from the
                optcSysInfo table a list of power supplies is maintained."
        -- 1.3.6.1.4.1.17534.2.2.1.3.2
        ::= { optcPhysicalEnvironment 2 }


optcPowerSupplyEntry OBJECT-TYPE
        SYNTAX  OptcPowerSupplyEntry
        MAX-ACCESS not-accessible
        STATUS current
        DESCRIPTION
                "An entry containing power supply information applicable
                to a particular device."
        INDEX {
                optcDeviceIndex,
                optcPowerSupplyIndex }
        -- 1.3.6.1.4.1.17534.2.2.1.3.2.1
        ::= { optcPowerSupplyTable 1 }


OptcPowerSupplyEntry ::= SEQUENCE {

        optcPowerSupplyIndex Integer32,
        optcNominalVoltage   Integer32,
        optcActualVoltage    Integer32,
        optcPeakVoltage      Integer32 }


optcPowerSupplyIndex OBJECT-TYPE
        SYNTAX  Integer32 (1..2147483647)
        MAX-ACCESS accessible-for-notify
        STATUS current
        DESCRIPTION
                "A unique value, greater than zero, for each power supply."
        -- 1.3.6.1.4.1.17534.2.2.1.3.2.1.1
        ::= { optcPowerSupplyEntry 1 }


optcNominalVoltage OBJECT-TYPE
        SYNTAX  Integer32
        UNITS
                "mV"
        MAX-ACCESS read-only
        STATUS current
        DESCRIPTION
                "The nominal value for this power supply."
        -- 1.3.6.1.4.1.17534.2.2.1.3.2.1.2
        ::= { optcPowerSupplyEntry 2 }


optcActualVoltage OBJECT-TYPE
        SYNTAX  Integer32
        UNITS
                "mV"
        MAX-ACCESS read-only
        STATUS current
        DESCRIPTION
                "The actual value for this power supply."
        -- 1.3.6.1.4.1.17534.2.2.1.3.2.1.3
        ::= { optcPowerSupplyEntry 3 }


optcPeakVoltage OBJECT-TYPE
        SYNTAX  Integer32
        UNITS
                "mV"
        MAX-ACCESS read-only
        STATUS current
        DESCRIPTION
                "The peak value for this power supply."
        -- 1.3.6.1.4.1.17534.2.2.1.3.2.1.4
        ::= { optcPowerSupplyEntry 4 }


optcPowerSupplyAlarm OBJECT-TYPE
        SYNTAX  TruthValue
        MAX-ACCESS read-only
        STATUS current
        DESCRIPTION
                "A boolean value which identifies whether a alarm is active
                for one of the power supplies. When an alarm is active,
                this means one of the power supplies actual value is not
                within specified nominal range."
        -- 1.3.6.1.4.1.17534.2.2.1.3.3
        ::= { optcPhysicalEnvironment 3 }


optcNetworkSettingsTable OBJECT-TYPE
        SYNTAX  SEQUENCE OF OptcNetworkSettingsEntry
        MAX-ACCESS not-accessible
        STATUS current
        DESCRIPTION
                "A list of network settings. For each device from the
                optcSysInfo table a list of network settings is maintained."
        -- 1.3.6.1.4.1.17534.2.2.1.4
        ::= { optcDevice 4 }


optcNetworkSettingsEntry OBJECT-TYPE
        SYNTAX  OptcNetworkSettingsEntry
        MAX-ACCESS not-accessible
        STATUS current
        DESCRIPTION
                "An entry containing network settings information applicable
                to a particular device. Each network settings entry can be seen
                as a separate network entity."
        INDEX {
                optcDeviceIndex,
                optcNetworkIndex }
        -- 1.3.6.1.4.1.17534.2.2.1.4.1
        ::= { optcNetworkSettingsTable 1 }


OptcNetworkSettingsEntry ::= SEQUENCE {

        optcNetworkIndex   Integer32,
        optcMACAddress     OCTET STRING,
        optcDHCPEnable     TruthValue,
        optcIPAddress      IpAddress,
        optcSubnetMask     IpAddress,
        optcDefaultGateway IpAddress,
        optcEthernetMode   INTEGER }


optcNetworkIndex OBJECT-TYPE
        SYNTAX  Integer32 (1..2147483647)
        MAX-ACCESS accessible-for-notify
        STATUS current
        DESCRIPTION
                "A unique value, greater than zero, for each network entity."
        -- 1.3.6.1.4.1.17534.2.2.1.4.1.1
        ::= { optcNetworkSettingsEntry 1 }


optcMACAddress OBJECT-TYPE
        SYNTAX  OCTET STRING (SIZE (17))
        MAX-ACCESS read-only
        STATUS current
        DESCRIPTION
                "An octet string containing the MAC address of this network
                entity. Format is: xx xx xx xx xx E.g. 00 04 7E 00 80 06"
        -- 1.3.6.1.4.1.17534.2.2.1.4.1.2
        ::= { optcNetworkSettingsEntry 2 }


optcDHCPEnable OBJECT-TYPE
        SYNTAX  TruthValue
        MAX-ACCESS read-only
        STATUS current
        DESCRIPTION
                "A boolean value which identifies whether DHCP is enabled for this
                network entity."
        -- 1.3.6.1.4.1.17534.2.2.1.4.1.3
        ::= { optcNetworkSettingsEntry 3 }


optcIPAddress OBJECT-TYPE
        SYNTAX  IpAddress
        MAX-ACCESS read-only
        STATUS current
        DESCRIPTION
                "The IP-address of this network entity."
        -- 1.3.6.1.4.1.17534.2.2.1.4.1.4
        ::= { optcNetworkSettingsEntry 4 }


optcSubnetMask OBJECT-TYPE
        SYNTAX  IpAddress
        MAX-ACCESS read-only
        STATUS current
        DESCRIPTION
                "The subnet mask of this network entity."
        -- 1.3.6.1.4.1.17534.2.2.1.4.1.5
        ::= { optcNetworkSettingsEntry 5 }


optcDefaultGateway OBJECT-TYPE
        SYNTAX  IpAddress
        MAX-ACCESS read-only
        STATUS current
        DESCRIPTION
                "The default gateway of this network entity."
        -- 1.3.6.1.4.1.17534.2.2.1.4.1.6
        ::= { optcNetworkSettingsEntry 6 }


optcEthernetMode OBJECT-TYPE
        SYNTAX  INTEGER {
                        autonegotiation(1),
                        duplex100Mbit(2),
                        simplex100Mbit(3),
                        duplex10Mbit(4),
                        simplex10Mbit(5) }
        MAX-ACCESS read-only
        STATUS current
        DESCRIPTION
                "The ethernet-mode currently active for this network entity."
        -- 1.3.6.1.4.1.17534.2.2.1.4.1.7
        ::= { optcNetworkSettingsEntry 7 }


optcTotalRxBitrate OBJECT-TYPE
        SYNTAX  Unsigned32
        UNITS
                "bit/s"
        MAX-ACCESS read-only
        STATUS current
        DESCRIPTION
                "The current receive bit rate."
        -- 1.3.6.1.4.1.17534.2.2.1.5.1.2
        ::= { optcNetworkStatisticsEntry 2 }


optcTotalTxBitrate OBJECT-TYPE
        SYNTAX  Unsigned32
        UNITS
                "bit/s"
        MAX-ACCESS read-only
        STATUS current
        DESCRIPTION
                "The current transmit bit rate."
        -- 1.3.6.1.4.1.17534.2.2.1.5.1.1
        ::= { optcNetworkStatisticsEntry 1 }


optcNetworkStatisticsTable OBJECT-TYPE
        SYNTAX  SEQUENCE OF OptcNetworkStatisticsEntry
        MAX-ACCESS not-accessible
        STATUS current
        DESCRIPTION
                "A list of network statistics. This table contains additional objects
                for the optcNetworkSettings table."
        -- 1.3.6.1.4.1.17534.2.2.1.5
        ::= { optcDevice 5 }


optcNetworkStatisticsEntry OBJECT-TYPE
        SYNTAX  OptcNetworkStatisticsEntry
        MAX-ACCESS not-accessible
        STATUS current
        DESCRIPTION
                "An entry containing additional management information
                applicable to a particular network entity."
        AUGMENTS {
                optcNetworkSettingsEntry }
        -- 1.3.6.1.4.1.17534.2.2.1.5.1
        ::= { optcNetworkStatisticsTable 1 }


OptcNetworkStatisticsEntry ::= SEQUENCE {

        optcTotalTxBitrate Unsigned32,
        optcTotalRxBitrate Unsigned32 }


optcDeviceNotifications OBJECT-IDENTITY
        STATUS current
        DESCRIPTION
                "The device notifications (traps)."
        -- 1.3.6.1.4.1.17534.2.2.1.6
        ::= { optcDevice 6 }


optcDeviceTemperatureTooHigh NOTIFICATION-TYPE
        OBJECTS {
                optcDeviceIndex,
                optcDeviceStatus,
                optcTemperatureIndex,
                optcActualTemperature,
                optcPeakTemperature,
                optcTemperatureAlarmLevel}
        STATUS current
        DESCRIPTION
                "A optcDeviceTemperatureTooHigh trap is sent by the device if
                a temperature (identified by optcTemperatureIndex), from the
                optcTemperatureTable, actual value exceeds its corresponding
                optcTemperatureAlarmLevel value."
        -- 1.3.6.1.4.1.17534.2.2.1.6.1
        ::= { optcDeviceNotifications 1 }


optcDeviceTemperatureTooLow NOTIFICATION-TYPE
        OBJECTS {
                optcDeviceIndex,
                optcDeviceStatus,
                optcTemperatureIndex,
                optcActualTemperature,
                optcPeakTemperature,
                optcTemperatureAlarmLevel}
        STATUS current
        DESCRIPTION
                "Not implemented yet."
        -- 1.3.6.1.4.1.17534.2.2.1.6.2
        ::= { optcDeviceNotifications 2 }


optcDeviceTemperatureOk NOTIFICATION-TYPE
        OBJECTS {
                optcDeviceIndex,
                optcDeviceStatus,
                optcTemperatureIndex,
                optcActualTemperature,
                optcPeakTemperature,
                optcTemperatureAlarmLevel}
        STATUS current
        DESCRIPTION
                "A optcDeviceTemperatureOk trap is sent by the device if
                a temperature (identified by optcTemperatureIndex), from
                the optcTemperatureTable, actual value goes below its
                corresponding optcTemperatureAlarmLevel value.
                I.e. the alarm, for that particular temperature, will no
                longer be active."
        -- 1.3.6.1.4.1.17534.2.2.1.6.3
        ::= { optcDeviceNotifications 3 }


optcDevicePowerFailure NOTIFICATION-TYPE
        OBJECTS {
                optcDeviceIndex,
                optcDeviceStatus}
        STATUS current
        DESCRIPTION
                "A optcDevicePowerFailure trap will be sent by the device if any
                of the power supplies, from the optcPowerSupplyTable, actual
                value goes from a value that is within the specified nominal range
                to a value that is not within the specified nominal range."
        -- 1.3.6.1.4.1.17534.2.2.1.6.4
        ::= { optcDeviceNotifications 4 }


optcDevicePowerOk NOTIFICATION-TYPE
        OBJECTS {
                optcDeviceIndex,
                optcDeviceStatus}
        STATUS current
        DESCRIPTION
                "A optcDevicePowerOk trap will be sent by the device if any
                of the power supplies, from the optcPowerSupplyTable, actual
                value goes from a value outside the specified nominal range to
                a value within the specified nominal range."
        -- 1.3.6.1.4.1.17534.2.2.1.6.6
        ::= { optcDeviceNotifications 6 }

optcSysInfoGroup OBJECT-GROUP
        OBJECTS {
                optcArticleCode,
                optcModuleID,
                optcProductName,
                optcProductDescription,
                optcSerialNumber,
                optcProductVersion,
                optcUserLabel1,
                optcUserLabel2,
                optcSoftwareArticleCode,
                optcDeviceStatus,
                optcDateTime,
                optcDeviceIndex,
                optcDeviceUpTime }
        STATUS current
        DESCRIPTION
                "General system information for this device."
        -- 1.3.6.1.4.1.17534.2.2.1.7
        ::= { optcDevice 7 }

optcDeviceControlGroup OBJECT-GROUP
        OBJECTS {
                optcDeviceReset }
        STATUS current
        DESCRIPTION
                "Device control objects for this device."
        -- 1.3.6.1.4.1.17534.2.2.1.8
        ::= { optcDevice 8 }

optcPhysicalEnvironmentGroup OBJECT-GROUP
        OBJECTS {
                optcPowerSupplyAlarm }
        STATUS current
        DESCRIPTION
                "Physical Environment information for this device."
        -- 1.3.6.1.4.1.17534.2.2.1.9
        ::= { optcDevice 9 }

optcTemperatureGroup OBJECT-GROUP
        OBJECTS {
                optcTemperatureAlarmLevel,
                optcActualTemperature,
                optcPeakTemperature,
                optcTemperatureAlarm,
                optcTemperatureIndex }
        STATUS current
        DESCRIPTION
                "Temperature information for this device."
        -- 1.3.6.1.4.1.17534.2.2.1.10
        ::= { optcDevice 10 }

optcPowerSupplyGroup OBJECT-GROUP
        OBJECTS {
                optcNominalVoltage,
                optcActualVoltage,
                optcPeakVoltage,
                optcPowerSupplyIndex }
        STATUS current
        DESCRIPTION
                "Power supply information for this device."
        -- 1.3.6.1.4.1.17534.2.2.1.11
        ::= { optcDevice 11 }

optcNetworkSettingsGroup OBJECT-GROUP
        OBJECTS {
                optcMACAddress,
                optcDHCPEnable,
                optcIPAddress,
                optcSubnetMask,
                optcDefaultGateway,
                optcEthernetMode,
                optcNetworkIndex }
        STATUS current
        DESCRIPTION
                "Network Settings information for this device."
        -- 1.3.6.1.4.1.17534.2.2.1.12
        ::= { optcDevice 12 }

optcNetworkStatisticsGroup OBJECT-GROUP
        OBJECTS {
                optcTotalTxBitrate,
                optcTotalRxBitrate }
        STATUS current
        DESCRIPTION
                "Network Statistics information for this device."
        -- 1.3.6.1.4.1.17534.2.2.1.13
        ::= { optcDevice 13 }

optcDeviceNotificationsGroup NOTIFICATION-GROUP
        NOTIFICATIONS {
                optcDeviceTemperatureTooHigh,
                optcDeviceTemperatureOk,
                optcDevicePowerFailure,
                optcDevicePowerOk,
                optcDeviceTemperatureTooLow }
        STATUS current
        DESCRIPTION
                "Group of objects describing notifications (traps)."
        -- 1.3.6.1.4.1.17534.2.2.1.14
        ::= { optcDevice 14 }

END
