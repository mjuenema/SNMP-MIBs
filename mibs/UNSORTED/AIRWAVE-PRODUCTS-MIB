AirWave-Products-MIB DEFINITIONS ::= BEGIN

IMPORTS
	MODULE-IDENTITY, 
	OBJECT-IDENTITY
		FROM SNMPv2-SMI
	airwaveProducts,
	airwaveModules
		FROM AirWave-SMI-MIB;

airwaveProductsMIB	MODULE-IDENTITY
	LAST-UPDATED "201112190000Z"
	ORGANIZATION "AirWave Wireless"
	CONTACT-INFO
		"        Paul Gray
		
		 Postal: Aruba Networks, Inc.
		         1344 Crossman Ave
		         Sunnyvale, CA 94402
		         
		    Tel: +1 408 227 4500
		    
		  Email: paul@arubanetworks.com
		    Web: http://www.arubanetworks.com/"
	DESCRIPTION
		"AirWave product line."
        REVISION "201112190000Z" -- December 2011
        DESCRIPTION "Made compliant with level 3 of smilint"
        REVISION "200304170001Z" -- April 2003
        DESCRIPTION "Initial creation."

	::= { airwaveModules 1 }

airwaveAMP OBJECT-IDENTITY
	STATUS current
	DESCRIPTION
		"AirWave Management Platform."
	::= { airwaveProducts 1 }

airwaveOemAMP OBJECT-IDENTITY
	STATUS current
	DESCRIPTION
		"OEM version of AirWave Management Platform."
	::= { airwaveProducts 2 }

airwaveAML OBJECT-IDENTITY
	STATUS current
	DESCRIPTION
		"AirWave Management Link NMS plugin."
	::= { airwaveProducts 3 }

airwaveSnmpLibrary OBJECT-IDENTITY
	STATUS current
	DESCRIPTION
		"AirWave's SNMP library."
	::= { airwaveProducts 4 }

END
