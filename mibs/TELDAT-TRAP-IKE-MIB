-- file automatically created


TELDAT-TRAP-IKE-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ikeTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IKE event subsystem."
    REVISION "201401200930Z"
    DESCRIPTION "Initial implementation"
        ::= { telEventTraps 176 }


ikeEventsGroup	OBJECT IDENTIFIER	::= { ikeTrapsMIB 1 }

ikeNotifications	OBJECT IDENTIFIER	::= { ikeTrapsMIB 2 }
ikeNotificationsPrefix	OBJECT IDENTIFIER	::= { ikeNotifications 0 }

ikeEventObjects1 OBJECT-IDENTITY
    STATUS current
    DESCRIPTION
        "Event IKE.1
        Matching template."
    ::= { ikeEventsGroup 1 }

ike1_remote_addr OBJECT-TYPE
    SYNTAX IpAddress
    MAX-ACCESS accessible-for-notify
    STATUS current
    DESCRIPTION
        "Parameter 'remote_addr' in event IKE.1"
    ::= { ikeEventObjects1 1 }

ike1_template_number OBJECT-TYPE
    SYNTAX Integer32
    MAX-ACCESS accessible-for-notify
    STATUS current
    DESCRIPTION
        "Parameter 'template_number' in event IKE.1"
    ::= { ikeEventObjects1 2 }

ikeEventObjects2 OBJECT-IDENTITY
    STATUS current
    DESCRIPTION
        "Event IKE.2
        Matching SA for negotiation."
    ::= { ikeEventsGroup 2 }

ike2_remote_addr OBJECT-TYPE
    SYNTAX IpAddress
    MAX-ACCESS accessible-for-notify
    STATUS current
    DESCRIPTION
        "Parameter 'remote_addr' in event IKE.2"
    ::= { ikeEventObjects2 1 }

ike2_connection OBJECT-TYPE
    SYNTAX Integer32
    MAX-ACCESS accessible-for-notify
    STATUS current
    DESCRIPTION
        "Parameter 'connection' in event IKE.2"
    ::= { ikeEventObjects2 2 }

ikeEventObjects3 OBJECT-IDENTITY
    STATUS current
    DESCRIPTION
        "Event IKE.3
        There was an error decrypting the message."
    ::= { ikeEventsGroup 3 }

ike3_remote_addr OBJECT-TYPE
    SYNTAX IpAddress
    MAX-ACCESS accessible-for-notify
    STATUS current
    DESCRIPTION
        "Parameter 'remote_addr' in event IKE.3"
    ::= { ikeEventObjects3 1 }

ikeEventObjects4 OBJECT-IDENTITY
    STATUS current
    DESCRIPTION
        "Event IKE.4
        Received message is a retransmission."
    ::= { ikeEventsGroup 4 }

ike4_remote_addr OBJECT-TYPE
    SYNTAX IpAddress
    MAX-ACCESS accessible-for-notify
    STATUS current
    DESCRIPTION
        "Parameter 'remote_addr' in event IKE.4"
    ::= { ikeEventObjects4 1 }

ikeEventObjects5 OBJECT-IDENTITY
    STATUS current
    DESCRIPTION
        "Event IKE.5
        Could not initiate IKE negotiation: unknown destination."
    ::= { ikeEventsGroup 5 }

ike5_remote_addr OBJECT-TYPE
    SYNTAX IpAddress
    MAX-ACCESS accessible-for-notify
    STATUS current
    DESCRIPTION
        "Parameter 'remote_addr' in event IKE.5"
    ::= { ikeEventObjects5 1 }

ikeEventObjects6 OBJECT-IDENTITY
    STATUS current
    DESCRIPTION
        "Event IKE.6
        Creating ISAKMP negotiation SA."
    ::= { ikeEventsGroup 6 }

ike6_remote_addr OBJECT-TYPE
    SYNTAX IpAddress
    MAX-ACCESS accessible-for-notify
    STATUS current
    DESCRIPTION
        "Parameter 'remote_addr' in event IKE.6"
    ::= { ikeEventObjects6 1 }

ike6_connection OBJECT-TYPE
    SYNTAX Integer32
    MAX-ACCESS accessible-for-notify
    STATUS current
    DESCRIPTION
        "Parameter 'connection' in event IKE.6"
    ::= { ikeEventObjects6 2 }

ikeEventObjects7 OBJECT-IDENTITY
    STATUS current
    DESCRIPTION
        "Event IKE.7
        Deleting ISAKMP negotiation SA."
    ::= { ikeEventsGroup 7 }

ike7_remote_addr OBJECT-TYPE
    SYNTAX IpAddress
    MAX-ACCESS accessible-for-notify
    STATUS current
    DESCRIPTION
        "Parameter 'remote_addr' in event IKE.7"
    ::= { ikeEventObjects7 1 }

ikeEventObjects8 OBJECT-IDENTITY
    STATUS current
    DESCRIPTION
        "Event IKE.8
        Creating ISAKMP SA."
    ::= { ikeEventsGroup 8 }

ike8_remote_addr OBJECT-TYPE
    SYNTAX IpAddress
    MAX-ACCESS accessible-for-notify
    STATUS current
    DESCRIPTION
        "Parameter 'remote_addr' in event IKE.8"
    ::= { ikeEventObjects8 1 }

ikeEventObjects9 OBJECT-IDENTITY
    STATUS current
    DESCRIPTION
        "Event IKE.9
        Creating ISAKMP SA id."
    ::= { ikeEventsGroup 9 }

ike9_remote_addr OBJECT-TYPE
    SYNTAX IpAddress
    MAX-ACCESS accessible-for-notify
    STATUS current
    DESCRIPTION
        "Parameter 'remote_addr' in event IKE.9"
    ::= { ikeEventObjects9 1 }

ike9_message_id OBJECT-TYPE
    SYNTAX Integer32
    MAX-ACCESS accessible-for-notify
    STATUS current
    DESCRIPTION
        "Parameter 'message_id' in event IKE.9"
    ::= { ikeEventObjects9 2 }

ikeEventObjects10 OBJECT-IDENTITY
    STATUS current
    DESCRIPTION
        "Event IKE.10
        Unable to create ISAKMP SA."
    ::= { ikeEventsGroup 10 }

ike10_remote_addr OBJECT-TYPE
    SYNTAX IpAddress
    MAX-ACCESS accessible-for-notify
    STATUS current
    DESCRIPTION
        "Parameter 'remote_addr' in event IKE.10"
    ::= { ikeEventObjects10 1 }

ike10_ini_cookie_lo OBJECT-TYPE
    SYNTAX Integer32
    MAX-ACCESS accessible-for-notify
    STATUS current
    DESCRIPTION
        "Parameter 'ini_cookie_lo' in event IKE.10"
    ::= { ikeEventObjects10 2 }

ike10_ini_cookie_hi OBJECT-TYPE
    SYNTAX Integer32
    MAX-ACCESS accessible-for-notify
    STATUS current
    DESCRIPTION
        "Parameter 'ini_cookie_hi' in event IKE.10"
    ::= { ikeEventObjects10 3 }

ike10_res_cookie_lo OBJECT-TYPE
    SYNTAX Integer32
    MAX-ACCESS accessible-for-notify
    STATUS current
    DESCRIPTION
        "Parameter 'res_cookie_lo' in event IKE.10"
    ::= { ikeEventObjects10 4 }

ike10_res_cookie_hi OBJECT-TYPE
    SYNTAX Integer32
    MAX-ACCESS accessible-for-notify
    STATUS current
    DESCRIPTION
        "Parameter 'res_cookie_hi' in event IKE.10"
    ::= { ikeEventObjects10 5 }

ikeEventObjects11 OBJECT-IDENTITY
    STATUS current
    DESCRIPTION
        "Event IKE.11
        Creating SA for incoming packets."
    ::= { ikeEventsGroup 11 }

ike11_remote_addr OBJECT-TYPE
    SYNTAX IpAddress
    MAX-ACCESS accessible-for-notify
    STATUS current
    DESCRIPTION
        "Parameter 'remote_addr' in event IKE.11"
    ::= { ikeEventObjects11 1 }

ike11_spi OBJECT-TYPE
    SYNTAX Integer32
    MAX-ACCESS accessible-for-notify
    STATUS current
    DESCRIPTION
        "Parameter 'spi' in event IKE.11"
    ::= { ikeEventObjects11 2 }

ikeEventObjects12 OBJECT-IDENTITY
    STATUS current
    DESCRIPTION
        "Event IKE.12
        Creating SA for outgoing packets."
    ::= { ikeEventsGroup 12 }

ike12_remote_addr OBJECT-TYPE
    SYNTAX IpAddress
    MAX-ACCESS accessible-for-notify
    STATUS current
    DESCRIPTION
        "Parameter 'remote_addr' in event IKE.12"
    ::= { ikeEventObjects12 1 }

ike12_spi OBJECT-TYPE
    SYNTAX Integer32
    MAX-ACCESS accessible-for-notify
    STATUS current
    DESCRIPTION
        "Parameter 'spi' in event IKE.12"
    ::= { ikeEventObjects12 2 }

ikeEventObjects13 OBJECT-IDENTITY
    STATUS current
    DESCRIPTION
        "Event IKE.13
        Deleting access list entry."
    ::= { ikeEventsGroup 13 }

ike13_remote_addr OBJECT-TYPE
    SYNTAX IpAddress
    MAX-ACCESS accessible-for-notify
    STATUS current
    DESCRIPTION
        "Parameter 'remote_addr' in event IKE.13"
    ::= { ikeEventObjects13 1 }

ikeEventObjects14 OBJECT-IDENTITY
    STATUS current
    DESCRIPTION
        "Event IKE.14
        Deleting SA for incoming packets."
    ::= { ikeEventsGroup 14 }

ike14_remote_addr OBJECT-TYPE
    SYNTAX IpAddress
    MAX-ACCESS accessible-for-notify
    STATUS current
    DESCRIPTION
        "Parameter 'remote_addr' in event IKE.14"
    ::= { ikeEventObjects14 1 }

ike14_spi OBJECT-TYPE
    SYNTAX Integer32
    MAX-ACCESS accessible-for-notify
    STATUS current
    DESCRIPTION
        "Parameter 'spi' in event IKE.14"
    ::= { ikeEventObjects14 2 }

ikeEventObjects15 OBJECT-IDENTITY
    STATUS current
    DESCRIPTION
        "Event IKE.15
        Deleting SA for outgoing packets."
    ::= { ikeEventsGroup 15 }

ike15_remote_addr OBJECT-TYPE
    SYNTAX IpAddress
    MAX-ACCESS accessible-for-notify
    STATUS current
    DESCRIPTION
        "Parameter 'remote_addr' in event IKE.15"
    ::= { ikeEventObjects15 1 }

ike15_spi OBJECT-TYPE
    SYNTAX Integer32
    MAX-ACCESS accessible-for-notify
    STATUS current
    DESCRIPTION
        "Parameter 'spi' in event IKE.15"
    ::= { ikeEventObjects15 2 }

ikeEventObjects16 OBJECT-IDENTITY
    STATUS current
    DESCRIPTION
        "Event IKE.16
        Keepalive expired: deleting SA."
    ::= { ikeEventsGroup 16 }

ike16_remote_addr OBJECT-TYPE
    SYNTAX IpAddress
    MAX-ACCESS accessible-for-notify
    STATUS current
    DESCRIPTION
        "Parameter 'remote_addr' in event IKE.16"
    ::= { ikeEventObjects16 1 }

ike16_spi OBJECT-TYPE
    SYNTAX Integer32
    MAX-ACCESS accessible-for-notify
    STATUS current
    DESCRIPTION
        "Parameter 'spi' in event IKE.16"
    ::= { ikeEventObjects16 2 }

ikeEventObjects17 OBJECT-IDENTITY
    STATUS current
    DESCRIPTION
        "Event IKE.17
        Purgetime expired for negotiation SA."
    ::= { ikeEventsGroup 17 }

ike17_remote_addr OBJECT-TYPE
    SYNTAX IpAddress
    MAX-ACCESS accessible-for-notify
    STATUS current
    DESCRIPTION
        "Parameter 'remote_addr' in event IKE.17"
    ::= { ikeEventObjects17 1 }

ikeEventObjects18 OBJECT-IDENTITY
    STATUS current
    DESCRIPTION
        "Event IKE.18
        Purgetime expired for phase II negotiation SA."
    ::= { ikeEventsGroup 18 }

ike18_remote_addr OBJECT-TYPE
    SYNTAX IpAddress
    MAX-ACCESS accessible-for-notify
    STATUS current
    DESCRIPTION
        "Parameter 'remote_addr' in event IKE.18"
    ::= { ikeEventObjects18 1 }

ike18_id OBJECT-TYPE
    SYNTAX Integer32
    MAX-ACCESS accessible-for-notify
    STATUS current
    DESCRIPTION
        "Parameter 'id' in event IKE.18"
    ::= { ikeEventObjects18 2 }

ike18_source OBJECT-TYPE
    SYNTAX IpAddress
    MAX-ACCESS accessible-for-notify
    STATUS current
    DESCRIPTION
        "Parameter 'source' in event IKE.18"
    ::= { ikeEventObjects18 3 }

ike18_destination OBJECT-TYPE
    SYNTAX IpAddress
    MAX-ACCESS accessible-for-notify
    STATUS current
    DESCRIPTION
        "Parameter 'destination' in event IKE.18"
    ::= { ikeEventObjects18 4 }

ikeEventObjects19 OBJECT-IDENTITY
    STATUS current
    DESCRIPTION
        "Event IKE.19
        ISAKMP SA commencing phase I negotiation."
    ::= { ikeEventsGroup 19 }

ike19_remote_addr OBJECT-TYPE
    SYNTAX IpAddress
    MAX-ACCESS accessible-for-notify
    STATUS current
    DESCRIPTION
        "Parameter 'remote_addr' in event IKE.19"
    ::= { ikeEventObjects19 1 }

ikeEventObjects20 OBJECT-IDENTITY
    STATUS current
    DESCRIPTION
        "Event IKE.20
        Negotiation on phase I: phase II not allowed."
    ::= { ikeEventsGroup 20 }

ike20_remote_addr OBJECT-TYPE
    SYNTAX IpAddress
    MAX-ACCESS accessible-for-notify
    STATUS current
    DESCRIPTION
        "Parameter 'remote_addr' in event IKE.20"
    ::= { ikeEventObjects20 1 }

ikeEventObjects21 OBJECT-IDENTITY
    STATUS current
    DESCRIPTION
        "Event IKE.21
        Either ISAKMP SA or phase II negotiation information is invalid."
    ::= { ikeEventsGroup 21 }

ike21_remote_addr OBJECT-TYPE
    SYNTAX IpAddress
    MAX-ACCESS accessible-for-notify
    STATUS current
    DESCRIPTION
        "Parameter 'remote_addr' in event IKE.21"
    ::= { ikeEventObjects21 1 }

ikeEventObjects22 OBJECT-IDENTITY
    STATUS current
    DESCRIPTION
        "Event IKE.22
        Renegotiation timer for outgoing packets SA initiated."
    ::= { ikeEventsGroup 22 }

ike22_remote_addr OBJECT-TYPE
    SYNTAX IpAddress
    MAX-ACCESS accessible-for-notify
    STATUS current
    DESCRIPTION
        "Parameter 'remote_addr' in event IKE.22"
    ::= { ikeEventObjects22 1 }

ike22_spi OBJECT-TYPE
    SYNTAX Integer32
    MAX-ACCESS accessible-for-notify
    STATUS current
    DESCRIPTION
        "Parameter 'spi' in event IKE.22"
    ::= { ikeEventObjects22 2 }

ikeEventObjects23 OBJECT-IDENTITY
    STATUS current
    DESCRIPTION
        "Event IKE.23
        Renegotiation timer for outgoing packets SA expired."
    ::= { ikeEventsGroup 23 }

ike23_remote_addr OBJECT-TYPE
    SYNTAX IpAddress
    MAX-ACCESS accessible-for-notify
    STATUS current
    DESCRIPTION
        "Parameter 'remote_addr' in event IKE.23"
    ::= { ikeEventObjects23 1 }

ike23_spi OBJECT-TYPE
    SYNTAX Integer32
    MAX-ACCESS accessible-for-notify
    STATUS current
    DESCRIPTION
        "Parameter 'spi' in event IKE.23"
    ::= { ikeEventObjects23 2 }

ikeEventObjects24 OBJECT-IDENTITY
    STATUS current
    DESCRIPTION
        "Event IKE.24
        Attempt to renegotiate delayed."
    ::= { ikeEventsGroup 24 }

ike24_remote_addr OBJECT-TYPE
    SYNTAX IpAddress
    MAX-ACCESS accessible-for-notify
    STATUS current
    DESCRIPTION
        "Parameter 'remote_addr' in event IKE.24"
    ::= { ikeEventObjects24 1 }

ikeEventObjects25 OBJECT-IDENTITY
    STATUS current
    DESCRIPTION
        "Event IKE.25
        Matching CRL (Certificate Revocation List)."
    ::= { ikeEventsGroup 25 }

ike25_remote_addr OBJECT-TYPE
    SYNTAX IpAddress
    MAX-ACCESS accessible-for-notify
    STATUS current
    DESCRIPTION
        "Parameter 'remote_addr' in event IKE.25"
    ::= { ikeEventObjects25 1 }

ikeEventObjects26 OBJECT-IDENTITY
    STATUS current
    DESCRIPTION
        "Event IKE.26
        Invalid ID information."
    ::= { ikeEventsGroup 26 }

ike26_remote_addr OBJECT-TYPE
    SYNTAX IpAddress
    MAX-ACCESS accessible-for-notify
    STATUS current
    DESCRIPTION
        "Parameter 'remote_addr' in event IKE.26"
    ::= { ikeEventObjects26 1 }

ikeEventObjects27 OBJECT-IDENTITY
    STATUS current
    DESCRIPTION
        "Event IKE.27
        No address information found in SA."
    ::= { ikeEventsGroup 27 }

ike27_remote_addr OBJECT-TYPE
    SYNTAX IpAddress
    MAX-ACCESS accessible-for-notify
    STATUS current
    DESCRIPTION
        "Parameter 'remote_addr' in event IKE.27"
    ::= { ikeEventObjects27 1 }

ikeEventObjects28 OBJECT-IDENTITY
    STATUS current
    DESCRIPTION
        "Event IKE.28
        ISAKMP SA commencing phase II negotiation."
    ::= { ikeEventsGroup 28 }

ike28_remote_addr OBJECT-TYPE
    SYNTAX IpAddress
    MAX-ACCESS accessible-for-notify
    STATUS current
    DESCRIPTION
        "Parameter 'remote_addr' in event IKE.28"
    ::= { ikeEventObjects28 1 }

ike28_last_id OBJECT-TYPE
    SYNTAX Integer32
    MAX-ACCESS accessible-for-notify
    STATUS current
    DESCRIPTION
        "Parameter 'last_id' in event IKE.28"
    ::= { ikeEventObjects28 2 }

ikeEventObjects29 OBJECT-IDENTITY
    STATUS current
    DESCRIPTION
        "Event IKE.29
        Negotiation from banned host stopped."
    ::= { ikeEventsGroup 29 }

ike29_remote_addr OBJECT-TYPE
    SYNTAX IpAddress
    MAX-ACCESS accessible-for-notify
    STATUS current
    DESCRIPTION
        "Parameter 'remote_addr' in event IKE.29"
    ::= { ikeEventObjects29 1 }

ikeEventObjects30 OBJECT-IDENTITY
    STATUS current
    DESCRIPTION
        "Event IKE.30
        DPD (Dead Peer Detection) system found a lost connection: deleting SAs."
    ::= { ikeEventsGroup 30 }

ike30_remote_addr OBJECT-TYPE
    SYNTAX IpAddress
    MAX-ACCESS accessible-for-notify
    STATUS current
    DESCRIPTION
        "Parameter 'remote_addr' in event IKE.30"
    ::= { ikeEventObjects30 1 }

ikeEventObjects31 OBJECT-IDENTITY
    STATUS current
    DESCRIPTION
        "Event IKE.31
        Maximum number of simultaneous tunnels reached."
    ::= { ikeEventsGroup 31 }

ike31_remote_addr OBJECT-TYPE
    SYNTAX IpAddress
    MAX-ACCESS accessible-for-notify
    STATUS current
    DESCRIPTION
        "Parameter 'remote_addr' in event IKE.31"
    ::= { ikeEventObjects31 1 }

ikeEventObjects32 OBJECT-IDENTITY
    STATUS current
    DESCRIPTION
        "Event IKE.32
        Renegotiation using DNAT started."
    ::= { ikeEventsGroup 32 }

ike32_remote_addr OBJECT-TYPE
    SYNTAX IpAddress
    MAX-ACCESS accessible-for-notify
    STATUS current
    DESCRIPTION
        "Parameter 'remote_addr' in event IKE.32"
    ::= { ikeEventObjects32 1 }

ikeEventObjects33 OBJECT-IDENTITY
    STATUS current
    DESCRIPTION
        "Event IKE.33
        SA lifetime counter changed."
    ::= { ikeEventsGroup 33 }

ike33_remote_addr OBJECT-TYPE
    SYNTAX IpAddress
    MAX-ACCESS accessible-for-notify
    STATUS current
    DESCRIPTION
        "Parameter 'remote_addr' in event IKE.33"
    ::= { ikeEventObjects33 1 }

ikeEventObjects34 OBJECT-IDENTITY
    STATUS current
    DESCRIPTION
        "Event IKE.34
        Searching Backup peer."
    ::= { ikeEventsGroup 34 }

ike34_remote_addr OBJECT-TYPE
    SYNTAX IpAddress
    MAX-ACCESS accessible-for-notify
    STATUS current
    DESCRIPTION
        "Parameter 'remote_addr' in event IKE.34"
    ::= { ikeEventObjects34 1 }

ikeEventObjects35 OBJECT-IDENTITY
    STATUS current
    DESCRIPTION
        "Event IKE.35
        Renegotiation Timer for negotiation SA expired."
    ::= { ikeEventsGroup 35 }

ike35_remote_addr OBJECT-TYPE
    SYNTAX IpAddress
    MAX-ACCESS accessible-for-notify
    STATUS current
    DESCRIPTION
        "Parameter 'remote_addr' in event IKE.35"
    ::= { ikeEventObjects35 1 }

ike35_connection OBJECT-TYPE
    SYNTAX Integer32
    MAX-ACCESS accessible-for-notify
    STATUS current
    DESCRIPTION
        "Parameter 'connection' in event IKE.35"
    ::= { ikeEventObjects35 2 }

ikeEventObjects36 OBJECT-IDENTITY
    STATUS current
    DESCRIPTION
        "Event IKE.36
        Local side starting negotiation."
    ::= { ikeEventsGroup 36 }

ike36_remote_addr OBJECT-TYPE
    SYNTAX IpAddress
    MAX-ACCESS accessible-for-notify
    STATUS current
    DESCRIPTION
        "Parameter 'remote_addr' in event IKE.36"
    ::= { ikeEventObjects36 1 }

ikeEventObjects37 OBJECT-IDENTITY
    STATUS current
    DESCRIPTION
        "Event IKE.37
        Remote side starting negotiation."
    ::= { ikeEventsGroup 37 }

ike37_remote_addr OBJECT-TYPE
    SYNTAX IpAddress
    MAX-ACCESS accessible-for-notify
    STATUS current
    DESCRIPTION
        "Parameter 'remote_addr' in event IKE.37"
    ::= { ikeEventObjects37 1 }

ikeEventObjects38 OBJECT-IDENTITY
    STATUS current
    DESCRIPTION
        "Event IKE.38
        Local side starting Backup negotiation."
    ::= { ikeEventsGroup 38 }

ike38_remote_addr OBJECT-TYPE
    SYNTAX IpAddress
    MAX-ACCESS accessible-for-notify
    STATUS current
    DESCRIPTION
        "Parameter 'remote_addr' in event IKE.38"
    ::= { ikeEventObjects38 1 }

ikeEventObjects39 OBJECT-IDENTITY
    STATUS current
    DESCRIPTION
        "Event IKE.39
        Remote side starting Backup negotiation."
    ::= { ikeEventsGroup 39 }

ike39_remote_addr OBJECT-TYPE
    SYNTAX IpAddress
    MAX-ACCESS accessible-for-notify
    STATUS current
    DESCRIPTION
        "Parameter 'remote_addr' in event IKE.39"
    ::= { ikeEventObjects39 1 }

ikeEventObjects40 OBJECT-IDENTITY
    STATUS current
    DESCRIPTION
        "Event IKE.40
        Tunnel correctly established."
    ::= { ikeEventsGroup 40 }

ike40_remote_addr OBJECT-TYPE
    SYNTAX IpAddress
    MAX-ACCESS accessible-for-notify
    STATUS current
    DESCRIPTION
        "Parameter 'remote_addr' in event IKE.40"
    ::= { ikeEventObjects40 1 }

ike40_spi OBJECT-TYPE
    SYNTAX Integer32
    MAX-ACCESS accessible-for-notify
    STATUS current
    DESCRIPTION
        "Parameter 'spi' in event IKE.40"
    ::= { ikeEventObjects40 2 }

ikeEventObjects41 OBJECT-IDENTITY
    STATUS current
    DESCRIPTION
        "Event IKE.41
        Tunnel disconnected."
    ::= { ikeEventsGroup 41 }

ike41_remote_addr OBJECT-TYPE
    SYNTAX IpAddress
    MAX-ACCESS accessible-for-notify
    STATUS current
    DESCRIPTION
        "Parameter 'remote_addr' in event IKE.41"
    ::= { ikeEventObjects41 1 }

ike41_spi OBJECT-TYPE
    SYNTAX Integer32
    MAX-ACCESS accessible-for-notify
    STATUS current
    DESCRIPTION
        "Parameter 'spi' in event IKE.41"
    ::= { ikeEventObjects41 2 }

ikeEventObjects42 OBJECT-IDENTITY
    STATUS current
    DESCRIPTION
        "Event IKE.42
        Unexpected notification from remote side received."
    ::= { ikeEventsGroup 42 }

ike42_remote_addr OBJECT-TYPE
    SYNTAX IpAddress
    MAX-ACCESS accessible-for-notify
    STATUS current
    DESCRIPTION
        "Parameter 'remote_addr' in event IKE.42"
    ::= { ikeEventObjects42 1 }

ike42_message OBJECT-TYPE
    SYNTAX DisplayString
    MAX-ACCESS accessible-for-notify
    STATUS current
    DESCRIPTION
        "Parameter 'message' in event IKE.42"
    ::= { ikeEventObjects42 2 }

ikeEventObjects43 OBJECT-IDENTITY
    STATUS current
    DESCRIPTION
        "Event IKE.43
        Notification from remote side received."
    ::= { ikeEventsGroup 43 }

ike43_remote_addr OBJECT-TYPE
    SYNTAX IpAddress
    MAX-ACCESS accessible-for-notify
    STATUS current
    DESCRIPTION
        "Parameter 'remote_addr' in event IKE.43"
    ::= { ikeEventObjects43 1 }

ike43_message OBJECT-TYPE
    SYNTAX DisplayString
    MAX-ACCESS accessible-for-notify
    STATUS current
    DESCRIPTION
        "Parameter 'message' in event IKE.43"
    ::= { ikeEventObjects43 2 }

ikeEventObjects44 OBJECT-IDENTITY
    STATUS current
    DESCRIPTION
        "Event IKE.44
        A new tunnel has opened and the router has established a new static
        route so it can be back-propagated via RIP or OSPF (RRI or Remote
        Route Injection)."
    ::= { ikeEventsGroup 44 }

ike44_spi OBJECT-TYPE
    SYNTAX Integer32
    MAX-ACCESS accessible-for-notify
    STATUS current
    DESCRIPTION
        "Parameter 'spi' in event IKE.44"
    ::= { ikeEventObjects44 1 }

ike44_dst_addr OBJECT-TYPE
    SYNTAX IpAddress
    MAX-ACCESS accessible-for-notify
    STATUS current
    DESCRIPTION
        "Parameter 'dst_addr' in event IKE.44"
    ::= { ikeEventObjects44 2 }

ike44_dest_mask OBJECT-TYPE
    SYNTAX Integer32
    MAX-ACCESS accessible-for-notify
    STATUS current
    DESCRIPTION
        "Parameter 'dest_mask' in event IKE.44"
    ::= { ikeEventObjects44 3 }

ike44_via_gw OBJECT-TYPE
    SYNTAX IpAddress
    MAX-ACCESS accessible-for-notify
    STATUS current
    DESCRIPTION
        "Parameter 'via_gw' in event IKE.44"
    ::= { ikeEventObjects44 4 }

ikeEventObjects45 OBJECT-IDENTITY
    STATUS current
    DESCRIPTION
        "Event IKE.45
        There was a problem establishing a static route for RRI."
    ::= { ikeEventsGroup 45 }

ike45_spi OBJECT-TYPE
    SYNTAX Integer32
    MAX-ACCESS accessible-for-notify
    STATUS current
    DESCRIPTION
        "Parameter 'spi' in event IKE.45"
    ::= { ikeEventObjects45 1 }

ike45_dst_addr OBJECT-TYPE
    SYNTAX IpAddress
    MAX-ACCESS accessible-for-notify
    STATUS current
    DESCRIPTION
        "Parameter 'dst_addr' in event IKE.45"
    ::= { ikeEventObjects45 2 }

ike45_dest_mask OBJECT-TYPE
    SYNTAX Integer32
    MAX-ACCESS accessible-for-notify
    STATUS current
    DESCRIPTION
        "Parameter 'dest_mask' in event IKE.45"
    ::= { ikeEventObjects45 3 }

ike45_via_gw OBJECT-TYPE
    SYNTAX IpAddress
    MAX-ACCESS accessible-for-notify
    STATUS current
    DESCRIPTION
        "Parameter 'via_gw' in event IKE.45"
    ::= { ikeEventObjects45 4 }

ikeEventObjects46 OBJECT-IDENTITY
    STATUS current
    DESCRIPTION
        "Event IKE.46
        RRI has cleared a static route."
    ::= { ikeEventsGroup 46 }

ike46_spi OBJECT-TYPE
    SYNTAX Integer32
    MAX-ACCESS accessible-for-notify
    STATUS current
    DESCRIPTION
        "Parameter 'spi' in event IKE.46"
    ::= { ikeEventObjects46 1 }

ike46_dst_addr OBJECT-TYPE
    SYNTAX IpAddress
    MAX-ACCESS accessible-for-notify
    STATUS current
    DESCRIPTION
        "Parameter 'dst_addr' in event IKE.46"
    ::= { ikeEventObjects46 2 }

ike46_dest_mask OBJECT-TYPE
    SYNTAX Integer32
    MAX-ACCESS accessible-for-notify
    STATUS current
    DESCRIPTION
        "Parameter 'dest_mask' in event IKE.46"
    ::= { ikeEventObjects46 3 }

ike46_via_gw OBJECT-TYPE
    SYNTAX IpAddress
    MAX-ACCESS accessible-for-notify
    STATUS current
    DESCRIPTION
        "Parameter 'via_gw' in event IKE.46"
    ::= { ikeEventObjects46 4 }

ikeEventObjects47 OBJECT-IDENTITY
    STATUS current
    DESCRIPTION
        "Event IKE.47
        User is trying authentication."
    ::= { ikeEventsGroup 47 }

ike47_user_addr OBJECT-TYPE
    SYNTAX IpAddress
    MAX-ACCESS accessible-for-notify
    STATUS current
    DESCRIPTION
        "Parameter 'user_addr' in event IKE.47"
    ::= { ikeEventObjects47 1 }

ike47_user_string OBJECT-TYPE
    SYNTAX DisplayString
    MAX-ACCESS accessible-for-notify
    STATUS current
    DESCRIPTION
        "Parameter 'user_string' in event IKE.47"
    ::= { ikeEventObjects47 2 }

ikeEventObjects48 OBJECT-IDENTITY
    STATUS current
    DESCRIPTION
        "Event IKE.48
        Tunnel ready to be established."
    ::= { ikeEventsGroup 48 }

ike48_remote_addr OBJECT-TYPE
    SYNTAX IpAddress
    MAX-ACCESS accessible-for-notify
    STATUS current
    DESCRIPTION
        "Parameter 'remote_addr' in event IKE.48"
    ::= { ikeEventObjects48 1 }

ike48_iniciator OBJECT-TYPE
    SYNTAX DisplayString
    MAX-ACCESS accessible-for-notify
    STATUS current
    DESCRIPTION
        "Parameter 'iniciator' in event IKE.48"
    ::= { ikeEventObjects48 2 }

ike48_responder OBJECT-TYPE
    SYNTAX DisplayString
    MAX-ACCESS accessible-for-notify
    STATUS current
    DESCRIPTION
        "Parameter 'responder' in event IKE.48"
    ::= { ikeEventObjects48 3 }

ike48_spi OBJECT-TYPE
    SYNTAX Integer32
    MAX-ACCESS accessible-for-notify
    STATUS current
    DESCRIPTION
        "Parameter 'spi' in event IKE.48"
    ::= { ikeEventObjects48 4 }

ikeEventObjects49 OBJECT-IDENTITY
    STATUS current
    DESCRIPTION
        "Event IKE.49
        Tunnel ready to be disconneted."
    ::= { ikeEventsGroup 49 }

ike49_remote_addr OBJECT-TYPE
    SYNTAX IpAddress
    MAX-ACCESS accessible-for-notify
    STATUS current
    DESCRIPTION
        "Parameter 'remote_addr' in event IKE.49"
    ::= { ikeEventObjects49 1 }

ike49_iniciator OBJECT-TYPE
    SYNTAX DisplayString
    MAX-ACCESS accessible-for-notify
    STATUS current
    DESCRIPTION
        "Parameter 'iniciator' in event IKE.49"
    ::= { ikeEventObjects49 2 }

ike49_responder OBJECT-TYPE
    SYNTAX DisplayString
    MAX-ACCESS accessible-for-notify
    STATUS current
    DESCRIPTION
        "Parameter 'responder' in event IKE.49"
    ::= { ikeEventObjects49 3 }

ike49_spi OBJECT-TYPE
    SYNTAX Integer32
    MAX-ACCESS accessible-for-notify
    STATUS current
    DESCRIPTION
        "Parameter 'spi' in event IKE.49"
    ::= { ikeEventObjects49 4 }

ikeEventObjects50 OBJECT-IDENTITY
    STATUS current
    DESCRIPTION
        "Event IKE.50
        Text Identification Payload registered."
    ::= { ikeEventsGroup 50 }

ike50_address OBJECT-TYPE
    SYNTAX IpAddress
    MAX-ACCESS accessible-for-notify
    STATUS current
    DESCRIPTION
        "Parameter 'address' in event IKE.50"
    ::= { ikeEventObjects50 1 }

ike50_idname OBJECT-TYPE
    SYNTAX DisplayString
    MAX-ACCESS accessible-for-notify
    STATUS current
    DESCRIPTION
        "Parameter 'idname' in event IKE.50"
    ::= { ikeEventObjects50 2 }

ike50_protocolnumber OBJECT-TYPE
    SYNTAX Integer32
    MAX-ACCESS accessible-for-notify
    STATUS current
    DESCRIPTION
        "Parameter 'protocolnumber' in event IKE.50"
    ::= { ikeEventObjects50 3 }

ike50_portnumber OBJECT-TYPE
    SYNTAX Integer32
    MAX-ACCESS accessible-for-notify
    STATUS current
    DESCRIPTION
        "Parameter 'portnumber' in event IKE.50"
    ::= { ikeEventObjects50 4 }

ike50_idtype OBJECT-TYPE
    SYNTAX DisplayString
    MAX-ACCESS accessible-for-notify
    STATUS current
    DESCRIPTION
        "Parameter 'idtype' in event IKE.50"
    ::= { ikeEventObjects50 5 }

ikeEventObjects51 OBJECT-IDENTITY
    STATUS current
    DESCRIPTION
        "Event IKE.51
        IP Identification Payload registered."
    ::= { ikeEventsGroup 51 }

ike51_address OBJECT-TYPE
    SYNTAX IpAddress
    MAX-ACCESS accessible-for-notify
    STATUS current
    DESCRIPTION
        "Parameter 'address' in event IKE.51"
    ::= { ikeEventObjects51 1 }

ike51_idaddress OBJECT-TYPE
    SYNTAX IpAddress
    MAX-ACCESS accessible-for-notify
    STATUS current
    DESCRIPTION
        "Parameter 'idaddress' in event IKE.51"
    ::= { ikeEventObjects51 2 }

ike51_protocolnumber OBJECT-TYPE
    SYNTAX Integer32
    MAX-ACCESS accessible-for-notify
    STATUS current
    DESCRIPTION
        "Parameter 'protocolnumber' in event IKE.51"
    ::= { ikeEventObjects51 3 }

ike51_portnumber OBJECT-TYPE
    SYNTAX Integer32
    MAX-ACCESS accessible-for-notify
    STATUS current
    DESCRIPTION
        "Parameter 'portnumber' in event IKE.51"
    ::= { ikeEventObjects51 4 }

ike51_idtype OBJECT-TYPE
    SYNTAX DisplayString
    MAX-ACCESS accessible-for-notify
    STATUS current
    DESCRIPTION
        "Parameter 'idtype' in event IKE.51"
    ::= { ikeEventObjects51 5 }

ikeEventObjects52 OBJECT-IDENTITY
    STATUS current
    DESCRIPTION
        "Event IKE.52
        Periodic information of the established tunnel."
    ::= { ikeEventsGroup 52 }

ike52_remote_addr OBJECT-TYPE
    SYNTAX IpAddress
    MAX-ACCESS accessible-for-notify
    STATUS current
    DESCRIPTION
        "Parameter 'remote_addr' in event IKE.52"
    ::= { ikeEventObjects52 1 }

ike52_spi OBJECT-TYPE
    SYNTAX Integer32
    MAX-ACCESS accessible-for-notify
    STATUS current
    DESCRIPTION
        "Parameter 'spi' in event IKE.52"
    ::= { ikeEventObjects52 2 }

ike52_remote_client OBJECT-TYPE
    SYNTAX IpAddress
    MAX-ACCESS accessible-for-notify
    STATUS current
    DESCRIPTION
        "Parameter 'remote_client' in event IKE.52"
    ::= { ikeEventObjects52 3 }

ikeEventObjects53 OBJECT-IDENTITY
    STATUS current
    DESCRIPTION
        "Event IKE.53
        Attribute string registered"
    ::= { ikeEventsGroup 53 }

ike53_remote_addr OBJECT-TYPE
    SYNTAX IpAddress
    MAX-ACCESS accessible-for-notify
    STATUS current
    DESCRIPTION
        "Parameter 'remote_addr' in event IKE.53"
    ::= { ikeEventObjects53 1 }

ike53_attribute_string OBJECT-TYPE
    SYNTAX DisplayString
    MAX-ACCESS accessible-for-notify
    STATUS current
    DESCRIPTION
        "Parameter 'attribute_string' in event IKE.53"
    ::= { ikeEventObjects53 2 }

ikeEventObjects54 OBJECT-IDENTITY
    STATUS current
    DESCRIPTION
        "Event IKE.54
        Information string registered"
    ::= { ikeEventsGroup 54 }

ike54_remote_addr OBJECT-TYPE
    SYNTAX IpAddress
    MAX-ACCESS accessible-for-notify
    STATUS current
    DESCRIPTION
        "Parameter 'remote_addr' in event IKE.54"
    ::= { ikeEventObjects54 1 }

ike54_info_string OBJECT-TYPE
    SYNTAX DisplayString
    MAX-ACCESS accessible-for-notify
    STATUS current
    DESCRIPTION
        "Parameter 'info_string' in event IKE.54"
    ::= { ikeEventObjects54 2 }

ikeEventObjects55 OBJECT-IDENTITY
    STATUS current
    DESCRIPTION
        "Event IKE.55
        There is been a change on the source or destination port for this SA"
    ::= { ikeEventsGroup 55 }

ike55_sa_conn_id OBJECT-TYPE
    SYNTAX Integer32
    MAX-ACCESS accessible-for-notify
    STATUS current
    DESCRIPTION
        "Parameter 'sa_conn_id' in event IKE.55"
    ::= { ikeEventObjects55 1 }

ike55_old_src_port OBJECT-TYPE
    SYNTAX Integer32
    MAX-ACCESS accessible-for-notify
    STATUS current
    DESCRIPTION
        "Parameter 'old_src_port' in event IKE.55"
    ::= { ikeEventObjects55 2 }

ike55_old_dst_port OBJECT-TYPE
    SYNTAX Integer32
    MAX-ACCESS accessible-for-notify
    STATUS current
    DESCRIPTION
        "Parameter 'old_dst_port' in event IKE.55"
    ::= { ikeEventObjects55 3 }

ike55_new_src_port OBJECT-TYPE
    SYNTAX Integer32
    MAX-ACCESS accessible-for-notify
    STATUS current
    DESCRIPTION
        "Parameter 'new_src_port' in event IKE.55"
    ::= { ikeEventObjects55 4 }

ike55_new_dst_port OBJECT-TYPE
    SYNTAX Integer32
    MAX-ACCESS accessible-for-notify
    STATUS current
    DESCRIPTION
        "Parameter 'new_dst_port' in event IKE.55"
    ::= { ikeEventObjects55 5 }

ikeEventObjects56 OBJECT-IDENTITY
    STATUS current
    DESCRIPTION
        "Event IKE.56
        A GDOI client message has been sent"
    ::= { ikeEventsGroup 56 }

ike56_message OBJECT-TYPE
    SYNTAX DisplayString
    MAX-ACCESS accessible-for-notify
    STATUS current
    DESCRIPTION
        "Parameter 'message' in event IKE.56"
    ::= { ikeEventObjects56 1 }

ike56_dst_ip OBJECT-TYPE
    SYNTAX IpAddress
    MAX-ACCESS accessible-for-notify
    STATUS current
    DESCRIPTION
        "Parameter 'dst_ip' in event IKE.56"
    ::= { ikeEventObjects56 2 }

ike56_group OBJECT-TYPE
    SYNTAX Integer32
    MAX-ACCESS accessible-for-notify
    STATUS current
    DESCRIPTION
        "Parameter 'group' in event IKE.56"
    ::= { ikeEventObjects56 3 }

ikeEventObjects57 OBJECT-IDENTITY
    STATUS current
    DESCRIPTION
        "Event IKE.57
        A GDOI client message has been received"
    ::= { ikeEventsGroup 57 }

ike57_message OBJECT-TYPE
    SYNTAX DisplayString
    MAX-ACCESS accessible-for-notify
    STATUS current
    DESCRIPTION
        "Parameter 'message' in event IKE.57"
    ::= { ikeEventObjects57 1 }

ike57_src_ip OBJECT-TYPE
    SYNTAX IpAddress
    MAX-ACCESS accessible-for-notify
    STATUS current
    DESCRIPTION
        "Parameter 'src_ip' in event IKE.57"
    ::= { ikeEventObjects57 2 }

ike57_group OBJECT-TYPE
    SYNTAX Integer32
    MAX-ACCESS accessible-for-notify
    STATUS current
    DESCRIPTION
        "Parameter 'group' in event IKE.57"
    ::= { ikeEventObjects57 3 }

ikeEventObjects58 OBJECT-IDENTITY
    STATUS current
    DESCRIPTION
        "Event IKE.58
        A GDOI server message has been sent"
    ::= { ikeEventsGroup 58 }

ike58_message OBJECT-TYPE
    SYNTAX DisplayString
    MAX-ACCESS accessible-for-notify
    STATUS current
    DESCRIPTION
        "Parameter 'message' in event IKE.58"
    ::= { ikeEventObjects58 1 }

ike58_dst_ip OBJECT-TYPE
    SYNTAX IpAddress
    MAX-ACCESS accessible-for-notify
    STATUS current
    DESCRIPTION
        "Parameter 'dst_ip' in event IKE.58"
    ::= { ikeEventObjects58 2 }

ike58_group OBJECT-TYPE
    SYNTAX Integer32
    MAX-ACCESS accessible-for-notify
    STATUS current
    DESCRIPTION
        "Parameter 'group' in event IKE.58"
    ::= { ikeEventObjects58 3 }

ikeEventObjects59 OBJECT-IDENTITY
    STATUS current
    DESCRIPTION
        "Event IKE.59
        A GDOI server message has been sent"
    ::= { ikeEventsGroup 59 }

ike59_message OBJECT-TYPE
    SYNTAX DisplayString
    MAX-ACCESS accessible-for-notify
    STATUS current
    DESCRIPTION
        "Parameter 'message' in event IKE.59"
    ::= { ikeEventObjects59 1 }

ike59_src_ip OBJECT-TYPE
    SYNTAX IpAddress
    MAX-ACCESS accessible-for-notify
    STATUS current
    DESCRIPTION
        "Parameter 'src_ip' in event IKE.59"
    ::= { ikeEventObjects59 2 }

ike59_group OBJECT-TYPE
    SYNTAX Integer32
    MAX-ACCESS accessible-for-notify
    STATUS current
    DESCRIPTION
        "Parameter 'group' in event IKE.59"
    ::= { ikeEventObjects59 3 }

ikeEventObjects60 OBJECT-IDENTITY
    STATUS current
    DESCRIPTION
        "Event IKE.60
        A GDOI client error"
    ::= { ikeEventsGroup 60 }

ike60_error OBJECT-TYPE
    SYNTAX DisplayString
    MAX-ACCESS accessible-for-notify
    STATUS current
    DESCRIPTION
        "Parameter 'error' in event IKE.60"
    ::= { ikeEventObjects60 1 }

ikeEventObjects61 OBJECT-IDENTITY
    STATUS current
    DESCRIPTION
        "Event IKE.61
        A GDOI server error"
    ::= { ikeEventsGroup 61 }

ike61_error OBJECT-TYPE
    SYNTAX DisplayString
    MAX-ACCESS accessible-for-notify
    STATUS current
    DESCRIPTION
        "Parameter 'error' in event IKE.61"
    ::= { ikeEventObjects61 1 }

ikeEventObjects62 OBJECT-IDENTITY
    STATUS current
    DESCRIPTION
        "Event IKE.62
        A GDOI client has added a new acl"
    ::= { ikeEventsGroup 62 }

ike62_spi OBJECT-TYPE
    SYNTAX Integer32
    MAX-ACCESS accessible-for-notify
    STATUS current
    DESCRIPTION
        "Parameter 'spi' in event IKE.62"
    ::= { ikeEventObjects62 1 }

ike62_srIP OBJECT-TYPE
    SYNTAX IpAddress
    MAX-ACCESS accessible-for-notify
    STATUS current
    DESCRIPTION
        "Parameter 'srIP' in event IKE.62"
    ::= { ikeEventObjects62 2 }

ike62_dstIP OBJECT-TYPE
    SYNTAX IpAddress
    MAX-ACCESS accessible-for-notify
    STATUS current
    DESCRIPTION
        "Parameter 'dstIP' in event IKE.62"
    ::= { ikeEventObjects62 3 }

ike62_prot OBJECT-TYPE
    SYNTAX Integer32
    MAX-ACCESS accessible-for-notify
    STATUS current
    DESCRIPTION
        "Parameter 'prot' in event IKE.62"
    ::= { ikeEventObjects62 4 }

ike62_sport OBJECT-TYPE
    SYNTAX Integer32
    MAX-ACCESS accessible-for-notify
    STATUS current
    DESCRIPTION
        "Parameter 'sport' in event IKE.62"
    ::= { ikeEventObjects62 5 }

ike62_dport OBJECT-TYPE
    SYNTAX Integer32
    MAX-ACCESS accessible-for-notify
    STATUS current
    DESCRIPTION
        "Parameter 'dport' in event IKE.62"
    ::= { ikeEventObjects62 6 }

ikeEventObjects63 OBJECT-IDENTITY
    STATUS current
    DESCRIPTION
        "Event IKE.63
        A GDOI client has created new in out sas"
    ::= { ikeEventsGroup 63 }

ike63_spi OBJECT-TYPE
    SYNTAX Integer32
    MAX-ACCESS accessible-for-notify
    STATUS current
    DESCRIPTION
        "Parameter 'spi' in event IKE.63"
    ::= { ikeEventObjects63 1 }

ike63_lifetime OBJECT-TYPE
    SYNTAX Integer32
    MAX-ACCESS accessible-for-notify
    STATUS current
    DESCRIPTION
        "Parameter 'lifetime' in event IKE.63"
    ::= { ikeEventObjects63 2 }

ikeEventObjects64 OBJECT-IDENTITY
    STATUS current
    DESCRIPTION
        "Event IKE.64
        A client rekey"
    ::= { ikeEventsGroup 64 }

ike64_ic_lo OBJECT-TYPE
    SYNTAX Integer32
    MAX-ACCESS accessible-for-notify
    STATUS current
    DESCRIPTION
        "Parameter 'ic_lo' in event IKE.64"
    ::= { ikeEventObjects64 1 }

ike64_ic_hi OBJECT-TYPE
    SYNTAX Integer32
    MAX-ACCESS accessible-for-notify
    STATUS current
    DESCRIPTION
        "Parameter 'ic_hi' in event IKE.64"
    ::= { ikeEventObjects64 2 }

ike64_rc_lo OBJECT-TYPE
    SYNTAX Integer32
    MAX-ACCESS accessible-for-notify
    STATUS current
    DESCRIPTION
        "Parameter 'rc_lo' in event IKE.64"
    ::= { ikeEventObjects64 3 }

ike64_rc_hi OBJECT-TYPE
    SYNTAX Integer32
    MAX-ACCESS accessible-for-notify
    STATUS current
    DESCRIPTION
        "Parameter 'rc_hi' in event IKE.64"
    ::= { ikeEventObjects64 4 }

ike64_nic_lo OBJECT-TYPE
    SYNTAX Integer32
    MAX-ACCESS accessible-for-notify
    STATUS current
    DESCRIPTION
        "Parameter 'nic_lo' in event IKE.64"
    ::= { ikeEventObjects64 5 }

ike64_nic_hi OBJECT-TYPE
    SYNTAX Integer32
    MAX-ACCESS accessible-for-notify
    STATUS current
    DESCRIPTION
        "Parameter 'nic_hi' in event IKE.64"
    ::= { ikeEventObjects64 6 }

ike64_nr_lo OBJECT-TYPE
    SYNTAX Integer32
    MAX-ACCESS accessible-for-notify
    STATUS current
    DESCRIPTION
        "Parameter 'nr_lo' in event IKE.64"
    ::= { ikeEventObjects64 7 }

ike64_nr_hi OBJECT-TYPE
    SYNTAX Integer32
    MAX-ACCESS accessible-for-notify
    STATUS current
    DESCRIPTION
        "Parameter 'nr_hi' in event IKE.64"
    ::= { ikeEventObjects64 8 }

ikeEventObjects65 OBJECT-IDENTITY
    STATUS current
    DESCRIPTION
        "Event IKE.65
        A server rekey"
    ::= { ikeEventsGroup 65 }

ike65_ic_lo OBJECT-TYPE
    SYNTAX Integer32
    MAX-ACCESS accessible-for-notify
    STATUS current
    DESCRIPTION
        "Parameter 'ic_lo' in event IKE.65"
    ::= { ikeEventObjects65 1 }

ike65_ic_hi OBJECT-TYPE
    SYNTAX Integer32
    MAX-ACCESS accessible-for-notify
    STATUS current
    DESCRIPTION
        "Parameter 'ic_hi' in event IKE.65"
    ::= { ikeEventObjects65 2 }

ike65_rc_lo OBJECT-TYPE
    SYNTAX Integer32
    MAX-ACCESS accessible-for-notify
    STATUS current
    DESCRIPTION
        "Parameter 'rc_lo' in event IKE.65"
    ::= { ikeEventObjects65 3 }

ike65_rc_hi OBJECT-TYPE
    SYNTAX Integer32
    MAX-ACCESS accessible-for-notify
    STATUS current
    DESCRIPTION
        "Parameter 'rc_hi' in event IKE.65"
    ::= { ikeEventObjects65 4 }

ike65_nic_lo OBJECT-TYPE
    SYNTAX Integer32
    MAX-ACCESS accessible-for-notify
    STATUS current
    DESCRIPTION
        "Parameter 'nic_lo' in event IKE.65"
    ::= { ikeEventObjects65 5 }

ike65_nic_hi OBJECT-TYPE
    SYNTAX Integer32
    MAX-ACCESS accessible-for-notify
    STATUS current
    DESCRIPTION
        "Parameter 'nic_hi' in event IKE.65"
    ::= { ikeEventObjects65 6 }

ike65_nr_lo OBJECT-TYPE
    SYNTAX Integer32
    MAX-ACCESS accessible-for-notify
    STATUS current
    DESCRIPTION
        "Parameter 'nr_lo' in event IKE.65"
    ::= { ikeEventObjects65 7 }

ike65_nr_hi OBJECT-TYPE
    SYNTAX Integer32
    MAX-ACCESS accessible-for-notify
    STATUS current
    DESCRIPTION
        "Parameter 'nr_hi' in event IKE.65"
    ::= { ikeEventObjects65 8 }

ikeEventObjects66 OBJECT-IDENTITY
    STATUS current
    DESCRIPTION
        "Event IKE.66
        Server has generated new ids"
    ::= { ikeEventsGroup 66 }

ike66_ic_lo OBJECT-TYPE
    SYNTAX Integer32
    MAX-ACCESS accessible-for-notify
    STATUS current
    DESCRIPTION
        "Parameter 'ic_lo' in event IKE.66"
    ::= { ikeEventObjects66 1 }

ike66_ic_hi OBJECT-TYPE
    SYNTAX Integer32
    MAX-ACCESS accessible-for-notify
    STATUS current
    DESCRIPTION
        "Parameter 'ic_hi' in event IKE.66"
    ::= { ikeEventObjects66 2 }

ike66_rc_lo OBJECT-TYPE
    SYNTAX Integer32
    MAX-ACCESS accessible-for-notify
    STATUS current
    DESCRIPTION
        "Parameter 'rc_lo' in event IKE.66"
    ::= { ikeEventObjects66 3 }

ike66_rc_hi OBJECT-TYPE
    SYNTAX Integer32
    MAX-ACCESS accessible-for-notify
    STATUS current
    DESCRIPTION
        "Parameter 'rc_hi' in event IKE.66"
    ::= { ikeEventObjects66 4 }

ike66_nic_lo OBJECT-TYPE
    SYNTAX Integer32
    MAX-ACCESS accessible-for-notify
    STATUS current
    DESCRIPTION
        "Parameter 'nic_lo' in event IKE.66"
    ::= { ikeEventObjects66 5 }

ike66_nic_hi OBJECT-TYPE
    SYNTAX Integer32
    MAX-ACCESS accessible-for-notify
    STATUS current
    DESCRIPTION
        "Parameter 'nic_hi' in event IKE.66"
    ::= { ikeEventObjects66 6 }

ike66_nr_lo OBJECT-TYPE
    SYNTAX Integer32
    MAX-ACCESS accessible-for-notify
    STATUS current
    DESCRIPTION
        "Parameter 'nr_lo' in event IKE.66"
    ::= { ikeEventObjects66 7 }

ike66_nr_hi OBJECT-TYPE
    SYNTAX Integer32
    MAX-ACCESS accessible-for-notify
    STATUS current
    DESCRIPTION
        "Parameter 'nr_hi' in event IKE.66"
    ::= { ikeEventObjects66 8 }

ikeEventObjects67 OBJECT-IDENTITY
    STATUS current
    DESCRIPTION
        "Event IKE.67
        client is processing a tek payload"
    ::= { ikeEventsGroup 67 }

ike67_spi OBJECT-TYPE
    SYNTAX Integer32
    MAX-ACCESS accessible-for-notify
    STATUS current
    DESCRIPTION
        "Parameter 'spi' in event IKE.67"
    ::= { ikeEventObjects67 1 }

ike67_size OBJECT-TYPE
    SYNTAX Integer32
    MAX-ACCESS accessible-for-notify
    STATUS current
    DESCRIPTION
        "Parameter 'size' in event IKE.67"
    ::= { ikeEventObjects67 2 }

ikeEventObjects68 OBJECT-IDENTITY
    STATUS current
    DESCRIPTION
        "Event IKE.68
        client is deleting and old sa"
    ::= { ikeEventsGroup 68 }

ike68_spi OBJECT-TYPE
    SYNTAX Integer32
    MAX-ACCESS accessible-for-notify
    STATUS current
    DESCRIPTION
        "Parameter 'spi' in event IKE.68"
    ::= { ikeEventObjects68 1 }

ike68_reason OBJECT-TYPE
    SYNTAX DisplayString
    MAX-ACCESS accessible-for-notify
    STATUS current
    DESCRIPTION
        "Parameter 'reason' in event IKE.68"
    ::= { ikeEventObjects68 2 }

ikeEventObjects69 OBJECT-IDENTITY
    STATUS current
    DESCRIPTION
        "Event IKE.69
        timestamp rcvd or sent"
    ::= { ikeEventsGroup 69 }

ike69_rcvd_or_sent OBJECT-TYPE
    SYNTAX DisplayString
    MAX-ACCESS accessible-for-notify
    STATUS current
    DESCRIPTION
        "Parameter 'rcvd_or_sent' in event IKE.69"
    ::= { ikeEventObjects69 1 }

ike69_timestam OBJECT-TYPE
    SYNTAX Integer32
    MAX-ACCESS accessible-for-notify
    STATUS current
    DESCRIPTION
        "Parameter 'timestam' in event IKE.69"
    ::= { ikeEventObjects69 2 }

ike69_diff OBJECT-TYPE
    SYNTAX Integer32
    MAX-ACCESS accessible-for-notify
    STATUS current
    DESCRIPTION
        "Parameter 'diff' in event IKE.69"
    ::= { ikeEventObjects69 3 }

ikeEventObjects70 OBJECT-IDENTITY
    STATUS current
    DESCRIPTION
        "Event IKE.70
        Doing a DNS request"
    ::= { ikeEventsGroup 70 }

ike70_host_addr OBJECT-TYPE
    SYNTAX DisplayString
    MAX-ACCESS accessible-for-notify
    STATUS current
    DESCRIPTION
        "Parameter 'host_addr' in event IKE.70"
    ::= { ikeEventObjects70 1 }

ikeEventObjects71 OBJECT-IDENTITY
    STATUS current
    DESCRIPTION
        "Event IKE.71
        DNS reply"
    ::= { ikeEventsGroup 71 }

ike71_host_addr OBJECT-TYPE
    SYNTAX DisplayString
    MAX-ACCESS accessible-for-notify
    STATUS current
    DESCRIPTION
        "Parameter 'host_addr' in event IKE.71"
    ::= { ikeEventObjects71 1 }

ike71_IP_addr OBJECT-TYPE
    SYNTAX IpAddress
    MAX-ACCESS accessible-for-notify
    STATUS current
    DESCRIPTION
        "Parameter 'IP_addr' in event IKE.71"
    ::= { ikeEventObjects71 2 }

ikeEventObjects72 OBJECT-IDENTITY
    STATUS current
    DESCRIPTION
        "Event IKE.72
        DNS ERROR "
    ::= { ikeEventsGroup 72 }

ike72_host_addr OBJECT-TYPE
    SYNTAX DisplayString
    MAX-ACCESS accessible-for-notify
    STATUS current
    DESCRIPTION
        "Parameter 'host_addr' in event IKE.72"
    ::= { ikeEventObjects72 1 }

ike72_error_code OBJECT-TYPE
    SYNTAX Integer32
    MAX-ACCESS accessible-for-notify
    STATUS current
    DESCRIPTION
        "Parameter 'error_code' in event IKE.72"
    ::= { ikeEventObjects72 2 }

ikeEventObjects73 OBJECT-IDENTITY
    STATUS current
    DESCRIPTION
        "Event IKE.73
        There is an IP address for this domain in the domain list"
    ::= { ikeEventsGroup 73 }

ike73_IP_addr OBJECT-TYPE
    SYNTAX IpAddress
    MAX-ACCESS accessible-for-notify
    STATUS current
    DESCRIPTION
        "Parameter 'IP_addr' in event IKE.73"
    ::= { ikeEventObjects73 1 }

ike73_host_addr OBJECT-TYPE
    SYNTAX DisplayString
    MAX-ACCESS accessible-for-notify
    STATUS current
    DESCRIPTION
        "Parameter 'host_addr' in event IKE.73"
    ::= { ikeEventObjects73 2 }

ike73_ttr OBJECT-TYPE
    SYNTAX Integer32
    MAX-ACCESS accessible-for-notify
    STATUS current
    DESCRIPTION
        "Parameter 'ttr' in event IKE.73"
    ::= { ikeEventObjects73 3 }

ikeEventObjects74 OBJECT-IDENTITY
    STATUS current
    DESCRIPTION
        "Event IKE.74
        There is a new IP/domain in the domain list"
    ::= { ikeEventsGroup 74 }

ike74_IP_addr OBJECT-TYPE
    SYNTAX IpAddress
    MAX-ACCESS accessible-for-notify
    STATUS current
    DESCRIPTION
        "Parameter 'IP_addr' in event IKE.74"
    ::= { ikeEventObjects74 1 }

ike74_host_addr OBJECT-TYPE
    SYNTAX DisplayString
    MAX-ACCESS accessible-for-notify
    STATUS current
    DESCRIPTION
        "Parameter 'host_addr' in event IKE.74"
    ::= { ikeEventObjects74 2 }

ike74_ttr OBJECT-TYPE
    SYNTAX Integer32
    MAX-ACCESS accessible-for-notify
    STATUS current
    DESCRIPTION
        "Parameter 'ttr' in event IKE.74"
    ::= { ikeEventObjects74 3 }

ikeEventObjects75 OBJECT-IDENTITY
    STATUS current
    DESCRIPTION
        "Event IKE.75
        The entry DOMAIN/IP will be removed"
    ::= { ikeEventsGroup 75 }

ike75_host_addr OBJECT-TYPE
    SYNTAX DisplayString
    MAX-ACCESS accessible-for-notify
    STATUS current
    DESCRIPTION
        "Parameter 'host_addr' in event IKE.75"
    ::= { ikeEventObjects75 1 }

ike75_IP_addr OBJECT-TYPE
    SYNTAX IpAddress
    MAX-ACCESS accessible-for-notify
    STATUS current
    DESCRIPTION
        "Parameter 'IP_addr' in event IKE.75"
    ::= { ikeEventObjects75 2 }


ikeNotification1 NOTIFICATION-TYPE
    OBJECTS { 
              ike1_remote_addr, 
              ike1_template_number 
            }
    STATUS current
    DESCRIPTION
        "Notification of Event IKE.1

        Message: 'IKE($1)01:--------- Matching template (number $2) ---------'

        Parameters list:
              $1: ike1_remote_addr
              $2: ike1_template_number

        Matching template."
    ::= { ikeNotificationsPrefix 1 }

ikeNotification2 NOTIFICATION-TYPE
    OBJECTS { 
              ike2_remote_addr, 
              ike2_connection 
            }
    STATUS current
    DESCRIPTION
        "Notification of Event IKE.2

        Message: 'IKE($1)02:--------- Matching SA NEG (connection number $2) ---------'

        Parameters list:
              $1: ike2_remote_addr
              $2: ike2_connection

        Matching SA for negotiation."
    ::= { ikeNotificationsPrefix 2 }

ikeNotification3 NOTIFICATION-TYPE
    OBJECTS { 
              ike3_remote_addr 
            }
    STATUS current
    DESCRIPTION
        "Notification of Event IKE.3

        Message: 'IKE($1)03:--------- Decryption error ---------'

        Parameters list:
              $1: ike3_remote_addr

        There was an error decrypting the message."
    ::= { ikeNotificationsPrefix 3 }

ikeNotification4 NOTIFICATION-TYPE
    OBJECTS { 
              ike4_remote_addr 
            }
    STATUS current
    DESCRIPTION
        "Notification of Event IKE.4

        Message: 'IKE($1)04:--------- Retransmission ---------'

        Parameters list:
              $1: ike4_remote_addr

        Received message is a retransmission."
    ::= { ikeNotificationsPrefix 4 }

ikeNotification5 NOTIFICATION-TYPE
    OBJECTS { 
              ike5_remote_addr 
            }
    STATUS current
    DESCRIPTION
        "Notification of Event IKE.5

        Message: 'IKE($1)05:--------- Unable to initiate. Unknown destination ---------'

        Parameters list:
              $1: ike5_remote_addr

        Could not initiate IKE negotiation: unknown destination."
    ::= { ikeNotificationsPrefix 5 }

ikeNotification6 NOTIFICATION-TYPE
    OBJECTS { 
              ike6_remote_addr, 
              ike6_connection 
            }
    STATUS current
    DESCRIPTION
        "Notification of Event IKE.6

        Message: 'IKE($1)06:--------- Creating ISAKMP NEG (connection number $2) ---------'

        Parameters list:
              $1: ike6_remote_addr
              $2: ike6_connection

        Creating ISAKMP negotiation SA."
    ::= { ikeNotificationsPrefix 6 }

ikeNotification7 NOTIFICATION-TYPE
    OBJECTS { 
              ike7_remote_addr 
            }
    STATUS current
    DESCRIPTION
        "Notification of Event IKE.7

        Message: 'IKE($1)07:--------- Deleting ISAKMP NEG ---------'

        Parameters list:
              $1: ike7_remote_addr

        Deleting ISAKMP negotiation SA."
    ::= { ikeNotificationsPrefix 7 }

ikeNotification8 NOTIFICATION-TYPE
    OBJECTS { 
              ike8_remote_addr 
            }
    STATUS current
    DESCRIPTION
        "Notification of Event IKE.8

        Message: 'IKE($1)08:--------- Creating ISAKMP SA ---------'

        Parameters list:
              $1: ike8_remote_addr

        Creating ISAKMP SA."
    ::= { ikeNotificationsPrefix 8 }

ikeNotification9 NOTIFICATION-TYPE
    OBJECTS { 
              ike9_remote_addr, 
              ike9_message_id 
            }
    STATUS current
    DESCRIPTION
        "Notification of Event IKE.9

        Message: 'IKE($1)09:--------- Creating ISAKMP SA id (0x$2) ---------'

        Parameters list:
              $1: ike9_remote_addr
              $2: ike9_message_id

        Creating ISAKMP SA id."
    ::= { ikeNotificationsPrefix 9 }

ikeNotification10 NOTIFICATION-TYPE
    OBJECTS { 
              ike10_remote_addr, 
              ike10_ini_cookie_lo,
              ike10_ini_cookie_hi,
              ike10_res_cookie_lo,
              ike10_res_cookie_hi 
            }
    STATUS current
    DESCRIPTION
        "Notification of Event IKE.10

        Message: 'IKE($1)10:--------- Unable to make ISAKMP SA (cookies initiator:$2$3 responder:$4$5) ---------'

        Parameters list:
              $1: ike10_remote_addr
              $2: ike10_ini_cookie_lo
              $3: ike10_ini_cookie_hi
              $4: ike10_res_cookie_lo
              $5: ike10_res_cookie_hi

        Unable to create ISAKMP SA."
    ::= { ikeNotificationsPrefix 10 }

ikeNotification11 NOTIFICATION-TYPE
    OBJECTS { 
              ike11_remote_addr, 
              ike11_spi 
            }
    STATUS current
    DESCRIPTION
        "Notification of Event IKE.11

        Message: 'IKE($1)11:--------- Creating SA IN spi: 0x$2---------'

        Parameters list:
              $1: ike11_remote_addr
              $2: ike11_spi

        Creating SA for incoming packets."
    ::= { ikeNotificationsPrefix 11 }

ikeNotification12 NOTIFICATION-TYPE
    OBJECTS { 
              ike12_remote_addr, 
              ike12_spi 
            }
    STATUS current
    DESCRIPTION
        "Notification of Event IKE.12

        Message: 'IKE($1)12:--------- Creating SA OUT spi: 0x$2---------'

        Parameters list:
              $1: ike12_remote_addr
              $2: ike12_spi

        Creating SA for outgoing packets."
    ::= { ikeNotificationsPrefix 12 }

ikeNotification13 NOTIFICATION-TYPE
    OBJECTS { 
              ike13_remote_addr 
            }
    STATUS current
    DESCRIPTION
        "Notification of Event IKE.13

        Message: 'IKE($1)13:--------- Deleting AL ENTRY ---------'

        Parameters list:
              $1: ike13_remote_addr

        Deleting access list entry."
    ::= { ikeNotificationsPrefix 13 }

ikeNotification14 NOTIFICATION-TYPE
    OBJECTS { 
              ike14_remote_addr, 
              ike14_spi 
            }
    STATUS current
    DESCRIPTION
        "Notification of Event IKE.14

        Message: 'IKE($1)14:--------- Deleting SA IN spi: 0x$2 ---------'

        Parameters list:
              $1: ike14_remote_addr
              $2: ike14_spi

        Deleting SA for incoming packets."
    ::= { ikeNotificationsPrefix 14 }

ikeNotification15 NOTIFICATION-TYPE
    OBJECTS { 
              ike15_remote_addr, 
              ike15_spi 
            }
    STATUS current
    DESCRIPTION
        "Notification of Event IKE.15

        Message: 'IKE($1)15:--------- Deleting SA OUT spi: 0x$2 ---------'

        Parameters list:
              $1: ike15_remote_addr
              $2: ike15_spi

        Deleting SA for outgoing packets."
    ::= { ikeNotificationsPrefix 15 }

ikeNotification16 NOTIFICATION-TYPE
    OBJECTS { 
              ike16_remote_addr, 
              ike16_spi 
            }
    STATUS current
    DESCRIPTION
        "Notification of Event IKE.16

        Message: 'IKE($1)16:--------- KeepAlive Deleting SA (spi: 0x$2) ---------'

        Parameters list:
              $1: ike16_remote_addr
              $2: ike16_spi

        Keepalive expired: deleting SA."
    ::= { ikeNotificationsPrefix 16 }

ikeNotification17 NOTIFICATION-TYPE
    OBJECTS { 
              ike17_remote_addr 
            }
    STATUS current
    DESCRIPTION
        "Notification of Event IKE.17

        Message: 'IKE($1)17:--------- Purgetime SA NEG ---------'

        Parameters list:
              $1: ike17_remote_addr

        Purgetime expired for negotiation SA."
    ::= { ikeNotificationsPrefix 17 }

ikeNotification18 NOTIFICATION-TYPE
    OBJECTS { 
              ike18_remote_addr, 
              ike18_id,
              ike18_source,
              ike18_destination 
            }
    STATUS current
    DESCRIPTION
        "Notification of Event IKE.18

        Message: 'IKE($1)18:--------- Purgetime SA NEG II (id:0x$2 source:$3 destination:$4) ---------'

        Parameters list:
              $1: ike18_remote_addr
              $2: ike18_id
              $3: ike18_source
              $4: ike18_destination

        Purgetime expired for phase II negotiation SA."
    ::= { ikeNotificationsPrefix 18 }

ikeNotification19 NOTIFICATION-TYPE
    OBJECTS { 
              ike19_remote_addr 
            }
    STATUS current
    DESCRIPTION
        "Notification of Event IKE.19

        Message: 'IKE($1)19:--------- Isakmp SA negotiating I ---------'

        Parameters list:
              $1: ike19_remote_addr

        ISAKMP SA commencing phase I negotiation."
    ::= { ikeNotificationsPrefix 19 }

ikeNotification20 NOTIFICATION-TYPE
    OBJECTS { 
              ike20_remote_addr 
            }
    STATUS current
    DESCRIPTION
        "Notification of Event IKE.20

        Message: 'IKE($1)20:--------- Negotiation on Phase I. Phase II not allowed ---------'

        Parameters list:
              $1: ike20_remote_addr

        Negotiation on phase I: phase II not allowed."
    ::= { ikeNotificationsPrefix 20 }

ikeNotification21 NOTIFICATION-TYPE
    OBJECTS { 
              ike21_remote_addr 
            }
    STATUS current
    DESCRIPTION
        "Notification of Event IKE.21

        Message: 'IKE($1)21:--------- Invalid NegII or Isakmp SA ---------'

        Parameters list:
              $1: ike21_remote_addr

        Either ISAKMP SA or phase II negotiation information is invalid."
    ::= { ikeNotificationsPrefix 21 }

ikeNotification22 NOTIFICATION-TYPE
    OBJECTS { 
              ike22_remote_addr, 
              ike22_spi 
            }
    STATUS current
    DESCRIPTION
        "Notification of Event IKE.22

        Message: 'IKE($1)22:--------- Initiated Renegotiation Timer for SA OUT (spi: 0x$2) ---------'

        Parameters list:
              $1: ike22_remote_addr
              $2: ike22_spi

        Renegotiation timer for outgoing packets SA initiated."
    ::= { ikeNotificationsPrefix 22 }

ikeNotification23 NOTIFICATION-TYPE
    OBJECTS { 
              ike23_remote_addr, 
              ike23_spi 
            }
    STATUS current
    DESCRIPTION
        "Notification of Event IKE.23

        Message: 'IKE($1)23:--------- Renegotiation Timer for SA OUT expired (spi: 0x$2) ---------'

        Parameters list:
              $1: ike23_remote_addr
              $2: ike23_spi

        Renegotiation timer for outgoing packets SA expired."
    ::= { ikeNotificationsPrefix 23 }

ikeNotification24 NOTIFICATION-TYPE
    OBJECTS { 
              ike24_remote_addr 
            }
    STATUS current
    DESCRIPTION
        "Notification of Event IKE.24

        Message: 'IKE($1)24:--------- Attempt to renegotiate delayed ---------'

        Parameters list:
              $1: ike24_remote_addr

        Attempt to renegotiate delayed."
    ::= { ikeNotificationsPrefix 24 }

ikeNotification25 NOTIFICATION-TYPE
    OBJECTS { 
              ike25_remote_addr 
            }
    STATUS current
    DESCRIPTION
        "Notification of Event IKE.25

        Message: 'IKE($1)25:--------- Matching CRL ---------'

        Parameters list:
              $1: ike25_remote_addr

        Matching CRL (Certificate Revocation List)."
    ::= { ikeNotificationsPrefix 25 }

ikeNotification26 NOTIFICATION-TYPE
    OBJECTS { 
              ike26_remote_addr 
            }
    STATUS current
    DESCRIPTION
        "Notification of Event IKE.26

        Message: 'IKE($1)26:--------- Invalid ID information ---------'

        Parameters list:
              $1: ike26_remote_addr

        Invalid ID information."
    ::= { ikeNotificationsPrefix 26 }

ikeNotification27 NOTIFICATION-TYPE
    OBJECTS { 
              ike27_remote_addr 
            }
    STATUS current
    DESCRIPTION
        "Notification of Event IKE.27

        Message: 'IKE($1)27:--------- No Dir Info in SA ---------'

        Parameters list:
              $1: ike27_remote_addr

        No address information found in SA."
    ::= { ikeNotificationsPrefix 27 }

ikeNotification28 NOTIFICATION-TYPE
    OBJECTS { 
              ike28_remote_addr, 
              ike28_last_id 
            }
    STATUS current
    DESCRIPTION
        "Notification of Event IKE.28

        Message: 'IKE($1)28:--------- Isakmp SA negotiating II (last id 0x$2) ---------'

        Parameters list:
              $1: ike28_remote_addr
              $2: ike28_last_id

        ISAKMP SA commencing phase II negotiation."
    ::= { ikeNotificationsPrefix 28 }

ikeNotification29 NOTIFICATION-TYPE
    OBJECTS { 
              ike29_remote_addr 
            }
    STATUS current
    DESCRIPTION
        "Notification of Event IKE.29

        Message: 'IKE($1)29:--------- Negotiation from banned host stopped ---------'

        Parameters list:
              $1: ike29_remote_addr

        Negotiation from banned host stopped."
    ::= { ikeNotificationsPrefix 29 }

ikeNotification30 NOTIFICATION-TYPE
    OBJECTS { 
              ike30_remote_addr 
            }
    STATUS current
    DESCRIPTION
        "Notification of Event IKE.30

        Message: 'IKE($1)30:--------- DPD Deleting SAs ---------'

        Parameters list:
              $1: ike30_remote_addr

        DPD (Dead Peer Detection) system found a lost connection: deleting SAs."
    ::= { ikeNotificationsPrefix 30 }

ikeNotification31 NOTIFICATION-TYPE
    OBJECTS { 
              ike31_remote_addr 
            }
    STATUS current
    DESCRIPTION
        "Notification of Event IKE.31

        Message: 'IKE($1)31:--------- Max tunnel supported reached ---------'

        Parameters list:
              $1: ike31_remote_addr

        Maximum number of simultaneous tunnels reached."
    ::= { ikeNotificationsPrefix 31 }

ikeNotification32 NOTIFICATION-TYPE
    OBJECTS { 
              ike32_remote_addr 
            }
    STATUS current
    DESCRIPTION
        "Notification of Event IKE.32

        Message: 'IKE($1)32:--------- Renegotiation using DNAT ---------'

        Parameters list:
              $1: ike32_remote_addr

        Renegotiation using DNAT started."
    ::= { ikeNotificationsPrefix 32 }

ikeNotification33 NOTIFICATION-TYPE
    OBJECTS { 
              ike33_remote_addr 
            }
    STATUS current
    DESCRIPTION
        "Notification of Event IKE.33

        Message: 'IKE($1)33:--------- Lifetime changed ---------'

        Parameters list:
              $1: ike33_remote_addr

        SA lifetime counter changed."
    ::= { ikeNotificationsPrefix 33 }

ikeNotification34 NOTIFICATION-TYPE
    OBJECTS { 
              ike34_remote_addr 
            }
    STATUS current
    DESCRIPTION
        "Notification of Event IKE.34

        Message: 'IKE($1)34:--------- Searching Backup Peer ---------'

        Parameters list:
              $1: ike34_remote_addr

        Searching Backup peer."
    ::= { ikeNotificationsPrefix 34 }

ikeNotification35 NOTIFICATION-TYPE
    OBJECTS { 
              ike35_remote_addr, 
              ike35_connection 
            }
    STATUS current
    DESCRIPTION
        "Notification of Event IKE.35

        Message: 'IKE($1)35:--------- Renegotiation Timer for SA NEG expired (connection number $2) ---------'

        Parameters list:
              $1: ike35_remote_addr
              $2: ike35_connection

        Renegotiation Timer for negotiation SA expired."
    ::= { ikeNotificationsPrefix 35 }

ikeNotification36 NOTIFICATION-TYPE
    OBJECTS { 
              ike36_remote_addr 
            }
    STATUS current
    DESCRIPTION
        "Notification of Event IKE.36

        Message: 'IKE($1)36:--------- Local Starting Neg ---------'

        Parameters list:
              $1: ike36_remote_addr

        Local side starting negotiation."
    ::= { ikeNotificationsPrefix 36 }

ikeNotification37 NOTIFICATION-TYPE
    OBJECTS { 
              ike37_remote_addr 
            }
    STATUS current
    DESCRIPTION
        "Notification of Event IKE.37

        Message: 'IKE($1)37:--------- Remote Starting Neg ---------'

        Parameters list:
              $1: ike37_remote_addr

        Remote side starting negotiation."
    ::= { ikeNotificationsPrefix 37 }

ikeNotification38 NOTIFICATION-TYPE
    OBJECTS { 
              ike38_remote_addr 
            }
    STATUS current
    DESCRIPTION
        "Notification of Event IKE.38

        Message: 'IKE($1)38:--------- Local Starting BackUp Neg ---------'

        Parameters list:
              $1: ike38_remote_addr

        Local side starting Backup negotiation."
    ::= { ikeNotificationsPrefix 38 }

ikeNotification39 NOTIFICATION-TYPE
    OBJECTS { 
              ike39_remote_addr 
            }
    STATUS current
    DESCRIPTION
        "Notification of Event IKE.39

        Message: 'IKE($1)39:--------- Remote Starting BackUp Neg ---------'

        Parameters list:
              $1: ike39_remote_addr

        Remote side starting Backup negotiation."
    ::= { ikeNotificationsPrefix 39 }

ikeNotification40 NOTIFICATION-TYPE
    OBJECTS { 
              ike40_remote_addr, 
              ike40_spi 
            }
    STATUS current
    DESCRIPTION
        "Notification of Event IKE.40

        Message: 'IKE($1)40:------!!! CONNECTED spi 0x$2!!!------'

        Parameters list:
              $1: ike40_remote_addr
              $2: ike40_spi

        Tunnel correctly established."
    ::= { ikeNotificationsPrefix 40 }

ikeNotification41 NOTIFICATION-TYPE
    OBJECTS { 
              ike41_remote_addr, 
              ike41_spi 
            }
    STATUS current
    DESCRIPTION
        "Notification of Event IKE.41

        Message: 'IKE($1)41:------!!! DISCONNECTED spi 0x$2!!!------'

        Parameters list:
              $1: ike41_remote_addr
              $2: ike41_spi

        Tunnel disconnected."
    ::= { ikeNotificationsPrefix 41 }

ikeNotification42 NOTIFICATION-TYPE
    OBJECTS { 
              ike42_remote_addr, 
              ike42_message 
            }
    STATUS current
    DESCRIPTION
        "Notification of Event IKE.42

        Message: 'IKE($1): $2'

        Parameters list:
              $1: ike42_remote_addr
              $2: ike42_message

        Unexpected notification from remote side received."
    ::= { ikeNotificationsPrefix 42 }

ikeNotification43 NOTIFICATION-TYPE
    OBJECTS { 
              ike43_remote_addr, 
              ike43_message 
            }
    STATUS current
    DESCRIPTION
        "Notification of Event IKE.43

        Message: 'IKE($1): $2'

        Parameters list:
              $1: ike43_remote_addr
              $2: ike43_message

        Notification from remote side received."
    ::= { ikeNotificationsPrefix 43 }

ikeNotification44 NOTIFICATION-TYPE
    OBJECTS { 
              ike44_spi, 
              ike44_dst_addr,
              ike44_dest_mask,
              ike44_via_gw 
            }
    STATUS current
    DESCRIPTION
        "Notification of Event IKE.44

        Message: 'RRI. SPI 0x$1 dst $2/$3 via $4'

        Parameters list:
              $1: ike44_spi
              $2: ike44_dst_addr
              $3: ike44_dest_mask
              $4: ike44_via_gw

        A new tunnel has opened and the router has established a new static
        route so it can be back-propagated via RIP or OSPF (RRI or Remote
        Route Injection)."
    ::= { ikeNotificationsPrefix 44 }

ikeNotification45 NOTIFICATION-TYPE
    OBJECTS { 
              ike45_spi, 
              ike45_dst_addr,
              ike45_dest_mask,
              ike45_via_gw 
            }
    STATUS current
    DESCRIPTION
        "Notification of Event IKE.45

        Message: 'RRI Problem. SPI 0x$1 dst $2/$3 via $4'

        Parameters list:
              $1: ike45_spi
              $2: ike45_dst_addr
              $3: ike45_dest_mask
              $4: ike45_via_gw

        There was a problem establishing a static route for RRI."
    ::= { ikeNotificationsPrefix 45 }

ikeNotification46 NOTIFICATION-TYPE
    OBJECTS { 
              ike46_spi, 
              ike46_dst_addr,
              ike46_dest_mask,
              ike46_via_gw 
            }
    STATUS current
    DESCRIPTION
        "Notification of Event IKE.46

        Message: 'Clearing RRI. SPI 0x$1, dst $2/$3, via $4'

        Parameters list:
              $1: ike46_spi
              $2: ike46_dst_addr
              $3: ike46_dest_mask
              $4: ike46_via_gw

        RRI has cleared a static route."
    ::= { ikeNotificationsPrefix 46 }

ikeNotification47 NOTIFICATION-TYPE
    OBJECTS { 
              ike47_user_addr, 
              ike47_user_string 
            }
    STATUS current
    DESCRIPTION
        "Notification of Event IKE.47

        Message: 'IKE($1): User $2'

        Parameters list:
              $1: ike47_user_addr
              $2: ike47_user_string

        User is trying authentication."
    ::= { ikeNotificationsPrefix 47 }

ikeNotification48 NOTIFICATION-TYPE
    OBJECTS { 
              ike48_remote_addr, 
              ike48_iniciator,
              ike48_responder,
              ike48_spi 
            }
    STATUS current
    DESCRIPTION
        "Notification of Event IKE.48

        Message: '($1): Ready to open->(Inic=$2, Resp=$3) spi 0x$4'

        Parameters list:
              $1: ike48_remote_addr
              $2: ike48_iniciator
              $3: ike48_responder
              $4: ike48_spi

        Tunnel ready to be established."
    ::= { ikeNotificationsPrefix 48 }

ikeNotification49 NOTIFICATION-TYPE
    OBJECTS { 
              ike49_remote_addr, 
              ike49_iniciator,
              ike49_responder,
              ike49_spi 
            }
    STATUS current
    DESCRIPTION
        "Notification of Event IKE.49

        Message: '($1): Ready to close->(Inic=$2, Resp=$3) spi 0x$4'

        Parameters list:
              $1: ike49_remote_addr
              $2: ike49_iniciator
              $3: ike49_responder
              $4: ike49_spi

        Tunnel ready to be disconneted."
    ::= { ikeNotificationsPrefix 49 }

ikeNotification50 NOTIFICATION-TYPE
    OBJECTS { 
              ike50_address, 
              ike50_idname,
              ike50_protocolnumber,
              ike50_portnumber,
              ike50_idtype 
            }
    STATUS current
    DESCRIPTION
        "Notification of Event IKE.50

        Message: '($1): Text Identification Payload, id $2, protocol $3, port $4, type $5'

        Parameters list:
              $1: ike50_address
              $2: ike50_idname
              $3: ike50_protocolnumber
              $4: ike50_portnumber
              $5: ike50_idtype

        Text Identification Payload registered."
    ::= { ikeNotificationsPrefix 50 }

ikeNotification51 NOTIFICATION-TYPE
    OBJECTS { 
              ike51_address, 
              ike51_idaddress,
              ike51_protocolnumber,
              ike51_portnumber,
              ike51_idtype 
            }
    STATUS current
    DESCRIPTION
        "Notification of Event IKE.51

        Message: '($1): IP Identification Payload, id $2, protocol $3, port $4, type $5'

        Parameters list:
              $1: ike51_address
              $2: ike51_idaddress
              $3: ike51_protocolnumber
              $4: ike51_portnumber
              $5: ike51_idtype

        IP Identification Payload registered."
    ::= { ikeNotificationsPrefix 51 }

ikeNotification52 NOTIFICATION-TYPE
    OBJECTS { 
              ike52_remote_addr, 
              ike52_spi,
              ike52_remote_client 
            }
    STATUS current
    DESCRIPTION
        "Notification of Event IKE.52

        Message: 'IKE($1)52:---------  Connection Event spi 0x$2 remote_client $3 ---------'

        Parameters list:
              $1: ike52_remote_addr
              $2: ike52_spi
              $3: ike52_remote_client

        Periodic information of the established tunnel."
    ::= { ikeNotificationsPrefix 52 }

ikeNotification53 NOTIFICATION-TYPE
    OBJECTS { 
              ike53_remote_addr, 
              ike53_attribute_string 
            }
    STATUS current
    DESCRIPTION
        "Notification of Event IKE.53

        Message: 'IKE($1): $2'

        Parameters list:
              $1: ike53_remote_addr
              $2: ike53_attribute_string

        Attribute string registered"
    ::= { ikeNotificationsPrefix 53 }

ikeNotification54 NOTIFICATION-TYPE
    OBJECTS { 
              ike54_remote_addr, 
              ike54_info_string 
            }
    STATUS current
    DESCRIPTION
        "Notification of Event IKE.54

        Message: 'IKE($1): Info: $2'

        Parameters list:
              $1: ike54_remote_addr
              $2: ike54_info_string

        Information string registered"
    ::= { ikeNotificationsPrefix 54 }

ikeNotification55 NOTIFICATION-TYPE
    OBJECTS { 
              ike55_sa_conn_id, 
              ike55_old_src_port,
              ike55_old_dst_port,
              ike55_new_src_port,
              ike55_new_dst_port 
            }
    STATUS current
    DESCRIPTION
        "Notification of Event IKE.55

        Message: 'UDP Port changed for SA with connid:$1, ($2-$3)=>($4-$5)'

        Parameters list:
              $1: ike55_sa_conn_id
              $2: ike55_old_src_port
              $3: ike55_old_dst_port
              $4: ike55_new_src_port
              $5: ike55_new_dst_port

        There is been a change on the source or destination port for this SA"
    ::= { ikeNotificationsPrefix 55 }

ikeNotification56 NOTIFICATION-TYPE
    OBJECTS { 
              ike56_message, 
              ike56_dst_ip,
              ike56_group 
            }
    STATUS current
    DESCRIPTION
        "Notification of Event IKE.56

        Message: 'GDOI client messsage $1 sent to $2 group $3'

        Parameters list:
              $1: ike56_message
              $2: ike56_dst_ip
              $3: ike56_group

        A GDOI client message has been sent"
    ::= { ikeNotificationsPrefix 56 }

ikeNotification57 NOTIFICATION-TYPE
    OBJECTS { 
              ike57_message, 
              ike57_src_ip,
              ike57_group 
            }
    STATUS current
    DESCRIPTION
        "Notification of Event IKE.57

        Message: 'GDOI client messsage $1 received from $2 group $3'

        Parameters list:
              $1: ike57_message
              $2: ike57_src_ip
              $3: ike57_group

        A GDOI client message has been received"
    ::= { ikeNotificationsPrefix 57 }

ikeNotification58 NOTIFICATION-TYPE
    OBJECTS { 
              ike58_message, 
              ike58_dst_ip,
              ike58_group 
            }
    STATUS current
    DESCRIPTION
        "Notification of Event IKE.58

        Message: 'GDOI server messsage $1 sent to $2 group $3'

        Parameters list:
              $1: ike58_message
              $2: ike58_dst_ip
              $3: ike58_group

        A GDOI server message has been sent"
    ::= { ikeNotificationsPrefix 58 }

ikeNotification59 NOTIFICATION-TYPE
    OBJECTS { 
              ike59_message, 
              ike59_src_ip,
              ike59_group 
            }
    STATUS current
    DESCRIPTION
        "Notification of Event IKE.59

        Message: 'GDOI server messsage $1 rcvd from $2 group $3'

        Parameters list:
              $1: ike59_message
              $2: ike59_src_ip
              $3: ike59_group

        A GDOI server message has been sent"
    ::= { ikeNotificationsPrefix 59 }

ikeNotification60 NOTIFICATION-TYPE
    OBJECTS { 
              ike60_error 
            }
    STATUS current
    DESCRIPTION
        "Notification of Event IKE.60

        Message: 'GDOI client error: $1'

        Parameters list:
              $1: ike60_error

        A GDOI client error"
    ::= { ikeNotificationsPrefix 60 }

ikeNotification61 NOTIFICATION-TYPE
    OBJECTS { 
              ike61_error 
            }
    STATUS current
    DESCRIPTION
        "Notification of Event IKE.61

        Message: 'GDOI server error: $1'

        Parameters list:
              $1: ike61_error

        A GDOI server error"
    ::= { ikeNotificationsPrefix 61 }

ikeNotification62 NOTIFICATION-TYPE
    OBJECTS { 
              ike62_spi, 
              ike62_srIP,
              ike62_dstIP,
              ike62_prot,
              ike62_sport,
              ike62_dport 
            }
    STATUS current
    DESCRIPTION
        "Notification of Event IKE.62

        Message: 'GDOI client acl added spi $1 src $2 dst $3 prot $4 sport $5 dport $6'

        Parameters list:
              $1: ike62_spi
              $2: ike62_srIP
              $3: ike62_dstIP
              $4: ike62_prot
              $5: ike62_sport
              $6: ike62_dport

        A GDOI client has added a new acl"
    ::= { ikeNotificationsPrefix 62 }

ikeNotification63 NOTIFICATION-TYPE
    OBJECTS { 
              ike63_spi, 
              ike63_lifetime 
            }
    STATUS current
    DESCRIPTION
        "Notification of Event IKE.63

        Message: 'GDOI client SAs created spi $1 lifetime $2'

        Parameters list:
              $1: ike63_spi
              $2: ike63_lifetime

        A GDOI client has created new in out sas"
    ::= { ikeNotificationsPrefix 63 }

ikeNotification64 NOTIFICATION-TYPE
    OBJECTS { 
              ike64_ic_lo, 
              ike64_ic_hi,
              ike64_rc_lo,
              ike64_rc_hi,
              ike64_nic_lo,
              ike64_nic_hi,
              ike64_nr_lo,
              ike64_nr_hi 
            }
    STATUS current
    DESCRIPTION
        "Notification of Event IKE.64

        Message: 'GDOI rekey ini:0x$1$2 res:0x$3$4 to ini:0x$5$6 res:0x$7$8'

        Parameters list:
              $1: ike64_ic_lo
              $2: ike64_ic_hi
              $3: ike64_rc_lo
              $4: ike64_rc_hi
              $5: ike64_nic_lo
              $6: ike64_nic_hi
              $7: ike64_nr_lo
              $8: ike64_nr_hi

        A client rekey"
    ::= { ikeNotificationsPrefix 64 }

ikeNotification65 NOTIFICATION-TYPE
    OBJECTS { 
              ike65_ic_lo, 
              ike65_ic_hi,
              ike65_rc_lo,
              ike65_rc_hi,
              ike65_nic_lo,
              ike65_nic_hi,
              ike65_nr_lo,
              ike65_nr_hi 
            }
    STATUS current
    DESCRIPTION
        "Notification of Event IKE.65

        Message: 'GDOI server rekey ini:0x$1$2 res:0x$3$4 to ini:0x$5$6 res:0x$7$8'

        Parameters list:
              $1: ike65_ic_lo
              $2: ike65_ic_hi
              $3: ike65_rc_lo
              $4: ike65_rc_hi
              $5: ike65_nic_lo
              $6: ike65_nic_hi
              $7: ike65_nr_lo
              $8: ike65_nr_hi

        A server rekey"
    ::= { ikeNotificationsPrefix 65 }

ikeNotification66 NOTIFICATION-TYPE
    OBJECTS { 
              ike66_ic_lo, 
              ike66_ic_hi,
              ike66_rc_lo,
              ike66_rc_hi,
              ike66_nic_lo,
              ike66_nic_hi,
              ike66_nr_lo,
              ike66_nr_hi 
            }
    STATUS current
    DESCRIPTION
        "Notification of Event IKE.66

        Message: 'GDOI server new ids ini:0x$1$2 res:0x$3$4 to ini:0x$5$6 res:0x$7$8'

        Parameters list:
              $1: ike66_ic_lo
              $2: ike66_ic_hi
              $3: ike66_rc_lo
              $4: ike66_rc_hi
              $5: ike66_nic_lo
              $6: ike66_nic_hi
              $7: ike66_nr_lo
              $8: ike66_nr_hi

        Server has generated new ids"
    ::= { ikeNotificationsPrefix 66 }

ikeNotification67 NOTIFICATION-TYPE
    OBJECTS { 
              ike67_spi, 
              ike67_size 
            }
    STATUS current
    DESCRIPTION
        "Notification of Event IKE.67

        Message: 'GDOI client tek payload received spi $1 size $2'

        Parameters list:
              $1: ike67_spi
              $2: ike67_size

        client is processing a tek payload"
    ::= { ikeNotificationsPrefix 67 }

ikeNotification68 NOTIFICATION-TYPE
    OBJECTS { 
              ike68_spi, 
              ike68_reason 
            }
    STATUS current
    DESCRIPTION
        "Notification of Event IKE.68

        Message: 'GDOI client sa $1 deleted, reason $2'

        Parameters list:
              $1: ike68_spi
              $2: ike68_reason

        client is deleting and old sa"
    ::= { ikeNotificationsPrefix 68 }

ikeNotification69 NOTIFICATION-TYPE
    OBJECTS { 
              ike69_rcvd_or_sent, 
              ike69_timestam,
              ike69_diff 
            }
    STATUS current
    DESCRIPTION
        "Notification of Event IKE.69

        Message: 'GDOI timestamp $1: $2 server diff $3'

        Parameters list:
              $1: ike69_rcvd_or_sent
              $2: ike69_timestam
              $3: ike69_diff

        timestamp rcvd or sent"
    ::= { ikeNotificationsPrefix 69 }

ikeNotification70 NOTIFICATION-TYPE
    OBJECTS { 
              ike70_host_addr 
            }
    STATUS current
    DESCRIPTION
        "Notification of Event IKE.70

        Message: 'DNS request: $1'

        Parameters list:
              $1: ike70_host_addr

        Doing a DNS request"
    ::= { ikeNotificationsPrefix 70 }

ikeNotification71 NOTIFICATION-TYPE
    OBJECTS { 
              ike71_host_addr, 
              ike71_IP_addr 
            }
    STATUS current
    DESCRIPTION
        "Notification of Event IKE.71

        Message: 'DNS reply: $1 ($2)'

        Parameters list:
              $1: ike71_host_addr
              $2: ike71_IP_addr

        DNS reply"
    ::= { ikeNotificationsPrefix 71 }

ikeNotification72 NOTIFICATION-TYPE
    OBJECTS { 
              ike72_host_addr, 
              ike72_error_code 
            }
    STATUS current
    DESCRIPTION
        "Notification of Event IKE.72

        Message: 'DNS ERROR for $1 (CODE: $2)'

        Parameters list:
              $1: ike72_host_addr
              $2: ike72_error_code

        DNS ERROR "
    ::= { ikeNotificationsPrefix 72 }

ikeNotification73 NOTIFICATION-TYPE
    OBJECTS { 
              ike73_IP_addr, 
              ike73_host_addr,
              ike73_ttr 
            }
    STATUS current
    DESCRIPTION
        "Notification of Event IKE.73

        Message: 'DNS IKE cache: Using $1 for $2 (Time to renegotiation < $3)'

        Parameters list:
              $1: ike73_IP_addr
              $2: ike73_host_addr
              $3: ike73_ttr

        There is an IP address for this domain in the domain list"
    ::= { ikeNotificationsPrefix 73 }

ikeNotification74 NOTIFICATION-TYPE
    OBJECTS { 
              ike74_IP_addr, 
              ike74_host_addr,
              ike74_ttr 
            }
    STATUS current
    DESCRIPTION
        "Notification of Event IKE.74

        Message: 'DNS IKE cache: $1 assigned for $2 (Time to renegotiation $3)'

        Parameters list:
              $1: ike74_IP_addr
              $2: ike74_host_addr
              $3: ike74_ttr

        There is a new IP/domain in the domain list"
    ::= { ikeNotificationsPrefix 74 }

ikeNotification75 NOTIFICATION-TYPE
    OBJECTS { 
              ike75_host_addr, 
              ike75_IP_addr 
            }
    STATUS current
    DESCRIPTION
        "Notification of Event IKE.75

        Message: 'DNS IKE cache: Purgetime expired. $1 ($2) deleted'

        Parameters list:
              $1: ike75_host_addr
              $2: ike75_IP_addr

        The entry DOMAIN/IP will be removed"
    ::= { ikeNotificationsPrefix 75 }


END
