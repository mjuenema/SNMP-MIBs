--******************************************************************************
--
--	TELDAT, SA.
--
--	Parque Tecnologico de Madrid
--	Tres Cantos
--	28760 MADRID
--	Tlf: +34-918076565
--  Fax: +34-918076521
--  E-mail: id@teldat.es
--
--******************************************************************************
--
--	MIB privada del router maestro GPRS (Despertado)
--
--******************************************************************************
--	HISTORIAL:
-- 1.1  11-01-13    E. Amorena      XH 2610. MIBs compilation.
--	1.0	01/07/04	J. Molina	Archivo de procedente de mng_gprs.mib
--
--
--
--
--	HISTORIAL de mng_gprs.mib
--
--   Ver     Fecha       Autor           Comentario
-- ======= =========== =============== ========================================
--  1.0     08/10/03    Benjam�n G.     Codificacion inicial.
--
--******************************************************************************

TELDAT-MASTER-GPRS-MIB DEFINITIONS ::= BEGIN

IMPORTS
	DisplayString			FROM RFC1213-MIB
	telproducts				FROM TELDAT-MIB
	OBJECT-TYPE			FROM RFC-1212;

	mstrGprsRouter OBJECT IDENTIFIER ::= { telproducts 78 }


	mstrGprsDial OBJECT-TYPE
		SYNTAX 	DisplayString(SIZE(20))
		ACCESS 	read-write
		STATUS 	mandatory
		DESCRIPTION
		"Phone number for GSM wake up dialling. Router dialling this number at 
		 command arrives. An error response indicates facility not 
		 supported or dialling already in progress"
		 ::={ mstrGprsRouter 1 }

	mstrGprsAbort OBJECT-TYPE
		SYNTAX 	INTEGER
		        {
                    abort(1)
				}
		ACCESS 	read-write
		STATUS 	mandatory
		DESCRIPTION
		"Abort wake up dialling in progress. "
		 ::={ mstrGprsRouter 2 }

	mstrGprsStatus OBJECT-TYPE
		SYNTAX 	INTEGER
				{ 
                    unavailable(0),
                    call_error(1),
                    loss_coverage(2),
                    user_abort(3),
                    in_progress(4),
                    remote_answer(5),
                    busy(6),
                    no_dial_tone(7),
                    no_carrier(8),
                    normal_clear(9)
            }
		ACCESS 	read-only
		STATUS 	mandatory
		DESCRIPTION
		"Last dialling wake up process status. "
		 ::={ mstrGprsRouter 3 }

END
