HP-SNTPCLIENTCONFIGURATION-MIB DEFINITIONS ::= BEGIN

   IMPORTS
      OBJECT-TYPE, MODULE-IDENTITY, Counter32, IpAddress, Integer32,
      Unsigned32
         FROM SNMPv2-SMI
      RowStatus, TruthValue
         FROM SNMPv2-TC
      OBJECT-GROUP, MODULE-COMPLIANCE
         FROM SNMPv2-CONF
      hpicfCommon
         FROM HP-ICF-OID 
      InetAddressType, InetAddress
         FROM INET-ADDRESS-MIB;

   hpSntpConfigMod MODULE-IDENTITY
      LAST-UPDATED "201401130000Z"  -- January 13, 2014      
      ORGANIZATION "HP Networking"
      CONTACT-INFO "Hewlett-Packard Company
                    8000 Foothills Blvd.
                    Roseville, CA 95747"
      DESCRIPTION  "Management information for configuring the SNTP client
                    on Hewlett-Packard network devices."

      REVISION     "201401130000Z"  -- January 13, 2014
      DESCRIPTION  "Added dhcp enumeration to hpSntpConfigMode"

      REVISION     "201102120000Z"  -- February 12, 2011
      DESCRIPTION  "Added hpSntpAuthenticationKeyEncrypted object in
                    hpSntpAuthenticationKeyTable."

      REVISION     "200902131230Z"  -- February 13, 2009
      DESCRIPTION  "Increased the range of 'hpSntpInetServerAuthKeyId' and
                    'hpSntpAuthenticationKeyId' MIB objects."
      
      REVISION     "200902101539Z"  -- February 10, 2009
      DESCRIPTION  "Added 'hpSntpInetServerIsOobm' MIB object
                    in 'hpSntpInetServersTable' table."
   
      REVISION     "200811260239Z"  -- November 26 2008  
      DESCRIPTION  "Added Objects for supporting Authentication in 
                    unicast and broadcast mode."

      REVISION     "200011030239Z"  -- November 3, 2000
      DESCRIPTION  "Initial version of the MIB module."

      ::= { hpicfCommon 8 }

   hpSntpConfig        OBJECT IDENTIFIER ::= { hpSntpConfigMod 1 }
   hpTimeSyncMethodMod OBJECT IDENTIFIER ::= { hpSntpConfigMod 2 }
   hpSntpStatistics    OBJECT IDENTIFIER ::= { hpSntpConfigMod 4 }

-- ----------------------------------------------------------------------   
-- Global TimeSyncMethod
-- ----------------------------------------------------------------------
  
   hpTimeSyncMethod OBJECT-TYPE
      SYNTAX      INTEGER {
                      none(1),
                      sntp(2),
                      timep(3),
                      timepOrSntp(4)
                  }
      MAX-ACCESS  read-write
      STATUS      current
      DESCRIPTION "Method to be used for time synchronization."
      ::= { hpTimeSyncMethodMod 1 }

-- ----------------------------------------------------------------------  
-- SNTP Statistics data 
-- ----------------------------------------------------------------------   

   hpSntpStatsRcvdPkts OBJECT-TYPE
     SYNTAX       Counter32
     MAX-ACCESS   read-only
     STATUS       current
     DESCRIPTION  "Total number of packets received."
     ::= { hpSntpStatistics 1 }

   hpSntpStatsSentPkts OBJECT-TYPE
     SYNTAX       Counter32
     MAX-ACCESS   read-only
     STATUS       current
     DESCRIPTION  "Total number of packets sent to the server"
     ::= { hpSntpStatistics 2}

   hpSntpStatsDroppedPkts OBJECT-TYPE
     SYNTAX       Counter32
     MAX-ACCESS   read-only
     STATUS       current
     DESCRIPTION  "Total number of packets dropped due to error."
     ::= { hpSntpStatistics 3}


-- ----------------------------------------------------------------------   
-- SNTP client configuration parameters
-- ----------------------------------------------------------------------
      
   hpSntpConfigMode OBJECT-TYPE
      SYNTAX      INTEGER {
                      disabled(1),
                      unicast(2),
                      broadcast(3),
                      dhcp(4)
                  }
      MAX-ACCESS  read-write
      STATUS      current
      DESCRIPTION "Current operational mode of SNTP client"
      ::= { hpSntpConfig 1 }

   hpSntpConfigPollInterval OBJECT-TYPE
      SYNTAX      Integer32 (30..65535)
      MAX-ACCESS  read-write
      STATUS      current
      DESCRIPTION "Period of time (in seconds) between successive attempts to
                  perform an update via SNTP"
      ::= { hpSntpConfig 2 }

-- ----------------------------------------------------------------------
-- Table for configuring Servers
-- ----------------------------------------------------------------------

   hpSntpConfigServerTable OBJECT-TYPE
      SYNTAX      SEQUENCE OF HpSntpServerEntry
      MAX-ACCESS  not-accessible
      STATUS      deprecated
      DESCRIPTION "### DEPRECATED ### A table containing trusted SNTP servers 
                  to be queried in unicast mode"
      ::= { hpSntpConfig 3 }

   hpSntpServerEntry OBJECT-TYPE
      SYNTAX      HpSntpServerEntry
      MAX-ACCESS  not-accessible
      STATUS      deprecated
      DESCRIPTION "### DEPRECATED ### A trusted server and its expected version 
                  number"
      INDEX       { hpSntpServerAddress }
      ::= { hpSntpConfigServerTable 1 }

   HpSntpServerEntry ::=
      SEQUENCE {
         hpSntpServerAddress        IpAddress,
         hpSntpServerVersion        Integer32,
         hpSntpServerPriority       Integer32,
         hpSntpServerRowStatus      RowStatus
      }
      
   hpSntpServerAddress OBJECT-TYPE
      SYNTAX      IpAddress
      MAX-ACCESS  not-accessible
      STATUS      deprecated
      DESCRIPTION "### DEPRECATED ### Ip Address of a trusted SNTP server."
      ::= { hpSntpServerEntry 1 }

   hpSntpServerVersion OBJECT-TYPE
      SYNTAX      Integer32 (1..7)
      MAX-ACCESS  read-create
      STATUS      deprecated
      DESCRIPTION "### DEPRECATED ### Protocol version used by this SNTP server"
      ::= { hpSntpServerEntry 2 }

   hpSntpServerPriority OBJECT-TYPE
      SYNTAX      Integer32 (1..65535)
      MAX-ACCESS  read-create
      STATUS      deprecated
      DESCRIPTION "### DEPRECATED ### Priority given to this server."
      ::= { hpSntpServerEntry 3 }

   hpSntpServerRowStatus OBJECT-TYPE
      SYNTAX      RowStatus
      MAX-ACCESS  read-create
      STATUS      deprecated
      DESCRIPTION "### DEPRECATED ### The Status of this SNTP server information."
      ::= { hpSntpServerEntry 4 }

   hpSntpInetConfigServerTable OBJECT-TYPE
      SYNTAX      SEQUENCE OF HpSntpInetServerEntry
      MAX-ACCESS  not-accessible
      STATUS      current
      DESCRIPTION "A table containing trusted IPv4 and IPv6 SNTP servers to be 
                   queried in unicast mode"
      ::= { hpSntpConfig 4 }

   hpSntpInetServerEntry OBJECT-TYPE
      SYNTAX       HpSntpInetServerEntry
      MAX-ACCESS  not-accessible
      STATUS      current
      DESCRIPTION "A trusted server and its expected version number and priority"
      INDEX       { hpSntpInetServerPriority,
                    hpSntpInetServerAddressType,
                    hpSntpInetServerAddress
                  }
      ::= { hpSntpInetConfigServerTable 1 }

   HpSntpInetServerEntry ::=
      SEQUENCE {
         hpSntpInetServerPriority       Integer32,
         hpSntpInetServerAddressType    InetAddressType,
         hpSntpInetServerAddress        InetAddress,         
         hpSntpInetServerVersion        Integer32,
         hpSntpInetServerRowStatus      RowStatus,
         hpSntpInetServerIsOobm         TruthValue,
         hpSntpInetServerAuthKeyId      Unsigned32
      }
      
   hpSntpInetServerPriority OBJECT-TYPE
      SYNTAX      Integer32 (1..65535)
      MAX-ACCESS  not-accessible
      STATUS      current
      DESCRIPTION "Priority given to this server."
      ::= { hpSntpInetServerEntry 1 }

   hpSntpInetServerAddressType OBJECT-TYPE
      SYNTAX      InetAddressType
      MAX-ACCESS  not-accessible
      STATUS      current
      DESCRIPTION "Ip Address type of a trusted SNTP server."
      ::= { hpSntpInetServerEntry 2 }

   hpSntpInetServerAddress OBJECT-TYPE
      SYNTAX      InetAddress
      MAX-ACCESS  not-accessible
      STATUS      current
      DESCRIPTION "Ip Address (of a trusted SNTP server) to which this entry's
                   addressing information pertains. hpSntpInetServerAddress is 
                   always interpreted within the context of     
                   hpSntpInetServerAddressType"
      ::= { hpSntpInetServerEntry 3 }

   hpSntpInetServerVersion OBJECT-TYPE
      SYNTAX      Integer32 (1..7)
      MAX-ACCESS  read-create
      STATUS      current
      DESCRIPTION "Protocol version used by this SNTP server"
      ::= { hpSntpInetServerEntry 4 }

   hpSntpInetServerRowStatus OBJECT-TYPE
      SYNTAX      RowStatus
      MAX-ACCESS  read-create
      STATUS      current
      DESCRIPTION "The Status of this SNTP server information."
      ::= { hpSntpInetServerEntry 5 }

   hpSntpInetServerIsOobm OBJECT-TYPE
      SYNTAX      TruthValue
      MAX-ACCESS  read-create
      STATUS      current
      DESCRIPTION "This object indicates whether this SNTP Server
                  is reachable over OOBM (Out Of Band Management)
                  interface or not. This mib object will be applicable
                  only if there is a physical OOBM port on the device."
      DEFVAL      {false}
      ::= { hpSntpInetServerEntry 6 }

   hpSntpInetServerAuthKeyId OBJECT-TYPE
      SYNTAX      Unsigned32 (0..4294967295)  
      MAX-ACCESS  read-create
      STATUS      current
      DESCRIPTION "The key identifier associated with the
                   SNTP server specified by this instance.Its an index
                   to the  hpSntpAuthenticationKeyTable.The value identifies 
                   the row in the hpSntpAuthenticationKeyTable where the 
                   authentication key can be found. The value '0' indicates
                   that the key Id is disassociated from the SNTP server."                  
      ::= { hpSntpInetServerEntry 7 }
    
-- --------------------------------------------------------------------------
-- SNTP client authentication parameters
-- --------------------------------------------------------------------------
   hpSntpAuthentication OBJECT-TYPE
      SYNTAX      INTEGER {
                      enabled (1),
                      disabled (2)
                  }
      MAX-ACCESS  read-write
      STATUS      current
      DESCRIPTION "This object is used to enable or disable SNTP 
                   authentication in the switch.By default authentication 
                   is disabled.Atleast one Key-id and it has to be trusted
                   to enable authentication."
      ::= { hpSntpConfig 5 }

-- -------------------------------------------------------------------------
-- SNTP server Authentication table 
-- --------------------------------------------------------------------------
   hpSntpAuthenticationKeyTable OBJECT-TYPE
     SYNTAX SEQUENCE OF HpSntpAuthenticationKeyEntry
     MAX-ACCESS   not-accessible
     STATUS       current
     DESCRIPTION "A table containing entries of authentication key-id.
                  The number of Key-id is restricted to 8 currently."
     ::= { hpSntpConfig 6 }

   hpSntpAuthenticationKeyEntry OBJECT-TYPE
     SYNTAX      HpSntpAuthenticationKeyEntry
     MAX-ACCESS  not-accessible
     STATUS      current
     DESCRIPTION "An authentication key entry comprising key-identifiers 
                  such as key-id, key-value, authentication mode(MD5),
                  and status of the key-id if it is trusted or not."
     INDEX        {  hpSntpAuthenticationKeyId }
     ::= { hpSntpAuthenticationKeyTable 1 }

   HpSntpAuthenticationKeyEntry ::= 
     SEQUENCE {
        hpSntpAuthenticationKeyId        Unsigned32,
        hpSntpAuthenticationKeyAuthMode  INTEGER,
        hpSntpAuthenticationKeyValue     OCTET STRING,
        hpSntpAuthenticationKeyTrusted   TruthValue,
        hpSntpAuthenticationKeyRowStatus RowStatus,
        hpSntpAuthenticationKeyEncrypted OCTET STRING
     }

   hpSntpAuthenticationKeyId OBJECT-TYPE
     SYNTAX      Unsigned32 (1..4294967295) 
     MAX-ACCESS  not-accessible 
     STATUS      current
     DESCRIPTION "A unique identifier for the authentication key."
     ::= { hpSntpAuthenticationKeyEntry 1 }

   hpSntpAuthenticationKeyAuthMode OBJECT-TYPE
     SYNTAX      INTEGER {
                     none(1),
                     md5(2)
                 }
     MAX-ACCESS  read-create
     STATUS      current
     DESCRIPTION "The authentication mode supported for this key."
     DEFVAL       { none }  --no keyvalue by default
     ::= { hpSntpAuthenticationKeyEntry 2 }

   hpSntpAuthenticationKeyValue OBJECT-TYPE
     SYNTAX      OCTET STRING (SIZE(1..32))
     MAX-ACCESS  read-create
     STATUS      current
     DESCRIPTION "A unique string that serves as the key-value for generating 
                  the message digest sent in the SNTP packet. A read on 
                  this object will return a Empty string."
     ::= { hpSntpAuthenticationKeyEntry 3 }

   hpSntpAuthenticationKeyTrusted OBJECT-TYPE
     SYNTAX      TruthValue
     MAX-ACCESS  read-create
     STATUS      current
     DESCRIPTION "This object is used to configure the status of the 
                  authentication key as trusted.If the key-value is
                  not trusted then the packet is not trusted. By default
                  the key-value is not trusted."
     ::= { hpSntpAuthenticationKeyEntry 4 }

   hpSntpAuthenticationKeyRowStatus OBJECT-TYPE
     SYNTAX       RowStatus
     MAX-ACCESS   read-create
     STATUS       current
     DESCRIPTION "The row status for this SNTP authentication
                  key instance. The Key-id is the index and 
                  it cannot be edited."
     ::= { hpSntpAuthenticationKeyEntry 5 }

   hpSntpAuthenticationKeyEncrypted OBJECT-TYPE
      SYNTAX      OCTET STRING (SIZE(0..256))
      MAX-ACCESS  read-create
      STATUS      current
      DESCRIPTION "The encrypted form of a unique string that serves as the
                   key-value for generating the message digest sent in the
                   SNTP packet. This object may only be read or written when
                   hpSwitchAuthenticationEncryptCredentialsMethod is set to
                   a value other than none(0). At most one of
                   hpSntpAuthenticationKey and
                   hpSntpAuthenticationKeyEncrypted may be set in any
                   transaction.  This object should only be written with
                   an encrypted key previously read from a compatible
                   HP Networking device."
      ::= { hpSntpAuthenticationKeyEntry 6 }

-- --------------------------------------------------------------------------
-- SNTP UNICAST statistics table 
-- --------------------------------------------------------------------------
   hpSntpServerStatisticsTable OBJECT-TYPE
     SYNTAX      SEQUENCE OF HpSntpServerStatisticsEntry
     MAX-ACCESS  not-accessible
     STATUS      current
     DESCRIPTION "A table containing a list of statistics entries per SNTP
                  server."
     ::= { hpSntpConfig 7 }

   hpSntpServerStatisticsEntry OBJECT-TYPE
     SYNTAX      HpSntpServerStatisticsEntry
     MAX-ACCESS  not-accessible
     STATUS      current
     DESCRIPTION "A statistics entry per SNTP server." 
     AUGMENTS {hpSntpInetServerEntry}
     ::= { hpSntpServerStatisticsTable 1 }


   HpSntpServerStatisticsEntry ::=
      SEQUENCE {
         hpSntpServerStatisticsAuthFailedPkts Counter32
      }
  
   hpSntpServerStatisticsAuthFailedPkts OBJECT-TYPE
    SYNTAX      Counter32
    MAX-ACCESS  read-only
    STATUS      current
    DESCRIPTION "This object indicates the number of packets
                 that have failed the authentication check with 
                 this server instance."
    ::= { hpSntpServerStatisticsEntry 1 }


-- --------------------------------------------------------------------------
-- SNTP BROADCAST parameters 
-- --------------------------------------------------------------------------
   hpSntpBroadcastServerTable OBJECT-TYPE
     SYNTAX      SEQUENCE OF HpSntpBroadcastServerEntry
     MAX-ACCESS  not-accessible
     STATUS      current
     DESCRIPTION "A table containing a SNTP broadcast server and statistics
                  information."
     ::= { hpSntpConfig 8 }

   hpSntpBroadcastServerEntry OBJECT-TYPE
     SYNTAX      HpSntpBroadcastServerEntry
     MAX-ACCESS  not-accessible
     STATUS      current
     DESCRIPTION "An entry comprising a preferred broadcast server address
                  and statistics information with respect to server."
     INDEX {
                 hpSntpBroadcastServerAddress     
           }
   ::= { hpSntpBroadcastServerTable 1 }

   HpSntpBroadcastServerEntry ::= 
      SEQUENCE {
         hpSntpBroadcastServerAddress  IpAddress,
         hpSntpBroadcastServerStatisticsAuthFailedPkts Counter32 
      }

   hpSntpBroadcastServerAddress OBJECT-TYPE
      SYNTAX      IpAddress
      MAX-ACCESS  not-accessible 
      STATUS      current 
      DESCRIPTION "IP Address of a preferred broadcast SNTP server."
      ::= { hpSntpBroadcastServerEntry 1 }

   hpSntpBroadcastServerStatisticsAuthFailedPkts OBJECT-TYPE
      SYNTAX      Counter32
      MAX-ACCESS  read-only
      STATUS      current
      DESCRIPTION "This object indicates the number of packets that have
                   failed the authentication check with this server instance."
      ::= { hpSntpBroadcastServerEntry 2 }


-- --------------------------------------------------------------------------
-- Compliance Information
-- --------------------------------------------------------------------------
   
   hpSntpConfigConformance
      OBJECT IDENTIFIER ::= { hpSntpConfigMod 3 }

   hpSntpConfigCompliances
      OBJECT IDENTIFIER ::= { hpSntpConfigConformance 1 }

   hpSntpConfigGroups
      OBJECT IDENTIFIER ::= { hpSntpConfigConformance 2 }

   hpSntpConfigCompliance MODULE-COMPLIANCE
      STATUS         deprecated
      DESCRIPTION    "###DEPRECATED###The compliance statement for devices 
                      implementing
                     the hpSntpConfig MIB."
      MODULE
      MANDATORY-GROUPS  { hpSntpConfigGroup }

      GROUP             hpSntpServerConfigGroup
      DESCRIPTION       "This group is optional if a device implements
                         the SNTP client in broadcast mode only."

      GROUP             hpTimeSyncMethodGroup
      DESCRIPTION       "Implementation of this group is mandatory for
                         devices that implement multiple time
                         synchronization protocols."
      ::= { hpSntpConfigCompliances 1 }

   hpSntpInetConfigCompliance MODULE-COMPLIANCE
      STATUS           current
      DESCRIPTION      "The compliance statement for devices implementing
                        the hpSntpConfig MIB."
      MODULE
      MANDATORY-GROUPS  { hpSntpConfigGroup }

      GROUP             hpSntpInetServerConfigGroup
      DESCRIPTION       "This group is optional if a device implements
                         the SNTP client in broadcast mode only."

      GROUP             hpTimeSyncMethodGroup
      DESCRIPTION       "Implementation of this group is mandatory for
                         devices that implement multiple time
                         synchronization protocols."
      ::= { hpSntpConfigCompliances 2 }
  
   hpSntpAuthenticationConfigCompliance MODULE-COMPLIANCE
       STATUS           deprecated
       DESCRIPTION      "### DEPRECATED ###
                         The compliance statement for devices implementing
                         the hpSntpConfig MIB."
      
       MODULE
       MANDATORY-GROUPS   {  hpSntpInetServerConfigGroup }
 
       GROUP              hpSntpAuthenticationKeyIdConfigGroup
       DESCRIPTION        "This group is required if a device implements
                           the SNTP client in broadcast mode only."
       ::= { hpSntpConfigCompliances 3 }

   hpSntpInetConfigComplianceOobm MODULE-COMPLIANCE
      STATUS         current
      DESCRIPTION    "The compliance statement for devices implementing the
                     HP SNTP MIB with OOBM support"
      MODULE

         GROUP             hpSntpInetServerOobmGroup
         DESCRIPTION       "A collection of objects for configuring
                           SNTP with OOBM."
      ::= { hpSntpConfigCompliances 4 }

   hpSntpAuthenticationConfigCompliance1 MODULE-COMPLIANCE
       STATUS           current
       DESCRIPTION      "The compliance statement for devices implementing
                         the hpSntpConfig MIB."
      
       MODULE
       MANDATORY-GROUPS   {  hpSntpInetServerConfigGroup }
 
       GROUP              hpSntpAuthenticationKeyIdConfigGroup1
       DESCRIPTION        "This group is required if a device implements
                           the SNTP client in broadcast mode only."
       ::= { hpSntpConfigCompliances 5 }

   hpSntpBroadcastServerCompliance MODULE-COMPLIANCE
      STATUS         current
      DESCRIPTION    "The compliance statement for devices implementing the
                     HP SNTP broadcast server support"
      MODULE
      GROUP             hpSntpBroadcastServerGroup 
      DESCRIPTION       "A collection of objects for preferred 
                          SNTP broadcast server and statistics."
      ::= { hpSntpConfigCompliances 6 }

   hpSntpConfigGroup OBJECT-GROUP
      OBJECTS     { hpSntpConfigMode,
                    hpSntpConfigPollInterval }
      STATUS      current
      DESCRIPTION "A collection of objects for configuring the SNTP
                  client."
      ::= { hpSntpConfigGroups 1 }

   hpSntpServerConfigGroup OBJECT-GROUP
      OBJECTS     { hpSntpServerVersion,
                    hpSntpServerPriority,
                    hpSntpServerRowStatus }
      STATUS      deprecated
      DESCRIPTION "### DEPRECATED ###This Group defines a server table entry."
      ::= { hpSntpConfigGroups 2 }

  hpTimeSyncMethodGroup OBJECT-GROUP
     OBJECTS     { hpTimeSyncMethod }
     STATUS      current
     DESCRIPTION "A collection of objects for selecting a time
                 synchronization protocol to use."
     ::= { hpSntpConfigGroups 3 }

   hpSntpInetServerConfigGroup OBJECT-GROUP
      OBJECTS     { hpSntpInetServerVersion,
                    hpSntpInetServerRowStatus }
      STATUS      current
      DESCRIPTION "This Group defines a server table entry."
      ::= { hpSntpConfigGroups 4 }

   hpSntpAuthenticationKeyIdConfigGroup OBJECT-GROUP
      OBJECTS   { 
                  hpSntpAuthenticationKeyAuthMode,
                  hpSntpAuthenticationKeyValue,
                  hpSntpAuthenticationKeyTrusted,
                  hpSntpAuthenticationKeyRowStatus,
                  hpSntpServerStatisticsAuthFailedPkts,
                  hpSntpStatsDroppedPkts,
                  hpSntpStatsSentPkts,
                  hpSntpStatsRcvdPkts,
                  hpSntpAuthentication,
                  hpSntpInetServerAuthKeyId 
                }
      STATUS      deprecated
      DESCRIPTION "### DEPRECATED ###
                    This group defines SNTP authentication related information.
                    It includes  Key-Identifier, Key-Value, flag to indicate
                    whether the information is trusted or not and authentication
                    mode(MD5) currently supported."
      ::= { hpSntpConfigGroups 5 }

   hpSntpInetServerOobmGroup OBJECT-GROUP
      OBJECTS     { hpSntpInetServerIsOobm }
      STATUS      current
      DESCRIPTION "A collection of objects for configuring the
                   SNTP server entry with support for OOBM
                   (Out of Band Management) interface."
      ::= { hpSntpConfigGroups 6 }

   hpSntpAuthenticationKeyIdConfigGroup1 OBJECT-GROUP
      OBJECTS   { 
                  hpSntpAuthenticationKeyAuthMode,
                  hpSntpAuthenticationKeyValue,
                  hpSntpAuthenticationKeyEncrypted,
                  hpSntpAuthenticationKeyTrusted,
                  hpSntpAuthenticationKeyRowStatus,
                  hpSntpServerStatisticsAuthFailedPkts,
                  hpSntpStatsDroppedPkts,
                  hpSntpStatsSentPkts,
                  hpSntpStatsRcvdPkts,
                  hpSntpAuthentication,
                  hpSntpInetServerAuthKeyId 
                }
      STATUS      current
      DESCRIPTION "This group defines SNTP authentication related information.
                   It includes  Key-Identifier, Key-Value, encrypted key
                   value, flag to indicate whether the information is trusted
                   or not and authentication mode(MD5) currently supported."
      ::= { hpSntpConfigGroups 7 }

   hpSntpBroadcastServerGroup OBJECT-GROUP
      OBJECTS     { hpSntpBroadcastServerStatisticsAuthFailedPkts }
      STATUS      current
      DESCRIPTION "A collection of objects for preferred
                   SNTP broadcast server and statistics."
      ::= { hpSntpConfigGroups 8 }

END
