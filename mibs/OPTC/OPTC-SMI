OPTC-SMI DEFINITIONS ::= BEGIN

IMPORTS
        enterprises,
        MODULE-IDENTITY
                FROM SNMPv2-SMI;

optelecom MODULE-IDENTITY
        LAST-UPDATED "200511020000Z"    -- Nov 2, 2005 12:00:00 AM
        ORGANIZATION "Optelecom-NKF"
        CONTACT-INFO
                "WWW.OPTELECOM-NKF.COM"
        DESCRIPTION
                "Optelecom-NKF enterprise MIB top-level node definitions"
        REVISION "200511020000Z"        -- Nov 2, 2005 12:00:00 AM
        DESCRIPTION
                "Added node optcServices"
        REVISION "200508290000Z"        -- Aug 29, 2005 12:00:00 AM
        DESCRIPTION
                "Revised MIB description, moved chassis product registration to OPTC-CHASSIS-MIB"
        REVISION "200409200000Z"        -- Sep 20, 2004 12:00:00 AM
        DESCRIPTION
                "The initial revision of this module"
        -- 1.3.6.1.4.1.17534
        ::= { enterprises 17534 }


--sub-tree for product registrations
optcReg OBJECT IDENTIFIER 
        -- 1.3.6.1.4.1.17534.1
        ::= { optelecom 1 }

--sub-tree for product-specific objects and events
optcProducts OBJECT IDENTIFIER 
        -- 1.3.6.1.4.1.17534.2
        ::= { optelecom 2 }

--optc9000SeriesChassisMIB is {optcProducts 1}
optcServices OBJECT IDENTIFIER 
        -- 1.3.6.1.4.1.17534.2.2
        ::= { optcProducts 2 }

--sub-tree for experimental objects and events
optcExper OBJECT IDENTIFIER 
        -- 1.3.6.1.4.1.17534.3
        ::= { optelecom 3 }

END
