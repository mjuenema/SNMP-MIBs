-- Copyright 2000 by Marconi
-- All Rights Reserved
--
-- This MIB defines extensions to the standard ATM-FORUM IMA
-- MIB to facilitate extended IMA configurations supported by 
-- Marconi.

Fore-Ima-Ext-MIB DEFINITIONS ::= BEGIN

IMPORTS
	 OBJECT-TYPE	      	FROM	SNMPv2-SMI
	 atmSwitch	        FROM    Fore-Common-MIB
	 asx		      	FROM	Fore-Switch-MIB
	 imaGroupIndex          FROM    IMA-MIB;


foreImaExtMib  MODULE-IDENTITY
          LAST-UPDATED         "0005110000Z"
          ORGANIZATION         "Marconi"
          CONTACT-INFO         
               "      Postal:   Marconi
                                 1000 FORE Drive
                                 Warrendale, PA 15086-7502
                       Tel:      +1 724 742 6900
                       Email:    nm_mibs@fore.com
                       Web:      http://www.fore.com"
          DESCRIPTION "
	      This MIB defines extensions to the standard ATM-FORUM IMA
	      MIB to facilitate extended IMA configurations supported by 
	      Marconi."
    ::= { asx 19 }


foreImaVersion OBJECT IDENTIFIER ::= { foreImaExtMib 1 }

-- Textual Convention

ForeImaVersionNumber ::= TEXTUAL-CONVENTION
	STATUS	current
	DESCRIPTION
	  "This variable represents the ATM-FORUM IMA Version
	  number.  The possible values are v10 (1) and v11 (2)."
	SYNTAX	INTEGER {
	v10 (1),
        v11 (2) }

-- Fore Ima Version Table

foreImaVersionTable OBJECT-TYPE
	SYNTAX		SEQUENCE OF ForeImaVersionEntry
	MAX-ACCESS	not-accessible
        STATUS		current
        DESCRIPTION
		"A table of IMA Group ifIndeces with their 
		 associated IMA version."
	::= { foreImaVersion 1 }

foreImaVersionEntry OBJECT-TYPE
	SYNTAX		ForeImaVersionEntry
	MAX-ACCESS	not-accessible
	STATUS		current
	DESCRIPTION
		"A table entry listing the association of IMA group
		index and IMA version."
	INDEX { imaGroupIndex }
	::= { foreImaVersionTable 1 }


ForeImaVersionEntry ::=
	SEQUENCE { 
		foreImaVersionConfigured	 ForeImaVersionNumber,
		foreImaVersionOperational        ForeImaVersionNumber
	}

foreImaVersionConfigured	OBJECT-TYPE
	SYNTAX		ForeImaVersionNumber
	MAX-ACCESS	read-create
	STATUS		current
	DESCRIPTION
	"Configured IMA version of IMA group"
	DEFVAL { 2 }
	::= { foreImaVersionEntry 1 }

foreImaVersionOperational	OBJECT-TYPE
	SYNTAX		ForeImaVersionNumber
	MAX-ACCESS	read-create
	STATUS		current
	DESCRIPTION
	"Operational IMA version of IMA group"
	::= { foreImaVersionEntry 2 }

END
