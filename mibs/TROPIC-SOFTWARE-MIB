TROPIC-SOFTWARE-MIB DEFINITIONS ::= BEGIN

-- (c) Copyright 2016 Nokia.  All rights reserved.
-- This software is the confidential and proprietary property of
-- Nokia and may only be used in accordance with the
-- terms of the license agreement provided with this software.

 IMPORTS
      SnmpAdminString                         FROM SNMP-FRAMEWORK-MIB
      OBJECT-TYPE, MODULE-IDENTITY,
      IpAddress,
      Unsigned32, Integer32                   FROM SNMPv2-SMI
      MODULE-COMPLIANCE, OBJECT-GROUP         FROM SNMPv2-CONF
      TEXTUAL-CONVENTION,
      TruthValue                              FROM SNMPv2-TC
      ifIndex                                 FROM IF-MIB
      TropicShelfIndexType,
      TropicSlotIndexType,
      AluWdmTransferProtocol,
      TnCommand                               FROM TROPIC-TC
      tnShelfIndex                            FROM TROPIC-SHELF-MIB
      tnSlotIndex                             FROM TROPIC-SLOT-MIB
      tnSystemModules, tnSoftwareMIB          FROM TROPIC-GLOBAL-REG;

  tnSoftwareMibModule MODULE-IDENTITY
      LAST-UPDATED    "201602291200Z"
      ORGANIZATION    "Nokia"
      CONTACT-INFO    "Nokia
                       Postal: 600 March Rd.
                       Kanata, Ontario
                       Canada K2K 2E6

                       Phone: +1 613 591 3600
                       Fax:   +1 613 591 3680"

      DESCRIPTION "The Software Loading MIB."

      REVISION    "200805021200Z"
      DESCRIPTION "1) Updated the MIB file description.
                   2) Added tnSwNodeFPGALockOverride."

      REVISION    "200805291200Z"
      DESCRIPTION "Added the FPGA MIB tables."

      REVISION    "200812171200Z"
      DESCRIPTION "Increased the string length of the following from 17 to 20:
                   tnSwNodeCommittedRelease
                   tnSwNodeWorkingRelease
                   tnSwNodeActiveRelease."

      REVISION    "200902011200Z"
      DESCRIPTION "Added the following table:
                   tnFwCardTable."

      REVISION    "200902051200Z"
      DESCRIPTION "1) Added the following table:
                      tnInstalledFwTable.
                   2) Fixed compliance group problem with tnFwCardTable."

      REVISION    "200902071200Z"
      DESCRIPTION "Changed tnCardType to tnInstalledFwCardType."

      REVISION    "200903021200Z"
      DESCRIPTION "Added the following to tnInstalledFwCardType:
                   4dpa4."

      REVISION    "200903151200Z"
      DESCRIPTION "Added the following to tnInstalledFwCardType:
                   cwr8-88
                   sfd44b
                   itlb."

      REVISION    "200903181200Z"
      DESCRIPTION "Added the following to tnInstalledFwCardType:
                   ahplg."

      REVISION    "200903311200Z"
      DESCRIPTION "Added the following to tnInstalledFwCardType:
                   43stx4."

      REVISION    "200909251200Z"
      DESCRIPTION "Added the following to tnInstalledFwCardType:
                   alpfgk
                   osc
                   4dpa2
                   sfd8[a-d]."

      REVISION    "200911011200Z"
      DESCRIPTION "Added the following to tnInstalledFwCardType:
                   43sta1p
                   43stx4p."

      REVISION    "200912101200Z"
      DESCRIPTION "Added the following to tnInstalledFwCardType:
                   11qpa4
                   Sfd40
                   Sfd40b
                   A2325A."

      REVISION    "201001041200Z"
      DESCRIPTION "Added the following to tnInstalledFwCardType:
                   112scx10
                   112sca1."

      REVISION    "201002171200Z"
      DESCRIPTION "Added the following to tnInstalledFwCardType:
                   alpfgt
                   osct."

      REVISION    "201005071200Z"
      DESCRIPTION "Added the following to tnInstalledFwCardType:
                   flc
                   mt0
                   mt3t8
                   mt1t9."

      REVISION    "201005101200Z"
      DESCRIPTION "Added the following to tnInstalledFwCardType:
                   wtocm
                   wr2-88
                   pss4ec."

      REVISION    "201006041200Z"
      DESCRIPTION "Added the following to tnInstalledFwCardType:
                   am2017b
                   am2325b
                   1dpp21."

      REVISION    "201006251200Z"
      DESCRIPTION "Added the following to tnInstalledFwCardType:
                   sfd4[a-h]."

      REVISION    "201007201200Z"
      DESCRIPTION "Added the following to tnInstalledFwCardType:
                   mvac."

      REVISION    "201009101200Z"
      DESCRIPTION "Added the following to tnInstalledFwCardType:
                   43scx4."

      REVISION    "201009201200Z"
      DESCRIPTION "Added the following to tnInstalledFwCardType:
                   ra2p
                   am2318a
                   am2125a
                   itlu
                   wr8c88a."

      REVISION    "201009241200Z"
      DESCRIPTION "Renamed mt0 to mt0c in tnInstalledFwCardType."

      REVISION    "201009281200Z"
      DESCRIPTION "Added the following to tnInstalledFwCardType:
                   11dpe12e."

      REVISION    "201010171200Z"
      DESCRIPTION "Added the following to tnInstalledFwCardType:
                   112sx10l
                   112sa1l."

      REVISION    "201010181200Z"
      DESCRIPTION "Marked the following as obsolete:
                   tnSwCardLastControlOperation
                   tnSwCardControlAbort
                   tnSwCardLastControlOperationStatus
                   tnSwCardLastControlOperationResult
                   tnSwCardLastControlOperationIntegerResult
                   tnSwCardLastControlOperationPercentCompleted
                   tnSwCardBytesTransferred."

      REVISION    "201010191200Z"
      DESCRIPTION "Added the following to tnInstalledFwCardType:
                   11dpm12."

      REVISION    "201011101200Z"
      DESCRIPTION "Added the following to tnInstalledFwCardType:
                   mesh4."

      REVISION    "201103281200Z"
      DESCRIPTION "Changed SYNTAX of tnSwNodeSwdlServerProtocol to
                   use AluWdmTransferProtocol."

      REVISION    "201105041200Z"
      DESCRIPTION "Added the following to tnInstalledFwCardType:
                   43sca1."

      REVISION    "201105171200Z"
      DESCRIPTION "Added the following to tnInstalledFwCardType:
                   43scx4l
                   am2125b."

      REVISION    "201106071200Z"
      DESCRIPTION "Added the following to tnInstalledFwCardType:
                   mxec."

      REVISION    "201106131200Z"
      DESCRIPTION "Added the following to tnInstalledFwCardType:
                   mxslc
                   eosm
                   eosul."

      REVISION    "201106301200Z"
      DESCRIPTION "Added the following to tnInstalledFwCardType:
                   112snx10
                   112sna1."

      REVISION    "201107071200Z"
      DESCRIPTION "Added the following to tnInstalledFwCardType:
                   11qta4."

      REVISION    "201107191200Z"
      DESCRIPTION "Added the following to tnInstalledFwCardType:
                   1dpp24m."

      REVISION    "201108311200Z"
      DESCRIPTION "Added the following to tnInstalledFwCardType:
                   ul43scup
                   ul11qcup."

      REVISION    "201109061200Z"
      DESCRIPTION "Added the following to tnInstalledFwCardType:
                   11qpen4."

      REVISION    "201109161200Z"
      DESCRIPTION "Added the following to tnInstalledFwCardType:
                   43scx4e."

      REVISION    "201111141200Z"
      DESCRIPTION "Added the following to tnInstalledFwCardType:
                   43scge1."

      REVISION    "201111211200Z"
      DESCRIPTION "Added the following to tnInstalledFwCardType:
                   11qpe24."

      REVISION    "201201101200Z"
      DESCRIPTION "Added the following to tnInstalledFwCardType:
                   11star1a
                   mvac8b."

      REVISION    "201201181200Z"
      DESCRIPTION "Added the following to tnInstalledFwCardType:
                   wr8c88af."

      REVISION    "201201191200Z"
      DESCRIPTION "Added the following to tnInstalledFwCardType:
                   cl10an10g
                   cl24anm."

      REVISION    "201202121200Z"
      DESCRIPTION "Added the following new tables:
                   tnPortGroupTable
                   tnInstalledFwPortGroupTable."

      REVISION    "201203181200Z"
      DESCRIPTION "Added the following to tnInstalledFwCardType:
                   opsb."

      REVISION    "201203291200Z"
      DESCRIPTION "Added the following to tnInstalledFwCardType:
                   11dpe12a."

      REVISION    "201204241200Z"
      DESCRIPTION "Added the following to tnInstalledFwCardType:
                   ul130scup."

      REVISION    "201204271200Z"
      DESCRIPTION "Added the following to tnInstalledFwCardType:
                   130scx10."

      REVISION    "201205181200Z"
      DESCRIPTION "Marked the following as obsolete:
                   tnSwNodeTFTPServer."

      REVISION    "201206181200Z"
      DESCRIPTION "Added the following to tnInstalledFwCardType:
                   a2p2125
                   4qpa8
                   112pdm11
                   wtocma
                   ptpctl
                   ptpio."

      REVISION    "201207241200Z"
      DESCRIPTION "1) Added the following to tnInstalledFwCardType:
                      24et1gb.
                   2) Marked the following as obsolete:
                      11qta4."

      REVISION    "201208281200Z"
      DESCRIPTION "Added the following to tnInstalledFwCardType:
                   4an10g
                   8et1gb
                   10et10g
                   11qcupc
                   520scx4."

      REVISION    "201303071200Z"
      DESCRIPTION "Added the following to tnInstalledFwCardType:
                   11ope8
                   11qce12x."

      REVISION    "201303161200Z"
      DESCRIPTION "Added the following to tnInstalledFwCardType:
                   am2625a
                   am2032a
                   ot260scx2."

      REVISION    "201304111200Z"
      DESCRIPTION "Added the following to tnInstalledFwCardType:
                   ot130snx10
                   io24anmb."

      REVISION    "201304191200Z"
      DESCRIPTION "Added the following to tnInstalledFwCardType:
                   ot11dpm8
                   ot11dpm4m
                   ot11dpm4e."

      REVISION    "201305211200Z"
      DESCRIPTION "Marked the following as obsolete:
                   tnSoftwareEvents."

      REVISION    "201305241200Z"
      DESCRIPTION "Added the following to tnInstalledFwCardType:
                   ul130scupb
                   ot112sdx11."

      REVISION    "201306241200Z"
      DESCRIPTION "Added the following to tnInstalledFwCardType:
                   aa2donw."

      REVISION    "201308121200Z"
      DESCRIPTION "Added the following to tnInstalledFwCardType:
                   ot130sca1."

      REVISION    "201309041200Z"
      DESCRIPTION "Added the following to tnInstalledFwCardType:
                   io10an10gb
                   io10et10gb."

      REVISION    "200309131200Z"
      DESCRIPTION "Added the following scalars to tnSoftwareNode:
                   tnSwNodePartialLoadCommand
                   tnSwNodePartialLoadSupportedCardTypes
                   tnSwNodePartialLoadImgInstalledCardTypes
                   tnSwNodePartialLoadImgToBeInstalledCardTypes
                   tnSwNodePartialLoadActionResult
                   tnSwNodePartialLoadActionPercentCompleted."

      REVISION    "201310071200Z"
      DESCRIPTION "Added the following to tnInstalledFwCardType:
                   psc1-6."

      REVISION    "201310101200Z"
      DESCRIPTION "Added the following to tnInstalledFwCardType:
                   wr20tf."

      REVISION    "201311061200Z"
      DESCRIPTION "Marked the following as obsolete:
                   tnSwNodeFPGALockOverride."

      REVISION    "201311251200Z"
      DESCRIPTION "Added the following to tnInstalledFwCardType:
                   wtocmf."

      REVISION    "201312201200Z"
      DESCRIPTION "Added the following to tnSwNodePartialLoadCommand:
                   forceDownload(3)."

      REVISION    "201401211200Z"
      DESCRIPTION "Added the following table:
                   tnFwHitlessCardTable."

      REVISION    "201402031200Z"
      DESCRIPTION "Added the following to tnFwCardTable:
                   tnFwCardProvisioningInfo."

      REVISION    "201402191200Z"
      DESCRIPTION "Added the following to tnInstalledFwCardType:
                   aswg
                   a4pswg
                   otdr
                   wr20tfm
                   aar8a
                   mcs8x16
                   msh8fsm."

      REVISION    "201403301200Z"
      DESCRIPTION "Changed SYNTAX of the following from (SIZE(0..255))
                   to (SIZE(0..128)):
                   tnSwNodeSwdlServerUserId
                   tnSwNodeSwdlServerPassword."

      REVISION    "201405061200Z"
      DESCRIPTION "Added the following to tnInstalledFwCardType:
                   io4an100g
                   io30an10g."

      REVISION    "201406231200Z"
      DESCRIPTION "Added the following to tnInstalledFwCardType:
                   io30an300."

      REVISION    "201407071200Z"
      DESCRIPTION "Added the following to tnInstalledFwCardType:
                   io4an400."

      REVISION    "201408081200Z"
      DESCRIPTION "Added the following to tnInstalledFwCardType:
                   12p120
                   20p200
                   1ud200."

      REVISION    "201409181200Z"
      DESCRIPTION "Added the following to tnInstalledFwCardType:
                   ot130snq10."

      REVISION    "201409251200Z"
      DESCRIPTION "Added the following to tnInstalledFwCardType:
                   iroadmv
                   iroadmf."

      REVISION    "201501161200Z"
      DESCRIPTION "Added the following to tnInstalledFwCardType:
                   monocm."

      REVISION    "201502201200Z"
      DESCRIPTION "Added the following to tnInstalledFwCardType:
                   ul2uc400
                   ul4uc400
                   ul20uc200."  
                   
      REVISION    "201506121200Z"
      DESCRIPTION "Added the following to tnInstalledFwCardType:
                   d5x500."

      REVISION    "201506121200Z"
      DESCRIPTION "Added the following to tnInstalledFwCardType:
                   ots11m100."

      REVISION    "201508061200Z"
      DESCRIPTION "Added the following to tnInstalledFwCardType:
                   monotdr."

      REVISION    "201510051200Z"
      DESCRIPTION "Added the following to tnInstalledFwCardType:
                   pss96powerfilter."

      REVISION    "201510281200Z"
      DESCRIPTION "Added the following to tnInstalledFwCardType:
                   12ce120
                   1ce100."

      REVISION    "201510281200Z"
      DESCRIPTION "Added the following to tnInstalledFwCardType:
                   lci1000."

      REVISION    "201602231200Z"
      DESCRIPTION "Added the following to tnInstalledFwCardType:
                   mfc,
                   sc."

      REVISION    "201602291200Z"
      DESCRIPTION "Added the following to tnInstalledFwCardType:
                   cec2."


      ::= { tnSystemModules 6 }

  tnSoftwareConf        OBJECT IDENTIFIER ::= { tnSoftwareMIB 1 }
  tnSoftwareGroups      OBJECT IDENTIFIER ::= { tnSoftwareConf 1 }
  tnSoftwareCompliances OBJECT IDENTIFIER ::= { tnSoftwareConf 2 }
  tnSoftwareObjs        OBJECT IDENTIFIER ::= { tnSoftwareMIB 2 }
  tnSoftwareBasics      OBJECT IDENTIFIER ::= { tnSoftwareObjs 1 }
  tnSoftwareNode        OBJECT IDENTIFIER ::= { tnSoftwareBasics 1 }
--  obsolete
--  tnSoftwareEvents      OBJECT IDENTIFIER ::= { tnSoftwareMIB 3 }

--------------------------------------------------------------------------------
-- Type Definitions
--------------------------------------------------------------------------------
    TropicSwControl ::= TEXTUAL-CONVENTION
        STATUS         current
        DESCRIPTION    "Control operations for software downloads."
        SYNTAX         INTEGER {
                         noCmd(1),
                         unknown(2),
                         audit(3),
                         activate(4),
                         upgradeAuto(5),
                         commit(6),
                         backout(7),
                         load(8),
                         cardActivate(9),
                         cardLoad(10),
                         autoInstall(11)
                       }

    TropicSwBank ::= TEXTUAL-CONVENTION
        STATUS         current
        DESCRIPTION    "The flash banks accessible to the network operator."
        SYNTAX         INTEGER {
                         none(1),
                         application0(2),
                         application1(3),
                         userBoot(4),
                         emergencyBoot(5)
                       }

    TropicSwLastOperationStatus ::= TEXTUAL-CONVENTION
        STATUS         current
        DESCRIPTION    "The status of the previously executed operation."
        SYNTAX         INTEGER {
                         completed(1),
                         inProgress(2),
                         failure(3),
                         none(4)
                       }

    TropicSwLastOperationResult ::= TEXTUAL-CONVENTION
        STATUS         current
        DESCRIPTION    "The result of the previously executed operation."
        SYNTAX         SnmpAdminString (SIZE(0..255))

    TropicSwLastOperationPercentCompleted ::= TEXTUAL-CONVENTION
        STATUS         current
        DESCRIPTION    "The percent complete of the previously executed
                        operation."
        SYNTAX         Unsigned32

    AluWdmPortGroupMode ::= TEXTUAL-CONVENTION
        STATUS         current
        DESCRIPTION    "Specifies an FPGA image type that supports certain
                        signal types."
        SYNTAX         INTEGER {
                         pwrSv(1),   -- Power save mode
                         oth(2),     -- OTUn signals
                         ethSth(3),  -- Ethernet, OCn, or STMn signals
                         eth(4),     -- Ethernet signals
                         sth(5),     -- OCn or STMn signals
                         fc(6)       -- Fibre channel signals
                       }

--------------------------------------------------------------------------------
--  Software - Node Level Scalars
--------------------------------------------------------------------------------
--    obsolete
--    tnSwNodeTFTPServer OBJECT-TYPE ::= { tnSoftwareNode 1 }

    tnSwNodeReleaseRoot OBJECT-TYPE
        SYNTAX         SnmpAdminString (SIZE(0..255))
        MAX-ACCESS     read-write
        STATUS         current
        DESCRIPTION    "The path to the directory containing releases,
                        relative to the TFTP server root directory.
                        A forward slash will be prepended if it
                        does not start with one."
        ::= { tnSoftwareNode 2 }

    tnSwNodeControl OBJECT-TYPE
        SYNTAX         TropicSwControl
        MAX-ACCESS     read-write
        STATUS         current
        DESCRIPTION    "Controls the software download.  Command details
                        are as follows:

                        ******************************************************
                        load - will simply execute the script generated
                               by audit, running only the load steps.  It
                               must be preceded by an audit.  Load will
                               not run an audit or delete the the audit
                               script.  Cards are not loaded in parallel.
                             - a set pdu including this attribute with
                               this value may also include attribute
                               tnSwNodeLastAuditTimeStamp.  If
                               tnSwNodeLastAuditTimeStamp is included,
                               and it differs from the value stored on
                               the node, the load will fail.

                        upgradeAuto - upgradeAuto will perform an audit,
                                      load, and activate.  It will not
                                      commit the release.  It will fail
                                      if no upgrade path exists unless
                                      tnSwNodeUpgradeForce is specified.
                                    - a set pdu including this attribute
                                      with this value must also include
                                      attribute tnSwNodeWorkingReleaseDir;
                                      otherwise, the set will be failed
                                      back to the network operator.
                                    - a set pdu including this attribute
                                      with this value may also include
                                      attributes tnSwNodeUpgradeForce
                                      and/or tnSwNodeUpgradeNoBackup.

                        audit - generates the audit script but does not
                                run it.
                              - sets the value of attribute
                                tnSwNodeUpgradePathAvailable.
                              - a set pdu including this attribute with
                                this value must also include attribute
                                tnSwNodeWorkingReleaseDir; otherwise, the
                                set will be failed back to the network
                                operator.
                              - a set pdu including this attribute with
                                this value may also include attributes
                                tnSwNodeUpgradeForce and/or
                                tnSwNodeUpgradeNoBackup.

                        activate - only runs the previously generated
                                   audit script but does not perform any
                                   load steps that may be in the audit
                                   script. The load command must precede
                                   activate.
                                 - a set pdu including this attribute
                                   with this value may also include
                                   attribute tnSwNodeLastAuditTimeStamp.
                                   If tnSwNodeLastAuditTimeStamp is
                                   included, and it differs from the
                                   value stored on the node, the activate
                                   will fail.

                        commit - sets tnSwNodeCommittedRelease equal
                                 to tnSwNodeWorkingRelease, then clears
                                 tnSwNodeWorkingRelease.
                               - clears tnSwNodeWorkingReleaseDir.

                        backout - only allowed if an upgrade has been
                                  attempted on the node.

                        Sets on all other values are restricted.  A read
                        on this attribute returns a value of noCmd.
                        ******************************************************"
        ::= { tnSoftwareNode 3 }

--    obsolete
--    tnSwNodeUseTFTPServerOnly OBJECT-TYPE ::= { tnSoftwareNode 4 }

    tnSwNodeCommittedRelease OBJECT-TYPE
        SYNTAX         SnmpAdminString (SIZE(0..20))
        MAX-ACCESS     read-only
        STATUS         current
        DESCRIPTION    "The committed software release."
        ::= { tnSoftwareNode 5 }

    tnSwNodeWorkingRelease OBJECT-TYPE
        SYNTAX         SnmpAdminString (SIZE(0..20))
        MAX-ACCESS     read-only
        STATUS         current
        DESCRIPTION    "The software release to which the system
                        is upgrading.  This is cleared following
                        a commit to the release."
        ::= { tnSoftwareNode 6 }

    tnSwNodeForce OBJECT-TYPE
        SYNTAX         INTEGER {
                         none(1),
                         false(2),
                         true(3)
                       }
        MAX-ACCESS     read-write
        STATUS         current
        DESCRIPTION    "This attribute, when set to true, MAY result in
                        the DB being purged (only if there is no upgrade
                        path available).  When this attribute is set to
                        false, the DB will NOT be purged.  All reads on
                        this attribute will return a value of none.  It's
                        value is not persistent on the 1696R/1830 NE.  A
                        set pdu including this attribute must also
                        include attribute tnSwNodeControl; otherwise,
                        the set will be failed back to the network
                        operator."
        ::= { tnSoftwareNode 7 }

    tnSwNodeNoBackup OBJECT-TYPE
        SYNTAX         INTEGER {
                         none(1),
                         false(2),
                         true(3)
                       }
        MAX-ACCESS     read-write
        STATUS         current
        DESCRIPTION    "This attribute, when set to true, a DB backup
                        will not be required or enforced.  When this
                        attribute is set to false, a DB will backup will
                        be required and enforced.  All reads on this
                        attribute will return a value of none.  Its
                        value is not persistent on the 1696R/1830 NE.
                        A set pdu including this attribute must also
                        include attribute tnSwNodeControl; otherwise,
                        the set will be failed back to the network
                        operator."
        ::= { tnSoftwareNode 8 }

    tnSwNodeUpgradePathAvailable OBJECT-TYPE
        SYNTAX         TruthValue
        MAX-ACCESS     read-only
        STATUS         current
        DESCRIPTION    "This object is set by the 1696R/1830 NE after
                        the completion of an audit, either by setting
                        tnSwNodeControl to audit or indirectly by
                        setting tnSwNodeControl to upgradeAuto."
        ::= { tnSoftwareNode 9 }

    tnSwNodeLastControlOperation OBJECT-TYPE
        SYNTAX         TropicSwControl
        MAX-ACCESS     read-only
        STATUS         current
        DESCRIPTION    "This is the last control command executed against
                        the software download subsystem.  If the last
                        operation against the software download subsystem
                        is not one of the valid operations in
                        TropicSwControl, the value of this attribute
                        will be unknown."
        ::= { tnSoftwareNode 10 }

    tnSwNodeControlAbort OBJECT-TYPE
        SYNTAX         TnCommand
        MAX-ACCESS     read-write
        STATUS         current
        DESCRIPTION    "This attribute allows the network operator to
                        submit an abort on any operation executed via
                        attribute tnSwNodeControl.  It is only allowed
                        if tnSwNodeLastControlOperationStatus is
                        inProgress.  When read back, the value of this
                        attribute is noCmd.  An abort will always
                        succeed."
        ::= { tnSoftwareNode 11 }

    tnSwNodeLastControlOperationStatus OBJECT-TYPE
        SYNTAX         TropicSwLastOperationStatus
        MAX-ACCESS     read-only
        STATUS         current
        DESCRIPTION    "This attribute indicates the status of the
                        previously executed tnSwNodeControl operation."
        ::= { tnSoftwareNode 12 }

    tnSwNodeLastControlOperationResult OBJECT-TYPE
        SYNTAX         TropicSwLastOperationResult
        MAX-ACCESS     read-only
        STATUS         current
        DESCRIPTION    "The result of the previously executed
                        tnSwNodeControl operation, whether or not it
                        passed or failed."
        ::= { tnSoftwareNode 13 }

    tnSwNodeLastControlOperationIntegerResult OBJECT-TYPE
        SYNTAX         Integer32
        MAX-ACCESS     read-only
        STATUS         current
        DESCRIPTION    "The result of the previously executed
                        tnSwNodeControl operation, as an integer."
        ::= { tnSoftwareNode 14 }

    tnSwNodeLastControlOperationPercentCompleted OBJECT-TYPE
        SYNTAX         TropicSwLastOperationPercentCompleted
        MAX-ACCESS     read-only
        STATUS         current
        DESCRIPTION    "The percent completion of the previously executed
                        tnSwNodeControl operation.  Only applies when
                        tnSwNodeLastControlOperationStatus is inProgress.
                        It should be 0 at all other times."
        ::= { tnSoftwareNode 15 }

    tnSwNodeLastAuditTimeStamp OBJECT-TYPE
        SYNTAX         Unsigned32
        MAX-ACCESS     read-write
        STATUS         current
        DESCRIPTION    "The time at which the last audit was executed,
                        measured in total time ticks (seconds) from the
                        year 1970.

                        When setting tnSwNodeControl to install,
                        tnSwNodeLastAuditTimeStamp may be included in
                        the set pdu.

                        Attempting to set tnSwNodeLastAuditTimeStamp
                        independent of attribute tnSwNodeControl will
                        be failed back to the network operator.

                        The value read back is controlled entirely by
                        the 1696R/1830 NE, which keeps this value in the
                        database.  The value in the database will not
                        be overwritten by setting this attribute via SNMP.

                        Setting this to a value of 0 or not including
                        this attribute with tnSwNodeControl in a set
                        pdu disables this feature."
        ::= { tnSoftwareNode 16 }

--    obsolete
--    tnSwNodeCommittedReleaseDir OBJECT-TYPE ::= { tnSoftwareNode 17 }

    tnSwNodeWorkingReleaseDir OBJECT-TYPE
        SYNTAX         SnmpAdminString (SIZE(0..255))
        MAX-ACCESS     read-write
        STATUS         current
        DESCRIPTION    "The directory associated with the software
                        release to which the system is upgrading.  For
                        sets, if the directory starts with a forward
                        slash, it is absolute; otherwise, it is relative
                        to the release root that contains the release
                        files.  For gets, the response will be the
                        absolute directory, including the release root
                        and including a leading forward slash.

                        This is cleared following a commit to the
                        release.  A set pdu including this attribute
                        must also include attribute tnSwNodeControl;
                        otherwise, the set will be failed back to the
                        network operator."
        ::= { tnSoftwareNode 18 }

    tnSwNodeActiveRelease OBJECT-TYPE
        SYNTAX         SnmpAdminString (SIZE(0..20))
        MAX-ACCESS     read-only
        STATUS         current
        DESCRIPTION    "The currently active software release."
        ::= { tnSoftwareNode 19 }

    tnSwNodeSwdlServerProtocol OBJECT-TYPE
        SYNTAX         AluWdmTransferProtocol
        MAX-ACCESS     read-write
        STATUS         current
        DESCRIPTION    "This attributes indicates the software download
                        protocol."
        ::= { tnSoftwareNode 20 }

    tnSwNodeSwdlServerIp OBJECT-TYPE
        SYNTAX         IpAddress
        MAX-ACCESS     read-write
        STATUS         current
        DESCRIPTION    "The software download server where software files
                        to be downloaded reside.  This will be used as
                        the primary source for files."
        ::= { tnSoftwareNode 21 }

    tnSwNodeSwdlServerUserId OBJECT-TYPE
        SYNTAX         SnmpAdminString (SIZE(0..128))
        MAX-ACCESS     read-write
        STATUS         current
        DESCRIPTION    "The userId used to access software download
                        server."
        ::= { tnSoftwareNode 22 }

    tnSwNodeSwdlServerPassword OBJECT-TYPE
        SYNTAX         SnmpAdminString (SIZE(0..128))
        MAX-ACCESS     read-write
        STATUS         current
        DESCRIPTION    "The password used to access software download
                        server."
        ::= { tnSoftwareNode 23 }

--    obsolete
--    tnSwNodeFPGALockOverride OBJECT-TYPE ::= { tnSoftwareNode 24 }

    tnSwNodePartialLoadCommand OBJECT-TYPE
        SYNTAX         INTEGER {
                         noCmd(1),
                         partialLoad(2),
                         forceDownload(3)
                       }
        MAX-ACCESS     read-write
        STATUS         current
        DESCRIPTION    ""
        DEFVAL         { noCmd }
        ::= { tnSoftwareNode 25 }

    tnSwNodePartialLoadSupportedCardTypes OBJECT-TYPE
        SYNTAX         SnmpAdminString (SIZE(0..2000))
        MAX-ACCESS     read-only
        STATUS         current
        DESCRIPTION    "The lc card types which image support by the
                        node software release.  Format like
                        11PDM12&112PDM11."
        ::= { tnSoftwareNode 26 }

    tnSwNodePartialLoadImgInstalledCardTypes OBJECT-TYPE
        SYNTAX         SnmpAdminString (SIZE(0..2000))
        MAX-ACCESS     read-only
        STATUS         current
        DESCRIPTION    "The lc card types which image have been installed
                        on the node.  Format like 11PDM12&112PDM11."
        ::= { tnSoftwareNode 27 }

    tnSwNodePartialLoadImgToBeInstalledCardTypes OBJECT-TYPE
        SYNTAX         SnmpAdminString (SIZE(0..2000))
        MAX-ACCESS     read-write
        STATUS         current
        DESCRIPTION    "The lc card types which image will need to install
                        on the node.  Format like 11PDM12&112PDM11.  Only
                        applies when tnSwNodePartialLoadCommand is
                        partialLoad."
        ::= { tnSoftwareNode 28 }

    tnSwNodePartialLoadActionResult OBJECT-TYPE
        SYNTAX         TropicSwLastOperationResult
        MAX-ACCESS     read-only
        STATUS         current
        DESCRIPTION    "The partial load result of the action."
        ::= { tnSoftwareNode 29 }

    tnSwNodePartialLoadActionPercentCompleted OBJECT-TYPE
        SYNTAX         TropicSwLastOperationPercentCompleted
        MAX-ACCESS     read-only
        STATUS         current
        DESCRIPTION    "The partial load percent completion of the action.
                        It should be 0 at all other times."
        ::= { tnSoftwareNode 30 }

--------------------------------------------------------------------------------
--  Software - Card Level Table
--------------------------------------------------------------------------------
    tnSwCardTable OBJECT-TYPE
        SYNTAX         SEQUENCE OF TnSwCardEntry
        MAX-ACCESS     not-accessible
        STATUS         current
        DESCRIPTION    "Software Downloading on a per card basis.

                        The following sets of attributes are legal in a
                        single SNMP set pdu.  Any other combinations
                        will be rejected.

                        tnSwCardControl (value load)
                        tnSwCardBankToLoad
                        tnSwCardReleaseDir

                        or

                        tnSwCardControl (value activate)
                        tnSwCardBankToActivate

                        or

                        tnSwCardControlAbort"
        ::= { tnSoftwareBasics 2 }

    tnSwCardEntry OBJECT-TYPE
        SYNTAX         TnSwCardEntry
        MAX-ACCESS     not-accessible
        STATUS         current
        DESCRIPTION    ""
        INDEX { tnShelfIndex,
                tnSlotIndex }
        ::= { tnSwCardTable 1 }

    TnSwCardEntry ::= SEQUENCE {
        tnSwCardAppBank0                             SnmpAdminString,
        tnSwCardAppBank1                             SnmpAdminString,
        tnSwCardEmergBootBank                        SnmpAdminString,
        tnSwCardUserBootBank                         SnmpAdminString,
        tnSwCardActiveBank                           TropicSwBank,
        tnSwCardNextBootBank                         TropicSwBank,
        tnSwCardBankToActivate                       TropicSwBank,
        tnSwCardBankToLoad                           INTEGER,
        tnSwCardControl                              TropicSwControl,
--        obsolete
--        tnSwCardLastControlOperation                 TropicSwControl,
--        tnSwCardControlAbort                         INTEGER,
--        tnSwCardLastControlOperationStatus           TropicSwLastOperationStatus,
--        tnSwCardLastControlOperationResult           TropicSwLastOperationResult,
--        tnSwCardLastControlOperationIntegerResult    Integer32,
--        tnSwCardLastControlOperationPercentCompleted TropicSwLastOperationPercentCompleted,
--        tnSwCardBytesTransferred                     Unsigned32,
        tnSwCardReleaseDir                           SnmpAdminString
    }

    tnSwCardAppBank0 OBJECT-TYPE
        SYNTAX         SnmpAdminString (SIZE(0..17))
        MAX-ACCESS     read-only
        STATUS         current
        DESCRIPTION    "The SW generic load currently in bank 0."
        ::= { tnSwCardEntry 1 }

    tnSwCardAppBank1 OBJECT-TYPE
        SYNTAX         SnmpAdminString (SIZE(0..17))
        MAX-ACCESS     read-only
        STATUS         current
        DESCRIPTION    "The SW generic load currently in bank 1."
        ::= { tnSwCardEntry 2 }

    tnSwCardEmergBootBank OBJECT-TYPE
        SYNTAX         SnmpAdminString (SIZE(0..17))
        MAX-ACCESS     read-only
        STATUS         current
        DESCRIPTION    "The SW generic load currently in the
                        emergency boot bank."
        ::= { tnSwCardEntry 3 }

    tnSwCardUserBootBank OBJECT-TYPE
        SYNTAX         SnmpAdminString (SIZE(0..17))
        MAX-ACCESS     read-only
        STATUS         current
        DESCRIPTION    "The SW generic load currently in the
                        user boot bank."
        ::= { tnSwCardEntry 4 }

    tnSwCardActiveBank OBJECT-TYPE
        SYNTAX         TropicSwBank
        MAX-ACCESS     read-only
        STATUS         current
        DESCRIPTION    "The currently active bank."
        ::= { tnSwCardEntry 5 }

    tnSwCardNextBootBank OBJECT-TYPE
        SYNTAX         TropicSwBank
        MAX-ACCESS     read-only
        STATUS         current
        DESCRIPTION    "The bank from which to boot the card on
                        the next card reset."
        ::= { tnSwCardEntry 6 }

    tnSwCardBankToActivate OBJECT-TYPE
        SYNTAX         TropicSwBank
        MAX-ACCESS     read-create
        STATUS         current
        DESCRIPTION    "This attribute indicates the bank to switch to
                        and reset.  A set PDU containing this attribute
                        must also contain attribute tnSwCardControl.
                        When read, this attribute returns a value of
                        none."
        ::= { tnSwCardEntry 7 }

    tnSwCardBankToLoad OBJECT-TYPE
        SYNTAX         INTEGER {
                         none(1),
                         application(2),
                         boot(3)
                       }
        MAX-ACCESS     read-create
        STATUS         current
        DESCRIPTION    "The flash bank to which the load will be
                        transferred.  Selecting a value of application
                        will result in the load being transferred to
                        the inactive application bank.  Selecting a
                        value of boot will result in the load being
                        transferred to the user boot bank.  All reads
                        on this attribute will return a value of none."
        ::= { tnSwCardEntry 8 }

    tnSwCardControl OBJECT-TYPE
        SYNTAX         TropicSwControl
        MAX-ACCESS     read-create
        STATUS         current
        DESCRIPTION    "Command cardLoad results in forced SW loading
                        at the card level.  Command cardActivate results
                        in a bank switch and card reset.  Sets on all
                        other values are restricted.  A read on this
                        attribute returns a value of noCmd."
        ::= { tnSwCardEntry 9 }

--    obsolete
--    tnSwCardLastControlOperation OBJECT-TYPE ::= { tnSwCardEntry 10 }
--    tnSwCardControlAbort OBJECT-TYPE ::= { tnSwCardEntry 11 }
--    tnSwCardLastControlOperationStatus OBJECT-TYPE ::= { tnSwCardEntry 12 }
--    tnSwCardLastControlOperationResult OBJECT-TYPE ::= { tnSwCardEntry 13 }
--    tnSwCardLastControlOperationIntegerResult OBJECT-TYPE ::= { tnSwCardEntry 14 }
--    tnSwCardLastControlOperationPercentCompleted OBJECT-TYPE ::= { tnSwCardEntry 15 }
--    tnSwCardBytesTransferred OBJECT-TYPE ::= { tnSwCardEntry 16 }

    tnSwCardReleaseDir OBJECT-TYPE
        SYNTAX         SnmpAdminString (SIZE(0..255))
        MAX-ACCESS     read-create
        STATUS         current
        DESCRIPTION    "The directory that contains all the release
                        files.  For sets, if the directory starts with
                        a forward slash, it is absolute; otherwise, it
                        is relative to the release root that contains
                        the release files.

                        All reads on this attribute will return an empty
                        string.  Its value is not persistent on the
                        1696R/1830 NE."
        ::= { tnSwCardEntry 17 }

--------------------------------------------------------------------------------
-- Software Audit Script Table
--------------------------------------------------------------------------------
    tnSwAuditScriptTable OBJECT-TYPE
        SYNTAX         SEQUENCE OF TnSwAuditScriptEntry
        MAX-ACCESS     not-accessible
        STATUS         current
        DESCRIPTION    "This table is comprised of the content of a
                        software upgrade script, created by the execution
                        of a software audit.  A network operator may view
                        the script prior to running it.  While the script
                        is running, the network operator may use this
                        table to view the progress of the software upgrade."
        ::= { tnSoftwareBasics 3 }

    tnSwAuditScriptEntry OBJECT-TYPE
        SYNTAX         TnSwAuditScriptEntry
        MAX-ACCESS     not-accessible
        STATUS         current
        DESCRIPTION    "This table is indexed via the software upgrade
                        stage and the step within the stage."
        INDEX { tnSwAuditScriptStage,
                tnSwAuditScriptStep }
        ::= { tnSwAuditScriptTable 1 }

    TnSwAuditScriptEntry ::= SEQUENCE {
        tnSwAuditScriptStage                  Unsigned32,
        tnSwAuditScriptStep                   Unsigned32,
        tnSwAuditScriptShelf                  TropicShelfIndexType,
        tnSwAuditScriptSlot                   TropicSlotIndexType,
        tnSwAuditScriptCardType               OBJECT IDENTIFIER,
        tnSwAuditScriptAction                 SnmpAdminString,
        tnSwAuditScriptActionStatus           SnmpAdminString,
        tnSwAuditScriptActionResult           TropicSwLastOperationResult,
        tnSwAuditScriptActionPercentCompleted TropicSwLastOperationPercentCompleted,
        tnSwAuditScriptResultTimeStamp        Unsigned32
    }

    tnSwAuditScriptStage OBJECT-TYPE
        SYNTAX         Unsigned32
        MAX-ACCESS     not-accessible
        STATUS         current
        DESCRIPTION    "The software upgrade stage.  The lower bound is
                        0."
        ::= { tnSwAuditScriptEntry 1 }

    tnSwAuditScriptStep OBJECT-TYPE
        SYNTAX         Unsigned32
        MAX-ACCESS     not-accessible
        STATUS         current
        DESCRIPTION    "The step within the software upgrade stage.  The
                        lower bound is 1."
        ::= { tnSwAuditScriptEntry 2 }

    tnSwAuditScriptShelf OBJECT-TYPE
        SYNTAX         TropicShelfIndexType
        MAX-ACCESS     read-only
        STATUS         current
        DESCRIPTION    "The shelf id of the shelf being upgraded."
        ::= { tnSwAuditScriptEntry 3 }

    tnSwAuditScriptSlot OBJECT-TYPE
        SYNTAX         TropicSlotIndexType
        MAX-ACCESS     read-only
        STATUS         current
        DESCRIPTION    "The slot of the card being upgraded."
        ::= { tnSwAuditScriptEntry 4 }

    tnSwAuditScriptCardType OBJECT-TYPE
        SYNTAX         OBJECT IDENTIFIER
        MAX-ACCESS     read-only
        STATUS         current
        DESCRIPTION    "The card type of the card being upgraded."
        ::= { tnSwAuditScriptEntry 5 }

    tnSwAuditScriptAction OBJECT-TYPE
        SYNTAX         SnmpAdminString (SIZE(0..255))
        MAX-ACCESS     read-only
        STATUS         current
        DESCRIPTION    "The currently executing operation."
        ::= { tnSwAuditScriptEntry 7 }

    tnSwAuditScriptActionStatus OBJECT-TYPE
        SYNTAX         SnmpAdminString (SIZE(0..255))
        MAX-ACCESS     read-only
        STATUS         current
        DESCRIPTION    "The status of the action."
        ::= { tnSwAuditScriptEntry 8 }

    tnSwAuditScriptActionResult OBJECT-TYPE
        SYNTAX         TropicSwLastOperationResult
        MAX-ACCESS     read-only
        STATUS         current
        DESCRIPTION    "The result of the action."
        ::= { tnSwAuditScriptEntry 9 }

    tnSwAuditScriptActionPercentCompleted OBJECT-TYPE
        SYNTAX         TropicSwLastOperationPercentCompleted
        MAX-ACCESS     read-only
        STATUS         current
        DESCRIPTION    "The percent completion of the action.  Only
                        applies when tnSwAuditScriptActionStatus is
                        inProgress.  It should be 0 at all other times."
        ::= { tnSwAuditScriptEntry 10 }

    tnSwAuditScriptResultTimeStamp OBJECT-TYPE
        SYNTAX         Unsigned32
        MAX-ACCESS     read-only
        STATUS         current
        DESCRIPTION    "The time at which the result occurred,
                        measured in total time ticks (seconds) from
                        the year 1970."
        ::= { tnSwAuditScriptEntry 11 }

--------------------------------------------------------------------------------
--  Software - CPLD Table
--------------------------------------------------------------------------------
    tnSwCpldTable OBJECT-TYPE
        SYNTAX         SEQUENCE OF TnSwCpldEntry
        MAX-ACCESS     not-accessible
        STATUS         current
        DESCRIPTION    "CPLD Software Programming on a per card basis."
        ::= { tnSoftwareBasics 4 }

    tnSwCpldEntry OBJECT-TYPE
        SYNTAX         TnSwCpldEntry
        MAX-ACCESS     not-accessible
        STATUS         current
        DESCRIPTION    ""
        INDEX { tnShelfIndex,
                tnSlotIndex }
        ::= { tnSwCpldTable 1 }

    TnSwCpldEntry ::= SEQUENCE {
        tnSwCpldProgramControl INTEGER
    }

    tnSwCpldProgramControl OBJECT-TYPE
        SYNTAX         INTEGER {
                         noCmd(1),
                         gentle(2),
                         force(3)
                       }
        MAX-ACCESS     read-create
        STATUS         current
        DESCRIPTION    "Values:

                        noCmd  - the returned value on get requests.
                        gentle - indicates to program the CPLDs only
                                 if CPLD versions differ.
                        force  - program the CPLDs regardless of the
                                 version numbers."
        ::= { tnSwCpldEntry 1 }

--------------------------------------------------------------------------------
--  Firmware - Card Level Table
--------------------------------------------------------------------------------
    tnFwCardTable OBJECT-TYPE
        SYNTAX         SEQUENCE OF TnFwCardEntry
        MAX-ACCESS     not-accessible
        STATUS         current
        DESCRIPTION    "Firmware Maintenance on a per card basis."
        ::= { tnSoftwareBasics 5 }

    tnFwCardEntry OBJECT-TYPE
        SYNTAX         TnFwCardEntry
        MAX-ACCESS     not-accessible
        STATUS         current
        DESCRIPTION    ""
        INDEX { tnShelfIndex,
                tnSlotIndex }
        ::= { tnFwCardTable 1 }

    TnFwCardEntry ::= SEQUENCE {
        tnFwCardCurrentBundle           SnmpAdminString,
        tnFwCardLoadedAt                Unsigned32,
        tnFwCardLoadBundle              SnmpAdminString,
        tnFwCardProvisionedAt           Unsigned32,
        tnFwCardLoadState               INTEGER,
        tnFwCardWatchDog                Unsigned32,
        tnFwCardProvisioningInfo        SnmpAdminString
    }

    tnFwCardCurrentBundle OBJECT-TYPE
        SYNTAX         SnmpAdminString (SIZE(0..64))
        MAX-ACCESS     read-only
        STATUS         current
        DESCRIPTION    "The filename of the bundle of firmware that is
                        currently loaded in the card, for example,
                        <cardFunction>_i.j.k.  This is updated on each
                        warm and cold restart by comparing the version
                        registers of each FPGA against the list of
                        version registers in the profile."
        DEFVAL         { {} }
        ::= { tnFwCardEntry 1 }

    tnFwCardLoadedAt OBJECT-TYPE
        SYNTAX         Unsigned32
        MAX-ACCESS     read-only
        STATUS         current
        DESCRIPTION    "The time at which the named firmware bundle was
                        last successfully loaded (seconds from 1970)."
        ::= { tnFwCardEntry 2 }

    tnFwCardLoadBundle OBJECT-TYPE
        SYNTAX         SnmpAdminString (SIZE(0..32))
        MAX-ACCESS     read-create
        STATUS         current
        DESCRIPTION    "The revision code portion of filename of the bundle
                        of firmware that is to be loaded in the card at the
                        next cold reset; the i.j[.k] portion of
                        <cardFunction>_i.j[.k].  When .k is not specified,
                        the file with the numerically highest value of k is
                        used.  When the <cardFunction> is not specified,
                        the word profile will be used in its place, e.g.
                        profile_1.1.0.  When the <tnFwCardLoadBundle> and
                        the <cardFunction> are not specified, the resulting
                        string will be profile_default."
        DEFVAL         { {} }
        ::= { tnFwCardEntry 3 }

    tnFwCardProvisionedAt OBJECT-TYPE
        SYNTAX         Unsigned32
        MAX-ACCESS     read-only
        STATUS         current
        DESCRIPTION    "The time at which the provisioned firmware bundle
                        name was changed for this card (seconds from 1970)."
        ::= { tnFwCardEntry 4 }

    tnFwCardLoadState OBJECT-TYPE
        SYNTAX         INTEGER {
                         none(1),
                         loaded(2),
                         init1(3),
                         init2(4),
                         init3(5),
                         init4(6),
                         init5(7),
                         init6(8),
                         init7(9),
                         init8(10),
                         init9(11),
                         init10(12),
                         failed(13),
                         timeOut(14)
                       }
        MAX-ACCESS     read-only
        STATUS         current
        DESCRIPTION    "The state of the firmware load process for the card
                        as a whole.  This uses conditions FPGAInit[1-10]
                        raised by Board Manager, which will also update the
                        ECId."
        ::= { tnFwCardEntry 5 }

    tnFwCardWatchDog OBJECT-TYPE
        SYNTAX         Unsigned32
        MAX-ACCESS     read-only
        STATUS         current
        DESCRIPTION    "This is the time since the beginning of the init
                        state for the individual FPGA device currently
                        being loaded.  It is updated only when requested
                        for display.  Timeout starts at 45 minutes.
                        Progress time displayed will be = 45:00-current
                        value."
        ::= { tnFwCardEntry 6 }

    tnFwCardProvisioningInfo OBJECT-TYPE
        SYNTAX         SnmpAdminString (SIZE(0..512))
        MAX-ACCESS     read-only
        STATUS         current
        DESCRIPTION    "FPGA card provisioning information for up
                        to 10 profiles.  The information for each
                        profile contains the following 5 fields:

                        NGOCC 01 static 40020402 hitless

                        where

                        NGOCC    - FPGA name of this profile.
                        01       - Vendor/hardware realization variant of a profile.
                        static   - FPGA type, static or dynamic.
                        40020402 - Version.
                        hitless  - Status.

                        Software developers are working out the details
                        of the arrangement of these fields."
        ::= { tnFwCardEntry 7 }

--------------------------------------------------------------------------------
--  Firmware - Installed files Table
--------------------------------------------------------------------------------
    tnInstalledFwTable OBJECT-TYPE
        SYNTAX         SEQUENCE OF TnInstalledFwEntry
        MAX-ACCESS     not-accessible
        STATUS         current
        DESCRIPTION    "This object describes the firmware available on
                        the EC"
        ::= { tnSoftwareBasics 6 }

    tnInstalledFwEntry OBJECT-TYPE
        SYNTAX         TnInstalledFwEntry
        MAX-ACCESS     not-accessible
        STATUS         current
        DESCRIPTION    "An entry of the installed firmware table"
        INDEX { tnInstalledFwCardType,
                tnInstalledFwFileName }
        ::= { tnInstalledFwTable 1 }

    TnInstalledFwEntry ::= SEQUENCE {
        tnInstalledFwCardType         Unsigned32,
        tnInstalledFwFileName         SnmpAdminString,
        tnInstalledFwIsDefault        TruthValue
    }

    tnInstalledFwCardType OBJECT-TYPE
        SYNTAX         Unsigned32
        MAX-ACCESS     not-accessible
        STATUS         current
        DESCRIPTION    "Supported values in R1.1:
                        11dpge12    - 1
                        11star1     - 2
                        11stge12    - 3
                        11stmm10    - 4
                        ahphg       - 5
                        alphg       - 6
                        cwr8        - 7
                        dcm         - 8
                        ec          - 9
                        opsa        - 10
                        sfc1a       - 11
                        sfc1b       - 12
                        sfc1c       - 13
                        sfc1d       - 14
                        sfc1e       - 15
                        sfc1f       - 16
                        sfc1g       - 17
                        sfc1h       - 18
                        sfc2a       - 19
                        sfc2b       - 20
                        sfc2c       - 21
                        sfc2d       - 22
                        sfc4a       - 23
                        sfc4b       - 24
                        sfc8        - 25
                        sfd44       - 26
                        sfd5a       - 27
                        sfd5b       - 28
                        sfd5c       - 29
                        sfd5d       - 30
                        sfd5e       - 31
                        sfd5f       - 32
                        sfd5g       - 33
                        sfd5h       - 34
                        svac        - 35

                        R2.0:
                        4dpa4       - 36
                        cwr8-88     - 37
                        sfd44b      - 38
                        itlb        - 39
                        ahplg       - 40
                        43stx4      - 41

                        R2.5:
                        alpfgk      - 42
                        osc         - 43
                        4dpa2       - 44
                        sfd8a       - 45
                        sfd8b       - 46
                        sfd8c       - 47
                        sfd8d       - 48
                        43sta1p     - 49
                        43stx4p     - 50
                        11qpa4      - 51
                        sfd40       - 52
                        sfd40b      - 53
                        a2325a      - 54
                        112scx10    - 55
                        112sca1     - 56
                        alpfgt      - 57
                        osct        - 58

                        R2.9:
                        flc         - 59
                        mt0c        - 60
                        mt3t8       - 61
                        mt1t9       - 62

                        R3.0:
                        wtocm       - 63
                        wr2-88      - 64
                        pss4ec      - 65
                        am2017b     - 66
                        am2325b     - 67
                        1dpp21      - 68
                        sfd4a       - 69
                        sfd4b       - 70
                        sfd4c       - 71
                        sfd4d       - 72
                        sfd4e       - 73
                        sfd4f       - 74
                        sfd4g       - 75
                        sfd4h       - 76
                        mvac        - 77

                        R3.1.5:
                        43scx4      - 78

                        R3.5:
                        ra2p        - 79
                        am2318a     - 80
                        am2125a     - 81
                        itlu        - 82
                        wr8c88a     - 83
                        11dpe12e    - 84
                        112sx10l    - 85
                        112sa1l     - 86
                        11dpm12     - 87
                        mesh4       - 88

                        R3.6:
                        43sca1      - 89
                        43scx4l     - 90
                        am2125b     - 91
                        mxec        - 92
                        mxslc       - 93
                        eosm        - 94
                        eosul       - 95

                        R3.6.5:
                        112snx10    - 96
                        112sna1     - 97
                        11qta4      - 98      -- obsolete
                        1dpp24m     - 99
                        ul43scup    - 100
                        ul11qcup    - 101
                        11qpen4     - 102
                        43scx4e     - 103
                        43scge1     - 104
                        11qpe24     - 105

                        R5.0:
                        11star1a    - 106
                        mvac8b      - 107
                        wr8c88af    - 108

                        R5.1:
                        opsb        - 111
                        11dpe12a    - 112

                        R5.5:
                        cl10an10g   - 109
                        cl24anm     - 110
                        ul130scup   - 113
                        130scx10    - 114
                        a2p2125     - 115
                        4qpa8       - 116
                        112pdm11    - 117
                        wtocma      - 118
                        ptpctl      - 119
                        ptpio       - 120
                        24et1gb     - 121
                        4an10g      - 122
                        8et1gb      - 123
                        10et10g     - 124
                        11qcupc     - 125
                        520scx4     - 126

                        R6.0.6:
                        ot130snx10  - 132
                        ot130sca1   - 140

                        R7.0:
                        11ope8      - 127
                        11qce12x    - 128
                        am2625a     - 129
                        am2032a     - 130
                        ot260scx2   - 131
                        io24anmb    - 133
                        ot11dpm8    - 134
                        ot11dpm4m   - 135
                        ot11dpm4e   - 136
                        ul130scupb  - 137
                        ot112sdx11  - 138
                        aa2donw     - 139
                        io10an10gb  - 141
                        io10et10gb  - 142
                        psc1-6      - 143
                        wr20tf      - 144
                        wtocmf      - 145

                        R7.0.2:
                        aswg        - 146
                        a4pswg      - 147
                        otdr        - 148
                        wr20-tfm    - 149
                        aar-8a      - 150
                        mcs8-16     - 151
                        msh8-fsm    - 152
                        mfc         - 174
                        sc          - 175
 
                        R8.0:
                        io4an100g   - 153
                        io30an10g   - 154
                        io30an300   - 155
                        io4an400    - 156
                        12p120      - 157
                        20p200      - 158
                        1ud200      - 159
                        ot130snq10  - 160
                        iroadmv     - 161
                        iroadmf     - 162
                        monocm      - 163
                        monotdr     - 169 
                        pss96powerfilter - 170
 
                        R9.0:
                        ul2uc400    - 164
                        ul4uc400    - 165
                        ul20uc200   - 166
                        d5x500      - 167
                        ots11m100   - 168
                        12ce120     - 171
                        1ce100      - 172
                        lci1000     - 173
                        cec2        - 176."  


        ::= { tnInstalledFwEntry 1 }

    tnInstalledFwFileName OBJECT-TYPE
        SYNTAX         SnmpAdminString
        MAX-ACCESS     read-only
        STATUS         current
        DESCRIPTION    "This attribute contains the name of the firmware
                        file for files with links, it specifies the
                        target file name."
    ::= { tnInstalledFwEntry 2 }

    tnInstalledFwIsDefault OBJECT-TYPE
        SYNTAX         TruthValue
        MAX-ACCESS     read-only
        STATUS         current
        DESCRIPTION    "This attribute specifies if the software is
                        default."
    ::= { tnInstalledFwEntry 3 }

--------------------------------------------------------------------------------
-- Port Group Table
--------------------------------------------------------------------------------
    tnPortGroupTable OBJECT-TYPE
        SYNTAX         SEQUENCE OF TnPortGroupEntry
        MAX-ACCESS     not-accessible
        STATUS         current
        DESCRIPTION    ""
        ::= { tnSoftwareBasics 7 }

    tnPortGroupEntry OBJECT-TYPE
        SYNTAX         TnPortGroupEntry
        MAX-ACCESS     not-accessible
        STATUS         current
        DESCRIPTION    ""
        INDEX { ifIndex }
        ::= { tnPortGroupTable 1 }

    TnPortGroupEntry ::= SEQUENCE {
        tnPortGroupMode           AluWdmPortGroupMode,
        tnPortGroupFwDownload     SnmpAdminString,
        tnPortGroupFwCurrent      SnmpAdminString
    }

    tnPortGroupMode OBJECT-TYPE
        SYNTAX         AluWdmPortGroupMode
        MAX-ACCESS     read-create
        STATUS         current
        DESCRIPTION    "Port group mode is a synonym for the applied
                        FPGA firmware type."
        ::= { tnPortGroupEntry 1 }

    tnPortGroupFwDownload OBJECT-TYPE
        SYNTAX         SnmpAdminString (SIZE(0..32))
        MAX-ACCESS     read-create
        STATUS         current
        DESCRIPTION    "The port group firmware version to be downloaded.
                        A null value means the preferred version for the
                        selected mode in the active card firmware profile."
        ::= { tnPortGroupEntry 2 }

    tnPortGroupFwCurrent OBJECT-TYPE
        SYNTAX         SnmpAdminString (SIZE(0..32))
        MAX-ACCESS     read-only
        STATUS         current
        DESCRIPTION    "The current port group firmware version that is
                        running on the FPGA."
        ::= { tnPortGroupEntry 3 }

--------------------------------------------------------------------------------
-- Installed Firmware Port Group Table
--------------------------------------------------------------------------------
    tnInstalledFwPortGroupTable OBJECT-TYPE
        SYNTAX         SEQUENCE OF TnInstalledFwPortGroupEntry
        MAX-ACCESS     not-accessible
        STATUS         current
        DESCRIPTION    ""
        ::= { tnSoftwareBasics 8 }

    tnInstalledFwPortGroupEntry OBJECT-TYPE
        SYNTAX         TnInstalledFwPortGroupEntry
        MAX-ACCESS     not-accessible
        STATUS         current
        DESCRIPTION    ""
        INDEX { tnInstalledFwCardType,
                tnInstalledFwFileName,
                tnInstalledFwPortGroupMode,
                tnInstalledFwPortGroupFw }
        ::= { tnInstalledFwPortGroupTable 1 }

    TnInstalledFwPortGroupEntry ::= SEQUENCE {
        tnInstalledFwPortGroupMode          AluWdmPortGroupMode,
        tnInstalledFwPortGroupFw            SnmpAdminString,
        tnInstalledFwPortGroupIsDefault     TruthValue
    }

    tnInstalledFwPortGroupMode OBJECT-TYPE
        SYNTAX         AluWdmPortGroupMode
        MAX-ACCESS     not-accessible
        STATUS         current
        DESCRIPTION    "The valid port group mode in the card firmware
                        profile."
        ::= { tnInstalledFwPortGroupEntry 1 }

    tnInstalledFwPortGroupFw OBJECT-TYPE
        SYNTAX         SnmpAdminString (SIZE(0..32))
        MAX-ACCESS     not-accessible
        STATUS         current
        DESCRIPTION    "The valid port group firmware version number
                        associated with the port group mode."
        ::= { tnInstalledFwPortGroupEntry 2 }

    tnInstalledFwPortGroupIsDefault OBJECT-TYPE
        SYNTAX         TruthValue
        MAX-ACCESS     read-only
        STATUS         current
        DESCRIPTION    "This attribute specifies if the software is
                        default."
        ::= { tnInstalledFwPortGroupEntry 3 }

--------------------------------------------------------------------------------
--  Firmware - Card Level HitLess Table
--------------------------------------------------------------------------------
    tnFwHitlessCardTable OBJECT-TYPE
        SYNTAX         SEQUENCE OF TnFwHitlessCardEntry
        MAX-ACCESS     not-accessible
        STATUS         current
        DESCRIPTION    "Firmware Hitless Maintenance on a per card basis."
        ::= { tnSoftwareBasics 9 }

    tnFwHitlessCardEntry OBJECT-TYPE
        SYNTAX         TnFwHitlessCardEntry
        MAX-ACCESS     not-accessible
        STATUS         current
        DESCRIPTION    ""
        INDEX { tnShelfIndex,
                tnSlotIndex }
        ::= { tnFwHitlessCardTable 1 }

    TnFwHitlessCardEntry ::= SEQUENCE {
        tnFwHitlessCardTrigger       TruthValue,
        tnFwHitlessCardLoadState     INTEGER,
        tnFwHitlessCardWatchDog      Unsigned32
    }

    tnFwHitlessCardTrigger  OBJECT-TYPE
        SYNTAX         TruthValue
        MAX-ACCESS     read-create
        STATUS         current
        DESCRIPTION    "Hitless - Provisioned firmware package will be
                        loaded to the card by performing a warm reboot."
        ::= { tnFwHitlessCardEntry 1 }

    tnFwHitlessCardLoadState OBJECT-TYPE
        SYNTAX         INTEGER {
                         none(1),
                         loaded(2),
                         initNsa1(3),
                         initNsa2(4),
                         initNsa3(5),
                         initNsa4(6),
                         initNsa5(7),
                         initNsa6(8),
                         initNsa7(9),
                         initNsa8(10),
                         initNsa9(11),
                         initNsa10(12),
                         failed(13),
                         timeOut(14)
                       }
        MAX-ACCESS     read-only
        STATUS         current
        DESCRIPTION    "The state of the firmware hitless load process
                        for the card as a whole.  This uses conditions
                        FPGAINITNSA[1-10] raised by Board Manager, which
                        will also update the ECId."
        ::= { tnFwHitlessCardEntry 2 }

    tnFwHitlessCardWatchDog OBJECT-TYPE
        SYNTAX         Unsigned32
        MAX-ACCESS     read-only
        STATUS         current
        DESCRIPTION    "This is the time since the beginning of the init
                        state for the individual FPGA Hitless device
                        currently being loaded.  It is updated only when
                        requested for display.  Timeout starts at 45
                        minutes.  Progress time displayed will be =
                        45:00-current value."
        ::= { tnFwHitlessCardEntry 3 }

--------------------------------------------------------------------------------
-- Conformance Group Definitions
--------------------------------------------------------------------------------
    tnSwNodeGroup OBJECT-GROUP
        OBJECTS {
--            obsolete
--            tnSwNodeTFTPServer,
            tnSwNodeReleaseRoot,
            tnSwNodeControl,
--            obsolete
--            tnSwNodeUseTFTPServerOnly,
            tnSwNodeCommittedRelease,
            tnSwNodeWorkingRelease,
            tnSwNodeForce,
            tnSwNodeNoBackup,
            tnSwNodeUpgradePathAvailable,
            tnSwNodeLastControlOperation,
            tnSwNodeControlAbort,
            tnSwNodeLastControlOperationStatus,
            tnSwNodeLastControlOperationResult,
            tnSwNodeLastControlOperationIntegerResult,
            tnSwNodeLastControlOperationPercentCompleted,
            tnSwNodeLastAuditTimeStamp,
--            obsolete
--            tnSwNodeCommittedReleaseDir,
            tnSwNodeWorkingReleaseDir,
            tnSwNodeActiveRelease,
            tnSwNodeSwdlServerProtocol,
            tnSwNodeSwdlServerIp,
            tnSwNodeSwdlServerUserId,
            tnSwNodeSwdlServerPassword,
--            obsolete
--            tnSwNodeFPGALockOverride,
            tnSwNodePartialLoadCommand,
            tnSwNodePartialLoadSupportedCardTypes,
            tnSwNodePartialLoadImgInstalledCardTypes,
            tnSwNodePartialLoadImgToBeInstalledCardTypes,
            tnSwNodePartialLoadActionResult,
            tnSwNodePartialLoadActionPercentCompleted
        }
        STATUS         current
        DESCRIPTION    "A collection of objects providing System Downloads"
        ::= { tnSoftwareGroups 1 }

    tnSwCardGroup OBJECT-GROUP
        OBJECTS {
            tnSwCardAppBank0,
            tnSwCardAppBank1,
            tnSwCardEmergBootBank,
            tnSwCardUserBootBank,
            tnSwCardActiveBank,
            tnSwCardNextBootBank,
            tnSwCardBankToActivate,
            tnSwCardBankToLoad,
            tnSwCardControl,
--            obsolete
--            tnSwCardLastControlOperation,
--            tnSwCardControlAbort,
--            tnSwCardLastControlOperationStatus,
--            tnSwCardLastControlOperationResult,
--            tnSwCardLastControlOperationIntegerResult,
--            tnSwCardLastControlOperationPercentCompleted,
--            tnSwCardBytesTransferred,
            tnSwCardReleaseDir
        }
        STATUS         current
        DESCRIPTION    ""
        ::= { tnSoftwareGroups 2 }

    tnSwAuditScriptGroup OBJECT-GROUP
        OBJECTS {
            tnSwAuditScriptShelf,
            tnSwAuditScriptSlot,
            tnSwAuditScriptCardType,
            tnSwAuditScriptAction,
            tnSwAuditScriptActionStatus,
            tnSwAuditScriptActionResult,
            tnSwAuditScriptActionPercentCompleted,
            tnSwAuditScriptResultTimeStamp
        }
        STATUS         current
        DESCRIPTION    ""
        ::= { tnSoftwareGroups 3 }

    tnSwCpldGroup OBJECT-GROUP
        OBJECTS {
            tnSwCpldProgramControl
        }
        STATUS         current
        DESCRIPTION    ""
        ::= { tnSoftwareGroups 4 }

    tnFwCardGroup OBJECT-GROUP
        OBJECTS {
            tnFwCardCurrentBundle,
            tnFwCardLoadedAt,
            tnFwCardLoadBundle,
            tnFwCardProvisionedAt,
            tnFwCardLoadState,
            tnFwCardWatchDog,
            tnFwCardProvisioningInfo
        }
        STATUS         current
        DESCRIPTION    ""
        ::= { tnSoftwareGroups 5 }

    tnInstalledFwGroup OBJECT-GROUP
        OBJECTS {
            tnInstalledFwCardType,
            tnInstalledFwFileName,
            tnInstalledFwIsDefault
        }
        STATUS         current
        DESCRIPTION    ""
        ::= { tnSoftwareGroups 6 }

    tnPortGroupGroup OBJECT-GROUP
        OBJECTS {
            tnPortGroupMode,
            tnPortGroupFwDownload,
            tnPortGroupFwCurrent
        }
        STATUS         current
        DESCRIPTION    ""
        ::= { tnSoftwareGroups 7 }

    tnInstalledFwPortGroupGroup OBJECT-GROUP
        OBJECTS {
            tnInstalledFwPortGroupIsDefault
        }
        STATUS         current
        DESCRIPTION    ""
        ::= { tnSoftwareGroups 8 }

    tnFwHitlessCardGroup OBJECT-GROUP
        OBJECTS {
            tnFwHitlessCardTrigger,
            tnFwHitlessCardLoadState,
            tnFwHitlessCardWatchDog
        }
        STATUS         current
        DESCRIPTION    ""
        ::= { tnSoftwareGroups 9 }

--------------------------------------------------------------------------------
-- Compliance Statements (mandatory)
--------------------------------------------------------------------------------
    tnSoftwareCompliance MODULE-COMPLIANCE
        STATUS         current
        DESCRIPTION    ""
        MODULE
        MANDATORY-GROUPS {
            tnSwNodeGroup,
            tnSwCardGroup,
            tnSwAuditScriptGroup,
            tnSwCpldGroup,
            tnFwCardGroup,
            tnInstalledFwGroup,
            tnPortGroupGroup,
            tnInstalledFwPortGroupGroup,
            tnFwHitlessCardGroup
        }
        ::= { tnSoftwareCompliances 1 }

END -- DEFINITION OF TROPIC-SOFTWARE-MIB
