TROPIC-TC DEFINITIONS ::= BEGIN

-- (c) Copyright 2016 Nokia.  All rights reserved.
-- This software is the confidential and proprietary property of
-- Nokia and may only be used in accordance with the
-- terms of the license agreement provided with this software.

 IMPORTS  
      SnmpAdminString                         FROM SNMP-FRAMEWORK-MIB
      OBJECT-TYPE, MODULE-IDENTITY,
      Unsigned32, Integer32, Counter32        FROM SNMPv2-SMI
      TEXTUAL-CONVENTION                      FROM SNMPv2-TC
      MODULE-COMPLIANCE, OBJECT-GROUP         FROM SNMPv2-CONF
      tnTypeDefinitionModules                 FROM TROPIC-GLOBAL-REG;

  tntcModule MODULE-IDENTITY
      LAST-UPDATED    "201607131200Z"
      ORGANIZATION    "Nokia"
      CONTACT-INFO    "Nokia
                       Postal: 600 March Rd.
                       Kanata, Ontario
                       Canada K2K 2E6

                       Phone: +1 613 591 3600
                       Fax:   +1 613 591 3680"

      DESCRIPTION "Nokia textual conventions."

      REVISION    "200803201200Z"
      DESCRIPTION "1) Updated the MIB file description.
                   2) Added conditions:
                      losO(203)              -- LOS-O
                      to
                      oprLoss(235)           -- OPR."

      REVISION    "200803261200Z"
      DESCRIPTION "Added entity types fc4g, fc10g and cbr2g5."

      REVISION    "200805061200Z"
      DESCRIPTION "1) Added conditions voltage, boardEqpt, init,
                      dbFl and dbFt.
                   2) Added the following to TnEntityType:
                      odu1(25),
                      odu2(26)."

      REVISION    "200805221200Z"
      DESCRIPTION "Added conditions fePortMm, timOdu, bdiOdu and
                   ssfOdu."

      REVISION    "200806251200Z"
      DESCRIPTION "Added VTS OCI and FDI conditions."

      REVISION    "200809111200Z"
      DESCRIPTION "Added NTP, DB, FW conditions."

      REVISION    "200809111200Z"
      DESCRIPTION "Cleaned up some existing conditions and added
                   the following conditions:
                   unknownSfpXfp(270)        -- UNKNOWN
                   to
                   losLdSig(272)             -- LOSLDSIG."

      REVISION    "200809241200Z"
      DESCRIPTION "Added System Ready condition."

      REVISION    "200811031200Z"
      DESCRIPTION "Added the following to TnCondition:
                   fpgaInit(276)             -- FPGAINIT
                   to
                   fpgaFail(278)             -- FPGAFAIL."

      REVISION    "200811141200Z"
      DESCRIPTION "Added the following to TnCondition:
                   condPwrMaxGain(279)       -- CONDPWRMAXGAIN."

      REVISION    "200811171200Z"
      DESCRIPTION "Change condPwrMaxGain to pwrMaxGain."

      REVISION    "200901071200Z"
      DESCRIPTION "Added the following to TnCondition:
                   invalidThreshold(280)     -- INVALIDTHRESHOLD."

      REVISION    "200902101200Z"
      DESCRIPTION "Added the following to TnCondition:
                   dataErr(281)              -- DATAERR."

      REVISION    "200903031200Z"
      DESCRIPTION "Defined AluWdmDisabledEnabled and AluWdmEnabledDisabled."

      REVISION    "200903031200Z"
      DESCRIPTION "Added port types fe and hdSdi."

      REVISION    "200903051200Z"
      DESCRIPTION "Added the following to TnCondition:
                   hwRevisionNotSupported(282) -- HWREVISIONNOTSUPPORTED."

      REVISION    "200903101200Z"
      DESCRIPTION "Added port types anyRate, fddi, esCon, dvbAsi, and dvi6000."

      REVISION    "200903221200Z"
      DESCRIPTION "1) Defined AluWdmTnIfType and added eVoa to it.
                   2) Deleted anyRate, hdSdi, fe, fddi, esCon, dvbAsi,
                      and dvi6000 from TnEntityType and added cbrar."

      REVISION    "200903241200Z"
      DESCRIPTION "1) Added otu3 and evoa to TnEntityType.
                   2) Added otu3 to AluWdmTnIfType."

      REVISION    "200903251200Z"
      DESCRIPTION "1) Changed swUpgCommit from deprecated to current.
                   2) Added odu3 to TnEntityType."

      REVISION    "200904271200Z"
      DESCRIPTION "Added the following to TnCondition:
                   farEndLos(283)            -- FARENDLOS
                   aprLine(284)              -- APRLINE."

      REVISION    "200905051200Z"
      DESCRIPTION "Added the following to TnCondition:
                   etrMismatch(285)          -- ETRMISMATCH."

      REVISION    "200905221200Z"
      DESCRIPTION "Added the following to TnCondition:
                   vtsOci11(286)             -- VTSOCI11
                   to
                   vtsFdi32(329)             -- VTSFDI32."

      REVISION    "200906041200Z"
      DESCRIPTION "Added the following to TnCondition:
                   envInput3Active(330)      -- ENV-3
                   to
                   envInput8Active(335)      -- ENV-8."

      REVISION    "200906091200Z"
      DESCRIPTION "Removed eVoa from AluWdmTnIfType."

      REVISION    "200906121200Z"
      DESCRIPTION "Added the following to TnCondition:
                   dormantUser(336)          -- DORMANTUSER
                   to
                   logBufOvflSecuLog(338)    -- LOGBUFOVFLSECULOG."

      REVISION    "200906141200Z"
      DESCRIPTION "Removed evoa from TnEntityType and renumbered list."

      REVISION    "200907171200Z"
      DESCRIPTION "Added the following to TnCondition:
                   vtsConnCreation(339)            -- VTSCONNCREATION
                   to
                   serverSignalFailureEgress(346)  -- SERVERSIGNALFAILUREEGRESS."

      REVISION    "200908201200Z"
      DESCRIPTION "Added the following to TnCondition:
                   oscSsf(347)               -- OSCSSF."

      REVISION    "200911011200Z"
      DESCRIPTION "1) Added the followeing to TnEntityType.
                      oc768stm256(30).
                   2) Added the following to AluWdmTnIfType:
                      oc768(32),
                      stm256(33)."

      REVISION    "200912231200Z"
      DESCRIPTION "Added the following to TnCondition:
                   oapumplaserbiascurrenthigh(348)             -- OAPumpbiasCurrHigh
                   to
                   sfpOrXfpOpticalReceiverPowerOutOfRange(358) -- SfpReceiverPwrOOR."

      REVISION    "201001041200Z"
      DESCRIPTION "1) Added otu4, odu4, fc8g, and hundredGige to TnEntityType.
                   2) Added otu4, fc8g, and hundredGige to AluWdmTnIfType."

      REVISION    "201001081200Z"
      DESCRIPTION "Added the following to TnCondition:
                   ramanSup(359)             -- RAMANSUP."

      REVISION    "201001151200Z"
      DESCRIPTION "1) Replaced laseroutputpoweroutofrange(350) with
                      laserEOL(350).
                   2) Renamed the following conditions:
                      sfpOrXfpLaserTemperatureOutOfRange(355)     -- SfpTempOOR
                      sfpOrXfpLaserEndOfLife(356)                 -- SfpEOL
                      sfpOrXfpOpticalTransmitPowerOutOfRange(357) -- SfpTrmtPwrOOR
                      sfpOrXfpOpticalReceiverPowerOutOfRange(358) -- SfpReceiverPwrOOR
                      to
                      msaTemp(355)              -- MSA_TEMP
                      msaEol(356)               -- MSA_EOL
                      msaOpt(357)               -- MSA_OPT
                      msaOpr(358)               -- MSA_OPR
                   3) Added the following to TnEntityType:
                      sdsdi(35).
                   4) Added the following to AluWdmTnIfType:
                      sdsdi(37)."

      REVISION    "201001241200Z"
      DESCRIPTION "Renamed the following conditions:
                   oaPumpLaserBiasCurrentHigh(348)  -- OAPumpbiasCurrHigh
                   oaPumpLaserTempHigh(349)  -- OAPumpTempHigh
                   laserEOL(350)             -- LASEREOL
                   modulatorOutputPowerOutOfRange(351)  --ModOutOpr
                   opticalPowerReceivedOutOfRange(352)  --OPROOR
                   b1SignalDegrade(353)      -- B1SD
                   fececSignalDegrade(354)   -- FECECSD
                   msaTemp(355)              -- MSA_TEMP
                   msaEol(356)               -- MSA_EOL
                   msaOpt(357)               -- MSA_OPT
                   msaOpr(358)               -- MSA_OPR
                   to
                   oaPumpBiasCurrHigh(348)   -- OAPUMPBIASCURRHIGH
                   oaPumpTempHigh(349)       -- OAPUMPTEMPHIGH
                   laserEOL(350)             -- LASEREOL
                   modOutOOR(351)            -- MODOUTOOR
                   oprOOR(352)               -- OPROOR
                   b1Sd(353)                 -- B1SD
                   fecEcSd(354)              -- FECECSD
                   sfpTempOOR(355)           -- SFPTEMPOOR
                   sfpEOL(356)               -- SFPEOL
                   sfpTrmtPwrOOR(357)        -- SFPTRMTPWROOR
                   sfpReceiverPwrOOR(358)    -- SFPRECEIVERPWROOR."

      REVISION    "201002011200Z"
      DESCRIPTION "Added the following to TnCondition:
                   rcvrOptProg(360)          -- RCVROPTPROG."

      REVISION    "201002081200Z"
      DESCRIPTION "Added the following to TnCondition:
                   cardNotAllowed(361)       -- CARDNOTALLOWED."

      REVISION    "201002161200Z"
      DESCRIPTION "Added the following to TnCondition:
                   fanSpeedMan(362)          -- FANSPEEDMAN."

      REVISION    "201002251200Z"
      DESCRIPTION "Added the following to TnCondition:
                   degOtu(363)               -- DEGOTU."

      REVISION    "201003031200Z"
      DESCRIPTION "Added the following to TnCondition:
                   mixedPFUsed(364)          -- MIXEDPFUSED."

      REVISION    "201004161200Z"
      DESCRIPTION "Added the following new alarm category to TnTrapCategory:
                   warningAlarms(12)."

      REVISION    "201005101200Z"
      DESCRIPTION "1) Marked sdsdi in TnEntityType as obsolete.
                   2) Added the following to TnCondition:
                      tBbeOtu(365)              -- T_BBE_OTU
                      to
                      tUasRst(408)              -- T_UAS_RST."

      REVISION    "201005181200Z"
      DESCRIPTION "1) Renamed conditions 365 to 408 for 15 minute bin
                      conditions by appending 15Min to the original
                      condition names.  For example:

                      tBbeOtu(365)              -- T_BBE_OTU
                      becomes
                      tBbeOtu15Min(365)         -- T_BBE_OTU_15MIN

                   2) Added 1 day bin conditions (409 to 452) by appending
                      1Day to the original condition names.  For example:

                      tBbeOtu(365)              -- T_BBE_OTU
                      becomes
                      tBbeOtu1Day(409)          -- T_BBE_OTU_1Day."

      REVISION    "201005271200Z"
      DESCRIPTION "1) Updated the sizes of the following to agree with
                      the software:
                      TropicCardSerialNumber from 10 to 16,
                      TropicCardManufacturingPartNumber from 12 to 16,
                      TropicCardSWGenericLoadName from 17 to 20.
                   2) Added the following to TnCondition:
                      eqptDgrOch(453)           -- EQPTDGROCH
                      to
                      incompatFan(479)          -- INCOMPATFAN."

      REVISION    "201005271200Z"
      DESCRIPTION "1) Added the following to AluWdmTnIfType:
                      e1(38).
                   2) Added the following to TnCondition:
                      clearAllTcas(480)         -- CLEARALLTCAS
                      to
                      tUasPt1Day(510)           -- T_UAS_PT_1DAY."

      REVISION    "201007071200Z"
      DESCRIPTION "Added the following to TnCondition:
                   lockoutOfPrVTS1(511)      -- LOCKOUTOFPRVTS1
                   to
                   postFecSd(573)            -- POSTFECSD."

      REVISION    "201007121200Z"
      DESCRIPTION "Added the following to TnCondition:
                   uruS(574)                 -- URUS."

      REVISION    "201007151200Z"
      DESCRIPTION "Added the following to TnCondition:
                   pwrTiltSusp(575)          -- PWRTILTSUSP."

      REVISION    "201007291200Z"
      DESCRIPTION "1) Renamed postFecSd to fecUbcSd.
                   2) Added the following to TnCondition:
                      ebero(576)                -- EBERO
                      to
                      msim(602)                 -- MSIM."

      REVISION    "201008291200Z"
      DESCRIPTION "1) Added the following to TnEntityType:
                      e1(35),
                      fe(36),
                      oms(37).
                   2) Added the following to TnCondition:
                      losOts(604)               -- LOSOTS
                      to
                      oduAisEgress(613)         -- ODUAISEGRESS."

      REVISION    "201009031200Z"
      DESCRIPTION "Added the following to TnCondition:
                   loam(603)                 -- LOAM."

      REVISION    "201009161200Z"
      DESCRIPTION "1) Added the following to TnEntityType:
                      timing(38).
                   2) Added the following to TnCondition:
                      frngSync(614)          -- FRNGSYNC
                      to
                      AisLM(618)             -- AISLM."

      REVISION    "201010161200Z"
      DESCRIPTION "Added the following to TnCondition:
                   uruOms(647)              -- URU-OMS
                   to
                   aprSwitch(666)           -- APRSWITCH."

      REVISION    "201010191200Z"
      DESCRIPTION "Added the following to AluWdmTnIfType:
                   sdi3g(39)."

      REVISION    "201011081200Z"
      DESCRIPTION "Added the following to TnCondition:
                   optIntDet(667)            -- OPTINTDET
                   to
                   uruOmsRx(671),            -- URUOMSRX
                   uruOtsLos(673),           -- URUOTSLOS
                   to
                   uruOchLos(673)            -- URUOCHLOS."

      REVISION    "201011301200Z"
      DESCRIPTION "1) Renamed timing(38) to sync(38) in TnEntityType.
                   2) Added the following to TnEntityType:
                      odu0(51),
                      to
                      lineRef(56).
                   3) Added the following to TnCondition:
                      manSwToInt(674),          -- MANSWTOINT
                      to
                      syncRefUnEq(681)          -- SYNCREFUNEQ."

      REVISION    "201012091200Z"
      DESCRIPTION "1) Renamed sync(38) to syncE(38) in TnEntityType.
                   2) Added the following to TnCondition:
                      pcsGeneratorActive(682),  -- PCSGENERATORACTIVE
                      ospfAdj(684)              -- OSPFADJ."

      REVISION    "201101161200Z"
      DESCRIPTION "1) Added the following to TnCondition:
                      uruOmsTx(672),            -- URUOMSTX
                      fdi(685),                 -- FDI
                      to
                      tBerPostFec1day(690)      -- T_BERPOSTFEC_1DAY.
                   2) Marked the following conditions as obsolete:
                      uruOts(471),              -- URUOTS
                      uruOms(647),              -- URU-OMS."

      REVISION    "201102041200Z"
      DESCRIPTION "Added the following to TnCondition:
                   lofLom(691)               -- LOFLOM."

      REVISION    "201102061200Z"
      DESCRIPTION "Added the following to TnCondition:
                   optIntBase(692)           -- OPTINTBASE."

      REVISION    "201102221200Z"
      DESCRIPTION "Added the following to TnCondition:
                   auAisP(693),              -- AUAISP
                   to
                   hpRdiP(697)               -- HPRDIP."

      REVISION    "201103081200Z"
      DESCRIPTION "Added the following to TnCondition:
                   intrusionEvt(698),        -- INTRUSIONEVT
                   autoSyncSw(702)           -- AUTOSYNCSW."

      REVISION    "201103191200Z"
      DESCRIPTION "1) Added the following to TnEntityType:
                      vts(57),
                      timing(58)
                   2) Added the following to TnCondition:
                      vtsOci(703),           -- VTSOCI
                      vtsFdi(704)            -- VTSFDI."

      REVISION    "201103281200Z"
      DESCRIPTION "1) Added the following to TnCondition:
                      transferLogFL(699),       -- TRANSFERLOGFL
                      transferLogFT(700),       -- TRANSFERLOGFT
                      transferLogIP(701)        -- TRANSFERLOGIP.
                   2) Defined AluWdmTransferProtocol."

      REVISION    "201103301200Z"
      DESCRIPTION "Added the following to TnCondition:
                   ntpLor(705)               -- NTPLOR."

      REVISION    "201104031200Z"
      DESCRIPTION "1) Added the following to TnCondition:
                      ntpClkAdj(706)            -- NTPCLKADJ
                   2) Added the following textual conventions:
                      AluWdmOtuBitRate
                      AluWdmOtuEncoding."

      REVISION    "201104041200Z"
      DESCRIPTION "Added the following to TnCondition:
                   inventoryError(707)       -- INVENTORYERROR."

      REVISION    "201104141200Z"
      DESCRIPTION "1) Added the following to TnCondition:
                      mepLoc(708),              -- MEPLOC
                      to
                      asonTopo(714)             -- ASONTOPO.
                   2) Added the following to TnEntityType:
                      mep(59)."

      REVISION    "201105021200Z"
      DESCRIPTION "1) Added the following textual convention:
                      AluWdmTcmLevelIndexType.
                   2) Added the following to TnEntityType:
                      odu2Tcm(60)
                      odu3Tcm(61).
                   3) Added the following to TnCondition:
                      ssfTcm(619),              -- SSFTCM
                      to
                      tFeuasTcm1Day(646)        -- T_FEUAS_TCM_1DAY."

      REVISION    "201105111200Z"
      DESCRIPTION "Added the following to TnCondition:
                   escLatchFail(715)         -- ESCLATCHFAIL."

      REVISION    "201105231200Z"
      DESCRIPTION "Added the following textual convention:
                   AluWdmCardCapacity."

      REVISION    "201105251200Z"
      DESCRIPTION "Added the following to TnCondition:
                   pwrAdjComms(716)          -- PWRADJCOMMS."

      REVISION    "201107021200Z"
      DESCRIPTION "Added the following to TnCondition:
                   lanSf(717)                -- LANSF."

      REVISION    "201108031200Z"
      DESCRIPTION "1) Added the following to TnCondition:
                      cardBoot(718)             -- CARDBOOT
                   2) Renamed syncE(38) to sync(38) in TnEntityType."

      REVISION    "201108311200Z"
      DESCRIPTION "Added the following to TnCondition:
                   lotOut(719)               -- LOTOUT."

      REVISION    "201109201200Z"
      DESCRIPTION "Added the following to TnCondition:
                   prcdrErrTopoOut(720),     -- PRCDRERRTOPOOUT
                   to
                   pwrAdjReqDrp(724)         -- PWRADJREQDRP."

      REVISION    "201110241200Z"
      DESCRIPTION "Added the following to TnCondition:
                   neModeMismatch(725)       -- NEMODEMISMATCH."

      REVISION    "201111091200Z"
      DESCRIPTION "Added the following to AluWdmTnIfType:
                   dcn(40),
                   to
                   otu2e(46)."

      REVISION    "201111161200Z"
      DESCRIPTION "1) Added the following to TnCondition:
                      ocsUnavail(726),          -- OCSUNAVAIL
                      to
                      nkm(728)                  -- NKM.
                   2) Added the following to AluWdmTnIfType:
                      fortyGige(47)."

      REVISION    "201111211200Z"
      DESCRIPTION "Added the following to TnEntityType:
                   fortyGige(62)."

      REVISION    "201112121200Z"
      DESCRIPTION "Added the following to TnCondition:
                   ocsAuditSuccess(729),     -- OCSAUDITSUCCESS
                   to
                   ssfCltEgr(734)            -- SSFCLTEGR."

      REVISION    "201112121200Z"
      DESCRIPTION "Added the following to TnCondition:
                   pwrTiltParams(735)        -- PWRTILTPARAMS."

      REVISION    "201201121200Z"
      DESCRIPTION "Added the following to TnCondition:
                   egressSSF(736),           -- EGRESSSSF
                   omsSSF(737)               -- OMSSSF."

      REVISION    "201202211200Z"
      DESCRIPTION "Added the following to TnCondition:
                   alienEgrLOS(738),         -- ALIENEGRLOS
                   to
                   fdiClt(740)               -- FDICLT."

      REVISION    "201202281200Z"
      DESCRIPTION "Added the following to TnCondition:
                   csfOduEgr(741)            -- CSFODUEGR."

      REVISION    "201203151200Z"
      DESCRIPTION "1) Moved the following textual convention from
                      TROPIC-OPTICALPORT-MIB:
                      AluWdmTtiStatus.
                   2) Added the following textual conventions:
                      AluWdmOdukStatus
                      AluWdmTimDetMode
                      AluWdmOthOdukCurrentStatusBits."

      REVISION    "201204101200Z"
      DESCRIPTION "Added the following to AluWdmTnIfType:
                   sdr(48)."

      REVISION    "201204241200Z"
      DESCRIPTION "Added the following textual convention:
                   AluWdmOthOdukRate."

      REVISION    "201204251200Z"
      DESCRIPTION "Added the following to AluWdmTnIfType:
                   ddr(49)."

      REVISION    "201205021200Z"
      DESCRIPTION "Added the following textual convention:
                   AluWdmOthOdukXcRate."

      REVISION    "201205241200Z"
      DESCRIPTION "1) Added the following to TnCondition:
                      lagLos(742),              -- LAGLOS
                      to
                      timOduOut(775),           -- TIMODUOUT.
                   2) Added the following to TnEntityType:
                      otu0(63),
                      to
                      odufTcm(137)."

      REVISION    "201206261200Z"
      DESCRIPTION "Added the following to TnEntityType:
                   otu2e(138),
                   otnFac(139)."

      REVISION    "201207141200Z"
      DESCRIPTION "Added the following to TnEntityType:
                   srSvc(140),
                   to
                   srErp(142)."

      REVISION    "201208061200Z"
      DESCRIPTION "1) Added the following to TnEntityType:
                      otu3e(143),
                      to
                      fc16g(161).
                   2) Added the following to TnCondition:
                      lol(792),                 -- LOL
                      to
                      mirrorSrcDisable(807)     -- MIRRORSRCDISABLE.
                   3) Added the following to AluWdmTnIfType:
                      tod(50),
                      to
                      qdr(54)."

      REVISION    "201208091200Z"
      DESCRIPTION "Added the following to TnCondition:
                   otmcpf(808)               -- OTMCPF."

      REVISION    "201208221200Z"
      DESCRIPTION "Added the following textual convention:
                   AluWdmOdukStateQualifier."

      REVISION    "201208281200Z"
      DESCRIPTION "1) Added the following to TnCondition:
                      wtocmaOsnrOomr(809),      -- WTOCMA_OSNROOMR
                      to
                      shelfInVoltLow(814)       -- SHELFINVOLTLOW.
                   2) Added the following to TnEntityType:
                      ddr(162),
                      sdr(163)."

      REVISION    "201209051200Z"
      DESCRIPTION "Added the following to TnCondition:
                   mirrorDestEnable(815),    -- MIRRORDESTENABLE
                   to
                   dcConfigFail(817)         -- DCCONFIGFAIL."

      REVISION    "201209061200Z"
      DESCRIPTION "Added the following to AluWdmTnIfType:
                   bits(55)."

      REVISION    "201209071200Z"
      DESCRIPTION "Added the following to TnCondition:
                   pwrEdfaMargin(818)        -- PWREDFAMARGIN."

      REVISION    "201209201200Z"
      DESCRIPTION "1) Added the following to TnCondition:
                      bitsLos(819),             -- BITSLOS
                      to
                      lockoutOfTimRefT4(828)    -- LOCKOUTOFTIMREFT4.
                   2) Added the following to TnEntityType:
                      bits(164),
                      sClock(165)."

      REVISION    "201209271200Z"
      DESCRIPTION "Added the following to TnCondition:
                   cardInitBcm(829),         -- CARDINITBCM
                   cardInitNonBcm(830)       -- CARDINITNONBCM."

      REVISION    "201210021200Z"
      DESCRIPTION "Added the following to TnCondition:
                   losEdfa(831)              -- LOSEDFA."

      REVISION    "201210121200Z"
      DESCRIPTION "Added the following to TropicStateQualifierType:
                   sdee(12)."

      REVISION    "201210221200Z"
      DESCRIPTION "Added the following to TnCondition:
                   oduAisOut(832),           -- ODUAISOUT
                   to
                   lofLomOut(834)            -- LOFLOMOUT."

      REVISION    "201211121200Z"
      DESCRIPTION "Added the following textual convention:
                   AluWdmTypeOfNetIfOperation."

      REVISION    "201211261200Z"
      DESCRIPTION "Added the following to TnCondition:
                   cpuPerformance(835),      -- CPUPERFORMANCE
                   contEqptSplit(836)        -- CONTEQPTSPLIT."

      REVISION    "201212051200Z"
      DESCRIPTION "Added the following to DESCRIPTION of AluWdmOtuEncoding:
                   cohpmqpskEnhOsnr(6)
                   to
                   icohpmqpsk(8)."

      REVISION    "201212181200Z"
      DESCRIPTION "Added the following to TnCondition:
                   csfGfpOut(837),           -- CSFGFPOUT
                   to
                   ptpPortSwitch(849)        -- PTPPORTSWITCH."

      REVISION    "201301261200Z"
      DESCRIPTION "Added the following to TnCondition:
                   rmdNDF(850),              -- RMDNDF
                   to
                   rmdEQF(853)               -- RMDEQF."

      REVISION    "201302141200Z"
      DESCRIPTION "Added the following to TnCondition:
                   cardIdRcvd(854),          -- CARDIDRCVD
                   to
                   fpgaInit10(873)           -- FPGAINIT10."

      REVISION    "201302211200Z"
      DESCRIPTION "Added the following to TnCondition:
                   slcCardInit(874),         -- SLCCARDINIT
                   to
                   slcClkSync(881)           -- SLCCLKSYNC."

      REVISION    "201302221200Z"
      DESCRIPTION "1) Added the following to TnCondition:
                      rmdIfEFMLOP(882),         -- RMDIFEFMLOP
                      to
                      fpgaPreLoad(888)          -- FPGAPRELOAD.
                   2) Added the following to TnEntityType:
                      rmd(166),
                      to
                      rmdIfMau(169)."

      REVISION    "201302261200Z"
      DESCRIPTION "Added the following to TnCondition:
                   csfGfp(889),              -- CSFGFP
                   gfpUpm(890)               -- GFPUPM."

      REVISION    "201303011200Z"
      DESCRIPTION "Added the following to TnCondition:
                   ssfSectionOut(891)        -- SSFSECTIONOUT."

      REVISION    "201303061200Z"
      DESCRIPTION "Added the following to TnCondition:
                   tFecUbc15Min(892),        -- T_FEC_UBC_15MIN
                   tFecUbc1Day(893)          -- T_FEC_UBC_1DAY."

      REVISION    "201303141200Z"
      DESCRIPTION "1) Added the following to TnCondition:
                      pgFpgaInit1(894),         -- PGFPGAINIT1
                      to
                      truBrkrOpen(905)          -- TRUBRKROPEN.
                   2) Added the following to TnEntityType:
                      tru(170).
                   3) Added the following to AluWdmTnIfType:
                      oneTru(56)."

      REVISION    "201303211200Z"
      DESCRIPTION "Added the following to TnCondition:
                   osnrMesc(906),            -- OSNRMESC
                   to
                   aesFipsFailure(908)       -- AESFIPSFAILURE."

      REVISION    "201303291200Z"
      DESCRIPTION "Renamed the following
                   fipsSfMismatch(855),      -- FIPSSFMISMATCH
                   to
                   fipsSwMismatch(855),      -- FIPSSWMISMATCH."

      REVISION    "201304091200Z"
      DESCRIPTION "1) Added the following to TnCondition:
                      todRefUnstable(909)       -- TODREFUNSTABLE.
                   2) Added the following to TnEntityType:
                      otu(171)."

      REVISION    "201305071200Z"
      DESCRIPTION "Marked the following as obsolete:
                   ptpGMDegrade(846),        -- PTPGMDEGRADE
                   to
                   ptpPortSwitch(849)        -- PTPPORTSWITCH."

      REVISION    "201305131200Z"
      DESCRIPTION "Renamed the following in TnEntityType:
                   sClock(165)
                   to
                   syncOut(165)."

      REVISION    "201305141200Z"
      DESCRIPTION "Added the following to TnCondition:
                   ochKeyUnavail(910),       -- OCHKEYUNAVAIL
                   to
                   ochKeysReused(912)        -- OCHKEYSREUSED."

      REVISION    "201305171200Z"
      DESCRIPTION "Added the following to TnCondition:
                   fan32HRqd(913)            -- FAN32HRQD."

      REVISION    "201305211200Z"
      DESCRIPTION "1) Added the following to TnCondition:
                      losOamp(914)              -- LOSOAMP
                   2) Added the following to AluWdmTnIfType:
                      otu4x2(57)."

      REVISION    "201306131200Z"
      DESCRIPTION "Added the following to AluWdmTnIfType:
                   otu1f(58),
                   cbr10g3(59),
                   fortyGigeMLD(60)."

      REVISION    "201306281200Z"
      DESCRIPTION "1) Added the following to TnEntityType:
                      otu1f(172),
                      to
                      srOamSaaCtl(180).
                   2) Added the following to TnCondition:
                      tPmonSapIngressPktsDropped15Min(915), -- T_PMON_SAPINGRESSPKTSDROPPED_15MIN
                      to
                      tPmonDmxfFdv1Day(986)                 -- T_PMON_DMXFFDV_1DAY."

      REVISION    "201308021200Z"
      DESCRIPTION "Added the following to TnCondition:
                   cfmLmTestComplete(987),   -- CFMLMTESTCOMPLETE
                   to
                   cbr10G3RxLSS(989)         -- CBR10G3RXLSS."

      REVISION    "201309101200Z"
      DESCRIPTION "1) Added the following to TnEntityType:
                      srMep(181),
                      to
                      netif(190).
                   2) Added the following to TnCondition:
                      lspFailedApe(990),     -- LSPFAILEDAPE
                      to
                      ssfOduTp(1025)         -- SSFODUTP."

      REVISION    "201309131200Z"
      DESCRIPTION "Added the following to TnCondition:
                   tPmonDmanfd15Min(1026),   -- T_PMON_DMANFD_15MIN
                   to
                   srTca(1058)               -- SRTCA."

      REVISION    "201309241200Z"
      DESCRIPTION "Added the following to TnCondition:
                   rmdCesChannelNoTdmPl(1059), -- RMDCESCHANNELNOTDMPL
                   to
                   rmdNimLOF(1062)           -- RMDNIMLOF."

      REVISION    "201310071200Z"
      DESCRIPTION "Added the following to TnEntityType:
                   rmdCesChannel(191),
                   rmdNim(192)."

      REVISION    "201311061200Z"
      DESCRIPTION "Added the following to TnCondition:
                   rmdIfLOS(1063),           -- RMDIFLOS
                   pwrSuspOut(1064)          -- PWRSUSPOUT."

      REVISION    "201311161200Z"
      DESCRIPTION "Added the following to TnCondition:
                   rmdDiscoveredDevice(1065) -- RMDDISCOVEREDDEVICE."

      REVISION    "201311221200Z"
      DESCRIPTION "Added the following to TnCondition:
                   tcmAis(1066)              -- TCMAIS."

      REVISION    "201312051200Z"
      DESCRIPTION "Added the following to TnCondition:
                   rmdTypeMismatch(1067)     -- RMDTYPEMISMATCH
                   to
                   rmdJbRecentered(1070)     -- RMDJBRECENTERED."

      REVISION    "201312061200Z"
      DESCRIPTION "1) Added the following to TnCondition:
                      tOprhLane1(1071),         -- T_OPRH_LANE_1
                      to
                      imageNotReady(1111)       -- IMAGENOTREADY.
                   2) Removed AluWdmTcmLevelIndexType."

      REVISION    "201312151200Z"
      DESCRIPTION "Added the following textual convention:
                   AluWdmWtClkValues."

      REVISION    "201401131200Z"
      DESCRIPTION "Added the following to TnCondition:
                   badClkFreq(1112),         -- BADCLKFREQ
                   to
                   esCableMismatch24(1137),  -- ESCABLEMISMATCH24."

      REVISION    "201401161200Z"
      DESCRIPTION "Added the following to TnCondition:
                   cardClkOffFreq(1138),     -- CARDCLKOFFFREQ
                   shelfInVoltMaxCur(1139)   -- SHELFINVOLTMAXCUR."

      REVISION    "201401241200Z"
      DESCRIPTION "Added the following to TnCondition:
                   fwMismatch(1140),         -- FWMISMATCH
                   to
                   fpgaFailNsa(1152),        -- FPGAFAILNSA."

      REVISION    "201401301200Z"
      DESCRIPTION "Added the following to TnCondition:
                   lagStateChange(1153),     -- LAGSTATECHANGE
                   lagMemberPortStateChange(1154) -- LAGMEMBERPORTSTATECHANGE."

      REVISION    "201402261200Z"
      DESCRIPTION "1) Added the following textual convention:
                      AluWdmDMInfoCurrentStatus.
                   2) Moved AluWdmFecMode from TROPIC-OPTICALPORT-MIB
                      to this file."

      REVISION    "201402281200Z"
      DESCRIPTION "Added the following to TnCondition:
                   packetCardInit(1155)      -- PACKETCARDINIT."

      REVISION    "201403191200Z"
      DESCRIPTION "1) Added the following to TnCondition:
                      frcRfCkSel(1156),         -- FRCRFCKSEL
                      to
                      aprLimited(1160)          -- APRLIMITED.
                   2) Marked the following in AluWdmFecMode as obsolete:
                      eFecI(7)
                      eFecE(8)
                      eFecB(9).
                   3) Renamed eSDFec(10) to sdFec(10) in AluWdmFecMode.
                   4) Moved AluWdmPortOchOtuRate from TROPIC-OPTICALPORT-MIB
                      to this file.
                   5) Added the following to AluWdmPortOchOtuRate:
                      otm27G952(13),
                      otm258G560(14)."

      REVISION    "201403201200Z"
      DESCRIPTION "Added the following to TnCondition:
                   insertMod(1161),          -- INSERTMOD
                   to
                   discoverMod(1163)         -- DISCOVERMOD."

      REVISION    "201404151200Z"
      DESCRIPTION "Added the following to TnCondition:
                   aprForced(1164)           -- APRFORCED."

      REVISION    "201404161200Z"
      DESCRIPTION "Added the following to TnCondition:
                   spiReadError(1165),       -- SPIREADERROR
                   shelfIncon(1166)          -- SHELFINCON."
      
      REVISION    "201405311200Z"
      DESCRIPTION "Changed sdFec(10) back to eSDFec(10) in AluWdmFecMode."

      REVISION    "201406161200Z"
      DESCRIPTION "Added the following to TnCondition:
                   configMM(1167)           -- CONFIGMM."

      REVISION    "201407241200Z"
      DESCRIPTION "Changed pwrSuspOut to pwrSuspRx in TnCondition."

      REVISION    "201408141200Z"
      DESCRIPTION "Added the following to TnCondition:
                   opticalTest(1168)         -- OPTICALTEST."

      REVISION    "201408211200Z"
      DESCRIPTION "Added the following to TnCondition:
                   hwAccessFailure(1169)     -- HWACCESSFAILURE."

      REVISION    "201408291200Z"
      DESCRIPTION "Added the following to TnCondition:
                   ftdEncrypt15Min(1170)     -- FTD_ENCRYPT_15MIN
                   ftdEncrypt1Day(1171)      -- FTD_ENCRYPT_1DAY
                   lagPortAddSuccess(1172)   -- LAGPORTADDSUCCESS."

      REVISION    "201409251200Z"
      DESCRIPTION "Added the following to TnCondition:
                   sdkMismatch(1173)            -- SDKMISMATCH
                   to
                   restrictedConnectivity(1180)  -- RESTRICTED_CONNECTIVITY."

      REVISION    "201410091200Z"
      DESCRIPTION "Changed the position of following in TnCondition:
                   ftdEncrypt15Min(1169),    -- FTD_ENCRYPT_15MIN
                   ftdEncrypt1Day(1170),     -- FTD_ENCRYPT_1DAY
                   lagPortAddSuccess(1171),  -- LAGPORTADDSUCCESS
                   hwAccessFailure(1172),    -- HWACCESSFAILURE."
     
      REVISION    "201410171200Z"
      DESCRIPTION "Added the following to AluWdmTnIfType:
                   interLaken(61),
                   otl410(62)."

      REVISION    "201410311200Z"
      DESCRIPTION "Added the following to TnCondition:
                   vwmIDFail(1181)  -- VWMIDFAIL."

      REVISION    "201412121200Z"
      DESCRIPTION "1) Added the following to TnCondition:
                      gfpExm(1182)              -- GFPEXM
                      syncMisc1(1183)           -- SYNCMISC1.
                   2) Added the following to AluWdmCardCapacity:
                      capacity2G(7)."

      REVISION    "201502131200Z"
      DESCRIPTION "1) Added the following to TnCondition:
                      sapPortStateChangeProcessed(1184), --SAP_PORT_STATE_CHANGE_PROCESSED
                      sapTlsMacMoveExceeded(1185) --SAP_MAC_MOVE_EXCEEDED."
      REVISION    "201503061200Z"
      DESCRIPTION "Restored these missing ones to TnCondition:
                         tUasOdu15MinOut(776),     -- T_UAS_ODU_15MIN_OUT
                         tUasOdu1DayOut(777),      -- T_UAS_ODU_1DAY_OUT
                         tSesOdu15MinOut(778),     -- T_SES_ODU_15MIN_OUT
                         tSesOdu1DayOut(779),      -- T_SES_ODU_1DAY_OUT
                         tEsOdu15MinOut(780),      -- T_ES_ODU_15MIN_OUT
                         tEsOdu1DayOut(781),       -- T_ES_ODU_1DAY_OUT
                         tBbeOdu15MinOut(782),     -- T_BBE_ODU_15MIN_OUT
                         tBbeOdu1DayOut(783),      -- T_BBE_ODU_1DAY_OUT
                         tFeUasOdu15MinOut(784),   -- T_FEUAS_ODU_15MIN_OUT
                         tFeUasOdu1DayOut(785),    -- T_FEUAS_ODU_1DAY_OUT
                         tFeSesOdu15MinOut(786),   -- T_FESES_ODU_15MIN_OUT
                         tFeSesOdu1DayOut(787),    -- T_FESES_ODU_1DAY_OUT
                         tFeEsOdu15MinOut(788),    -- T_FEES_ODU_15MIN_OUT
                         tFeEsOdu1DayOut(789),     -- T_FEES_ODU_1DAY_OUT
                         tFeBbeOdu15MinOut(790),   -- T_FEBBE_ODU_15MIN_OUT
                         tFeBbeOdu1DayOut(791),    -- T_FEBBE_ODU_1DAY_OUT."

      REVISION    "201504271200Z"
      DESCRIPTION "1) Added the following to TnCondition:
                      intfcOprDown(1186) -- INTFC-OPR-DWN."

      REVISION    "201505151200Z"
      DESCRIPTION "Added the following textual convention:
                   AluWdmAsapType."

      REVISION    "201505191200Z"
      DESCRIPTION "Added the following to TnCondition:
                    eCondHiRamanGain(1187),   -- LORAMGAIN
                    eCondLoRamanGain(1188),   -- HIRAMGAIN
                    eCondUruO(1189),          -- URU-O
                    eCondUruP(1190),          -- URU-P
                    mplsIfStateChange(1191),  -- MPLS-IF-STATE-CHANGE
                    mplsLspUp(1192),          -- MPLS-LSP-UP
                    eCondMplsLspDown(1193),   -- MPLS-LSP-DWN
                    mplsTpLspActivePathUp(1194),    -- MPLSTP-LSP-ACTIVE-PATH-UP
                    mplsTpLspActivePathChange(1195) -- MPLSTP-LSP-ACTIVE-PATH-CHANGE"

      REVISION    "201506241200Z"
      DESCRIPTION "Added the following to TnCondition:
                    eCondFrequencySlotMismatch(1196)  -- FREQUENCYSLOTMISMATCH"

      REVISION    "201506291200Z"
      DESCRIPTION "Added the following to TnCondition:
                    mplsTpLspPingTestComplete(1197)  --  LSP-PING-TEST
                    mplsTpLspTraceTestComplete(1198) -- LSP-TRACE-TEST"

      REVISION    "201507031200Z"
      DESCRIPTION "Added the following to AluWdmTnIfType:
                   otu4x4(63),
                   otu4Half(64),
                   otu4Halfx5(65)."

      REVISION    "201507171200Z"
      DESCRIPTION "Added the following to AluWdmFecMode:
                   usdfec(7)"

      REVISION    "201507201200Z"
      DESCRIPTION "Added the following to TnCondition:
                   mjcpf(1199)                , --  MJCPF
                   extIfFail(1200)            , --  EXTIFFAIL
                   sdpOprDwn(1201)            , --  SDP-OPR-DWN
                   sdpOprStatChg(1202)        , --  SDP-OPR-STAT-CHG
                   tPmonIntfcTransmittedPkts15Min(1203)   , --  T_PMON_INTFCTRANSMITTEDPKTS_15MIN
                   tPmonIntfcTransmittedPkts1Day(1204)    , --  T_PMON_INTFCTRANSMITTEDPKTS_1DAY
                   tPmonIntfcTransmittedOctets15Min(1205) , --  T_PMON_INTFCTRANSMITTEDOCTETS_15MIN
                   tPmonIntfcTransmittedOctets1Day(1206)  , --  T_PMON_INTFCTRANSMITTEDOCTETS_1DAY
                   tPmonIntfcReceivedPkts15Min(1207)      , --  T_PMON_INTFCRECEIVEDPKTS_15MIN
                   tPmonIntfcReceivedPkts1Day(1208)       , --  T_PMON_INTFCRECEIVEDPKTS_1DAY
                   tPmonIntfcReceivedOctets15Min(1209)    , --  T_PMON_INTFCRECEIVEDOCTETS_15MIN
                   tPmonIntfcReceivedOctets1Day(1210)     , --  T_PMON_INTFCRECEIVEDOCTETS_1DAY
                   tPmonSdpIngressForwardedPkts15Min(1211)  , --  T_PMON_SDPINGRESSFORWARDEDPKTS_15MIN
                   tPmonSdpIngressForwardedPkts1Day(1212)   , --  T_PMON_SDPINGRESSFORWARDEDPKTS_1DAY
                   tPmonSdpIngressForwardedOctets15Min(1213)  , --  T_PMON_SDPINGRESSFORWARDEDOCTETS_15MIN
                   tPmonSdpIngressForwardedOctets1Day(1214)   , --  T_PMON_SDPINGRESSFORWARDEDOCTETS_1DAY
                   tPmonSdpEgressForwardedPkts15Min(1215)     , --  T_PMON_SDPEGRESSFORWARDEDPKTS_15MIN
                   tPmonSdpEgressForwardedPkts1Day(1216)      , --  T_PMON_SDPEGRESSFORWARDEDPKTS_1DAY
                   tPmonSdpEgressForwardedOctets15Min(1217)   , --  T_PMON_SDPEGRESSFORWARDEDOCTETS_15MIN
                   tPmonSdpEgressForwardedOctets1Day(1218)    , --  T_PMON_SDPEGRESSFORWARDEDOCTETS_1DAY
                   sdpSpkOprDwn(1219)              , -- SDP-SPK-OPR-DWN
                   sdpSpkStateChg(1220)            , -- SDP-SPK-STATE-CHG
                   sdpBindOprStateChg(1221)          -- SDP-BIND-OPR-STATE-CHG"

      REVISION    "201508051200Z"
      DESCRIPTION "Added the following to TnEntityType:
                   mplsLsp(193),
                   sdpBind(194)"

      REVISION    "201508141200Z"
      DESCRIPTION "Added the following to TnEntityType:
                   mplsIf(195)"

      REVISION    "201509021200Z"
      DESCRIPTION "Added the following to TnCondition:
                   envInput9Active(1222),     -- ENV-9
                   envInput10Active(1223),     -- ENV-10
                   envInput11Active(1224),     -- ENV-11
                   envInput12Active(1225),     -- ENV-12
                   envInput13Active(1226),     -- ENV-13
                   envInput14Active(1227),     -- ENV-14
                   envInput15Active(1228),     -- ENV-15
                   envInput16Active(1229)      -- ENV-16."

      REVISION    "201509141200Z"
      DESCRIPTION "Added the following to AluWdmPortOchOtuRate:
                   otm268G925(15)."

      REVISION    "201509181200Z"
      DESCRIPTION "Added the following to TnCondition:
                   mplsMepLoc(1230),           -- MEP-LOC
                   mplsMepMmg(1231),           -- MEP-MMG
                   mplsMepUnm(1232),           -- MEP-UNM
                   mplsMepRdi(1233),           -- MEP-RDI
                   mplsMepUnp(1234),           -- MEP-UNP
                   vRtrBfdSessExtDown(1235),   -- BFD-SESS-DOWN
                   vRtrBfdSessExtDeleted(1236),  -- BFD-SESS-DELETED
                   vRtrBfdSessExtProtChange(1237),  -- BFD-SESS-PROT-CHANGE
                   mplsTpLspPtTypeMsmtch(1238),  -- MPLSTP-LSP-PTTYPE-MSMTCH
                   mplsTpLspRvrtMsmtch(1239)   -- MPLSTP-LSP-RVRT-MSMTCH"

      REVISION    "201509241200Z"
      DESCRIPTION "Added the following to AluWdmTnIfType:
                   sensor(66)."

      REVISION    "201509291200Z"
      DESCRIPTION "Added the following to TnCondition:
                   noAssociation(1240),          -- NoAssociation 
                   lanSignalDegrade(1241),       -- LANSIGNALDEGRADE
                   farEndSignalDegrade(1242),    -- FARENDSIGNALDEGRADE
                   farEndB1SignalDegrade(1243)   -- FARENDB1SIGNALDEGRADE"

      REVISION    "201507201200Z"
      DESCRIPTION "Added the following to TnCondition:
                   clusterUnavail(1244),         -- CLUSTERUNAVAIL
                   clusterAuditSuccess(1245),    -- CLUSTERAUDITSUCCESS
                   clusterAuditFail(1246),       -- CLUSTERAUDITFAIL
                   clusterUplinkDeleted(1247),   -- CLUSTERUPLINKDELETED
                   clusterDataRtrv(1248),        -- CLUSTERDATARTRV
                   clusterDataFlt(1249),         -- CLUSTERDATAFLT
                   clusterTrapFail(1250)         -- CLUSTERTRAPFAIL"

      REVISION    "201507171200Z"
      DESCRIPTION "Renamed the following from usdfec to sdFecG2:
                   AluWdmFecMode"

      REVISION    "201510121200Z"
      DESCRIPTION "1)Added the below to TnCondition:
                   vRtrBfdSessExtUp(1251)        -- BFD-SESS-UP"

      REVISION    "201510191200Z"
      DESCRIPTION "Added the following to TnEntityType:
                   mplsLspPath(196)"

      REVISION    "201510261200Z"
      DESCRIPTION "Added the following to TnEntityType:
                   sdpOpr(197)"

      REVISION    "201511041200Z"
      DESCRIPTION "1)Added the below to TnCondition:
                    occpCr(1252),                          -- OCCPCR
                    occpMj(1253),                          -- OCCPMJ
                    occpMn(1254),                          -- PCCPMN
                    shelfAirFilterMaintenance(1255),       -- INSPECTAIRFILTER
                    sdpBindEndPointTxActiveChanged(1256),  -- SDP-SPK-ACTIVE-CHANGE
                    sdpBindPwLocalStatusBitsChanged(1257), -- PW-LOCAL-STATUS-CHANGE
                    sdpBindPwPeerStatusBitsChanged(1258),  -- PW-PEER-STATUS-CHANGE
                    sdpBindPingTestComplete(1259),         -- PW-PING-TEST
                    sdpBindTraceTestComplete(1260)         -- PW-TRACE-TEST."

      REVISION    "201511131200Z"
      DESCRIPTION "1)Added the below to TnCondition:
                    hwrvunknown(1261)                   -- HWRVUNKNOWN."

      REVISION    "201511231200Z"
      DESCRIPTION "1)Added the below to TnCondition:
                    ecTypeMis(1262),                    -- ECTYPEMIS
                    latchOpen(1286)                     -- LATCHOPEN."

      REVISION    "201512071200Z"
      DESCRIPTION "1)Added the below to TnCondition:
                    xcMismatch(1287),                   -- XCMISMATCH
                    invalidXc(1288)                     -- INVALIDXC."

      REVISION    "201512101200Z"
      DESCRIPTION "1)Added the following to AluWdmFecMode:
                     hpFec(11).
                   2)Added the following to AluWdmPortOchOtuRate:
                     otm120G00(16)."

      REVISION    "201512241200Z"
      DESCRIPTION "Added the below to TnCondition:
                   cardThermShutdown(1289)              -- THERMSHUTD"

      REVISION    "201512291200Z"
      DESCRIPTION "Added the below to TnCondition:
                   sc1LinkFail(1290),                   -- SC1LNKFAI
                   sc2LinkFail(1291),                   -- SC2LNKFAI
                   sc3LinkFail(1292),                   -- SC3LNKFAI
                   scLinkFail(1293),                    -- SCLNKFAIL
                   sc1LinkDegarde(1294),                -- SC1LNKDGR
                   sc2LinkDegarde(1295),                -- SC2LNKDGR
                   sc3LinkDegarde(1296),                -- SC3LNKDGR
                   scLinkDegarde(1297)                  -- SCLNKDGR"

      REVISION    "201601271200Z"
      DESCRIPTION "Added the below to AluWdmAsapType:
                   packet(38)."

      REVISION    "201602011200Z"
      DESCRIPTION "1) Added the below to TnCondition:
                      faceplateMissing(1299)               -- FACEPLATEMISS.
                   2) Added the following textual convention:
                      TnRackSize."

      REVISION    "201602151200Z"
      DESCRIPTION "Added the below to TnCondition:
                   softwareError(1285)                -- SOFTWAREERROR."

      REVISION    "201602171200Z"
      DESCRIPTION "Added the below to TnCondition:
                   oaPumpBiasCurrHighC(1263),            -- OAPUMPBIASCURRHIGH-C
                   oaPumpBiasCurrHighL(1264),            -- OAPUMPBIASCURRHIGH-L
                   oaPumpTempHighC(1265),                -- OAPUMPTEMPHIGH-L
                   oaPumpTempHighL(1266),                -- OAPUMPTEMPHIGH-C
                   losPC(1267),                          -- LOS-P-C
                   losPL(1268),                          -- LOS-P-L
                   oprPwrLowC(1269),                     -- OPRPWRLOW-C
                   oprPwrLowL(1270),                     -- OPRPWRLOW-L
                   oprPwrHighC(1271),                    -- OPRPWRHIGH-C
                   oprPwrHighL(1272),                    -- OPRPWRHIGH-L
                   ampDisabledC(1273),                   -- AMPDISABLED-C
                   ampDisabledL(1274),                   -- AMPDISABLED-L
                   highGainC(1275),                      -- HIGAIN-C
                   highGainL(1276),                      -- HIGAIN-L
                   loGainC(1277),                        -- LOGAIN-C
                   loGainL(1278),                        -- LOGAIN-L
                   allChanMissOutC(1279),                -- ALLCHANMISS-OUT-C
                   allChanMissOutL(1280),                -- ALLCHANMISS-OUT-L
                   lotOutC(1281),                        -- LOT-OUT-C
                   lotOutL(1282),                        -- LOT-OUT-L
                   pwrMaxGainC(1283),                    -- PWRMAXGAIN-C
                   pwrMaxGainL(1284)                     -- PWRMAXGAIN-L."

      REVISION    "201602191200Z"
      DESCRIPTION "Added the following to TropicStateQualifierType:
                   mdlt(10),
                   noimp(11)."

      REVISION    "201603081200Z"
      DESCRIPTION "Added the below to TnCondition:
                   intOhFail(1298)                       -- INTOHFAIL."

      REVISION    "201603151200Z"                                                  
      DESCRIPTION "1)Added the following to TnEntityType:                            
                     srErpPath(198)                                                  
                   2)Added the below to TnCondition:                                 
                     erpRingStateChng(1301),             -- ERPRINGSTATECHNG       
                     erpRingPortStateChng(1302),         -- ERPRINGPORTSTATECHNG."

      REVISION    "201603181200Z"
      DESCRIPTION "Added the below to TnCondition:
                   invalidModule(1303)                   -- INVALIDMOD."

      REVISION    "201603301200Z"
      DESCRIPTION "Added the below to TnCondition:
                   intTsiFail(1304)                      -- INTTSIFAIL."

      REVISION    "201604011200Z"
      DESCRIPTION "Added the below to AluWdmPortOchOtuRate:
                   otm336G156(17),
                   otm537G850(18),
                   otm134G463(19),
                   otm131G679(20),
                   otm67G231(21)."

      REVISION    "201604061200Z"
      DESCRIPTION "Added the below to TnCondition:
                   ecModeMismatch(1305)                 -- ECMODEMISMATCH."

      REVISION    "201604081200Z"
      DESCRIPTION "Added the below to TnCondition:
                   dbCrcTypeMis(1306)                   -- DBCRCTYPEMIS."

      REVISION    "201604211200Z"
      DESCRIPTION "Added the following to TnEntityType:
                   lldp(199)
                   Added the below to TnCondition:
                   lldpRemTablesChange(1307)            -- LLDPREMTABLESCHANGE ."

      REVISION    "201604281200Z"
      DESCRIPTION "Added the below to TnCondition:
                   cardPowerOff(1300)                   -- CRDPWROFF."

      REVISION    "201605061200Z"
      DESCRIPTION "Added the below to TnCondition:
                   eqptCru(1308),                       -- EQPTCRU
                   shelfInvError(1309),                 -- SHELFINVERROR
                   shelfInvMismatch(1310)               -- SHELFINVMISMATCH."

      REVISION    "201605141200Z"
      DESCRIPTION "Added the below to TnCondition:
                   intSyncA(1311),                      -- INTSYNCA
                   intSyncB(1312),                      -- INTSYNCB
                   intSyncBoth(1313)                    -- INTSYNCBOTH."

      REVISION    "201605241200Z"
      DESCRIPTION "Added the below to TnCondition:
                   cKWKATMis(1314),                     -- CKWKATMIS
                   inventoryErrMod(1315),               -- INVENTORYERRMOD
                   lnkSpdDeg(1316),                     -- LNKSPDDEG
                   bdLnkSpd(1317)                       -- BDLNKSPD."

      REVISION    "201607121200Z"
      DESCRIPTION "Added the below to TnCondition:
                   fopOm(1318),                         -- FOP-OM
                   fopPm(1319),                         -- FOP-PM
                   fopSm(1320),                         -- FOP-SM
                   fopNr(1321),                         -- FOP-NR
                   fopIncon(1322),                      -- FOP-INCON
                   frcdWkSwBkFe(1323),                  -- FRCDWKSWBK-FE
                   frcdWkSwPrFe(1324),                  -- FRCDWKSWPR-FE
                   lockoutOfPrFe(1325),                 -- LOCKOUTOFPR-FE
                   manWkSwBkFe(1326),                   -- MANWKSWBK-FE
                   manWkSwPrFe(1327),                   -- MANWKSWPR-FE
                   wkSwBkFe(1328),                      -- WKSWBK-FE
                   wkSwPrFe(1329),                      -- WKSWPR-FE
                   wtrFe(1330),                         -- WTR-FE
                   exWkSwBk(1331),                      -- EXWKSWBK
                   exWkSwPr(1332),                      -- EXWKSWPR
                   exWkSwBkFe(1333),                    -- EXWKSWBK-FE
                   exWkSwPrFe(1334)                     -- EXWKSWPR-FE."


      ::= { tnTypeDefinitionModules 1 }

--------------------------------------------------------------------------------
-- Type Definitions
--------------------------------------------------------------------------------
    TropicCardCLEI ::= TEXTUAL-CONVENTION
        STATUS         current
        DESCRIPTION    ""
        SYNTAX         SnmpAdminString (SIZE(0..20))

    TropicCardHFD ::= TEXTUAL-CONVENTION
        STATUS         current
        DESCRIPTION    ""
        SYNTAX         SnmpAdminString (SIZE(0..2))

    TropicCardSerialNumber ::= TEXTUAL-CONVENTION
        STATUS         current
        DESCRIPTION    ""
        SYNTAX         SnmpAdminString (SIZE(0..16))

    TropicCardManufacturingPartNumber ::= TEXTUAL-CONVENTION
        STATUS         current
        DESCRIPTION    ""
        SYNTAX         SnmpAdminString (SIZE(0..16))

    TropicCardMarketingPartNumber ::= TEXTUAL-CONVENTION
        STATUS         current
        DESCRIPTION    ""
        SYNTAX         SnmpAdminString (SIZE(0..20))

    TropicCardSWGenericLoadName ::= TEXTUAL-CONVENTION
        STATUS         current
        DESCRIPTION    ""
        SYNTAX         SnmpAdminString (SIZE(0..20))

    TropicResetType ::= TEXTUAL-CONVENTION
        STATUS         current
        DESCRIPTION    ""
        SYNTAX         INTEGER {
                         noCmd(1),
                         warmReset(2),
                         coldReset(3)
                       }

    TropicShelfIndexType ::= TEXTUAL-CONVENTION
        STATUS         current
        DESCRIPTION    ""
        SYNTAX         Integer32 (1..256)

    TropicSlotIndexType ::= TEXTUAL-CONVENTION
        STATUS         current
        DESCRIPTION    ""
        SYNTAX         Integer32 (1..142)

    TropicPortIndexType ::= TEXTUAL-CONVENTION
        STATUS         current
        DESCRIPTION    ""
        SYNTAX         Integer32 (1..12)

    TropicChannelIndexType ::= TEXTUAL-CONVENTION
        STATUS         current
        DESCRIPTION    ""
        SYNTAX         Integer32 (1..256)

    TnTrapCategory ::= TEXTUAL-CONVENTION
        STATUS         current
        DESCRIPTION    "The event type associated with a trap queue."
        SYNTAX         INTEGER {
                         criticalAlarms(1),
                         majorAlarms(2),
                         minorAlarms(3),
                         stateChanges(4),
                         uiActions(5),
                         generalEvents(6),
                         notAlarmed(7),
                         none(8),
                         unknown(9),
                         notReported(10),
                         security(11),
                         warningAlarms(12)
                       }

    TropicAdminStateType ::= TEXTUAL-CONVENTION
        STATUS         current
        DESCRIPTION    ""
        SYNTAX         INTEGER {
                         up(1),
                         down(2),
                         testing(3)
                       }

    TropicOperationalStateType ::= TEXTUAL-CONVENTION
        STATUS         current
        DESCRIPTION    ""
        SYNTAX         INTEGER {
                         up(1),
                         down(2),
                         testing(3)
                       }

    TropicOperationalCapabilityType ::= TEXTUAL-CONVENTION
        STATUS         current
        DESCRIPTION    ""
        SYNTAX         INTEGER {
                         disabled(1),
                         enabled(2),
                         partiallyEnabled(3)
                       }

    TropicStateQualifierType ::= TEXTUAL-CONVENTION
        STATUS         current
        DESCRIPTION    ""
        SYNTAX         BITS {
                         portRxFault(0),
                         portTxFault(1),
                         locked(2),
                         ains(3),
                         flt(4),
                         mea(5),
                         uas(6),
                         ueq(7),
                         reserved8(8),
                         reserved9(9),
                         mdlt(10),
                         noimp(11),
                         sdee(12),
                         mt(13),
                         sgeo(14),
                         faf(15)
                       }

    TropicLEDColorType ::= TEXTUAL-CONVENTION
        STATUS         current
        DESCRIPTION    ""
        SYNTAX         INTEGER {
                         unknown(1),
                         off(2),
                         red(3),
                         green(4),
                         orange(5)
                       }

    TropicLEDStateType ::= TEXTUAL-CONVENTION
        STATUS         current
        DESCRIPTION    ""
        SYNTAX         INTEGER {
                         unknown(1),
                         solid(2),
                         fastBlink(3),
                         slowBlink(4)
                       }

    TnPerHopBehaviourType ::= TEXTUAL-CONVENTION
        STATUS         current
        DESCRIPTION    "The value of this object identifies the different
                        class of service types."
        SYNTAX         INTEGER {
                         ef(1),
                         af1(2),
                         af2(3),
                         be(4)
                       }

    TropicSonetOverheadByteType ::= TEXTUAL-CONVENTION
        STATUS         obsolete
        DESCRIPTION    ""
        SYNTAX         INTEGER (0..255)

    TnApsGroupId ::= TEXTUAL-CONVENTION
        STATUS         current
        DESCRIPTION    ""
        SYNTAX         Unsigned32

    TnStatsProfileId ::= TEXTUAL-CONVENTION
        STATUS         current
        DESCRIPTION    ""
        SYNTAX         Unsigned32

    TnSfpModuleState ::= TEXTUAL-CONVENTION
        STATUS         current
        DESCRIPTION    ""
        SYNTAX         INTEGER {
                         sfpWithoutSeep(1),
                         noSfp(2),
                         sfpWithSeep(3)
                       }

    TnSfpType ::= TEXTUAL-CONVENTION
        STATUS         current
        DESCRIPTION    ""
        SYNTAX         INTEGER {
                         standardSfp(1),
                         userSfp(2)
                       }

    TnEntityType ::= TEXTUAL-CONVENTION
        STATUS         current
        DESCRIPTION    ""
        SYNTAX         INTEGER {
                         all(1),
                         tenGige(2),
                         eqpt(3),
                         gige(4),
                         oc192stm64(5),
                         oc48stm16(6),
                         och(7),
                         ofa(8),
                         ots(9),
                         otu1(10),
                         otu2(11),
                         com(12),
                         log(13),
                         plk(14),
                         pm(15),
                         env(16),
                         oc3stm1(17),
                         oc12stm4(18),
                         session(19),
                         fc1g(20),
                         fc2g(21),
                         fc4g(22),
                         fc10g(23),
                         cbr2g5(24),
                         odu1(25),
                         odu2(26),
                         cbrar(27),
                         otu3(28),
                         odu3(29),
                         oc768stm256(30),
                         otu4(31),
                         odu4(32),
                         fc8g(33),
                         hundredGige(34),
                         e1(35),
                         fe(36),
                         oms(37),
                         sync(38),
                         odu0(51),
                         oduf(52),
                         odu1PTF(53),
                         loOdu(54),
                         optsg(55),
                         lineRef(56),
                         vts(57),
                         timing(58),
                         mep(59),
                         odu2Tcm(60),
                         odu3Tcm(61),
                         fortyGige(62),
                         otu0(63),
                         odu2e(64),
                         odu3e(65),
                         otuOdu0(66),
                         otuOdu1(67),
                         otuOdu2(68),
                         otuOdu2e(69),
                         otuOdu3(70),
                         otuOdu3e(71),
                         otuOdu4(72),
                         odu1Odu0(73),
                         odu2Odu0(74),
                         odu2Odu1(75),
                         odu2Oduf(76),
                         odu2eOdu0(77),
                         odu2eOdu1(78),
                         odu2eOduf(79),
                         odu3Odu0(80),
                         odu3Odu1(81),
                         odu3Odu2(82),
                         odu3Odu2e(83),
                         odu3Oduf(84),
                         odu3eOdu0(85),
                         odu3eOdu1(86),
                         odu3eOdu2(87),
                         odu3eOdu2e(88),
                         odu3eOduf(89),
                         odu4Odu0(90),
                         odu4Odu1(91),
                         odu4Odu2(92),
                         odu4Odu2e(93),
                         odu4Odu3(94),
                         odu4Odu3e(95),
                         odu4Oduf(96),
                         odu0Tcm(97),
                         odu1Tcm(98),
                         odu2eTcm(99),
                         odu3eTcm(100),
                         odu4Tcm(101),
                         lag(102),
                         tod(103),
                         ptpClock(104),
                         ptpPort(105),
                         otuOdu0Tcm(106),
                         otuOdu1Tcm(107),
                         otuOdu2Tcm(108),
                         otuOdu2eTcm(109),
                         otuOdu3Tcm(110),
                         otuOdu3eTcm(111),
                         otuOdu4Tcm(112),
                         odu1Odu0Tcm(113),
                         odu2Odu0Tcm(114),
                         odu2Odu1Tcm(115),
                         odu2OdufTcm(116),
                         odu2eOdu0Tcm(117),
                         odu2eOdu1Tcm(118),
                         odu2eOdufTcm(119),
                         odu3Odu0Tcm(120),
                         odu3Odu1Tcm(121),
                         odu3Odu2Tcm(122),
                         odu3Odu2eTcm(123),
                         odu3OdufTcm(124),
                         odu3eOdu0Tcm(125),
                         odu3eOdu1Tcm(126),
                         odu3eOdu2Tcm(127),
                         odu3eOdu2eTcm(128),
                         odu3eOdufTcm(129),
                         odu4Odu0Tcm(130),
                         odu4Odu1Tcm(131),
                         odu4Odu2Tcm(132),
                         odu4Odu2eTcm(133),
                         odu4Odu3Tcm(134),
                         odu4Odu3eTcm(135),
                         odu4OdufTcm(136),
                         odufTcm(137),
                         otu2e(138),
                         otnFac(139),
                         srSvc(140),
                         srSap(141),
                         srErp(142),
                         otu3e(143),
                         otu3e2(144),
                         odu3e2(145),
                         odu3e2Tcm(146),
                         otuOdu3e2(147),
                         otuOdu3e2Tcm(148),
                         odu3e2Odu0(149),
                         odu3e2Odu0Tcm(150),
                         odu3e2Odu1(151),
                         odu3e2Odu1Tcm(152),
                         odu3e2Odu2(153),
                         odu3e2Odu2Tcm(154),
                         odu3e2Odu2e(155),
                         odu3e2Odu2eTcm(156),
                         odu3e2Oduf(157),
                         odu3e2OdufTcm(158),
                         odu4Odu3e2(159),
                         odu4Odu3e2Tcm(160),
                         fc16g(161),
                         ddr(162),
                         sdr(163),
                         bits(164),
                         syncOut(165),
                         rmd(166),
                         rmdMep(167),
                         rmdIf(168),
                         rmdIfMau(169),
                         tru(170),
                         otu(171),
                         otu1f(172),
                         odu1f(173),
                         odu1fTcm(174),
                         otuOdu1f(175),
                         otuOdu1fTcm(176),
                         odu4Odu1f(177),
                         odu4Odu1fTcm(178),
                         cbr10g3(179),
                         srOamSaaCtl(180),
                         srMep(181),
                         lsp(182),
                         gmreNode(183),
                         cpNeighbor(184),
                         cpRsvp(185),
                         cpDpr(186),
                         cpLmp(187),
                         teLink(188),
                         dbLink(189),
                         netif(190),
                         rmdCesChannel(191),
                         rmdNim(192),
                         mplsLsp(193),
                         sdpBind(194),
                         mplsIf(195),
                         mplsLspPath(196),
                         sdpOpr(197),
                         srErpPath(198),
                         lldp(199)
                       }

    TnCondition ::= TEXTUAL-CONVENTION
        STATUS         current
        DESCRIPTION    ""
        SYNTAX         INTEGER {
                         aisLmsAis(1),             -- AIS-L (SDH MS-AIS)
                         allChanMiss(2),           -- ALLCHANMISS
                         ampDisabled(3),           -- AMPDISABLED
                         ampEol(4),                -- deprecated
                         apsB(5),                  -- APSB
                         apsCm(6),                 -- APSCM
                         apsMm(7),                 -- APSMM
                         apsNoRed(8),              -- APSNORED
                         brkTrip(9),               -- BRKTRIP
                         capBufr(10),              -- CAPBUFR
                         cardInBoot(11),           -- CARDINBOOT
                         cardInit(12),             -- CARDINIT
                         cardInitFail(13),         -- deprecated
                         cardSanity(14),           -- CARDSANITY
                         contCom(15),              -- CONTCOM
                         contr(16),                -- CONTR
                         dbFull(17),               -- DBFULL
                         dbInvalid(18),            -- DBINVALID
                         dbMemTrf(19),             -- DBMEMTRF
                         dwAis(20),                -- DW-AIS
                         dwLof(21),                -- DW-LOF
                         dwSd(22),                 -- DW-SD
                         dwSf(23),                 -- DW-SF
                         eqpt(24),                 -- EQPT
                         facTerm(25),              -- FACTERM
                         fanSpeed(26),             -- FANSPEED
                         feAls(27),                -- deprecated
                         feFlt(28),                -- deprecated
                         fePrLf(29),               -- FEPRLF
                         flt(30),                  -- FLT
                         frcdWkSwBk(31),           -- FRCDWKSWBK
                         frcdWkSwPr(32),           -- FRCDWKSWPR
                         hdFail(33),               -- deprecated
                         hdFull(34),               -- deprecated
                         highGain(35),             -- HIGAIN
                         int(36),                  -- INT
                         intSft(37),               -- INTSFT
                         intTemp(38),              -- INTTEMP
                         linkDown(39),             -- LINKDOWN
                         lockoutToPr(40),          -- LOCKOUTTOPR
                         lof(41),                  -- LOF
                         loGain(42),               -- LOGAIN
                         los(43),                  -- LOS
                         losOut(44),               -- LOS-OUT
                         lostClock(45),            -- LOSTCLOCK
                         lpbkLine(46),             -- LPBKLINE
                         lpbkTerm(47),             -- LPBKTERM
                         lsrOutDgr(48),            -- LSROUTDGR
                         manWkSwBk(49),            -- MANWKSWBK
                         manWkSwPr(50),            -- MANWKSWPR
                         mismatch(51),             -- MISMATCH
                         mod(52),                  -- MOD
                         neAls(53),                -- NE-ALS
                         neFlt(54),                -- NE-FLT
                         net(55),                  -- NET
                         ochCollision(56),         -- OCHCOLLISION
                         ochIntErr(57),            -- deprecated
                         ochMissing(58),           -- OCHMISSING
                         ochUnknown(59),           -- OCHUNKNOWN
                         opr(60),                  -- OPR
                         oprUnachieve(61),         -- OPRUNACHIEVE
                         ovrld(62),                -- OVRLD
                         prcdrErr(63),             -- PRCDRERR
                         pwr(64),                  -- PWR
                         replUnitMiss(65),         -- REPLUNITMISS
                         rfi(66),                  -- RFI
                         rfiLmsRfi(67),            -- RFI-L (SDH MS-RFI)
                         sd(68),                   -- SDBER
                         sf(69),                   -- EBER
                         swEqpt(70),               -- SWEQPT
                         swMtxMod(71),             -- SWMTXMOD
                         sync(72),                 -- SYNC
                         syncClk(73),              -- SYNCCLK
                         syncEqpt(74),             -- SYNCEQPT
                         syncOos(75),              -- SYNCOOS
                         termOc192stm64(76),       -- deprecated
                         termOc312stm14(77),       -- deprecated
                         termOc48stm16(78),        -- deprecated
                         termOtu1(79),             -- deprecated
                         termOtu2(80),             -- deprecated
                         tim(81),                  -- TIM
                         trmt(82),                 -- TRMT
                         unknown(83),              -- UNKNOWN
                         wkSwPr(84),               -- WKSWPR
                         sysBoot(85),              -- SYSBOOT
                         unknownNotif(86),         -- UNKNOWNNOTIF
                         change(87),               -- CHANGE
                         almRSync(88),             -- ALM-RSYNC
                         almRSyncEnd(89),          -- ALM-RSYNCEND
                         linkUp(90),               -- LINKUP
                         crdInit(91),              -- CRDINIT
                         configFail(92),           -- CONFIGFAIL
                         sysInit(93),              -- SYSINIT
                         syncCommand(94),          -- SYNCCOMMAND
                         syncActRef(95),           -- SYNCACTREF
                         syncClkUnit(96),          -- SYNCCLKUNIT
                         ledState(97),             -- LEDSTATE
                         intErr(98),               -- INTERR
                         seepScrub(99),            -- SEEPSCRUB
                         unexWkSet(100),           -- UNEXWKSET
                         ccActChg(101),            -- CCACTCHG
                         crTca(102),               -- CRTCA
                         mjTca(103),               -- MJTCA
                         mnTca(104),               -- MNTCA
                         warnTca(105),             -- WARNTCA
                         binsRolled(106),          -- BINSROLLED
                         swUpgrade(107),           -- deprecated
                         swUpgFail(108),           -- SWUPGFAIL
                         wkSwBk(109),              -- WKSWBK
                         pwrMgtOff(110),           -- PWRMGTOFF
                         invalidTopo(111),         -- INVALIDTOPO
                         man(112),                 -- MAN
                         syncClkMode(113),         -- deprecated
                         syncMode(114),            -- SYNCMODE
                         swToSec(115),             -- SWTOSEC
                         ochKeyDup(116),           -- OCHKEYDUP
                         ochKeyOverlap(117),       -- OCHKEYOVERLAP
                         ochTrailDup(118),         -- OCHTRAILDUP
                         authFail(119),            -- AUTHFAIL
                         lockoutOfPr(120),         -- LOCKOUTOFPR
                         intrusion(121),           -- INTRUSION
                         syncStatChng(122),        -- SYNCSTATCHNG
                         facServ(123),             -- deprecated
                         bkupCom(124),             -- deprecated
                         contEqpt(125),            -- CONTEQPT
                         swUpgCommit(126),         -- SWUPGCOMMIT
                         lopPauLop(127),           -- LOP-P (SDH AU-LOP)
                         syncClkHldovr(128),       -- HLDOVRSYNC
                         syncClkFrng(129),         -- FRNGSYNC
                         arcIND(130),              -- ARC-IND
                         vcgDown(131),             -- deprecated
                         dataFlt(132),             -- DATAFLT
                         sfMismatch(133),          -- SFMISMATCH
                         usAls(134),               -- USALS
                         usFlt(135),               -- USFLT
                         aisPauAis(136),           -- AIS-P (SDH AU-AIS)
                         rfiPauRfi(137),           -- RFI-P (SDH AU-RFI)
                         plmPauPlm(138),           -- PLM-P (SDH AU-PLM)
                         pdiPauPdi(139),           -- PDI-P (SDH AU-PDI)
                         gfpLof(140),              -- GFPLOF
                         gfpSsf(141),              -- GFPSSF
                         vcgLoa(142),              -- VCGLOA
                         vcgMap(143),              -- deprecated
                         ochFdi(144),              -- OCHFDI
                         ochPwrUnstable(145),      -- deprecated
                         manSwToPri(146),          -- MANSWTOPRI
                         manSwToSec(147),          -- MANSWTOSEC
                         usAis(148),               -- USAIS
                         usSFEber(149),            -- USSFEBER
                         fecFail(150),             -- FECFAIL
                         plm(151),                 -- PLM-P (SDH AU-PLM)
                         usIdle(152),              -- USIDLE
                         comm(153),                -- COMM
                         pwrSusp(154),             -- PWRSUSP
                         contrenFail(155),         -- deprecated
                         contrenDgr(156),          -- deprecated
                         chkBkplane(157),          -- deprecated
                         allChanMissOut(158),      -- ALLCHANMISS-OUT
                         ochCollisionOut(159),     -- OCHCOLLISION-OUT
                         ochUnknownOut(160),       -- OCHUNKNOWN-OUT
                         oprOut(161),              -- OPR-OUT
                         pwrAdjReq(162),           -- PWRADJREQ
                         pwrAdjFail(163),          -- PWRADJFAIL
                         vcMfi(164),               -- VCMFI
                         eqptDgrOut(165),          -- EQPTDGR-OUT
                         contrOut(166),            -- CONTR-OUT
                         ochPdi(167),              -- OCHPDI
                         autoReset(168),           -- AUTORESET
                         pwrMargin(169),           -- PWRMARGIN
                         contBus(170),             -- CONTBUS
                         contrDup(171),            -- CONTRDUP
                         missing(172),             -- MISSING
                         facTermDev(173),          -- FACTERM-DEV
                         facTermDgr(174),          -- FACTERM-DGR
                         mtcesurv(175),            -- MTCESURV
                         mtcesurvDgr(176),         -- MTCESURVDGR
                         contComm(177),            -- deprecated
                         manReset(178),            -- MANRESET
                         pwrAlmp(179),             -- PWR-ALMP
                         pwrFan(180),              -- PWR-FAN
                         pdi(181),                 -- PDI
                         sft(182),                 -- SFT
                         swftDwn(183),             -- SWFTDWN
                         inhMsgPmRept(184),        -- INHMSG-PMREPT
                         slcr(185),                -- SLCR
                         laserOffLpbk(186),        -- LASEROFFLPBK
                         otuAis(187),              -- OTU-AIS
                         ochTrailUnknown(188),     -- OCHTRAILUNKNOWN
                         netCraft(189),            -- NET-CRAFT
                         usOchCollision(190),      -- USOCHCOLLISION
                         syncClkFail(191),         -- SYNCCLKFAIL
                         syncSys(192),             -- SYNCSYS
                         syncSysOos(193),          -- SYNCSYSOOS
                         usLos(194),               -- USLOS
                         eqptDgr(195),             -- EQPTDGR
                         dbErr(196),               -- DBERR
                         dwLom(197),               -- LOM
                         prcdrErrOut(198),         -- PRCDRERR-OUT
                         oprIngress(199),          -- OPR
                         eqptDgrMon(200),          -- EQPTDGRMON
                         prcdrErrTopo(201),        -- PRCDRERR-TOPO
                         userEqptMismatch(202),    -- USEREQPT-MISMATCH
                         envInput1Active(203),     -- ENV-1
                         envInput2Active(204),     -- ENV-2
                         sdegO(205),               -- SDEG-O
                         losDcm(206),              -- LOSDCM
                         baseline(207),            -- BASELINE
                         lss(208),                 -- LANLSS
                         lfd(209),                 -- LFD
                         upm(210),                 -- UPM
                         vcgSsf(211),              -- VCGSSF
                         fePortMismatch(212),      -- FEPORTMISMATCH
                         feLss(213),               -- FELANLSS
                         feLos(214),               -- FELANLOS
                         feLfi(215),               -- FELANLFI
                         feRfi(216),               -- FELANRFI
                         lofEgr(217),              -- LOFEGR
                         lssEgr(218),              -- LSSEGR
                         lfiEgr(219),              -- LFIEGR
                         rfiEgr(220),              -- RFIEGR
                         lck(221),                 -- LCK
                         oci(222),                 -- OCI
                         ssf(223),                 -- SSF
                         bdi(224),                 -- BDI
                         hiBer(225),               -- HIBER
                         excessLoad(226),          -- EXCESSLOAD
                         losP(227),                -- LOS-P
                         deg(228),                 -- DEG
                         lanLos(229),              -- LANLOS
                         lanLfi(230),              -- LANLFI
                         lanRfi(231),              -- LANRFI
                         notUsed1(232),            -- defunct
                         notUsed2(233),            -- defunct
                         rdiL(234),                -- RDIL
                         notUsed3(235),            -- defunct
                         voltage(236),             -- VOLTAGE
                         boardEqpt(237),           -- EQPT
                         init(238),                -- INIT
                         dbFl(239),                -- DBFL
                         dbFt(240),                -- DBFT
                         notUsed4(241),            -- defunct
                         timOdu(242),              -- TIMODU
                         bdiOdu(243),              -- BDIODU
                         ssfOdu(244),              -- SSFODU
                         vtsOci1(245),             -- VTSOCI1
                         vtsOci2(246),             -- VTSOCI2
                         vtsOci3(247),             -- VTSOCI3
                         vtsOci4(248),             -- VTSOCI4
                         vtsOci5(249),             -- VTSOCI5
                         vtsOci6(250),             -- VTSOCI6
                         vtsOci7(251),             -- VTSOCI7
                         vtsOci8(252),             -- VTSOCI8
                         vtsOci9(253),             -- VTSOCI9
                         vtsOci10(254),            -- VTSOCI10
                         vtsFdi1(255),             -- VTSFDI1
                         vtsFdi2(256),             -- VTSFDI2
                         vtsFdi3(257),             -- VTSFDI3
                         vtsFdi4(258),             -- VTSFDI4
                         vtsFdi5(259),             -- VTSFDI5
                         vtsFdi6(260),             -- VTSFDI6
                         vtsFdi7(261),             -- VTSFDI7
                         vtsFdi8(262),             -- VTSFDI8
                         vtsFdi9(263),             -- VTSFDI9
                         vtsFdi10(264),            -- VTSFDI10
                         ntpOoSync(265),           -- NTPOOSYNC
                         dbUnsync(266),            -- DBUNSYNC
                         fwVersionNotDefault(267), -- FWVERSIONNOTDEFAULT
                         fwUpgradePending(268),    -- FWUPGRADEPENDING
                         fwPendingObsolete(269),   -- FWPENDINGOBSOLETE
                         unknownSfpXfp(270),       -- UNKNOWN
                         mismatchSfpXfp(271),      -- MISMATCH
                         losLdSig(272),            -- LOSLDSIG
                         losO(273),                -- LOS-O
                         lofO(274),                -- LOF-O
                         systemReady(275),         -- SYSTEMREADY
                         fpgaInit(276),            -- FPGAINIT
                         fpgaTimeout(277),         -- FPGATIMEOUT
                         fpgaFail(278),            -- FPGAFAIL
                         pwrMaxGain(279),          -- PWRMAXGAIN
                         invalidThreshold(280),    -- INVALIDTHRESHOLD
                         dataErr(281),             -- DATAERR
                         hwRevisionNotSupported(282),-- HWREVISIONNOTSUPPORTED
                         farEndLos(283),           -- FARENDLOS
                         aprLine(284),             -- APRLINE
                         etrMismatch(285),         -- ETRMISMATCH
                         vtsOci11(286),            -- VTSOCI11
                         vtsOci12(287),            -- VTSOCI12
                         vtsOci13(288),            -- VTSOCI13
                         vtsOci14(289),            -- VTSOCI14
                         vtsOci15(290),            -- VTSOCI15
                         vtsOci16(291),            -- VTSOCI16
                         vtsOci17(292),            -- VTSOCI17
                         vtsOci18(293),            -- VTSOCI18
                         vtsOci19(294),            -- VTSOCI19
                         vtsOci20(295),            -- VTSOCI20
                         vtsOci21(296),            -- VTSOCI21
                         vtsOci22(297),            -- VTSOCI22
                         vtsOci23(298),            -- VTSOCI23
                         vtsOci24(299),            -- VTSOCI24
                         vtsOci25(300),            -- VTSOCI25
                         vtsOci26(301),            -- VTSOCI26
                         vtsOci27(302),            -- VTSOCI27
                         vtsOci28(303),            -- VTSOCI28
                         vtsOci29(304),            -- VTSOCI29
                         vtsOci30(305),            -- VTSOCI30
                         vtsOci31(306),            -- VTSOCI31
                         vtsOci32(307),            -- VTSOCI32
                         vtsFdi11(308),            -- VTSFDI11
                         vtsFdi12(309),            -- VTSFDI12
                         vtsFdi13(310),            -- VTSFDI13
                         vtsFdi14(311),            -- VTSFDI14
                         vtsFdi15(312),            -- VTSFDI15
                         vtsFdi16(313),            -- VTSFDI16
                         vtsFdi17(314),            -- VTSFDI17
                         vtsFdi18(315),            -- VTSFDI18
                         vtsFdi19(316),            -- VTSFDI19
                         vtsFdi20(317),            -- VTSFDI20
                         vtsFdi21(318),            -- VTSFDI21
                         vtsFdi22(319),            -- VTSFDI22
                         vtsFdi23(320),            -- VTSFDI23
                         vtsFdi24(321),            -- VTSFDI24
                         vtsFdi25(322),            -- VTSFDI25
                         vtsFdi26(323),            -- VTSFDI26
                         vtsFdi27(324),            -- VTSFDI27
                         vtsFdi28(325),            -- VTSFDI28
                         vtsFdi29(326),            -- VTSFDI29
                         vtsFdi30(327),            -- VTSFDI30
                         vtsFdi31(328),            -- VTSFDI31
                         vtsFdi32(329),            -- VTSFDI32
                         envInput3Active(330),     -- ENV-3
                         envInput4Active(331),     -- ENV-4
                         envInput5Active(332),     -- ENV-5
                         envInput6Active(333),     -- ENV-6
                         envInput7Active(334),     -- ENV-7
                         envInput8Active(335),     -- ENV-8
                         dormantUser(336),         -- DORMANTUSER
                         logBuf90SecuLog(337),     -- LOGBUF90SECULOG
                         logBufOvflSecuLog(338),   -- LOGBUFOVFLSECULOG
                         vtsConnCreation(339),     -- VTSCONNCREATION
                         lockedIndicationEgress(340), -- LOCKEDINDICATIONEGRESS
                         openConnectionIndicationEgress(341), -- OPENCONNECTIONINDICATIONEGRESS
                         signalDegradeEgress(342), -- SIGNALDEGRADEEGRESS
                         backwardDefectIndicationEgress(343), -- BACKWARDDEFECTINDICATIONEGRESS
                         trailTraceIdentifierMismatchEgress(344), -- trailTraceIdentifierMismatchEgress
                         payloadTypeMismatchEgress(345), -- PAYLOADTYPEMISMATCHEGRESS
                         serverSignalFailureEgress(346), -- SERVERSIGNALFAILUREEGRESS
                         oscSsf(347),              -- OSCSSF
                         oaPumpBiasCurrHigh(348),  -- OAPUMPBIASCURRHIGH
                         oaPumpTempHigh(349),      -- OAPUMPTEMPHIGH
                         laserEOL(350),            -- LASEREOL
                         modOutOOR(351),           -- MODOUTOOR
                         oprOOR(352),              -- OPROOR
                         b1Sd(353),                -- B1SD
                         fecEcSd(354),             -- FECECSD
                         sfpTempOOR(355),          -- SFPTEMPOOR
                         sfpEOL(356),              -- SFPEOL
                         sfpTrmtPwrOOR(357),       -- SFPTRMTPWROOR
                         sfpReceiverPwrOOR(358),   -- SFPRECEIVERPWROOR
                         ramanSup(359),            -- RAMANSUP
                         rcvrOptProg(360),         -- RCVROPTPROG
                         cardNotAllowed(361),      -- CARDNOTALLOWED
                         fanSpeedMan(362),         -- FANSPEEDMAN
                         degOtu(363),              -- DEGOTU
                         mixedPFUsed(364),         -- MIXEDPFUSED
                         tBbeOtu15Min(365),        -- T_BBE_OTU_15MIN
                         tBbeRs15Min(366),         -- T_BBE_RS_15MIN
                         tCv15Min(367),            -- T_CV_15MIN
                         tCvPcs15Min(368),         -- T_CV_PCS_15MIN
                         tCvPcst15Min(369),        -- T_CV_PCST_15MIN
                         tCvs15Min(370),           -- T_CVS_15MIN
                         tCvst15Min(371),          -- T_CVST_15MIN
                         tEs15Min(372),            -- T_ES_15MIN
                         tEsOtu15Min(373),         -- T_ES_OTU_15MIN
                         tEsRs15Min(374),          -- T_ES_RS_15MIN
                         tEsPcs15Min(375),         -- T_ES_PCS_15MIN
                         tEsPcst15Min(376),        -- T_ES_PCST_15MIN
                         tEss15Min(377),           -- T_ESS_15MIN
                         tEthpkter15Min(378),      -- T_ETHPKTER_15MIN
                         tEthpktert15Min(379),     -- T_ETHPKTERT_15MIN
                         tFecc15Min(380),          -- T_FECC_15MIN
                         tFecUbu15Min(381),        -- T_FEC_UBU_15MIN
                         tOprh15Min(382),          -- T_OPRH_15MIN
                         tOprl15Min(383),          -- T_OPRL_15MIN
                         tOpth15Min(384),          -- T_OPTH_15MIN
                         tOptl15Min(385),          -- T_OPTL_15MIN
                         tSefs15Min(386),          -- T_SEFS_15MIN
                         tSefsPcs15Min(387),       -- T_SEFS_PCS_15MIN
                         tSefsPcst15Min(388),      -- T_SEFS_PCST_15MIN
                         tSefss15Min(389),         -- T_SEFSS_15MIN
                         tSefsst15Min(390),        -- T_SEFSST_15MIN
                         tSes15Min(391),           -- T_SES_15MIN
                         tSesOtu15Min(392),        -- T_SES_OTU_15MIN
                         tSesPcs15Min(393),        -- T_SES_PCS_15MIN
                         tSesPcst15Min(394),       -- T_SES_PCST_15MIN
                         tSesRs15Min(395),         -- T_SES_RS_15MIN
                         tSess15Min(396),          -- T_SESS_15MIN
                         tSesst15Min(397),         -- T_SESST_15MIN
                         tUasOtu15Min(398),        -- T_UAS_OTU_15MIN
                         tUasRs15Min(399),         -- T_UAS_RS_15MIN
                         tEsst15Min(400),          -- T_ESST_15MIN
                         tBbeOdu15Min(401),        -- T_BBE_ODU_15MIN
                         tEsOdu15Min(402),         -- T_ES_ODU_15MIN
                         tSesOdu15Min(403),        -- T_SES_ODU_15MIN
                         tUasOdu15Min(404),        -- T_UAS_ODU_15MIN
                         tBbeRst15Min(405),        -- T_BBE_RST_15MIN
                         tEsRst15Min(406),         -- T_ES_RST_15MIN
                         tSesRst15Min(407),        -- T_SES_RST_15MIN
                         tUasRst15Min(408),        -- T_UAS_RST_15MIN
                         tBbeOtu1Day(409),         -- T_BBE_OTU_1DAY
                         tBbeRs1Day(410),          -- T_BBE_RS_1DAY
                         tCv1Day(411),             -- T_CV_1DAY
                         tCvPcs1Day(412),          -- T_CV_PCS_1DAY
                         tCvPcst1Day(413),         -- T_CV_PCST_1DAY
                         tCvs1Day(414),            -- T_CVS_1DAY
                         tCvst1Day(415),           -- T_CVST_1DAY
                         tEs1Day(416),             -- T_ES_1DAY
                         tEsOtu1Day(417),          -- T_ES_OTU_1DAY
                         tEsRs1Day(418),           -- T_ES_RS_1DAY
                         tEsPcs1Day(419),          -- T_ES_PCS_1DAY
                         tEsPcst1Day(420),         -- T_ES_PCST_1DAY
                         tEss1Day(421),            -- T_ESS_1DAY
                         tEthpkter1Day(422),       -- T_ETHPKTER_1DAY
                         tEthpktert1Day(423),      -- T_ETHPKTERT_1DAY
                         tFecc1Day(424),           -- T_FECC_1DAY
                         tFecUbu1Day(425),         -- T_FEC_UBU_1DAY
                         tOprh1Day(426),           -- T_OPRH_1DAY
                         tOprl1Day(427),           -- T_OPRL_1DAY
                         tOpth1Day(428),           -- T_OPTH_1DAY
                         tOptl1Day(429),           -- T_OPTL_1DAY
                         tSefs1Day(430),           -- T_SEFS_1DAY
                         tSefsPcs1Day(431),        -- T_SEFS_PCS_1DAY
                         tSefsPcst1Day(432),       -- T_SEFS_PCST_1DAY
                         tSefss1Day(433),          -- T_SEFSS_1DAY
                         tSefsst1Day(434),         -- T_SEFSST_1DAY
                         tSes1Day(435),            -- T_SES_1DAY
                         tSesOtu1Day(436),         -- T_SES_OTU_1DAY
                         tSesPcs1Day(437),         -- T_SES_PCS_1DAY
                         tSesPcst1Day(438),        -- T_SES_PCST_1DAY
                         tSesRs1Day(439),          -- T_SES_RS_1DAY
                         tSess1Day(440),           -- T_SESS_1DAY
                         tSesst1Day(441),          -- T_SESST_1DAY
                         tUasOtu1Day(442),         -- T_UAS_OTU_1DAY
                         tUasRs1Day(443),          -- T_UAS_RS_1DAY
                         tEsst1Day(444),           -- T_ESST_1DAY
                         tBbeOdu1Day(445),         -- T_BBE_ODU_1DAY
                         tEsOdu1Day(446),          -- T_ES_ODU_1DAY
                         tSesOdu1Day(447),         -- T_SES_ODU_1DAY
                         tUasOdu1Day(448),         -- T_UAS_ODU_1DAY
                         tBbeRst1Day(449),         -- T_BBE_RST_1DAY
                         tEsRst1Day(450),          -- T_ES_RST_1DAY
                         tSesRst1Day(451),         -- T_SES_RST_1DAY
                         tUasRst1Day(452),         -- T_UAS_RST_1DAY
                         eqptDgrOch(453),          -- EQPTDGROCH
                         eqptDgrOchOut(454),       -- EQPTDGROCHOUT
                         etrMismatchMod(455),      -- ETRMISMATCHMOD
                         fanSpeedHigh(456),        -- FANSPEEDHIGH
                         fanSpeedLow(457),         -- FANSPEEDLOW
                         intTempHigh(458),         -- INTTEMPHIGH
                         intTempLow(459),          -- INTTEMPLOW
                         intTempOpt(460),          -- INTTEMPOPT
                         oprLossLow(461),          -- OPRLOSSLOW
                         oprLossHigh(462),         -- OPRLOSSHIGH
                         oprTx(463),               -- OPRTX
                         oprPwrLow(464),           -- OPRPWRLOW
                         oprPwrHigh(465),          -- OPRPWRHIGH
                         trmtMOD(466),             -- TRMTMOD
                         replUnitMissMOD(467),     -- REPLUNITMISSMOD
                         voltageHigh(468),         -- VOLTAGEHIGH
                         voltageLow(469),          -- VOLTAGELOW
                         eqptPort(470),            -- EQPTPORT
--                         obsolete
--                         uruOts(471),               URUOTS
                         uruOtu(472),              -- URUOTU
                         mismatchFiber(473),       -- MISMATCHFIBER
                         losPld(474),              -- LOSPLD
                         aprNode(475),             -- APRNODE
                         aprOsc(476),              -- APROSC
                         aprUnavail(477),          -- APRUNAVAIL
                         aprInvalidTopo(478),      -- APRINVALIDTOPO
                         incompatFan(479),         -- INCOMPATFAN
                         clearAllTcas(480),        -- CLEARALLTCAS
                         aprUnavailOsc(481),       -- APRUNAVAILOSC
                         e1Los(482),               -- E1LOS
                         e1Lof(483),               -- E1LOF
                         e1AisL(484),              -- E1AISL
                         e1NoCrc4M(485),           -- E1NOCRC4M
                         e1Rai(486),               -- E1RAI
                         e1LofEgr(487),            -- E1LOFEGR
                         e1AisEgr(488),            -- E1AISEGR
                         e1NoCRC4MEgr(489),        -- E1NOCRC4MEGR
                         e1RaiEgr(490),            -- E1RAIEGR
                         tBbeP15Min(491),          -- T_BBE_P_15MIN
                         tEsP15Min(492),           -- T_ES_P_15MIN
                         tSesP15Min(493),          -- T_SES_P_15MIN
                         tUasP15Min(494),          -- T_UAS_P_15MIN
                         tEsL15Min(495),           -- T_UAS_L_15MIN
                         tSesL15Min(496),          -- T_SES_L_15MIN
                         tBbeP1Day(497),           -- T_BBE_P_1DAY
                         tEsP1Day(498),            -- T_ES_P_1DAY
                         tSesP1Day(499),           -- T_SES_P_1DAY
                         tUasP1Day(500),           -- T_UAS_P_1DAY
                         tEsL1Day(501),            -- T_UAS_L_1DAY
                         tSesL1Day(502),           -- T_SES_L_1DAY
                         tBbePt15Min(503),         -- T_BBE_PT_15MIN
                         tEsPt15Min(504),          -- T_ES_PT_15MIN
                         tSesPt15Min(505),         -- T_SES_PT_15MIN
                         tUasPt15Min(506),         -- T_UAS_PT_15MIN
                         tBbePt1Day(507),          -- T_BBE_PT_1DAY
                         tEsPt1Day(508),           -- T_ES_PT_1DAY
                         tSesPt1Day(509),          -- T_SES_PT_1DAY
                         tUasPt1Day(510),          -- T_UAS_PT_1DAY
                         lockoutOfPrVTS1(511),     -- LOCKOUTOFPRVTS1
                         lockoutOfPrVTS2(512),     -- LOCKOUTOFPRVTS2
                         lockoutOfPrVTS3(513),     -- LOCKOUTOFPRVTS3
                         lockoutOfPrVTS4(514),     -- LOCKOUTOFPRVTS4
                         lockoutOfPrVTS5(515),     -- LOCKOUTOFPRVTS5
                         lockoutOfPrVTS6(516),     -- LOCKOUTOFPRVTS6
                         lockoutOfPrVTS7(517),     -- LOCKOUTOFPRVTS7
                         lockoutOfPrVTS8(518),     -- LOCKOUTOFPRVTS8
                         lockoutOfPrVTS9(519),     -- LOCKOUTOFPRVTS9
                         lockoutOfPrVTS10(520),    -- LOCKOUTOFPRVTS10
                         frcdWkSwPrVTS1(521),      -- FRCDWKSWPRVTS1
                         frcdWkSwPrVTS2(522),      -- FRCDWKSWPRVTS2
                         frcdWkSwPrVTS3(523),      -- FRCDWKSWPRVTS3
                         frcdWkSwPrVTS4(524),      -- FRCDWKSWPRVTS4
                         frcdWkSwPrVTS5(525),      -- FRCDWKSWPRVTS5
                         frcdWkSwPrVTS6(526),      -- FRCDWKSWPRVTS6
                         frcdWkSwPrVTS7(527),      -- FRCDWKSWPRVTS7
                         frcdWkSwPrVTS8(528),      -- FRCDWKSWPRVTS8
                         frcdWkSwPrVTS9(529),      -- FRCDWKSWPRVTS9
                         frcdWkSwPrVTS10(530),     -- FRCDWKSWPRVTS10
                         frcdWkSwBkVTS1(531),      -- FRCDWKSWBKVTS1
                         frcdWkSwBkVTS2(532),      -- FRCDWKSWBKVTS2
                         frcdWkSwBkVTS3(533),      -- FRCDWKSWBKVTS3
                         frcdWkSwBkVTS4(534),      -- FRCDWKSWBKVTS4
                         frcdWkSwBkVTS5(535),      -- FRCDWKSWBKVTS5
                         frcdWkSwBkVTS6(536),      -- FRCDWKSWBKVTS6
                         frcdWkSwBkVTS7(537),      -- FRCDWKSWBKVTS7
                         frcdWkSwBkVTS8(538),      -- FRCDWKSWBKVTS8
                         frcdWkSwBkVTS9(539),      -- FRCDWKSWBKVTS9
                         frcdWkSwBkVTS10(540),     -- FRCDWKSWBKVTS10
                         manWkSwPrVTS1(541),       -- MANWKSWPRVTS1
                         manWkSwPrVTS2(542),       -- MANWKSWPRVTS2
                         manWkSwPrVTS3(543),       -- MANWKSWPRVTS3
                         manWkSwPrVTS4(544),       -- MANWKSWPRVTS4
                         manWkSwPrVTS5(545),       -- MANWKSWPRVTS5
                         manWkSwPrVTS6(546),       -- MANWKSWPRVTS6
                         manWkSwPrVTS7(547),       -- MANWKSWPRVTS7
                         manWkSwPrVTS8(548),       -- MANWKSWPRVTS8
                         manWkSwPrVTS9(549),       -- MANWKSWPRVTS9
                         manWkSwPrVTS10(550),      -- MANWKSWPRVTS10
                         manWkSwBkVTS1(551),       -- MANWKSWBKVTS1
                         manWkSwBkVTS2(552),       -- MANWKSWBKVTS2
                         manWkSwBkVTS3(553),       -- MANWKSWBKVTS3
                         manWkSwBkVTS4(554),       -- MANWKSWBKVTS4
                         manWkSwBkVTS5(555),       -- MANWKSWBKVTS5
                         manWkSwBkVTS6(556),       -- MANWKSWBKVTS6
                         manWkSwBkVTS7(557),       -- MANWKSWBKVTS7
                         manWkSwBkVTS8(558),       -- MANWKSWBKVTS8
                         manWkSwBkVTS9(559),       -- MANWKSWBKVTS9
                         manWkSwBkVTS10(560),      -- MANWKSWBKVTS10
                         wkSwPrVTS1(561),          -- WKSWPRVTS1
                         wkSwPrVTS2(562),          -- WKSWPRVTS2
                         wkSwPrVTS3(563),          -- WKSWPRVTS3
                         wkSwPrVTS4(564),          -- WKSWPRVTS4
                         wkSwPrVTS5(565),          -- WKSWPRVTS5
                         wkSwPrVTS6(566),          -- WKSWPRVTS6
                         wkSwPrVTS7(567),          -- WKSWPRVTS7
                         wkSwPrVTS8(568),          -- WKSWPRVTS8
                         wkSwPrVTS9(569),          -- WKSWPRVTS9
                         wkSwPrVTS10(570),         -- WKSWPRVTS10
                         excessLoss(571),          -- EXCESSLOSS
                         losOcm(572),              -- LOSOCM
                         fecUbcSd(573),            -- FECUBCSD
                         uruS(574),                -- URUS
                         pwrTiltSusp(575),         -- PWRTILTSUSP
                         ebero(576),               -- EBERO
                         tPreFec15Min(577),        -- T_PREFEC_15MIN
                         tPostFec15Min(578),       -- T_POSTFEC_15MIN
                         tPreFec1Day(579),         -- T_PREFEC_1DAY
                         tPostFec1Day(580),        -- T_POSTFEC_1DAY
                         tIaesOtu15Min(581),       -- T_IAES_OTU_15MIN
                         tBiaesOtu15Min(582),      -- T_BIAES_OTU_15MIN
                         tIaesOtu1Day(583),        -- T_IAES_OTU_1DAY
                         tBiaesOtu1Day(584),       -- T_BIAES_OTU_1DAY
                         tFebbeOtu15Min(585),      -- T_FEBBE_OTU_15MIN
                         tFeesOtu15Min(586),       -- T_FEES_OTU_15MIN
                         tFesesOtu15Min(587),      -- T_FESES_OTU_15MIN
                         tFeuasOtu15Min(588),      -- T_FEUAS_OTU_15MIN
                         tFebbeOtu1Day(589),       -- T_FEBBE_OTU_1DAY
                         tFeesOtu1Day(590),        -- T_FEES_OTU_1DAY
                         tFesesOtu1Day(591),       -- T_FESES_OTU_1DAY
                         tFeuasOtu1Day(592),       -- T_FEUAS_OTU_1DAY
                         tFebbeOdu15Min(593),      -- T_FEBBE_ODU_15MIN
                         tFeesOdu15Min(594),       -- T_FEES_ODU_15MIN
                         tFesesOdu15Min(595),      -- T_FESES_ODU_15MIN
                         tFeuasOdu15Min(596),      -- T_FEUAS_ODU_15MIN
                         tFebbeOdu1Day(597),       -- T_FEBBE_ODU_1DAY
                         tFeesOdu1Day(598),        -- T_FEES_ODU_1DAY
                         tFesesOdu1Day(599),       -- T_FESES_ODU_1DAY
                         tFeuasOdu1Day(600),       -- T_FEUAS_ODU_1DAY
                         oduAis(601),              -- ODUAIS
                         msim(602),                -- MSIM
                         loam(603),                -- LOAM
                         losOts(604),              -- LOSOTS
                         invalidThresholdOts(605), -- INVALIDTHRESHOLDOTS
                         pwrUnbalance(606),        -- PWRUNBALANCE
                         spLoAdjFail(607),         -- SPLOADJFAIL
                         losOms(608),              -- LOSOMS
                         invalidThresholdOms(609), -- INVALIDTHRESHOLDOMS
                         laserBackFacetOptPwrTca(610), -- LASERBACKFACETOPTPWRTCA
                         laserCoolingCurTca(611),  -- LASERCOOLINGCURTCA
                         pwrUnbalanceOms(612),     -- PWRUNBALANCEOMS
                         oduAisEgress(613),        -- ODUAISEGRESS
                         frngSync(614),            -- FRNGSYNC
                         hldOvrSync(615),          -- HLDOVRSYNC
                         syncRefFail(616),         -- SYNCREFFAIL
                         wtr(617),                 -- WTR
                         aisLM(618),               -- AISLM
                         ssfTcm(619),              -- SSFTCM
                         lckTcm(620),              -- LCKTCM
                         ociTcm(621),              -- OCITCM
                         degTcm(622),              -- DEGTCM
                         bdiTcm(623),              -- BDITCM
                         timTcm(624),              -- TIMTCM
                         ltcTcm(625),              -- LTCTCM
                         aisTcm(626),              -- AISTCM
                         tIaesTcm15Min(627),       -- T_IAES_TCM_15MIN
                         tBbeTcm15Min(628),        -- T_BBE_TCM_15MIN
                         tEsTcm15Min(629),         -- T_ES_TCM_15MIN
                         tSesTcm15Min(630),        -- T_SES_TCM_15MIN
                         tUasTcm15Min(631),        -- T_UAS_TCM_15MIN
                         tBiaesTcm15Min(632),      -- T_BIAES_TCM_15MIN
                         tFebbeTcm15Min(633),      -- T_FEBBE_TCM_15MIN
                         tFeesTcm15Min(634),       -- T_FEES_TCM_15MIN
                         tFesesTcm15Min(635),      -- T_FESES_TCM_15MIN
                         tFeuasTcm15Min(636),      -- T_FEUAS_TCM_15MIN
                         tIaesTcm1Day(637),        -- T_IAES_TCM_1DAY
                         tBbeTcm1Day(638),         -- T_BBE_TCM_1DAY
                         tEsTcm1Day(639),          -- T_ES_TCM_1DAY
                         tSesTcm1Day(640),         -- T_SES_TCM_1DAY
                         tUasTcm1Day(641),         -- T_UAS_TCM_1DAY
                         tBiaesTcm1Day(642),       -- T_BIAES_TCM_1DAY
                         tFebbeTcm1Day(643),       -- T_FEBBE_TCM_1DAY
                         tFeesTcm1Day(644),        -- T_FEES_TCM_1DAY
                         tFesesTcm1Day(645),       -- T_FESES_TCM_1DAY
                         tFeuasTcm1Day(646),       -- T_FEUAS_TCM_1DAY
--                         obsolete
--                         uruOms(647),               URU-OMS
                         tBbeMs15Min(648),         -- T_BBE_MS_15MIN
                         tEsMs15Min(649),          -- T_ES_MS_15MIN
                         tSesMs15Min(650),         -- T_SES_MS_15MIN
                         tUasMs15Min(651),         -- T_UAS_MS_15MIN
                         tFebbeMs15Min(652),       -- T_FEBBE_MS_15MIN
                         tFeesMs15Min(653),        -- T_FEES_MS_15MIN
                         tFesesMs15Min(654),       -- T_FESES_MS_15MIN
                         tFeuasMs15Min(655),       -- T_FEUAS_MS_15MIN
                         tBbeMs1Day(656),          -- T_BBE_MS_1DAY
                         tEsMs1Day(657),           -- T_ES_MS_1DAY
                         tSesMs1Day(658),          -- T_SES_MS_1DAY
                         tUasMs1Day(659),          -- T_UAS_MS_1DAY
                         tFebbeMs1Day(660),        -- T_FEBBE_MS_1DAY
                         tFeesMs1Day(661),         -- T_FEES_MS_1DAY
                         tFesesMs1Day(662),        -- T_FESES_MS_1DAY
                         tFeuasMs1Day(663),        -- T_FEUAS_MS_1DAY
                         losOOut(664),             -- LOSOOUT
                         invalidEgress(665),       -- INVALIDEGRESS
                         aprSwitch(666),           -- APRSWITCH
                         optIntDet(667),           -- OPTINTDET
                         optIntSusp(668),          -- OPTINTSUSP
                         uruOtsRx(669),            -- URUOTSRX
                         uruOtsTx(670),            -- URUOTSTX
                         uruOmsRx(671),            -- URUOMSRX
                         uruOmsTx(672),            -- URUOMSTX
                         uruOtsLos(673),           -- URUOTSLOS
                         uruOchLos(674),           -- URUOCHLOS
                         manSwToInt(675),          -- MANSWTOINT
                         autoSwTimRef(676),        -- AUTOSWTIMREF
                         manSwTimRef(677),         -- MANSWTIMREF
                         frcdSwTimRef(678),        -- FRCDSWTIMREF
                         lockoutOfTimRef(679),     -- LOCKOUTOFTIMREF
                         manLR(680),               -- MANLR
                         sltmSig(681),             -- SLTMSIG
                         syncRefUnEq(682),         -- SYNCREFUNEQ
                         pcsGeneratorActive(683),  -- PCSGENERATORACTIVE
                         ospfAdj(684),             -- OSPFADJ
                         fdi(685),                 -- FDI
                         tsMismatch(686),          -- TSMISMATCH
                         tBerPreFec15min(687),     -- T_BERPREFEC_15MIN
                         tBerPreFec1day(688),      -- T_BERPREFEC_1DAY
                         tBerPostFec15min(689),    -- T_BERPOSTFEC_15MIN
                         tBerPostFec1day(690),     -- T_BERPOSTFEC_1DAY
                         lofLom(691),              -- LOFLOM
                         optIntBase(692),          -- OPTINTBASE
                         auAisP(693),              -- AUAISP
                         auLopP(694),              -- AULOPP
                         hpUneqP(695),             -- HPUNEQP
                         hpPlmP(696),              -- HPPLMP
                         hpRdiP(697),              -- HPRDIP
                         intrusionEvt(698),        -- INTRUSIONEVT
                         transferLogFL(699),       -- TRANSFERLOGFL
                         transferLogFT(700),       -- TRANSFERLOGFT
                         transferLogIP(701),       -- TRANSFERLOGIP
                         autoSyncSw(702),          -- AUTOSYNCSW
                         vtsOci(703),              -- VTSOCI
                         vtsFdi(704),              -- VTSFDI
                         ntpLor(705),              -- NTPLOR
                         ntpClkAdj(706),           -- NTPCLKADJ
                         inventoryError(707),      -- INVENTORYERROR
                         mepLoc(708),              -- MEPLOC
                         mepMmg(709),              -- MEPMMG
                         unMOrUnP(710),            -- UNMORUNP
                         ethCSF(711),              -- ETHCSF
                         rdi(712),                 -- RDI
                         cfCapacityWarning(713),   -- CFCAPACITYWARNING
                         asonTopo(714),            -- ASONTOPO
                         escLatchFail(715),        -- ESCLATCHFAIL
                         pwrAdjComms(716),         -- PWRADJCOMMS
                         lanSf(717),               -- LANSF
                         cardBoot(718),            -- CARDBOOT
                         lotOut(719),              -- LOTOUT
                         prcdrErrTopoOut(720),     -- PRCDRERRTOPOOUT
                         pwrAdjFailAdd(721),       -- PWRADJFAILADD
                         pwrAdjFailDrp(722),       -- PWRADJFAILDRP
                         pwrAdjReqAdd(723),        -- PWRADJREQADD
                         pwrAdjReqDrp(724),        -- PWRADJREQDRP
                         neModeMismatch(725),      -- NEMODEMISMATCH
                         ocsUnavail(726),          -- OCSUNAVAIL
                         ckm(727),                 -- CKM
                         nkm(728),                 -- NKM
                         ocsAuditSuccess(729),     -- OCSAUDITSUCCESS
                         ocsAuditFail(730),        -- OCSAUDITFAIL
                         ocsUplinkDeleted(731),    -- OCSUPLINKDELETED
                         ocsDataRtrv(732),         -- OCSDATARTRV
                         ocsDataFlt(733),          -- OCSDATAFLT
                         ssfCltEgr(734),           -- SSFCLTEGR
                         pwrTiltParams(735),       -- PWRTILTPARAMS
                         egressSSF(736),           -- EGRESSSSF
                         omsSSF(737),              -- OMSSSF
                         alienEgrLOS(738),         -- ALIENEGRLOS
                         csf(739),                 -- CSF
                         fdiClt(740),              -- FDICLT
                         csfOduEgr(741),           -- CSFODUEGR
                         lagLos(742),              -- LAGLOS
                         lagDeg(743),              -- LAGDEG
                         unL(744),                 -- UNL
                         unM(745),                 -- UNM
                         unP(746),                 -- UNP
                         unPr(747),                -- UNPR
                         toDLOS(748),              -- TODLOS
                         toDDEG(749),              -- TODDEG
                         lossOfLock(750),          -- LOSSOFLOCK
                         faulty(751),              -- FAULTY
                         ppsLos(752),              -- PPSLOS
                         ethRingPathProvMismatch(753), -- ETHRINGPATHPROVMISMATCH
                         mepMacError(754),         -- MEPMACERROR
                         mepXcon(755),             -- MEPXCON
                         mepError(756),            -- MEPERROR
                         mepRemote(757),           -- MEPREMOTE
                         mepAIS(758),              -- MEPAIS
                         svcOperDown(759),         -- SVCOPERDOWN
                         svcTlsFwdTblFullAlarm(760), -- SVCTLSFWDTBLFULLALARM
                         svcTlsMfibTblFullAlarm(761), -- SVCTLSMFIBTBLFULLALARM
                         sapOperDown(762),         -- SAPOPERDOWN
                         sapTlsMacAddrLimitAlarm(763), -- SAPTLSMACADDRLIMITALARM
                         lagPortAddFailed(764),    -- LAGPORTADDFAILED
                         syncIfTimingHoldover(765), -- SYNCIFTIMINGHOLDOVER
                         syncIfTimingRef1Alarm(766), -- SYNCIFTIMINGREF1ALARM
                         syncIfTimingRef2Alarm(767), -- SYNCIFTIMINGREF2ALARM
                         linkoamLoopDetected(768), -- LINKOAMLOOPDETECTED
                         esm(769),                 -- ESM
                         ssfOduOut(770),           -- SSFODUOUT
                         lckOut(771),              -- LCKOUT
                         ociOut(772),              -- OCIOUT
                         degOut(773),              -- DEGOUT
                         bdiOduOut(774),           -- BDIODUOUT
                         timOduOut(775),           -- TIMODUOUT
                         tUasOdu15MinOut(776),     -- T_UAS_ODU_15MIN_OUT
                         tUasOdu1DayOut(777),      -- T_UAS_ODU_1DAY_OUT
                         tSesOdu15MinOut(778),     -- T_SES_ODU_15MIN_OUT
                         tSesOdu1DayOut(779),      -- T_SES_ODU_1DAY_OUT
                         tEsOdu15MinOut(780),      -- T_ES_ODU_15MIN_OUT
                         tEsOdu1DayOut(781),       -- T_ES_ODU_1DAY_OUT
                         tBbeOdu15MinOut(782),     -- T_BBE_ODU_15MIN_OUT
                         tBbeOdu1DayOut(783),      -- T_BBE_ODU_1DAY_OUT
                         tFeUasOdu15MinOut(784),   -- T_FEUAS_ODU_15MIN_OUT
                         tFeUasOdu1DayOut(785),    -- T_FEUAS_ODU_1DAY_OUT
                         tFeSesOdu15MinOut(786),   -- T_FESES_ODU_15MIN_OUT
                         tFeSesOdu1DayOut(787),    -- T_FESES_ODU_1DAY_OUT
                         tFeEsOdu15MinOut(788),    -- T_FEES_ODU_15MIN_OUT
                         tFeEsOdu1DayOut(789),     -- T_FEES_ODU_1DAY_OUT
                         tFeBbeOdu15MinOut(790),   -- T_FEBBE_ODU_15MIN_OUT
                         tFeBbeOdu1DayOut(791),    -- T_FEBBE_ODU_1DAY_OUT
                         lol(792),                 -- LOL
                         erpFwdStateChng(793),     -- ERPFWDSTATECHNG
                         lagSubGrpSelect(794),     -- LAGSUBGRPSELECT
                         linkoamPeerChng(795),     -- LINKOAMPEERCHNG
                         linkoamNonThresh(796),    -- LINKOAMNONTHRESH
                         svcStateChng(797),        -- SVCSTATECHNG
                         sapStateChng(798),        -- SAPSTATECHNG
                         cfmFltEvnt(799),          -- CFMFLTEVNT
                         cfmAisEvnt(800),          -- CFMAISEVNT
                         cfmSlmTestComplete(801),  -- CFMSLMTESTCOMPLETE
                         cfmDmTestComplete(802),   -- CFMDMTESTCOMPLETE
                         cfmLbmTestComplete(803),  -- CFMLBMTESTCOMPLETE
                         cfmLtmTestComplete(804),  -- CFMLTMTESTCOMPLETE
                         igmpSnpgSrcLimitExceed(805), -- IGMPSNPGSRCLIMITEXCEED
                         mirrorSrcEnable(806),     -- MIRRORSRCENABLE
                         mirrorSrcDisable(807),    -- MIRRORSRCDISABLE
                         otmcpf(808),              -- OTMCPF
                         wtocmaOsnrOomr(809),      -- WTOCMA_OSNROOMR
                         lanLol(810),              -- LANLOL
                         plmOduOut(811),           -- PLMODUOUT
                         csfOduOut(812),           -- CSFODUOUT
                         shelfInVoltHigh(813),     -- SHELFINVOLTHIGH
                         shelfInVoltLow(814),      -- SHELFINVOLTLOW
                         mirrorDestEnable(815),    -- MIRRORDESTENABLE
                         mirrorDestDisable(816),   -- MIRRORDESTDISABLE
                         dcConfigFail(817),        -- DCCONFIGFAIL
                         pwrEdfaMargin(818),       -- PWREDFAMARGIN
                         bitsLos(819),             -- BITSLOS
                         bitsLof(820),             -- BITSLOF
                         bitsAIS(821),             -- BITSAIS
                         bitsMAN(822),             -- BITSMAN
                         syncOosT4(823),           -- SYNCOOST4
                         syncT4Out(824),           -- SYNCT4OUT
                         autoSwTimRefT4(825),      -- AUTOSWTIMREFT4
                         manSwTimRefT4(826),       -- MANSWTIMREFT4
                         frcdSwTimRefT4(827),      -- FRCDSWTIMREFT4
                         lockoutOfTimRefT4(828),   -- LOCKOUTOFTIMREFT4
                         cardInitBcm(829),         -- CARDINITBCM
                         cardInitNonBcm(830),      -- CARDINITNONBCM
                         losEdfa(831),             -- LOSEDFA
                         oduAisOut(832),           -- ODUAISOUT
                         tsMismatchOut(833),       -- TSMISMATCHOUT
                         lofLomOut(834),           -- LOFLOMOUT
                         cpuPerformance(835),      -- CPUPERFORMANCE
                         contEqptSplit(836),       -- CONTEQPTSPLIT
                         csfGfpOut(837),           -- CSFGFPOUT
                         gfpLofOut(838),           -- GFPLOFOUT
                         ssfSection(839),          -- SSFSECTION
                         ptpRefUnstable(840),      -- PTPREFUNSTABLE
                         ptpFreeRun(841),          -- PTPFREERUN
                         ptpRefLoss(842),          -- PTPREFLOSS
                         announceLoss(843),        -- ANNOUNCELOSS
                         syncLoss(844),            -- SYNCLOSS
                         delayResLoss(845),        -- DELAYRESLOSS
--                         obsolete
--                         ptpGMDegrade(846),         PTPGMDEGRADE
--                         ptpGMSwitch(847),          PTPGMSWITCH
--                         ptpPathSwitch(848),        PTPPATHSWITCH
--                         ptpPortSwitch(849),        PTPPORTSWITCH
                         rmdNDF(850),              -- RMDNDF
                         rmdDNR(851),              -- RMDDNR
                         rmdWDP(852),              -- RMDWDP
                         rmdEQF(853),              -- RMDEQF
                         cardIdRcvd(854),          -- CARDIDRCVD
                         fipsSwMismatch(855),      -- FIPSSWMISMATCH
                         eqptCrypto(856),          -- EQPTCRYPTO
                         rmdPWR(857),              -- RMDPWR
                         rmdMepUNL(858),           -- RMDMEPUNL
                         rmdMepMMG(859),           -- RMDMEPMMG
                         rmdMepUNM(860),           -- RMDMEPUNM
                         rmdMepLOC(861),           -- RMDMEPLOC
                         rmdMepUNP(862),           -- RMDMEPUNP
                         rmdMepRDI(863),           -- RMDMEPRDI
                         fpgaInit1(864),           -- FPGAINIT1
                         fpgaInit2(865),           -- FPGAINIT2
                         fpgaInit3(866),           -- FPGAINIT3
                         fpgaInit4(867),           -- FPGAINIT4
                         fpgaInit5(868),           -- FPGAINIT5
                         fpgaInit6(869),           -- FPGAINIT6
                         fpgaInit7(870),           -- FPGAINIT7
                         fpgaInit8(871),           -- FPGAINIT8
                         fpgaInit9(872),           -- FPGAINIT9
                         fpgaInit10(873),          -- FPGAINIT10
                         slcCardInit(874),         -- SLCCARDINIT
                         slcBootContCom(875),      -- SLCBOOTCONTCOM
                         slcContCom(876),          -- SLCCONTCOM
                         slcDataFlt(877),          -- SLCDATAFLT
                         slcEqptBoot(878),         -- SLCEQPTBOOT
                         slcNotInService(879),     -- SLCNOTINSERVICE
                         slcMismatch(880),         -- SLCMISMATCH
                         slcClkSync(881),          -- SLCCLKSYNC
                         rmdIfEFMLOP(882),         -- RMDIFEFMLOP
                         rmdIfMauLOS(883),         -- RMDIFMAULOS
                         rmdIfMauANM(884),         -- RMDIFMAUANM
                         rmdIfMauEQF(885),         -- RMDIFMAUEQF
                         rmdIfMauUNI(886),         -- RMDIFMAUUNI
                         rmdIfMauWUP(887),         -- RMDIFMAUWUP
                         fpgaPreLoad(888),         -- FPGAPRELOAD
                         csfGfp(889),              -- CSFGFP
                         gfpUpm(890),              -- GFPUPM
                         ssfSectionOut(891),       -- SSFSECTIONOUT
                         tFecUbc15Min(892),        -- T_FEC_UBC_15MIN
                         tFecUbc1Day(893),         -- T_FEC_UBC_1DAY
                         pgFpgaInit1(894),         -- PGFPGAINIT1
                         pgFpgaInit2(895),         -- PGFPGAINIT2
                         pgFpgaInit3(896),         -- PGFPGAINIT3
                         pgFpgaInit4(897),         -- PGFPGAINIT4
                         pgFpgaInit5(898),         -- PGFPGAINIT5
                         pgFpgaFail1(899),         -- PGFPGAFAIL1
                         pgFpgaFail2(900),         -- PGFPGAFAIL2
                         pgFpgaFail3(901),         -- PGFPGAFAIL3
                         pgFpgaFail4(902),         -- PGFPGAFAIL4
                         pgFpgaFail5(903),         -- PGFPGAFAIL5
                         truSvcVoltFlt(904),       -- TRUSVCVOLTFLT
                         truBrkrOpen(905),         -- TRUBRKROPEN
                         osnrMesc(906),            -- OSNRMESC
                         fipsFailure(907),         -- FIPSFAILURE
                         aesFipsFailure(908),      -- AESFIPSFAILURE
                         todRefUnstable(909),      -- TODREFUNSTABLE
                         ochKeyUnavail(910),       -- OCHKEYUNAVAIL
                         keyDomainErr(911),        -- KEYDOMAINERR
                         ochKeysReused(912),       -- OCHKEYSREUSED
                         fan32HRqd(913),           -- FAN32HRQD
                         losOamp(914),             -- LOSOAMP
                         tPmonSapIngressPktsDropped15Min(915),   -- T_PMON_SAPINGRESSPKTSDROPPED_15MIN
                         tPmonSapIngressOctetsDropped15Min(916), -- T_PMON_SAPINGRESSOCTETSDROPPED_15MIN
                         tPmonPortIfInPackets15Min(917),         -- T_PMON_PORTIFINPACKETS_15MIN
                         tPmonPortIfOutPackets15Min(918),        -- T_PMON_PORTIFOUTPACKETS_15MIN
                         tPmonPortIfInOctets15Min(919),          -- T_PMON_PORTIFINOCTETS_15MIN
                         tPmonPortIfOutOctets15Min(920),         -- T_PMON_PORTIFOUTOCTETS_15MIN
                         tPmonPortIfInDiscards15Min(921),        -- T_PMON_PORTIFINDISCARDS_15MIN
                         tPmonPortIfOutDiscards15Min(922),       -- T_PMON_PORTIFOUTDISCARDS_15MIN
                         tPmonPortIfInErrors15Min(923),          -- T_PMON_PORTIFINERRORS_15MIN
                         tPmonPortIfOutErrors15Min(924),         -- T_PMON_PORTIFOUTERRORS_15MIN
                         tPmonPortHighCapacityPkts15Min(925),    -- T_PMON_PORTHIGHCAPACITYPKTS_15MIN
                         tPmonPortHighCapacityOctets15Min(926),  -- T_PMON_PORTHIGHCAPACITYOCTETS_15MIN
                         tPmonPortQueue1PktsDropped15Min(927),   -- T_PMON_PORTQUEUE1PKTSDROPPED_15MIN
                         tPmonPortQueue2PktsDropped15Min(928),   -- T_PMON_PORTQUEUE2PKTSDROPPED_15MIN
                         tPmonPortQueue3PktsDropped15Min(929),   -- T_PMON_PORTQUEUE3PKTSDROPPED_15MIN
                         tPmonPortQueue4PktsDropped15Min(930),   -- T_PMON_PORTQUEUE4PKTSDROPPED_15MIN
                         tPmonPortQueue5PktsDropped15Min(931),   -- T_PMON_PORTQUEUE5PKTSDROPPED_15MIN
                         tPmonPortQueue6PktsDropped15Min(932),   -- T_PMON_PORTQUEUE6PKTSDROPPED_15MIN
                         tPmonPortQueue7PktsDropped15Min(933),   -- T_PMON_PORTQUEUE7PKTSDROPPED_15MIN
                         tPmonPortQueue8PktsDropped15Min(934),   -- T_PMON_PORTQUEUE8PKTSDROPPED_15MIN
                         tPmonPortQueue1OctetsDropped15Min(935), -- T_PMON_PORTQUEUE1OCTETSDROPPED_15MIN
                         tPmonPortQueue2OctetsDropped15Min(936), -- T_PMON_PORTQUEUE2OCTETSDROPPED_15MIN
                         tPmonPortQueue3OctetsDropped15Min(937), -- T_PMON_PORTQUEUE3OCTETSDROPPED_15MIN
                         tPmonPortQueue4OctetsDropped15Min(938), -- T_PMON_PORTQUEUE4OCTETSDROPPED_15MIN
                         tPmonPortQueue5OctetsDropped15Min(939), -- T_PMON_PORTQUEUE5OCTETSDROPPED_15MIN
                         tPmonPortQueue6OctetsDropped15Min(940), -- T_PMON_PORTQUEUE6OCTETSDROPPED_15MIN
                         tPmonPortQueue7OctetsDropped15Min(941), -- T_PMON_PORTQUEUE7OCTETSDROPPED_15MIN
                         tPmonPortQueue8OctetsDropped15Min(942), -- T_PMON_PORTQUEUE8OCTETSDROPPED_15MIN
                         tPmonDmaBfd15Min(943),    -- T_PMON_DMABFD_15MIN
                         tPmonDmxBfd15Min(944),    -- T_PMON_DMXBFD_15MIN
                         tPmonDmanFdv15Min(945),   -- T_PMON_DMANFDV_15MIN
                         tPmonDmxnFdv15Min(946),   -- T_PMON_DMXNFDV_15MIN
                         tPmonDmafFdv15Min(947),   -- T_PMON_DMAFFDV_15MIN
                         tPmonDmxfFdv15Min(948),   -- T_PMON_DMXFFDV_15MIN
                         tPmonSapIngressPktsDropped1Day(949),    -- T_PMON_SAPINGRESSPKTSDROPPED_1DAY
                         tPmonSapIngressOctetsDropped1Day(950),  -- T_PMON_SAPINGRESSOCTETSDROPPED_1DAY
                         tPmonPortIfInPackets1Day(951),          -- T_PMON_PORTIFINPACKETS_1DAY
                         tPmonPortIfOutPackets1Day(952),         -- T_PMON_PORTIFOUTPACKETS_1DAY
                         tPmonPortIfInOctets1Day(953),           -- T_PMON_PORTIFINOCTETS_1DAY
                         tPmonPortIfOutOctets1Day(954),          -- T_PMON_PORTIFOUTOCTETS_1DAY
                         tPmonPortIfInDiscards1Day(955),         -- T_PMON_PORTIFINDISCARDS_1DAY
                         tPmonPortIfOutDiscards1Day(956),        -- T_PMON_PORTIFOUTDISCARDS_1DAY
                         tPmonPortIfInErrors1Day(957),           -- T_PMON_PORTIFINERRORS_1DAY
                         tPmonPortIfOutErrors1Day(958),          -- T_PMON_PORTIFOUTERRORS_1DAY
                         tPmonPortHighCapacityPkts1Day(959),     -- T_PMON_PORTHIGHCAPACITYPKTS_1DAY
                         tPmonPortHighCapacityOctets1Day(960),   -- T_PMON_PORTHIGHCAPACITYOCTETS_1DAY
                         tPmonPortQueue1PktsDropped1Day(961),    -- T_PMON_PORTQUEUEPKTSDROPPED_1DAY
                         tPmonPortQueue2PktsDropped1Day(962),    -- T_PMON_PORTQUEUEPKTSDROPPED_1DAY
                         tPmonPortQueue3PktsDropped1Day(963),    -- T_PMON_PORTQUEUEPKTSDROPPED_1DAY
                         tPmonPortQueue4PktsDropped1Day(964),    -- T_PMON_PORTQUEUEPKTSDROPPED_1DAY
                         tPmonPortQueue5PktsDropped1Day(965),    -- T_PMON_PORTQUEUEPKTSDROPPED_1DAY
                         tPmonPortQueue6PktsDropped1Day(966),    -- T_PMON_PORTQUEUEPKTSDROPPED_1DAY
                         tPmonPortQueue7PktsDropped1Day(967),    -- T_PMON_PORTQUEUEPKTSDROPPED_1DAY
                         tPmonPortQueue8PktsDropped1Day(968),    -- T_PMON_PORTQUEUEPKTSDROPPED_1DAY
                         tPmonPortQueue1OctetsDropped1Day(969),  -- T_PMON_PORTQUEUEOCTETSDROPPED_1DAY
                         tPmonPortQueue2OctetsDropped1Day(970),  -- T_PMON_PORTQUEUEOCTETSDROPPED_1DAY
                         tPmonPortQueue3OctetsDropped1Day(971),  -- T_PMON_PORTQUEUEOCTETSDROPPED_1DAY
                         tPmonPortQueue4OctetsDropped1Day(972),  -- T_PMON_PORTQUEUEOCTETSDROPPED_1DAY
                         tPmonPortQueue5OctetsDropped1Day(973),  -- T_PMON_PORTQUEUEOCTETSDROPPED_1DAY
                         tPmonPortQueue6OctetsDropped1Day(974),  -- T_PMON_PORTQUEUEOCTETSDROPPED_1DAY
                         tPmonPortQueue7OctetsDropped1Day(975),  -- T_PMON_PORTQUEUEOCTETSDROPPED_1DAY
                         tPmonPortQueue8OctetsDropped1Day(976),  -- T_PMON_PORTQUEUEOCTETSDROPPED_1DAY
                         tPmonSlmanFlr1Day(977),   -- T_PMON_SLMANFLR_1DAY
                         tPmonSlmxnFlr1Day(978),   -- T_PMON_SLMXNFLR_1DAY
                         tPmonSlmafFlr1Day(979),   -- T_PMON_SLMAFFLR_1DAY
                         tPmonSlmxfFlr1Day(980),   -- T_PMON_SLMXFFLR_1DAY
                         tPmonDmaBfd1Day(981),     -- T_PMON_DMABFD_1DAY
                         tPmonDmxBfd1Day(982),     -- T_PMON_DMXBFD_1DAY
                         tPmonDmanFdv1Day(983),    -- T_PMON_DMANFDV_1DAY
                         tPmonDmxnFdv1Day(984),    -- T_PMON_DMXNFDV_1DAY
                         tPmonDmafFdv1Day(985),    -- T_PMON_DMAFFDV_1DAY
                         tPmonDmxfFdv1Day(986),    -- T_PMON_DMXFFDV_1DAY
                         cfmLmTestComplete(987),   -- CFMLMTESTCOMPLETE
                         cbr10G3RxLOS(988),        -- CBR10G3RXLOS
                         cbr10G3RxLSS(989),        -- CBR10G3RXLSS
                         lspFailedApe(990),        -- LSPFAILEDAPE
                         lspFailedXc(991),         -- LSPFAILEDXC
                         lspFailedPre(992),        -- LSPFAILEDPRE
                         lspFailedTp(993),         -- LSPFAILEDTP
                         lspFailedUnprot(994),     -- LSPFAILEDUNPROT
                         apeInProgress(995),       -- APEINPROGRESS
                         backupUnavail(996),       -- BACKUPUNAVAIL
                         channelViolation(997),    -- CHANNELVIOLATION
                         colorViolation(998),      -- COLORVIOLATION
                         feasibilityViolation(999), -- FEASIBILITYVIOLATION
                         srgDiviersity(1000),      -- SRGDIVIERSITY
                         linkDiviersity(1001),     -- LINKDIVIERSITY
                         nunvComm(1002),           -- NUNVCOMM
                         nunvConfig(1003),         -- NUNVCONFIG
                         nunvIndetermined(1004),   -- NUNVINDETERMINED
                         nunvReversion(1005),      -- NUNVREVERSION
                         nunvTpBlocked(1006),      -- NUNVTPBLOCKED
                         nunvTransmission(1007),   -- NUNVTRANSMISSION
                         readyToRevert(1008),      -- READYTOREVERT
                         routeNotPossible(1009),   -- ROUTENOTPOSSIBLE
                         reRouted(1010),           -- REROUTED
                         testMode(1011),           -- TESTMODE
                         restorationDisabled(1012), -- RESTORATIONDISABLED
                         nodeDeg(1013),            -- NODEDEG
                         inMigration(1014),        -- INMIGRATION
                         subNodeUnreachable(1015), -- SUBNODEUNREACHABLE
                         neUnreachable(1016),      -- NEUNREACHABLE
                         opticalParamErr(1017),    -- OPTICALPARAMERR
                         eptUploadErr(1018),       -- EPTUPLOADERR
                         commDown(1019),           -- COMMDOWN
                         commDeg(1020),            -- COMMDEG
                         nvMismatch(1021),         -- NVMISMATCH
                         objCreated(1022),         -- OBJCREATED
                         objDeleted(1023),         -- OBJDELETED
                         ssfOtu(1024),             -- SSFOTU
                         ssfOduTp(1025),           -- SSFODUTP
                         tPmonDmanfd15Min(1026),   -- T_PMON_DMANFD_15MIN
                         tPmonDmxnfd15Min(1027),   -- T_PMON_DMXNFD_15MIN
                         tPmonDmaffd15Min(1028),   -- T_PMON_DMAFFD_15MIN
                         tPmonDmxffd15Min(1029),   -- T_PMON_DMXFFD_15MIN
                         tPmonSlmanflr15Min(1030), -- T_PMON_SLMANFLR_15MIN
                         tPmonSlmafflr15Min(1031), -- T_PMON_SLMAFFLR_15MIN
                         tPmonSlmnhli15Min(1032),  -- T_PMON_SLMNHLI_15MIN
                         tPmonSlmfhli15Min(1033),  -- T_PMON_SLMFHLI_15MIN
                         tPmonLmanflr15Min(1034),  -- T_PMON_LMANFLR_15MIN
                         tPmonLmxnflr15Min(1035),  -- T_PMON_LMXNFLR_15MIN
                         tPmonLmafflr15Min(1036),  -- T_PMON_LMAFFLR_15MIN
                         tPmonLmxfflr15Min(1037),  -- T_PMON_LMXFFLR_15MIN
                         tPmonLmnhli15Min(1038),   -- T_PMON_LMNHLI_15MIN
                         tPmonLmfhli15Min(1039),   -- T_PMON_LMFHLI_15MIN
                         tPmonDmanfd1Day(1040),    -- T_PMON_DMANFD_1DAY
                         tPmonDmxnfd1Day(1041),    -- T_PMON_DMXNFD_1DAY
                         tPmonDmaffd1Day(1042),    -- T_PMON_DMAFFD_1DAY
                         tPmonDmxffd1Day(1043),    -- T_PMON_DMXFFD_1DAY
                         tPmonSlmnhli1Day(1044),   -- T_PMON_SLMNHLI_1DAY
                         tPmonSlmfhli1Day(1045),   -- T_PMON_SLMFHLI_1DAY
                         tPmonLmanflr1Day(1046),   -- T_PMON_LMANFLR_1DAY
                         tPmonLmxnflr1Day(1047),   -- T_PMON_LMXNFLR_1DAY
                         tPmonLmafflr1Day(1048),   -- T_PMON_LMAFFLR_1DAY
                         tPmonLmxfflr1Day(1049),   -- T_PMON_LMXFFLR_1DAY
                         tPmonLmnhli1Day(1050),    -- T_PMON_LMNHLI_1DAY
                         tPmonLmfhli1Day(1051),    -- T_PMON_LMFHLI_1DAY
                         tPmonSlmfhliContinuous(1052),  -- T_PMON_SLMFHLI_CONTINUOUS
                         tPmonSlmnhliContinuous(1053),  -- T_PMON_SLMNHLI_CONTINUOUS
                         tPmonSlmxfflrContinuous(1054), -- T_PMON_SLMXNFLR_CONTINUOUS
                         tPmonSlmxnflrContinuous(1055), -- T_PMON_SLMXNFLR_CONTINUOUS
                         tPmonSlmanflrContinuous(1056), -- T_PMON_SLMANFLR_CONTINUOUS
                         tPmonSlmafflrContinuous(1057), -- T_PMON_SLMAFFLR_CONTINUOUS
                         srTca(1058),              -- SRTCA
                         rmdCesChannelNoTdmPl(1059), -- RMDCESCHANNELNOTDMPL
                         rmdCesChannelLPL(1060),   -- RMDCESCHANNELLPL
                         rmdCesChannelRPL(1061),   -- RMDCESCHANNELRPL
                         rmdNimLOF(1062),          -- RMDNIMLOF
                         rmdIfLOS(1063),           -- RMDIFLOS
                         pwrSuspRx(1064),          -- PWRSUSPRX
                         rmdDiscoveredDevice(1065), -- RMDDISCOVEREDDEVICE
                         tcmAis(1066),             -- TCMAIS
                         rmdTypeMismatch(1067),    -- RMDTYPEMISMATCH
                         rmdWrongDestMac(1068),    -- RMDWRONGDESTMAC
                         rmdUnknownEcid(1069),     -- RMDUNKNOWNECID
                         rmdJbRecentered(1070),    -- RMDJBRECENTERED
                         tOprhLane1(1071),         -- T_OPRH_LANE_1
                         tOprhLane2(1072),         -- T_OPRH_LANE_2
                         tOprhLane3(1073),         -- T_OPRH_LANE_3
                         tOprhLane4(1074),         -- T_OPRH_LANE_4
                         tOprhLane5(1075),         -- T_OPRH_LANE_5
                         tOprhLane6(1076),         -- T_OPRH_LANE_6
                         tOprhLane7(1077),         -- T_OPRH_LANE_7
                         tOprhLane8(1078),         -- T_OPRH_LANE_8
                         tOprhLane9(1079),         -- T_OPRH_LANE_9
                         tOprhLane10(1080),        -- T_OPRH_LANE_10
                         tOprlLane1(1081),         -- T_OPRL_LANE_1
                         tOprlLane2(1082),         -- T_OPRL_LANE_2
                         tOprlLane3(1083),         -- T_OPRL_LANE_3
                         tOprlLane4(1084),         -- T_OPRL_LANE_4
                         tOprlLane5(1085),         -- T_OPRL_LANE_5
                         tOprlLane6(1086),         -- T_OPRL_LANE_6
                         tOprlLane7(1087),         -- T_OPRL_LANE_7
                         tOprlLane8(1088),         -- T_OPRL_LANE_8
                         tOprlLane9(1089),         -- T_OPRL_LANE_9
                         tOprlLane10(1090),        -- T_OPRL_LANE_10
                         tOpthLane1(1091),         -- T_OPTH_LANE_1
                         tOpthLane2(1092),         -- T_OPTH_LANE_2
                         tOpthLane3(1093),         -- T_OPTH_LANE_3
                         tOpthLane4(1094),         -- T_OPTH_LANE_4
                         tOpthLane5(1095),         -- T_OPTH_LANE_5
                         tOpthLane6(1096),         -- T_OPTH_LANE_6
                         tOpthLane7(1097),         -- T_OPTH_LANE_7
                         tOpthLane8(1098),         -- T_OPTH_LANE_8
                         tOpthLane9(1099),         -- T_OPTH_LANE_9
                         tOpthLane10(1100),        -- T_OPTH_LANE_10
                         tOptlLane1(1101),         -- T_OPTL_LANE_1
                         tOptlLane2(1102),         -- T_OPTL_LANE_2
                         tOptlLane3(1103),         -- T_OPTL_LANE_3
                         tOptlLane4(1104),         -- T_OPTL_LANE_4
                         tOptlLane5(1105),         -- T_OPTL_LANE_5
                         tOptlLane6(1106),         -- T_OPTL_LANE_6
                         tOptlLane7(1107),         -- T_OPTL_LANE_7
                         tOptlLane8(1108),         -- T_OPTL_LANE_8
                         tOptlLane9(1109),         -- T_OPTL_LANE_9
                         tOptlLane10(1110),        -- T_OPTL_LANE_10
                         imageNotReady(1111),      -- IMAGENOTREADY
                         badClkFreq(1112),         -- BADCLKFREQ
                         suspectClkFreq(1113),     -- SUSPECTCLKFREQ
                         esCableMismatch1(1114),   -- ESCABLEMISMATCH1
                         esCableMismatch2(1115),   -- ESCABLEMISMATCH2
                         esCableMismatch3(1116),   -- ESCABLEMISMATCH3
                         esCableMismatch4(1117),   -- ESCABLEMISMATCH4
                         esCableMismatch5(1118),   -- ESCABLEMISMATCH5
                         esCableMismatch6(1119),   -- ESCABLEMISMATCH6
                         esCableMismatch7(1120),   -- ESCABLEMISMATCH7
                         esCableMismatch8(1121),   -- ESCABLEMISMATCH8
                         esCableMismatch9(1122),   -- ESCABLEMISMATCH9
                         esCableMismatch10(1123),  -- ESCABLEMISMATCH10
                         esCableMismatch11(1124),  -- ESCABLEMISMATCH11
                         esCableMismatch12(1125),  -- ESCABLEMISMATCH12
                         esCableMismatch13(1126),  -- ESCABLEMISMATCH13
                         esCableMismatch14(1127),  -- ESCABLEMISMATCH14
                         esCableMismatch15(1128),  -- ESCABLEMISMATCH15
                         esCableMismatch16(1129),  -- ESCABLEMISMATCH16
                         esCableMismatch17(1130),  -- ESCABLEMISMATCH17
                         esCableMismatch18(1131),  -- ESCABLEMISMATCH18
                         esCableMismatch19(1132),  -- ESCABLEMISMATCH19
                         esCableMismatch20(1133),  -- ESCABLEMISMATCH20
                         esCableMismatch21(1134),  -- ESCABLEMISMATCH21
                         esCableMismatch22(1135),  -- ESCABLEMISMATCH22
                         esCableMismatch23(1136),  -- ESCABLEMISMATCH23
                         esCableMismatch24(1137),  -- ESCABLEMISMATCH24
                         cardClkOffFreq(1138),     -- CARDCLKOFFFREQ
                         shelfInVoltMaxCur(1139),  -- SHELFINVOLTMAXCUR
                         fwMismatch(1140),         -- FWMISMATCH
                         fpgaInitNsa1(1141),       -- FPGAINITNSA1
                         fpgaInitNsa2(1142),       -- FPGAINITNSA2
                         fpgaInitNsa3(1143),       -- FPGAINITNSA3
                         fpgaInitNsa4(1144),       -- FPGAINITNSA4
                         fpgaInitNsa5(1145),       -- FPGAINITNSA5
                         fpgaInitNsa6(1146),       -- FPGAINITNSA6
                         fpgaInitNsa7(1147),       -- FPGAINITNSA7
                         fpgaInitNsa8(1148),       -- FPGAINITNSA8
                         fpgaInitNsa9(1149),       -- FPGAINITNSA9
                         fpgaInitNsa10(1150),      -- FPGAINITNSA10
                         fpgaTimeoutNsa(1151),     -- FPGATIMEOUTNSA
                         fpgaFailNsa(1152),        -- FPGAFAILNSA
                         lagStateChange(1153),     -- LAGSTATECHANGE
                         lagMemberPortStateChange(1154), -- LAGMEMBERPORTSTATECHANGE
                         packetCardInit(1155),     -- PACKETCARDINIT
                         frcRfCkSel(1156),         -- FRCRFCKSEL
                         lola(1157),               -- LOLA
                         otdrScanSuccess(1158),    -- OTDRSCANSUCCESS
                         otdrScanFail(1159),       -- OTDRSCANFAIL
                         aprLimited(1160),         -- APRLIMITED
                         insertMod(1161),          -- INSERTMOD
                         removeMod(1162),          -- REMOVEMOD
                         discoverMod(1163),        -- DISCOVERMOD
                         aprForced(1164),          -- APRFORCED
                         spiReadError(1165),       -- SPIREADERROR
                         shelfIncon(1166),         -- SHELFINCON
                         configMM(1167),           -- CONFIGMM
                         opticalTest(1168),        -- OPTICALTEST
                         ftdEncrypt15Min(1169),    -- FTD_ENCRYPT_15MIN
                         ftdEncrypt1Day(1170),     -- FTD_ENCRYPT_1DAY
                         lagPortAddSuccess(1171),  -- LAGPORTADDSUCCESS
                         hwAccessFailure(1172),    -- HWACCESSFAILURE
                         sdkMismatch(1173),        -- SDKMISMATCH
                         loOMFI(1174),             -- LOOMFI
                         losN1(1175),              -- LOSN1
                         losN2(1176),              -- LOSN2
                         notAllowPowered(1177),    -- NOTALLOWPOWERED
                         shelfLoadWarning(1178),   -- SHELFLOADWARNING
                         shelfIdMismatch(1179),    -- SHELFIDMISMATCH
                         restrictedConnectivity(1180),  -- RESTRICTED_CONNECTIVITY
                         vwmIDFail(1181),          -- VWMIDFAIL
                         gfpExm(1182),             -- GFPEXM
                         syncMisc1(1183),           -- SYNCMISC1
                         sapPortStateChangeProcessed(1184), --SAP_PORT_STATE_CHANGE_PROCESSED
                         sapTlsMacMoveExceeded(1185), --SAP_MAC_MOVE_EXCEEDED
                         intfcOprDown(1186), 	     -- INTFC-OPR-DWN
                         eCondHiRamanGain(1187),   -- LORAMGAIN
                         eCondLoRamanGain(1188),   -- HIRAMGAIN
                         eCondUruO(1189),         -- URU-O
                         eCondUruP(1190),         -- URU-P
                         mplsIfStateChange(1191),   -- MPLS-IF-STATE-CHANGE
                         mplsLspUp(1192),           -- MPLS-LSP-UP
                         eCondMplsLspDown(1193),  -- MPLS-LSP-DWN
                         mplsTpLspActivePathUp(1194), -- MPLSTP-LSP-ACTIVE-PATH-UP
                         mplsTpLspActivePathChange(1195), -- MPLSTP-LSP-ACTIVE-PATH-CHANGE
                         eCondFrequencySlotMismatch(1196), -- FREQUENCYSLOTMISMATCH
                         mplsTpLspPingTestComplete(1197), -- LSP-PING-TEST
                         mplsTpLspTraceTestComplete(1198), -- LSP-TRACE-TEST
                         mjcpf(1199),              --  MJCPF
                         extIfFail(1200),          --  EXTIFFAIL
                         sdpOprDwn(1201), 		 --  SDP-OPR-DWN
                         sdpOprStatChg(1202), 	 --  SDP-OPR-STAT-CHG
                         tPmonIntfcTransmittedPkts15Min(1203), --  T_PMON_INTFCTRANSMITTEDPKTS_15MIN
                         tPmonIntfcTransmittedPkts1Day(1204), --  T_PMON_INTFCTRANSMITTEDPKTS_1DAY
                         tPmonIntfcTransmittedOctets15Min(1205), --  T_PMON_INTFCTRANSMITTEDOCTETS_15MIN
                         tPmonIntfcTransmittedOctets1Day(1206), --  T_PMON_INTFCTRANSMITTEDOCTETS_1DAY
                         tPmonIntfcReceivedPkts15Min(1207), --  T_PMON_INTFCRECEIVEDPKTS_15MIN
                         tPmonIntfcReceivedPkts1Day(1208), --  T_PMON_INTFCRECEIVEDPKTS_1DAY
                         tPmonIntfcReceivedOctets15Min(1209), --  T_PMON_INTFCRECEIVEDOCTETS_15MIN
                         tPmonIntfcReceivedOctets1Day(1210), --  T_PMON_INTFCRECEIVEDOCTETS_1DAY
                         tPmonSdpIngressForwardedPkts15Min(1211), --  T_PMON_SDPINGRESSFORWARDEDPKTS_15MIN
                         tPmonSdpIngressForwardedPkts1Day(1212), --  T_PMON_SDPINGRESSFORWARDEDPKTS_1DAY
                         tPmonSdpIngressForwardedOctets15Min(1213), --  T_PMON_SDPINGRESSFORWARDEDOCTETS_15MIN
                         tPmonSdpIngressForwardedOctets1Day(1214), --  T_PMON_SDPINGRESSFORWARDEDOCTETS_1DAY
                         tPmonSdpEgressForwardedPkts15Min(1215), --  T_PMON_SDPEGRESSFORWARDEDPKTS_15MIN
                         tPmonSdpEgressForwardedPkts1Day(1216), --  T_PMON_SDPEGRESSFORWARDEDPKTS_1DAY
                         tPmonSdpEgressForwardedOctets15Min(1217), --  T_PMON_SDPEGRESSFORWARDEDOCTETS_15MIN
                         tPmonSdpEgressForwardedOctets1Day(1218), --  T_PMON_SDPEGRESSFORWARDEDOCTETS_1DAY
                         sdpSpkOprDwn(1219), 		 -- SDP-SPK-OPR-DWN
                         sdpSpkStateChg(1220), 	 -- SDP-SPK-STATE-CHG
                         sdpBindOprStateChg(1221),  -- SDP-BIND-OPR-STATE-CHG
                         envInput9Active(1222),     -- ENV-9
                         envInput10Active(1223),     -- ENV-10
                         envInput11Active(1224),     -- ENV-11
                         envInput12Active(1225),     -- ENV-12
                         envInput13Active(1226),     -- ENV-13
                         envInput14Active(1227),     -- ENV-14
                         envInput15Active(1228),     -- ENV-15
                         envInput16Active(1229),     -- ENV-16
                         mplsMepLoc(1230),           -- MEP-LOC
                         mplsMepMmg(1231),           -- MEP-MMG
                         mplsMepUnm(1232),           -- MEP-UNM
                         mplsMepRdi(1233),           -- MEP-RDI
                         mplsMepUnp(1234),           -- MEP-UNP
                         vRtrBfdSessExtDown(1235),   -- BFD-SESS-DOWN
                         vRtrBfdSessExtDeleted(1236),  -- BFD-SESS-DELETED
                         vRtrBfdSessExtProtChange(1237),  -- BFD-SESS-PROT-CHANGE
                         mplsTpLspPtTypeMsmtch(1238),  -- MPLSTP-LSP-PTTYPE-MSMTCH
                         mplsTpLspRvrtMsmtch(1239),  -- MPLSTP-LSP-RVRT-MSMTCH
                         noAssociation(1240),        -- NoAssociation 
                         lanSignalDegrade(1241),     -- LANSIGNALDEGRADE
                         farEndSignalDegrade(1242),  -- FARENDSIGNALDEGRADE
                         farEndB1SignalDegrade(1243),-- FARENDB1SIGNALDEGRADE
                         clusterUnavail(1244),       -- CLUSTERUNAVAIL
                         clusterAuditSuccess(1245),  -- CLUSTERAUDITSUCCESS
                         clusterAuditFail(1246),     -- CLUSTERAUDITFAIL
                         clusterUplinkDeleted(1247), -- CLUSTERUPLINKDELETED
                         clusterDataRtrv(1248),      -- CLUSTERDATARTRV
                         clusterDataFlt(1249),       -- CLUSTERDATAFLT
                         clusterTrapFail(1250),      -- CLUSTERTRAPFAIL
                         vRtrBfdSessExtUp(1251),     -- BFD-SESS-UP
                         occpCr(1252),               -- OCCPCR
                         occpMj(1253),               -- OCCPMJ
                         occpMn(1254),               -- OCCPMN
                         shelfAirFilterMaintenance(1255),  -- INSPECTAIRFILTER
                         sdpBindEndPointTxActiveChanged(1256),  -- SDP-SPK-ACTIVE-CHANGE
                         sdpBindPwLocalStatusBitsChanged(1257),  -- PW-LOCAL-STATUS-CHANGE
                         sdpBindPwPeerStatusBitsChanged(1258),  -- PW-PEER-STATUS-CHANGE
                         sdpBindPingTestComplete(1259),  -- PW-PING-TEST
                         sdpBindTraceTestComplete(1260), -- PW-TRACE-TEST
                         hwrvunknown(1261),          -- HWRVUNKNOWN
                         ecTypeMis(1262),            -- ECTYPEMIS
                         oaPumpBiasCurrHighC(1263),  -- OAPUMPBIASCURRHIGH-C
                         oaPumpBiasCurrHighL(1264),  -- OAPUMPBIASCURRHIGH-L
                         oaPumpTempHighC(1265),      -- OAPUMPTEMPHIGH-L
                         oaPumpTempHighL(1266),      -- OAPUMPTEMPHIGH-C
                         losPC(1267),                -- LOS-P-C
                         losPL(1268),                -- LOS-P-L
                         oprPwrLowC(1269),           -- OPRPWRLOW-C
                         oprPwrLowL(1270),           -- OPRPWRLOW-L
                         oprPwrHighC(1271),          -- OPRPWRHIGH-C
                         oprPwrHighL(1272),          -- OPRPWRHIGH-L
                         ampDisabledC(1273),         -- AMPDISABLED-C
                         ampDisabledL(1274),         -- AMPDISABLED-L
                         highGainC(1275),            -- HIGAIN-C
                         highGainL(1276),            -- HIGAIN-L
                         loGainC(1277),              -- LOGAIN-C
                         loGainL(1278),              -- LOGAIN-L
                         allChanMissOutC(1279),      -- ALLCHANMISS-OUT-C
                         allChanMissOutL(1280),      -- ALLCHANMISS-OUT-L
                         lotOutC(1281),              -- LOT-OUT-C
                         lotOutL(1282),              -- LOT-OUT-L
                         pwrMaxGainC(1283),          -- PWRMAXGAIN-C
                         pwrMaxGainL(1284),          -- PWRMAXGAIN-L
                         softwareError(1285),        -- SOFTWAREERROR
                         latchOpen(1286),            -- LATCHOPEN
                         xcMismatch(1287),           -- XCMISMATCH
                         invalidXc(1288),            -- INVALIDXC
                         cardThermShutdown(1289),    -- THERMSHUTD
                         sc1LinkFail(1290),          -- SC1LNKFAIL
                         sc2LinkFail(1291),          -- SC2LNKFAIL
                         sc3LinkFail(1292),          -- SC3LNKFAIL
                         scLinkFail(1293),           -- SCLNKFAIL
                         sc1LinkDegarde(1294),       -- SC1LNKDGR
                         sc2LinkDegarde(1295),       -- SC2LNKDGR
                         sc3LinkDegarde(1296),       -- SC3LNKDGR
                         scLinkDegarde(1297),        -- SCLNKDGR
                         intOhFail(1298),            -- INTOHFAIL
                         faceplateMissing(1299),     -- FACEPLATEMISS
                         cardPowerOff(1300),         -- CRDPWROFF
                         erpRingStateChng(1301),     -- ERPRINGSTATECHNG           
                         erpRingPortStateChng(1302), -- ERPRINGPORTSTATECHNG
                         invalidModule(1303),        -- INVALIDMOD
                         intTsiFail(1304),           -- INTTSIFAIL
                         ecModeMismatch(1305),       -- ECMODEMISMATCH
                         dbCrcTypeMis(1306),         -- DBCRCTYPEMIS
                         lldpRemTablesChange(1307),  -- LLDPREMTABLESCHANGE
                         eqptCru(1308),              -- EQPTCRU 
                         shelfInvError(1309),        -- SHELFINVERROR
                         shelfInvMismatch(1310),     -- SHELFINVMISMATCH
                         intSyncA(1311),             -- INTSYNCA
                         intSyncB(1312),             -- INTSYNCB
                         intSyncBoth(1313),          -- INTSYNCBOTH
                         cKWKATMis(1314),            -- CKWKATMIS
                         inventoryErrMod(1315),      -- INVENTORYERRMOD
                         lnkSpdDeg(1316),            -- LNKSPDDEG
                         bdLnkSpd(1317),             -- BDLNKSPD
                         fopOm(1318),                -- FOP-OM
                         fopPm(1319),                -- FOP-PM
                         fopSm(1320),                -- FOP-SM
                         fopNr(1321),                -- FOP-NR
                         fopIncon(1322),             -- FOP-INCON
                         frcdWkSwBkFe(1323),         -- FRCDWKSWBK-FE
                         frcdWkSwPrFe(1324),         -- FRCDWKSWPR-FE
                         lockoutOfPrFe(1325),        -- LOCKOUTOFPR-FE
                         manWkSwBkFe(1326),          -- MANWKSWBK-FE
                         manWkSwPrFe(1327),          -- MANWKSWPR-FE
                         wkSwBkFe(1328),             -- WKSWBK-FE
                         wkSwPrFe(1329),             -- WKSWPR-FE
                         wtrFe(1330),                -- WTR-FE
                         exWkSwBk(1331),             -- EXWKSWBK
                         exWkSwPr(1332),             -- EXWKSWPR
                         exWkSwBkFe(1333),           -- EXWKSWBK-FE
                         exWkSwPrFe(1334)            -- EXWKSWPR-FE
                         }

    TnCommand ::= TEXTUAL-CONVENTION
        STATUS         current
        DESCRIPTION    ""
        SYNTAX         INTEGER {
                         noCmd(1),
                         execute(2)
                       }

    TnOchStatus ::= TEXTUAL-CONVENTION
        STATUS         current
        DESCRIPTION    ""
        SYNTAX         INTEGER {
                         up(1),
                         down(2),
                         testing(3),
                         unassigned(4)
                       }

    AluWdmDisabledEnabled ::= TEXTUAL-CONVENTION
        STATUS         current
        DESCRIPTION    "Represents disable or enable action."
        SYNTAX         INTEGER {
                         disabled(1),
                         enabled(2)
                      }

    AluWdmEnabledDisabled ::= TEXTUAL-CONVENTION
        STATUS         current
        DESCRIPTION    "Represents enable or disable action."
        SYNTAX         INTEGER {
                         enabled(1),
                         disabled(2)
                      }

    AluWdmTnIfType ::= TEXTUAL-CONVENTION
        STATUS         current
        DESCRIPTION    "In a set request, value default indicates that
                        the NE assigns the port automatically, if
                        possible.  A value of default will not be
                        returned to the network operator.  If tnIfType
                        is set to unassigned and ifAdminStatus has also
                        been set, the set request will be failed back
                        to the network operator."
        SYNTAX         INTEGER {
                         unassigned(1),
                         default(2),
                         unknown(3),
                         oc3(4),
                         oc12(5),
                         oc48(6),
                         oc192(7),
                         ots(8),
                         och(9),
                         otu1(10),
                         otu2(11),
                         gige(12),
                         tenGige(13),
                         stm1(14),
                         stm4(15),
                         stm16(16),
                         stm64(17),
                         fc1g(18),
                         fc2g(19),
                         fc4g(20),
                         fc10g(21),
                         cbr2g5(22),
                         cbr10g(23),
                         anyRate(24),
                         hdSdi(25),
                         fe(26),
                         fddi(27),
                         esCon(28),
                         dvbAsi(29),
                         dvi6000(30),
                         otu3(31),
                         oc768(32),
                         stm256(33),
                         otu4(34),
                         fc8g(35),
                         hundredGige(36),
                         sdsdi(37),
                         e1(38),
                         sdi3g(39),
                         dcn(40),
                         evoa(41),
                         fee(42),
                         oduptf(43),
                         ds1(44),
                         otu3e2(45),
                         otu2e(46),
                         fortyGige(47),
                         sdr(48),
                         ddr(49),
                         tod(50),
                         lagGroup(51),
                         otl44(52),
                         fc16g(53),
                         qdr(54),
                         bits(55),
                         oneTru(56),
                         otu4x2(57),
                         otu1f(58),
                         cbr10g3(59),
                         fortyGigeMLD(60),
                         interLaken(61),
                         otl410(62),
                         otu4x4(63),
                         otu4Half(64),
                         otu4Halfx5(65),
                         sensor(66)
                       }

    AluWdmTransferProtocol ::= TEXTUAL-CONVENTION
        STATUS         current
        DESCRIPTION    "This attibutes indicates the transfer protocol."
        SYNTAX         INTEGER {
                         ftp(1),
                         sftp(2),
                         tftp(3)
                       }

    AluWdmOtuBitRate ::= TEXTUAL-CONVENTION
        STATUS         current
        DESCRIPTION    "OTU Bit-Rate.  Values not enumerated below
                        are also valid.  Some common values are:
                        otm10G709(1)
                        otm11G049(2)
                        otm11G096(3)
                        otm11G27(4)
                        otm2G66(5)
                        otm4G55(6)
                        otm111G810(7)
                        otm43G018(8)
                        unassigned(9998)
                        alien(9999)
                        unknown(10000)"
        SYNTAX         Unsigned32 (1..10000)

    AluWdmOtuEncoding ::= TEXTUAL-CONVENTION
        STATUS         current
        DESCRIPTION    "Signal modulation format.  Values not enumerated
                        below are also valid.  Some common values are:
                        nrz(1)
                        pdpsk(2)
                        dpsk(3)
                        cohpmbpsk(4)
                        cohpmqpsk(5)
                        cohpmqpskEnhOsnr(6)
                        nrzCFP1(7)
                        icohpmqpsk(8)
                        unassigned(9998)
                        alien(9999)
                        unknown(10000)"
        SYNTAX         Unsigned32 (1..10000)

    AluWdmCardCapacity ::= TEXTUAL-CONVENTION
        STATUS         current
        DESCRIPTION    "The capacity of the storage medium."
        SYNTAX         INTEGER {
                         unknownCapacity(1),
                         capacity4G(2),
                         capacity8G(3),
                         capacity16G(4),
                         capacity32G(5),
                         capacity64G(6),
                         capacity2G(7)
                       }

    AluWdmTtiStatus ::= TEXTUAL-CONVENTION
        STATUS         current
        DESCRIPTION    "TTI status."
        SYNTAX         INTEGER {
                         unavailable(1),
                         normal(2),
                         mismatch(3),
                         unspecified(4)
                       }

    AluWdmOdukStatus ::= TEXTUAL-CONVENTION
        STATUS         current
        DESCRIPTION    "Otuk operational state of the interface."
        SYNTAX         INTEGER {
                         up(1),
                         down(2)
                       }

    AluWdmTimDetMode ::= TEXTUAL-CONVENTION
        STATUS         current
        DESCRIPTION    "Trace Identifier Mismatch (TIM) modes."
        SYNTAX         INTEGER {
                         off(1),
                         dapi(2),
                         sapi(3),
                         both(4)
                       }

    AluWdmOthOdukCurrentStatusBits ::= TEXTUAL-CONVENTION
        STATUS         current
        DESCRIPTION    "Defect condition of the entity."
        SYNTAX         BITS {
                         oci(0),
                         lck(1),
                         tim(2),
                         deg(3),
                         bdi(4),
                         ssf(5)
                       }

    AluWdmOthOdukRate ::= TEXTUAL-CONVENTION
        STATUS         current
        DESCRIPTION    "Indicates the ODUk entity rate.
                          - odu1e is for 11.049G 10gbe CBR mapping.
                          - odu1f is for 11.27G 10FC CBR mapping.
                          - odu2e is for 11.096 10gbe CBR mapping.
                          - odu2f is for 11.32G 10GFC CBR mapping.
                          - odu3e1 has a lower bit rate than odu3e2."
        SYNTAX         INTEGER {
                         null(1),
                         odu0(2),
                         odu1(3),
                         odu1e(4),
                         odu1f(5),
                         odu2(6),
                         odu2e(7),
                         odu2f(8),
                         odu3(9),
                         odu3e1(10),
                         odu3e2(11),
                         odu4(12),
                         oduFlexCbr(13),
                         optSg(14),
                         oduFlexGfp(15)
                       }

    AluWdmOthOdukXcRate ::= TEXTUAL-CONVENTION
        STATUS         current
        DESCRIPTION    "Indicates the ODUk entity rate.
                          - odu1e is for 11.049G 10gbe CBR mapping.
                          - odu1f is for 11.27G 10FC CBR mapping.
                          - odu2e is for 11.096 10gbe CBR mapping.
                          - odu2f is for 11.32G 10GFC CBR mapping.
                          - odu3e1 has a lower bit rate than odu3e2."
        SYNTAX         INTEGER {
                         null(1),
                         odu0(2),
                         odu1(3),
                         odu1e(4),
                         odu1f(5),
                         odu2(6),
                         odu2e(7),
                         odu2f(8),
                         odu3(9),
                         odu3e1(10),
                         odu3e2(11),
                         odu4(12),
                         oduFlex(13),
                         optSg(14),
                         oduFlexFc400(15),
                         oduFlex3gSdi(16),
                         oduFlexSdr(17)
                       }

    AluWdmOdukStateQualifier ::= TEXTUAL-CONVENTION
        STATUS         current
        DESCRIPTION    "Indicates the state qualifier (i.e., the
                        secondary state) of the ODUk/OTUk state."
        SYNTAX         BITS {
                         act(0),
                         ains(1),
                         busy(2),
                         cp(3),
                         cpmp(4),
                         dsbld(5),
                         faf(6),
                         pmd(7),
                         sdee(8),
                         sgeo(9),
                         stbyh(10),
                         stbys(11),
                         uas(12),
                         wrk(13)
                       }

    AluWdmTypeOfNetIfOperation ::= TEXTUAL-CONVENTION
        STATUS         current
        DESCRIPTION    "Indicates the requested operation."
        SYNTAX         INTEGER {
                         empty(1),
                         add(2),
                         modify(3)
                       }

    AluWdmWtClkValues ::= TEXTUAL-CONVENTION
        STATUS         current
        DESCRIPTION    "Indicates the wavetracker clock values."
        SYNTAX         INTEGER {
                         wtClkAuto(1),
                         wtClkA(2),
                         wtClkB(3)
                       }

    AluWdmFecMode ::= TEXTUAL-CONVENTION
        STATUS         current
        DESCRIPTION    "FEC mode for OT cards."
        SYNTAX         INTEGER {
                         noFec(1),
                         g709Fec(2),
                         enhancedFec(3),
                         uFec(4),
                         enhancedFec2(5),
                         aFec(6),
                         sdFecG2(7),
--                         obsolete
--                         eFecI(7),
--                         eFecE(8),
--                         eFecB(9),
                         eSDFec(10),
                         hpFec(11)
                       }

    AluWdmDMInfoCurrentStatus ::= TEXTUAL-CONVENTION
        STATUS         current
        DESCRIPTION    "Indicates whether this Delay Measurement test
                        is valid.  notAvailable(3) indicates timeout,
                        resource unavailable, etc., types of failure in
                        the retrieval."
        SYNTAX         INTEGER {
                         invalid(1),
                         valid(2),
                         notAvailable(3)
                       }

    AluWdmPortOchOtuRate ::= TEXTUAL-CONVENTION
        STATUS         current
        DESCRIPTION    "The OCH OTU1/OTU2/OTU4 rates."
        SYNTAX         INTEGER {
                         otm10G709(1),
                         otm11G049(2),
                         otm11G096(3),
                         otm11G27(4),
                         otm2G66(5),
                         otm4G55(6),
                         otm111G810(7),
                         otm43G018(8),
                         otm44G58(9),
                         otm10G714(10),
                         otm11G317(11),
                         otm129G280(12),
                         otm27G952(13),
                         otm258G560(14),
                         otm268G925(15),
                         otm120G00(16),
                         otm336G156(17),
                         otm537G850(18),
                         otm134G463(19),
                         otm131G679(20),
                         otm67G231(21)
                       }
    
   AluWdmAsapType ::= TEXTUAL-CONVENTION
       STATUS         current
       DESCRIPTION    "tnASAPName is a Profile that belongs to this ASAP Type."
       SYNTAX         INTEGER {
                        unknown(1),
                        bits(2),
                        ngige(3),
                        cbr(4),
                        com(5),
                        ddr(6),
                        e1(7),
                        env(8),
                        eqpt(9),
                        erp(10),
                        fcn(11),
                        fe(12),
                        lag(13),
                        lineRef(14),
                        mep(15),
                        ocn(16),
                        och(17),
                        odu(18),
                        oduTcm(19),
                        oms(20),
                        omsp(21),
                        optsg(22),
                        ots(23),
                        otu(24),
                        plk(25),
                        proactiveTest(26),
                        ptpClock(27),
                        ptpPort(28),
                        rmd(29),
                        sap(30),
                        sdr(31),
                        stmn(32),
                        svc(33),
                        sync(34),
                        syncOut(35),
                        tod(36),
                        vts(37),
                        packet(38)
                      } 

   TnRackSize ::= TEXTUAL-CONVENTION
       STATUS       current
       DESCRIPTION  ""
       SYNTAX       INTEGER {
                      inch19(1),
                      other(2)
                    }

END  -- DEFINITION OF TROPIC-TC
