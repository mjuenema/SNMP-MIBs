HUAWEI-PTP-MIB DEFINITIONS ::= BEGIN
 
        IMPORTS
            hwDatacomm            
                FROM HUAWEI-MIB            
            InterfaceIndex            
                FROM IF-MIB            
            OBJECT-GROUP, MODULE-COMPLIANCE, NOTIFICATION-GROUP            
                FROM SNMPv2-CONF            
            IpAddress, Integer32, Unsigned32, OBJECT-TYPE, MODULE-IDENTITY, 
            NOTIFICATION-TYPE            
                FROM SNMPv2-SMI            
            TruthValue, MacAddress, RowStatus, TEXTUAL-CONVENTION            
                FROM SNMPv2-TC;
    
    
        -- 1.3.6.1.4.1.2011.5.25.187
        hwPtpMIB MODULE-IDENTITY 
            LAST-UPDATED "200902111449Z"        -- February 11, 2009 at 14:49 GMT
            ORGANIZATION 
                "Huawei Technologies co.,Ltd."
            CONTACT-INFO 
                "R&D BeiJing, Huawei Technologies co.,Ltd.
                Huawei Bld.,NO.3 Xinxi Rd., 
                Shang-Di Information Industry Base,
                Hai-Dian District Beijing P.R. China
                Zip:100085 
                Http://www.huawei.com                       
                E-mail:support@huawei.com"
            DESCRIPTION 
                "The HUAWEI-PTP-MIB contains objects to manage PTP."
            ::= { hwDatacomm 187 }

        
    
--
-- Textual conventions
--
    
        EnabledStatus ::= TEXTUAL-CONVENTION
            STATUS current
            DESCRIPTION 
                "A simple status value for the object."
            SYNTAX INTEGER
                {
                enabled(1),
                disabled(2)
                }

        VlanIdOrNone ::= TEXTUAL-CONVENTION
            STATUS current
            DESCRIPTION 
                "VlanIdOrNone."
            SYNTAX Integer32 (0 | 1..4094)

    
--
-- Node definitions
--
    
        -- 1.3.6.1.4.1.2011.5.25.187.1
        hwPtpGlobalObjects OBJECT IDENTIFIER ::= { hwPtpMIB 1 }

        
        -- 1.3.6.1.4.1.2011.5.25.187.1.1
        hwPtpEnable OBJECT-TYPE
            SYNTAX EnabledStatus
            MAX-ACCESS read-write
            STATUS current
            DESCRIPTION
                "Enable PTP function."
            ::= { hwPtpGlobalObjects 1 }

        
        -- 1.3.6.1.4.1.2011.5.25.187.1.2
        hwPtpDomain OBJECT-TYPE
            SYNTAX Integer32 (0..255)
            MAX-ACCESS read-write
            STATUS current
            DESCRIPTION
                "PTP device's domain attribute,this attribute is used by PTP Device to join
                BMC compute."
            ::= { hwPtpGlobalObjects 2 }

        
        -- 1.3.6.1.4.1.2011.5.25.187.1.3
        hwPtpDeviceType OBJECT-TYPE
            SYNTAX INTEGER
                {
                oc(1),
                bc(2),
                p2ptc(3),
                e2etc(4),
                p2ptcoc(5),
                e2etcoc(6),
                tcandbc(7),
                invalid(99)
                }
            MAX-ACCESS read-write
            STATUS current
            DESCRIPTION
                "PTP device's type attribute."
            ::= { hwPtpGlobalObjects 3 }

        
        -- 1.3.6.1.4.1.2011.5.25.187.1.4
        hwPtpSlaveOnly OBJECT-TYPE
            SYNTAX TruthValue
            MAX-ACCESS read-write
            STATUS current
            DESCRIPTION
                "PTP device's SlaveOnly attribute."
            ::= { hwPtpGlobalObjects 4 }

        
        -- 1.3.6.1.4.1.2011.5.25.187.1.5
        hwPtpLocalClockId OBJECT-TYPE
            SYNTAX OCTET STRING
            MAX-ACCESS read-write
            STATUS current
            DESCRIPTION
                "Local PTP device's ClockId."
            ::= { hwPtpGlobalObjects 5 }

        
        -- 1.3.6.1.4.1.2011.5.25.187.1.6
        hwPtpLocalClockAccuracy OBJECT-TYPE
            SYNTAX Integer32 (0..255)
            MAX-ACCESS read-write
            STATUS current
            DESCRIPTION
                "PTP device's clock accuracy attribute."
            ::= { hwPtpGlobalObjects 6 }

        
        -- 1.3.6.1.4.1.2011.5.25.187.1.7
        hwPtpLocalClockClass OBJECT-TYPE
            SYNTAX Integer32 (1..255)
            MAX-ACCESS read-write
            STATUS current
            DESCRIPTION
                "PTP device's clock class attribute."
            ::= { hwPtpGlobalObjects 7 }

        
        -- 1.3.6.1.4.1.2011.5.25.187.1.8
        hwPtpLocalClockPriority1 OBJECT-TYPE
            SYNTAX Integer32 (0..255)
            MAX-ACCESS read-write
            STATUS current
            DESCRIPTION
                "PTP device's clock priority1 attribute."
            ::= { hwPtpGlobalObjects 8 }

        
        -- 1.3.6.1.4.1.2011.5.25.187.1.9
        hwPtpLocalClockPriority2 OBJECT-TYPE
            SYNTAX Integer32 (0..255)
            MAX-ACCESS read-write
            STATUS current
            DESCRIPTION
                "PTP device's clock priority2 attribute."
            ::= { hwPtpGlobalObjects 9 }

        
        -- 1.3.6.1.4.1.2011.5.25.187.1.10
        hwPtpLocalClockTimeSource OBJECT-TYPE
            SYNTAX INTEGER
                {
                atomicclock(1),
                gps(2),
                terrestrialradio(3),
                ptp(4),
                ntp(5),
                handset(6),
                other(7),
                internaloscillator(8)
                }
            MAX-ACCESS read-write
            STATUS current
            DESCRIPTION
                "PTP device's clock time source attribute."
            ::= { hwPtpGlobalObjects 10 }

        
        -- 1.3.6.1.4.1.2011.5.25.187.1.11
        hwPtpUtc OBJECT-TYPE
            SYNTAX OCTET STRING
            MAX-ACCESS read-only
            STATUS current
            DESCRIPTION
                "Indicates current UTC."
            ::= { hwPtpGlobalObjects 11 }

        
        -- 1.3.6.1.4.1.2011.5.25.187.1.12
        hwPtpCurrentUtcOffset OBJECT-TYPE
            SYNTAX Integer32
            MAX-ACCESS read-write
            STATUS current
            DESCRIPTION
                "The offset between TAI and UTC. CurrentUtcOffset=TAI-UTC."
            ::= { hwPtpGlobalObjects 12 }

        
        -- 1.3.6.1.4.1.2011.5.25.187.1.13
        hwCurrentUtcOffsetValid OBJECT-TYPE
            SYNTAX TruthValue
            MAX-ACCESS read-only
            STATUS current
            DESCRIPTION
                "CurrentUtcOffsetValid."
            ::= { hwPtpGlobalObjects 13 }

        
        -- 1.3.6.1.4.1.2011.5.25.187.1.14
        hwPtpOldMasterClockId OBJECT-TYPE
            SYNTAX OCTET STRING
            MAX-ACCESS read-only
            STATUS current
            DESCRIPTION
                "Old grandmaster clock's clockId"
            ::= { hwPtpGlobalObjects 14 }

        
        -- 1.3.6.1.4.1.2011.5.25.187.1.15
        hwPtpCurrentMasterClockReceivePortType OBJECT-TYPE
            SYNTAX INTEGER
                {
                local(1),
                bits(2),
                line(3)
                }
            MAX-ACCESS read-only
            STATUS current
            DESCRIPTION
                "The current grandmaster clock received port type."
            ::= { hwPtpGlobalObjects 15 }

        
        -- 1.3.6.1.4.1.2011.5.25.187.1.16
        hwPtpCurrentMasterClockReceivePort OBJECT-TYPE
            SYNTAX OCTET STRING
            MAX-ACCESS read-only
            STATUS current
            DESCRIPTION
                "The current grandmaster clock received from which port."
            ::= { hwPtpGlobalObjects 16 }

        
        -- 1.3.6.1.4.1.2011.5.25.187.1.17
        hwPtpCurrentMasterClockStepRemoved OBJECT-TYPE
            SYNTAX Integer32 (0..127)
            MAX-ACCESS read-only
            STATUS current
            DESCRIPTION
                "Steps between current grandmaster clock device and the local clock device."
            ::= { hwPtpGlobalObjects 17 }

        
        -- 1.3.6.1.4.1.2011.5.25.187.1.18
        hwPtpVersion OBJECT-TYPE
            SYNTAX INTEGER
                {
                ieee1588v2(1),
                invalid(10)
                }
            MAX-ACCESS read-only
            STATUS current
            DESCRIPTION
                "The version of PTP."
            ::= { hwPtpGlobalObjects 18 }

        
        -- 1.3.6.1.4.1.2011.5.25.187.1.19
        hwPtpTimeScale OBJECT-TYPE
            SYNTAX INTEGER
                {
                ptp(1),
                arb(2)
                }
            MAX-ACCESS read-only
            STATUS current
            DESCRIPTION
                "The time scale of PTP."
            ::= { hwPtpGlobalObjects 19 }

        
        -- 1.3.6.1.4.1.2011.5.25.187.1.20
        hwPtpFrequencyTraceable OBJECT-TYPE
            SYNTAX TruthValue
            MAX-ACCESS read-only
            STATUS current
            DESCRIPTION
                "The frequency trace is enable."
            ::= { hwPtpGlobalObjects 20 }

        
        -- 1.3.6.1.4.1.2011.5.25.187.1.21
        hwPtpTimeTraceable OBJECT-TYPE
            SYNTAX TruthValue
            MAX-ACCESS read-only
            STATUS current
            DESCRIPTION
                "The time trace is enable."
            ::= { hwPtpGlobalObjects 21 }

        
        -- 1.3.6.1.4.1.2011.5.25.187.1.22
        hwPtpTimeSynchronizationStatus OBJECT-TYPE
            SYNTAX INTEGER
                {
                unsynchronization(1),
                synchronization(2)
                }
            MAX-ACCESS read-only
            STATUS current
            DESCRIPTION
                "Indicates TimeSynchronizationStatus is synchronization or not."
            ::= { hwPtpGlobalObjects 22 }

        
        -- 1.3.6.1.4.1.2011.5.25.187.1.23
        hwPtpGrandMasterClockPriority1 OBJECT-TYPE
            SYNTAX Integer32 (0..255)
            MAX-ACCESS read-only
            STATUS current
            DESCRIPTION
                "PTP GrandMaster clock priority1 attribute."
            ::= { hwPtpGlobalObjects 23 }

        
        -- 1.3.6.1.4.1.2011.5.25.187.1.24
        hwPtpGrandMasterClockPriority2 OBJECT-TYPE
            SYNTAX Integer32 (0..255)
            MAX-ACCESS read-only
            STATUS current
            DESCRIPTION
                "PTP GrandMaster clock priority2 attribute."
            ::= { hwPtpGlobalObjects 24 }

        
        -- 1.3.6.1.4.1.2011.5.25.187.1.25
        hwPtpGrandMasterClockAccuracy OBJECT-TYPE
            SYNTAX Integer32 (0..255)
            MAX-ACCESS read-only
            STATUS current
            DESCRIPTION
                "PTP GrandMaster clock accuracy attribute."
            ::= { hwPtpGlobalObjects 25 }

        
        -- 1.3.6.1.4.1.2011.5.25.187.1.26
        hwPtpGrandMasterClockClass OBJECT-TYPE
            SYNTAX Integer32 (1..255)
            MAX-ACCESS read-only
            STATUS current
            DESCRIPTION
                "PTP GrandMaster clock class attribute."
            ::= { hwPtpGlobalObjects 26 }

        
        -- 1.3.6.1.4.1.2011.5.25.187.1.27
        hwPtpGrandMasterClockTimeSource OBJECT-TYPE
            SYNTAX INTEGER
                {
                atomicclock(1),
                gps(2),
                terrestrialradio(3),
                ptp(4),
                ntp(5),
                handset(6),
                other(7),
                internaloscillator(8)
                }
            MAX-ACCESS read-only
            STATUS current
            DESCRIPTION
                "PTP GrandMaster clock timesource attribute."
            ::= { hwPtpGlobalObjects 27 }

        
        -- 1.3.6.1.4.1.2011.5.25.187.1.28
        hwPtpTimeSyncTime OBJECT-TYPE
            SYNTAX INTEGER
                {
                on(1),
                off(2)
                }
            MAX-ACCESS read-write
            STATUS current
            DESCRIPTION
                "Indicates PTP time is synchronization or not."
            ::= { hwPtpGlobalObjects 28 }

        
        -- 1.3.6.1.4.1.2011.5.25.187.1.29
        hwPtpFrequencyRecoverMode OBJECT-TYPE
            SYNTAX INTEGER
                {
                packetRecover(1),
                phyRecover(2)
                }
            MAX-ACCESS read-write
            STATUS current
            DESCRIPTION
                "The recover mode of  PTP."
            ::= { hwPtpGlobalObjects 29 }

        
        -- 1.3.6.1.4.1.2011.5.25.187.1.30
        hwPtpAclEnable OBJECT-TYPE
            SYNTAX EnabledStatus
            MAX-ACCESS read-write
            STATUS current
            DESCRIPTION
                "Enable PTP acl function."
            ::= { hwPtpGlobalObjects 30 }

        
        -- 1.3.6.1.4.1.2011.5.25.187.1.31
        hwPtpSetPortStateEnable OBJECT-TYPE
            SYNTAX EnabledStatus
            MAX-ACCESS read-write
            STATUS current
            DESCRIPTION
                "Enable PTP set port state function."
            ::= { hwPtpGlobalObjects 31 }

        
        -- 1.3.6.1.4.1.2011.5.25.187.1.32
        hwPtpCurrentMasterClockId OBJECT-TYPE
            SYNTAX OCTET STRING
            MAX-ACCESS read-only
            STATUS current
            DESCRIPTION
                "Current grandmaster clockId."
            ::= { hwPtpGlobalObjects 32 }

        
        -- 1.3.6.1.4.1.2011.5.25.187.1.33
        hwPtpBits1ppsReceiveDelay OBJECT-TYPE
            SYNTAX Integer32 (0..2000000)
            MAX-ACCESS read-write
            STATUS current
            DESCRIPTION
                "Bits1ppsReceiveDelay."
            ::= { hwPtpGlobalObjects 33 }

        
        -- 1.3.6.1.4.1.2011.5.25.187.1.34
        hwPtpBits1ppsSendDelay OBJECT-TYPE
            SYNTAX Integer32 (0..1600)
            MAX-ACCESS read-write
            STATUS current
            DESCRIPTION
                "Bits1ppsSendDelay."
            ::= { hwPtpGlobalObjects 34 }

        
        -- 1.3.6.1.4.1.2011.5.25.187.1.35
        hwPtpBitsDclsReceiveDelay OBJECT-TYPE
            SYNTAX Integer32 (0..2000000)
            MAX-ACCESS read-write
            STATUS current
            DESCRIPTION
                "BitsDclsReceiveDelay."
            ::= { hwPtpGlobalObjects 35 }

        
        -- 1.3.6.1.4.1.2011.5.25.187.1.36
        hwPtpBitsDclsSendDelay OBJECT-TYPE
            SYNTAX Integer32 (0..1600)
            MAX-ACCESS read-write
            STATUS current
            DESCRIPTION
                "BitsDclsSendDelay."
            ::= { hwPtpGlobalObjects 36 }

        
        -- 1.3.6.1.4.1.2011.5.25.187.1.37
        hwPtpAdaptiveEnable OBJECT-TYPE
            SYNTAX EnabledStatus
            MAX-ACCESS read-write
            STATUS current
            DESCRIPTION
                "Enable ptp adaptive function."
            ::= { hwPtpGlobalObjects 37 }

        
        -- 1.3.6.1.4.1.2011.5.25.187.1.38
        hwPtpAdaptiveUserMode OBJECT-TYPE
            SYNTAX INTEGER
                {
                primaryserver(1),
                standbyserver(2),
                client(3),
                server(4),
                invalid(99)
                }
            MAX-ACCESS read-write
            STATUS current
            DESCRIPTION
                "Ptp adaptive set user mode attribute."
            ::= { hwPtpGlobalObjects 38 }

        
        -- 1.3.6.1.4.1.2011.5.25.187.1.39
        hwPtpAdaptiveUserState OBJECT-TYPE
            SYNTAX INTEGER
                {
                master(1),
                slave(2),
                invalid(99)
                }
            MAX-ACCESS read-only
            STATUS current
            DESCRIPTION
                "Ptp adaptive user state."
            ::= { hwPtpGlobalObjects 39 }

        
        -- 1.3.6.1.4.1.2011.5.25.187.1.40
        hwPtpAdaptiveSyncMode OBJECT-TYPE
            SYNTAX INTEGER
                {
                atr(1),
                acr(2),
                invalid(99)
                }
            MAX-ACCESS read-write
            STATUS current
            DESCRIPTION
                "Ptp adaptive sysc mode."
            ::= { hwPtpGlobalObjects 40 }

        
        -- 1.3.6.1.4.1.2011.5.25.187.1.41
        hwPtpAdaptiveDscp OBJECT-TYPE
            SYNTAX Integer32 (0..63)
            MAX-ACCESS read-write
            STATUS current
            DESCRIPTION
                "Ptp adaptive UdpEgress Dscp."
            ::= { hwPtpGlobalObjects 41 }

        
        -- 1.3.6.1.4.1.2011.5.25.187.1.42
        hwPtpAdaptiveDomain OBJECT-TYPE
            SYNTAX Integer32 (0..255)
            MAX-ACCESS read-write
            STATUS current
            DESCRIPTION
                "Ptp adaptive device's domain attribute,this attribute is used by ptp adaptive device to join BMC compute."
            ::= { hwPtpGlobalObjects 42 }

        
        -- 1.3.6.1.4.1.2011.5.25.187.1.43
        hwPtpAdaptiveLocalIp OBJECT-TYPE
            SYNTAX IpAddress
            MAX-ACCESS read-write
            STATUS current
            DESCRIPTION
                "Ptp adaptive device's local ip attribute."
            ::= { hwPtpGlobalObjects 43 }

        
        -- 1.3.6.1.4.1.2011.5.25.187.1.44
        hwPtpAdaptiveAnnounceInterval OBJECT-TYPE
            SYNTAX Integer32 (7..14)
            MAX-ACCESS read-write
            STATUS current
            DESCRIPTION
                "Client device's requested send interval of announce packet."
            ::= { hwPtpGlobalObjects 44 }

        
        -- 1.3.6.1.4.1.2011.5.25.187.1.45
        hwPtpAdaptiveSyncInterval OBJECT-TYPE
            SYNTAX Integer32 (3..14)
            MAX-ACCESS read-write
            STATUS current
            DESCRIPTION
                "Client device's requested send interval of sync packet."
            ::= { hwPtpGlobalObjects 45 }

        
        -- 1.3.6.1.4.1.2011.5.25.187.1.46
        hwPtpAdaptiveDlyReqInterval OBJECT-TYPE
            SYNTAX Integer32 (3..14)
            MAX-ACCESS read-write
            STATUS current
            DESCRIPTION
                "Client device's requested send interval of delay_req packet."
            ::= { hwPtpGlobalObjects 46 }

        
        -- 1.3.6.1.4.1.2011.5.25.187.1.47
        hwPtpAdaptiveAnnounceRecepitTimeout OBJECT-TYPE
            SYNTAX Integer32 (4 | 8 | 16 | 32 | 64 | 128 | 256)
            MAX-ACCESS read-write
            STATUS current
            DESCRIPTION
                "Ptp adaptive device's announce receipt timeout attribute."
            ::= { hwPtpGlobalObjects 47 }

        
        -- 1.3.6.1.4.1.2011.5.25.187.1.48
        hwPtpAdaptiveRemoteServer1Ip OBJECT-TYPE
            SYNTAX IpAddress
            MAX-ACCESS read-write
            STATUS current
            DESCRIPTION
                "Ptp adaptive device's remote server1 ip attribute."
            ::= { hwPtpGlobalObjects 48 }

        
        -- 1.3.6.1.4.1.2011.5.25.187.1.49
        hwPtpAdaptiveRemoteServer1KeepAliveEnable OBJECT-TYPE
            SYNTAX INTEGER
                {
                enable(1),
                disable(2),
                invalid(99)
                }
            MAX-ACCESS read-write
            STATUS current
            DESCRIPTION
                "Ptp adaptive device's remote server1 keepalive attribute."
            ::= { hwPtpGlobalObjects 49 }

        
        -- 1.3.6.1.4.1.2011.5.25.187.1.50
        hwPtpAdaptiveRemoteServer1NegoState OBJECT-TYPE
            SYNTAX INTEGER
                {
                init(0),
                success(1),
                error(2),
                none(3)
                }
            MAX-ACCESS read-only
            STATUS current
            DESCRIPTION
                "Ptp adaptive device's remote server1 negotiate state."
            ::= { hwPtpGlobalObjects 50 }

        
        -- 1.3.6.1.4.1.2011.5.25.187.1.51
        hwPtpAdaptiveRemoteServer2Ip OBJECT-TYPE
            SYNTAX IpAddress
            MAX-ACCESS read-write
            STATUS current
            DESCRIPTION
                "Ptp adaptive device's remote server2 ip attribute."
            ::= { hwPtpGlobalObjects 51 }

        
        -- 1.3.6.1.4.1.2011.5.25.187.1.52
        hwPtpAdaptiveRemoteServer2KeepAliveEnable OBJECT-TYPE
            SYNTAX INTEGER
                {
                enable(1),
                disable(2),
                invalid(99)
                }
            MAX-ACCESS read-write
            STATUS current
            DESCRIPTION
                "Ptp adaptive device's remote server2 keepalive attribute."
            ::= { hwPtpGlobalObjects 52 }

        
        -- 1.3.6.1.4.1.2011.5.25.187.1.53
        hwPtpAdaptiveRemoteServer2NegoState OBJECT-TYPE
            SYNTAX INTEGER
                {
                init(0),
                success(1),
                error(2),
                none(3)
                }
            MAX-ACCESS read-only
            STATUS current
            DESCRIPTION
                "Ptp adaptive device's remote server2 negotiate state."
            ::= { hwPtpGlobalObjects 53 }

        
        -- 1.3.6.1.4.1.2011.5.25.187.1.54
        hwPtpAdaptiveVpnInstance OBJECT-TYPE
            SYNTAX OCTET STRING
            MAX-ACCESS read-write
            STATUS current
            DESCRIPTION
                "Ptp adaptive device's vpn instance."
            ::= { hwPtpGlobalObjects 54 }

        
        -- 1.3.6.1.4.1.2011.5.25.187.1.55
        hwPtpAdaptiveClientIpChangeFlag OBJECT-TYPE
            SYNTAX INTEGER
                {
                added(0),
                deleted(1)
                }
            MAX-ACCESS read-only
            STATUS current
            DESCRIPTION
                "Indicates the master's client ip list change state, added or deleted."
            ::= { hwPtpGlobalObjects 55 }

        
        -- 1.3.6.1.4.1.2011.5.25.187.1.56
        hwPtpAdaptiveAnnounceDuration OBJECT-TYPE
            SYNTAX Integer32 (60..1000)
            UNITS "s"
            MAX-ACCESS read-write
            STATUS current
            DESCRIPTION
                "Ptp adaptive device's announce packet duration attribute."
            ::= { hwPtpGlobalObjects 56 }

        
        -- 1.3.6.1.4.1.2011.5.25.187.1.57
        hwPtpAdaptiveSyncDuration OBJECT-TYPE
            SYNTAX Integer32 (60..1000)
            UNITS "s"
            MAX-ACCESS read-write
            STATUS current
            DESCRIPTION
                "Ptp adaptive device's sync packet duration attribute."
            ::= { hwPtpGlobalObjects 57 }

        
        -- 1.3.6.1.4.1.2011.5.25.187.1.58
        hwPtpAdaptiveDelayRespDuration OBJECT-TYPE
            SYNTAX Integer32 (60..1000)
            UNITS "s"
            MAX-ACCESS read-write
            STATUS current
            DESCRIPTION
                "Ptp adaptive device's delay-resp packet duration attribute."
            ::= { hwPtpGlobalObjects 58 }

        
        -- 1.3.6.1.4.1.2011.5.25.187.1.59
        hwPtpDfxDlyMeasureEnable OBJECT-TYPE
            SYNTAX EnabledStatus
            MAX-ACCESS read-write
            STATUS current
            DESCRIPTION
                "Enable delay-measure function."
            ::= { hwPtpGlobalObjects 59 }

        
        -- 1.3.6.1.4.1.2011.5.25.187.1.60
        hwPtpDfxPhyPhaseSubCur OBJECT-TYPE
            SYNTAX Integer32
            UNITS "ns"
            MAX-ACCESS read-only
            STATUS current
            DESCRIPTION
                "Physics frequences synchronization offset current value."
            ::= { hwPtpGlobalObjects 60 }

        
        -- 1.3.6.1.4.1.2011.5.25.187.1.61
        hwPtpDfxPhyPhaseSubMin OBJECT-TYPE
            SYNTAX Integer32
            UNITS "ns"
            MAX-ACCESS read-only
            STATUS current
            DESCRIPTION
                "Physics frequences synchronization offset min value."
            ::= { hwPtpGlobalObjects 61 }

        
        -- 1.3.6.1.4.1.2011.5.25.187.1.62
        hwPtpDfxPhyPhaseSubMax OBJECT-TYPE
            SYNTAX Integer32
            UNITS "ns"
            MAX-ACCESS read-only
            STATUS current
            DESCRIPTION
                "Physics frequences synchronization offset max value."
            ::= { hwPtpGlobalObjects 62 }

        
        -- 1.3.6.1.4.1.2011.5.25.187.1.63
        hwPtpDfxPhyPhaseSubMean OBJECT-TYPE
            SYNTAX Integer32
            UNITS "ns"
            MAX-ACCESS read-only
            STATUS current
            DESCRIPTION
                "Physics frequences synchronization offset mean value."
            ::= { hwPtpGlobalObjects 63 }

        
        -- 1.3.6.1.4.1.2011.5.25.187.1.64
        hwPtpDfxFreqOffsetCur OBJECT-TYPE
            SYNTAX Integer32
            UNITS "ns"
            MAX-ACCESS read-only
            STATUS current
            DESCRIPTION
                "1588V2 frequency synchronization offset current value."
            ::= { hwPtpGlobalObjects 64 }

        
        -- 1.3.6.1.4.1.2011.5.25.187.1.65
        hwPtpDfxFreqOffsetMin OBJECT-TYPE
            SYNTAX Integer32
            UNITS "ns"
            MAX-ACCESS read-only
            STATUS current
            DESCRIPTION
                "1588V2 frequency synchronization offset min value."
            ::= { hwPtpGlobalObjects 65 }

        
        -- 1.3.6.1.4.1.2011.5.25.187.1.66
        hwPtpDfxFreqOffsetMax OBJECT-TYPE
            SYNTAX Integer32
            UNITS "ns"
            MAX-ACCESS read-only
            STATUS current
            DESCRIPTION
                "1588V2 frequency synchronization offset max value."
            ::= { hwPtpGlobalObjects 66 }

        
        -- 1.3.6.1.4.1.2011.5.25.187.1.67
        hwPtpDfxFreqOffsetMean OBJECT-TYPE
            SYNTAX Integer32
            UNITS "ns"
            MAX-ACCESS read-only
            STATUS current
            DESCRIPTION
                "1588V2 frequency synchronization offset mean value."
            ::= { hwPtpGlobalObjects 67 }

        
        -- 1.3.6.1.4.1.2011.5.25.187.1.68
        hwPtpDfxACRMaxPdCur OBJECT-TYPE
            SYNTAX Integer32
            UNITS "ms"
            MAX-ACCESS read-only
            STATUS current
            DESCRIPTION
                "1588 ACR frequency synchronization max path delay current value."
            ::= { hwPtpGlobalObjects 68 }

        
        -- 1.3.6.1.4.1.2011.5.25.187.1.69
        hwPtpDfxACRMaxPdMin OBJECT-TYPE
            SYNTAX Integer32
            UNITS "ms"
            MAX-ACCESS read-only
            STATUS current
            DESCRIPTION
                "1588 ACR frequency synchronization max path delay min value."
            ::= { hwPtpGlobalObjects 69 }

        
        -- 1.3.6.1.4.1.2011.5.25.187.1.70
        hwPtpDfxACRMaxPdMax OBJECT-TYPE
            SYNTAX Integer32
            UNITS "ms"
            MAX-ACCESS read-only
            STATUS current
            DESCRIPTION
                "1588 ACR frequency synchronization max path delay max value."
            ::= { hwPtpGlobalObjects 70 }

        
        -- 1.3.6.1.4.1.2011.5.25.187.1.71
        hwPtpDfxACRMaxPdMean OBJECT-TYPE
            SYNTAX Integer32
            UNITS "ms"
            MAX-ACCESS read-only
            STATUS current
            DESCRIPTION
                "1588 ACR frequency synchronization max path delay mean value."
            ::= { hwPtpGlobalObjects 71 }

        
        -- 1.3.6.1.4.1.2011.5.25.187.1.72
        hwPtpDfxACRMinPdCur OBJECT-TYPE
            SYNTAX Integer32
            UNITS "ms"
            MAX-ACCESS read-only
            STATUS current
            DESCRIPTION
                "1588 ACR frequency synchronization min path delay current value."
            ::= { hwPtpGlobalObjects 72 }

        
        -- 1.3.6.1.4.1.2011.5.25.187.1.73
        hwPtpDfxACRMinPdMin OBJECT-TYPE
            SYNTAX Integer32
            UNITS "ms"
            MAX-ACCESS read-only
            STATUS current
            DESCRIPTION
                "1588 ACR frequency synchronization min path delay min value."
            ::= { hwPtpGlobalObjects 73 }

        
        -- 1.3.6.1.4.1.2011.5.25.187.1.74
        hwPtpDfxACRMinPdMax OBJECT-TYPE
            SYNTAX Integer32
            UNITS "ms"
            MAX-ACCESS read-only
            STATUS current
            DESCRIPTION
                "1588 ACR frequency synchronization min path delay max value."
            ::= { hwPtpGlobalObjects 74 }

        
        -- 1.3.6.1.4.1.2011.5.25.187.1.75
        hwPtpDfxACRMinPdMean OBJECT-TYPE
            SYNTAX Integer32
            UNITS "ms"
            MAX-ACCESS read-only
            STATUS current
            DESCRIPTION
                "1588 ACR frequency synchronization min path delay mean value."
            ::= { hwPtpGlobalObjects 75 }

        
        -- 1.3.6.1.4.1.2011.5.25.187.1.76
        hwPtpDfxTimeSyncOffsetCur OBJECT-TYPE
            SYNTAX Integer32
            UNITS "ns"
            MAX-ACCESS read-only
            STATUS current
            DESCRIPTION
                "1588V2 time synchronization offset current value."
            ::= { hwPtpGlobalObjects 76 }

        
        -- 1.3.6.1.4.1.2011.5.25.187.1.77
        hwPtpDfxTimeSyncOffsetMin OBJECT-TYPE
            SYNTAX Integer32
            UNITS "ns"
            MAX-ACCESS read-only
            STATUS current
            DESCRIPTION
                "1588V2 time synchronization offset min value."
            ::= { hwPtpGlobalObjects 77 }

        
        -- 1.3.6.1.4.1.2011.5.25.187.1.78
        hwPtpDfxTimeSyncOffsetMax OBJECT-TYPE
            SYNTAX Integer32
            UNITS "ns"
            MAX-ACCESS read-only
            STATUS current
            DESCRIPTION
                "1588V2 time synchronization offset max value."
            ::= { hwPtpGlobalObjects 78 }

        
        -- 1.3.6.1.4.1.2011.5.25.187.1.79
        hwPtpDfxTimeSyncOffsetMean OBJECT-TYPE
            SYNTAX Integer32
            UNITS "ns"
            MAX-ACCESS read-only
            STATUS current
            DESCRIPTION
                "1588V2 time synchronization offset mean value."
            ::= { hwPtpGlobalObjects 79 }

        
        -- 1.3.6.1.4.1.2011.5.25.187.1.80
        hwPtpDfxTimeSyncMPDlyCur OBJECT-TYPE
            SYNTAX Integer32
            UNITS "ns"
            MAX-ACCESS read-only
            STATUS current
            DESCRIPTION
                "1588V2 time synchronization mean path delay current value."
            ::= { hwPtpGlobalObjects 80 }

        
        -- 1.3.6.1.4.1.2011.5.25.187.1.81
        hwPtpDfxTimeSyncMPDlyMin OBJECT-TYPE
            SYNTAX Integer32
            UNITS "ns"
            MAX-ACCESS read-only
            STATUS current
            DESCRIPTION
                "1588V2 time synchronization mean path delay min value."
            ::= { hwPtpGlobalObjects 81 }

        
        -- 1.3.6.1.4.1.2011.5.25.187.1.82
        hwPtpDfxTimeSyncMPDlyMax OBJECT-TYPE
            SYNTAX Integer32
            UNITS "ns"
            MAX-ACCESS read-only
            STATUS current
            DESCRIPTION
                "1588V2 time synchronization mean path delay max value."
            ::= { hwPtpGlobalObjects 82 }

        
        -- 1.3.6.1.4.1.2011.5.25.187.1.83
        hwPtpDfxTimeSyncMPDlyMean OBJECT-TYPE
            SYNTAX Integer32
            UNITS "ns"
            MAX-ACCESS read-only
            STATUS current
            DESCRIPTION
                "1588V2 time synchronization mean path delay mean value."
            ::= { hwPtpGlobalObjects 83 }

        
        -- 1.3.6.1.4.1.2011.5.25.187.1.84
        hwPtpDfxFreqSyncMode OBJECT-TYPE
            SYNTAX INTEGER
                {
                none(0),
                phyfreq(1),
                ptpfreq(2),
                ptpacrfreq(3)
                }
            MAX-ACCESS read-only
            STATUS current
            DESCRIPTION
                "Current frequence synchronization mode."
            ::= { hwPtpGlobalObjects 84 }

        
        -- 1.3.6.1.4.1.2011.5.25.187.1.85
        hwPtpDfxTimeSyncMode OBJECT-TYPE
            SYNTAX INTEGER
                {
                none(0),
                ptp(1),
                ptpatr(2)
                }
            MAX-ACCESS read-only
            STATUS current
            DESCRIPTION
                "Current time synchronization mode."
            ::= { hwPtpGlobalObjects 85 }

        
        -- 1.3.6.1.4.1.2011.5.25.187.1.86
        hwPtpTimeLockStatus OBJECT-TYPE
            SYNTAX INTEGER
                {
                unlock(0),
                lock(1)
                }
            MAX-ACCESS read-only
            STATUS current
            DESCRIPTION
                "Describe current the time lock status."
            ::= { hwPtpGlobalObjects 86 }

        
        -- 1.3.6.1.4.1.2011.5.25.187.1.87
        hwPtpTimeStampStatus OBJECT-TYPE
            SYNTAX INTEGER
                {
                abnormal(0),
                normal(1)
                }
            MAX-ACCESS read-only
            STATUS current
            DESCRIPTION
                "Describe the time stamp changing status."
            ::= { hwPtpGlobalObjects 87 }

        
        -- 1.3.6.1.4.1.2011.5.25.187.1.88
        hwPtpFreqLockStatus OBJECT-TYPE
            SYNTAX INTEGER
                {
                unlock(0),
                lock(1)
                }
            MAX-ACCESS read-only
            STATUS current
            DESCRIPTION
                "Describe current the frequency lock status."
            ::= { hwPtpGlobalObjects 88 }

        
        -- 1.3.6.1.4.1.2011.5.25.187.1.89
        hwPtpExtTimePortStatus OBJECT-TYPE
            SYNTAX INTEGER
                {
                normal(0),
                portDown(1),
                todSecUnChange(2),
                todSecpulseInvalid(3)
                }
            MAX-ACCESS read-only
            STATUS current
            DESCRIPTION
                "Description."
            ::= { hwPtpGlobalObjects 89 }

        
        -- 1.3.6.1.4.1.2011.5.25.187.1.90
        hwPtpExtTimePortType OBJECT-TYPE
            SYNTAX INTEGER
                {
                bits0(0),
                bits1(1),
                bits2(2),
                bits3(3)
                }
            MAX-ACCESS read-only
            STATUS current
            DESCRIPTION
                "Description."
            ::= { hwPtpGlobalObjects 90 }

        
        -- 1.3.6.1.4.1.2011.5.25.187.2
        hwPtpPortObjects OBJECT IDENTIFIER ::= { hwPtpMIB 2 }

        
        -- 1.3.6.1.4.1.2011.5.25.187.2.1
        hwPtpPortTable OBJECT-TYPE
            SYNTAX SEQUENCE OF HwPtpPortEntry
            MAX-ACCESS not-accessible
            STATUS current
            DESCRIPTION
                "PtpPortTable."
            ::= { hwPtpPortObjects 1 }

        
        -- 1.3.6.1.4.1.2011.5.25.187.2.1.1
        hwPtpPortEntry OBJECT-TYPE
            SYNTAX HwPtpPortEntry
            MAX-ACCESS not-accessible
            STATUS current
            DESCRIPTION
                "An entry in hwPtpPortTable."
            INDEX { hwPtpPortIfIndex }
            ::= { hwPtpPortTable 1 }

        
        HwPtpPortEntry ::=
            SEQUENCE { 
                hwPtpPortIfIndex
                    InterfaceIndex,
                hwPtpPortEnable
                    EnabledStatus,
                hwPtpPortDelayMechanism
                    INTEGER,
                hwPtpPortType
                    INTEGER,
                hwPtpPortDomain
                    Integer32,
                hwPtpPortTcOcStaticClockId
                    OCTET STRING,
                hwPtpPortTcOcStaticClockPortNum
                    Integer32,
                hwPtpPortTcOcStaticClockSlot
                    Integer32,
                hwPtpPortTcOcStaticClockCard
                    Integer32,
                hwPtpPortTcOcStaticClockPort
                    Integer32,
                hwPtpPortAnnounceInterval
                    Integer32,
                hwPtpPortAnnounceReceipTimeout
                    Integer32,
                hwPtpPortSyncInterval
                    Integer32,
                hwPtpPortMinDelayReqInterval
                    Integer32,
                hwPtpPortMinPdelayReqInterval
                    Integer32,
                hwPtpPortAsymmetryNegativeCorrection
                    Unsigned32,
                hwPtpPortAsymmetryPositiveCorrection
                    Unsigned32,
                hwPtpPortMacEgressDestinationMac
                    MacAddress,
                hwPtpPortMacEgressVlanId
                    VlanIdOrNone,
                hwPtpPortMacEgressPacketPriority
                    Integer32,
                hwPtpPortUdpEgressSourceIp
                    IpAddress,
                hwPtpPortUdpEgressDestinationIp
                    IpAddress,
                hwPtpPortUdpEgressDestinationMac
                    MacAddress,
                hwPtpPortUdpEgressDscp
                    Integer32,
                hwPtpPortUdpEgressVlanId
                    VlanIdOrNone,
                hwPtpPortUdpEgressPacketPriority
                    Integer32,
                hwPtpPortAnnounceDrop
                    EnabledStatus,
                hwPtpOldPortState
                    INTEGER,
                hwPtpPortSourcePortClockId
                    OCTET STRING,
                hwPtpPortSourcePortNum
                    Integer32,
                hwPtpPortSourcePortSlot
                    Integer32,
                hwPtpPortSourcePortCard
                    Integer32,
                hwPtpPortSourcePort
                    Integer32,
                hwPtpPortNumber
                    Integer32,
                hwPtpPortPortVlan
                    Integer32,
                hwPtpPortCfgLinkStatus
                    INTEGER,
                hwPtpPortCfgExtInterfaceMode
                    INTEGER,
                hwPtpPortCfgMsgFormat
                    INTEGER,
                hwPtpPortAnnounceReceipTimeout2
                    Integer32,
                hwPtpPortClockStep
                    INTEGER,
                hwPtpPortState
                    INTEGER,
                hwPtpPeerAnnounceSendInterval
                    Integer32,
                hwPtpPortName
                    OCTET STRING,
                hwPtpPortCfgState
                    INTEGER,
                hwPtpPortRingFiberLengthChangeValue
                    Integer32,
                hwPtpPortRingFiberLengthChangeValueFlag
                    INTEGER,
                hwPtpPortOldSourcePortNum
                    Integer32,
                hwPtpOldPortName
                    OCTET STRING,
                hwPtpPortRowStatus
                    RowStatus
             }

        -- 1.3.6.1.4.1.2011.5.25.187.2.1.1.1
        hwPtpPortIfIndex OBJECT-TYPE
            SYNTAX InterfaceIndex
            MAX-ACCESS not-accessible
            STATUS current
            DESCRIPTION
                "Port ifIndex."
            ::= { hwPtpPortEntry 1 }

        
        -- 1.3.6.1.4.1.2011.5.25.187.2.1.1.2
        hwPtpPortEnable OBJECT-TYPE
            SYNTAX EnabledStatus
            MAX-ACCESS read-create
            STATUS current
            DESCRIPTION
                "The port enable PTP function."
            ::= { hwPtpPortEntry 2 }

        
        -- 1.3.6.1.4.1.2011.5.25.187.2.1.1.3
        hwPtpPortDelayMechanism OBJECT-TYPE
            SYNTAX INTEGER
                {
                none(1),
                delay(2),
                pdelay(3)
                }
            MAX-ACCESS read-create
            STATUS current
            DESCRIPTION
                "The port delay mechanism."
            ::= { hwPtpPortEntry 3 }

        
        -- 1.3.6.1.4.1.2011.5.25.187.2.1.1.4
        hwPtpPortType OBJECT-TYPE
            SYNTAX INTEGER
                {
                none(1),
                tc(2),
                bc(3),
                tcoc(4),
                oc(5)
                }
            MAX-ACCESS read-create
            STATUS current
            DESCRIPTION
                "This port is tc type or bc type,only used in the PTP device type is tcandbc."
            ::= { hwPtpPortEntry 4 }

        
        -- 1.3.6.1.4.1.2011.5.25.187.2.1.1.5
        hwPtpPortDomain OBJECT-TYPE
            SYNTAX Integer32 (0..255)
            MAX-ACCESS read-create
            STATUS current
            DESCRIPTION
                "This port's domain,only used in the PTP device type is tcandbc."
            ::= { hwPtpPortEntry 5 }

        
        -- 1.3.6.1.4.1.2011.5.25.187.2.1.1.6
        hwPtpPortTcOcStaticClockId OBJECT-TYPE
            SYNTAX OCTET STRING
            MAX-ACCESS read-create
            STATUS current
            DESCRIPTION
                "TcOc device sourceport clockId."
            ::= { hwPtpPortEntry 6 }

        
        -- 1.3.6.1.4.1.2011.5.25.187.2.1.1.7
        hwPtpPortTcOcStaticClockPortNum OBJECT-TYPE
            SYNTAX Integer32 (0..65535)
            MAX-ACCESS read-create
            STATUS current
            DESCRIPTION
                "TcOc device sourceport number."
            ::= { hwPtpPortEntry 7 }

        
        -- 1.3.6.1.4.1.2011.5.25.187.2.1.1.8
        hwPtpPortTcOcStaticClockSlot OBJECT-TYPE
            SYNTAX Integer32
            MAX-ACCESS read-create
            STATUS current
            DESCRIPTION
                "TcOc device portnumber slot."
            ::= { hwPtpPortEntry 8 }

        
        -- 1.3.6.1.4.1.2011.5.25.187.2.1.1.9
        hwPtpPortTcOcStaticClockCard OBJECT-TYPE
            SYNTAX Integer32
            MAX-ACCESS read-create
            STATUS current
            DESCRIPTION
                "TcOc device portnumber card."
            ::= { hwPtpPortEntry 9 }

        
        -- 1.3.6.1.4.1.2011.5.25.187.2.1.1.10
        hwPtpPortTcOcStaticClockPort OBJECT-TYPE
            SYNTAX Integer32
            MAX-ACCESS read-create
            STATUS current
            DESCRIPTION
                "TcOc device portnumber port."
            ::= { hwPtpPortEntry 10 }

        
        -- 1.3.6.1.4.1.2011.5.25.187.2.1.1.11
        hwPtpPortAnnounceInterval OBJECT-TYPE
            SYNTAX Integer32 (0..20)
            MAX-ACCESS read-create
            STATUS current
            DESCRIPTION
                "Interval of sending announce message."
            ::= { hwPtpPortEntry 11 }

        
        -- 1.3.6.1.4.1.2011.5.25.187.2.1.1.12
        hwPtpPortAnnounceReceipTimeout OBJECT-TYPE
            SYNTAX Integer32 (0..20)
            MAX-ACCESS read-create
            STATUS current
            DESCRIPTION
                "Timeout of receiving announce message."
            ::= { hwPtpPortEntry 12 }

        
        -- 1.3.6.1.4.1.2011.5.25.187.2.1.1.13
        hwPtpPortSyncInterval OBJECT-TYPE
            SYNTAX Integer32 (0..20)
            MAX-ACCESS read-create
            STATUS current
            DESCRIPTION
                "Interval of sending sync message."
            ::= { hwPtpPortEntry 13 }

        
        -- 1.3.6.1.4.1.2011.5.25.187.2.1.1.14
        hwPtpPortMinDelayReqInterval OBJECT-TYPE
            SYNTAX Integer32 (0..20)
            MAX-ACCESS read-create
            STATUS current
            DESCRIPTION
                "Interval of sending DelayReq message."
            ::= { hwPtpPortEntry 14 }

        
        -- 1.3.6.1.4.1.2011.5.25.187.2.1.1.15
        hwPtpPortMinPdelayReqInterval OBJECT-TYPE
            SYNTAX Integer32 (0..20)
            MAX-ACCESS read-create
            STATUS current
            DESCRIPTION
                "Interval of sending PdelayReq message."
            ::= { hwPtpPortEntry 15 }

        
        -- 1.3.6.1.4.1.2011.5.25.187.2.1.1.16
        hwPtpPortAsymmetryNegativeCorrection OBJECT-TYPE
            SYNTAX Unsigned32 (0..2000000)
            MAX-ACCESS read-create
            STATUS current
            DESCRIPTION
                "Negtive asymmetry-correction value"
            ::= { hwPtpPortEntry 16 }

        
        -- 1.3.6.1.4.1.2011.5.25.187.2.1.1.17
        hwPtpPortAsymmetryPositiveCorrection OBJECT-TYPE
            SYNTAX Unsigned32 (0..2000000)
            MAX-ACCESS read-create
            STATUS current
            DESCRIPTION
                "Positive asymmetry-correction value"
            ::= { hwPtpPortEntry 17 }

        
        -- 1.3.6.1.4.1.2011.5.25.187.2.1.1.18
        hwPtpPortMacEgressDestinationMac OBJECT-TYPE
            SYNTAX MacAddress
            MAX-ACCESS read-create
            STATUS current
            DESCRIPTION
                "MacEgress destination Mac."
            ::= { hwPtpPortEntry 18 }

        
        -- 1.3.6.1.4.1.2011.5.25.187.2.1.1.19
        hwPtpPortMacEgressVlanId OBJECT-TYPE
            SYNTAX VlanIdOrNone
            MAX-ACCESS read-create
            STATUS current
            DESCRIPTION
                "MacEgress VlanId."
            ::= { hwPtpPortEntry 19 }

        
        -- 1.3.6.1.4.1.2011.5.25.187.2.1.1.20
        hwPtpPortMacEgressPacketPriority OBJECT-TYPE
            SYNTAX Integer32 (0..7)
            MAX-ACCESS read-create
            STATUS current
            DESCRIPTION
                "MacEgress Packet Priority."
            ::= { hwPtpPortEntry 20 }

        
        -- 1.3.6.1.4.1.2011.5.25.187.2.1.1.21
        hwPtpPortUdpEgressSourceIp OBJECT-TYPE
            SYNTAX IpAddress
            MAX-ACCESS read-create
            STATUS current
            DESCRIPTION
                "UdpEgress SourceIp."
            ::= { hwPtpPortEntry 21 }

        
        -- 1.3.6.1.4.1.2011.5.25.187.2.1.1.22
        hwPtpPortUdpEgressDestinationIp OBJECT-TYPE
            SYNTAX IpAddress
            MAX-ACCESS read-create
            STATUS current
            DESCRIPTION
                "UdpEgress DestinationIp."
            ::= { hwPtpPortEntry 22 }

        
        -- 1.3.6.1.4.1.2011.5.25.187.2.1.1.23
        hwPtpPortUdpEgressDestinationMac OBJECT-TYPE
            SYNTAX MacAddress
            MAX-ACCESS read-create
            STATUS current
            DESCRIPTION
                "UdpEgress Destination Mac."
            ::= { hwPtpPortEntry 23 }

        
        -- 1.3.6.1.4.1.2011.5.25.187.2.1.1.24
        hwPtpPortUdpEgressDscp OBJECT-TYPE
            SYNTAX Integer32 (0..63)
            MAX-ACCESS read-create
            STATUS current
            DESCRIPTION
                "UdpEgress Dscp."
            ::= { hwPtpPortEntry 24 }

        
        -- 1.3.6.1.4.1.2011.5.25.187.2.1.1.25
        hwPtpPortUdpEgressVlanId OBJECT-TYPE
            SYNTAX VlanIdOrNone
            MAX-ACCESS read-create
            STATUS current
            DESCRIPTION
                "UdpEgress VlanId."
            ::= { hwPtpPortEntry 25 }

        
        -- 1.3.6.1.4.1.2011.5.25.187.2.1.1.26
        hwPtpPortUdpEgressPacketPriority OBJECT-TYPE
            SYNTAX Integer32 (0..7)
            MAX-ACCESS read-create
            STATUS current
            DESCRIPTION
                "UdpEgress Packet Priority."
            ::= { hwPtpPortEntry 26 }

        
        -- 1.3.6.1.4.1.2011.5.25.187.2.1.1.27
        hwPtpPortAnnounceDrop OBJECT-TYPE
            SYNTAX EnabledStatus
            MAX-ACCESS read-create
            STATUS current
            DESCRIPTION
                "Enable AnnounceDrop function."
            ::= { hwPtpPortEntry 27 }

        
        -- 1.3.6.1.4.1.2011.5.25.187.2.1.1.28
        hwPtpOldPortState OBJECT-TYPE
            SYNTAX INTEGER
                {
                master(1),
                slave(2),
                passive(3),
                listening(4),
                faulty(5),
                initializing(6),
                premaster(7),
                disabled(8),
                uncalibrated(9)
                }
            MAX-ACCESS read-only
            STATUS current
            DESCRIPTION
                "Old port state."
            ::= { hwPtpPortEntry 28 }

        
        -- 1.3.6.1.4.1.2011.5.25.187.2.1.1.29
        hwPtpPortSourcePortClockId OBJECT-TYPE
            SYNTAX OCTET STRING
            MAX-ACCESS read-only
            STATUS current
            DESCRIPTION
                "Indicates sourceportclockid of the port."
            ::= { hwPtpPortEntry 29 }

        
        -- 1.3.6.1.4.1.2011.5.25.187.2.1.1.30
        hwPtpPortSourcePortNum OBJECT-TYPE
            SYNTAX Integer32 (0..65535)
            MAX-ACCESS read-only
            STATUS current
            DESCRIPTION
                "Indicates sourceport number of the port."
            ::= { hwPtpPortEntry 30 }

        
        -- 1.3.6.1.4.1.2011.5.25.187.2.1.1.31
        hwPtpPortSourcePortSlot OBJECT-TYPE
            SYNTAX Integer32
            MAX-ACCESS read-only
            STATUS current
            DESCRIPTION
                "Indicates sourceport slot of the port."
            ::= { hwPtpPortEntry 31 }

        
        -- 1.3.6.1.4.1.2011.5.25.187.2.1.1.32
        hwPtpPortSourcePortCard OBJECT-TYPE
            SYNTAX Integer32
            MAX-ACCESS read-only
            STATUS current
            DESCRIPTION
                "Indicates sourceport card of the port."
            ::= { hwPtpPortEntry 32 }

        
        -- 1.3.6.1.4.1.2011.5.25.187.2.1.1.33
        hwPtpPortSourcePort OBJECT-TYPE
            SYNTAX Integer32
            MAX-ACCESS read-only
            STATUS current
            DESCRIPTION
                "Indicates sourceport port of the port."
            ::= { hwPtpPortEntry 33 }

        
        -- 1.3.6.1.4.1.2011.5.25.187.2.1.1.34
        hwPtpPortNumber OBJECT-TYPE
            SYNTAX Integer32
            MAX-ACCESS read-only
            STATUS current
            DESCRIPTION
                "Port number."
            ::= { hwPtpPortEntry 34 }

        
        -- 1.3.6.1.4.1.2011.5.25.187.2.1.1.35
        hwPtpPortPortVlan OBJECT-TYPE
            SYNTAX Integer32
            MAX-ACCESS read-create
            STATUS current
            DESCRIPTION
                "The VLAN of packet sent from port."
            ::= { hwPtpPortEntry 35 }

        
        -- 1.3.6.1.4.1.2011.5.25.187.2.1.1.36
        hwPtpPortCfgLinkStatus OBJECT-TYPE
            SYNTAX INTEGER
                {
                down(0),
                up(1)
                }
            MAX-ACCESS read-create
            STATUS current
            DESCRIPTION
                "The link status of port."
            ::= { hwPtpPortEntry 36 }

        
        -- 1.3.6.1.4.1.2011.5.25.187.2.1.1.37
        hwPtpPortCfgExtInterfaceMode OBJECT-TYPE
            SYNTAX INTEGER
                {
                extclock(1),
                exttime(2)
                }
            MAX-ACCESS read-create
            STATUS current
            DESCRIPTION
                "The mode of interface."
            ::= { hwPtpPortEntry 37 }

        
        -- 1.3.6.1.4.1.2011.5.25.187.2.1.1.38
        hwPtpPortCfgMsgFormat OBJECT-TYPE
            SYNTAX INTEGER
                {
                ptpeth(1),
                ptpip(2)
                }
            MAX-ACCESS read-create
            STATUS current
            DESCRIPTION
                "The format of massage."
            ::= { hwPtpPortEntry 38 }

        
        -- 1.3.6.1.4.1.2011.5.25.187.2.1.1.39
        hwPtpPortAnnounceReceipTimeout2 OBJECT-TYPE
            SYNTAX Integer32 (0..20)
            MAX-ACCESS read-create
            STATUS current
            DESCRIPTION
                "Timeout of receiving announce message."
            ::= { hwPtpPortEntry 39 }

        
        -- 1.3.6.1.4.1.2011.5.25.187.2.1.1.40
        hwPtpPortClockStep OBJECT-TYPE
            SYNTAX INTEGER
                {
                onestep(1),
                twostep(2)
                }
            MAX-ACCESS read-create
            STATUS current
            DESCRIPTION
                "Port clock step."
            ::= { hwPtpPortEntry 40 }

        
        -- 1.3.6.1.4.1.2011.5.25.187.2.1.1.41
        hwPtpPortState OBJECT-TYPE
            SYNTAX INTEGER
                {
                master(1),
                slave(2),
                passive(3),
                listening(4),
                faulty(5),
                initializing(6),
                premaster(7),
                disabled(8),
                uncalibrated(9)
                }
            MAX-ACCESS read-only
            STATUS current
            DESCRIPTION
                "Current port state."
            ::= { hwPtpPortEntry 41 }

        
        -- 1.3.6.1.4.1.2011.5.25.187.2.1.1.42
        hwPtpPeerAnnounceSendInterval OBJECT-TYPE
            SYNTAX Integer32 (0..20)
            MAX-ACCESS read-only
            STATUS current
            DESCRIPTION
                "peer announce send interval."
            ::= { hwPtpPortEntry 42 }

        
        -- 1.3.6.1.4.1.2011.5.25.187.2.1.1.43
        hwPtpPortName OBJECT-TYPE
            SYNTAX OCTET STRING
            MAX-ACCESS read-only
            STATUS current
            DESCRIPTION
                "Port name."
            ::= { hwPtpPortEntry 43 }

        
        -- 1.3.6.1.4.1.2011.5.25.187.2.1.1.44
        hwPtpPortCfgState OBJECT-TYPE
            SYNTAX INTEGER
                {
                master(1),
                slave(2),
                passive(3),
                listening(4),
                faulty(5),
                initializing(6),
                premaster(7),
                disabled(8),
                uncalibrated(9)
                }
            MAX-ACCESS read-create
            STATUS current
            DESCRIPTION
                "Cfg port state value."
            ::= { hwPtpPortEntry 44 }

        
        -- 1.3.6.1.4.1.2011.5.25.187.2.1.1.45
        hwPtpPortRingFiberLengthChangeValue OBJECT-TYPE
            SYNTAX Integer32
            UNITS "ns"
            MAX-ACCESS read-only
            STATUS current
            DESCRIPTION
                "ring fiber length change value."
            ::= { hwPtpPortEntry 45 }

        
        -- 1.3.6.1.4.1.2011.5.25.187.2.1.1.46
        hwPtpPortRingFiberLengthChangeValueFlag OBJECT-TYPE
            SYNTAX INTEGER
                {
                negative(0),
                positive(1)
                }
            MAX-ACCESS read-only
            STATUS current
            DESCRIPTION
                "ring fiber length change value flag."
            ::= { hwPtpPortEntry 46 }

        
        -- 1.3.6.1.4.1.2011.5.25.187.2.1.1.47
        hwPtpPortOldSourcePortNum OBJECT-TYPE
            SYNTAX Integer32
            MAX-ACCESS read-only
            STATUS current
            DESCRIPTION
                "Description."
            ::= { hwPtpPortEntry 47 }

        
        -- 1.3.6.1.4.1.2011.5.25.187.2.1.1.48
        hwPtpOldPortName OBJECT-TYPE
            SYNTAX OCTET STRING
            MAX-ACCESS read-only
            STATUS current
            DESCRIPTION
                "Description."
            ::= { hwPtpPortEntry 48 }

        
        -- 1.3.6.1.4.1.2011.5.25.187.2.1.1.100
        hwPtpPortRowStatus OBJECT-TYPE
            SYNTAX RowStatus
            MAX-ACCESS read-create
            STATUS current
            DESCRIPTION
                "The row status."
            ::= { hwPtpPortEntry 100 }

        
        -- 1.3.6.1.4.1.2011.5.25.187.2.2
        hwPtpPortStatisticTable OBJECT-TYPE
            SYNTAX SEQUENCE OF HwPtpPortStatisticEntry
            MAX-ACCESS not-accessible
            STATUS current
            DESCRIPTION
                "PortStatisticTable."
            ::= { hwPtpPortObjects 2 }

        
        -- 1.3.6.1.4.1.2011.5.25.187.2.2.1
        hwPtpPortStatisticEntry OBJECT-TYPE
            SYNTAX HwPtpPortStatisticEntry
            MAX-ACCESS not-accessible
            STATUS current
            DESCRIPTION
                "PortStatisticEntry."
            INDEX { hwPtpPortStatisticIfIndex }
            ::= { hwPtpPortStatisticTable 1 }

        
        HwPtpPortStatisticEntry ::=
            SEQUENCE { 
                hwPtpPortStatisticIfIndex
                    InterfaceIndex,
                hwPtpPortRecvTransparent
                    Unsigned32,
                hwPtpPortRecvCorrectend
                    Unsigned32,
                hwPtpPortRecvAnnounce
                    Unsigned32,
                hwPtpPortRecvSync
                    Unsigned32,
                hwPtpPortRecvReq
                    Unsigned32,
                hwPtpPortRecvRespCnt
                    Unsigned32,
                hwPtpPortRecvFollowup
                    Unsigned32,
                hwPtpPortRecvPdelayrespfollowup
                    Unsigned32,
                hwPtpPortSendTotal1588
                    Unsigned32,
                hwPtpPortSendAnnounce
                    Unsigned32,
                hwPtpPortSendSync
                    Unsigned32,
                hwPtpPortSendReq
                    Unsigned32,
                hwPtpPortSendResp
                    Unsigned32,
                hwPtpPortSendFollowup
                    Unsigned32,
                hwPtpPortSendPdelayrespfollowup
                    Unsigned32,
                hwPtpPortDiscardTotal1588
                    Unsigned32,
                hwPtpPortDiscardAnnounce
                    Unsigned32,
                hwPtpPortDiscardSync
                    Unsigned32,
                hwPtpPortDiscardDelayreq
                    Unsigned32,
                hwPtpPortDiscardPdelayreq
                    Unsigned32,
                hwPtpPortDiscardResp
                    Unsigned32,
                hwPtpPortDiscardPdelayresp
                    Unsigned32,
                hwPtpPortDiscardFollowup
                    Unsigned32,
                hwPtpPortDiscardPdelayrespfollowup
                    Unsigned32,
                hwPtpPortStaticPktReset
                    INTEGER
             }

        -- 1.3.6.1.4.1.2011.5.25.187.2.2.1.1
        hwPtpPortStatisticIfIndex OBJECT-TYPE
            SYNTAX InterfaceIndex
            MAX-ACCESS not-accessible
            STATUS current
            DESCRIPTION
                "The PortStatisticIfIndex."
            ::= { hwPtpPortStatisticEntry 1 }

        
        -- 1.3.6.1.4.1.2011.5.25.187.2.2.1.2
        hwPtpPortRecvTransparent OBJECT-TYPE
            SYNTAX Unsigned32
            MAX-ACCESS read-only
            STATUS current
            DESCRIPTION
                "The number of the PTP packets Transparent in this port."
            ::= { hwPtpPortStatisticEntry 2 }

        
        -- 1.3.6.1.4.1.2011.5.25.187.2.2.1.3
        hwPtpPortRecvCorrectend OBJECT-TYPE
            SYNTAX Unsigned32
            MAX-ACCESS read-only
            STATUS current
            DESCRIPTION
                "The number of the PTP packets Correct_end in this port."
            ::= { hwPtpPortStatisticEntry 3 }

        
        -- 1.3.6.1.4.1.2011.5.25.187.2.2.1.4
        hwPtpPortRecvAnnounce OBJECT-TYPE
            SYNTAX Unsigned32
            MAX-ACCESS read-only
            STATUS current
            DESCRIPTION
                "The number of the PTP packets Announce in this port."
            ::= { hwPtpPortStatisticEntry 4 }

        
        -- 1.3.6.1.4.1.2011.5.25.187.2.2.1.5
        hwPtpPortRecvSync OBJECT-TYPE
            SYNTAX Unsigned32
            MAX-ACCESS read-only
            STATUS current
            DESCRIPTION
                "The number of the PTP packets Sync in this port."
            ::= { hwPtpPortStatisticEntry 5 }

        
        -- 1.3.6.1.4.1.2011.5.25.187.2.2.1.6
        hwPtpPortRecvReq OBJECT-TYPE
            SYNTAX Unsigned32
            MAX-ACCESS read-only
            STATUS current
            DESCRIPTION
                "The number of the packets Req in this port."
            ::= { hwPtpPortStatisticEntry 6 }

        
        -- 1.3.6.1.4.1.2011.5.25.187.2.2.1.7
        hwPtpPortRecvRespCnt OBJECT-TYPE
            SYNTAX Unsigned32
            MAX-ACCESS read-only
            STATUS current
            DESCRIPTION
                "The number of the Resp packets in this port."
            ::= { hwPtpPortStatisticEntry 7 }

        
        -- 1.3.6.1.4.1.2011.5.25.187.2.2.1.8
        hwPtpPortRecvFollowup OBJECT-TYPE
            SYNTAX Unsigned32
            MAX-ACCESS read-only
            STATUS current
            DESCRIPTION
                "The number of the PTP Followup packets in this port."
            ::= { hwPtpPortStatisticEntry 8 }

        
        -- 1.3.6.1.4.1.2011.5.25.187.2.2.1.9
        hwPtpPortRecvPdelayrespfollowup OBJECT-TYPE
            SYNTAX Unsigned32
            MAX-ACCESS read-only
            STATUS current
            DESCRIPTION
                "The number of Pdelay_resp_followup in this port ."
            ::= { hwPtpPortStatisticEntry 9 }

        
        -- 1.3.6.1.4.1.2011.5.25.187.2.2.1.10
        hwPtpPortSendTotal1588 OBJECT-TYPE
            SYNTAX Unsigned32
            MAX-ACCESS read-only
            STATUS current
            DESCRIPTION
                "The number of SendTotal1588 in this port."
            ::= { hwPtpPortStatisticEntry 10 }

        
        -- 1.3.6.1.4.1.2011.5.25.187.2.2.1.11
        hwPtpPortSendAnnounce OBJECT-TYPE
            SYNTAX Unsigned32
            MAX-ACCESS read-only
            STATUS current
            DESCRIPTION
                "The number of the SendAnnounce in this port."
            ::= { hwPtpPortStatisticEntry 11 }

        
        -- 1.3.6.1.4.1.2011.5.25.187.2.2.1.12
        hwPtpPortSendSync OBJECT-TYPE
            SYNTAX Unsigned32
            MAX-ACCESS read-only
            STATUS current
            DESCRIPTION
                "The number of the SendSync in this port."
            ::= { hwPtpPortStatisticEntry 12 }

        
        -- 1.3.6.1.4.1.2011.5.25.187.2.2.1.13
        hwPtpPortSendReq OBJECT-TYPE
            SYNTAX Unsigned32
            MAX-ACCESS read-only
            STATUS current
            DESCRIPTION
                "The number of the SendReq in this port."
            ::= { hwPtpPortStatisticEntry 13 }

        
        -- 1.3.6.1.4.1.2011.5.25.187.2.2.1.14
        hwPtpPortSendResp OBJECT-TYPE
            SYNTAX Unsigned32
            MAX-ACCESS read-only
            STATUS current
            DESCRIPTION
                "The number of SendResp in this port."
            ::= { hwPtpPortStatisticEntry 14 }

        
        -- 1.3.6.1.4.1.2011.5.25.187.2.2.1.15
        hwPtpPortSendFollowup OBJECT-TYPE
            SYNTAX Unsigned32
            MAX-ACCESS read-only
            STATUS current
            DESCRIPTION
                "The number of SendFollowup in this port."
            ::= { hwPtpPortStatisticEntry 15 }

        
        -- 1.3.6.1.4.1.2011.5.25.187.2.2.1.16
        hwPtpPortSendPdelayrespfollowup OBJECT-TYPE
            SYNTAX Unsigned32
            MAX-ACCESS read-only
            STATUS current
            DESCRIPTION
                "The number of SendPdelay_resp_followup in this port."
            ::= { hwPtpPortStatisticEntry 16 }

        
        -- 1.3.6.1.4.1.2011.5.25.187.2.2.1.17
        hwPtpPortDiscardTotal1588 OBJECT-TYPE
            SYNTAX Unsigned32
            MAX-ACCESS read-only
            STATUS current
            DESCRIPTION
                "The number of the DiscardTotal1588 in this port."
            ::= { hwPtpPortStatisticEntry 17 }

        
        -- 1.3.6.1.4.1.2011.5.25.187.2.2.1.18
        hwPtpPortDiscardAnnounce OBJECT-TYPE
            SYNTAX Unsigned32
            MAX-ACCESS read-only
            STATUS current
            DESCRIPTION
                "The number of DiscardAnnounce in this port."
            ::= { hwPtpPortStatisticEntry 18 }

        
        -- 1.3.6.1.4.1.2011.5.25.187.2.2.1.19
        hwPtpPortDiscardSync OBJECT-TYPE
            SYNTAX Unsigned32
            MAX-ACCESS read-only
            STATUS current
            DESCRIPTION
                "The number of DiscardSync in this port."
            ::= { hwPtpPortStatisticEntry 19 }

        
        -- 1.3.6.1.4.1.2011.5.25.187.2.2.1.20
        hwPtpPortDiscardDelayreq OBJECT-TYPE
            SYNTAX Unsigned32
            MAX-ACCESS read-only
            STATUS current
            DESCRIPTION
                "The number of DiscardDelayreq in this port."
            ::= { hwPtpPortStatisticEntry 20 }

        
        -- 1.3.6.1.4.1.2011.5.25.187.2.2.1.21
        hwPtpPortDiscardPdelayreq OBJECT-TYPE
            SYNTAX Unsigned32
            MAX-ACCESS read-only
            STATUS current
            DESCRIPTION
                "The number of DiscardPdelayreq in this port."
            ::= { hwPtpPortStatisticEntry 21 }

        
        -- 1.3.6.1.4.1.2011.5.25.187.2.2.1.22
        hwPtpPortDiscardResp OBJECT-TYPE
            SYNTAX Unsigned32
            MAX-ACCESS read-only
            STATUS current
            DESCRIPTION
                "The number of DiscardResp in this port."
            ::= { hwPtpPortStatisticEntry 22 }

        
        -- 1.3.6.1.4.1.2011.5.25.187.2.2.1.23
        hwPtpPortDiscardPdelayresp OBJECT-TYPE
            SYNTAX Unsigned32
            MAX-ACCESS read-only
            STATUS current
            DESCRIPTION
                "The number of DiscardPdelayresp in this port."
            ::= { hwPtpPortStatisticEntry 23 }

        
        -- 1.3.6.1.4.1.2011.5.25.187.2.2.1.24
        hwPtpPortDiscardFollowup OBJECT-TYPE
            SYNTAX Unsigned32
            MAX-ACCESS read-only
            STATUS current
            DESCRIPTION
                "The number of DiscardFollowup in this port."
            ::= { hwPtpPortStatisticEntry 24 }

        
        -- 1.3.6.1.4.1.2011.5.25.187.2.2.1.25
        hwPtpPortDiscardPdelayrespfollowup OBJECT-TYPE
            SYNTAX Unsigned32
            MAX-ACCESS read-only
            STATUS current
            DESCRIPTION
                "The number of the DiscardPdelay_resp_followup in this port."
            ::= { hwPtpPortStatisticEntry 25 }

        
        -- 1.3.6.1.4.1.2011.5.25.187.2.2.1.26
        hwPtpPortStaticPktReset OBJECT-TYPE
            SYNTAX INTEGER
                {
                reset(1),
                unused(2)
                }
            MAX-ACCESS read-write
            STATUS current
            DESCRIPTION
                "Reset port PTP packets statistic."
            ::= { hwPtpPortStatisticEntry 26 }

        
        -- 1.3.6.1.4.1.2011.5.25.187.2.3
        hwPtpBitsClockSourceTable OBJECT-TYPE
            SYNTAX SEQUENCE OF HwPtpBitsClockSourceEntry
            MAX-ACCESS not-accessible
            STATUS current
            DESCRIPTION
                "BitsClockSourceTable."
            ::= { hwPtpPortObjects 3 }

        
        -- 1.3.6.1.4.1.2011.5.25.187.2.3.1
        hwPtpBitsClockSourceEntry OBJECT-TYPE
            SYNTAX HwPtpBitsClockSourceEntry
            MAX-ACCESS not-accessible
            STATUS current
            DESCRIPTION
                "An entry in hwPtpPortStatisticTable."
            INDEX { hwPtpBitsPortIndex }
            ::= { hwPtpBitsClockSourceTable 1 }

        
        HwPtpBitsClockSourceEntry ::=
            SEQUENCE { 
                hwPtpBitsPortIndex
                    Integer32,
                hwPtpBitsClockAccuracy
                    Integer32,
                hwPtpBitsClockClass
                    Integer32,
                hwPtpBitsPriority1
                    Integer32,
                hwPtpBitsPriority2
                    Integer32,
                hwPtpBitsTimeSource
                    INTEGER,
                hwPtpBitsSignal
                    INTEGER,
                hwPtpBitsSwitch
                    INTEGER,
                hwPtpBitsDirection
                    INTEGER,
                hwPtpBitsNormalStatus
                    INTEGER
             }

        -- 1.3.6.1.4.1.2011.5.25.187.2.3.1.1
        hwPtpBitsPortIndex OBJECT-TYPE
            SYNTAX Integer32 (1..10)
            MAX-ACCESS not-accessible
            STATUS current
            DESCRIPTION
                "The BitsPortIndex."
            ::= { hwPtpBitsClockSourceEntry 1 }

        
        -- 1.3.6.1.4.1.2011.5.25.187.2.3.1.2
        hwPtpBitsClockAccuracy OBJECT-TYPE
            SYNTAX Integer32 (0..255)
            MAX-ACCESS read-write
            STATUS current
            DESCRIPTION
                "BitsClockAccuracy."
            ::= { hwPtpBitsClockSourceEntry 2 }

        
        -- 1.3.6.1.4.1.2011.5.25.187.2.3.1.3
        hwPtpBitsClockClass OBJECT-TYPE
            SYNTAX Integer32 (1..255)
            MAX-ACCESS read-write
            STATUS current
            DESCRIPTION
                "BitsClockClass."
            ::= { hwPtpBitsClockSourceEntry 3 }

        
        -- 1.3.6.1.4.1.2011.5.25.187.2.3.1.4
        hwPtpBitsPriority1 OBJECT-TYPE
            SYNTAX Integer32 (0..255)
            MAX-ACCESS read-write
            STATUS current
            DESCRIPTION
                "BitsPriority1."
            ::= { hwPtpBitsClockSourceEntry 4 }

        
        -- 1.3.6.1.4.1.2011.5.25.187.2.3.1.5
        hwPtpBitsPriority2 OBJECT-TYPE
            SYNTAX Integer32 (0..255)
            MAX-ACCESS read-write
            STATUS current
            DESCRIPTION
                "BitsPriority2."
            ::= { hwPtpBitsClockSourceEntry 5 }

        
        -- 1.3.6.1.4.1.2011.5.25.187.2.3.1.6
        hwPtpBitsTimeSource OBJECT-TYPE
            SYNTAX INTEGER
                {
                atomicclock(1),
                gps(2),
                terrestrialradio(3),
                ptp(4),
                ntp(5),
                handset(6),
                other(7),
                internaloscillator(8)
                }
            MAX-ACCESS read-write
            STATUS current
            DESCRIPTION
                "BitsTimeSource."
            ::= { hwPtpBitsClockSourceEntry 6 }

        
        -- 1.3.6.1.4.1.2011.5.25.187.2.3.1.7
        hwPtpBitsSignal OBJECT-TYPE
            SYNTAX INTEGER
                {
                onepps(1),
                twomhz(2),
                twombps(3),
                dcls(4),
                none(5)
                }
            MAX-ACCESS read-only
            STATUS current
            DESCRIPTION
                "The signal of BITS."
            ::= { hwPtpBitsClockSourceEntry 7 }

        
        -- 1.3.6.1.4.1.2011.5.25.187.2.3.1.8
        hwPtpBitsSwitch OBJECT-TYPE
            SYNTAX INTEGER
                {
                off(1),
                on(2)
                }
            MAX-ACCESS read-write
            STATUS current
            DESCRIPTION
                "The switch status."
            ::= { hwPtpBitsClockSourceEntry 8 }

        
        -- 1.3.6.1.4.1.2011.5.25.187.2.3.1.9
        hwPtpBitsDirection OBJECT-TYPE
            SYNTAX INTEGER
                {
                in(1),
                out(2),
                both(3),
                none(4)
                }
            MAX-ACCESS read-only
            STATUS current
            DESCRIPTION
                "The direction of BITS."
            ::= { hwPtpBitsClockSourceEntry 9 }

        
        -- 1.3.6.1.4.1.2011.5.25.187.2.3.1.10
        hwPtpBitsNormalStatus OBJECT-TYPE
            SYNTAX INTEGER
                {
                normal(1),
                abnormal(2)
                }
            MAX-ACCESS read-only
            STATUS current
            DESCRIPTION
                "The normal status of BITS."
            ::= { hwPtpBitsClockSourceEntry 10 }

        
        -- 1.3.6.1.4.1.2011.5.25.187.3
        hwPtpLeapObjects OBJECT IDENTIFIER ::= { hwPtpMIB 3 }

        
        -- 1.3.6.1.4.1.2011.5.25.187.3.1
        hwPtpLeapTable OBJECT-TYPE
            SYNTAX SEQUENCE OF HwPtpLeapEntry
            MAX-ACCESS not-accessible
            STATUS current
            DESCRIPTION
                "Ptp Leap Table."
            ::= { hwPtpLeapObjects 1 }

        
        -- 1.3.6.1.4.1.2011.5.25.187.3.1.1
        hwPtpLeapEntry OBJECT-TYPE
            SYNTAX HwPtpLeapEntry
            MAX-ACCESS not-accessible
            STATUS current
            DESCRIPTION
                "PtpLeapEntry."
            INDEX { hwPtpLeapInfo }
            ::= { hwPtpLeapTable 1 }

        
        HwPtpLeapEntry ::=
            SEQUENCE { 
                hwPtpLeapInfo
                    OCTET STRING,
                hwPtpLeap59or61
                    INTEGER,
                hwPtpLeapRowStatus
                    RowStatus
             }

        -- 1.3.6.1.4.1.2011.5.25.187.3.1.1.1
        hwPtpLeapInfo OBJECT-TYPE
            SYNTAX OCTET STRING
            MAX-ACCESS not-accessible
            STATUS current
            DESCRIPTION
                "leap59 or leap61 adjust time."
            ::= { hwPtpLeapEntry 1 }

        
        -- 1.3.6.1.4.1.2011.5.25.187.3.1.1.2
        hwPtpLeap59or61 OBJECT-TYPE
            SYNTAX INTEGER
                {
                leap59(1),
                leap61(2),
                none(3)
                }
            MAX-ACCESS read-create
            STATUS current
            DESCRIPTION
                "leap59 or leap61,default is none. "
            ::= { hwPtpLeapEntry 2 }

        
        -- 1.3.6.1.4.1.2011.5.25.187.3.1.1.3
        hwPtpLeapRowStatus OBJECT-TYPE
            SYNTAX RowStatus
            MAX-ACCESS read-create
            STATUS current
            DESCRIPTION
                "leap table rowstatus."
            ::= { hwPtpLeapEntry 3 }

        
        -- 1.3.6.1.4.1.2011.5.25.187.4
        hwPtpAclPermitClkIdObjects OBJECT IDENTIFIER ::= { hwPtpMIB 4 }

        
        -- 1.3.6.1.4.1.2011.5.25.187.4.1
        hwPtpAclPermitClkIdTable OBJECT-TYPE
            SYNTAX SEQUENCE OF HwPtpAclPermitClkIdEntry
            MAX-ACCESS not-accessible
            STATUS current
            DESCRIPTION
                "PtpAclPermitClkIdTable."
            ::= { hwPtpAclPermitClkIdObjects 1 }

        
        -- 1.3.6.1.4.1.2011.5.25.187.4.1.1
        hwPtpAclPermitClkIdEntry OBJECT-TYPE
            SYNTAX HwPtpAclPermitClkIdEntry
            MAX-ACCESS not-accessible
            STATUS current
            DESCRIPTION
                "PtpAclPermitClkIdEntry."
            INDEX { hwPtpAclPermitClkIdInfo }
            ::= { hwPtpAclPermitClkIdTable 1 }

        
        HwPtpAclPermitClkIdEntry ::=
            SEQUENCE { 
                hwPtpAclPermitClkIdInfo
                    OCTET STRING,
                hwPtpAclPermitClkIdRowStatus
                    RowStatus
             }

        -- 1.3.6.1.4.1.2011.5.25.187.4.1.1.1
        hwPtpAclPermitClkIdInfo OBJECT-TYPE
            SYNTAX OCTET STRING
            MAX-ACCESS not-accessible
            STATUS current
            DESCRIPTION
                "permit join BMC's clockID"
            ::= { hwPtpAclPermitClkIdEntry 1 }

        
        -- 1.3.6.1.4.1.2011.5.25.187.4.1.1.2
        hwPtpAclPermitClkIdRowStatus OBJECT-TYPE
            SYNTAX RowStatus
            MAX-ACCESS read-create
            STATUS current
            DESCRIPTION
                "aclclockid's rowstatus."
            ::= { hwPtpAclPermitClkIdEntry 2 }

        
        -- 1.3.6.1.4.1.2011.5.25.187.5
        hwPtpNotifications OBJECT IDENTIFIER ::= { hwPtpMIB 5 }

        
        -- 1.3.6.1.4.1.2011.5.25.187.5.1
        hwPtpPortStateChange NOTIFICATION-TYPE
            OBJECTS { hwPtpPortName, hwPtpPortState, hwPtpOldPortState }
            STATUS current
            DESCRIPTION 
                "Port status change notification."
            ::= { hwPtpNotifications 1 }

        
        -- 1.3.6.1.4.1.2011.5.25.187.5.2
        hwPtpClockSourceChange NOTIFICATION-TYPE
            OBJECTS { hwPtpOldMasterClockId, hwPtpCurrentMasterClockId, hwPtpPortOldSourcePortNum, hwPtpPortSourcePortNum, hwPtpOldPortName, 
                hwPtpPortName }
            STATUS current
            DESCRIPTION 
                "Clock source change notification."
            ::= { hwPtpNotifications 2 }

        
        -- 1.3.6.1.4.1.2011.5.25.187.5.3
        hwPtpTimeSyncFaulty NOTIFICATION-TYPE
            OBJECTS { hwPtpTimeSynchronizationStatus }
            STATUS current
            DESCRIPTION 
                "This is a private node,for time synchronization status is faulty."
            ::= { hwPtpNotifications 3 }

        
        -- 1.3.6.1.4.1.2011.5.25.187.5.4
        hwPtpTimeSyncResume NOTIFICATION-TYPE
            OBJECTS { hwPtpTimeSynchronizationStatus }
            STATUS current
            DESCRIPTION 
                "This is a private node,for time synchronization status is resume."
            ::= { hwPtpNotifications 4 }

        
        -- 1.3.6.1.4.1.2011.5.25.187.5.9
        hwPtpAdaptiveClientListChange NOTIFICATION-TYPE
            OBJECTS { hwPtpAdaptiveClientIpList, hwPtpAdaptiveClientIpChangeFlag }
            STATUS current
            DESCRIPTION 
                "Indicates the master's client ip list"
            ::= { hwPtpNotifications 9 }

        
        -- 1.3.6.1.4.1.2011.5.25.187.5.10
        hwPtpAdaptiveNegoStateChange NOTIFICATION-TYPE
            OBJECTS { hwPtpAdaptiveRemoteServer1NegoState, hwPtpAdaptiveRemoteServer2NegoState }
            STATUS current
            DESCRIPTION 
                "Indicates the client device's negotiate state with remote-server."
            ::= { hwPtpNotifications 10 }

        
        -- 1.3.6.1.4.1.2011.5.25.187.5.11
        hwPTPRingFiberLengthChange NOTIFICATION-TYPE
            OBJECTS { hwPtpPortName, hwPtpPortRingFiberLengthChangeValue, hwPtpPortRingFiberLengthChangeValueFlag }
            STATUS current
            DESCRIPTION 
                "Ring fiber length value change notification."
            ::= { hwPtpNotifications 11 }

        
        -- 1.3.6.1.4.1.2011.5.25.187.5.12
        hwPTPRingFiberLengthChangeResume NOTIFICATION-TYPE
            OBJECTS { hwPtpPortName, hwPtpPortRingFiberLengthChangeValue, hwPtpPortRingFiberLengthChangeValueFlag }
            STATUS current
            DESCRIPTION 
                "Ring fiber length value change resume notification."
            ::= { hwPtpNotifications 12 }

        
        -- 1.3.6.1.4.1.2011.5.25.187.5.13
        hwPtpTimeLockFail NOTIFICATION-TYPE
            OBJECTS { hwPtpTimeLockStatus }
            STATUS current
            DESCRIPTION 
                "Current time synchronization lock failed."
            ::= { hwPtpNotifications 13 }

        
        -- 1.3.6.1.4.1.2011.5.25.187.5.14
        hwPtpTimeLockFailResume NOTIFICATION-TYPE
            OBJECTS { hwPtpTimeLockStatus }
            STATUS current
            DESCRIPTION 
                "Current time synchronization lock resumed."
            ::= { hwPtpNotifications 14 }

        
        -- 1.3.6.1.4.1.2011.5.25.187.5.15
        hwPtpTimeStampUnChanged NOTIFICATION-TYPE
            OBJECTS { hwPtpTimeStampStatus }
            STATUS current
            DESCRIPTION 
                "Current time stamp in the sync-message isn't changed."
            ::= { hwPtpNotifications 15 }

        
        -- 1.3.6.1.4.1.2011.5.25.187.5.16
        hwPtpTimeStampUnChangedResume NOTIFICATION-TYPE
            OBJECTS { hwPtpTimeStampStatus }
            STATUS current
            DESCRIPTION 
                "Current time stamp in the sync-message is changed."
            ::= { hwPtpNotifications 16 }

        
        -- 1.3.6.1.4.1.2011.5.25.187.5.17
        hwPtpFrequencyLockFail NOTIFICATION-TYPE
            OBJECTS { hwPtpFreqLockStatus }
            STATUS current
            DESCRIPTION 
                "Current frequency synchronization lock failed."
            ::= { hwPtpNotifications 17 }

        
        -- 1.3.6.1.4.1.2011.5.25.187.5.18
        hwPtpFrequencyLockResume NOTIFICATION-TYPE
            OBJECTS { hwPtpFreqLockStatus }
            STATUS current
            DESCRIPTION 
                "Current frequency synchronization lock resumed."
            ::= { hwPtpNotifications 18 }

        
        -- 1.3.6.1.4.1.2011.5.25.187.5.19
        hwPtpExtTimePortLost NOTIFICATION-TYPE
            OBJECTS { hwPtpExtTimePortStatus, hwPtpExtTimePortType }
            STATUS current
            DESCRIPTION 
                "External time port lost."
            ::= { hwPtpNotifications 19 }

        
        -- 1.3.6.1.4.1.2011.5.25.187.5.20
        hwPtpExtTimePortLostResume NOTIFICATION-TYPE
            OBJECTS { hwPtpExtTimePortStatus, hwPtpExtTimePortType }
            STATUS current
            DESCRIPTION 
                "External time port lost resume."
            ::= { hwPtpNotifications 20 }

        
        -- 1.3.6.1.4.1.2011.5.25.187.5.21
        hwPtpPdvOverflow NOTIFICATION-TYPE
            STATUS current
            DESCRIPTION 
                "Packet delay variety overflow."
            ::= { hwPtpNotifications 21 }

        
        -- 1.3.6.1.4.1.2011.5.25.187.5.22
        hwPtpPdvOverflowResume NOTIFICATION-TYPE
            STATUS current
            DESCRIPTION 
                "Packet delay variety overflow resume."
            ::= { hwPtpNotifications 22 }

        
        -- 1.3.6.1.4.1.2011.5.25.187.6
        hwPtpConformance OBJECT IDENTIFIER ::= { hwPtpMIB 6 }

        
        -- 1.3.6.1.4.1.2011.5.25.187.6.1
        hwPtpCompliance OBJECT IDENTIFIER ::= { hwPtpConformance 1 }

        
        -- 1.3.6.1.4.1.2011.5.25.187.6.1.1
        hwPtpComliance MODULE-COMPLIANCE
            STATUS current
            DESCRIPTION 
                "This is the PTP module compliance."
            MODULE -- this module
                MANDATORY-GROUPS { hwPtpGlobalObjectsGroup, hwPtpPortObjectsGroup, hwPtpNotificationsGroup, hwPtpLeapObjectsGroup, hwPtpAclPermitClkIdObjectsGroup
                     }
            ::= { hwPtpCompliance 1 }

        
        -- 1.3.6.1.4.1.2011.5.25.187.6.2
        hwPtpGroups OBJECT IDENTIFIER ::= { hwPtpConformance 2 }

        
        -- 1.3.6.1.4.1.2011.5.25.187.6.2.1
        hwPtpGlobalObjectsGroup OBJECT-GROUP
            OBJECTS { hwPtpEnable, hwPtpDomain, hwPtpSlaveOnly, hwPtpDeviceType, hwPtpLocalClockId, 
                hwPtpLocalClockClass, hwPtpLocalClockAccuracy, hwPtpLocalClockPriority1, hwPtpLocalClockPriority2, hwPtpLocalClockTimeSource, 
                hwPtpUtc, hwPtpCurrentUtcOffset, hwPtpCurrentMasterClockId, hwPtpCurrentMasterClockReceivePort, hwPtpCurrentMasterClockStepRemoved, 
                hwPtpTimeSynchronizationStatus, hwPtpTimeTraceable, hwPtpTimeScale, hwPtpVersion, hwPtpFrequencyRecoverMode, 
                hwPtpTimeSyncTime, hwPtpGrandMasterClockTimeSource, hwPtpGrandMasterClockClass, hwPtpGrandMasterClockAccuracy, hwPtpGrandMasterClockPriority2, 
                hwPtpGrandMasterClockPriority1, hwPtpCurrentMasterClockReceivePortType, hwPtpBitsDclsSendDelay, hwPtpBitsDclsReceiveDelay, hwPtpBits1ppsSendDelay, 
                hwPtpBits1ppsReceiveDelay, hwPtpOldMasterClockId, hwCurrentUtcOffsetValid, hwPtpFrequencyTraceable, hwPtpAclEnable, 
                hwPtpSetPortStateEnable }
            STATUS current
            DESCRIPTION 
                "This is the hwPtpGlobalObjectsGroups."
            ::= { hwPtpGroups 1 }

        
        -- 1.3.6.1.4.1.2011.5.25.187.6.2.2
        hwPtpPortObjectsGroup OBJECT-GROUP
            OBJECTS { hwPtpPortEnable, hwPtpPortDelayMechanism, hwPtpPortDomain, hwPtpPortTcOcStaticClockId, hwPtpPortAnnounceInterval, 
                hwPtpPortAnnounceReceipTimeout, hwPtpPortSyncInterval, hwPtpPortMinDelayReqInterval, hwPtpPortMinPdelayReqInterval, hwPtpPortAsymmetryNegativeCorrection, 
                hwPtpPortAsymmetryPositiveCorrection, hwPtpPortMacEgressDestinationMac, hwPtpPortMacEgressVlanId, hwPtpPortMacEgressPacketPriority, hwPtpPortUdpEgressSourceIp, 
                hwPtpPortUdpEgressDestinationIp, hwPtpPortUdpEgressDestinationMac, hwPtpPortUdpEgressDscp, hwPtpPortUdpEgressVlanId, hwPtpPortUdpEgressPacketPriority, 
                hwPtpPortAnnounceDrop, hwPtpPortState, hwPtpPortSourcePortClockId, hwPtpBitsDirection, hwPtpBitsSignal, 
                hwPtpBitsSwitch, hwPtpBitsNormalStatus, hwPtpPortRowStatus, hwPtpPortStaticPktReset, hwPtpPortType, 
                hwPtpBitsClockAccuracy, hwPtpBitsClockClass, hwPtpPortCfgMsgFormat, hwPtpPortCfgExtInterfaceMode, hwPtpPortCfgLinkStatus, 
                hwPtpPortPortVlan, hwPtpPortNumber, hwPtpPortSourcePort, hwPtpPortSourcePortCard, hwPtpPortSourcePortSlot, 
                hwPtpPortSourcePortNum, hwPtpPortTcOcStaticClockPort, hwPtpPortTcOcStaticClockCard, hwPtpPortTcOcStaticClockSlot, hwPtpPortTcOcStaticClockPortNum, 
                hwPtpPortAnnounceReceipTimeout2, hwPtpBitsPriority2, hwPtpBitsPriority1, hwPtpBitsTimeSource, hwPtpPortClockStep, 
                hwPtpPeerAnnounceSendInterval, hwPtpOldPortState, hwPtpPortRecvCorrectend, hwPtpPortRecvAnnounce, hwPtpPortRecvSync, 
                hwPtpPortRecvReq, hwPtpPortRecvRespCnt, hwPtpPortRecvFollowup, hwPtpPortRecvPdelayrespfollowup, hwPtpPortSendTotal1588, 
                hwPtpPortSendAnnounce, hwPtpPortSendSync, hwPtpPortSendReq, hwPtpPortSendResp, hwPtpPortSendFollowup, 
                hwPtpPortSendPdelayrespfollowup, hwPtpPortDiscardTotal1588, hwPtpPortDiscardAnnounce, hwPtpPortDiscardSync, hwPtpPortDiscardDelayreq, 
                hwPtpPortDiscardPdelayreq, hwPtpPortDiscardResp, hwPtpPortDiscardPdelayresp, hwPtpPortDiscardFollowup, hwPtpPortDiscardPdelayrespfollowup, 
                hwPtpPortCfgState, hwPtpPortRecvTransparent, hwPtpPortName }
            STATUS current
            DESCRIPTION 
                "This is the group of PTP port table."
            ::= { hwPtpGroups 2 }

        
        -- 1.3.6.1.4.1.2011.5.25.187.6.2.3
        hwPtpLeapObjectsGroup OBJECT-GROUP
            OBJECTS { hwPtpLeapRowStatus, hwPtpLeap59or61 }
            STATUS current
            DESCRIPTION 
                "This is the group of PTP leap table."
            ::= { hwPtpGroups 3 }

        
        -- 1.3.6.1.4.1.2011.5.25.187.6.2.4
        hwPtpAclPermitClkIdObjectsGroup OBJECT-GROUP
            OBJECTS { hwPtpAclPermitClkIdRowStatus }
            STATUS current
            DESCRIPTION 
                "This is the group of PTP acl table."
            ::= { hwPtpGroups 4 }

        
        -- 1.3.6.1.4.1.2011.5.25.187.6.2.5
        hwPtpNotificationsGroup NOTIFICATION-GROUP
            NOTIFICATIONS { hwPtpClockSourceChange, hwPtpTimeSyncResume, hwPtpTimeSyncFaulty, hwPtpPortStateChange }
            STATUS current
            DESCRIPTION 
                "This is the group of PTP notification."
            ::= { hwPtpGroups 5 }

        
        -- 1.3.6.1.4.1.2011.5.25.187.7
        hwPtpAdaptiveClientList OBJECT IDENTIFIER ::= { hwPtpMIB 7 }

        
        -- 1.3.6.1.4.1.2011.5.25.187.7.1
        hwPtpAdaptiveClientListTable OBJECT-TYPE
            SYNTAX SEQUENCE OF HwPtpAdaptiveClientListEntry
            MAX-ACCESS not-accessible
            STATUS current
            DESCRIPTION
                "PtpAdaptiveClientListTable."
            ::= { hwPtpAdaptiveClientList 1 }

        
        -- 1.3.6.1.4.1.2011.5.25.187.7.1.1
        hwPtpAdaptiveClientListEntry OBJECT-TYPE
            SYNTAX HwPtpAdaptiveClientListEntry
            MAX-ACCESS not-accessible
            STATUS current
            DESCRIPTION
                "An entry in hwPtpAdaptiveClientListTable."
            INDEX { hwPtpAdaptiveClientIpList }
            ::= { hwPtpAdaptiveClientListTable 1 }

        
        HwPtpAdaptiveClientListEntry ::=
            SEQUENCE { 
                hwPtpAdaptiveClientIpList
                    IpAddress
             }

        -- 1.3.6.1.4.1.2011.5.25.187.7.1.1.1
        hwPtpAdaptiveClientIpList OBJECT-TYPE
            SYNTAX IpAddress
            MAX-ACCESS read-only
            STATUS current
            DESCRIPTION
                "Ptp adaptive device's client info."
            ::= { hwPtpAdaptiveClientListEntry 1 }

        
    
    END
