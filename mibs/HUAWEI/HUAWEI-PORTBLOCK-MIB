--==================================================================
-- Copyright (C) 2002 by  HUAWEI TECHNOLOGIES. All rights reserved.
-- 
-- Description: HUAWEI PORTBLOCK MIB
-- Reference:
-- Version: V1.0
-- History: For DT project,block qinq subif
-- ==================================================================
-- ==================================================================
-- 
-- Varibles and types be imported
--
-- ==================================================================
HUAWEI-PORTBLOCK-MIB DEFINITIONS ::= BEGIN
IMPORTS
    
    RowStatus
        FROM SNMPv2-TC

    MODULE-IDENTITY, OBJECT-TYPE, Integer32, OBJECT-IDENTITY
        FROM SNMPv2-SMI

    hwDatacomm
        FROM HUAWEI-MIB
        
    VlanId, VlanIdOrNone
        FROM Q-BRIDGE-MIB
    
    InterfaceIndex
        FROM IF-MIB;    
            
-- ==================================================================

        hwPortBlockMIB MODULE-IDENTITY
        LAST-UPDATED "200912120000Z"        -- December 14, 2009 at 00:00 GMT
        ORGANIZATION 
        "Huawei Technologies co., Ltd."
        CONTACT-INFO 
        "L2-Adp Team Huawei Technologies co., Ltd.
        Huawei Bld., NO.3 Xinxi Rd., 
        Shang-Di Information Industry Base,
        Hai-Dian District Beijing P.R. China
        http://www.huawei.com
            Zip:100085
        "
        DESCRIPTION
            "The PortBlock MIB module is defined to indicate port block function of Huawei Technologies co., Ltd."
            ::= { hwDatacomm 210 }
            

    hwPortBlockTable OBJECT-TYPE
        SYNTAX SEQUENCE OF HwPortBlockEntry
        MAX-ACCESS not-accessible
        STATUS current
        DESCRIPTION 
           "The table contains QinQ subIf block information."
        ::= { hwPortBlockMIB 1 }


    hwPortBlockEntry OBJECT-TYPE
        SYNTAX HwPortBlockEntry
        MAX-ACCESS not-accessible
        STATUS current
        DESCRIPTION 
           "Entries of QinQ subIf block MIB table."
        INDEX   { hwPortBlockIfIndex, hwPortBlockVlan, hwPortBlockBegCEVlan, hwPortBlockEndCEVlan, hwPortBlockPe8021p, hwPortBlockCe8021p }
        ::= { hwPortBlockTable 1}

    HwPortBlockEntry ::=
    SEQUENCE {
        hwPortBlockIfIndex      InterfaceIndex,
        hwPortBlockVlan         VlanIdOrNone,
        hwPortBlockBegCEVlan    VlanIdOrNone,
        hwPortBlockEndCEVlan    VlanIdOrNone,
        hwPortBlockPe8021p      Integer32,
        hwPortBlockCe8021p      Integer32,
        hwPortBlockRowStatus    RowStatus
        }

    hwPortBlockIfIndex OBJECT-TYPE
        SYNTAX  InterfaceIndex
        MAX-ACCESS not-accessible
        STATUS current
        DESCRIPTION 
           "The IfIndex of the QinQ SubIf."
        ::= { hwPortBlockEntry 1 }

    hwPortBlockVlan OBJECT-TYPE
        SYNTAX  VlanIdOrNone
        MAX-ACCESS not-accessible
        STATUS current
        DESCRIPTION 
           "The PE Vlan of the block SubIf."
        ::= { hwPortBlockEntry 2 }
        
    hwPortBlockBegCEVlan OBJECT-TYPE
        SYNTAX  VlanIdOrNone
        MAX-ACCESS not-accessible
        STATUS current
        DESCRIPTION 
           "The Min CE Vlan of the block SubIf."
        ::= { hwPortBlockEntry 3 }
        
    hwPortBlockEndCEVlan OBJECT-TYPE
        SYNTAX  VlanIdOrNone
        MAX-ACCESS not-accessible
        STATUS current
        DESCRIPTION 
           "The Max CE Vlan of the block SubIf."
        ::= { hwPortBlockEntry 4 }

    hwPortBlockPe8021p OBJECT-TYPE
    SYNTAX Integer32 (0..8)
          MAX-ACCESS not-accessible
          STATUS current
          DESCRIPTION
              "The 802.1p value of th Pe Vlan, default value is 8"
          ::= { hwPortBlockEntry 5 }

    hwPortBlockCe8021p OBJECT-TYPE
    SYNTAX Integer32 (0..8)
          MAX-ACCESS not-accessible
          STATUS current
          DESCRIPTION
              "The 802.1p value of th Ce Vlan, default value is 8"
          ::= { hwPortBlockEntry 6 }

    hwPortBlockRowStatus  OBJECT-TYPE
        SYNTAX  RowStatus
        MAX-ACCESS read-create
        STATUS current
        DESCRIPTION 
           "Operation status."
        ::= { hwPortBlockEntry 7 }
            
END
