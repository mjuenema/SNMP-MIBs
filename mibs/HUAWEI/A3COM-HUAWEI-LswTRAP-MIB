-- ==================================================================
-- Copyright (C) 2002 by  HUAWEI TECHNOLOGIES. All rights reserved.
--
-- Description: HUAWEI Lan Switch trap MIB
-- Reference:
-- Version: V1.0
-- History:
--(1) Created by Zhangshilin, 2001.06.29
-- ==================================================================

-- ==================================================================
--
-- Varibles and types be imported
--
-- ==================================================================
A3COM-HUAWEI-LswTRAP-MIB DEFINITIONS ::= BEGIN
IMPORTS
	MODULE-IDENTITY,NOTIFICATION-TYPE
		FROM SNMPv2-SMI

	lswCommon
		FROM A3COM-HUAWEI-OID-MIB

	hwDevMPowerNum, hwDevMFanNum
		FROM A3COM-HUAWEI-LswDEVM-MIB

	hwLswFrameIndex,hwLswSlotIndex ,hwLswSubslotIndex
		FROM A3COM-HUAWEI-DEVICE-MIB;

-- ==================================================================
--
-- ======================= definition begin =========================
--
-- ==================================================================

	 hwsLswTrapMib MODULE-IDENTITY
			LAST-UPDATED "200106290000Z"
			ORGANIZATION ""
			CONTACT-INFO
			""
			DESCRIPTION
			""
			REVISION "200106290000Z"
			DESCRIPTION
			""
			::= { lswCommon  12 }

	hwsLswTRAPMibObject OBJECT IDENTIFIER ::= {   hwsLswTrapMib 1  }


	powerfailure NOTIFICATION-TYPE
	  OBJECTS { hwDevMPowerNum }
	  STATUS  current
	  DESCRIPTION
			  "This trap is sent when power supply fails."
	  ::= { hwsLswTRAPMibObject 1 }

	hwPowerNormal NOTIFICATION-TYPE
	  OBJECTS { hwDevMPowerNum }
	  STATUS  current
	  DESCRIPTION
			  "This trap is sent when power supply becomes normal."
	  ::= { hwsLswTRAPMibObject 2 }

	hwMasterPowerNormal NOTIFICATION-TYPE
	  OBJECTS { hwDevMPowerNum }
	  STATUS  current
	  DESCRIPTION
			  "This trap is sent when master power supply becomes normal."
	  ::= { hwsLswTRAPMibObject 3 }

	hwSlavePowerNormal NOTIFICATION-TYPE
	  OBJECTS { hwDevMPowerNum }
	  STATUS  current
	  DESCRIPTION
			  "This trap is sent when slave power supply becomes normal."
	  ::= { hwsLswTRAPMibObject 4 }

	hwPowerRemoved NOTIFICATION-TYPE
	  OBJECTS { hwDevMPowerNum }
	  STATUS  current
	  DESCRIPTION
			  "This trap is sent when a power is removed."
	  ::= { hwsLswTRAPMibObject 5 }

	fanfailure NOTIFICATION-TYPE
	  OBJECTS { hwDevMFanNum }
	  STATUS  current
	  DESCRIPTION
			  "This trap is sent when a fan fails"
	  ::= { hwsLswTRAPMibObject 6 }


	hwFanNormal NOTIFICATION-TYPE
	  OBJECTS { hwDevMFanNum }
	  STATUS  current
	  DESCRIPTION
			  "This trap is sent when a fan becomes normal."
	  ::= { hwsLswTRAPMibObject 7 }


	hwBoardRemoved NOTIFICATION-TYPE
	  OBJECTS { hwLswFrameIndex, hwLswSlotIndex }
	  STATUS  current
	  DESCRIPTION
			  "This trap is sent when a board is removed."
	  ::= { hwsLswTRAPMibObject 8 }

	hwBoardInserted NOTIFICATION-TYPE
	  OBJECTS { hwLswFrameIndex,hwLswSlotIndex }
	  STATUS  current
	  DESCRIPTION
			  "This trap is sent when a board is inserted."
	  ::= { hwsLswTRAPMibObject 9 }

	hwBoardFailure NOTIFICATION-TYPE
	  OBJECTS { hwLswFrameIndex, hwLswSlotIndex }
	  STATUS  current
	  DESCRIPTION
			  "This trap is sent when a board fails."
	  ::= { hwsLswTRAPMibObject 10 }

	hwBoardNormal NOTIFICATION-TYPE
	  OBJECTS { hwLswFrameIndex, hwLswSlotIndex }
	  STATUS  current
	  DESCRIPTION
			  "This trap is sent when a board becomes normal."
	  ::= { hwsLswTRAPMibObject 11 }

	hwSubcardRemove NOTIFICATION-TYPE
	  OBJECTS { hwLswFrameIndex, hwLswSlotIndex, hwLswSubslotIndex }
	  STATUS  current
	  DESCRIPTION
			  "This trap is sent when a sub card is removed"
	  ::= { hwsLswTRAPMibObject 12 }

	hwSubcardInsert NOTIFICATION-TYPE
	  OBJECTS { hwLswFrameIndex, hwLswSlotIndex, hwLswSubslotIndex }
	  STATUS  current
	  DESCRIPTION
			  "This trap is sent when sub card is inserted"
	  ::= { hwsLswTRAPMibObject 13 }

	hwBoaardTemperatureLower NOTIFICATION-TYPE
	  OBJECTS { hwLswFrameIndex, hwLswSlotIndex }
	  STATUS  current
	  DESCRIPTION
			  "This trap is sent when a board's temperature is too low."
	  ::= { hwsLswTRAPMibObject 14 }

	hwBoaardTemperatureFromLowerToNormal NOTIFICATION-TYPE
	  OBJECTS { hwLswFrameIndex, hwLswSlotIndex }
	  STATUS  current
	  DESCRIPTION
			  "This trap is sent when a board's temperature goes form too low to normal."
	  ::= { hwsLswTRAPMibObject 15 }


	hwBoaardTemperatureHigher NOTIFICATION-TYPE
	  OBJECTS { hwLswFrameIndex, hwLswSlotIndex }
	  STATUS  current
	  DESCRIPTION
			  "This trap is sent when a board's temperature is too high"
	  ::= { hwsLswTRAPMibObject 16 }

	hwBoaardTemperatureFormHigherToNormal NOTIFICATION-TYPE
	  OBJECTS { hwLswFrameIndex, hwLswSlotIndex }
	  STATUS  current
	  DESCRIPTION
			  "This trap is sent when a board's temperature goes from too high to normal"
	  ::= { hwsLswTRAPMibObject 17 }

	hwRequestLoading NOTIFICATION-TYPE
	  OBJECTS { hwLswFrameIndex, hwLswSlotIndex }
	  STATUS  current
	  DESCRIPTION
			  "This trap is sent when a board request loading."
	  ::= { hwsLswTRAPMibObject 18 }

	hwLoadFailure NOTIFICATION-TYPE
	  OBJECTS { hwLswFrameIndex, hwLswSlotIndex }
	  STATUS  current
	  DESCRIPTION
			  "This trap is sent when a board loading fails."
	  ::= { hwsLswTRAPMibObject 19 }

	hwLoadFinished NOTIFICATION-TYPE
	  OBJECTS { hwLswFrameIndex, hwLswSlotIndex }
	  STATUS  current
	  DESCRIPTION
			  "This trap is sent when a board loading finishes."
	  ::= { hwsLswTRAPMibObject 20 }

	hwBackBoardModeSetFuilure NOTIFICATION-TYPE
	  OBJECTS { hwLswFrameIndex }
	  STATUS  current
	  DESCRIPTION
			  "This trap is sent when a back board mode set fails."
	  ::= { hwsLswTRAPMibObject 21 }

	hwBackBoardModeSetOK NOTIFICATION-TYPE
	  OBJECTS { hwLswFrameIndex }
	  STATUS  current
	  DESCRIPTION
			  "This trap is sent when a back board mode set is OK"
	  ::= { hwsLswTRAPMibObject 22 }

	hwPowerInserted NOTIFICATION-TYPE
	  OBJECTS { hwDevMPowerNum }
	  STATUS  current
	  DESCRIPTION
			  "This trap is sent when power inserted"
	  ::= { hwsLswTRAPMibObject 23 }

END
