--  ======================================================================
-- Copyright (C) 2009 by  HUAWEI TECHNOLOGIES. All rights reserved
-- 
-- Description: HUAWEI-SECURITY-LICENSE-MIB
-- Reference:
-- Version:     V1.00
-- History:
-- 
--  V1.00 2009-03-13 shaoyu created for license of security product
-- =======================================================================

HUAWEI-SECURITY-LICENSE-MIB DEFINITIONS ::= BEGIN

	IMPORTS
	    enterprises
		FROM RFC1155-SMI
            OBJECT-GROUP            
                FROM SNMPv2-CONF            
            Integer32, Counter64, OBJECT-TYPE, MODULE-IDENTITY            
                FROM SNMPv2-SMI            
            TruthValue            
                FROM SNMPv2-TC;

	hwLicenseMibObjects MODULE-IDENTITY 
		LAST-UPDATED "200303180900Z"		-- March 18, 2003 at 09:00 GMT
		ORGANIZATION 
			"Huawei Technologies Co., Ltd.
			"
		CONTACT-INFO 
			"
			R&D BeiJing, Huawei Technologies co.,Ltd.
			Huawei Bld.,NO.3 Xinxi Rd.,
			Shang-Di Information Industry Base,
			Hai-Dian District Beijing P.R. China
			Zip:100085
			Http://www.huawei.com
			E-mail:support@huawei.com
			"
		DESCRIPTION 
			"
			V1.00
			The License mib is for Eudemon and USG product series..
			"
		::= { hwSecurity 16 }
	
--
-- Node definitions
--
	huawei OBJECT IDENTIFIER ::= { enterprises 2011 }
        
    -- 1.3.6.1.4.1.2011.6
    huaweiUtility OBJECT IDENTIFIER ::= { huawei 6 }
        
    -- 1.3.6.1.4.1.2011.6.122
    hwSecurity OBJECT IDENTIFIER ::= { huaweiUtility 122 }  
	
	-- 1.3.6.1.4.1.2011.6.122.16.1
	hwLicenseCfgObjects OBJECT IDENTIFIER ::= { hwLicenseMibObjects 1 }
	
	-- 1.3.6.1.4.1.2011.6.122.16.2
	hwLicenseMonitorObjects OBJECT IDENTIFIER ::= { hwLicenseMibObjects 2 }

	-- 1.3.6.1.4.1.2011.6.122.16.3	
	hwLicenseConformance OBJECT IDENTIFIER ::= { hwLicenseMibObjects 3 }
	
	-- 1.3.6.1.4.1.2011.6.122.16.4	
	hwLicenseSysObjects OBJECT IDENTIFIER ::= { hwLicenseMibObjects 4 }
	
	-- 1.3.6.1.4.1.2011.6.122.16.5
	hwLicenseTraps OBJECT IDENTIFIER ::= { hwLicenseMibObjects 5 }
	
	-- 1.3.6.1.4.1.2011.6.122.16.2.1
        hwLicenseTotalVfwNumber OBJECT-TYPE
            SYNTAX Counter64
            MAX-ACCESS read-only
            STATUS current
            DESCRIPTION
                "The total number of virtual firewalls."
            ::= { hwLicenseMonitorObjects 1 }
            	
    -- 1.3.6.1.4.1.2011.6.122.16.2.2  	
        hwLicenseCurVfwNumber OBJECT-TYPE
            SYNTAX Counter64
            MAX-ACCESS read-only
            STATUS current
            DESCRIPTION
                "The current number of virtual firewalls."
            ::= { hwLicenseMonitorObjects 2 }

    -- 1.3.6.1.4.1.2011.6.122.16.2.3  	
        hwLicenseTotalIPsecTunnelNumber OBJECT-TYPE
            SYNTAX Counter64
            MAX-ACCESS read-only
            STATUS current
            DESCRIPTION
                "The total number of ipsec tunnels."
            ::= { hwLicenseMonitorObjects 3 }
                                                  
    -- 1.3.6.1.4.1.2011.6.122.16.2.4  	
        hwLicenseCurIPsecTunnelNumber OBJECT-TYPE
            SYNTAX Counter64
            MAX-ACCESS read-only
            STATUS current
            DESCRIPTION
                "The current number of ipsec tunnels."
            ::= { hwLicenseMonitorObjects 4 }
			
    -- 1.3.6.1.4.1.2011.6.122.16.2.5  	
        hwLicenseTotal6RDSessCount OBJECT-TYPE
            SYNTAX Counter64
            MAX-ACCESS read-only
            STATUS current
            DESCRIPTION
                "The total number of 6RD sessions."
            ::= { hwLicenseMonitorObjects 5 }
                                                  
    -- 1.3.6.1.4.1.2011.6.122.16.2.6  	
        hwLicenseCur6RDSessCount OBJECT-TYPE
            SYNTAX Counter64
            MAX-ACCESS read-only
            STATUS current
            DESCRIPTION
                "The current number of 6RD sessions."
            ::= { hwLicenseMonitorObjects 6 }
			
	-- 1.3.6.1.4.1.2011.6.122.16.2.7  	
        hwLicenseTotalNAT64SessCount OBJECT-TYPE
            SYNTAX Counter64
            MAX-ACCESS read-only
            STATUS current
            DESCRIPTION
                "The total number of NAT64 sessions."
            ::= { hwLicenseMonitorObjects 7 }
                                                  
    -- 1.3.6.1.4.1.2011.6.122.16.2.8  	
        hwLicenseCurNAT64SessCount OBJECT-TYPE
            SYNTAX Counter64
            MAX-ACCESS read-only
            STATUS current
            DESCRIPTION
                "The current number of NAT64 sessions."
            ::= { hwLicenseMonitorObjects 8 }
			
	-- 1.3.6.1.4.1.2011.6.122.16.2.9  	
        hwLicenseTotalDSLiteSessCount OBJECT-TYPE
            SYNTAX Counter64
            MAX-ACCESS read-only
            STATUS current
            DESCRIPTION
                "The total number of DS-Lite sessions."
            ::= { hwLicenseMonitorObjects 9 }
                                                  
    -- 1.3.6.1.4.1.2011.6.122.16.2.10  	
        hwLicenseCurDSLiteSessCount OBJECT-TYPE
            SYNTAX Counter64
            MAX-ACCESS read-only
            STATUS current
            DESCRIPTION
                "The current number of DS-Lite sessions."
            ::= { hwLicenseMonitorObjects 10 }

	-- ===============================================
	-- definition of hwLicenseSysObjects.      
	-- ===============================================
	-- 1.3.6.1.4.1.2011.6.122.16.4.1  	
        hwLicenseSysCur6RDSessCount OBJECT-TYPE
            SYNTAX Gauge32
            MAX-ACCESS accessible-for-notify
            STATUS current
            DESCRIPTION
                "The current number of 6RD sessions."
            ::= { hwLicenseSysObjects 1 }
                                                  
    -- 1.3.6.1.4.1.2011.6.122.16.4.2  	
        hwLicenseSysTotal6RDSessCount OBJECT-TYPE
            SYNTAX Gauge32
            MAX-ACCESS accessible-for-notify
            STATUS current
            DESCRIPTION
                "The total number of 6RD sessions."
            ::= { hwLicenseSysObjects 2 }
	
	-- 1.3.6.1.4.1.2011.6.122.16.4.3  	
        hwLicenseSys6RDSessPercent OBJECT-TYPE
            SYNTAX Gauge32
            MAX-ACCESS accessible-for-notify
            STATUS current
            DESCRIPTION
                "Percentage of used 6RD sessions."
            ::= { hwLicenseSysObjects 3 }
                                                  
    -- 1.3.6.1.4.1.2011.6.122.16.4.4  	
        hwLicenseSys6RDSessThreshold OBJECT-TYPE
            SYNTAX Gauge32
            MAX-ACCESS accessible-for-notify
            STATUS current
            DESCRIPTION
                "The alarm threshold of 6RD sessions."
            ::= { hwLicenseSysObjects 4 }
	
	-- 1.3.6.1.4.1.2011.6.122.16.4.5  	
        hwLicenseSysCurNAT64SessCount OBJECT-TYPE
            SYNTAX Gauge32
            MAX-ACCESS accessible-for-notify
            STATUS current
            DESCRIPTION
                "The current number of NAT64 sessions."
            ::= { hwLicenseSysObjects 5 }
                                                  
    -- 1.3.6.1.4.1.2011.6.122.16.4.6  	
        hwLicenseSysTotalNAT64SessCount OBJECT-TYPE
            SYNTAX Gauge32
            MAX-ACCESS accessible-for-notify
            STATUS current
            DESCRIPTION
                "The total number of NAT64 sessions."
            ::= { hwLicenseSysObjects 6 }
	
	-- 1.3.6.1.4.1.2011.6.122.16.4.7  	
        hwLicenseSysNAT64SessPercent OBJECT-TYPE
            SYNTAX Gauge32
            MAX-ACCESS accessible-for-notify
            STATUS current
            DESCRIPTION
                "Percentage of used NAT64 sessions."
            ::= { hwLicenseSysObjects 7 }
                                                  
    -- 1.3.6.1.4.1.2011.6.122.16.4.8  	
        hwLicenseSysNAT64SessThreshold OBJECT-TYPE
            SYNTAX Gauge32
            MAX-ACCESS accessible-for-notify
            STATUS current
            DESCRIPTION
                "The alarm threshold of NAT64 sessions."
            ::= { hwLicenseSysObjects 8 }
	
	-- 1.3.6.1.4.1.2011.6.122.16.4.9  	
        hwLicenseSysCurDSLiteSessCount OBJECT-TYPE
            SYNTAX Gauge32
            MAX-ACCESS accessible-for-notify
            STATUS current
            DESCRIPTION
                "The current number of DS-Lite sessions."
            ::= { hwLicenseSysObjects 9 }
                                                  
    -- 1.3.6.1.4.1.2011.6.122.16.4.10  	
        hwLicenseSysTotalDSLiteSessCount OBJECT-TYPE
            SYNTAX Gauge32
            MAX-ACCESS accessible-for-notify
            STATUS current
            DESCRIPTION
                "The total number of DS-Lite sessions."
            ::= { hwLicenseSysObjects 10 }
	
	-- 1.3.6.1.4.1.2011.6.122.16.4.11  	
        hwLicenseSysDSLiteSessPercent OBJECT-TYPE
            SYNTAX Gauge32
            MAX-ACCESS accessible-for-notify
            STATUS current
            DESCRIPTION
                "Percentage of used DS-Lite sessions."
            ::= { hwLicenseSysObjects 11 }
                                                  
    -- 1.3.6.1.4.1.2011.6.122.16.4.12  	
        hwLicenseSysDSLiteSessThreshold OBJECT-TYPE
            SYNTAX Gauge32
            MAX-ACCESS accessible-for-notify
            STATUS current
            DESCRIPTION
                "The alarm threshold of DS-Lite sessions."
            ::= { hwLicenseSysObjects 12 }
			
	-- ===============================================
	-- definition of hwLicenseTraps.      
	-- ===============================================
	-- 1.3.6.1.4.1.2011.6.122.16.5.1   	
            hwLicense6RDSessOverThreshold NOTIFICATION-TYPE
            OBJECTS { hwLicenseSysCur6RDSessCount, hwLicenseSysTotal6RDSessCount, hwLicenseSys6RDSessPercent, hwLicenseSys6RDSessThreshold
                  }
            STATUS current
            DESCRIPTION 
                "The current number of 6RD sessions exceeds the threshold."
            ::= { hwLicenseTraps 1 }
	
	-- 1.3.6.1.4.1.2011.6.122.16.5.2   	
            hwLicense6RDSessBelowThreshold NOTIFICATION-TYPE
            OBJECTS { hwLicenseSysCur6RDSessCount, hwLicenseSysTotal6RDSessCount, hwLicenseSys6RDSessPercent, hwLicenseSys6RDSessThreshold
                  }
            STATUS current
            DESCRIPTION 
                "The current number of 6RD sessions is below the threshold."
            ::= { hwLicenseTraps 2 }
			
	-- 1.3.6.1.4.1.2011.6.122.16.5.3   	
            hwLicenseNAT64SessOverThreshold NOTIFICATION-TYPE
            OBJECTS { hwLicenseSysCurNAT64SessCount, hwLicenseSysTotalNAT64SessCount, hwLicenseSysNAT64SessPercent, hwLicenseSysNAT64SessThreshold
                  }
            STATUS current
            DESCRIPTION 
                "The current number of NAT64 sessions exceeds the threshold."
            ::= { hwLicenseTraps 3 }
	
	-- 1.3.6.1.4.1.2011.6.122.16.5.4   	
            hwLicenseNAT64SessBelowThreshold NOTIFICATION-TYPE
            OBJECTS { hwLicenseSysCurNAT64SessCount, hwLicenseSysTotalNAT64SessCount, hwLicenseSysNAT64SessPercent, hwLicenseSysNAT64SessThreshold
                  }
            STATUS current
            DESCRIPTION 
                "The current number of NAT64 sessions is below the threshold."
            ::= { hwLicenseTraps 4 }
	
	-- 1.3.6.1.4.1.2011.6.122.16.5.5   	
            hwLicenseDSLiteSessOverThreshold NOTIFICATION-TYPE
            OBJECTS { hwLicenseSysCurDSLiteSessCount, hwLicenseSysTotalDSLiteSessCount, hwLicenseSysDSLiteSessPercent, hwLicenseSysDSLiteSessThreshold
                  }
            STATUS current
            DESCRIPTION 
                "The current number of DS-Lite sessions exceeds the threshold."
            ::= { hwLicenseTraps 5 }
	
	-- 1.3.6.1.4.1.2011.6.122.16.5.6   	
            hwLicenseDSLiteSessBelowThreshold NOTIFICATION-TYPE
            OBJECTS { hwLicenseSysCurDSLiteSessCount, hwLicenseSysTotalDSLiteSessCount, hwLicenseSysDSLiteSessPercent, hwLicenseSysDSLiteSessThreshold
                  }
            STATUS current
            DESCRIPTION 
                "The current number of DS-Lite sessions is below the threshold."
            ::= { hwLicenseTraps 6 }
			
	--conformance		
       hwLicenseGroups OBJECT IDENTIFIER ::= { hwLicenseConformance 1 }  
       
       hwLicenseCompliances OBJECT IDENTIFIER ::= { hwLicenseConformance 2 }
       
       licenseModuleCompliance MODULE-COMPLIANCE
            STATUS current
            DESCRIPTION 
                "The compliance statement for entities which 
                implement the huaweisymantec License MIB."
            MODULE -- this module
            MANDATORY-GROUPS {hwlicenseMoniGroup,hwlicenseObjectGroup,hwlicenseTrapGroup
                             }
            ::= { hwLicenseCompliances 1 }
            
       hwlicenseMoniGroup OBJECT-GROUP
            OBJECTS {hwLicenseTotalVfwNumber,
                     hwLicenseCurVfwNumber,
                     hwLicenseTotalIPsecTunnelNumber,
                     hwLicenseCurIPsecTunnelNumber,
					 hwLicenseTotal6RDSessCount,
					 hwLicenseCur6RDSessCount,
					 hwLicenseTotalNAT64SessCount,
					 hwLicenseCurNAT64SessCount,
					 hwLicenseTotalDSLiteSessCount,
					 hwLicenseCurDSLiteSessCount					 
                    }
            STATUS current
            DESCRIPTION 
                "Description."
            ::= { hwLicenseGroups 1 }
        
        hwlicenseSysObjectGroup OBJECT-GROUP
            OBJECTS {hwLicenseSysCur6RDSessCount,
                     hwLicenseSysTotal6RDSessCount,
                     hwLicenseSys6RDSessPercent,
                     hwLicenseSys6RDSessThreshold,
					 hwLicenseSysCurNAT64SessCount,
					 hwLicenseSysTotalNAT64SessCount,
					 hwLicenseSysNAT64SessPercent,
					 hwLicenseSysNAT64SessThreshold,
					 hwLicenseSysCurDSLiteSessCount,
					 hwLicenseSysTotalDSLiteSessCount,
					 hwLicenseSysDSLiteSessPercent,
					 hwLicenseSysDSLiteSessThreshold
                    }
            STATUS current
            DESCRIPTION 
                "Group for license trap objects."
            ::= { hwLicenseGroups 2 }

        
        hwlicenseTrapGroup NOTIFICATION-GROUP
            NOTIFICATIONS { hwLicense6RDSessOverThreshold, 
			                hwLicense6RDSessBelowThreshold,
							hwLicenseNAT64SessOverThreshold,
							hwLicenseNAT64SessBelowThreshold,
							hwLicenseDSLiteSessOverThreshold,
			                hwLicenseDSLiteSessBelowThreshold 
						  }
            STATUS current
            DESCRIPTION 
                "Group for all license traps."
            ::= { hwLicenseGroups 3 }
                                                  
END
