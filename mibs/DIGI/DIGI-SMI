-- =============================================================
-- = DIGI-SMI : Enterprise structure of management information =
-- =                                                           =
-- =   Digi International Part Number: 40002195_M              =
-- =                                                           =
-- = (c) Copyright 2000-2002 Digi International, Inc.          =
-- =============================================================


DIGI-SMI DEFINITIONS ::= BEGIN

IMPORTS
    enterprises
        FROM RFC1155-SMI;
        
--   digiEnterprise MODULE-IDENTITY
--       LAST-UPDATED "0502240100Z"
--       ORGANIZATION "Digi International Inc."
--       CONTACT-INFO
--               "Digi International Inc.
--		          11001 Bren Road East
--                Minnetonka, MN 55343
--                support@digi.com"
--       DESCRIPTION
--               "Digi Structure of Management Information MIB"
--       ::= { enterprises 332 }

-- =============================================================
-- Top Level for Digi Enterprise        
digiEnterprise      OBJECT IDENTIFIER ::= { enterprises 332 }
digiCommon          OBJECT IDENTIFIER ::= { digiEnterprise 10 }
digiProducts        OBJECT IDENTIFIER ::= { digiEnterprise 11 }
digiCapabilities    OBJECT IDENTIFIER ::= { digiEnterprise 12 }
digiRequirements    OBJECT IDENTIFIER ::= { digiEnterprise 13 }
digiExperimental    OBJECT IDENTIFIER ::= { digiEnterprise 14 }

-- =============================================================
-- digiCommon
digiProtocols	    OBJECT IDENTIFIER ::= { digiCommon 11 }
digiResources	    OBJECT IDENTIFIER ::= { digiCommon 12 }
digiInterfaces	    OBJECT IDENTIFIER ::= { digiCommon 13 }
digiFeatures        OBJECT IDENTIFIER ::= { digiCommon 14 }

-- =============================================================
-- digiProtocols
digiModbus	        OBJECT IDENTIFIER ::= { digiProtocols 11 }
digiIA		        OBJECT IDENTIFIER ::= { digiProtocols 12 }
digiUdpSerial		OBJECT IDENTIFIER ::= { digiProtocols 13 }

-- =============================================================
-- digiResources
-- (no entries)

-- =============================================================
-- digiInterfaces
-- 
digiMei             OBJECT IDENTIFIER ::= { digiInterfaces 11 }
digiPowerSupply     OBJECT IDENTIFIER ::= { digiInterfaces 12 }
digiWLan            OBJECT IDENTIFIER ::= { digiInterfaces 13 }
digiPowerMgmt       OBJECT IDENTIFIER ::= { digiInterfaces 14 }

-- =============================================================
-- digiFeatures
digiPortBuffering        OBJECT IDENTIFIER ::= { digiFeatures 11 }
digiKeywordNotify        OBJECT IDENTIFIER ::= { digiFeatures 12 }
digiSocketID             OBJECT IDENTIFIER ::= { digiFeatures 13 }
digiLoginTraps           OBJECT IDENTIFIER ::= { digiFeatures 14 }
digiSecureAccess         OBJECT IDENTIFIER ::= { digiFeatures 15 }
digiPowerManagementTraps OBJECT IDENTIFIER ::= { digiFeatures 16 }
digiSerialTraps          OBJECT IDENTIFIER ::= { digiFeatures 17 }
digiModemTestTraps       OBJECT IDENTIFIER ::= { digiFeatures 18 }
digiSerialAlarmTraps     OBJECT IDENTIFIER ::= { digiFeatures 19 }
digiActiveDetectionTraps OBJECT IDENTIFIER ::= { digiFeatures 20 }
digiNFSTraps             OBJECT IDENTIFIER ::= { digiFeatures 21 }
digiIPMINotify           OBJECT IDENTIFIER ::= { digiFeatures 22 }
digiPowerTraps           OBJECT IDENTIFIER ::= { digiFeatures 23 }
digiMobileTraps          OBJECT IDENTIFIER ::= { digiFeatures 24 }

-- =============================================================
-- digiProducts
digiDeviceDrivers   OBJECT IDENTIFIER ::= { digiProducts 1 }
digiRasAdapters     OBJECT IDENTIFIER ::= { digiProducts 2 }
digiSerialAdapters  OBJECT IDENTIFIER ::= { digiProducts 3 }
digiDigitalAdapters OBJECT IDENTIFIER ::= { digiProducts 4 }
digiTerminalServers OBJECT IDENTIFIER ::= { digiProducts 5 }
digiConnect         OBJECT IDENTIFIER ::= { digiProducts 6 }
digiCM              OBJECT IDENTIFIER ::= { digiProducts 7 }
digiPassport        OBJECT IDENTIFIER ::= { digiProducts 8 }

-- =============================================================
-- Drivers
-- (no entries)

-- =============================================================
-- digiRasAdapters
digiDataFireRAST1E1 OBJECT IDENTIFIER ::= { digiRasAdapters 1 } 
digiDataFireRASBRI  OBJECT IDENTIFIER ::= { digiRasAdapters 2 }
digiAcceleportRAS   OBJECT IDENTIFIER ::= { digiRasAdapters 3 }

-- =============================================================
-- digiSerialAdapters
-- (no entries)

-- =============================================================
-- digiDigitalAdapters
digiSyncAdapters    OBJECT IDENTIFIER ::= { digiDigitalAdapters 1 }
digiISDNAdapters    OBJECT IDENTIFIER ::= { digiDigitalAdapters 2 }

-- =============================================================
-- digiSyncAdapters
digiSync2000        OBJECT IDENTIFIER ::= { digiSyncAdapters 1 }
digiSync2000CPCI    OBJECT IDENTIFIER ::= { digiSyncAdapters 2 }
digiSync570         OBJECT IDENTIFIER ::= { digiSyncAdapters 3 }

-- =============================================================
-- digiISDNAdapters
digiDataFirePRIme   OBJECT IDENTIFIER ::= { digiISDNAdapters 1 }
digiDataFireBRI     OBJECT IDENTIFIER ::= { digiISDNAdapters 2 }

       
-- =============================================================
-- digiTerminalServers
digiEtherlites      OBJECT IDENTIFIER ::= { digiTerminalServers 1 } 
digiSCSIs           OBJECT IDENTIFIER ::= { digiTerminalServers 2 } 
digiPortServers     OBJECT IDENTIFIER ::= { digiTerminalServers 3 } 
digiMultiModeCons   OBJECT IDENTIFIER ::= { digiTerminalServers 4 } 

-- =============================================================
-- digiEtherlites
-- (no entries)

-- =============================================================
-- digiSCSIs
-- (no entries)
     
-- =============================================================
-- digiPortServers
digiPortServer      OBJECT IDENTIFIER ::= { digiPortServers 1 }
digiPortServer2     OBJECT IDENTIFIER ::= { digiPortServers 2 }
digiPortServerTS    OBJECT IDENTIFIER ::= { digiPortServers 3 }
     
-- =============================================================
-- digiConnect
digiDeviceInfo       OBJECT IDENTIFIER ::= { digiConnect 1 }
digiDeviceIdent	     OBJECT IDENTIFIER ::= { digiConnect 2 } 
digiMobileInfo       OBJECT IDENTIFIER ::= { digiConnect 3 }
digiCwmNotifications OBJECT IDENTIFIER ::= { digiConnect 100 } 


END
