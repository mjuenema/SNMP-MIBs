-- =====================================================================
-- == DIGI-MOBILE-INFOINFORMATION-MIB:                                ==
-- == DIGI Connect Mobile Information Management Information Base     ==
-- ==                                                                 ==
-- ==   Digi International Part Number: 4000xxxx_A                    ==
-- ==                                                                 ==
-- == (c) Copyright 2001-2007 Digi International, Inc.                ==
-- =====================================================================

DIGI-MOBILE-INFORMATION-MIB DEFINITIONS ::= BEGIN

IMPORTS
digiMobileInfo FROM DIGI-SMI
OBJECT-TYPE FROM RFC-1212;

--   digiMobileInfo MODULE-IDENTITY
--       LAST-UPDATED "0201090100Z"
--       ORGANIZATION "Digi International Inc."
--       CONTACT-INFO
--               "        Michael Nicholson
--                Postal: Digi International Inc.
--		          11001 Bren Road East
--                        Minnetonka, MN 55343
--
--                   Tel: 952-912-3146
--                   Fax: 952-912-4952
--                E-mail: Mike.Nicholson@digi.com"
--       DESCRIPTION
--               "Digi Connect Mobile Information MIB"
--       ::= { digiConnect 3 }

-- === + Textual Conventions + =========================================

-- =====================================================================
-- =====================================================================
-- === + MOBILE INFORMATION + ==========================================
-- =====================================================================
-- =====================================================================

miNumber OBJECT-TYPE
    SYNTAX  INTEGER (0..8)
    ACCESS  read-only
    STATUS  mandatory
    DESCRIPTION
  "The number of network interfaces (regardless of
  their current state) present on this system.  The 
  interface identifiedby a particular value of this 
  index is the sameinterface as identified by the 
  same value of ifIndex."
    ::= { digiMobileInfo 1 }

miTable OBJECT-TYPE
    SYNTAX  SEQUENCE OF MiEntry
    ACCESS  not-accessible
    STATUS  mandatory
    DESCRIPTION
  "A list of mobile interface information entries.  The number of
  possible entries is given by the value of miNumber."
    ::= { digiMobileInfo 2 }

miEntry OBJECT-TYPE
    SYNTAX  MiEntry
    ACCESS  not-accessible
    STATUS  mandatory
    DESCRIPTION
  "A mobile interface information entry containing the number of
  information name/value pairs available for read"
    INDEX   { miIndex }
    ::= { miTable 1 }

MiEntry ::= SEQUENCE {
    miIndex INTEGER,
    miNumFields INTEGER
}

miIndex OBJECT-TYPE
    SYNTAX  INTEGER (1..8)
    ACCESS  read-only
    STATUS  mandatory
    DESCRIPTION
  "A unique value for each interface.  Its value
  ranges between 1 and the value of miNumber.  The
  value for each interface must remain constant at
  least from one re-initialization of the entity's
  network management system to the next re-
  initialization. The interface identified
  by a particular value of this index is the same
  interface as identified by the same value of
  ifIndex."
    ::= { miEntry 1 }

miNumFields OBJECT-TYPE
    SYNTAX  INTEGER (1..64)
    ACCESS  read-only
    STATUS  mandatory
    DESCRIPTION
  "The number of information fields associated with this interface."
    ::= { miEntry 2 }

miInfoTable OBJECT-TYPE
    SYNTAX SEQUENCE OF MiInfoEntry
    ACCESS not-accessible
    STATUS mandatory
    DESCRIPTION
        "A table of information name/value pairs"
::= { digiMobileInfo 3 }

miInfoEntry OBJECT-TYPE
    SYNTAX MiInfoEntry
    ACCESS not-accessible
    STATUS mandatory
    DESCRIPTION
        "An information name/value pair entry"
    INDEX { miInfoInterface, miInfoIndex }
::= { miInfoTable 1 }

MiInfoEntry ::= SEQUENCE {
    miInfoInterface INTEGER,
    miInfoIndex INTEGER,
    miInfoName OCTET STRING,
    miInfoValue OCTET STRING
}

miInfoInterface OBJECT-TYPE
    SYNTAX  INTEGER (1..8)
    ACCESS  read-only
    STATUS  mandatory
    DESCRIPTION
  "A unique value for each interface.  Its value
  ranges between 1 and the value of miNumber.  The
  value for each interface must remain constant at
  least from one re-initialization of the entity's
  network management system to the next re-
  initialization. The interface identified
  by a particular value of this index is the same
  interface as identified by the same value of
  ifIndex."
    ::= { miInfoEntry 1 }

miInfoIndex OBJECT-TYPE
    SYNTAX  INTEGER (1..64)
    ACCESS  read-only
    STATUS  mandatory
    DESCRIPTION
  "A unique value for each information Name/Value pair
  ranges between 1 and the value of miNumFields.  The
  value for each interface must remain constant at
  least from one re-initialization of the entity's
  network management system to the next re-
  initialization."
    ::= { miInfoEntry 2 }

miInfoName OBJECT-TYPE
    SYNTAX  OCTET STRING (SIZE (0..80))
    ACCESS  read-only
    STATUS  mandatory
    DESCRIPTION
  "The name portion of this information name/value pair"
    ::= { miInfoEntry 3 }

miInfoValue OBJECT-TYPE
    SYNTAX  OCTET STRING (SIZE (0..80))
    ACCESS  read-only
    STATUS  mandatory
    DESCRIPTION
  "The value portion of this information name/value pair"
    ::= { miInfoEntry 4 }

END
