-- ==================================================================
-- Copyright (C) 2008 by H3C Technologies. All rights reserved.
--
-- Description: Loopback detection MIB
-- Reference:
-- Version: V1.0
-- History:
-- V1.0 2008-09-27 Created by LuoXuefang
-- ==================================================================
H3C-LPBKDT-MIB DEFINITIONS ::= BEGIN

IMPORTS
    h3cCommon
        FROM HUAWEI-3COM-OID-MIB
    ifIndex, ifDescr
        FROM IF-MIB
    MODULE-IDENTITY, NOTIFICATION-TYPE
        FROM SNMPv2-SMI;

h3cLpbkdt MODULE-IDENTITY
    LAST-UPDATED "200809271504Z"        -- September 27, 2008 at 15:04 GMT
    ORGANIZATION "H3C Technologies Co., Ltd."
    CONTACT-INFO
        "Comware Team H3C Technologies Co., Ltd.
        Hai-Dian District Beijing P.R. China
        http://www.h3c.com
        Zip:100085"
    DESCRIPTION
        "Loops may cause broadcast storms.  The purpose of loopback detection
         is to detect loops on the device and to protect the network."
    ::= { h3cCommon 95 }

-- ==================================================================
--
-- ======================= definition begin =========================
--
-- ==================================================================

h3cLpbkdtNotifications OBJECT IDENTIFIER ::= {  h3cLpbkdt 1  }
h3cLpbkdtTrapPrefix OBJECT IDENTIFIER ::= { h3cLpbkdtNotifications 0 }

h3cLpbkdtTrapLoopbacked NOTIFICATION-TYPE
    OBJECTS { ifIndex, ifDescr }
    STATUS current
    DESCRIPTION
        "Trap message is generated when the interface is looped."
    ::= { h3cLpbkdtTrapPrefix 1 }

h3cLpbkdtTrapRecovered NOTIFICATION-TYPE
    OBJECTS { ifIndex, ifDescr }
    STATUS current
    DESCRIPTION
        "Trap message is generated when the loops on the interface
         are eliminated."
    ::= { h3cLpbkdtTrapPrefix 2 }

END
