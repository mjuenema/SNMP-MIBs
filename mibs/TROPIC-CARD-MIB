TROPIC-CARD-MIB DEFINITIONS ::= BEGIN

-- (c) Copyright 2016 Nokia.  All rights reserved.
-- This software is the confidential and proprietary property of
-- Nokia and may only be used in accordance with the
-- terms of the license agreement provided with this software.

 IMPORTS
      SnmpAdminString                         FROM SNMP-FRAMEWORK-MIB
      OBJECT-TYPE, MODULE-IDENTITY,
      Unsigned32, Integer32                   FROM SNMPv2-SMI
      MODULE-COMPLIANCE, OBJECT-GROUP         FROM SNMPv2-CONF
      TruthValue                              FROM SNMPv2-TC
      TropicCardCLEI,
      TropicCardHFD,
      TropicCardSerialNumber,
      TropicCardManufacturingPartNumber,
      TropicCardMarketingPartNumber,
      TropicCardSWGenericLoadName,
      TropicLEDColorType,
      TropicLEDStateType,
      AluWdmCardCapacity,
      AluWdmWtClkValues                       FROM TROPIC-TC
      tnShelfIndex                            FROM TROPIC-SHELF-MIB
      tnSlotIndex                             FROM TROPIC-SLOT-MIB
      tnCardModules, tnCardMIB                FROM TROPIC-GLOBAL-REG
      InterfaceIndexOrZero                    FROM IF-MIB;

  tnCardMibModule MODULE-IDENTITY
      LAST-UPDATED    "201510051200Z"
      ORGANIZATION    "Nokia"
      CONTACT-INFO    "Nokia
                       Postal: 600 March Rd.
                       Kanata, Ontario
                       Canada K2K 2E6

                       Phone: +1 613 591 3600
                       Fax:   +1 613 591 3680"

      DESCRIPTION "The card MIB."

      REVISION    "200804111200Z"
      DESCRIPTION "1) Updated the MIB file description.
                   2) Added remote inventory attributes to tnCardTable
                      (they exist in the slot table as well)."

      REVISION    "200805291200Z"
      DESCRIPTION "Updated the LED attribute applicability for the 1830
                   PSS-32."

      REVISION    "200806051200Z"
      DESCRIPTION "Added the FPGA content."

      REVISION    "200809191200Z"
      DESCRIPTION "Corrected the temperature threshold configurable range."

      REVISION    "200809241200Z"
      DESCRIPTION "Added tnCardFactoryID."

      REVISION    "200809261200Z"
      DESCRIPTION "Updated high temperature from 85 to 90."

      REVISION    "200902011200Z"
      DESCRIPTION "Added tnCardFunction."

      REVISION    "200902101200Z"
      DESCRIPTION "Removed tnCardFunction."

      REVISION    "200903311200Z"
      DESCRIPTION "Added the following to tnCardWidth:
                   tripleWidth(4)."

      REVISION    "201105191200Z"
      DESCRIPTION "Added the following to tnCardTable:
                   tnCardCapacity."

      REVISION    "201105231200Z"
      DESCRIPTION "Added DEFVAL for the following attribute:
                   tnCardTemperatureTolerance, 0."

      REVISION    "201207101200Z"
      DESCRIPTION "Added the following to tnCardTable:
                   tnCardLACPSystemPriority."

      REVISION    "201207171200Z"
      DESCRIPTION "Added the following to tnCardTable:
                   tnCardMaxPower."

      REVISION    "201209061200Z"
      DESCRIPTION "Marked the following as obsolete:
                   tnCardFPGATable."

      REVISION    "201305211200Z"
      DESCRIPTION "Marked the following as obsolete:
                   tnCardEvents."

      REVISION    "201308161200Z"
      DESCRIPTION "Added the following to tnCardTable:
                   tnCardEthOamCcmFaultMgntMode."

      REVISION    "201311181200Z"
      DESCRIPTION "Marked the following as obsolete:
                   tnCardOverride."

      REVISION    "201312151200Z"
      DESCRIPTION "Added the following to tnCardTable:
                   1) tnCardClkSwitch
                   2) tnCardRtrvClkSwitch."

      REVISION    "201312261200Z"
      DESCRIPTION "Added the following to tnCardTable:
                   tnCardWtClkMeasureValues."

      REVISION    "201402261200Z"
      DESCRIPTION "Added DEFVAL to attributes."

      REVISION    "201502061200Z"
      DESCRIPTION "Added the following to tnCardTable:
                   tnCardPower 
                   tnCardCurrent."
                   
      REVISION    "201503111200Z"
      DESCRIPTION "Added the following to tnCardTable:
                   tnCardUplinkAdminMode."

      REVISION    "201505291200Z"
      DESCRIPTION "Added unassigned(0) mode to tnCardUplinkAdminMode MIB.
                   and updated the DEFVAL to unassigned"

      REVISION    "201507301200Z"
      DESCRIPTION "Added the following to tnCardTable:
                   tnCardLoopbackNoServPort."

      REVISION    "201509301200Z"
      DESCRIPTION "Added the following to tnCardTable:
                   tnCardAlmProfName."

      REVISION    "201510051200Z"
      DESCRIPTION "Added the following to tnCardTable:
                   tnCardAlmProfEnvName."


      ::= { tnCardModules 1 }

  tnCardConf             OBJECT IDENTIFIER ::= { tnCardMIB 1 }
  tnCardGroups           OBJECT IDENTIFIER ::= { tnCardConf 1 }
  tnCardCompliances      OBJECT IDENTIFIER ::= { tnCardConf 2 }
  tnCardObjs             OBJECT IDENTIFIER ::= { tnCardMIB 2 }
  tnCardBasics           OBJECT IDENTIFIER ::= { tnCardObjs 1 }
--  obsolete
--  tnCardEvents           OBJECT IDENTIFIER ::= { tnCardMIB 3 }

--------------------------------------------------------------------------------
-- Type Definitions
--------------------------------------------------------------------------------

--------------------------------------------------------------------------------
-- Object Definitions
--------------------------------------------------------------------------------

--------------------------------------------------------------------------------
-- Generic Card Scalars
--------------------------------------------------------------------------------
    tnCardTotal OBJECT-TYPE
        SYNTAX         Integer32
        MAX-ACCESS     read-only
        STATUS         current
        DESCRIPTION    "The total number of card records allocated on
                        a 1696R/1830 NE."
        ::= { tnCardBasics 1 }

--------------------------------------------------------------------------------
-- Generic Card Table
--------------------------------------------------------------------------------
    tnCardTable OBJECT-TYPE
        SYNTAX         SEQUENCE OF TnCardEntry
        MAX-ACCESS     not-accessible
        STATUS         current
        DESCRIPTION    ""
        ::= { tnCardBasics 2 }

    tnCardEntry OBJECT-TYPE
        SYNTAX         TnCardEntry
        MAX-ACCESS     not-accessible
        STATUS         current
        DESCRIPTION    ""
        INDEX { tnShelfIndex,
                tnSlotIndex }
        ::= { tnCardTable 1 }

    TnCardEntry ::= SEQUENCE {
        tnCardName                    SnmpAdminString,
        tnCardDescr                   SnmpAdminString,
        tnCardCLEI                    TropicCardCLEI,
        tnCardHFD                     TropicCardHFD,
        tnCardSerialNumber            TropicCardSerialNumber,
        tnCardManufacturingPartNumber TropicCardManufacturingPartNumber,
        tnCardMarketingPartNumber     TropicCardMarketingPartNumber,
        tnCardSWGenericLoadName       TropicCardSWGenericLoadName,
--        obsolete
--        tnCardReset                   TropicResetType,
        tnCardHeight                  INTEGER,
        tnCardWidth                   INTEGER,
--        obsolete
--        tnCardResetReason             INTEGER,
        tnCardTemperature             Integer32,
        tnCardHighTemperatureThresh   Integer32,
        tnCardLowTemperatureThresh    Integer32,
        tnCardTemperatureTolerance    Unsigned32,
        tnCardStatusLEDColor          TropicLEDColorType,
        tnCardStatusLEDState          TropicLEDStateType,
        tnCardActivityLEDColor        TropicLEDColorType,
        tnCardActivityLEDState        TropicLEDStateType,
        tnCardCompanyID               SnmpAdminString,
        tnCardMnemonic                SnmpAdminString,
        tnCardSWPartNum               SnmpAdminString,
        tnCardDate                    SnmpAdminString,
        tnCardExtraData               SnmpAdminString,
--        obsolete
--        tnCardOverride                TruthValue,
        tnCardAnyPortsInService       TruthValue,
        tnCardLastBootedFwBundleVer   SnmpAdminString,
        tnCardNextFwBundleVer         SnmpAdminString,
        tnCardFactoryID               SnmpAdminString,
        tnCardCapacity                AluWdmCardCapacity,
        tnCardLACPSystemPriority      Unsigned32,
        tnCardMaxPower                Unsigned32,
        tnCardEthOamCcmFaultMgntMode  INTEGER,
        tnCardClkSwitch               AluWdmWtClkValues,
        tnCardRtrvClkSwitch           AluWdmWtClkValues,
        tnCardWtClkMeasureValues      OCTET STRING,
        tnCardPower                   Unsigned32,
        tnCardCurrent                 Unsigned32,
        tnCardUplinkAdminMode         INTEGER,
        tnCardLoopbackNoServPort      InterfaceIndexOrZero,
        tnCardAlmProfName             OCTET STRING,
        tnCardAlmProfEnvName          OCTET STRING
    }

    tnCardName OBJECT-TYPE
        SYNTAX         SnmpAdminString (SIZE(0..31))
        MAX-ACCESS     read-create
        STATUS         current
        DESCRIPTION    ""
        DEFVAL         { "" }
        ::= { tnCardEntry 1 }

    tnCardDescr OBJECT-TYPE
        SYNTAX         SnmpAdminString (SIZE(0..255))
        MAX-ACCESS     read-create
        STATUS         current
        DESCRIPTION    ""
        DEFVAL         { "" }
        ::= { tnCardEntry 2 }

    tnCardCLEI OBJECT-TYPE
        SYNTAX         TropicCardCLEI
        MAX-ACCESS     read-only
        STATUS         current
        DESCRIPTION    ""
        DEFVAL         { "" }
        ::= { tnCardEntry 3 }

    tnCardHFD OBJECT-TYPE
        SYNTAX         TropicCardHFD
        MAX-ACCESS     read-only
        STATUS         current
        DESCRIPTION    ""
        DEFVAL         { "" }
        ::= { tnCardEntry 4 }

    tnCardSerialNumber OBJECT-TYPE
        SYNTAX         TropicCardSerialNumber
        MAX-ACCESS     read-only
        STATUS         current
        DESCRIPTION    ""
        DEFVAL         { "" }
        ::= { tnCardEntry 5 }

    tnCardManufacturingPartNumber OBJECT-TYPE
        SYNTAX         TropicCardManufacturingPartNumber
        MAX-ACCESS     read-only
        STATUS         current
        DESCRIPTION    ""
        DEFVAL         { "" }
        ::= { tnCardEntry 6 }

    tnCardMarketingPartNumber OBJECT-TYPE
        SYNTAX         TropicCardMarketingPartNumber
        MAX-ACCESS     read-only
        STATUS         current
        DESCRIPTION    ""
        DEFVAL         { "" }
        ::= { tnCardEntry 7 }

    tnCardSWGenericLoadName OBJECT-TYPE
        SYNTAX         TropicCardSWGenericLoadName
        MAX-ACCESS     read-only
        STATUS         current
        DESCRIPTION    "The SW generic load currently active."
        DEFVAL         { "" }
        ::= { tnCardEntry 8 }

--    obsolete
--    tnCardReset OBJECT-TYPE ::= { tnCardEntry 9 }

    tnCardHeight OBJECT-TYPE
        SYNTAX         INTEGER{
                         unknown(1),
                         halfHeight(2),
                         fullHeight(3)
                       }
        MAX-ACCESS     read-only
        STATUS         current
        DESCRIPTION    ""
        ::= { tnCardEntry 10 }

    tnCardWidth OBJECT-TYPE
        SYNTAX         INTEGER{
                         unknown(1),
                         singleWidth(2),
                         doubleWidth(3),
                         tripleWidth(4)
                       }
        MAX-ACCESS     read-only
        STATUS         current
        DESCRIPTION    ""
        ::= { tnCardEntry 11 }

--    obsolete
--    tnCardResetReason OBJECT-TYPE ::= { tnCardEntry 12 }

    tnCardTemperature OBJECT-TYPE
        SYNTAX         Integer32
        UNITS          "Celsius"
        MAX-ACCESS     read-only
        STATUS         current
        DESCRIPTION    "The current temperature of the card."
        ::= { tnCardEntry 13 }

    tnCardHighTemperatureThresh OBJECT-TYPE
        SYNTAX         Integer32
        UNITS          "Celsius"
        MAX-ACCESS     read-create
        STATUS         current
        DESCRIPTION    "The high temperature threshold of the card.

                        Current configurable range:
                        1696R:  -5 to 60
                        1830:   -5 to 90."
        DEFVAL         { 90 }
        ::= { tnCardEntry 14 }

    tnCardLowTemperatureThresh OBJECT-TYPE
        SYNTAX         Integer32
        UNITS          "Celsius"
        MAX-ACCESS     read-create
        STATUS         current
        DESCRIPTION    "The low temperature threshold of the card.

                        Current configurable range:
                        1696R:   -5 to 60
                        1830:   -45 to 90."
        DEFVAL         { -5 }
        ::= { tnCardEntry 15 }

    tnCardTemperatureTolerance OBJECT-TYPE
        SYNTAX         Unsigned32
        UNITS          "Celsius"
        MAX-ACCESS     read-create
        STATUS         current
        DESCRIPTION    "The temperature tolerance of the card, applied
                        to the card's high and low temperature thresholds.

                        Current configurable range: 0 to 10."
        DEFVAL         { 3 }
        ::= { tnCardEntry 16 }

    tnCardStatusLEDColor OBJECT-TYPE
        SYNTAX         TropicLEDColorType
        MAX-ACCESS     read-only
        STATUS         current
        DESCRIPTION    "The color of the status LED.
                        For the 1830 PSS-32, not applicable to the DCM
                        and SFD cards."
        ::= { tnCardEntry 17 }

    tnCardStatusLEDState OBJECT-TYPE
        SYNTAX         TropicLEDStateType
        MAX-ACCESS     read-only
        STATUS         current
        DESCRIPTION    "The state of the status LED.
                        For the 1830 PSS-32, not applicable to the DCM
                        and SFD cards."
        ::= { tnCardEntry 18 }

    tnCardActivityLEDColor OBJECT-TYPE
        SYNTAX         TropicLEDColorType
        MAX-ACCESS     read-only
        STATUS         current
        DESCRIPTION    "The color of the activity LED.
                        For the 1830 PSS-32, only applicable to the EC
                        card."
        ::= { tnCardEntry 19 }

    tnCardActivityLEDState OBJECT-TYPE
        SYNTAX         TropicLEDStateType
        MAX-ACCESS     read-only
        STATUS         current
        DESCRIPTION    "The state of the activity LED.
                        For the 1830 PSS-32, only applicable to the EC
                        card."
        ::= { tnCardEntry 20 }

    tnCardCompanyID OBJECT-TYPE
        SYNTAX         SnmpAdminString
        MAX-ACCESS     read-only
        STATUS         current
        DESCRIPTION    ""
        DEFVAL         { "" }
        ::= { tnCardEntry 21 }

    tnCardMnemonic OBJECT-TYPE
        SYNTAX         SnmpAdminString
        MAX-ACCESS     read-only
        STATUS         current
        DESCRIPTION    ""
        DEFVAL         { "" }
        ::= { tnCardEntry 22 }

    tnCardSWPartNum OBJECT-TYPE
        SYNTAX         SnmpAdminString
        MAX-ACCESS     read-only
        STATUS         current
        DESCRIPTION    ""
        DEFVAL         { "" }
        ::= { tnCardEntry 23 }

    tnCardDate OBJECT-TYPE
        SYNTAX         SnmpAdminString
        MAX-ACCESS     read-only
        STATUS         current
        DESCRIPTION    ""
        DEFVAL         { "" }
        ::= { tnCardEntry 24 }

    tnCardExtraData OBJECT-TYPE
        SYNTAX         SnmpAdminString
        MAX-ACCESS     read-only
        STATUS         current
        DESCRIPTION    ""
        DEFVAL         { "" }
        ::= { tnCardEntry 25 }

--    obsolete
--    tnCardOverride OBJECT-TYPE ::= { tnCardEntry 26 }

    tnCardAnyPortsInService OBJECT-TYPE
        SYNTAX         TruthValue
        MAX-ACCESS     read-create
        STATUS         current
        DESCRIPTION    ""
        ::= { tnCardEntry 27 }

    tnCardLastBootedFwBundleVer OBJECT-TYPE
        SYNTAX         SnmpAdminString
        MAX-ACCESS     read-create
        STATUS         current
        DESCRIPTION    ""
        DEFVAL         { "" }
        ::= { tnCardEntry 28 }

    tnCardNextFwBundleVer OBJECT-TYPE
        SYNTAX         SnmpAdminString
        MAX-ACCESS     read-only
        STATUS         current
        DESCRIPTION    ""
        DEFVAL         { "" }
        ::= { tnCardEntry 29 }

    tnCardFactoryID OBJECT-TYPE
        SYNTAX         SnmpAdminString
        MAX-ACCESS     read-only
        STATUS         current
        DESCRIPTION    ""
        DEFVAL         { "" }
        ::= { tnCardEntry 30 }

    tnCardCapacity OBJECT-TYPE
        SYNTAX         AluWdmCardCapacity
        MAX-ACCESS     read-create
        STATUS         current
        DESCRIPTION    "The capacity of the storage medium in the slot."
        DEFVAL         { unknownCapacity }
        ::= { tnCardEntry 31 }

    tnCardLACPSystemPriority OBJECT-TYPE
        SYNTAX         Unsigned32 (1..65535)
        MAX-ACCESS     read-create
        STATUS         current
        DESCRIPTION    "tnCardLACPSystemPriority is the Link Aggregation
                        Control Protocol (LACP) system priority which is
                        combined with the system MAC address to make up
                        a unique system ID that is used by LACP in
                        communications with LACP peer systems on Link
                        Aggregation (LAG) ports."
        DEFVAL         { 32768 }
        ::= { tnCardEntry 32 }

    tnCardMaxPower OBJECT-TYPE
        SYNTAX         Unsigned32
        UNITS          "milli-Watts"
        MAX-ACCESS     read-only
        STATUS         current
        DESCRIPTION    "P sub 0, P sub 50 and P sub 100 (percent
                        utilization of transmission function) provided
                        for ATIS TEER calculation.  These measurements
                        are to be made under the conditions provided in
                        ATIS-0600015-2009:

                        Temperature:  25 deg C +/- 3 deg C (77 deg F +/- 5 deg F)
                        Humidity:  Relative humidity between 30% and 75%
                        Barometric Pressure:  Between 1020 and 812 mbar.

                        Current range: 0 to 1,000,000."
        ::= { tnCardEntry 33 }

    tnCardEthOamCcmFaultMgntMode OBJECT-TYPE
        SYNTAX         INTEGER{
                         ieee(1),
                         itu(2)
                       }
        MAX-ACCESS     read-create
        STATUS         current
        DESCRIPTION    "The Ethernet OAM fault management compliancy of the card.

                        Current configurable modes:
                        ieee:  IEEE 802.1ag compliant
                        itu:   ITU-T G.8021 compliant."
        DEFVAL         { ieee }
        ::= { tnCardEntry 34 }

    tnCardClkSwitch    OBJECT-TYPE
        SYNTAX         AluWdmWtClkValues
        MAX-ACCESS     read-create
        STATUS         current
        DESCRIPTION    "Clock Switch on pack level."
        DEFVAL         { wtClkAuto }
        ::= { tnCardEntry 35 }

    tnCardRtrvClkSwitch  OBJECT-TYPE
        SYNTAX         AluWdmWtClkValues
        MAX-ACCESS     read-only
        STATUS         current
        DESCRIPTION    "Retrieve Clock Selection on pack level."
        ::= { tnCardEntry 36 }

    tnCardWtClkMeasureValues OBJECT-TYPE
        SYNTAX         OCTET STRING (SIZE(0..100))
        MAX-ACCESS     read-only
        STATUS         current
        DESCRIPTION    "Retrieve PF Wt clock measurements."
        DEFVAL         { "" }
        ::= { tnCardEntry 37 }

    tnCardPower OBJECT-TYPE
        SYNTAX         Unsigned32
        UNITS          "milli-Watts"
        MAX-ACCESS     read-only
        STATUS         current
        DESCRIPTION    "The monitored card power consumption value"
        ::= { tnCardEntry 38 }

    tnCardCurrent OBJECT-TYPE
        SYNTAX         Unsigned32
        UNITS          "milli-Amperes"
        MAX-ACCESS     read-only
        STATUS         current
        DESCRIPTION    "The monitored card current value"
        ::= { tnCardEntry 39 }

    tnCardUplinkAdminMode OBJECT-TYPE
        SYNTAX         INTEGER{
                         unassigned    (0),
                         network       (1),
                         accessUplink  (2)
                       }
        MAX-ACCESS     read-create
        STATUS         current
        DESCRIPTION    "Each card can be configured in one of two administrative
                        modes. In network mode the system uses MPLS-TP to 
                        provide service transport, and in access-uplink mode the
                        system uses Ethernet QinQ (802.1ad) switching.

                        NOTE: to change the administrative mode, the mode must
                        be unassigned. To set the mode to unassigned, the slot
                        must first be set to empty then back to the previously
                        configure pack type. "

        DEFVAL         { unassigned }
        ::= { tnCardEntry 40 }

   tnCardLoopbackNoServPort OBJECT-TYPE
        SYNTAX          InterfaceIndexOrZero
        MAX-ACCESS      read-write
        STATUS          current
        DESCRIPTION     "Second loopback port used for internal sap creation,
                         which is needed for Mac address swapping.
                         0 indicates the port is undefined."
        DEFVAL          { 0 }
        ::= { tnCardEntry 41 }

    tnCardAlmProfName OBJECT-TYPE
        SYNTAX         OCTET STRING (SIZE(1..40))
        MAX-ACCESS     read-create
        STATUS         current
        DESCRIPTION    ""
        ::= { tnCardEntry 42 }

    tnCardAlmProfEnvName OBJECT-TYPE
        SYNTAX         OCTET STRING (SIZE(1..40))
        MAX-ACCESS     read-create
        STATUS         current
        DESCRIPTION    ""
        ::= { tnCardEntry 43 }

--------------------------------------------------------------------------------
-- Generic Card Assembly Table
--------------------------------------------------------------------------------
    tnCardAssemblyTable OBJECT-TYPE
        SYNTAX         SEQUENCE OF TnCardAssemblyEntry
        MAX-ACCESS     not-accessible
        STATUS         current
        DESCRIPTION    ""
        ::= { tnCardBasics 3 }

    tnCardAssemblyEntry OBJECT-TYPE
        SYNTAX         TnCardAssemblyEntry
        MAX-ACCESS     not-accessible
        STATUS         current
        DESCRIPTION    ""
        INDEX { tnShelfIndex,
                tnSlotIndex,
                tnCardAssemblyIndex }
        ::= { tnCardAssemblyTable 1 }

    TnCardAssemblyEntry ::= SEQUENCE {
        tnCardAssemblyIndex                   Integer32,
        tnCardAssemblyName                    SnmpAdminString,
        tnCardAssemblyCLEI                    TropicCardCLEI,
        tnCardAssemblyHFD                     TropicCardHFD,
        tnCardAssemblySerialNumber            TropicCardSerialNumber,
        tnCardAssemblyManufacturingPartNumber TropicCardManufacturingPartNumber,
        tnCardAssemblyMarketingPartNumber     TropicCardMarketingPartNumber
    }

    tnCardAssemblyIndex OBJECT-TYPE
        SYNTAX         Integer32 (1..256)
        MAX-ACCESS     not-accessible
        STATUS         current
        DESCRIPTION    ""
        ::= { tnCardAssemblyEntry 1 }

    tnCardAssemblyName OBJECT-TYPE
        SYNTAX         SnmpAdminString (SIZE(0..31))
        MAX-ACCESS     read-only
        STATUS         current
        DESCRIPTION    ""
        ::= { tnCardAssemblyEntry 2 }

    tnCardAssemblyCLEI OBJECT-TYPE
        SYNTAX         TropicCardCLEI
        MAX-ACCESS     read-only
        STATUS         current
        DESCRIPTION    ""
        ::= { tnCardAssemblyEntry 3 }

    tnCardAssemblyHFD OBJECT-TYPE
        SYNTAX         TropicCardHFD
        MAX-ACCESS     read-only
        STATUS         current
        DESCRIPTION    ""
        ::= { tnCardAssemblyEntry 4 }

    tnCardAssemblySerialNumber OBJECT-TYPE
        SYNTAX         TropicCardSerialNumber
        MAX-ACCESS     read-only
        STATUS         current
        DESCRIPTION    ""
        ::= { tnCardAssemblyEntry 5 }

    tnCardAssemblyManufacturingPartNumber OBJECT-TYPE
        SYNTAX         TropicCardManufacturingPartNumber
        MAX-ACCESS     read-only
        STATUS         current
        DESCRIPTION    ""
        ::= { tnCardAssemblyEntry 6 }

    tnCardAssemblyMarketingPartNumber OBJECT-TYPE
        SYNTAX         TropicCardMarketingPartNumber
        MAX-ACCESS     read-only
        STATUS         current
        DESCRIPTION    ""
        ::= { tnCardAssemblyEntry 7 }

--------------------------------------------------------------------------------
-- Card FPGA Table
--------------------------------------------------------------------------------
--    obsolete
--    tnCardFPGATable OBJECT-TYPE ::= { tnCardBasics 4 }

--------------------------------------------------------------------------------
-- Conformance Group Definitions
--------------------------------------------------------------------------------
    tnCardScalarsGroup OBJECT-GROUP
        OBJECTS {
            tnCardTotal
        }
        STATUS         current
        DESCRIPTION    ""
        ::= { tnCardGroups 1 }

    tnCardTableGroup OBJECT-GROUP
        OBJECTS {
            tnCardName,
            tnCardDescr,
            tnCardCLEI,
            tnCardHFD,
            tnCardSerialNumber,
            tnCardManufacturingPartNumber,
            tnCardMarketingPartNumber,
            tnCardSWGenericLoadName,
--            obsolete
--            tnCardReset,
            tnCardHeight,
            tnCardWidth,
--            obsolete
--            tnCardResetReason,
            tnCardTemperature,
            tnCardHighTemperatureThresh,
            tnCardLowTemperatureThresh,
            tnCardTemperatureTolerance,
            tnCardStatusLEDColor,
            tnCardStatusLEDState,
            tnCardActivityLEDColor,
            tnCardActivityLEDState,
            tnCardCompanyID,
            tnCardMnemonic,
            tnCardSWPartNum,
            tnCardDate,
            tnCardExtraData,
--            obsolete
--            tnCardOverride,
            tnCardAnyPortsInService,
            tnCardLastBootedFwBundleVer,
            tnCardNextFwBundleVer,
            tnCardFactoryID,
            tnCardCapacity,
            tnCardLACPSystemPriority,
            tnCardMaxPower,
            tnCardEthOamCcmFaultMgntMode,
            tnCardClkSwitch,
            tnCardRtrvClkSwitch,
            tnCardWtClkMeasureValues,
            tnCardPower,
            tnCardCurrent,
            tnCardUplinkAdminMode,
            tnCardLoopbackNoServPort,
            tnCardAlmProfName,
            tnCardAlmProfEnvName
        }
        STATUS         current
        DESCRIPTION    ""
        ::= { tnCardGroups 2 }

    tnCardAssemblyTableGroup OBJECT-GROUP
        OBJECTS {
            tnCardAssemblyName,
            tnCardAssemblyCLEI,
            tnCardAssemblyHFD,
            tnCardAssemblySerialNumber,
            tnCardAssemblyManufacturingPartNumber,
            tnCardAssemblyMarketingPartNumber
        }
        STATUS         current
        DESCRIPTION    ""
        ::= { tnCardGroups 3 }

--    obsolete
--    tnCardFPGATableGroup OBJECT-GROUP ::= { tnCardGroups 4 }

--------------------------------------------------------------------------------
-- Compliance Statements (mandatory)
--------------------------------------------------------------------------------
    tnCardCompliance MODULE-COMPLIANCE
        STATUS         current
        DESCRIPTION    ""
        MODULE
        MANDATORY-GROUPS {
            tnCardScalarsGroup,
            tnCardTableGroup,
            tnCardAssemblyTableGroup
--            obsolete
--            tnCardFPGATableGroup,
        }
        ::= { tnCardCompliances 1 }

END -- DEFINITION OF TROPIC-CARD-MIB
