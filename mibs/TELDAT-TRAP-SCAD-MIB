-- file automatically created


TELDAT-TRAP-SCAD-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


scadTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SCAD event subsystem."
    REVISION "201401200930Z"
    DESCRIPTION "Initial implementation"
        ::= { telEventTraps 178 }


scadEventsGroup	OBJECT IDENTIFIER	::= { scadTrapsMIB 1 }

scadNotifications	OBJECT IDENTIFIER	::= { scadTrapsMIB 2 }
scadNotificationsPrefix	OBJECT IDENTIFIER	::= { scadNotifications 0 }

scadEventObjects1 OBJECT-IDENTITY
    STATUS current
    DESCRIPTION
        "Event SCAD.1
        Data has been received from Serial Terminal."
    ::= { scadEventsGroup 1 }

scad1_bytes_number OBJECT-TYPE
    SYNTAX Integer32
    MAX-ACCESS accessible-for-notify
    STATUS current
    DESCRIPTION
        "Parameter 'bytes_number' in event SCAD.1"
    ::= { scadEventObjects1 1 }

scad1_interface OBJECT-TYPE
    SYNTAX DisplayString
    MAX-ACCESS accessible-for-notify
    STATUS current
    DESCRIPTION
        "Parameter 'interface' in event SCAD.1"
    ::= { scadEventObjects1 2 }

scadEventObjects2 OBJECT-IDENTITY
    STATUS current
    DESCRIPTION
        "Event SCAD.2
        One OK Message has been received from Serial Terminal."
    ::= { scadEventsGroup 2 }

scad2_coment OBJECT-TYPE
    SYNTAX DisplayString
    MAX-ACCESS accessible-for-notify
    STATUS current
    DESCRIPTION
        "Parameter 'coment' in event SCAD.2"
    ::= { scadEventObjects2 1 }

scad2_serrial_address OBJECT-TYPE
    SYNTAX Integer32
    MAX-ACCESS accessible-for-notify
    STATUS current
    DESCRIPTION
        "Parameter 'serrial_address' in event SCAD.2"
    ::= { scadEventObjects2 2 }

scad2_bytes_number OBJECT-TYPE
    SYNTAX Integer32
    MAX-ACCESS accessible-for-notify
    STATUS current
    DESCRIPTION
        "Parameter 'bytes_number' in event SCAD.2"
    ::= { scadEventObjects2 3 }

scad2_interface OBJECT-TYPE
    SYNTAX DisplayString
    MAX-ACCESS accessible-for-notify
    STATUS current
    DESCRIPTION
        "Parameter 'interface' in event SCAD.2"
    ::= { scadEventObjects2 4 }

scad2_state OBJECT-TYPE
    SYNTAX Integer32
    MAX-ACCESS accessible-for-notify
    STATUS current
    DESCRIPTION
        "Parameter 'state' in event SCAD.2"
    ::= { scadEventObjects2 5 }

scadEventObjects3 OBJECT-IDENTITY
    STATUS current
    DESCRIPTION
        "Event SCAD.3
        A Message with bad address has been received from Serial Terminal."
    ::= { scadEventsGroup 3 }

scad3_bad_addr OBJECT-TYPE
    SYNTAX Integer32
    MAX-ACCESS accessible-for-notify
    STATUS current
    DESCRIPTION
        "Parameter 'bad_addr' in event SCAD.3"
    ::= { scadEventObjects3 1 }

scad3_interface OBJECT-TYPE
    SYNTAX DisplayString
    MAX-ACCESS accessible-for-notify
    STATUS current
    DESCRIPTION
        "Parameter 'interface' in event SCAD.3"
    ::= { scadEventObjects3 2 }

scadEventObjects4 OBJECT-IDENTITY
    STATUS current
    DESCRIPTION
        "Event SCAD.4
        One Bad Message has been received from Serial Terminal."
    ::= { scadEventsGroup 4 }

scad4_cause OBJECT-TYPE
    SYNTAX DisplayString
    MAX-ACCESS accessible-for-notify
    STATUS current
    DESCRIPTION
        "Parameter 'cause' in event SCAD.4"
    ::= { scadEventObjects4 1 }

scad4_interface OBJECT-TYPE
    SYNTAX DisplayString
    MAX-ACCESS accessible-for-notify
    STATUS current
    DESCRIPTION
        "Parameter 'interface' in event SCAD.4"
    ::= { scadEventObjects4 2 }

scad4_state OBJECT-TYPE
    SYNTAX Integer32
    MAX-ACCESS accessible-for-notify
    STATUS current
    DESCRIPTION
        "Parameter 'state' in event SCAD.4"
    ::= { scadEventObjects4 3 }

scadEventObjects5 OBJECT-IDENTITY
    STATUS current
    DESCRIPTION
        "Event SCAD.5
        A message with LRC/CRC error has been received from Serial Terminal."
    ::= { scadEventsGroup 5 }

scad5_interface OBJECT-TYPE
    SYNTAX DisplayString
    MAX-ACCESS accessible-for-notify
    STATUS current
    DESCRIPTION
        "Parameter 'interface' in event SCAD.5"
    ::= { scadEventObjects5 1 }

scad5_state OBJECT-TYPE
    SYNTAX Integer32
    MAX-ACCESS accessible-for-notify
    STATUS current
    DESCRIPTION
        "Parameter 'state' in event SCAD.5"
    ::= { scadEventObjects5 2 }

scadEventObjects6 OBJECT-IDENTITY
    STATUS current
    DESCRIPTION
        "Event SCAD.6
        A message with error has been received from Remote."
    ::= { scadEventsGroup 6 }

scad6_error_type OBJECT-TYPE
    SYNTAX DisplayString
    MAX-ACCESS accessible-for-notify
    STATUS current
    DESCRIPTION
        "Parameter 'error_type' in event SCAD.6"
    ::= { scadEventObjects6 1 }

scad6_interface OBJECT-TYPE
    SYNTAX DisplayString
    MAX-ACCESS accessible-for-notify
    STATUS current
    DESCRIPTION
        "Parameter 'interface' in event SCAD.6"
    ::= { scadEventObjects6 2 }

scad6_state OBJECT-TYPE
    SYNTAX Integer32
    MAX-ACCESS accessible-for-notify
    STATUS current
    DESCRIPTION
        "Parameter 'state' in event SCAD.6"
    ::= { scadEventObjects6 3 }

scadEventObjects7 OBJECT-IDENTITY
    STATUS current
    DESCRIPTION
        "Event SCAD.7
        Addres received from Serial Terminal is not included in configuration
        registers list."
    ::= { scadEventsGroup 7 }

scad7_serial_address OBJECT-TYPE
    SYNTAX Integer32
    MAX-ACCESS accessible-for-notify
    STATUS current
    DESCRIPTION
        "Parameter 'serial_address' in event SCAD.7"
    ::= { scadEventObjects7 1 }

scad7_interface OBJECT-TYPE
    SYNTAX DisplayString
    MAX-ACCESS accessible-for-notify
    STATUS current
    DESCRIPTION
        "Parameter 'interface' in event SCAD.7"
    ::= { scadEventObjects7 2 }

scadEventObjects8 OBJECT-IDENTITY
    STATUS current
    DESCRIPTION
        "Event SCAD.8
        It's trying the connection against remote IP and P port."
    ::= { scadEventsGroup 8 }

scad8_serial_address OBJECT-TYPE
    SYNTAX Integer32
    MAX-ACCESS accessible-for-notify
    STATUS current
    DESCRIPTION
        "Parameter 'serial_address' in event SCAD.8"
    ::= { scadEventObjects8 1 }

scad8_rtu_ip_address OBJECT-TYPE
    SYNTAX IpAddress
    MAX-ACCESS accessible-for-notify
    STATUS current
    DESCRIPTION
        "Parameter 'rtu_ip_address' in event SCAD.8"
    ::= { scadEventObjects8 2 }

scad8_port OBJECT-TYPE
    SYNTAX Integer32
    MAX-ACCESS accessible-for-notify
    STATUS current
    DESCRIPTION
        "Parameter 'port' in event SCAD.8"
    ::= { scadEventObjects8 3 }

scad8_interface OBJECT-TYPE
    SYNTAX DisplayString
    MAX-ACCESS accessible-for-notify
    STATUS current
    DESCRIPTION
        "Parameter 'interface' in event SCAD.8"
    ::= { scadEventObjects8 4 }

scadEventObjects9 OBJECT-IDENTITY
    STATUS current
    DESCRIPTION
        "Event SCAD.9
        The Transfer has been completed successfully."
    ::= { scadEventsGroup 9 }

scad9_interface OBJECT-TYPE
    SYNTAX DisplayString
    MAX-ACCESS accessible-for-notify
    STATUS current
    DESCRIPTION
        "Parameter 'interface' in event SCAD.9"
    ::= { scadEventObjects9 1 }

scadEventObjects10 OBJECT-IDENTITY
    STATUS current
    DESCRIPTION
        "Event SCAD.10
        Trying to send message to Remote end."
    ::= { scadEventsGroup 10 }

scad10_bytes OBJECT-TYPE
    SYNTAX Integer32
    MAX-ACCESS accessible-for-notify
    STATUS current
    DESCRIPTION
        "Parameter 'bytes' in event SCAD.10"
    ::= { scadEventObjects10 1 }

scad10_interface OBJECT-TYPE
    SYNTAX DisplayString
    MAX-ACCESS accessible-for-notify
    STATUS current
    DESCRIPTION
        "Parameter 'interface' in event SCAD.10"
    ::= { scadEventObjects10 2 }

scadEventObjects11 OBJECT-IDENTITY
    STATUS current
    DESCRIPTION
        "Event SCAD.11
        A message from Remote end has been received."
    ::= { scadEventsGroup 11 }

scad11_message_type OBJECT-TYPE
    SYNTAX Integer32
    MAX-ACCESS accessible-for-notify
    STATUS current
    DESCRIPTION
        "Parameter 'message_type' in event SCAD.11"
    ::= { scadEventObjects11 1 }

scad11_bytes OBJECT-TYPE
    SYNTAX Integer32
    MAX-ACCESS accessible-for-notify
    STATUS current
    DESCRIPTION
        "Parameter 'bytes' in event SCAD.11"
    ::= { scadEventObjects11 2 }

scad11_interface OBJECT-TYPE
    SYNTAX DisplayString
    MAX-ACCESS accessible-for-notify
    STATUS current
    DESCRIPTION
        "Parameter 'interface' in event SCAD.11"
    ::= { scadEventObjects11 3 }

scad11_state OBJECT-TYPE
    SYNTAX Integer32
    MAX-ACCESS accessible-for-notify
    STATUS current
    DESCRIPTION
        "Parameter 'state' in event SCAD.11"
    ::= { scadEventObjects11 4 }

scadEventObjects12 OBJECT-IDENTITY
    STATUS current
    DESCRIPTION
        "Event SCAD.12
        A TCP Packet has been received."
    ::= { scadEventsGroup 12 }

scad12_message_type OBJECT-TYPE
    SYNTAX DisplayString
    MAX-ACCESS accessible-for-notify
    STATUS current
    DESCRIPTION
        "Parameter 'message_type' in event SCAD.12"
    ::= { scadEventObjects12 1 }

scad12_bytes OBJECT-TYPE
    SYNTAX Integer32
    MAX-ACCESS accessible-for-notify
    STATUS current
    DESCRIPTION
        "Parameter 'bytes' in event SCAD.12"
    ::= { scadEventObjects12 2 }

scad12_foreign_host OBJECT-TYPE
    SYNTAX IpAddress
    MAX-ACCESS accessible-for-notify
    STATUS current
    DESCRIPTION
        "Parameter 'foreign_host' in event SCAD.12"
    ::= { scadEventObjects12 3 }

scad12_remote_port OBJECT-TYPE
    SYNTAX Integer32
    MAX-ACCESS accessible-for-notify
    STATUS current
    DESCRIPTION
        "Parameter 'remote_port' in event SCAD.12"
    ::= { scadEventObjects12 4 }

scadEventObjects13 OBJECT-IDENTITY
    STATUS current
    DESCRIPTION
        "Event SCAD.13
        The TCP session has been closed."
    ::= { scadEventsGroup 13 }

scad13_foreign_host OBJECT-TYPE
    SYNTAX IpAddress
    MAX-ACCESS accessible-for-notify
    STATUS current
    DESCRIPTION
        "Parameter 'foreign_host' in event SCAD.13"
    ::= { scadEventObjects13 1 }

scad13_remote_port OBJECT-TYPE
    SYNTAX Integer32
    MAX-ACCESS accessible-for-notify
    STATUS current
    DESCRIPTION
        "Parameter 'remote_port' in event SCAD.13"
    ::= { scadEventObjects13 2 }

scadEventObjects14 OBJECT-IDENTITY
    STATUS current
    DESCRIPTION
        "Event SCAD.14
        The TCP session has been closed by the Remote end."
    ::= { scadEventsGroup 14 }

scad14_foreign_host OBJECT-TYPE
    SYNTAX IpAddress
    MAX-ACCESS accessible-for-notify
    STATUS current
    DESCRIPTION
        "Parameter 'foreign_host' in event SCAD.14"
    ::= { scadEventObjects14 1 }

scad14_remote_port OBJECT-TYPE
    SYNTAX Integer32
    MAX-ACCESS accessible-for-notify
    STATUS current
    DESCRIPTION
        "Parameter 'remote_port' in event SCAD.14"
    ::= { scadEventObjects14 2 }

scadEventObjects15 OBJECT-IDENTITY
    STATUS current
    DESCRIPTION
        "Event SCAD.15
        The TCP session has been opened by the Remote end."
    ::= { scadEventsGroup 15 }

scad15_remote_ip OBJECT-TYPE
    SYNTAX IpAddress
    MAX-ACCESS accessible-for-notify
    STATUS current
    DESCRIPTION
        "Parameter 'remote_ip' in event SCAD.15"
    ::= { scadEventObjects15 1 }

scad15_remote_port OBJECT-TYPE
    SYNTAX Integer32
    MAX-ACCESS accessible-for-notify
    STATUS current
    DESCRIPTION
        "Parameter 'remote_port' in event SCAD.15"
    ::= { scadEventObjects15 2 }

scadEventObjects16 OBJECT-IDENTITY
    STATUS current
    DESCRIPTION
        "Event SCAD.16
        A Message has been transmitted to Serial Terminal."
    ::= { scadEventsGroup 16 }

scad16_address OBJECT-TYPE
    SYNTAX Integer32
    MAX-ACCESS accessible-for-notify
    STATUS current
    DESCRIPTION
        "Parameter 'address' in event SCAD.16"
    ::= { scadEventObjects16 1 }

scad16_bytes OBJECT-TYPE
    SYNTAX Integer32
    MAX-ACCESS accessible-for-notify
    STATUS current
    DESCRIPTION
        "Parameter 'bytes' in event SCAD.16"
    ::= { scadEventObjects16 2 }

scad16_interface OBJECT-TYPE
    SYNTAX DisplayString
    MAX-ACCESS accessible-for-notify
    STATUS current
    DESCRIPTION
        "Parameter 'interface' in event SCAD.16"
    ::= { scadEventObjects16 3 }

scad16_state OBJECT-TYPE
    SYNTAX Integer32
    MAX-ACCESS accessible-for-notify
    STATUS current
    DESCRIPTION
        "Parameter 'state' in event SCAD.16"
    ::= { scadEventObjects16 4 }

scadEventObjects17 OBJECT-IDENTITY
    STATUS current
    DESCRIPTION
        "Event SCAD.17
        A change ON/OFF has been detected in Serial Control Signal Input."
    ::= { scadEventsGroup 17 }

scad17_message_type OBJECT-TYPE
    SYNTAX DisplayString
    MAX-ACCESS accessible-for-notify
    STATUS current
    DESCRIPTION
        "Parameter 'message_type' in event SCAD.17"
    ::= { scadEventObjects17 1 }

scad17_interface OBJECT-TYPE
    SYNTAX DisplayString
    MAX-ACCESS accessible-for-notify
    STATUS current
    DESCRIPTION
        "Parameter 'interface' in event SCAD.17"
    ::= { scadEventObjects17 2 }

scad17_state OBJECT-TYPE
    SYNTAX Integer32
    MAX-ACCESS accessible-for-notify
    STATUS current
    DESCRIPTION
        "Parameter 'state' in event SCAD.17"
    ::= { scadEventObjects17 3 }

scadEventObjects18 OBJECT-IDENTITY
    STATUS current
    DESCRIPTION
        "Event SCAD.18
        Timeout has occur waiting data."
    ::= { scadEventsGroup 18 }

scad18_site OBJECT-TYPE
    SYNTAX DisplayString
    MAX-ACCESS accessible-for-notify
    STATUS current
    DESCRIPTION
        "Parameter 'site' in event SCAD.18"
    ::= { scadEventObjects18 1 }

scad18_interface OBJECT-TYPE
    SYNTAX DisplayString
    MAX-ACCESS accessible-for-notify
    STATUS current
    DESCRIPTION
        "Parameter 'interface' in event SCAD.18"
    ::= { scadEventObjects18 2 }

scad18_state OBJECT-TYPE
    SYNTAX Integer32
    MAX-ACCESS accessible-for-notify
    STATUS current
    DESCRIPTION
        "Parameter 'state' in event SCAD.18"
    ::= { scadEventObjects18 3 }

scadEventObjects19 OBJECT-IDENTITY
    STATUS current
    DESCRIPTION
        "Event SCAD.19
        A packet was lost, due TCP Tx overrun error."
    ::= { scadEventsGroup 19 }

scad19_interface OBJECT-TYPE
    SYNTAX DisplayString
    MAX-ACCESS accessible-for-notify
    STATUS current
    DESCRIPTION
        "Parameter 'interface' in event SCAD.19"
    ::= { scadEventObjects19 1 }

scad19_state OBJECT-TYPE
    SYNTAX Integer32
    MAX-ACCESS accessible-for-notify
    STATUS current
    DESCRIPTION
        "Parameter 'state' in event SCAD.19"
    ::= { scadEventObjects19 2 }

scadEventObjects20 OBJECT-IDENTITY
    STATUS current
    DESCRIPTION
        "Event SCAD.20
        A packet was lost, due TCP is closed."
    ::= { scadEventsGroup 20 }

scad20_interface OBJECT-TYPE
    SYNTAX DisplayString
    MAX-ACCESS accessible-for-notify
    STATUS current
    DESCRIPTION
        "Parameter 'interface' in event SCAD.20"
    ::= { scadEventObjects20 1 }

scad20_state OBJECT-TYPE
    SYNTAX Integer32
    MAX-ACCESS accessible-for-notify
    STATUS current
    DESCRIPTION
        "Parameter 'state' in event SCAD.20"
    ::= { scadEventObjects20 2 }

scadEventObjects21 OBJECT-IDENTITY
    STATUS current
    DESCRIPTION
        "Event SCAD.21
        The transfer has been wrong against specified NA and IP addr."
    ::= { scadEventsGroup 21 }

scad21_na OBJECT-TYPE
    SYNTAX Integer32
    MAX-ACCESS accessible-for-notify
    STATUS current
    DESCRIPTION
        "Parameter 'na' in event SCAD.21"
    ::= { scadEventObjects21 1 }

scad21_ip_host_address OBJECT-TYPE
    SYNTAX IpAddress
    MAX-ACCESS accessible-for-notify
    STATUS current
    DESCRIPTION
        "Parameter 'ip_host_address' in event SCAD.21"
    ::= { scadEventObjects21 2 }

scad21_cause OBJECT-TYPE
    SYNTAX Integer32
    MAX-ACCESS accessible-for-notify
    STATUS current
    DESCRIPTION
        "Parameter 'cause' in event SCAD.21"
    ::= { scadEventObjects21 3 }

scad21_interface OBJECT-TYPE
    SYNTAX DisplayString
    MAX-ACCESS accessible-for-notify
    STATUS current
    DESCRIPTION
        "Parameter 'interface' in event SCAD.21"
    ::= { scadEventObjects21 4 }

scadEventObjects22 OBJECT-IDENTITY
    STATUS current
    DESCRIPTION
        "Event SCAD.22
        TCP generic event was occurred."
    ::= { scadEventsGroup 22 }

scad22_event OBJECT-TYPE
    SYNTAX DisplayString
    MAX-ACCESS accessible-for-notify
    STATUS current
    DESCRIPTION
        "Parameter 'event' in event SCAD.22"
    ::= { scadEventObjects22 1 }

scad22_ip OBJECT-TYPE
    SYNTAX IpAddress
    MAX-ACCESS accessible-for-notify
    STATUS current
    DESCRIPTION
        "Parameter 'ip' in event SCAD.22"
    ::= { scadEventObjects22 2 }

scad22_port OBJECT-TYPE
    SYNTAX Integer32
    MAX-ACCESS accessible-for-notify
    STATUS current
    DESCRIPTION
        "Parameter 'port' in event SCAD.22"
    ::= { scadEventObjects22 3 }

scadEventObjects23 OBJECT-IDENTITY
    STATUS current
    DESCRIPTION
        "Event SCAD.23
        A change ON/OFF has been make in Serial Control Signal Output."
    ::= { scadEventsGroup 23 }

scad23_message_type OBJECT-TYPE
    SYNTAX DisplayString
    MAX-ACCESS accessible-for-notify
    STATUS current
    DESCRIPTION
        "Parameter 'message_type' in event SCAD.23"
    ::= { scadEventObjects23 1 }

scad23_interface OBJECT-TYPE
    SYNTAX DisplayString
    MAX-ACCESS accessible-for-notify
    STATUS current
    DESCRIPTION
        "Parameter 'interface' in event SCAD.23"
    ::= { scadEventObjects23 2 }

scad23_state OBJECT-TYPE
    SYNTAX Integer32
    MAX-ACCESS accessible-for-notify
    STATUS current
    DESCRIPTION
        "Parameter 'state' in event SCAD.23"
    ::= { scadEventObjects23 3 }

scadEventObjects24 OBJECT-IDENTITY
    STATUS current
    DESCRIPTION
        "Event SCAD.24
        Data error from Serial Terminal has been received."
    ::= { scadEventsGroup 24 }

scad24_message_type OBJECT-TYPE
    SYNTAX DisplayString
    MAX-ACCESS accessible-for-notify
    STATUS current
    DESCRIPTION
        "Parameter 'message_type' in event SCAD.24"
    ::= { scadEventObjects24 1 }

scad24_interface OBJECT-TYPE
    SYNTAX DisplayString
    MAX-ACCESS accessible-for-notify
    STATUS current
    DESCRIPTION
        "Parameter 'interface' in event SCAD.24"
    ::= { scadEventObjects24 2 }

scad24_state OBJECT-TYPE
    SYNTAX Integer32
    MAX-ACCESS accessible-for-notify
    STATUS current
    DESCRIPTION
        "Parameter 'state' in event SCAD.24"
    ::= { scadEventObjects24 3 }

scadEventObjects25 OBJECT-IDENTITY
    STATUS current
    DESCRIPTION
        "Event SCAD.25
        TCP Listen has been closed, due max session number has been reached."
    ::= { scadEventsGroup 25 }

scad25_port OBJECT-TYPE
    SYNTAX Integer32
    MAX-ACCESS accessible-for-notify
    STATUS current
    DESCRIPTION
        "Parameter 'port' in event SCAD.25"
    ::= { scadEventObjects25 1 }

scadEventObjects26 OBJECT-IDENTITY
    STATUS current
    DESCRIPTION
        "Event SCAD.26
        An input TCP session has been rejet."
    ::= { scadEventsGroup 26 }

scad26_event OBJECT-TYPE
    SYNTAX DisplayString
    MAX-ACCESS accessible-for-notify
    STATUS current
    DESCRIPTION
        "Parameter 'event' in event SCAD.26"
    ::= { scadEventObjects26 1 }

scad26_ip OBJECT-TYPE
    SYNTAX IpAddress
    MAX-ACCESS accessible-for-notify
    STATUS current
    DESCRIPTION
        "Parameter 'ip' in event SCAD.26"
    ::= { scadEventObjects26 2 }

scad26_port OBJECT-TYPE
    SYNTAX Integer32
    MAX-ACCESS accessible-for-notify
    STATUS current
    DESCRIPTION
        "Parameter 'port' in event SCAD.26"
    ::= { scadEventObjects26 3 }

scadEventObjects27 OBJECT-IDENTITY
    STATUS current
    DESCRIPTION
        "Event SCAD.27
        Detailed Data send to serial interface."
    ::= { scadEventsGroup 27 }

scad27_interface OBJECT-TYPE
    SYNTAX DisplayString
    MAX-ACCESS accessible-for-notify
    STATUS current
    DESCRIPTION
        "Parameter 'interface' in event SCAD.27"
    ::= { scadEventObjects27 1 }

scad27_serial_address OBJECT-TYPE
    SYNTAX Integer32
    MAX-ACCESS accessible-for-notify
    STATUS current
    DESCRIPTION
        "Parameter 'serial_address' in event SCAD.27"
    ::= { scadEventObjects27 2 }

scad27_lenght OBJECT-TYPE
    SYNTAX Integer32
    MAX-ACCESS accessible-for-notify
    STATUS current
    DESCRIPTION
        "Parameter 'lenght' in event SCAD.27"
    ::= { scadEventObjects27 3 }

scad27_hex_data OBJECT-TYPE
    SYNTAX DisplayString
    MAX-ACCESS accessible-for-notify
    STATUS current
    DESCRIPTION
        "Parameter 'hex_data' in event SCAD.27"
    ::= { scadEventObjects27 4 }

scadEventObjects28 OBJECT-IDENTITY
    STATUS current
    DESCRIPTION
        "Event SCAD.28
        Detailed Data received from serial interface."
    ::= { scadEventsGroup 28 }

scad28_interface OBJECT-TYPE
    SYNTAX DisplayString
    MAX-ACCESS accessible-for-notify
    STATUS current
    DESCRIPTION
        "Parameter 'interface' in event SCAD.28"
    ::= { scadEventObjects28 1 }

scad28_serial_address OBJECT-TYPE
    SYNTAX Integer32
    MAX-ACCESS accessible-for-notify
    STATUS current
    DESCRIPTION
        "Parameter 'serial_address' in event SCAD.28"
    ::= { scadEventObjects28 2 }

scad28_lenght OBJECT-TYPE
    SYNTAX Integer32
    MAX-ACCESS accessible-for-notify
    STATUS current
    DESCRIPTION
        "Parameter 'lenght' in event SCAD.28"
    ::= { scadEventObjects28 3 }

scad28_hex_data OBJECT-TYPE
    SYNTAX DisplayString
    MAX-ACCESS accessible-for-notify
    STATUS current
    DESCRIPTION
        "Parameter 'hex_data' in event SCAD.28"
    ::= { scadEventObjects28 4 }

scadEventObjects29 OBJECT-IDENTITY
    STATUS current
    DESCRIPTION
        "Event SCAD.29
        Configured NSLA track has triggered."
    ::= { scadEventsGroup 29 }

scad29_state OBJECT-TYPE
    SYNTAX DisplayString
    MAX-ACCESS accessible-for-notify
    STATUS current
    DESCRIPTION
        "Parameter 'state' in event SCAD.29"
    ::= { scadEventObjects29 1 }

scad29_interface OBJECT-TYPE
    SYNTAX DisplayString
    MAX-ACCESS accessible-for-notify
    STATUS current
    DESCRIPTION
        "Parameter 'interface' in event SCAD.29"
    ::= { scadEventObjects29 2 }


scadNotification1 NOTIFICATION-TYPE
    OBJECTS { 
              scad1_bytes_number, 
              scad1_interface 
            }
    STATUS current
    DESCRIPTION
        "Notification of Event SCAD.1

        Message: 'Rx Data from Serial Terminal $1 bytes, interface $2'

        Parameters list:
              $1: scad1_bytes_number
              $2: scad1_interface

        Data has been received from Serial Terminal."
    ::= { scadNotificationsPrefix 1 }

scadNotification2 NOTIFICATION-TYPE
    OBJECTS { 
              scad2_coment, 
              scad2_serrial_address,
              scad2_bytes_number,
              scad2_interface,
              scad2_state 
            }
    STATUS current
    DESCRIPTION
        "Notification of Event SCAD.2

        Message: 'Rx Message$1 from Serial Terminal address $2, $3 bytes, interface $4 state $5'

        Parameters list:
              $1: scad2_coment
              $2: scad2_serrial_address
              $3: scad2_bytes_number
              $4: scad2_interface
              $5: scad2_state

        One OK Message has been received from Serial Terminal."
    ::= { scadNotificationsPrefix 2 }

scadNotification3 NOTIFICATION-TYPE
    OBJECTS { 
              scad3_bad_addr, 
              scad3_interface 
            }
    STATUS current
    DESCRIPTION
        "Notification of Event SCAD.3

        Message: 'Rx Address error from Serial Terminal $1 bytes, interface $2'

        Parameters list:
              $1: scad3_bad_addr
              $2: scad3_interface

        A Message with bad address has been received from Serial Terminal."
    ::= { scadNotificationsPrefix 3 }

scadNotification4 NOTIFICATION-TYPE
    OBJECTS { 
              scad4_cause, 
              scad4_interface,
              scad4_state 
            }
    STATUS current
    DESCRIPTION
        "Notification of Event SCAD.4

        Message: 'Rx Bad Message from Serial Terminal ($1), interface $2 state $3'

        Parameters list:
              $1: scad4_cause
              $2: scad4_interface
              $3: scad4_state

        One Bad Message has been received from Serial Terminal."
    ::= { scadNotificationsPrefix 4 }

scadNotification5 NOTIFICATION-TYPE
    OBJECTS { 
              scad5_interface, 
              scad5_state 
            }
    STATUS current
    DESCRIPTION
        "Notification of Event SCAD.5

        Message: 'A block with LRC/CRC error has been received from Serial Terminal, interface $1 state $2'

        Parameters list:
              $1: scad5_interface
              $2: scad5_state

        A message with LRC/CRC error has been received from Serial Terminal."
    ::= { scadNotificationsPrefix 5 }

scadNotification6 NOTIFICATION-TYPE
    OBJECTS { 
              scad6_error_type, 
              scad6_interface,
              scad6_state 
            }
    STATUS current
    DESCRIPTION
        "Notification of Event SCAD.6

        Message: 'A block with $1 error has been received from Serial Terminal, interface $2 state $3'

        Parameters list:
              $1: scad6_error_type
              $2: scad6_interface
              $3: scad6_state

        A message with error has been received from Remote."
    ::= { scadNotificationsPrefix 6 }

scadNotification7 NOTIFICATION-TYPE
    OBJECTS { 
              scad7_serial_address, 
              scad7_interface 
            }
    STATUS current
    DESCRIPTION
        "Notification of Event SCAD.7

        Message: 'Address $1 received from Serial Terminal is not included in configuration regiters. Interface $2'

        Parameters list:
              $1: scad7_serial_address
              $2: scad7_interface

        Addres received from Serial Terminal is not included in configuration
        registers list."
    ::= { scadNotificationsPrefix 7 }

scadNotification8 NOTIFICATION-TYPE
    OBJECTS { 
              scad8_serial_address, 
              scad8_rtu_ip_address,
              scad8_port,
              scad8_interface 
            }
    STATUS current
    DESCRIPTION
        "Notification of Event SCAD.8

        Message: 'Address $1 is trying the connection against IP $2 Host, Port $3, Interface $4'

        Parameters list:
              $1: scad8_serial_address
              $2: scad8_rtu_ip_address
              $3: scad8_port
              $4: scad8_interface

        It's trying the connection against remote IP and P port."
    ::= { scadNotificationsPrefix 8 }

scadNotification9 NOTIFICATION-TYPE
    OBJECTS { 
              scad9_interface 
            }
    STATUS current
    DESCRIPTION
        "Notification of Event SCAD.9

        Message: 'The Transfer has been completed successfully. Interface $1'

        Parameters list:
              $1: scad9_interface

        The Transfer has been completed successfully."
    ::= { scadNotificationsPrefix 9 }

scadNotification10 NOTIFICATION-TYPE
    OBJECTS { 
              scad10_bytes, 
              scad10_interface 
            }
    STATUS current
    DESCRIPTION
        "Notification of Event SCAD.10

        Message: 'Trying to send a message to Remote with $1 bytes. Interface $2'

        Parameters list:
              $1: scad10_bytes
              $2: scad10_interface

        Trying to send message to Remote end."
    ::= { scadNotificationsPrefix 10 }

scadNotification11 NOTIFICATION-TYPE
    OBJECTS { 
              scad11_message_type, 
              scad11_bytes,
              scad11_interface,
              scad11_state 
            }
    STATUS current
    DESCRIPTION
        "Notification of Event SCAD.11

        Message: 'A message from Remote of $1 type has been received, $2 bytes. Interface $3 state $4'

        Parameters list:
              $1: scad11_message_type
              $2: scad11_bytes
              $3: scad11_interface
              $4: scad11_state

        A message from Remote end has been received."
    ::= { scadNotificationsPrefix 11 }

scadNotification12 NOTIFICATION-TYPE
    OBJECTS { 
              scad12_message_type, 
              scad12_bytes,
              scad12_foreign_host,
              scad12_remote_port 
            }
    STATUS current
    DESCRIPTION
        "Notification of Event SCAD.12

        Message: 'A TCP packet $1 has been received, $2 bytes. rem. IP: $3, Port: $4'

        Parameters list:
              $1: scad12_message_type
              $2: scad12_bytes
              $3: scad12_foreign_host
              $4: scad12_remote_port

        A TCP Packet has been received."
    ::= { scadNotificationsPrefix 12 }

scadNotification13 NOTIFICATION-TYPE
    OBJECTS { 
              scad13_foreign_host, 
              scad13_remote_port 
            }
    STATUS current
    DESCRIPTION
        "Notification of Event SCAD.13

        Message: 'The TCP session has been closed. rem. IP: $1, Port: $2'

        Parameters list:
              $1: scad13_foreign_host
              $2: scad13_remote_port

        The TCP session has been closed."
    ::= { scadNotificationsPrefix 13 }

scadNotification14 NOTIFICATION-TYPE
    OBJECTS { 
              scad14_foreign_host, 
              scad14_remote_port 
            }
    STATUS current
    DESCRIPTION
        "Notification of Event SCAD.14

        Message: 'The TCP session has been closed by the Remote end. rem. IP: $1, Port: $2'

        Parameters list:
              $1: scad14_foreign_host
              $2: scad14_remote_port

        The TCP session has been closed by the Remote end."
    ::= { scadNotificationsPrefix 14 }

scadNotification15 NOTIFICATION-TYPE
    OBJECTS { 
              scad15_remote_ip, 
              scad15_remote_port 
            }
    STATUS current
    DESCRIPTION
        "Notification of Event SCAD.15

        Message: 'The TCP session has been opened by the Remote end. Remote IP:$1 , Port: $2'

        Parameters list:
              $1: scad15_remote_ip
              $2: scad15_remote_port

        The TCP session has been opened by the Remote end."
    ::= { scadNotificationsPrefix 15 }

scadNotification16 NOTIFICATION-TYPE
    OBJECTS { 
              scad16_address, 
              scad16_bytes,
              scad16_interface,
              scad16_state 
            }
    STATUS current
    DESCRIPTION
        "Notification of Event SCAD.16

        Message: 'Tx Message to Serial Terminal,address: $1, $2 bytes interface $3 state $4'

        Parameters list:
              $1: scad16_address
              $2: scad16_bytes
              $3: scad16_interface
              $4: scad16_state

        A Message has been transmitted to Serial Terminal."
    ::= { scadNotificationsPrefix 16 }

scadNotification17 NOTIFICATION-TYPE
    OBJECTS { 
              scad17_message_type, 
              scad17_interface,
              scad17_state 
            }
    STATUS current
    DESCRIPTION
        "Notification of Event SCAD.17

        Message: 'Serial Control Signal Imput change to $1, interface $2 state $3'

        Parameters list:
              $1: scad17_message_type
              $2: scad17_interface
              $3: scad17_state

        A change ON/OFF has been detected in Serial Control Signal Input."
    ::= { scadNotificationsPrefix 17 }

scadNotification18 NOTIFICATION-TYPE
    OBJECTS { 
              scad18_site, 
              scad18_interface,
              scad18_state 
            }
    STATUS current
    DESCRIPTION
        "Notification of Event SCAD.18

        Message: 'Timeout waiting data from $1, interface $2 state $3'

        Parameters list:
              $1: scad18_site
              $2: scad18_interface
              $3: scad18_state

        Timeout has occur waiting data."
    ::= { scadNotificationsPrefix 18 }

scadNotification19 NOTIFICATION-TYPE
    OBJECTS { 
              scad19_interface, 
              scad19_state 
            }
    STATUS current
    DESCRIPTION
        "Notification of Event SCAD.19

        Message: 'Packet lost due TCP Tx overrun error. Interface $1 state $2'

        Parameters list:
              $1: scad19_interface
              $2: scad19_state

        A packet was lost, due TCP Tx overrun error."
    ::= { scadNotificationsPrefix 19 }

scadNotification20 NOTIFICATION-TYPE
    OBJECTS { 
              scad20_interface, 
              scad20_state 
            }
    STATUS current
    DESCRIPTION
        "Notification of Event SCAD.20

        Message: 'Packet lost due TCP session is closes. Interface $1 state $2'

        Parameters list:
              $1: scad20_interface
              $2: scad20_state

        A packet was lost, due TCP is closed."
    ::= { scadNotificationsPrefix 20 }

scadNotification21 NOTIFICATION-TYPE
    OBJECTS { 
              scad21_na, 
              scad21_ip_host_address,
              scad21_cause,
              scad21_interface 
            }
    STATUS current
    DESCRIPTION
        "Notification of Event SCAD.21

        Message: 'The transfer has been wrong, against address $1, IP $2, Cause $3, interface $4'

        Parameters list:
              $1: scad21_na
              $2: scad21_ip_host_address
              $3: scad21_cause
              $4: scad21_interface

        The transfer has been wrong against specified NA and IP addr."
    ::= { scadNotificationsPrefix 21 }

scadNotification22 NOTIFICATION-TYPE
    OBJECTS { 
              scad22_event, 
              scad22_ip,
              scad22_port 
            }
    STATUS current
    DESCRIPTION
        "Notification of Event SCAD.22

        Message: 'The TCP event: $1 . Rem. IP: $2, rem. Port: $3'

        Parameters list:
              $1: scad22_event
              $2: scad22_ip
              $3: scad22_port

        TCP generic event was occurred."
    ::= { scadNotificationsPrefix 22 }

scadNotification23 NOTIFICATION-TYPE
    OBJECTS { 
              scad23_message_type, 
              scad23_interface,
              scad23_state 
            }
    STATUS current
    DESCRIPTION
        "Notification of Event SCAD.23

        Message: 'Serial Control Output change to $1, interface $2 state $3'

        Parameters list:
              $1: scad23_message_type
              $2: scad23_interface
              $3: scad23_state

        A change ON/OFF has been make in Serial Control Signal Output."
    ::= { scadNotificationsPrefix 23 }

scadNotification24 NOTIFICATION-TYPE
    OBJECTS { 
              scad24_message_type, 
              scad24_interface,
              scad24_state 
            }
    STATUS current
    DESCRIPTION
        "Notification of Event SCAD.24

        Message: 'Data ERROR from Serial Terminal has been received type: $1. Interface $2 state $3'

        Parameters list:
              $1: scad24_message_type
              $2: scad24_interface
              $3: scad24_state

        Data error from Serial Terminal has been received."
    ::= { scadNotificationsPrefix 24 }

scadNotification25 NOTIFICATION-TYPE
    OBJECTS { 
              scad25_port 
            }
    STATUS current
    DESCRIPTION
        "Notification of Event SCAD.25

        Message: 'Max sessions number has been reached, port $1'

        Parameters list:
              $1: scad25_port

        TCP Listen has been closed, due max session number has been reached."
    ::= { scadNotificationsPrefix 25 }

scadNotification26 NOTIFICATION-TYPE
    OBJECTS { 
              scad26_event, 
              scad26_ip,
              scad26_port 
            }
    STATUS current
    DESCRIPTION
        "Notification of Event SCAD.26

        Message: 'TCP inout session rejet: $1 . Rem. IP: $2, rem. Port: $3'

        Parameters list:
              $1: scad26_event
              $2: scad26_ip
              $3: scad26_port

        An input TCP session has been rejet."
    ::= { scadNotificationsPrefix 26 }

scadNotification27 NOTIFICATION-TYPE
    OBJECTS { 
              scad27_interface, 
              scad27_serial_address,
              scad27_lenght,
              scad27_hex_data 
            }
    STATUS current
    DESCRIPTION
        "Notification of Event SCAD.27

        Message: 'Data transmitted to serial interface $1 (addr:$2,$3 bytes):$4'

        Parameters list:
              $1: scad27_interface
              $2: scad27_serial_address
              $3: scad27_lenght
              $4: scad27_hex_data

        Detailed Data send to serial interface."
    ::= { scadNotificationsPrefix 27 }

scadNotification28 NOTIFICATION-TYPE
    OBJECTS { 
              scad28_interface, 
              scad28_serial_address,
              scad28_lenght,
              scad28_hex_data 
            }
    STATUS current
    DESCRIPTION
        "Notification of Event SCAD.28

        Message: 'Data received from serial interface $1 (addr:$2,$3 bytes):$4'

        Parameters list:
              $1: scad28_interface
              $2: scad28_serial_address
              $3: scad28_lenght
              $4: scad28_hex_data

        Detailed Data received from serial interface."
    ::= { scadNotificationsPrefix 28 }

scadNotification29 NOTIFICATION-TYPE
    OBJECTS { 
              scad29_state, 
              scad29_interface 
            }
    STATUS current
    DESCRIPTION
        "Notification of Event SCAD.29

        Message: 'Track nsla triggered(state:$1) ifc $2'

        Parameters list:
              $1: scad29_state
              $2: scad29_interface

        Configured NSLA track has triggered."
    ::= { scadNotificationsPrefix 29 }


END
