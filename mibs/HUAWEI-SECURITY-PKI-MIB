-- =============================================================================
-- Copyright (C) 2010 by HUAWEI TECHNOLOGIES. All rights reserved.
--    
-- Description:  
-- Reference: Huawei Enterprise MIB
-- Version: 1.0
-- History: 
--          V1.0 The initial version created by LiShengbai 90004270. 
-- =============================================================================

HUAWEI-SECURITY-PKI-MIB DEFINITIONS ::= BEGIN
 
	IMPORTS   
		    Gauge32, IpAddress, OBJECT-TYPE
			FROM SNMPv2-SMI 
    		enterprises			
		    FROM RFC1155-SMI 
            DateAndTime			
			FROM SNMPv2-TC;


    hwPKI MODULE-IDENTITY 
		        LAST-UPDATED "201003010900Z"        -- March 1, 2010 at 09:00 GMT
		        ORGANIZATION 
		            "Huawei Symantec Technologies Co., Ltd."
		        CONTACT-INFO 
		            "3rd Floor,Section D, Keshi Building, No.28, Xinxi Rd., Shangdi,
		         	 Hai-Dian District Beijing P.R. China
			         Zip:100085
			         Http://www.huaweisymantec.com
                     "
		        DESCRIPTION 
		            "V1.00
			         The PKI mib is for Eudemon and USG product series."

		        ::= { hwSecurity 34 }
           
		
-- ===============================================
-- Node definitions
-- ===============================================
	    
	    	-- 1.3.6.1.4.1.2011
		huawei OBJECT IDENTIFIER ::= { enterprises 2011 }
	        
		-- 1.3.6.1.4.1.2011.6
		huaweiUtility OBJECT IDENTIFIER ::= { huawei 6 }
	        
		-- 1.3.6.1.4.1.2011.6.122
		hwSecurity OBJECT IDENTIFIER ::= { huaweiUtility 122 }     
		       
		  
		hwPKINotification OBJECT IDENTIFIER ::= { hwPKI 0 }  
		hwPKITrapObject OBJECT IDENTIFIER ::= { hwPKINotification 1 }   
		hwPKITraps OBJECT IDENTIFIER ::= { hwPKINotification 2 }


-- ===============================================
-- TrapObject.
-- ===============================================
 	        	        		
 		    hwPKICrlUrl  OBJECT-TYPE
	        	SYNTAX OCTET STRING (SIZE (1..127)) 
	        	MAX-ACCESS accessible-for-notify
	        	STATUS current
	        	DESCRIPTION
	            		"the URL for getting CRL."
	        	::= { hwPKITrapObject 1 }     
	        	        
	        hwPKILdapIP OBJECT-TYPE
	        	SYNTAX IpAddress 
	        	MAX-ACCESS accessible-for-notify
	       	 	STATUS current
	        	DESCRIPTION
	            		"the IP address of LDAP server."
	        	::= { hwPKITrapObject 2 }
	        	
	    	hwPKILdapPort OBJECT-TYPE
	        	SYNTAX Gauge32
	        	MAX-ACCESS accessible-for-notify
	        	STATUS current
	        	DESCRIPTION
	            		"the port of LDAP server."
	        	::= { hwPKITrapObject 3 }   
	        	    	
	        hwPKILdapVersion OBJECT-TYPE
	        	SYNTAX Gauge32
	        	MAX-ACCESS accessible-for-notify
	        	STATUS current
	        	DESCRIPTION
	            		"the version of LDAP server."
	        	::= { hwPKITrapObject 4 }   
	        
	        hwPKICrlAttribute OBJECT-TYPE
	        	SYNTAX OCTET STRING (SIZE (1..63))
	        	MAX-ACCESS accessible-for-notify
	        	STATUS current
	        	DESCRIPTION
	            		"the attribute of CRL."
	        	::= { hwPKITrapObject 5 } 
	        
            
             hwPKICrlDN OBJECT-TYPE
	        	SYNTAX OCTET STRING (SIZE (1..127))
	        	MAX-ACCESS accessible-for-notify
	       	 	STATUS current
	        	DESCRIPTION
	            		"the distinguished name of CRL."
	        	::= { hwPKITrapObject 6 }   
	        	
	         hwPKICertUrl OBJECT-TYPE
	        	SYNTAX OCTET STRING (SIZE (1..127)) 
	            MAX-ACCESS accessible-for-notify
	       	 	STATUS current
	        	DESCRIPTION
	            		"the URL for getting certificate."
	        	::= { hwPKITrapObject 7 } 
        	
	         hwPKICertSaveName OBJECT-TYPE
	        	SYNTAX OCTET STRING (SIZE (5..63)) 
	            MAX-ACCESS accessible-for-notify
	       	 	STATUS current
	        	DESCRIPTION
	            		"the saved name of certificate."
	        	::= { hwPKITrapObject 8 }
	        
	         hwPKICertAttribute OBJECT-TYPE
	        	SYNTAX OCTET STRING (SIZE (1..63)) 
	            MAX-ACCESS accessible-for-notify
	       	 	STATUS current
	        	DESCRIPTION
	            		"the attribute of certificate."
	        	::= { hwPKITrapObject 9 }
	        	
	         hwPKICertDN OBJECT-TYPE
	        	SYNTAX OCTET STRING (SIZE (1..127)) 
	            MAX-ACCESS accessible-for-notify
	       	 	STATUS current
	        	DESCRIPTION
	            		"the distinguished name of certificate."
	        	::= { hwPKITrapObject 10 }
	        	
	         hwPKICACertStartTime OBJECT-TYPE
	        	SYNTAX  DateAndTime 
	            MAX-ACCESS accessible-for-notify
	       	 	STATUS current
	        	DESCRIPTION
	            		"the start time of CA certificate."
	        	::= { hwPKITrapObject 11 }
	        	
	         hwPKICACertFinishTime OBJECT-TYPE
	        	SYNTAX  DateAndTime 
	            MAX-ACCESS accessible-for-notify
	       	 	STATUS current
	        	DESCRIPTION
	            		"the finish time of CA certificate."
	        	::= { hwPKITrapObject 12 }	     
	        	         
	         hwPKICACertIssuer OBJECT-TYPE
	        	SYNTAX OCTET STRING (SIZE (1..1023)) 
	            MAX-ACCESS accessible-for-notify
	       	 	STATUS current
	        	DESCRIPTION
	            		"the issuer of CA certificate."
	        	::= { hwPKITrapObject 13 }   
	        	
	         hwPKICACertSubject OBJECT-TYPE
	        	SYNTAX OCTET STRING (SIZE (1..1023)) 
	            MAX-ACCESS accessible-for-notify
	       	 	STATUS current
	        	DESCRIPTION
	            		"the subject of CA certificate."
	        	::= { hwPKITrapObject 14 } 	
	        	
	         hwPKILocalCertStartTime OBJECT-TYPE
	        	SYNTAX  DateAndTime 
	            MAX-ACCESS accessible-for-notify
	       	 	STATUS current
	        	DESCRIPTION
	            		"the start time of local certificate."
	        	::= { hwPKITrapObject 15 }
	        	
	         hwPKILocalCertFinishTime OBJECT-TYPE
	        	SYNTAX  DateAndTime 
	            MAX-ACCESS accessible-for-notify
	       	 	STATUS current
	        	DESCRIPTION
	            		"the finish time of local certificate."
	        	::= { hwPKITrapObject 16 }
	        	
	         hwPKILocalCertIssuer OBJECT-TYPE
	        	SYNTAX OCTET STRING (SIZE (1..1023)) 
	            MAX-ACCESS accessible-for-notify
	       	 	STATUS current
	        	DESCRIPTION
	            		"the issuer of local certificate."
	        	::= { hwPKITrapObject 17 }
	        	
	         hwPKILocalCertSubject OBJECT-TYPE
	        	SYNTAX OCTET STRING (SIZE (1..1023)) 
	            MAX-ACCESS accessible-for-notify
	       	 	STATUS current
	        	DESCRIPTION
	            		"the subject of local certificate."
	        	::= { hwPKITrapObject 18 } 	
	        	
	         hwPKICrlStartTime OBJECT-TYPE
	        	SYNTAX  DateAndTime 
	            MAX-ACCESS accessible-for-notify
	       	 	STATUS current
	        	DESCRIPTION
	            		"the start time of CRL."
	        	::= { hwPKITrapObject 19 }
	        	
	         hwPKICrlFinishTime OBJECT-TYPE
	        	SYNTAX  DateAndTime 
	            MAX-ACCESS accessible-for-notify
	       	 	STATUS current
	        	DESCRIPTION
	            		"the finish time of CRL."
	        	::= { hwPKITrapObject 20 }	
	        	
	         hwPKICrlIssuer OBJECT-TYPE
	        	SYNTAX OCTET STRING (SIZE (1..1023))  
	            MAX-ACCESS accessible-for-notify
	       	 	STATUS current
	        	DESCRIPTION
	            		"the issuer of CRL."
	        	::= { hwPKITrapObject 21 }        		        		        
	        	
	         hwPKICMPUrl OBJECT-TYPE
	         	SYNTAX OCTET STRING (SIZE (1..128))
	         	MAX-ACCESS accessible-for-notify
	         	STATUS current
	         	DESCRIPTION
	            		"the url of the CMP server"
	         	::= { hwPKITrapObject 22 }	
	         	
	         hwPKICASubject OBJECT-TYPE
	         	SYNTAX OCTET STRING (SIZE (1..256))
	         	MAX-ACCESS accessible-for-notify
	         	STATUS current
	         	DESCRIPTION
	            		"the subject name of the CA"
	         	::= { hwPKITrapObject 23 }
	         	
	         hwPKICMPSessionName OBJECT-TYPE
	         	SYNTAX OCTET STRING (SIZE (1..32))
	         	MAX-ACCESS accessible-for-notify
	         	STATUS current
	         	DESCRIPTION
	            		"the name of the CMP session"
	         	::= { hwPKITrapObject 24 }	
	         	
	         hwPKISCEPUrl OBJECT-TYPE
	         	SYNTAX OCTET STRING (SIZE (1..128))
	         	MAX-ACCESS accessible-for-notify
	         	STATUS current
	         	DESCRIPTION
	            		"the url of the SCEP server"
	         	::= { hwPKITrapObject 25 }
	         	
	         hwPKIDomainName OBJECT-TYPE
	         	SYNTAX OCTET STRING (SIZE (1..32))
	         	MAX-ACCESS accessible-for-notify
	         	STATUS current
	         	DESCRIPTION
	            		"the name of the PKI domain"
	         	::= { hwPKITrapObject 26 }	
	         	
	         hwPKIKeyName OBJECT-TYPE
	         	SYNTAX OCTET STRING (SIZE (1..33))
	         	MAX-ACCESS accessible-for-notify
	         	STATUS current
	         	DESCRIPTION
	            		"the name of the RSA key pair"
	         	::= { hwPKITrapObject 27 }	
	         	
	         hwPKIKeyBit OBJECT-TYPE
	         	SYNTAX Gauge32
	        	MAX-ACCESS accessible-for-notify
	        	STATUS current
	        	DESCRIPTION
	            		"the bit of the RSA key pair"
	         	::= { hwPKITrapObject 28 }		        		        
-- ===============================================
-- definition of traps.      
-- ===============================================                        
	        hwPKIGetCrlSucHttp NOTIFICATION-TYPE
			OBJECTS { 
				hwPKICrlUrl
			        }
			STATUS     current
			DESCRIPTION
			    "Send the message when get crl successfully with HTTP."
			::= { hwPKITraps 1}           
			
			hwPKIGetCrlFailHttp NOTIFICATION-TYPE
			OBJECTS { 
				hwPKICrlUrl  
			        }
			STATUS     current
			DESCRIPTION
			    "Send the message when get crl unsuccessfully with HTTP."
			::= { hwPKITraps 2}  
			
	        hwPKIGetCrlSucLdap NOTIFICATION-TYPE
			OBJECTS { 
				hwPKILdapIP,
				hwPKILdapPort,
				hwPKICrlAttribute,
				hwPKICrlDN,
				hwPKILdapVersion
		      		}
			STATUS     current
			DESCRIPTION
			    "Send the message when get crl successfully with LDAP."
			::= { hwPKITraps 3}

	        hwPKIGetCrlFailLdap NOTIFICATION-TYPE
			OBJECTS { 
				hwPKILdapIP,
				hwPKILdapPort,		
				hwPKICrlAttribute,
				hwPKICrlDN,
				hwPKILdapVersion  
			        }
			STATUS     current
			DESCRIPTION
			    "Send the message when get crl unsuccessfully with LDAP."
			::= { hwPKITraps 4}

	        			
	        hwPKIGetCertSucHttp NOTIFICATION-TYPE
			OBJECTS { 
				hwPKICertUrl,
				hwPKICertSaveName  
			        }
			STATUS     current
			DESCRIPTION
			    "Send the message when get certificate successfully with HTTP."
			::= { hwPKITraps 5}

	        hwPKIGetCertFailHttp NOTIFICATION-TYPE
			OBJECTS { 
				hwPKICertUrl,
				hwPKICertSaveName  
			        }
			STATUS     current
			DESCRIPTION
			    "Send the message when get certificate unsuccessfully with HTTP."
			::= { hwPKITraps 6}

	        hwPKIGetCertSucLdap NOTIFICATION-TYPE
			OBJECTS { 
				hwPKILdapIP,
				hwPKILdapPort,			
				hwPKICertAttribute,
				hwPKICertDN,    
				hwPKILdapVersion,
				hwPKICertSaveName
				     }
			STATUS     current
			DESCRIPTION
			    "Send the message when get certificate successfully with LDAP."
			::= { hwPKITraps 7}
	        
	        hwPKIGetCertFailLdap NOTIFICATION-TYPE
			OBJECTS { 
				hwPKILdapIP,
				hwPKILdapPort,
				hwPKICertAttribute,
				hwPKICertDN,   
				hwPKILdapVersion,
				hwPKICertSaveName   
			        }
			STATUS     current
			DESCRIPTION
			    "Send the message when get certificate unsuccessfully with LDAP."
			::= { hwPKITraps 8}  
			
			hwPKICACertInvalid NOTIFICATION-TYPE
			OBJECTS { 
				hwPKICACertIssuer,
				hwPKICACertSubject, 
				hwPKICACertStartTime,
				hwPKICACertFinishTime
				     }
			STATUS     current
			DESCRIPTION
			    "Send the message when the CA certificate is invalid."
			::= { hwPKITraps 9}    
			
		    hwPKICACertValid NOTIFICATION-TYPE
			OBJECTS { 
				hwPKICACertIssuer,
				hwPKICACertSubject,    
				hwPKICACertStartTime,
				hwPKICACertFinishTime
				     }
			STATUS     current
			DESCRIPTION
			    "Send the message when the CA certificate is valid."
			::= { hwPKITraps 10}


	        hwPKICACertNearlyExpired NOTIFICATION-TYPE
			OBJECTS { 
				hwPKICACertIssuer,
				hwPKICACertSubject,   
				hwPKICACertStartTime,
				hwPKICACertFinishTime
				     }
			STATUS     current
			DESCRIPTION
			    "Send the message when the CA certificate is nearly expired."
			::= { hwPKITraps 11}   
			
			hwPKILocalCertInvalid NOTIFICATION-TYPE
			OBJECTS { 
				hwPKILocalCertIssuer,
				hwPKILocalCertSubject,  
				hwPKILocalCertStartTime,
				hwPKILocalCertFinishTime
				     }
			STATUS     current
			DESCRIPTION
			    "Send the message when the local certificate is invalid."
			::= { hwPKITraps 12}

	        hwPKILocalCertValid NOTIFICATION-TYPE
			OBJECTS { 
				hwPKILocalCertIssuer,
				hwPKILocalCertSubject,
				hwPKILocalCertStartTime,
				hwPKILocalCertFinishTime
				     }
			STATUS     current
			DESCRIPTION
			    "Send the message when the local certificate is valid."
			::= { hwPKITraps 13}


	        hwPKILocalCertNearlyExpired NOTIFICATION-TYPE
			OBJECTS { 
				hwPKILocalCertIssuer,
				hwPKILocalCertSubject,
				hwPKILocalCertStartTime,
				hwPKILocalCertFinishTime  
			        }
			STATUS     current
			DESCRIPTION
			    "Send the message when the local certificate is nearly expired."
			::= { hwPKITraps 14}

	        hwPKICrlInvalid NOTIFICATION-TYPE
			OBJECTS { 
				hwPKICrlIssuer,
				hwPKICrlStartTime,
				hwPKICrlFinishTime				  
			        }
			STATUS     current
			DESCRIPTION
			    "Send the message when the crl is invalid."
			::= { hwPKITraps 15}    
			
			hwPKICrlValid NOTIFICATION-TYPE
			OBJECTS { 
				hwPKICrlIssuer,
				hwPKICrlStartTime,
				hwPKICrlFinishTime
			        }
			STATUS     current
			DESCRIPTION
			    "Send the message when the crl is valid."
			::= { hwPKITraps 16}        
			
			hwPKICrlNearlyExpired NOTIFICATION-TYPE
			OBJECTS { 
				hwPKICrlIssuer,
				hwPKICrlStartTime,
				hwPKICrlFinishTime			  
				    }
			STATUS     current
			DESCRIPTION
			    "Send the message when the crl is nearly expired."
			::= { hwPKITraps 17}
	                  
			hwPKIRequestCertSucCmp NOTIFICATION-TYPE
			OBJECTS { 
				hwPKICMPUrl,
				hwPKICASubject,
				hwPKICMPSessionName			  
				    }
			STATUS     current
			DESCRIPTION
			    "Send the message when requesting local certificate through CMPv2 succeeded."
			::= { hwPKITraps 18}
 			                     
			hwPKIRequestCertFailCmp NOTIFICATION-TYPE
			OBJECTS { 
				hwPKICMPUrl,
				hwPKICASubject,
				hwPKICMPSessionName			  
				    }
			STATUS     current
			DESCRIPTION
			    "Send the message when requesting local certificate through CMPv2 failed."
			::= { hwPKITraps 19}
 			
                     
			hwPKIRequestCertSucScep NOTIFICATION-TYPE
			OBJECTS { 
				hwPKISCEPUrl,
				hwPKIDomainName			  
				    }
			STATUS     current
			DESCRIPTION
			    "Send the message when requesting local certificate through SCEP succeeded."
			::= { hwPKITraps 20}
 			                     
			hwPKIRequestCertFailScep NOTIFICATION-TYPE
			OBJECTS { 
				hwPKISCEPUrl,
				hwPKIDomainName			  
				    }
			STATUS     current
			DESCRIPTION
			    "Send the message when requesting local certificate through SCEP failed."
			::= { hwPKITraps 21}
 			                     
			hwPKIRsaHrpBackFail NOTIFICATION-TYPE
			OBJECTS { 
				hwPKIKeyName,
				hwPKIKeyBit		  
				    }
			STATUS     current
			DESCRIPTION
			    "Send the message when backing up the RSA key pair to the standby device failed."
			::= { hwPKITraps 22}
 			
	END
