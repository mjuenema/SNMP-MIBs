--
-- This SMIv2 module has been generated by smidump 0.4.8. Do not edit.
--

--
-- WARNING: this output may be incorrect due to significant parse errors
--

CISCO-OSPF-TRAP-CAPABILITY DEFINITIONS ::= BEGIN

IMPORTS
    ospfConfigErrorType, ospfLsdbApproachingOverflow, ospfLsdbOverflow, 
    ospfPacketSrc, ospfPacketType, ospfSetTrap, ospfTrapControlGroup
        FROM OSPF-TRAP-MIB
    MODULE-IDENTITY
        FROM SNMPv2-SMI;

ciscoOspfTrapCapability MODULE-IDENTITY
    LAST-UPDATED "200211240000Z"
    ORGANIZATION 
        "Cisco Systems, Inc."
    CONTACT-INFO 
        "Cisco Systems Customer Service
         
         Postal:    170 West Tasman Drive
                    San Jose, CA  95134,
                    USA
         
            Tel:    +1 800 553-NETS
         
         E-mail:    cs-ospf@cisco.com"
    DESCRIPTION 
        "Agent capabilities for the OSPF TRAP MIB."
    REVISION    "200211240000Z"
    DESCRIPTION 
        "Initial version of the MIB Module"
    ::= { ciscoAgentCapability 288 }


-- This has been an SMIv2 AGENT-CAPABILITIES node:
ciscoOspfTrapCapabilityV12R026S OBJECT-IDENTITY
    STATUS      current
    DESCRIPTION 
        "CISCO-OSPF-TRAP-MIB capabilites"
    ::= { ciscoOspfTrapCapability 1 }

END -- end of module CISCO-OSPF-TRAP-CAPABILITY.
