--
-- This SMIv2 module has been generated by smidump 0.4.8. Do not edit.
--

--
-- WARNING: this output may be incorrect due to significant parse errors
--

CISCO-LWAPP-PMIP-MIB DEFINITIONS ::= BEGIN

IMPORTS
    InetAddress, InetAddressType
        FROM INET-ADDRESS-MIB
    SnmpAdminString
        FROM SNMP-FRAMEWORK-MIB
    Counter32, Gauge32, Integer32, MODULE-IDENTITY, NOTIFICATION-TYPE, 
    OBJECT-TYPE, TimeTicks, Unsigned32
        FROM SNMPv2-SMI
    DisplayString, MacAddress, RowStatus, TimeInterval, TimeStamp, 
    TruthValue
        FROM SNMPv2-TC;

ciscoLwappPmipMIB MODULE-IDENTITY
    LAST-UPDATED "201112220000Z"
    ORGANIZATION 
        "Cisco Systems Inc."
    CONTACT-INFO 
        "        Cisco Systems,
         Customer Service
         
         Postal: 170 West Tasman Drive
         San Jose, CA  95134
         USA
         
         Tel: +1 800 553-NETS
         
         Email: cs-snmp@cisco.com"
    DESCRIPTION 
        "This MIB is intended to be implemented on all those
         devices operating as Central Controllers (CC) that
         terminate the Light Weight Access Point Protocol
         tunnel from Light-weight LWAPP Access Points.
         
         This MIB provides configuration and status information
         about local mobility anchor to which the controller has 
         the joined.                  
         
         The relationship between CC and the LWAPP APs
         can be depicted as follows:
         
         +......+     +......+     +......+           +......+
         +      +     +      +     +      +           +      +
         +  LMA +     + LMA  +     + LMA  +           + LMA  +
         +      +     +      +     +      +           +      +
         +......+     +......+     +......+           +......+
         ..            .             .                 .
         ..            .             .                 .
         .  .            .             .                 .
         .    .            .             .                 .
         .      .            .             .                 .
         .        .            .             .                 .
         +......+ +......+     +......+      +......+          +......+
         +      + +      +     +      +      +      +          +      +
         +  WLC + + WLC  +     + WLC  +      + WLC  +          + WLC  +
         +      + +      +     +      +      +      +          +      +
         +......+ +......+     +......+      +......+          +......+
         .              .             .                 .
         .  .              .             .                 .
         .    .              .             .                 .
         .      .              .             .                 .
         .        .              .             .                 .
         +......+ +......+     +......+      +......+          +......+
         +      + +      +     +      +      +      +          +      +
         +  AP  + +  AP  +     +  AP  +      +  AP  +          +  AP  +
         +      + +      +     +      +      +      +          +      +
         +......+ +......+     +......+      +......+          +......+
         .              .             .                 .
         .  .              .             .                 .
         .    .              .             .                 .
         .      .              .             .                 .
         .        .              .             .                 .
         +......+ +......+     +......+      +......+          +......+
         +      + +      +     +      +      +      +          +      +
         +  MN  + +  MN  +     +  MN  +      +  MN  +          +  MN  +
         +      + +      +     +      +      +      +          +      +
         +......+ +......+     +......+      +......+          +......+
         
         
         The LWAPP tunnel exists between the controller and
         the APs.  The MNs communicate with the APs through
         the protocol defined by the 802.11 standard.
         
         LWAPP APs, upon bootup, discover and join one of the
         controllers and the controller pushes the configuration,
         that includes the WLAN parameters, to the LWAPP APs.
         The APs then encapsulate all the 802.11 frames from
         wireless clients inside LWAPP frames and forward
         the LWAPP frames to the controller.
         
                            GLOSSARY
         
         Access Point ( AP )
         
         An entity that contains an 802.11 medium access
         control ( MAC ) and physical layer ( PHY ) interface
         and provides access to the distribution services via
         the wireless medium for associated clients.  
         
         LWAPP APs encapsulate all the 802.11 frames in
         LWAPP frames and sends it to the controller to which
         it is logically connected.
         
         Central Controller ( CC )
         
         The central entity that terminates the LWAPP protocol
         tunnel from the LWAPP APs.  Throughout this MIB,
         this entity also referred to as 'controller'. 
         
         Light Weight Access Point Protocol ( LWAPP ) 
         
         This is a generic protocol that defines the 
         communication between the Access Points and the
         Central Controller. 
         
         Mobile Node ( MN )
         
         A roaming 802.11 wireless device in a wireless
         network associated with an access point. 
         
         REFERENCE
         
         [1] Part 11 Wireless LAN Medium Access Control ( MAC )
         and Physical Layer ( PHY ) Specifications.
         
         [2] Draft-obara-capwap-lwapp-00.txt, IETF Light 
         Weight Access Point Protocol. "
    REVISION    "197001010000Z"
    DESCRIPTION 
        "Initial version of this MIB module. "
    ::= { ciscoMgmt 888 }


ciscoLwappPmipMIBObjects OBJECT IDENTIFIER
    ::= { ciscoLwappPmipMIB 0 }

ciscoLwappPmipGlobal OBJECT IDENTIFIER
    ::= { ciscoLwappPmipMIBObjects 1 }

cLPmipDomainName OBJECT-TYPE
    SYNTAX      SnmpAdminString
    MAX-ACCESS  read-write
    STATUS      current
    DESCRIPTION 
        "This object specifies the domain name to which the 
         controller belongs."
    ::= { ciscoLwappPmipGlobal 1 }

cLPmipMAGInterface OBJECT-TYPE
    SYNTAX      SnmpAdminString (SIZE(1..32))
    MAX-ACCESS  read-write
    STATUS      current
    DESCRIPTION 
        "This object specifies the interface to which the 
         LMAs communicate."
    ::= { ciscoLwappPmipGlobal 2 }

cLPmipMaxBindings OBJECT-TYPE
    SYNTAX      Unsigned32
    MAX-ACCESS  read-write
    STATUS      current
    DESCRIPTION 
        "This object indicates the number of binding updates sent 
         by the controller."
    ::= { ciscoLwappPmipGlobal 3 }

cLPmipBindingLifeTime OBJECT-TYPE
    SYNTAX      TimeTicks
    MAX-ACCESS  read-write
    STATUS      current
    DESCRIPTION 
        "This object indicates the lifetime of the binding entries 
         maintained by the controller."
    ::= { ciscoLwappPmipGlobal 4 }

cLPmipBindingRefreshTime OBJECT-TYPE
    SYNTAX      TimeTicks
    MAX-ACCESS  read-write
    STATUS      current
    DESCRIPTION 
        "This object indicates the refresh time for the binding entries
         maintained by the controller."
    ::= { ciscoLwappPmipGlobal 5 }

cLPmipBindingInitRetxTime OBJECT-TYPE
    SYNTAX      TimeTicks
    MAX-ACCESS  read-write
    STATUS      current
    DESCRIPTION 
        "This object indicates the initial timeout between proxy binding 
         updates if the proxy binding ack does not arrive at the controller."
    ::= { ciscoLwappPmipGlobal 6 }

cLPmipBindingMaxRetxTime OBJECT-TYPE
    SYNTAX      TimeTicks
    MAX-ACCESS  read-write
    STATUS      current
    DESCRIPTION 
        "This object indicates the maximum timeout between proxy binding 
         updates if the proxy binding ack does not arrive at the controller."
    ::= { ciscoLwappPmipGlobal 7 }

cLPmipReplayProtectionTimestamp OBJECT-TYPE
    SYNTAX      TimeStamp
    MAX-ACCESS  read-write
    STATUS      current
    DESCRIPTION 
        "This object specifies the maximum amount of time difference 
         between the timestamp in the received proxy binding ack and 
         the current time of the day."
    ::= { ciscoLwappPmipGlobal 8 }

cLPmipBriMinDelayTime OBJECT-TYPE
    SYNTAX      TimeTicks
    MAX-ACCESS  read-write
    STATUS      current
    DESCRIPTION 
        "This object specifies the minimum amount of time the 
         controller should wait before retransmitting the BRI message."
    ::= { ciscoLwappPmipGlobal 9 }

cLPmipBriMaxDelayTime OBJECT-TYPE
    SYNTAX      TimeTicks
    MAX-ACCESS  read-write
    STATUS      current
    DESCRIPTION 
        "This object specifies the maximum amount of time the controller 
         should wait before retransmitting the BRI message."
    ::= { ciscoLwappPmipGlobal 10 }

cLPmipBriRetries OBJECT-TYPE
    SYNTAX      Unsigned32
    MAX-ACCESS  read-write
    STATUS      current
    DESCRIPTION 
        "This object specifies the maximum number of times the controller 
         retransmits the BRI message before receiving the BRA message."
    ::= { ciscoLwappPmipGlobal 11 }

cLPmipMagApnName OBJECT-TYPE
    SYNTAX      SnmpAdminString
    MAX-ACCESS  read-write
    STATUS      current
    DESCRIPTION 
        "This object specifies the MAG APN name for PMIPv6 MAG on AP."
    ::= { ciscoLwappPmipGlobal 12 }

ciscoLwappPmipConfig OBJECT IDENTIFIER
    ::= { ciscoLwappPmipMIBObjects 2 }

cLPmipLmaTable OBJECT-TYPE
    SYNTAX      SEQUENCE OF CLPmipLmaEntry
    MAX-ACCESS  not-accessible
    STATUS      current
    DESCRIPTION 
        "This table represents the information about the
         details of local mobility anchors connected to 
         the controller."
    ::= { ciscoLwappPmipConfig 1 }

cLPmipLmaEntry OBJECT-TYPE
    SYNTAX      CLPmipLmaEntry
    MAX-ACCESS  not-accessible
    STATUS      current
    DESCRIPTION 
        "An entry in this table represents the details of
         local mobility anchors connected to the controller."
    INDEX       { cLPmipLmaName }
    ::= { cLPmipLmaTable 1 }

CLPmipLmaEntry ::= SEQUENCE {
    cLPmipLmaName           SnmpAdminString,
    cLPmipLmaIPAddrType     InetAddressType,
    cLPmipLmaIPAddr         InetAddress,
    cLPmipLmaRowStatus      RowStatus
}

cLPmipLmaName OBJECT-TYPE
    SYNTAX      SnmpAdminString
    MAX-ACCESS  read-create
    STATUS      current
    DESCRIPTION 
        "This object indicates the name of the
         LMA connected to the controller."
    ::= { cLPmipLmaEntry 1 }

cLPmipLmaIPAddrType OBJECT-TYPE
    SYNTAX      InetAddressType
    MAX-ACCESS  read-create
    STATUS      current
    DESCRIPTION 
        "This object indicates the LMA's IP address type,
         made available through cLPmipLmaIPAddr."
    ::= { cLPmipLmaEntry 2 }

cLPmipLmaIPAddr OBJECT-TYPE
    SYNTAX      InetAddress
    MAX-ACCESS  read-create
    STATUS      current
    DESCRIPTION 
        "This object indicates the LMA's IP address."
    ::= { cLPmipLmaEntry 3 }

cLPmipLmaRowStatus OBJECT-TYPE
    SYNTAX      RowStatus
    MAX-ACCESS  read-create
    STATUS      current
    DESCRIPTION 
        "This object is used to add or delete an entry in this table."
    ::= { cLPmipLmaEntry 4 }

cLPmipProfileTable OBJECT-TYPE
    SYNTAX      SEQUENCE OF CLPmipProfileEntry
    MAX-ACCESS  not-accessible
    STATUS      current
    DESCRIPTION 
        "This table represents the information about the
         details of PMIP profiles created on the controller."
    ::= { ciscoLwappPmipConfig 2 }

cLPmipProfileEntry OBJECT-TYPE
    SYNTAX      CLPmipProfileEntry
    MAX-ACCESS  not-accessible
    STATUS      current
    DESCRIPTION 
        "An entry in this table represents the details of
         PMIP profiles created on the controller."
    INDEX       { cLPmipProfileName }
    ::= { cLPmipProfileTable 1 }

CLPmipProfileEntry ::= SEQUENCE {
    cLPmipProfileName   SnmpAdminString
}

cLPmipProfileName OBJECT-TYPE
    SYNTAX      SnmpAdminString
    MAX-ACCESS  read-only
    STATUS      current
    DESCRIPTION 
        "This object indicates the name of the profile."
    ::= { cLPmipProfileEntry 1 }

cLPmipProfileNaiTable OBJECT-TYPE
    SYNTAX      SEQUENCE OF CLPmipProfileNaiEntry
    MAX-ACCESS  not-accessible
    STATUS      current
    DESCRIPTION 
        "This table represents the information about the
         details of PMIP profiles created in the controller."
    ::= { ciscoLwappPmipConfig 3 }

cLPmipProfileNaiEntry OBJECT-TYPE
    SYNTAX      CLPmipProfileNaiEntry
    MAX-ACCESS  not-accessible
    STATUS      current
    DESCRIPTION 
        "An entry in this table represents the details of
         PMIP profiles created in the controller."
    INDEX       { cLPmipProfileName, cLPmipProfileNai }
    ::= { cLPmipProfileNaiTable 1 }

CLPmipProfileNaiEntry ::= SEQUENCE {
    cLPmipProfileNai            SnmpAdminString,
    cLPmipProfileApn            SnmpAdminString,
    cLPmipProfileLmaName        SnmpAdminString,
    cLPmipProfileNaiRowStatus   RowStatus
}

cLPmipProfileNai OBJECT-TYPE
    SYNTAX      SnmpAdminString
    MAX-ACCESS  read-create
    STATUS      current
    DESCRIPTION 
        "This object indicates the name of the
         nai string assocaited with this profile."
    ::= { cLPmipProfileNaiEntry 1 }

cLPmipProfileApn OBJECT-TYPE
    SYNTAX      SnmpAdminString
    MAX-ACCESS  read-create
    STATUS      current
    DESCRIPTION 
        "This object indicates the name of the
         access point node connected to the controller."
    ::= { cLPmipProfileNaiEntry 2 }

cLPmipProfileLmaName OBJECT-TYPE
    SYNTAX      SnmpAdminString
    MAX-ACCESS  read-create
    STATUS      current
    DESCRIPTION 
        "This object indicates the name of the LMA 
         to which the profile is associated to."
    ::= { cLPmipProfileNaiEntry 3 }

cLPmipProfileNaiRowStatus OBJECT-TYPE
    SYNTAX      RowStatus
    MAX-ACCESS  read-create
    STATUS      current
    DESCRIPTION 
        "This object is used to add or delete an entry in this table."
    ::= { cLPmipProfileNaiEntry 4 }

cLPmipWlanTable OBJECT-TYPE
    SYNTAX      SEQUENCE OF CLPmipWlanEntry
    MAX-ACCESS  not-accessible
    STATUS      current
    DESCRIPTION 
        "This table represents the generic PMIP configuration for 
         a particular WLAN in a controller.
         
         This table has a one-to-one relationship with
         cLWlanConfigTable. There exist a row in this
         table corresponding to each row representing
         a WLAN in cLWlanConfigTable."
    ::= { ciscoLwappPmipConfig 4 }

cLPmipWlanEntry OBJECT-TYPE
    SYNTAX      CLPmipWlanEntry
    MAX-ACCESS  not-accessible
    STATUS      current
    DESCRIPTION 
        "Each entry in this table represents the generic PMIP
         configuration for a WLAN."
    INDEX       { cLWlanIndex }
    ::= { cLPmipWlanTable 1 }

CLPmipWlanEntry ::= SEQUENCE {
    cLPmipWlanProfileName   SnmpAdminString,
    cLPmipWlanMobilityType  INTEGER,
    cLPmipWlanDefaultRealm  SnmpAdminString
}

cLPmipWlanProfileName OBJECT-TYPE
    SYNTAX      SnmpAdminString
    MAX-ACCESS  read-write
    STATUS      current
    DESCRIPTION 
        "This object indicates the name of the
         profile associated to this WLAN."
    ::= { cLPmipWlanEntry 1 }

cLPmipWlanMobilityType OBJECT-TYPE
    SYNTAX      INTEGER { none(1), pmipv6(2) }
    MAX-ACCESS  read-write
    STATUS      current
    DESCRIPTION 
        "This object specifies the mobility type of the clients 
         associated to this particular WLAN."
    ::= { cLPmipWlanEntry 2 }

cLPmipWlanDefaultRealm OBJECT-TYPE
    SYNTAX      SnmpAdminString
    MAX-ACCESS  read-write
    STATUS      current
    DESCRIPTION 
        "This object indicates the name of the
         default realm associated to this WLAN."
    ::= { cLPmipWlanEntry 3 }

ciscoLwappPmipStatistics OBJECT IDENTIFIER
    ::= { ciscoLwappPmipMIBObjects 3 }

cLPmipLmaStatsTable OBJECT-TYPE
    SYNTAX      SEQUENCE OF CLPmipLmaStatsEntry
    MAX-ACCESS  not-accessible
    STATUS      current
    DESCRIPTION 
        "This table represents the information about the
         LMAs that are connected to the controller."
    ::= { ciscoLwappPmipStatistics 1 }

cLPmipLmaStatsEntry OBJECT-TYPE
    SYNTAX      CLPmipLmaStatsEntry
    MAX-ACCESS  not-accessible
    STATUS      current
    DESCRIPTION 
        "Each entry in this table provides statistical information
         about the Local Mobility Anchors that are connected to the 
         controller."
    INDEX       { cLPmipLmaName }
    ::= { cLPmipLmaStatsTable 1 }

CLPmipLmaStatsEntry ::= SEQUENCE {
    cLPmipLmaTotalBindings  Counter32,
    cLPmipLmaPbuSent        Counter32,
    cLPmipLmaPbaReceived    Counter32,
    cLPmipLmaPbriSent       Counter32,
    cLPmipLmaPbriReceived   Counter32,
    cLPmipLmaPbraSent       Counter32,
    cLPmipLmaPbraReceived   Counter32,
    cLPmipLmaNoOfHandoff    Counter32,
    cLPmipLmaPbuDropped     Counter32
}

cLPmipLmaTotalBindings OBJECT-TYPE
    SYNTAX      Counter32
    UNITS       "packets"
    MAX-ACCESS  read-only
    STATUS      current
    DESCRIPTION 
        "This object represents total number of bindings sent to the 
         LMA by the controller."
    ::= { cLPmipLmaStatsEntry 1 }

cLPmipLmaPbuSent OBJECT-TYPE
    SYNTAX      Counter32
    UNITS       "packets"
    MAX-ACCESS  read-only
    STATUS      current
    DESCRIPTION 
        "This object represents total number of proxy binding units
         sent to the LMA by the controller."
    ::= { cLPmipLmaStatsEntry 2 }

cLPmipLmaPbaReceived OBJECT-TYPE
    SYNTAX      Counter32
    UNITS       "packets"
    MAX-ACCESS  read-only
    STATUS      current
    DESCRIPTION 
        "This object represents total number of proxy binding acks 
         received for this LMA by the controller."
    ::= { cLPmipLmaStatsEntry 3 }

cLPmipLmaPbriSent OBJECT-TYPE
    SYNTAX      Counter32
    UNITS       "packets"
    MAX-ACCESS  read-only
    STATUS      current
    DESCRIPTION 
        "This object represents total number of pbri sent by the 
         controller to the LMA"
    ::= { cLPmipLmaStatsEntry 4 }

cLPmipLmaPbriReceived OBJECT-TYPE
    SYNTAX      Counter32
    UNITS       "packets"
    MAX-ACCESS  read-only
    STATUS      current
    DESCRIPTION 
        "This object represents total number of pbri received from 
         the LMA by the controller."
    ::= { cLPmipLmaStatsEntry 5 }

cLPmipLmaPbraSent OBJECT-TYPE
    SYNTAX      Counter32
    UNITS       "packets"
    MAX-ACCESS  read-only
    STATUS      current
    DESCRIPTION 
        "This object represents total number of pbra sent."
    ::= { cLPmipLmaStatsEntry 6 }

cLPmipLmaPbraReceived OBJECT-TYPE
    SYNTAX      Counter32
    UNITS       "packets"
    MAX-ACCESS  read-only
    STATUS      current
    DESCRIPTION 
        "This object represents total number of pbra received."
    ::= { cLPmipLmaStatsEntry 7 }

cLPmipLmaNoOfHandoff OBJECT-TYPE
    SYNTAX      Counter32
    UNITS       "packets"
    MAX-ACCESS  read-only
    STATUS      current
    DESCRIPTION 
        "This object represents number of hand offs between 
         the controller and the LMA."
    ::= { cLPmipLmaStatsEntry 8 }

cLPmipLmaPbuDropped OBJECT-TYPE
    SYNTAX      Counter32
    UNITS       "packets"
    MAX-ACCESS  read-only
    STATUS      current
    DESCRIPTION 
        "This object represents number of pbus dropped between 
         the controller and the LMA."
    ::= { cLPmipLmaStatsEntry 9 }

cLPmipClientInfoTable OBJECT-TYPE
    SYNTAX      SEQUENCE OF CLPmipClientInfoEntry
    MAX-ACCESS  not-accessible
    STATUS      current
    DESCRIPTION 
        "This table represents the PMIP information of the clients
         associated to this controller."
    ::= { ciscoLwappPmipStatistics 2 }

cLPmipClientInfoEntry OBJECT-TYPE
    SYNTAX      CLPmipClientInfoEntry
    MAX-ACCESS  not-accessible
    STATUS      current
    DESCRIPTION 
        "Each entry in this table represents the generic PMIP
         information for a client."
    INDEX       { cldcClientMacAddress }
    ::= { cLPmipClientInfoTable 1 }

CLPmipClientInfoEntry ::= SEQUENCE {
    cLPmipClientNai                 SnmpAdminString,
    cLPmipClientState               SnmpAdminString,
    cLPmipClientInterface           SnmpAdminString,
    cLPmipClientHomeAddressType     InetAddressType,
    cLPmipClientHomeAddress         InetAddress,
    cLPmipClientAtt                 INTEGER,
    cLPmipClientLocalLinkId         MacAddress,
    cLPmipClientLmaName             SnmpAdminString,
    cLPmipClientLifeTime            TimeTicks,
    cLPmipClientDomainName          SnmpAdminString,
    cLPmipClientUpKey               Unsigned32,
    cLPmipClientDownKey             Unsigned32
}

cLPmipClientNai OBJECT-TYPE
    SYNTAX      SnmpAdminString
    MAX-ACCESS  read-only
    STATUS      current
    DESCRIPTION 
        "This object indicates the name of the
         profile, the client is associated to."
    ::= { cLPmipClientInfoEntry 1 }

cLPmipClientState OBJECT-TYPE
    SYNTAX      SnmpAdminString
    MAX-ACCESS  read-only
    STATUS      current
    DESCRIPTION 
        "This object indicates the state of the PMIP client:
         null: binding doesn't exist
         init: binding created, Retx timer running for PBU, binding not yet 
               accepted from LMA, Tunnel/route is not yet setup
         active:  binding accepted by LMA, refresh timer running, Tunnel/route setup   
               complete. 
         refreshPending: Refresh timer expired and Retx timer running. PBU refresh
               sent, PBA not yet received from LMA, (Tunnel/route is already setup).
         disconnectingSt: Dereg reply is expected.  Retx  timer is   
               running, tunnel/route is still setup."
    ::= { cLPmipClientInfoEntry 2 }

cLPmipClientInterface OBJECT-TYPE
    SYNTAX      SnmpAdminString (SIZE(1..32))
    MAX-ACCESS  read-only
    STATUS      current
    DESCRIPTION 
        "This object indicates the interface to which the 
         client is associated."
    ::= { cLPmipClientInfoEntry 3 }

cLPmipClientHomeAddressType OBJECT-TYPE
    SYNTAX      InetAddressType
    MAX-ACCESS  read-only
    STATUS      current
    DESCRIPTION 
        "This object indicates the type of the Client's Home
         address made available through cLPmipClientHomeAddress."
    ::= { cLPmipClientInfoEntry 4 }

cLPmipClientHomeAddress OBJECT-TYPE
    SYNTAX      InetAddress
    MAX-ACCESS  read-only
    STATUS      current
    DESCRIPTION 
        "This object indicates the Home Address of the client."
    ::= { cLPmipClientInfoEntry 5 }

cLPmipClientAtt OBJECT-TYPE
    SYNTAX      INTEGER { reserved(0), logicalNetworkInterface(1), 
                    pointToPointInterface(2), ethernet(3), 
                    wirelessLan(4), wimax(5), threeGPPGERAN(6), 
                    threeGPPUTRAN(7), threeGPPETRAN(8), 
                    threeGPP2eHRPD(9), threeGPP2HRPD(10), 
                    threeGPP21xRTT(11), threeGPP2UMB(12) }
    MAX-ACCESS  read-only
    STATUS      current
    DESCRIPTION 
        "This object indicates the access technology type by which 
         the client is currently attached."
    ::= { cLPmipClientInfoEntry 6 }

cLPmipClientLocalLinkId OBJECT-TYPE
    SYNTAX      MacAddress
    MAX-ACCESS  read-only
    STATUS      current
    DESCRIPTION 
        "This object indicates the local link identifier of the client."
    ::= { cLPmipClientInfoEntry 7 }

cLPmipClientLmaName OBJECT-TYPE
    SYNTAX      SnmpAdminString
    MAX-ACCESS  read-only
    STATUS      current
    DESCRIPTION 
        "This object indicates the LMA to which the client is connected."
    ::= { cLPmipClientInfoEntry 8 }

cLPmipClientLifeTime OBJECT-TYPE
    SYNTAX      TimeTicks
    MAX-ACCESS  read-only
    STATUS      current
    DESCRIPTION 
        "This object indicates the duration of the PMIP client association."
    ::= { cLPmipClientInfoEntry 9 }

cLPmipClientDomainName OBJECT-TYPE
    SYNTAX      SnmpAdminString
    MAX-ACCESS  read-only
    STATUS      current
    DESCRIPTION 
        "This object indicates the domain to which the PMIP client is associated."
    ::= { cLPmipClientInfoEntry 10 }

cLPmipClientUpKey OBJECT-TYPE
    SYNTAX      Unsigned32
    MAX-ACCESS  read-only
    STATUS      current
    DESCRIPTION 
        "This object indicates the upstream key of the PMIP client."
    ::= { cLPmipClientInfoEntry 11 }

cLPmipClientDownKey OBJECT-TYPE
    SYNTAX      Unsigned32
    MAX-ACCESS  read-only
    STATUS      current
    DESCRIPTION 
        "This object indicates the downstream key of the PMIP client."
    ::= { cLPmipClientInfoEntry 12 }

END -- end of module CISCO-LWAPP-PMIP-MIB.
