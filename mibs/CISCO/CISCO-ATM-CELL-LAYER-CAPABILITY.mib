--
-- This SMIv2 module has been generated by smidump 0.4.8. Do not edit.
--

--
-- WARNING: this output may be incorrect due to significant parse errors
--

CISCO-ATM-CELL-LAYER-CAPABILITY DEFINITIONS ::= BEGIN

IMPORTS
    MODULE-IDENTITY
        FROM SNMPv2-SMI;

ciscoAtmCellLayerCapability MODULE-IDENTITY
    LAST-UPDATED "200301300000Z"
    ORGANIZATION 
        "Cisco Systems, Inc."
    CONTACT-INFO 
        "       Cisco Systems
         Customer Service
         
         Postal: 170 W Tasman Drive
         San Jose, CA  95134
         USA
         
         Tel: +1 800 553-NETS
         
         E-mail: cs-wanatm@cisco.com"
    DESCRIPTION 
        "The Agent Capabilities for 
         CISCO-ATM-CELL-LAYER-MIB.
         
         - cacLayerCapabilityAxsmV2R00 is for
           ATM Switch Service Module(AXSM).
         
         - cacLayerCapabilityAxsmeV2R0160 is for
           Enhanced AXSM(AXSM-E).
         
         - cacLayerCapabilityAxsmxgV4R00 is for
           10 Gig. AXSM(AXSM-XG)."
    REVISION    "200301300000Z"
    DESCRIPTION 
        "Added cacLayerCapabilityAxsmxgV4R00."
    REVISION    "200205140000Z"
    DESCRIPTION 
        "Initial version of this MIB module."
    ::= { ciscoAgentCapability 275 }


-- This has been an SMIv2 AGENT-CAPABILITIES node:
cacLayerCapabilityAxsmV2R00 OBJECT-IDENTITY
    STATUS      current
    DESCRIPTION 
        "CISCO-ATM-CELL-LAYER-MIB Capabilities for
         AXSM Service Module."
    ::= { ciscoAtmCellLayerCapability 1 }

-- This has been an SMIv2 AGENT-CAPABILITIES node:
cacLayerCapabilityAxsmeV2R0160 OBJECT-IDENTITY
    STATUS      current
    DESCRIPTION 
        "CISCO-ATM-CELL-LAYER-MIB Capabilities for
         Enhanced AXSM(AXSM-E) Service Module."
    ::= { ciscoAtmCellLayerCapability 2 }

-- This has been an SMIv2 AGENT-CAPABILITIES node:
cacLayerCapabilityAxsmxgV4R00 OBJECT-IDENTITY
    STATUS      current
    DESCRIPTION 
        "CISCO-ATM-CELL-LAYER-MIB Capabilities for
         10 Gig. AXSM Service Module (AXSM-XG)."
    ::= { ciscoAtmCellLayerCapability 3 }

END -- end of module CISCO-ATM-CELL-LAYER-CAPABILITY.
