--
-- This SMIv2 module has been generated by smidump 0.4.8. Do not edit.
--

--
-- WARNING: this output may be incorrect due to significant parse errors
--

CISCO-OSPF-CAPABILITY DEFINITIONS ::= BEGIN

IMPORTS
    ospfASBdrRtrStatus, ospfAdminStat, ospfAreaAggregateEffect, 
    ospfAreaAggregateGroup, ospfAreaAggregateStatus, ospfAreaGroup, 
    ospfAreaStatus, ospfAreaSummary, ospfAuthType, ospfBasicGroup, 
    ospfDemandExtensions, ospfExitOverflowInterval, ospfExtLsdbGroup, 
    ospfExtLsdbLimit, ospfHostGroup, ospfHostMetric, ospfHostStatus, 
    ospfIfAdminStat, ospfIfAreaId, ospfIfAuthKey, ospfIfAuthType, 
    ospfIfDemand, ospfIfGroup, ospfIfHelloInterval, ospfIfMetricGroup, 
    ospfIfMetricStatus, ospfIfMetricValue, ospfIfMulticastForwarding, 
    ospfIfPollInterval, ospfIfRetransInterval, ospfIfRtrDeadInterval, 
    ospfIfRtrPriority, ospfIfStatus, ospfIfTransitDelay, ospfIfType, 
    ospfImportAsExtern, ospfLsdbGroup, ospfMulticastExtensions, 
    ospfNbmaNbrStatus, ospfNbrGroup, ospfNbrPriority, ospfRouterId, 
    ospfStubAreaGroup, ospfStubMetric, ospfStubMetricType, 
    ospfStubStatus, ospfTOSSupport, ospfVirtIfAuthKey, 
    ospfVirtIfAuthType, ospfVirtIfGroup, ospfVirtIfHelloInterval, 
    ospfVirtIfRetransInterval, ospfVirtIfRtrDeadInterval, 
    ospfVirtIfStatus, ospfVirtIfTransitDelay, ospfVirtNbrGroup
        FROM OSPF-MIB
    MODULE-IDENTITY
        FROM SNMPv2-SMI;

ciscoOspfCapability MODULE-IDENTITY
    LAST-UPDATED "200704260000Z"
    ORGANIZATION 
        "Cisco Systems, Inc."
    CONTACT-INFO 
        "	Cisco Systems
         Customer Service
         
         Postal:	170 West Tasman Drive
         San Jose, CA  95134
         USA
         
         Tel:	+1 800 553-NETS
         
         E-mail:	cs-ospf@cisco.com"
    DESCRIPTION 
        "Agent capabilities for the OSPF MIB."
    REVISION    "200704260000Z"
    DESCRIPTION 
        "Updated the ACCESS definition for 
         ospfIfAuthKey, ospfIfStatus, 
         ospfIfMulticastForwarding, ospfIfDemand,
         ospfIfAuthType, ospfVirtIfAuthKey and 
         ospfVirtIfAuthType"
    REVISION    "200211260000Z"
    DESCRIPTION 
        "Initial version of the MIB Module"
    ::= { ciscoAgentCapability 287 }


-- This has been an SMIv2 AGENT-CAPABILITIES node:
ciscoOspfCapabilityV12R025S OBJECT-IDENTITY
    STATUS      current
    DESCRIPTION 
        "CISCO-OSPF-MIB capabilites"
    ::= { ciscoOspfCapability 1 }

END -- end of module CISCO-OSPF-CAPABILITY.
