--
-- This SMIv2 module has been generated by smidump 0.4.8. Do not edit.
--

--
-- WARNING: this output may be incorrect due to significant parse errors
--

CISCO-ATM-PVCTRAP-EXTN-CAPABILITY DEFINITIONS ::= BEGIN

IMPORTS
    MODULE-IDENTITY
        FROM SNMPv2-SMI;

ciscoATMPVCTRAPExtnCapability MODULE-IDENTITY
    LAST-UPDATED "200211060000Z"
    ORGANIZATION 
        "Cisco Systems, Inc."
    CONTACT-INFO 
        "       Cisco Systems
         Customer Service
         
         Postal: 170 W Tasman Drive
         San Jose, CA  95134
         USA
         
         Tel: +1 800 553-NETS
         
         E-mail: cs-atm@cisco.com"
    DESCRIPTION 
        "The Agent Capabilities for 
         CISCO-ATM-PVCTRAP-EXTN-MIB."
    REVISION    "200211060000Z"
    DESCRIPTION 
        "Initial version of the MIB Module."
    ::= { ciscoAgentCapability 289 }


-- This has been an SMIv2 AGENT-CAPABILITIES node:
ciscoATMPVCTRAPExtnCapabilityV12R00S OBJECT-IDENTITY
    STATUS      current
    DESCRIPTION 
        "CISCO-ATM-PVCTRAP-EXTN-MIB Capabilities"
    ::= { ciscoATMPVCTRAPExtnCapability 1 }

END -- end of module CISCO-ATM-PVCTRAP-EXTN-CAPABILITY.
