--
-- ==================================================================
--  Copyright © 1999 - 2006 Siemens Network Convergence LLC
--
--  All Rights Reserved.
--
--  Reproduction of this document is authorized on condition that
--  this copyright notice is included.
--
--  This MIB document embodies proprietary intellectual property. 
--  of Siemens Network Convergence LLC, which retains all title and
--  ownership in this MIB, including any revisions.
--
--  This module will be extended, as required.
--
--  Siemens Network Convergence LLC reserves the right to make 
--  changes in specification and other information contained in this 
--  document without prior notice. The reader should consult 
--  Siemens Network Convergence LLC to determine whether any such
--  changes have been made.
--
--  Copyright © 1999 - 2006 Siemens Network Convergence LLC
-- ==================================================================
--
-- ==================================================================
-- Revision History
--  02/28/2005    Emilio Negron      Added new sysObjectIDs for the
--                                   Communication, Presence, and
--                                   Comm + Presence combo servers.
--  06/12/08     C. Chatzidimitriou  updated MIB to be fully compatible with SNMPv2
-- ==================================================================

-- **************************************************************************

SURPASS-RTP-PRODUCTS-MIB DEFINITIONS ::= BEGIN

-- **************************************************************************
IMPORTS
    MODULE-IDENTITY,OBJECT-IDENTITY
       FROM SNMPv2-SMI
    surpassRtp                           
       FROM SURPASS-RTP-MIB;   
       
-- **************************************************************************

--
--  Surpass RTP related HiQ MOs
--

    surpassRtpProducts MODULE-IDENTITY
        LAST-UPDATED "200806111500Z"
        ORGANIZATION "Siemens Network Convergence LLC"
        CONTACT-INFO " "
        DESCRIPTION
            "The MIB module describes the top level sysObjectID 
             registry for Siemens Surpass RTP-based products."
             
        REVISION "200806111500Z"    
        DESCRIPTION
            "Updated the MIB to be fully compatible with SNMPv2"

        ::= { surpassRtp 1 }

	hiq8000 OBJECT-IDENTITY
        STATUS current
        DESCRIPTION
            "The sysObjectID for the hiQ8000 product."
        ::= { surpassRtpProducts 1 }

	hiPath OBJECT-IDENTITY
        STATUS current
        DESCRIPTION
            "The sysObjectID for the hiPath product."
        ::= { surpassRtpProducts 2 }

END
